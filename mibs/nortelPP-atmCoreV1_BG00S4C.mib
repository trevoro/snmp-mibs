Nortel-Magellan-Passport-AtmCoreMIB
DEFINITIONS ::= BEGIN



IMPORTS

      OBJECT-TYPE
   FROM RFC-1212

      components,
      passportMIBs
   FROM Nortel-Magellan-Passport-UsefulDefinitionsMIB

      Counter32,
      DisplayString,
      StorageType,
      RowStatus,
      PassportCounter64,
      Gauge32,
      Integer32,
      Unsigned32
   FROM Nortel-Magellan-Passport-StandardTextualConventionsMIB

      AsciiString,
      Hex,
      NonReplicated,
      Link,
      AsciiStringIndex,
      IntegerSequence
   FROM Nortel-Magellan-Passport-TextualConventionsMIB;




-- LAST-UPDATED   "9906090000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     AtmCore Enterprise MIB."

atmCoreMIB OBJECT IDENTIFIER ::= { passportMIBs 123 }










-- AtmInterface/n
-- An AtmIf component is provisioned for each ATM interface. It 
-- manages the set of ATM connections that terminate at or traverse 
-- the interface.

atmIf OBJECT IDENTIFIER ::= { components 114 }



atmIfRowStatusTable OBJECT-TYPE
   SYNTAX     SEQUENCE OF AtmIfRowStatusEntry
   ACCESS     not-accessible
   STATUS     mandatory
   DESCRIPTION
     "This entry controls the addition and deletion of 
      atmIf components."
::= { atmIf 1 }

atmIfRowStatusEntry OBJECT-TYPE
   SYNTAX     AtmIfRowStatusEntry
   ACCESS     not-accessible
   STATUS     mandatory
   DESCRIPTION
     "A single entry in the table represents a single 
      atmIf component."
   INDEX {
      atmIfIndex }
::= { atmIfRowStatusTable 1 }

AtmIfRowStatusEntry ::= SEQUENCE {
   atmIfRowStatus
      RowStatus,
   atmIfComponentName
      DisplayString,
   atmIfStorageType
      StorageType,
   atmIfIndex
      Integer32 }

atmIfRowStatus OBJECT-TYPE
   SYNTAX     RowStatus 
   ACCESS     read-write
   STATUS     mandatory
   DESCRIPTION
     "This variable is used as the basis for SNMP naming of
      atmIf components.
      These components can be added and deleted."
::= { atmIfRowStatusEntry 1 }

atmIfComponentName OBJECT-TYPE
   SYNTAX     DisplayString 
   ACCESS     read-only
   STATUS     mandatory
   DESCRIPTION
     "This variable provides the component's string name for
      use with the ASCII Console Interface"
::= { atmIfRowStatusEntry 2 }

atmIfStorageType OBJECT-TYPE
   SYNTAX     StorageType 
   ACCESS     read-only
   STATUS     mandatory
   DESCRIPTION
     "This variable represents the storage type value for the
      atmIf tables."
::= { atmIfRowStatusEntry 4 }

atmIfIndex OBJECT-TYPE
   SYNTAX     Integer32 (1..1024)
   ACCESS     not-accessible
   STATUS     mandatory
   DESCRIPTION
     "This variable represents the index for the atmIf tables."
::= { atmIfRowStatusEntry 10 }

atmIfCidDataTable OBJECT-TYPE
   SYNTAX     SEQUENCE OF AtmIfCidDataEntry
   ACCESS     not-accessible
   STATUS     mandatory
   DESCRIPTION
     "This group contains the attribute for a component's Customer 
      Identifier (CID). Refer to the attribute description for a detailed 
      explanation of CIDs."
::= { atmIf 100 }

atmIfCidDataEntry OBJECT-TYPE
   SYNTAX     AtmIfCidDataEntry
   ACCESS     not-accessible
   STATUS     mandatory
   DESCRIPTION
     "An entry in the atmIfCidDataTable."
   INDEX {
      atmIfIndex }
::= { atmIfCidDataTable 1 }

AtmIfCidDataEntry ::= SEQUENCE {
   atmIfCustomerIdentifier
      Unsigned32 }

atmIfCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { atmIfCidDataEntry 1 }

atmIfProvTable OBJECT-TYPE
   SYNTAX     SEQUENCE OF AtmIfProvEntry
   ACCESS     not-accessible
   STATUS     mandatory
   DESCRIPTION
     "This group contains provisionable attributes for the AtmIf 
      component."
::= { atmIf 110 }

atmIfProvEntry OBJECT-TYPE
   SYNTAX     AtmIfProvEntry
   ACCESS     not-accessible
   STATUS     mandatory
   DESCRIPTION
     "An entry in the atmIfProvTable."
   INDEX {
      atmIfIndex }
::= { atmIfProvTable 1 }

AtmIfProvEntry ::= SEQUENCE {
   atmIfInterfaceName
      Link,
   atmIfType
      INTEGER,
   atmIfOamSegmentBoundary
      INTEGER,
   atmIfMaxVpcs
      Unsigned32,
   atmIfMaxVccs
      Unsigned32,
   atmIfTrafficShaping
      INTEGER,
   atmIfUnshapedTransmitQueueing
      INTEGER,
   atmIfUsageParameterControl
      INTEGER,
   atmIfMaxVpiBits
      Unsigned32,
   atmIfRemoteAtmInterfaceLabel
      AsciiString,
   atmIfTxCellMemory
      Unsigned32,
   atmIfFaultHoldOffTime
      INTEGER }

atmIfInterfaceName OBJECT-TYPE
   SYNTAX     Link 
   ACCESS     read-write
   STATUS     mandatory
   DESCRIPTION
     "This attribute associates the AtmIf component with a specific 
      interface on a Function Processorfor example, Lp/1 Ds3/0. This 
      implicitly defines the logical processor on which the AtmIf is 
      activated."
::= { atmIfProvEntry 10 }

atmIfType OBJECT-TYPE
   SYNTAX     INTEGER  {
                 uni(0),
                 ppi(1) }
   ACCESS     read-write
   STATUS     obsolete
   DESCRIPTION
     "This attribute indicates the type of AtmIf, either uni or ppi. These 
      types differ only in their handling of OAM cellsall connections 
      passing through a uni interface terminate segment loopback cells; 
      whereas a ppi interface permits these cells to be passed 
      transparently. This is obsoleted. The value is migrated into 
      oamSegmentBoundary.
      
      uni maps to yes. ppi maps to no."
   DEFVAL     { uni }
::= { atmIfProvEntry 20 }

atmIfOamSegmentBoundary OBJECT-TYPE
   SYNTAX     INTEGER  {
                 no(0),
                 yes(1) }
   ACCESS     read-write
   STATUS     mandatory
   DESCRIPTION
     "This attribute specifies whether the interface is on an OAM segment 
      boundary. 
      
      When yes is selected, the interface is on an OAM segment boundary 
      and all connections passing through the interface terminate OAM 
      segment cells. 
      
      When no is selected, the interface is not on an OAM segment 
      boundary and the interface permits the segment cells to be passed 
      transparently."
   DEFVAL     { yes }
::= { atmIfProvEntry 30 }

atmIfMaxVpcs OBJECT-TYPE
   SYNTAX     Unsigned32 (0..255)
   ACCESS     read-write
   STATUS     obsolete
   DESCRIPTION
     "This attribute specifies the maximum number of VPCs that can be 
      configured on this AtmIf. The value must not exceed the total 
      number of usable VPCs supported by this AtmIf (which is equal to 
      256 or (256 - (number of VPIs used for VCCs)), according to the 
      ConnectionMapping component).
      
      Furthermore, if the AtmIf is linked to an LogicalProcessor of 
      cardType other than 3pE3Atm, 3pDS3Atm, 3pOC3MmAtm, 
      3pOC3SmAtm, 3pE1Atm, 3pDS1Atm, 2pJ6MAtm, the sum of 
      (maxVccs + maxVpcs + 1) across all AtmIf linked to that Lp must be 
      less than or equal to the totalConnectionPoolCapacity attribute of 
      the Arc component. If the Arc component doesn't exist, the default 
      value of totalConnectionPoolCapacity is used as the limit.
      
      This attribute has been migrated to the Ca component."
   DEFVAL     { 128 }
::= { atmIfProvEntry 40 }

atmIfMaxVccs OBJECT-TYPE
   SYNTAX     Unsigned32 (0..16384)
   ACCESS     read-write
   STATUS     obsolete
   DESCRIPTION
     "This attribute specifies the maximum number of usable VCCs that 
      can be configured on this AtmIf. The value must not exceed the 
      number of non-reserved VCC identifiers in the Vcc space supported 
      by this AtmIf (which is specified by the ConnectionMapping 
      component).
      
      Furthermore, if the AtmIf is linked to an LogicalProcessor of 
      cardType other than 3pE3Atm, 3pDS3Atm, 3pOC3MmAtm, 
      3pOC3SmAtm, 3pE1Atm, 3pDS1Atm, 2pJ6MAtm, the sum of 
      (maxVccs + maxVpcs + 1) across all AtmIf linked to that Lp must be 
      less than the totalConnectionPoolCapacity attribute of the Arc 
      component. If the Arc component doesn't exist, the default value of 
      totalConnectionPoolCapacity is used as the limit.
      
      This attribute has been migrated to the Ca component."
   DEFVAL     { 255 }
::= { atmIfProvEntry 50 }

atmIfTrafficShaping OBJECT-TYPE
   SYNTAX     INTEGER  {
                 enabled(0),
                 disabled(1) }
   ACCESS     read-write
   STATUS     obsolete
   DESCRIPTION
     "It is migrated in P6.0 to a combination of the trafficShaping 
      attributes and the emissionPriority attributes under each ATM 
      service category component of the AtmIf CA.
      
      This attribute defines whether traffic shaping is enabled or disabled 
      for the entire AtmIf. When this attribute is set to enabled, each 
      provisioned connection under the interface can be individually 
      provisioned to permit or prohibit traffic shaping. When this attribute 
      is set to disabled, no traffic shaping is performed on the transmit 
      path for any of the connections. This attribute may be set to enabled 
      if the interface supports shaping, as defined by the 
      perVcQueueInterfaces attribute in the AtmResourceControl 
      component. If the AtmResourceControl component does not exist, 
      this attribute may not be set to enabled."
   DEFVAL     { disabled }
::= { atmIfProvEntry 60 }

atmIfUnshapedTransmitQueueing OBJECT-TYPE
   SYNTAX     INTEGER  {
                 perVc(0),
                 common(1),
                 autoConfigure(2) }
   ACCESS     read-write
   STATUS     obsolete
   DESCRIPTION
     "It is migrated in P6.0 to the attributes of the same name under each 
      ATM service category component of the AtmIf CA.
      
      This attribute applies only for unshaped VCC and VPC 
      connections. This attribute defines the transmit queueing method for 
      all unshaped connections under this AtmIf. Per-VC queueing means 
      that unshaped connections are treated with the same fairness as 
      shaped queues in the transmit round-robin scheduling. The 
      alternative to per-VC queueing is to use the common queue for a 
      particular service category (medium or low priority). The common 
      queue is only counted as one queue in the transmit round-robin 
      scheduling. Thus, if there are multiple connections which are 
      destined for the common queue, they are not fairly allocated a 
      portion of the transmit bandwidth compared to shaped connections. 
      
      When this attribute is set to perVc, any unshaped connection is 
      allocated its own per-VC queue, and is treated with the same 
      fairness as any shaped connections. Per-VC queues have a 
      maximum rate of 58,962 cell/s (25 Mbit/s) in a multi-port shaping 
      configuration. Per-VC queues also have their own congestion 
      control level. This means that total number of cell/frame blocks 
      allocated for several per-VC queues are higher than would be 
      allowed on the common queue. This can be an advantage in 
      reducing cell loss due to queue congestion. This attribute may only 
      be set to perVc if the interface supports per-VC queueing, (specified 
      by the perVcQueueInterfaces attribute in the AtmResourceControl 
      component).
      
      When this attribute is set to common, any unshaped connection is 
      destined for the common queue. The common queue has one set of 
      congestion control levels for all cells enqueued on it. The common 
      queue is only allocated one queue position when scheduling which 
      queue to transmit from. Due to the possibility of unfairness, this 
      value is only recommended in cases where the configuration cannot 
      otherwise achieve full link utilization. 
      
      When this attribute is set to autoConfigure and the interface 
      support per-VC queueing (specified by the perVcQueueInterfaces 
      attribute in the AtmResourceControl component) per-VC queueing 
      is enabled for all unshaped connections. Otherwise, the common 
      queue is used. The unshapedTransmitQueueingOper attribute 
      indicates whether the transmit queueing is perVc or common."
   DEFVAL     { autoConfigure }
::= { atmIfProvEntry 70 }

atmIfUsageParameterControl OBJECT-TYPE
   SYNTAX     INTEGER  {
                 enabled(0),
                 disabled(1) }
   ACCESS     read-write
   STATUS     obsolete
   DESCRIPTION
     "It is migrated in P6.0 to the attributes of the same name under each 
      ATM service category component of the AtmIf CA.
      
      This attribute defines whether usage parameter control (UPC) is 
      enabled or disabled for receive traffic for Vcc and Vpc connections 
      for this entire AtmIf. When this attribute is set to enabled, each 
      provisioned connection under the interface can be individually 
      provisioned to enforce or ignore UPC. When this attribute is set to 
      disabled, UPC cannot be enabled on the receive path for any of the 
      connections."
   DEFVAL     { disabled }
::= { atmIfProvEntry 80 }

atmIfMaxVpiBits OBJECT-TYPE
   SYNTAX     Unsigned32 (8 | 12)
   ACCESS     read-write
   STATUS     mandatory
   DESCRIPTION
     "This attribute specifies the maximum number of VPI bits that may 
      be active for this AtmIf. These bits start at the least significant bit 
      position and are contiguous. In general, the maximum VPI which 
      may be used on the interface is 2**maxVpiBits - 1. The value of the 
      remaining (inactive) VPI bits is ignored on cells received from the 
      link.
      
      If the AtmIf is linked to a LogicalProcessor of cardType 
      3pOC3MmAtm, 3pOC3SmAtm, 3pE3Atm, 3pDS3Atm, 3pE1Atm, 
      3pDS1Atm, or 2pJ6MAtm, the value of this attribute must be 8. The 
      maximum VPI supported on these card types is 255.
      
      If the AtmIf is linked to a LogicalProcessor of any other cardType, 
      the value of this attribute may be 8 or 12. The maximum VPI 
      supported on these card types is 4095. An exception is that 
      cardType 8pE1Atm and 8pDS1Atm do not support VPI 4095; the 
      maximum VPI on these card types is 4094.
      
      If a Uni or an Iisp component is present directly under the AtmIf, 
      the value of this attribute must be 8."
   DEFVAL     { 8 }
::= { atmIfProvEntry 85 }

atmIfRemoteAtmInterfaceLabel OBJECT-TYPE
   SYNTAX     AsciiString (SIZE (0..60))
   ACCESS     read-write
   STATUS     mandatory
   DESCRIPTION
     "This attribute specifies a unique indication of the remote ATM 
      service or interface component connected to this one. The value of 
      this attribute can be used by network management applications to 
      discover the network's ATM topology from its configuration 
      information.
      
      The syntax of the value, such as component ID, address, or other 
      numerical identifier, must follow the conventions of the network 
      management platform. In absence of such convention or platform, 
      the value should be left empty.
      
      The value is only stored by the module. It is neither validated nor 
      used to perform any form of remote connectivity validation."
   DEFVAL     { ''H }  -- ""
::= { atmIfProvEntry 90 }

atmIfTxCellMemory OBJECT-TYPE
   SYNTAX     Unsigned32 (1..100)
   ACCESS     read-write
   STATUS     mandatory
   DESCRIPTION
     "This attribute specifies the percentage of total transmit cell memory 
      which is available for use by connections under this AtmIf. This 
      attribute is not applicable, and is ignored for CQC-based ATM FPs. 
      Transmit cell memory is used for storing ATM cells to be 
      transmitted by connections under this AtmIf. It includes all cells in 
      connections at the nrt-VBR or UBR service category. It includes 
      cells in CBR or rt-VBR connections which are doing per-VC 
      queueing. It does not include cells in CBR or rt-VBR connections 
      which are allocated from the dedicated buffer for CBR common 
      queuing or rt-VBR common queuing. 
      
      If the value of this attribute is specified as 100, connections under 
      this AtmIf may use up to 100% of the total transmit cell memory. If 
      this attribute is specified as an amount less than 100, then only that 
      percentage of the total transmit cell memory may be used by 
      connections under this AtmIf. The minimum value for this attribute 
      is 1% since some cell memory is always required for connections. 
      
      For 3pDs3Atm2 and 3pE3Atm2 card types, the total cell memory 
      displayed in Lp/x Eng Arc Aqm/0 txCellMemoryThreshold 0 is 
      shared across all three interfaces for the card. Specifying a value of 
      100% enables complete overbooking of the total transmit cell 
      memory by the three AtmIf's on this card. On a DS3 or E3 card, 
      specifying values for this attribute such that each value is less than 
      100% but the sum for the three AtmIf's is more than 100% enables 
      partial overbooking of the transmit cell memory. Specifying values 
      for this attribute under the three AtmIf's where the sum of these 
      attributes adds up to exactly 100%, ensures that each AtmIf has a 
      dedicated pool of transmit cells with no overbooking. Specifying 
      values for this attribute under the three AtmIf's where the sum of 
      these attributes adds up to less than 100%, restricts the total size of 
      the free list. This can be used to ensure the functioning of port 
      aggregation even with a small number of connections.
      
      For 2pOc3MmAtm2 and 2pOC3SmAtm2 card types, the cell 
      memory displayed in Lp/x Eng Arc Aqm/0 txCellMemoryThreshold 
      0 is allocated to the first interface for the card. Cell memory 
      displayed in Lp/x Eng Arc Aqm/1 txCellMemoryThreshold 0 is 
      allocated to the second interface for the card. Specifying an amount 
      less than 100% restricts the total size of the free list. This can be 
      used to ensure the functioning of port aggregation even with a small 
      number of connections."
   DEFVAL     { 100 }
::= { atmIfProvEntry 91 }

atmIfFaultHoldOffTime OBJECT-TYPE
   SYNTAX     INTEGER  {
                 n0(0),
                 infinity(65535) }
   ACCESS     read-write
   STATUS     mandatory
   DESCRIPTION
     "This attribute specifies the delay before faults detected at the VP 
      layer are propagated to the VC layer, and thus to the application 
      using the connection.
      
      If the value is 0 (zero), applications using a VirtualPathTerminator 
      are immediately notified of faults detected by the VP. Using this 
      value allows these applications to be advised of faults without 
      requiring loopbacks on each Vcc. Typically, the application goes out 
      of service when advised of a fault.
      
      If the value is infinity, applications are not notified of VP layer 
      faults. Using this value allows the applications to survive transient 
      VP layer fault conditions.
      
      The value chosen applies only to Vpts and Vccs directly beneath a 
      Vpt."
   DEFVAL     { infinity }
::= { atmIfProvEntry 100 }

atmIfLbkTable OBJECT-TYPE
   SYNTAX     SEQUENCE OF AtmIfLbkEntry
   ACCESS     not-accessible
   STATUS     mandatory
   DESCRIPTION
     "This group contains the default loopback attribute 
      values for all Vcc, Vpc and Vpt components. Note that these 
      attribute values can be overridden by setting different values in the 
      Vcd component of the provisioned Vcc or the Vpd component of the 
      provisioned Vpc or Vpt.
      
      Certain loopback requests may not be possible on a given 
      connection. In such cases, the corresponding operational loopback 
      attribute in the AtmStatus group of the Vcc, Vpc, or Vpt component 
      is set to notApplicable and the requested loopback is not performed."
::= { atmIf 120 }

atmIfLbkEntry OBJECT-TYPE
   SYNTAX     AtmIfLbkEntry
   ACCESS     not-accessible
   STATUS     mandatory
   DESCRIPTION
     "An entry in the atmIfLbkTable."
   INDEX {
      atmIfIndex }
::= { atmIfLbkTable 1 }

AtmIfLbkEntry ::= SEQUENCE {
   atmIfSegLinkSideLoopback
      INTEGER,
   atmIfSegSwitchSideLoopback
      INTEGER,
   atmIfEndToEndLoopback
      INTEGER,
   atmIfLoopbackMonitoring
      INTEGER }

atmIfSegLinkSideLoopback OBJECT-TYPE
   SYNTAX     INTEGER  {
                 on(0),
                 off(1) }
   ACCESS     read-write
   STATUS     mandatory
   DESCRIPTION
     "This attribute specifies the default value for link-side segment 
      loopback insertion for all connections under this interface. Link-
      side segment loopback is not possible if the oamSegmentBoundary 
      attribute of the AtmIf component is no."
   DEFVAL     { off }
::= { atmIfLbkEntry 10 }

atmIfSegSwitchSideLoopback OBJECT-TYPE
   SYNTAX     INTEGER  {
                 on(0),
                 off(1) }
   ACCESS     read-write
   STATUS     mandatory
   DESCRIPTION
     "This attribute specifies the default value for switch-side segment 
      loopback insertion for all connections under this interface. Switch-
      side segment loopback is not possible if the oamSegmentBoundary 
      attribute of the AtmIf component is no."
   DEFVAL     { off }
::= { atmIfLbkEntry 20 }

atmIfEndToEndLoopback OBJECT-TYPE
   SYNTAX     INTEGER  {
                 on(0),
                 off(1) }
   ACCESS     read-write
   STATUS     mandatory
   DESCRIPTION
     "This attribute specifies the default value for end-to-end loopback 
      insertion for all connections under this interface. End-to-end 
      loopback insertion is not possible if the connectionPointType 
      attribute of the Vcc or Vpc component is connectingPoint or 
      segmentEndPoint. End-to-end loopback insertion is possible if the 
      connectionPointType attribute of the Vcc or Vpc component is 
      connectionEndPoint. End-to-end loopback insertion is always 
      possible on a Vpt component."
   DEFVAL     { off }
::= { atmIfLbkEntry 30 }

atmIfLoopbackMonitoring OBJECT-TYPE
   SYNTAX     INTEGER  {
                 on(0),
                 off(1) }
   ACCESS     read-write
   STATUS     mandatory
   DESCRIPTION
     "'This attribute specifies the default value for loopback monitoring 
      for all connecting points of this interface. Currently this attribute 
      only applies to Passport specific trace cells.
      
      When Passport-specific trace cells are received at connecting points 
      connections under this interface the value of this attribute 
      determines if a response will be generated. 
      
      This attribute is only applicable to connectingPoint and will be 
      ignored by connectionEndPoints or segmentEndPoints.'"
   DEFVAL     { on }
::= { atmIfLbkEntry 110 }

atmIfStateTable OBJECT-TYPE
   SYNTAX     SEQUENCE OF AtmIfStateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { atmIf 130 }

atmIfStateEntry OBJECT-TYPE
   SYNTAX     AtmIfStateEntry
   ACCESS     not-accessible
   STATUS     mandatory
   DESCRIPTION
     "An entry in the atmIfStateTable."
   INDEX {
      atmIfIndex }
::= { atmIfStateTable 1 }

AtmIfStateEntry ::= SEQUENCE {
   atmIfAdminState
      INTEGER,
   atmIfOperationalState
      INTEGER,
   atmIfUsageState
      INTEGER,
   atmIfAvailabilityStatus
      OCTET STRING,
   atmIfProceduralStatus
      OCTET STRING,
   atmIfControlStatus
      OCTET STRING,
   atmIfAlarmStatus
      OCTET STRING,
   atmIfStandbyStatus
      INTEGER,
   atmIfUnknownStatus
      INTEGER }

atmIfAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { atmIfStateEntry 1 }

atmIfOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { atmIfStateEntry 2 }

atmIfUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { atmIfStateEntry 3 }

atmIfAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { atmIfStateEntry 4 }

atmIfProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { atmIfStateEntry 5 }

atmIfControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { atmIfStateEntry 6 }

atmIfAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { atmIfStateEntry 7 }

atmIfStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { atmIfStateEntry 8 }

atmIfUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { atmIfStateEntry 9 }

atmIfOperTable OBJECT-TYPE
   SYNTAX     SEQUENCE OF AtmIfOperEntry
   ACCESS     not-accessible
   STATUS     mandatory
   DESCRIPTION
     "This group contains operational attributes which show the status of 
      the AtmIf component."
::= { atmIf 140 }

atmIfOperEntry OBJECT-TYPE
   SYNTAX     AtmIfOperEntry
   ACCESS     not-accessible
   STATUS     mandatory
   DESCRIPTION
     "An entry in the atmIfOperTable."
   INDEX {
      atmIfIndex }
::= { atmIfOperTable 1 }

AtmIfOperEntry ::= SEQUENCE {
   atmIfTxCellMemoryAvailable
      Gauge32,
   atmIfTxCellMemoryCongestionState
      Gauge32,
   atmIfTxCellMemoryUsage
      Gauge32,
   atmIfUnshapedTransmitQueueingOper
      INTEGER }

atmIfTxCellMemoryAvailable OBJECT-TYPE
   SYNTAX     Gauge32 (0..163839)
   ACCESS     read-only
   STATUS     obsolete
   DESCRIPTION
     "This attribute is HISTORICAL and is replaced by 
      txCellMemoryUsage. 
      
      This attribute is only valid for AtmIf's on ATM IP FPs. It is not 
      displayed for AtmIf's on other card types. 
      
      This attribute indicates the current amount of transmit cells 
      available for this AtmIf. Transmit cell memory is the memory 
      available for storing ATM cells to be transmitted by connections 
      under this AtmIf."
::= { atmIfOperEntry 1 }

atmIfTxCellMemoryCongestionState OBJECT-TYPE
   SYNTAX     Gauge32 (0..3)
   ACCESS     read-only
   STATUS     mandatory
   DESCRIPTION
     "This attribute indicates the congestion state of the transmit cell 
      memory for this AtmIf. This attribute is not applicable, and is not 
      displayed on CQC-based ATM FPs. 
      
      This attribute indicates which txCellMemoryThreshold corresponds 
      to the current value of txCellMemoryUsage. The congestion state is 
      used to determine if cells of a particular discard priority (DP) are 
      discarded before being queued for transmit. 
      
      The congestion state of transmit cell memory is indicated by a 
      numeric value ranging from 3 to 0. When transmit cell memory is in 
      congestion state 'x', traffic with DP > 'x' is discarded before 
      transmit. Traffic with DP < 'x' may be queued for transmit, 
      depending on the congestion level of the connection transmit queue. 
      Traffic with DP = 'x' may be either queued or discarded depending 
      on how close the value of txCellMemoryUsage is to the next 
      threshold as displayed in txCellMemoryThreshold. For example, 
      CLP1 traffic is queued until the value indicated by 
      txCellMemoryUsage equals the value indicated in 
      txCellMemoryThreshold 3. At that point, CLP1 traffic is discarded."
::= { atmIfOperEntry 2 }

atmIfTxCellMemoryUsage OBJECT-TYPE
   SYNTAX     Gauge32 (0..163839)
   ACCESS     read-only
   STATUS     mandatory
   DESCRIPTION
     "This attribute indicates the current number of transmit cells which 
      are in use for this AtmIf. This attribute is not applicable, and is not 
      displayed on CQC-based ATM FPs. 
      
      Transmit cell memory is used for storing ATM cells to be 
      transmitted by connections under this AtmIf. It includes all cells in 
      connections at the nrt-VBR or UBR service category. It includes 
      cells in CBR or rt-VBR connections which are doing per-VC 
      queueing. It does not include cells in CBR or rt-VBR connections 
      which are allocated from the dedicated buffer for CBR common 
      queuing or rt-VBR common queuing."
::= { atmIfOperEntry 3 }

atmIfUnshapedTransmitQueueingOper OBJECT-TYPE
   SYNTAX     INTEGER  {
                 perVc(0),
                 common(1) }
   ACCESS     read-only
   STATUS     obsolete
   DESCRIPTION
     "This attribute is HISTORICAL in P6.0.
      
      This attribute indicates the state of transmit queuing for unshaped 
      connections under this AtmIf. 
      
      A value of perVc indicates that any unshaped connections use per-
      VC queueing in the CQC. A value of common indicates that traffic 
      for unshaped connections uses the common queue which 
      corresponds to the atmServiceCategory for this connection."
::= { atmIfOperEntry 10 }

atmIfStatsTable OBJECT-TYPE
   SYNTAX     SEQUENCE OF AtmIfStatsEntry
   ACCESS     not-accessible
   STATUS     mandatory
   DESCRIPTION
     "This group contains operational attributes which keep statistics 
      about the behavior of the AtmIf component."
::= { atmIf 150 }

atmIfStatsEntry OBJECT-TYPE
   SYNTAX     AtmIfStatsEntry
   ACCESS     not-accessible
   STATUS     mandatory
   DESCRIPTION
     "An entry in the atmIfStatsTable."
   INDEX {
      atmIfIndex }
::= { atmIfStatsTable 1 }

AtmIfStatsEntry ::= SEQUENCE {
   atmIfTransmittedCells
      PassportCounter64,
   atmIfTxCell
      PassportCounter64,
   atmIfTxCellClp
      PassportCounter64,
   atmIfTxCellEfci
      PassportCounter64,
   atmIfTxCellDiscard
      PassportCounter64,
   atmIfTxCellDiscardClp
      PassportCounter64,
   atmIfTxFrameDiscard
      PassportCounter64,
   atmIfTxFrameDiscardClp
      PassportCounter64,
   atmIfReceivedCells
      PassportCounter64,
   atmIfRxCell
      PassportCounter64,
   atmIfRxCellClp
      PassportCounter64,
   atmIfRxCellEfci
      PassportCounter64,
   atmIfRxCellDiscard
      PassportCounter64,
   atmIfRxCellDiscardClp
      PassportCounter64,
   atmIfRxFrameDiscard
      PassportCounter64,
   atmIfRxFrameDiscardClp
      PassportCounter64,
   atmIfDroppedRxCells
      PassportCounter64,
   atmIfLastDroppedRxCellConnection
      IntegerSequence,
   atmIfAal5RxErrors
      Counter32,
   atmIfLastAal5RxErrorConnection
      IntegerSequence,
   atmIfLrcFrameErrors
      Counter32,
   atmIfLastLrcFrameErrorConnection
      IntegerSequence,
   atmIfAal5RxAborts
      Counter32,
   atmIfLastAal5RxAbortConnection
      IntegerSequence,
   atmIfTxLinkUtilization
      Gauge32,
   atmIfRxLinkUtilization
      Gauge32 }

atmIfTransmittedCells OBJECT-TYPE
   SYNTAX     PassportCounter64 
   ACCESS     read-only
   STATUS     obsolete
   DESCRIPTION
     "This attribute is renamed in P6.0 to txCell for naming compatibility 
      with the Vcc and Vpc components.
      
      This attribute counts cells transmitted from the ATM interface. The 
      counter is reset to zero when the component is created, or when any 
      critical attribute of the component is changed. The counter wraps to 
      zero when it exceeds the maximum value of (2**64)-1."
::= { atmIfStatsEntry 10 }

atmIfTxCell OBJECT-TYPE
   SYNTAX     PassportCounter64 
   ACCESS     read-only
   STATUS     mandatory
   DESCRIPTION
     "This attribute counts cells transmitted from the ATM interface. It 
      does not include cells discarded due to congestion before transmit. 
      The counter is reset to zero when the component is activated, or 
      when any critical attribute of the component is changed. The 
      counter wraps to zero when it exceeds its maximum value of 
      (2**64)-1."
::= { atmIfStatsEntry 13 }

atmIfTxCellClp OBJECT-TYPE
   SYNTAX     PassportCounter64 
   ACCESS     read-only
   STATUS     mandatory
   DESCRIPTION
     "This attribute is not applicable and is not displayed on CQC-based 
      ATM cards. 
      
      This attribute counts cells transmitted from the ATM interface 
      which have the CLP bit set to 1. This includes cells which arrive at 
      this interface with CLP=1, and also cells which are marked with 
      CLP=1 as a result of forced tagging at this interface. This count is 
      included in the txCell attribute. The counter is reset to zero when 
      the component is activated, or when any critical attribute of the 
      component is changed. The counter wraps to zero when it exceeds 
      its maximum value of (2**64)-1."
::= { atmIfStatsEntry 14 }

atmIfTxCellEfci OBJECT-TYPE
   SYNTAX     PassportCounter64 
   ACCESS     read-only
   STATUS     mandatory
   DESCRIPTION
     "This attribute is not applicable and is not displayed on CQC-based 
      ATM cards. 
      
      This attribute counts cells transmitted from the ATM interface 
      which have the EFCI bit set to 1. This includes cells which arrive at 
      this interface with EFCI=1, and also cells which are marked with 
      EFCI=1 as a result of congestion at this interface. This count is 
      included in the txCell attribute. The counter is reset to zero when 
      the component is activated, or when any critical attribute of the 
      component is changed. The counter wraps to zero when it exceeds 
      its maximum value of (2**64)-1."
::= { atmIfStatsEntry 15 }

atmIfTxCellDiscard OBJECT-TYPE
   SYNTAX     PassportCounter64 
   ACCESS     read-only
   STATUS     mandatory
   DESCRIPTION
     "This attribute is not applicable and is not displayed on CQC-based 
      ATM cards. 
      
      This attribute counts cells discarded and not transmitted out the 
      ATM interface. Since cells are discarded before they are 
      transmitted, this count is not included in the txCell attribute. This 
      count is independent of the txFrameDiscard attribute. 
      
      Transmit cells are discarded due to transmit congestion, Partial 
      Packet Discard (PPD), Early Packet Discard (EPD), and Weighted 
      Random Early Detection (W-RED) mechanisms, or when the 
      connection's interface is disabled.
      
      The counter is reset to zero when the component is activated, or 
      when any critical attribute of the component is changed. The 
      counter wraps to zero when it exceeds its maximum value of 
      (2**64)-1."
::= { atmIfStatsEntry 16 }

atmIfTxCellDiscardClp OBJECT-TYPE
   SYNTAX     PassportCounter64 
   ACCESS     read-only
   STATUS     mandatory
   DESCRIPTION
     "This attribute is not applicable and is not displayed on CQC-based 
      ATM cards. 
      
      This attribute counts cells discarded and not transmitted out the 
      ATM interface which have the CLP bit set to 1. Since cells are 
      discarded before they are transmitted, this count is not included in 
      the txCellClp attribute. This count is included in the txCellDiscard 
      attribute, but it is independent of the txFrameDiscardClp attribute. 
      
      Transmit cells are discarded due to transmit congestion, Partial 
      Packet Discard (PPD), Early Packet Discard (EPD), and Weighted 
      Random Early Detection (W-RED) mechanisms, or when the 
      connection's interface is disabled.
      
      The counter is reset to zero when the component is activated, or 
      when any critical attribute of the component is changed. The 
      counter wraps to zero when it exceeds its maximum value of 
      (2**64)-1."
::= { atmIfStatsEntry 17 }

atmIfTxFrameDiscard OBJECT-TYPE
   SYNTAX     PassportCounter64 
   ACCESS     read-only
   STATUS     mandatory
   DESCRIPTION
     "This attribute is not applicable and is not displayed on CQC-based 
      ATM cards. 
      
      This attribute counts frames discarded and not transmitted out the 
      ATM interface. This count is independent of txCellDiscard. 
      
      Transmit frames are discarded due to congestion, Partial Packet 
      Discard (PPD), Early Packet Discard (EPD), and Weighted Random 
      Early Detection (W-RED) mechanisms, or when the connection 
      interface is disabled.
      
      The counter is reset to zero when the component is activated, or 
      when any critical attribute of the component is changed. The 
      counter wraps to zero when it exceeds its maximum value of 
      (2**64)-1."
::= { atmIfStatsEntry 18 }

atmIfTxFrameDiscardClp OBJECT-TYPE
   SYNTAX     PassportCounter64 
   ACCESS     read-only
   STATUS     mandatory
   DESCRIPTION
     "This attribute is not applicable and is not displayed on CQC-based 
      ATM cards. 
      
      This attribute counts frames which have at least one cell with the 
      CLP bit set to 1, and have been discarded and not transmitted out 
      the ATM interface. It is independent of the txCellDiscard attribute. 
      This count is included in the txFrameDiscard attribute. 
      
      Transmit frames are discarded due to congestion, Partial Packet 
      Discard (PPD), Early Packet Discard (EPD), and Weighted Random 
      Early Detection (W-RED) mechanisms, or when the connection 
      interface is disabled.
      
      The counter is reset to zero when the component is activated, or 
      when any critical attribute of the component is changed. The 
      counter wraps to zero when it exceeds its maximum value of 
      (2**64)-1."
::= { atmIfStatsEntry 19 }

atmIfReceivedCells OBJECT-TYPE
   SYNTAX     PassportCounter64 
   ACCESS     read-only
   STATUS     obsolete
   DESCRIPTION
     "This attribute is renamed in P6.0 to rxCell for naming compatibility 
      with the Vcc and Vpc component.
      
      This attribute counts valid cells received from the ATM interface. 
      The counter is reset to zero when the component is created, or when 
      any critical attribute of the component is changed. The counter 
      wraps to zero when it exceeds its maximum value of (2**64)-1."
::= { atmIfStatsEntry 20 }

atmIfRxCell OBJECT-TYPE
   SYNTAX     PassportCounter64 
   ACCESS     read-only
   STATUS     mandatory
   DESCRIPTION
     "This attribute counts valid cells received from the ATM interface. 
      This count includes cells which may be subsequently discarded. 
      The counter is reset to zero when the component is activated, or 
      when any critical attribute of the component is changed. On ATM 
      IP FPs valid cells include cells that arrive on a VCC whose 
      VPI.VCI cannot be identified. These cells are also counted under 
      the droppedRxCell attribute. The value of this attribute on ATM IP 
      FPs should be greater than or equal to the sum of droppedRxCell 
      and all the Vcc and Vpc rxCell attributes under this interface. The 
      counter wraps to zero when it exceeds its maximum value of 
      (2**64)-1."
::= { atmIfStatsEntry 23 }

atmIfRxCellClp OBJECT-TYPE
   SYNTAX     PassportCounter64 
   ACCESS     read-only
   STATUS     mandatory
   DESCRIPTION
     "This attribute is not applicable and is not displayed on CQC-based 
      ATM cards. 
      
      This attribute counts valid cells received from the ATM interface 
      which have the CLP bit set to 1. This count includes cells which 
      may be subsequently discarded. This count is included in the rxCell 
      attribute. The counter is reset to zero when the component is 
      activated, or when any critical attribute of the component is 
      changed. The counter wraps to zero when it exceeds its maximum 
      value of (2**64)-1."
::= { atmIfStatsEntry 24 }

atmIfRxCellEfci OBJECT-TYPE
   SYNTAX     PassportCounter64 
   ACCESS     read-only
   STATUS     mandatory
   DESCRIPTION
     "This attribute is not applicable and is not displayed on CQC-based 
      ATM cards. 
      
      This attribute counts valid cells received from the ATM interface 
      which have the EFCI bit set to 1. This count includes cells which 
      may be subsequently discarded. This count is included in the rxCell 
      attribute. The counter is reset to zero when the component is 
      activated, or when any critical attribute of the component is 
      changed. The counter wraps to zero when it exceeds its maximum 
      value of (2**64)-1."
::= { atmIfStatsEntry 25 }

atmIfRxCellDiscard OBJECT-TYPE
   SYNTAX     PassportCounter64 
   ACCESS     read-only
   STATUS     mandatory
   DESCRIPTION
     "This attribute is not applicable and is not displayed on CQC-based 
      ATM cards. 
      
      This attribute counts cells received from the ATM interface which 
      have been discarded. This count is included in the rxCell attribute. 
      
      This count includes cells discarded due to non-conformance with 
      UPC, cells which are part of a frame which has been discarded due 
      to an AAL5 frame reassembly error, cells which are discarded due 
      to congestion, or cells which are received while the next hop 
      connection to which the traffic is directed across the backplane is 
      down. The next hop connection is the Vcc or Vpc identified by the 
      nextHop attribute of the Nrp or Rp component. 
      
      The counter is reset to zero when the component is activated, or 
      when any critical attribute of the component is changed. The 
      counter wraps to zero when it exceeds its maximum value of 
      (2**64)-1."
::= { atmIfStatsEntry 26 }

atmIfRxCellDiscardClp OBJECT-TYPE
   SYNTAX     PassportCounter64 
   ACCESS     read-only
   STATUS     mandatory
   DESCRIPTION
     "This attribute is not applicable and is not displayed on CQC-based 
      ATM cards. 
      
      This attribute counts valid cells received from the ATM interface 
      which have the CLP bit set to 1, which have been discarded. This 
      count is included in the rxCell and rxCellDiscard attributes. 
      
      This count includes cells discarded due to non-conformance with 
      UPC, cells which are part of a frame which has been discarded due 
      to an AAL5 frame reassembly error, cells which are discarded due 
      to congestion, or cells which are received while the next hop 
      connection to which the traffic is directed across the backplane is 
      down. The next hop connection is the Vcc or Vpc identified by the 
      nextHop attribute of the Nrp or Rp component. 
      
      This counter is reset to zero when the component is activated, or 
      when any critical attribute of the component is changed. The 
      counter wraps to zero when it exceeds its maximum value of 
      (2**64)-1."
::= { atmIfStatsEntry 27 }

atmIfRxFrameDiscard OBJECT-TYPE
   SYNTAX     PassportCounter64 
   ACCESS     read-only
   STATUS     mandatory
   DESCRIPTION
     "This attribute is not applicable and is not displayed on CQC-based 
      ATM cards. 
      
      This attribute counts frames received from the ATM interface which 
      have been discarded. This count includes the count of 
      rxFrameDiscardClp and aal5RxErrors. It is independent of the 
      rxCellDiscard attribute. 
      
      This count includes frames discarded due to an AAL5 frame 
      reassembly error, frames discarded due to early packet discard 
      (EPD), and frames discarded due to processor (CPU) congestion. 
      This attribute is applicable only for connections that reassemble 
      incoming cells into frames. Connections which reassemble cells 
      into frames have a connectionPointType of connectionEndPoint. 
      AAL1 connections are an exception to this rule; even though they 
      have a connectionPointType of connectionEndPoint, they do not 
      do adaptation at this point.
      
      The counter is reset to zero when the component is activated, or 
      when any critical attribute of the component is changed. The 
      counter wraps to zero when it exceeds its maximum value of 
      (2**64)-1."
::= { atmIfStatsEntry 28 }

atmIfRxFrameDiscardClp OBJECT-TYPE
   SYNTAX     PassportCounter64 
   ACCESS     read-only
   STATUS     mandatory
   DESCRIPTION
     "This attribute is not applicable and is not displayed on CQC-based 
      ATM cards. 
      
      This attribute counts frames received from the ATM interface which 
      have been discarded and which have at least one cell with the CLP 
      bit set to 1. This count is included in the rxFrameDiscard attribute. 
      It is independent of the rxCellDiscardClp attribute. 
      
      This count includes frames discarded due to an AAL5 frame 
      reassembly error, frames discarded due to early packet discard 
      (EPD), and frames discarded due to processor (CPU) congestion. 
      This attribute is applicable only for connections that reassemble 
      incoming cells into frames. Connections which reassemble cells 
      into frames have a connectionPointType of connectionEndPoint. 
      AAL1 connections are an exception to this rule; even though they 
      have a connectionPointType of connectionEndPoint, they do not 
      do adaptation at this point.
      
      The counter is reset to zero when the component is activated, or 
      when any critical attribute of the component is changed. The 
      counter wraps to zero when it exceeds its maximum value of 
      (2**64)-1."
::= { atmIfStatsEntry 29 }

atmIfDroppedRxCells OBJECT-TYPE
   SYNTAX     PassportCounter64 
   ACCESS     read-only
   STATUS     mandatory
   DESCRIPTION
     "This attribute counts cells received from the interface that were 
      dropped because they contained invalid VPI or VCI values, or 
      dropped because they had no associated connection for the VPI or 
      VCI. On ATM IP FPs this count is included in the rxCell count for 
      the interface. Note that this attribute does not keep an exact count. 
      Idle cells and unassigned cells are ignored without being counted as 
      dropped cells. The counter is reset to zero when the component is 
      created, or when any critical attribute of the component is changed. 
      The counter wraps to zero when it exceeds its maximum value of 
      (2**64)-1. 
      
      The VPI and VCI of the last dropped cell are indicated in the 
      attribute lastDroppedRxCellConnection."
::= { atmIfStatsEntry 30 }

atmIfLastDroppedRxCellConnection OBJECT-TYPE
   SYNTAX     IntegerSequence (SIZE (3..10))
   ACCESS     read-only
   STATUS     mandatory
   DESCRIPTION
     "This attribute indicates the VPI and VCI of the last cell that was 
      dropped. Cells are dropped because they have no associated 
      connection for the VPI and VCI.
      
      Dropped cells are counted in the attribute droppedRxCells."
::= { atmIfStatsEntry 31 }

atmIfAal5RxErrors OBJECT-TYPE
   SYNTAX     Counter32 
   ACCESS     read-only
   STATUS     mandatory
   DESCRIPTION
     "This attribute counts AAL5 frame reassembly errors which have 
      occurred since the component was activated. These errors are either 
      CRC errors or length errors, possibly caused by dropped cells.This 
      attribute includes the count of AAL5 aborted frames. This count is 
      included in the rxFrameDiscard count.
      
      The counter is reset to zero when the component is created, or when 
      any critical attribute of the component is changed. The counter 
      wraps to zero if it exceeds its maximum value of (2**64)-1.
      
      The VPI and VCI of the last connection which exhibited AAL5 
      reassembly errors are indicated in the attribute 
      lastAal5ErrorConnection."
::= { atmIfStatsEntry 32 }

atmIfLastAal5RxErrorConnection OBJECT-TYPE
   SYNTAX     IntegerSequence (SIZE (3..10))
   ACCESS     read-only
   STATUS     mandatory
   DESCRIPTION
     "This attribute indicates the VPI and VCI of the last connection that 
      exhibited AAL5 reassembly errors.
      
      These errors are counted in the attribute aal5RxErrors."
::= { atmIfStatsEntry 33 }

atmIfLrcFrameErrors OBJECT-TYPE
   SYNTAX     Counter32 
   ACCESS     read-only
   STATUS     mandatory
   DESCRIPTION
     "This attribute counts egress LRC frame errors on frames received 
      across the bus. The likely cause of this is a hardware fault on either 
      the sending or receiving card. The counter is reset to zero when the 
      component is created, or when any critical attribute of the 
      component is changed. The counter wraps to zero when it exceeds 
      its maximum value of (2**64)-1.
      
      The VPI and VCI of the last connection which exhibited LRC errors 
      are indicated in the attribute lastLrcFrameErrorConnection."
::= { atmIfStatsEntry 34 }

atmIfLastLrcFrameErrorConnection OBJECT-TYPE
   SYNTAX     IntegerSequence (SIZE (3..10))
   ACCESS     read-only
   STATUS     mandatory
   DESCRIPTION
     "This attribute indicates the VPI and VCI of the last connection that 
      had LRC frame errors on frames received across the bus.
      These errors are counted in the attribute lrcFrameErrors."
::= { atmIfStatsEntry 35 }

atmIfAal5RxAborts OBJECT-TYPE
   SYNTAX     Counter32 
   ACCESS     read-only
   STATUS     mandatory
   DESCRIPTION
     "This attribute is not supported on any card type in Release 6.0 or 
      earlier. 
      
      This attribute counts AAL5 frame aborts which have been received 
      since the component was activated. An AAL5 aborted frame is one 
      in which the AAL5 frame length has been set to zero. This count is 
      included in aal5RxErrors. 
      
      The counter is reset to zero when the component is created, or when 
      any critical attribute of the component is changed. The counter 
      wraps to zero when it exceeds its maximum value of (2**64)-1. 
      
      The VPI and VCI of the last connection which received AAL5 abort 
      errors are displayed in the attribute lastAal5RxAbortConnection."
::= { atmIfStatsEntry 40 }

atmIfLastAal5RxAbortConnection OBJECT-TYPE
   SYNTAX     IntegerSequence (SIZE (3..10))
   ACCESS     read-only
   STATUS     mandatory
   DESCRIPTION
     "This attribute is not supported on any card type in Release 6.0 or 
      earlier. 
      
      This attribute indicates the VPI and VCI of the last connection that 
      exhibited AAL5 aborts. These errors are counted in the attribute 
      aal5RxAborts."
::= { atmIfStatsEntry 50 }

atmIfTxLinkUtilization OBJECT-TYPE
   SYNTAX     Gauge32 (0..100)
   ACCESS     read-only
   STATUS     mandatory
   DESCRIPTION
     "This attribute indicates the current transmit interface utilization 
      during the most recent minute, expressed as a percentage of the 
      total bandwidth which can be carried by this ATM interface."
::= { atmIfStatsEntry 59 }

atmIfRxLinkUtilization OBJECT-TYPE
   SYNTAX     Gauge32 (0..100)
   ACCESS     read-only
   STATUS     mandatory
   DESCRIPTION
     "This attribute indicates the current receive interface utilization 
      during the most recent minute, expressed as a percentage of the 
      total bandwidth which can be carried by this ATM interface."
::= { atmIfStatsEntry 60 }

atmIfTxCellMemoryThresholdTable OBJECT-TYPE
   SYNTAX     SEQUENCE OF AtmIfTxCellMemoryThresholdEntry
   ACCESS     not-accessible
   STATUS     mandatory
   DESCRIPTION
     "This attribute is a vector which indicates the size and three discard 
      thresholds for transmit cell memory for this AtmIf. This attribute is 
      not applicable, and is not displayed on CQC-based ATM FPs. 
      Transmit cell memory used for storing ATM cells to be transmitted 
      by connections under this AtmIf. It includes all cells in connections 
      at the nrt-VBR or UBR service category. It includes cells in CBR or 
      rt-VBR connections which are doing per-VC queueing. It does not 
      include cells in CBR or rt-VBR connections which are allocated 
      from the dedicated buffer for CBR common queuing or rt-VBR 
      common queuing.
      
      The first value indicates the transmit cell memory size. It is the 
      multiplication of the Lp/x Eng Arc Aqm/y txCellMemoryThreshold 0 
      attribute by the txCellMemoryPercentage attribute of this AtmIf. 
      
      The current value of txCellMemoryUsage together with the vector 
      of values in txCellMemoryThreshold determines the 
      txCellMemoryCongestionState. The congestion state determines 
      whether cells of a given discard priority (DP) are discarded or 
      queued for transmit. 
      
      When the txCellMemoryUsage attribute is between threshold 0 and 
      threshold 1, the txCellMemoryCongestionState indicates the value 
      0. In congestion state 0, traffic with DP > 0 is discarded. Threshold 
      1 is set approximately at 90 percent of threshold 0, the total transmit 
      cell memory size. 
      
      When the txCellMemoryUsage attribute is between threshold 1 and 
      threshold 2, the txCellMemoryCongestionState indicates the value 
      1. In congestion state 1, traffic with DP > 1 is discarded. Threshold 
      2 is set approximately at 85 percent of threshold 0, the total transmit 
      cell memory size. 
      
      When the txCellMemoryUsage attribute is between threshold 2 and 
      threshold 3, the txCellMemoryCongestionState indicates the value 
      2. In congestion state 2, traffic with DP > 2 is discarded. Threshold 
      3 is set approximately at 75 percent of threshold 0, the total transmit 
      cell memory size. 
      
      When the txCellMemoryUsage attribute is below threshold 3, the 
      txCellMemoryCongestionState indicates the value 3. In congestion 
      state 3, traffic with DP=3 is queued."
::= { atmIf 441 }

atmIfTxCellMemoryThresholdEntry OBJECT-TYPE
   SYNTAX     AtmIfTxCellMemoryThresholdEntry
   ACCESS     not-accessible
   STATUS     mandatory
   DESCRIPTION
     "An entry in the atmIfTxCellMemoryThresholdTable."
   INDEX {
      atmIfIndex,
      atmIfTxCellMemoryThresholdIndex }
::= { atmIfTxCellMemoryThresholdTable 1 }

AtmIfTxCellMemoryThresholdEntry ::= SEQUENCE {
   atmIfTxCellMemoryThresholdIndex
      Integer32,
   atmIfTxCellMemoryThresholdValue
      Unsigned32 }

atmIfTxCellMemoryThresholdIndex OBJECT-TYPE
   SYNTAX     Integer32 (0..3)
   ACCESS     not-accessible
   STATUS     mandatory
   DESCRIPTION
     "This variable represents the atmIfTxCellMemoryThresholdTable
      specific index for the atmIfTxCellMemoryThresholdTable."
::= { atmIfTxCellMemoryThresholdEntry 1 }

atmIfTxCellMemoryThresholdValue OBJECT-TYPE
   SYNTAX     Unsigned32 (0..163839)
   ACCESS     read-only
   STATUS     mandatory
   DESCRIPTION
     "This variable represents an individual value for the
      atmIfTxCellMemoryThresholdTable."
::= { atmIfTxCellMemoryThresholdEntry 2 }


-- AtmIf/n ConnectionMapping
-- The ConnectionMapping component is used to to view the VCC 
-- space supported by an ATM interface on card types 3pOC3MmAtm, 
-- 3pOC3SmAtm, 3pE3Atm, 3pDS3Atm, 3pE1Atm, 3pDS1Atm, and 
-- 2pJ6MAtm. Only VPI and VCI values that lie within the VCC 
-- space may be used for VCC connections.
-- 
-- Any VPI values not assigned to the VCC space are, by implication, 
-- consigned to the VPC space. Only VPI values that lie within the 
-- VPC space may be used to support VPC connections.

atmIfConnMap OBJECT IDENTIFIER ::= { atmIf 2 }



atmIfConnMapRowStatusTable OBJECT-TYPE
   SYNTAX     SEQUENCE OF AtmIfConnMapRowStatusEntry
   ACCESS     not-accessible
   STATUS     mandatory
   DESCRIPTION
     "This entry controls the addition and deletion of 
      atmIfConnMap components."
::= { atmIfConnMap 1 }

atmIfConnMapRowStatusEntry OBJECT-TYPE
   SYNTAX     AtmIfConnMapRowStatusEntry
   ACCESS     not-accessible
   STATUS     mandatory
   DESCRIPTION
     "A single entry in the table represents a single 
      atmIfConnMap component."
   INDEX {
      atmIfIndex,
      atmIfConnMapIndex }
::= { atmIfConnMapRowStatusTable 1 }

AtmIfConnMapRowStatusEntry ::= SEQUENCE {
   atmIfConnMapRowStatus
      RowStatus,
   atmIfConnMapComponentName
      DisplayString,
   atmIfConnMapStorageType
      StorageType,
   atmIfConnMapIndex
      NonReplicated }

atmIfConnMapRowStatus OBJECT-TYPE
   SYNTAX     RowStatus 
   ACCESS     read-write
   STATUS     mandatory
   DESCRIPTION
     "This variable is used as the basis for SNMP naming of
      atmIfConnMap components.
      These components can be added and deleted."
::= { atmIfConnMapRowStatusEntry 1 }

atmIfConnMapComponentName OBJECT-TYPE
   SYNTAX     DisplayString 
   ACCESS     read-only
   STATUS     mandatory
   DESCRIPTION
     "This variable provides the component's string name for
      use with the ASCII Console Interface"
::= { atmIfConnMapRowStatusEntry 2 }

atmIfConnMapStorageType OBJECT-TYPE
   SYNTAX     StorageType 
   ACCESS     read-only
   STATUS     mandatory
   DESCRIPTION
     "This variable represents the storage type value for the
      atmIfConnMap tables."
::= { atmIfConnMapRowStatusEntry 4 }

atmIfConnMapIndex OBJECT-TYPE
   SYNTAX     NonReplicated 
   ACCESS     not-accessible
   STATUS     mandatory
   DESCRIPTION
     "This variable represents the index for the atmIfConnMap tables."
::= { atmIfConnMapRowStatusEntry 10 }

atmIfConnMapVccProvTable OBJECT-TYPE
   SYNTAX     SEQUENCE OF AtmIfConnMapVccProvEntry
   ACCESS     not-accessible
   STATUS     obsolete
   DESCRIPTION
     "This group is obsolete. Please refer to the Override component 
      below for the current provisioning group
      
      This group contains provisionable attributes which specify the VCC 
      space to be supported by an ATM interface. The VCC space 
      consists of an optional 'VPI Zero VCC Space' and an optional 
      'Programmable VCC Space'.
      
      The VPI Zero VCC Space is used to support VCCs with a VPI of 
      zero. The VCI values supported in this space range from 0 to a 
      provisioned maximum. The size of the VPI Zero VCC Space must 
      either be 0 or a multiple of 256. A value of 0 implies that no 
      programmable VCCs can be used. In this case 
      atmNumberOfNonZeroVpisForVccs_m must also be 0.
      
      The optional Programmable VCC Space is used to support VCCs 
      with a VPI other than zero. The VPI values supported in this space 
      must lie in a single contiguous range which excludes VPI 0. The 
      VCI values supported in this space range from 0 to a provisioned 
      maximum. The size of the Programmable VCC Space (should it 
      exist) must adhere to the following rules:
      
      If (firstNonZeroVpiForVccs = 1) THEN
      (numNonZeroVpisForVccs + 1) *
      numVccsPerNonZeroVpi must be a multiple of 256
      OTHERWISE
      numNonZeroVpisForVccs * numVccsPerNonZeroVpi
      must be a multiple of 256
      
      If the AtmIf is linked to a LogicalProcessor with a cardType of 
      3pE3Atm, 3pDS3Atm, 3pOC3MmAtm, 3pOC3SmAtm, 3pE1Atm, 
      3pDS1Atm or 2pJ6MAtm, the size of the entire VCC space (both 
      mandatory and optional parts) and VPC space must not exceed the 
      capacity of the port to which the interface is linked, which is 
      defined in the Arc component's totalConnectionPoolCapacity or 
      connectionPoolCapacity attribute (whichever is non-zero). When 
      using the totalConnectionPoolCapacity attribute, the capacity of the 
      port is (totalConnectionPoolCapacity divided by the number of 
      physical ports). The number of connection identifiers in the VCC 
      and VPC space can be determined as follows:
      
      IF (numNonZeroVpisForVccs = 0) THEN
      number of connection ids = 256 + numVccsForVpiZero
      OTHERWISE IF (firstNonZeroVpiForVccs = 1) THEN
      number of connection ids = 256 + numVccsForVpiZero +
      (numNonZeroVpisForVccs + 1) *
      numVccsPerNonZeroVpi
      OTHERWISE
      number of connection ids = 256 + numVccsForVpiZero +
      (numNonZeroVpisForVccs * numVccsPerNonZeroVpi)"
::= { atmIfConnMap 100 }

atmIfConnMapVccProvEntry OBJECT-TYPE
   SYNTAX     AtmIfConnMapVccProvEntry
   ACCESS     not-accessible
   STATUS     obsolete
   DESCRIPTION
     "An entry in the atmIfConnMapVccProvTable."
   INDEX {
      atmIfIndex,
      atmIfConnMapIndex }
::= { atmIfConnMapVccProvTable 1 }

AtmIfConnMapVccProvEntry ::= SEQUENCE {
   atmIfConnMapNumVccsForVpiZero
      Unsigned32,
   atmIfConnMapNumNonZeroVpisForVccs
      Unsigned32,
   atmIfConnMapFirstNonZeroVpiForVccs
      Unsigned32,
   atmIfConnMapNumVccsPerNonZeroVpi
      Unsigned32 }

atmIfConnMapNumVccsForVpiZero OBJECT-TYPE
   SYNTAX     Unsigned32 (0..16128)
   ACCESS     write-only
   STATUS     obsolete
   DESCRIPTION
     "This attribute is obsolete. Please refer to the Override component 
      for the new attribute.
      
      This attribute specifies the number of VCCs supported for the VPI 
      Zero VCC Space. The VCI values of these VCCs range from 0 to 
      (numVccsForVpiZero - 1).
      
      The size of the VPI Zero VCC Space must either be 0 or a multiple 
      of 256. A value of 0 implies that no programmable VCCs can be 
      used. In this case atmNumberOfNonZeroVpisForVccs_m must also 
      be 0. 
      
      The VCC Space as a whole must adhere to the guidelines laid down 
      in the description of the AtmConnMappingVccProv group."
   DEFVAL     { 768 }
::= { atmIfConnMapVccProvEntry 10 }

atmIfConnMapNumNonZeroVpisForVccs OBJECT-TYPE
   SYNTAX     Unsigned32 (0..255)
   ACCESS     write-only
   STATUS     obsolete
   DESCRIPTION
     "This attribute is obsolete. Please refer to the Override component 
      for the new attribute.
      
      This attribute specifies the number of conti	guous VPIs supported in 
      the optional Programmable VCC Space.
      
      If numNonZeroVpisForVccs is 0 the Programmable VCC Space 
      does not exist. If numNonZeroVpisForVccs is greater than 0 the 
      Programmable VCC Space exists and covers the VPI values ranging 
      from firstNonZeroVpiForVccs to (firstNonZeroVpiForVccs + 
      numNonZeroVpisForVccs - 1).
      
      The VCC Space as a whole must adhere to the guidelines laid down 
      in the description of the AtmConnMappingVccProv group."
   DEFVAL     { 0 }
::= { atmIfConnMapVccProvEntry 20 }

atmIfConnMapFirstNonZeroVpiForVccs OBJECT-TYPE
   SYNTAX     Unsigned32 (1 | 16 | 32 | 48 | 64 | 80 | 96 | 112 | 128 | 144 | 160 | 176 | 192 | 208 | 224 | 240)
   ACCESS     write-only
   STATUS     obsolete
   DESCRIPTION
     "This attribute is obsolete. Please refer to the Override component 
      for the new attribute.
      
      This attribute specifies the initial VPI of the optional Programmable 
      VCC Space.
      
      If numNonZeroVpisForVccs is 0 the Programmable VCC Space 
      does not exist. If numNonZeroVpisForVccs is greater than 0 the 
      Programmable VCC Space exists and covers the VPI values ranging 
      from firstNonZeroVpiForVccs to (firstNonZeroVpiForVccs + 
      numNonZeroVpisForVccs - 1).
      
      The initial VPI of the Programmable VCC Space must either be 1 
      or a non-zero multiple of 16.
      
      The VCC Space as a whole must adhere to the guidelines laid down 
      in the description of the AtmConnMappingVccProv group."
   DEFVAL     { 1 }
::= { atmIfConnMapVccProvEntry 30 }

atmIfConnMapNumVccsPerNonZeroVpi OBJECT-TYPE
   SYNTAX     Unsigned32 (2 | 4 | 8 | 16 | 32 | 64 | 128 | 256 | 512 | 1024 | 2048)
   ACCESS     write-only
   STATUS     obsolete
   DESCRIPTION
     "This attribute is obsolete. Please refer to the Override component 
      for the new attribute.
      
      This attribute specifies the number of VCCs supported for each VPI 
      in the Programmable VCC Space. The VCI values of these VCCs 
      range from 0 to (numVccsPerNonZeroVpi - 1) for each VPI in this 
      space.
      
      The size of the Programmable VCC Space must be a power of 2.
      
      The VCC Space as a whole must adhere to the guidelines laid down 
      in the description of the AtmConnMappingVccProv group."
   DEFVAL     { 64 }
::= { atmIfConnMapVccProvEntry 40 }

atmIfConnMapOperTable OBJECT-TYPE
   SYNTAX     SEQUENCE OF AtmIfConnMapOperEntry
   ACCESS     not-accessible
   STATUS     mandatory
   DESCRIPTION
     "This group contains operational attributes which specify the VCC 
      space to be supported by an ATM interface. The VCC space 
      consists of an optional 'VPI Zero VCC Space' and an optional 
      'Programmable VCC Space'.
      
      The VPI Zero VCC Space is used to support VCCs with a VPI of 
      zero. The VCI values supported in this space range from 0 to an 
      optionally provisioned maximum of numVccsForVpiZero. The size 
      of the VPI Zero VCC Space is either 0 or a multiple of 256. A value 
      of 0 implies that not only can no VCCs be provisioned in the VPI 
      Zero VCC Space but no Programmable VCCs can be used. In this 
      case numNonZeroVpisForVccs will also be 0.
      
      The optional Programmable VCC Space supports VCCs with a VPI 
      other than zero. The VPI values supported in this space lie in a 
      single contiguous range which excludes VPI 0. The VCI values 
      supported in this space range from 0 to an optionally provisioned 
      maximum.
      
      The number of connection identifier resources in the VCC and VPC 
      space (not all of which are available for user connections) is the 
      value reported in the Lp/n Eng Arc totalConnectionPoolAvailable 
      attribute divided by the number of physical ports on the card, and 
      can be determined as follows:
      
      IF (numNonZeroVpisForVccs = 0) THEN
      number of connection ID resources =
      256 + numVccsForVpiZero
      OTHERWISE IF (firstNonZeroVpiForVccs = 1) THEN
      number of connection ID resources =
      256 + numVccsForVpiZero +
      (numNonZeroVpisForVccs + 1) * numVccsPerNonZeroVpi
      OTHERWISE
      number of connection ID resources =
      256 + numVccsForVpiZero +
      (numNonZeroVpisForVccs * numVccsPerNonZeroVpi)"
::= { atmIfConnMap 110 }

atmIfConnMapOperEntry OBJECT-TYPE
   SYNTAX     AtmIfConnMapOperEntry
   ACCESS     not-accessible
   STATUS     mandatory
   DESCRIPTION
     "An entry in the atmIfConnMapOperTable."
   INDEX {
      atmIfIndex,
      atmIfConnMapIndex }
::= { atmIfConnMapOperTable 1 }

AtmIfConnMapOperEntry ::= SEQUENCE {
   atmIfConnMapNumVccsForVpiZeroOper
      Unsigned32,
   atmIfConnMapNumNonZeroVpisForVccsOper
      Unsigned32,
   atmIfConnMapFirstNonZeroVpiForVccsOper
      Unsigned32,
   atmIfConnMapNumVccsPerNonZeroVpiOper
      Unsigned32 }

atmIfConnMapNumVccsForVpiZeroOper OBJECT-TYPE
   SYNTAX     Unsigned32 (0..16128)
   ACCESS     read-only
   STATUS     mandatory
   DESCRIPTION
     "This attribute indicates the number of VCCs supported for the VPI 
      Zero VCC Space. The VCI values of these VCCs range from 0 to 
      (numVccsForVpiZero - 1).
      
      To override the system default, see the AtmIf ConnMap Ov attribute 
      numVccsForVpiZero."
::= { atmIfConnMapOperEntry 10 }

atmIfConnMapNumNonZeroVpisForVccsOper OBJECT-TYPE
   SYNTAX     Unsigned32 (0..255)
   ACCESS     read-only
   STATUS     mandatory
   DESCRIPTION
     "This attribute indicates the number of contiguous VPIs supported in 
      the optional Programmable VCC Space.
      
      If numNonZeroVpisForVccs is 0 the Programmable VCC Space 
      does not exist. If numNonZeroVpisForVccs is greater than 0 the 
      Programmable VCC Space exists and covers the VPI values ranging 
      from firstNonZeroVpiForVccs to (firstNonZeroVpiForVccs + 
      numNonZeroVpisForVccs - 1).
      
      To override the system default, see the AtmIf ConnMap Ov attribute 
      numNonZeroVpisForVccs."
::= { atmIfConnMapOperEntry 20 }

atmIfConnMapFirstNonZeroVpiForVccsOper OBJECT-TYPE
   SYNTAX     Unsigned32 (1 | 16 | 32 | 48 | 64 | 80 | 96 | 112 | 128 | 144 | 160 | 176 | 192 | 208 | 224 | 240)
   ACCESS     read-only
   STATUS     mandatory
   DESCRIPTION
     "This attribute indicates the initial VPI of the optional Programmable 
      VCC Space.
      
      If numNonZeroVpisForVccs is 0 the Programmable VCC Space 
      does not exist. If numNonZeroVpisForVccs is greater than 0 the 
      Programmable VCC Space exists and covers the VPI values ranging 
      from firstNonZeroVpiForVccs to (firstNonZeroVpiForVccs + 
      numNonZeroVpisForVccs - 1).
      
      To override the system default, see the AtmIf ConnMap Ov attribute 
      firstNonZeroVpiForVccs."
::= { atmIfConnMapOperEntry 30 }

atmIfConnMapNumVccsPerNonZeroVpiOper OBJECT-TYPE
   SYNTAX     Unsigned32 (2 | 4 | 8 | 16 | 32 | 64 | 128 | 256 | 512 | 1024 | 2048)
   ACCESS     read-only
   STATUS     mandatory
   DESCRIPTION
     "This attribute indicates the number of VCCs supported for each VPI 
      in the Programmable VCC Space. The VCI values of these VCCs 
      range from 0 to (numVccsPerNonZeroVpi - 1) for each VPI in this 
      space.
      
      To override the system default, see the AtmIf ConnMap Ov attribute 
      numVccsPerNonZeroVpi."
::= { atmIfConnMapOperEntry 40 }


-- AtmIf/n ConnMap Override
-- The Override component is used to specify the VCC space to be 
-- supported on an ATM interface on card types 3pOC3MmAtm, 
-- 3pOC3SmAtm, 3pE3Atm, 3pDS3Atm, 3pE1Atm, 3pDS1Atm, and 
-- 2pJ6MAtm. Only VPI and VCI values that lie within the VCC 
-- space may be used for VCC connections.
-- 
-- Any VPI values not assigned to the VCC space are, by implication, 
-- consigned to the VPC space. Only VPI values that lie within the 
-- VPC space may be used to support VPC connections.
-- 
-- This component is used to override the default values used for the 
-- parent ConnectionMapping component.

atmIfConnMapOv OBJECT IDENTIFIER ::= { atmIfConnMap 120 }



atmIfConnMapOvRowStatusTable OBJECT-TYPE
   SYNTAX     SEQUENCE OF AtmIfConnMapOvRowStatusEntry
   ACCESS     not-accessible
   STATUS     mandatory
   DESCRIPTION
     "This entry controls the addition and deletion of 
      atmIfConnMapOv components."
::= { atmIfConnMapOv 1 }

atmIfConnMapOvRowStatusEntry OBJECT-TYPE
   SYNTAX     AtmIfConnMapOvRowStatusEntry
   ACCESS     not-accessible
   STATUS     mandatory
   DESCRIPTION
     "A single entry in the table represents a single 
      atmIfConnMapOv component."
   INDEX {
      atmIfIndex,
      atmIfConnMapIndex,
      atmIfConnMapOvIndex }
::= { atmIfConnMapOvRowStatusTable 1 }

AtmIfConnMapOvRowStatusEntry ::= SEQUENCE {
   atmIfConnMapOvRowStatus
      RowStatus,
   atmIfConnMapOvComponentName
      DisplayString,
   atmIfConnMapOvStorageType
      StorageType,
   atmIfConnMapOvIndex
      NonReplicated }

atmIfConnMapOvRowStatus OBJECT-TYPE
   SYNTAX     RowStatus 
   ACCESS     read-only
   STATUS     mandatory
   DESCRIPTION
     "This variable is used as the basis for SNMP naming of
      atmIfConnMapOv components.
      These components cannot be added nor deleted."
::= { atmIfConnMapOvRowStatusEntry 1 }

atmIfConnMapOvComponentName OBJECT-TYPE
   SYNTAX     DisplayString 
   ACCESS     read-only
   STATUS     mandatory
   DESCRIPTION
     "This variable provides the component's string name for
      use with the ASCII Console Interface"
::= { atmIfConnMapOvRowStatusEntry 2 }

atmIfConnMapOvStorageType OBJECT-TYPE
   SYNTAX     StorageType 
   ACCESS     read-only
   STATUS     mandatory
   DESCRIPTION
     "This variable represents the storage type value for the
      atmIfConnMapOv tables."
::= { atmIfConnMapOvRowStatusEntry 4 }

atmIfConnMapOvIndex OBJECT-TYPE
   SYNTAX     NonReplicated 
   ACCESS     not-accessible
   STATUS     mandatory
   DESCRIPTION
     "This variable represents the index for the atmIfConnMapOv tables."
::= { atmIfConnMapOvRowStatusEntry 10 }

atmIfConnMapOvProvTable OBJECT-TYPE
   SYNTAX     SEQUENCE OF AtmIfConnMapOvProvEntry
   ACCESS     not-accessible
   STATUS     mandatory
   DESCRIPTION
     "This group contains provisionable attributes which specify the VCC 
      space to be supported by this ATM interface. The VCC space 
      consists of an optional 'VPI Zero VCC Space' and an optional 
      'Programmable VCC Space'.
      
      The VPI Zero VCC Space is used to support VCCs with a VPI of 
      zero. The VCI values supported in this space range from 0 to a 
      provisioned maximum. The size of the VPI Zero VCC Space must 
      either be 0 or a multiple of 256. A value of 0 implies that no 
      programmable VCCs can be used. In this case 
      numNonZeroVpisForVccs must also be 0.
      
      The optional Programmable VCC Space is used to support VCCs 
      with a VPI other than zero. The VPI values supported in this space 
      must lie in a single contiguous range which excludes VPI 0. The 
      VCI values supported in this space range from 0 to a provisioned 
      maximum. The size of the Programmable VCC Space (should it 
      exist) must adhere to the following rules:
      
      If (firstNonZeroVpiForVccs = 1) THEN
      (numNonZeroVpisForVccs + 1) * numVccsPerNonZeroVpi
      must be a multiple of 256
      OTHERWISE
      numNonZeroVpisForVccs * numVccsPerNonZeroVpi
      must be a multiple of 256
      
      The number of connection identifier resources in the VCC and VPC 
      space can be determined as follows:
      
      The number of connection identifier resources in the VCC and VPC 
      space (not all of which are available for user connections) is 
      reported in the Lp/n Eng Arc totalConnectionPoolAvailable 
      attribute, and can be determined as follows:
      
      IF (numNonZeroVpisForVccs = 0) THEN
      number of connection ID resources =
      256 + numVccsForVpiZero
      OTHERWISE IF (firstNonZeroVpiForVccs = 1) THEN
      number of connection ID resources =
      256 + numVccsForVpiZero +
      (numNonZeroVpisForVccs + 1) * numVccsPerNonZeroVpi
      OTHERWISE
      number of connection ID resources =
      256 + numVccsForVpiZero +
      (numNonZeroVpisForVccs * numVccsPerNonZeroVpi)
      
      The number of connection identifier resources must not exceed the 
      capacity of the port to which the interface is linked. If the Lp has an 
      Eng Arc Cqc Ov component provisioned with a non-zero 
      connectionPoolCapacity the port's capacity is specified by this 
      attribute. Otherwise the port's capacity is indicated by the Lp/n Eng 
      Arc totalConnectionPoolAvailable divided by the number of 
      physical ports on the card."
::= { atmIfConnMapOv 100 }

atmIfConnMapOvProvEntry OBJECT-TYPE
   SYNTAX     AtmIfConnMapOvProvEntry
   ACCESS     not-accessible
   STATUS     mandatory
   DESCRIPTION
     "An entry in the atmIfConnMapOvProvTable."
   INDEX {
      atmIfIndex,
      atmIfConnMapIndex,
      atmIfConnMapOvIndex }
::= { atmIfConnMapOvProvTable 1 }

AtmIfConnMapOvProvEntry ::= SEQUENCE {
   atmIfConnMapOvNumVccsForVpiZero
      Unsigned32,
   atmIfConnMapOvNumNonZeroVpisForVccs
      Unsigned32,
   atmIfConnMapOvFirstNonZeroVpiForVccs
      Unsigned32,
   atmIfConnMapOvNumVccsPerNonZeroVpi
      Unsigned32 }

atmIfConnMapOvNumVccsForVpiZero OBJECT-TYPE
   SYNTAX     Unsigned32 (0..16128)
   ACCESS     read-write
   STATUS     mandatory
   DESCRIPTION
     "This attribute specifies the number of VCCs supported for the VPI 
      Zero VCC Space. The VCI values of these VCCs range from 0 to 
      (numVccsForVpiZero - 1).
      
      The size of the VPI Zero VCC Space must either be 0 or a multiple 
      of 256. A value of 0 implies that no programmable VCCs can be 
      used. In this case numNonZeroVpisForVccs must also 
      be 0. 
      
      The values of all attributes provisioned in this group must adhere to 
      the guidelines laid down in the description of the Provisioned 
      group."
   DEFVAL     { 768 }
::= { atmIfConnMapOvProvEntry 10 }

atmIfConnMapOvNumNonZeroVpisForVccs OBJECT-TYPE
   SYNTAX     Unsigned32 (0..255)
   ACCESS     read-write
   STATUS     mandatory
   DESCRIPTION
     "This attribute specifies the number of contiguous VPIs supported in 
      the optional Programmable VCC Space.
      
      If numNonZeroVpisForVccs is 0 the Programmable VCC Space 
      does not exist. If numNonZeroVpisForVccs is greater than 0 the 
      Programmable VCC Space exists and covers the VPI values ranging 
      from firstNonZeroVpiForVccs to (firstNonZeroVpiForVccs + 
      numNonZeroVpisForVccs - 1).
      
      The values of all attributes provisioned in this group must adhere to 
      the guidelines laid down in the description of the Provisioned 
      group."
   DEFVAL     { 0 }
::= { atmIfConnMapOvProvEntry 20 }

atmIfConnMapOvFirstNonZeroVpiForVccs OBJECT-TYPE
   SYNTAX     Unsigned32 (1 | 16 | 32 | 48 | 64 | 80 | 96 | 112 | 128 | 144 | 160 | 176 | 192 | 208 | 224 | 240)
   ACCESS     read-write
   STATUS     mandatory
   DESCRIPTION
     "This attribute specifies the initial VPI of the optional Programmable 
      VCC Space.
      
      If numNonZeroVpisForVccs is 0 then the Programmable VCC 
      Space does not exist and the value of this attribute is ignored. If 
      numNonZeroVpisForVccs is greater than 0 the Programmable VCC 
      Space exists and covers the VPI values ranging from 
      firstNonZeroVpiForVccs to (firstNonZeroVpiForVccs + 
      numNonZeroVpisForVccs - 1).
      
      The initial VPI of the Programmable VCC Space must either be 1 
      or a non-zero multiple of 16.
      
      The values of all attributes provisioned in this group must adhere to 
      the guidelines laid down in the description of the Provisioned 
      group."
   DEFVAL     { 1 }
::= { atmIfConnMapOvProvEntry 30 }

atmIfConnMapOvNumVccsPerNonZeroVpi OBJECT-TYPE
   SYNTAX     Unsigned32 (2 | 4 | 8 | 16 | 32 | 64 | 128 | 256 | 512 | 1024 | 2048)
   ACCESS     read-write
   STATUS     mandatory
   DESCRIPTION
     "This attribute specifies the number of VCCs supported for each VPI 
      in the Programmable VCC Space. The VCI values of these VCCs 
      range from 0 to (numVccsPerNonZeroVpi - 1) for each VPI in this 
      space.
      
      The values of all attributes provisioned in this group must adhere to 
      the guidelines laid down in the description of the Provisioned 
      group."
   DEFVAL     { 64 }
::= { atmIfConnMapOvProvEntry 40 }


-- AtmIf/n ConnectionAdministrator
-- This component controls connection admission, and reports 
-- statistics about the ATM connections which have been admitted on 
-- this ATM interface.

atmIfCA OBJECT IDENTIFIER ::= { atmIf 3 }



atmIfCARowStatusTable OBJECT-TYPE
   SYNTAX     SEQUENCE OF AtmIfCARowStatusEntry
   ACCESS     not-accessible
   STATUS     mandatory
   DESCRIPTION
     "This entry controls the addition and deletion of 
      atmIfCA components."
::= { atmIfCA 1 }

atmIfCARowStatusEntry OBJECT-TYPE
   SYNTAX     AtmIfCARowStatusEntry
   ACCESS     not-accessible
   STATUS     mandatory
   DESCRIPTION
     "A single entry in the table represents a single 
      atmIfCA component."
   INDEX {
      atmIfIndex,
      atmIfCAIndex }
::= { atmIfCARowStatusTable 1 }

AtmIfCARowStatusEntry ::= SEQUENCE {
   atmIfCARowStatus
      RowStatus,
   atmIfCAComponentName
      DisplayString,
   atmIfCAStorageType
      StorageType,
   atmIfCAIndex
      NonReplicated }

atmIfCARowStatus OBJECT-TYPE
   SYNTAX     RowStatus 
   ACCESS     read-only
   STATUS     mandatory
   DESCRIPTION
     "This variable is used as the basis for SNMP naming of
      atmIfCA components.
      These components cannot be added nor deleted."
::= { atmIfCARowStatusEntry 1 }

atmIfCAComponentName OBJECT-TYPE
   SYNTAX     DisplayString 
   ACCESS     read-only
   STATUS     mandatory
   DESCRIPTION
     "This variable provides the component's string name for
      use with the ASCII Console Interface"
::= { atmIfCARowStatusEntry 2 }

atmIfCAStorageType OBJECT-TYPE
   SYNTAX     StorageType 
   ACCESS     read-only
   STATUS     mandatory
   DESCRIPTION
     "This variable represents the storage type value for the
      atmIfCA tables."
::= { atmIfCARowStatusEntry 4 }

atmIfCAIndex OBJECT-TYPE
   SYNTAX     NonReplicated 
   ACCESS     not-accessible
   STATUS     mandatory
   DESCRIPTION
     "This variable represents the index for the atmIfCA tables."
::= { atmIfCARowStatusEntry 10 }

atmIfCAProvTable OBJECT-TYPE
   SYNTAX     SEQUENCE OF AtmIfCAProvEntry
   ACCESS     not-accessible
   STATUS     mandatory
   DESCRIPTION
     "This group contains provisioned attributes which specify the 
      behavior of Connection Admission Control (CAC) for the ATM 
      connections configured on an ATM interface. Note that the names 
      of some of the attributes follow the conventions of UNI 4.0 for 
      forward compatibility reasons. This does not imply conformance in 
      general with the UNI 4.0 specification."
::= { atmIfCA 100 }

atmIfCAProvEntry OBJECT-TYPE
   SYNTAX     AtmIfCAProvEntry
   ACCESS     not-accessible
   STATUS     mandatory
   DESCRIPTION
     "An entry in the atmIfCAProvTable."
   INDEX {
      atmIfIndex,
      atmIfCAIndex }
::= { atmIfCAProvTable 1 }

AtmIfCAProvEntry ::= SEQUENCE {
   atmIfCAMaxVpcs
      Unsigned32,
   atmIfCAMaxVccs
      Unsigned32,
   atmIfCAMinMulticastBranches
      Unsigned32,
   atmIfCAMaxMulticastBranches
      Unsigned32,
   atmIfCAMaxVpts
      Unsigned32,
   atmIfCAMinAutoSelectedVci
      Unsigned32,
   atmIfCAMinAutoSelectedVciForVpiZero
      Unsigned32,
   atmIfCAMinAutoSelectedVciForNonZeroVpi
      Unsigned32,
   atmIfCAPermittedSvcAtmServiceCategories
      OCTET STRING,
   atmIfCACbrPool
      INTEGER,
   atmIfCACbrCdvt
      Unsigned32,
   atmIfCACbrCellLossRatio
      INTEGER,
   atmIfCASvcCbrHoldingPriority
      INTEGER,
   atmIfCASvcVbrRtHoldingPriority
      INTEGER,
   atmIfCASvcVbrNrtHoldingPriority
      INTEGER,
   atmIfCAVbrRtPool
      INTEGER,
   atmIfCAVbrRtCdvt
      Unsigned32,
   atmIfCAVbrRtCellLossRatio
      INTEGER,
   atmIfCAVbrNrtPool
      INTEGER,
   atmIfCAVbrNrtCdvt
      Unsigned32,
   atmIfCAMaxCaVpcs
      Unsigned32,
   atmIfCAMaxCaVpts
      Unsigned32,
   atmIfCAVbrNrtCellLossRatio
      INTEGER,
   atmIfCAUbrMaxConnections
      Unsigned32,
   atmIfCAMinAutoSelectedVpi
      Unsigned32,
   atmIfCAPermittedAtmServiceCategories
      OCTET STRING,
   atmIfCAMaxAutoSelectedVpi
      Unsigned32,
   atmIfCAMaxAutoSelectedVciForVpiZero
      Unsigned32,
   atmIfCAMaxAutoSelectedVciForNonZeroVpi
      Unsigned32 }

atmIfCAMaxVpcs OBJECT-TYPE
   SYNTAX     Unsigned32 (0..4096)
   ACCESS     read-write
   STATUS     obsolete
   DESCRIPTION
     "This attribute specifies the maximum number of Vpcs that can be 
      activated on this AtmIf. 
      
      If the AtmIf is linked to a LogicalProcessor of cardType other than 
      3pE3Atm, 3pDS3Atm, 3pOC3MmAtm, 3pOC3SmAtm, 3pE1Atm, 
      3pDS1Atm, 2pJ6MAtm, the sum of (maxVccs + maxVpcs + 
      (maxVpts * 3) + 1) across all AtmIfs linked to that Lp must not 
      exceed the totalConnectionPoolCapacity attribute of the Arc 
      component. Note that 3 connections are used for every standard Vpt 
      and 2 for each basic Vpt. If the Arc component doesn't exist, the 
      default value of the Arc totalConnectionPoolCapacity attribute is 
      used as the limit.
      
      This attribute has been obsoleted and its value migrated to the 
      maxVpcs attribute."
   DEFVAL     { 128 }
::= { atmIfCAProvEntry 5 }

atmIfCAMaxVccs OBJECT-TYPE
   SYNTAX     Unsigned32 (0..16384)
   ACCESS     read-write
   STATUS     mandatory
   DESCRIPTION
     "This attribute specifies the maximum number of usable Vccs (and 
      Vpt Vccs) that can be configured on this AtmIf. The value must not 
      exceed the number of non-reserved Vcc identifiers in the Vcc space 
      supported by this AtmIf (which is specified by the 
      ConnectionMapping component).
      
      Furthermore, if the AtmIf is linked to a LogicalProcessor of 
      cardType other than 3pE3Atm, 3pDS3Atm, 3pOC3MmAtm, 
      3pOC3SmAtm, 3pE1Atm, 3pDS1Atm, 2pJ6MAtm, the sum of 
      (maxVccs + maxVpcs + (maxVpts * 3) + 1) across all AtmIfs linked 
      to that Lp must not exceed the totalConnectionPoolCapacity 
      attribute of the Arc component. Note that 3 connections are used for 
      every standard Vpt and 2 for each basic Vpt. If the Arc component 
      doesn't exist, the default value of the Arc 
      totalConnectionPoolCapacity attribute is used as the limit."
   DEFVAL     { 255 }
::= { atmIfCAProvEntry 6 }

atmIfCAMinMulticastBranches OBJECT-TYPE
   SYNTAX     Unsigned32 (0..16384)
   ACCESS     read-write
   STATUS     mandatory
   DESCRIPTION
     "This attribute specifies the guaranteed number of multicast branches 
      that can be activated on this AtmIf, including those activated 
      beneath a Vpt.
      
      The sum of minMulticastBranches across all AtmIfs of the Lp must 
      be less than or equal to the multicastBranchesCapacity attribute of 
      the Arc component of the Lp.
      
      For CQC-based ATM cards, the value of the attribute can not 
      exceed 10752.
      
      If this value is non zero, the Arc component must exist and have 
      multicastBranchesCapacity set to a value greater than or equal to 
      this attribute."
   DEFVAL     { 0 }
::= { atmIfCAProvEntry 7 }

atmIfCAMaxMulticastBranches OBJECT-TYPE
   SYNTAX     Unsigned32 (0 | 1..16384)
   ACCESS     read-write
   STATUS     mandatory
   DESCRIPTION
     "This attribute specifies the maximum number of provisionable 
      multicast branches that can be activated on this AtmIf, including 
      those activated beneath a Vpt.
      
      If this attribute is set to a value other than autoConfigure, it must 
      be greater than or equal to the value of minMulticastBranches of 
      this AtmIf.
      
      For CQC-based ATM cards, the value of the attribute can not 
      exceed 10752.
      
      When this attribute is set to autoConfigure, an appropriate value is 
      selected based on the card type. It is set to 10752 for all CQC-based 
      ATM cards, and to 16384 for ATM IP cards.

      VALUES (

      0 = autoConfigure

      )"
   DEFVAL     { 0 }
::= { atmIfCAProvEntry 8 }

atmIfCAMaxVpts OBJECT-TYPE
   SYNTAX     Unsigned32 (0..4096)
   ACCESS     read-write
   STATUS     obsolete
   DESCRIPTION
     "This attribute specifies the maximum number of Vpts that can be 
      activated on this AtmIf. 
      
      If the AtmIf is linked to a LogicalProcessor of cardType other than 
      3pE3Atm, 3pDS3Atm, 3pOC3MmAtm, 3pOC3SmAtm, 3pE1Atm, 
      3pDS1Atm, 2pJ6MAtm, the sum of (maxVccs + maxVpcs + 
      (maxVpts * 3) + 1) across all AtmIfs linked to that Lp must not 
      exceed the totalConnectionPoolCapacity attribute of the Arc 
      component. Note that 3 connections are used for every standard Vpt 
      and 2 for each basic Vpt. If the Arc component doesn't exist, the 
      default value of the Arc totalConnectionPoolCapacity attribute is 
      used as the limit. 
      
      This attribute has been obsoleted and its value migrated to the 
      maxVpts attribute."
   DEFVAL     { 128 }
::= { atmIfCAProvEntry 9 }

atmIfCAMinAutoSelectedVci OBJECT-TYPE
   SYNTAX     Unsigned32 (32..65535)
   ACCESS     read-write
   STATUS     obsolete
   DESCRIPTION
     "This attribute specifies the default lower boundary for VCIs which 
      are automatically allocated for a switched Vcc. A VCI number is 
      automatically allocated when a switched Vcc does not request a 
      specific VCI number. This attribute has been obsoleted and its value 
      migrated to the minAutoSelectedVciForVpiZero attribute."
   DEFVAL     { 32 }
::= { atmIfCAProvEntry 10 }

atmIfCAMinAutoSelectedVciForVpiZero OBJECT-TYPE
   SYNTAX     Unsigned32 (0..65535)
   ACCESS     read-write
   STATUS     mandatory
   DESCRIPTION
     "This attribute specifies the minimum VCI value which is 
      automatically allocated for a switched Vcc with VPI value of zero. 
      A VCI number is automatically allocated when a switched Vcc does 
      not request a specific VCI number. This value also applies to 
      switched Vccs created beneath Vpt/0."
   DEFVAL     { 32 }
::= { atmIfCAProvEntry 15 }

atmIfCAMinAutoSelectedVciForNonZeroVpi OBJECT-TYPE
   SYNTAX     Unsigned32 (5..65535)
   ACCESS     read-write
   STATUS     mandatory
   DESCRIPTION
     "This attribute specifies the minimum VCI value which is 
      automatically allocated for a switched Vcc with a non-zero VPI 
      value. A VCI number is automatically allocated when a switched 
      Vcc does not request a specific VCI number. This value also applies 
      to switched Vccs created beneath a Vpt."
   DEFVAL     { 32 }
::= { atmIfCAProvEntry 20 }

atmIfCAPermittedSvcAtmServiceCategories OBJECT-TYPE
   SYNTAX     OCTET STRING (SIZE (1))
   ACCESS     read-write
   STATUS     obsolete
   DESCRIPTION
     "This attribute specifies which ATM service categories are permitted 
      on this interface for SVCs. The value of this attribute does not affect 
      control VCCs, such as signalling and ILMI channels. If the value is 
      empty, no SVCs may use this interface.
      This attribute has been obsoleted and its value migrated to the 
      permittedAtmServiceCategories attribute.

      Description of bits:
      unspecifiedBitRate(0)
      constantBitRate(1)
      rtVariableBitRate(2)
      nrtVariableBitRate(3)"
   DEFVAL     { 'f0'H }
::= { atmIfCAProvEntry 25 }

atmIfCACbrPool OBJECT-TYPE
   SYNTAX     INTEGER  {
                 notApplicable(0),
                 pool1(1),
                 pool2(2),
                 pool3(3) }
   ACCESS     read-write
   STATUS     obsolete
   DESCRIPTION
     "This attribute has been obsoleted and migrated under the Cbr 
      subcomponent. In addition, notApplicable is no longer a valid value 
      of the new attribute.
      This attribute specifies the bandwidth pool which is to be used to 
      support the constant bit rate (CBR) service category. When the user 
      does not intend to support the CBR service category, this attribute 
      should be set to notApplicable. Otherwise, one of the three 
      bandwidth pools should be selected. The percentage of link capacity 
      reserved for the given bandwidth pool is the maximum bandwidth 
      that can be allocated to CBR traffic."
   DEFVAL     { pool1 }
::= { atmIfCAProvEntry 30 }

atmIfCACbrCdvt OBJECT-TYPE
   SYNTAX     Unsigned32 (1..10000)
   ACCESS     read-write
   STATUS     obsolete
   DESCRIPTION
     "This attribute has been obsoleted and migrated under the Cbr 
      subcomponent.
      This attribute specifies the cell delay variation tolerance (CDVT) 
      which is to be applied to the entire ATM Interface for CBR traffic."
   DEFVAL     { 250 }
::= { atmIfCAProvEntry 40 }

atmIfCACbrCellLossRatio OBJECT-TYPE
   SYNTAX     INTEGER (-10..0)
   ACCESS     read-write
   STATUS     obsolete
   DESCRIPTION
     "This attribute has been obsoleted and migrated under the Cbr 
      subcomponent. In addition, the type and range of the new attribute 
      have been changed.
      This attribute specifies the tolerable cell loss ratio (CLR) for CBR 
      traffic. The number is the logarithm (base 10) of the CLR. In other 
      words if the target CLR = 1E-10 then cbrCellLossRatio = -10. This 
      number must be the same as the vbrRtCellLossRatio since CBR and 
      rt-VBR traffic have the same discard priority. The cbrCellLossRatio 
      is used by the Connection Admission Control (CAC) algorithm to 
      compute the required (equivalent) cell rate for CBR connections. 
      
      There is a trade-off between the service category CLR and the 
      achievable link utilization. To guarantee an excellent service 
      category, the CLR should be as small as possible (e.g., 1E-10). 
      However, a smaller CLR results in a larger equivalent cell rate for a 
      given connection and hence a lower link utilization."
   DEFVAL     { -10 }
::= { atmIfCAProvEntry 50 }

atmIfCASvcCbrHoldingPriority OBJECT-TYPE
   SYNTAX     INTEGER  {
                 n0(0),
                 n1(1),
                 n2(2),
                 n3(3),
                 n4(4) }
   ACCESS     read-write
   STATUS     obsolete
   DESCRIPTION
     "This attribute has been obsoleted and migrated under the Cbr 
      subcomponent. 
      This attribute specifies the default holding priority which applies for 
      SVC CBR connections. It takes a value from 0 (highest priority) to 
      4 (lowest priority). In a situation where the link bandwidth 
      fluctuates, such as over an IMA link, holding priority is used to 
      determine which connections are held and which are released. 
      Holding priority 4 connections are the first to be released. Holding 
      priority 0 connections are the last to be released."
   DEFVAL     { n3 }
::= { atmIfCAProvEntry 51 }

atmIfCASvcVbrRtHoldingPriority OBJECT-TYPE
   SYNTAX     INTEGER  {
                 n0(0),
                 n1(1),
                 n2(2),
                 n3(3),
                 n4(4) }
   ACCESS     read-write
   STATUS     obsolete
   DESCRIPTION
     "This attribute has been obsoleted and migrated under the RtVbr 
      subcomponent.
      This attribute specifies the default holding priority which applies for 
      SVC rt-VBR connections. It takes a value from 0 (highest priority) 
      to 4 (lowest priority). In a situation where the link bandwidth 
      fluctuates, such as over an IMA link, holding priority is used to 
      determine which connections are held and which are released. 
      Holding priority 4 connections are the first to be released. Holding 
      priority 0 connections are the last to be released."
   DEFVAL     { n3 }
::= { atmIfCAProvEntry 52 }

atmIfCASvcVbrNrtHoldingPriority OBJECT-TYPE
   SYNTAX     INTEGER  {
                 n0(0),
                 n1(1),
                 n2(2),
                 n3(3),
                 n4(4) }
   ACCESS     read-write
   STATUS     obsolete
   DESCRIPTION
     "This attribute has been obsoleted and migrated under the NrtVbr 
      subcomponent.
      This attribute specifies the default holding priority which applies for 
      SVC nrt-VBR connections. It takes a value from 0 (highest priority) 
      to 4 (lowest priority). In a situation where the link bandwidth 
      fluctuates, such as over an IMA link, holding priority is used to 
      determine which connections are held and which are released. 
      Holding priority 4 connections are the first to be released. Holding 
      priority 0 connections are the last to be released."
   DEFVAL     { n3 }
::= { atmIfCAProvEntry 53 }

atmIfCAVbrRtPool OBJECT-TYPE
   SYNTAX     INTEGER  {
                 notApplicable(0),
                 pool1(1),
                 pool2(2),
                 pool3(3) }
   ACCESS     read-write
   STATUS     obsolete
   DESCRIPTION
     "This attribute has been obsoleted and migrated under the RtVbr 
      subcomponent. In addition, notApplicable is no longer a valid value 
      of the new attribute.
      This attribute specifies the bandwidth pool which is to be used to 
      support the variable bit rate real time (rt-VBR) service category. 
      When the user does not intend to support the rt-VBR service 
      category, this attribute should be set to notApplicable. Otherwise, 
      one of the three bandwidth pools should be selected. The percentage 
      of link capacity reserved for the given bandwidth pool is the 
      maximum bandwidth that can be allocated to rt-VBR traffic."
   DEFVAL     { pool1 }
::= { atmIfCAProvEntry 60 }

atmIfCAVbrRtCdvt OBJECT-TYPE
   SYNTAX     Unsigned32 (1..1200000)
   ACCESS     read-write
   STATUS     obsolete
   DESCRIPTION
     "This attribute has been obsoleted and migrated under the RtVbr 
      subcomponent.
      This attribute specifies the cell delay variation tolerance (CDVT) 
      which is to be applied to the entire ATM Interface for rt-VBR 
      traffic."
   DEFVAL     { 250 }
::= { atmIfCAProvEntry 70 }

atmIfCAVbrRtCellLossRatio OBJECT-TYPE
   SYNTAX     INTEGER (-10..0)
   ACCESS     read-write
   STATUS     obsolete
   DESCRIPTION
     "This attribute has been obsoleted and migrated under the RtVbr 
      subcomponent. In addition, the type and range of this attribute has 
      been changed.
      This attribute specifies the tolerable cell loss ratio (CLR) for rt-
      VBR traffic. The number is the logarithm (base 10) of the CLR. In 
      other words if the target CLR = 1E-10 then vbrRtCellLossRatio = -
      10. This number must be the same as the cbrCellLossRatio since 
      CBR and rt-VBR traffic have the same discard priority. The 
      vbrRtCellLossRatio is used by the Connection Admission Control 
      (CAC) algorithm to compute the required (equivalent) cell rate for 
      rt-VBR connections. This number must be less than or equal to the 
      vbrNrtCellLossRatio, since rt-VBR traffic has a higher discard 
      priority.
      
      There is a trade-off between the service category CLR and the 
      achievable link utilization. To guarantee an excellent service 
      category, the CLR should be as small as possible (e.g., 1E-10). 
      However, a smaller CLR results in a larger equivalent cell rate for a 
      given connection and hence a lower link utilization."
   DEFVAL     { -10 }
::= { atmIfCAProvEntry 80 }

atmIfCAVbrNrtPool OBJECT-TYPE
   SYNTAX     INTEGER  {
                 notApplicable(0),
                 pool1(1),
                 pool2(2),
                 pool3(3) }
   ACCESS     read-write
   STATUS     obsolete
   DESCRIPTION
     "This attribute has been obsoleted and migrated under the NrtVbr 
      subcomponent. In addition, notApplicable is no longer a valid value 
      of the new attribute.
      This attribute specifies the bandwidth pool which is to be used to 
      support the variable bit rate non-real time (nrt-VBR) service 
      category. When the user does not intend to support the nrt-VBR, 
      this attribute should be set to notApplicable. Otherwise, one of the 
      three bandwidth pools should be selected. The percentage of link 
      capacity reserved for the given bandwidth pool is the maximum 
      bandwidth that can be allocated to nrt-VBR traffic."
   DEFVAL     { pool1 }
::= { atmIfCAProvEntry 90 }

atmIfCAVbrNrtCdvt OBJECT-TYPE
   SYNTAX     Unsigned32 (1..1200000)
   ACCESS     read-write
   STATUS     obsolete
   DESCRIPTION
     "This attribute has been obsoleted and migrated under the NrtVbr 
      subcomponent.
      This attribute specifies the cell delay variation tolerance (CDVT), 
      which is to be applied to the entire ATM Interface for nrt-VBR 
      traffic."
   DEFVAL     { 250 }
::= { atmIfCAProvEntry 100 }

atmIfCAMaxCaVpcs OBJECT-TYPE
   SYNTAX     Unsigned32 (0..4096)
   ACCESS     read-write
   STATUS     mandatory
   DESCRIPTION
     "This attribute specifies the maximum number of Vpcs that can be 
      activated on this AtmIf. 
      
      If the AtmIf is linked to a LogicalProcessor of cardType other than 
      3pE3Atm, 3pDS3Atm, 3pOC3MmAtm, 3pOC3SmAtm, 3pE1Atm, 
      3pDS1Atm, 2pJ6MAtm, the sum of (maxVccs + maxVpcs + 
      (maxVpts * 3) + 1) across all AtmIfs linked to that Lp must not 
      exceed the totalConnectionPoolCapacity attribute of the Arc 
      component. Note that 3 connections are used for every standard Vpt 
      and 2 for each basic Vpt. If the Arc component doesn't exist, the 
      default value of the Arc totalConnectionPoolCapacity attribute is 
      used as the limit."
   DEFVAL     { 128 }
::= { atmIfCAProvEntry 105 }

atmIfCAMaxCaVpts OBJECT-TYPE
   SYNTAX     Unsigned32 (0..4096)
   ACCESS     read-write
   STATUS     mandatory
   DESCRIPTION
     "This attribute specifies the maximum number of Vpts that can be 
      activated on this AtmIf. 
      
      If the AtmIf is linked to a LogicalProcessor of cardType other than 
      3pE3Atm, 3pDS3Atm, 3pOC3MmAtm, 3pOC3SmAtm, 3pE1Atm, 
      3pDS1Atm, 2pJ6MAtm, the sum of (maxVccs + maxVpcs + 
      (maxVpts * 3) + 1) across all AtmIfs linked to that Lp must not 
      exceed the totalConnectionPoolCapacity attribute of the Arc 
      component. Note that 3 connections are used for every standard Vpt 
      and 2 for each basic Vpt. If the Arc component doesn't exist, the 
      default value of the Arc totalConnectionPoolCapacity attribute is 
      used as the limit."
   DEFVAL     { 128 }
::= { atmIfCAProvEntry 106 }

atmIfCAVbrNrtCellLossRatio OBJECT-TYPE
   SYNTAX     INTEGER (-10..0)
   ACCESS     read-write
   STATUS     obsolete
   DESCRIPTION
     "This attribute has been obsoleted and migrated under the NrtVbr 
      subcomponent. In addition, the type and range of new attribute has 
      been changed.
      This attribute specifies the tolerable cell loss ratio (CLR) for nrt-
      VBR traffic. The number is the logarithm (base 10) of the CLR. In 
      other words if the target CLR = 1E-10 then vbrNrtCellLossRatio = -
      10.This number must be greater than or equal to 
      vbrRtCellLossRatio since rt-VBR traffic has a higher discard 
      priority. The vbrNrtCellLossRatio is used by the Connection 
      Admission Control (CAC) algorithm to compute the required 
      (equivalent) cell rate for nrt-VBR connections. 
      
      There is a trade-off between the service category CLR and the 
      achievable link utilization. To guarantee an excellent service 
      category, the CLR should be as small as possible (e.g., 1E-10). 
      However, a smaller CLR results in a larger equivalent cell rate for a 
      given connection and hence a lower link utilization."
   DEFVAL     { -7 }
::= { atmIfCAProvEntry 110 }

atmIfCAUbrMaxConnections OBJECT-TYPE
   SYNTAX     Unsigned32 (0..16384)
   ACCESS     read-write
   STATUS     obsolete
   DESCRIPTION
     "This attribute is obsolete in P6.0, and has been migrated to the CA 
      Ubr/0 maxVccs and maxVpcs attributes. 
      
      This attribute specifies the maximum number of unspecified bit rate 
      (UBR) connections which are to be admitted managed by this CA. 
      This number is enforced by the connection admission control 
      (CAC) algorithm for this AtmIf."
   DEFVAL     { 16384 }
::= { atmIfCAProvEntry 120 }

atmIfCAMinAutoSelectedVpi OBJECT-TYPE
   SYNTAX     Unsigned32 (1..4095)
   ACCESS     read-write
   STATUS     mandatory
   DESCRIPTION
     "This attribute specifies the minimum VPI value which will be 
      automatically allocated for a switched Vpc. A VPI number is 
      automatically allocated when a switched Vpc does not request a 
      specific VPI number."
   DEFVAL     { 1 }
::= { atmIfCAProvEntry 121 }

atmIfCAPermittedAtmServiceCategories OBJECT-TYPE
   SYNTAX     OCTET STRING (SIZE (1))
   ACCESS     read-write
   STATUS     mandatory
   DESCRIPTION
     "This attribute specifies which ATM service categories are permitted 
      on this interface for SVPs and SVCs. The value of this attribute 
      does not affect control VCCs, such as signalling and ILMI channels. 
      If the value is empty, no non-control SVPs or SVCs will use this 
      interface. This attribute is ignored for the admission of provisioned 
      VCCs, VPCs, VPTs, S-PVCs, and S-PVPs.
      
      The value of the permittedAtmServiceCategories in a VPT CA 
      overrides this AtmIf CA setting for all the given VPT's VCCs.

      Description of bits:
      unspecifiedBitRate(0)
      constantBitRate(1)
      rtVariableBitRate(2)
      nrtVariableBitRate(3)"
   DEFVAL     { 'f0'H }
::= { atmIfCAProvEntry 122 }

atmIfCAMaxAutoSelectedVpi OBJECT-TYPE
   SYNTAX     Unsigned32 (1..4095)
   ACCESS     read-write
   STATUS     mandatory
   DESCRIPTION
     "This attribute specifies the maximumVPI value which will be 
      automatically allocated for a switched Vpc or Vcc. A VPI number is 
      automatically allocated when a switched Vpc or Vcc does not 
      request a specific VPI number."
   DEFVAL     { 128 }
::= { atmIfCAProvEntry 125 }

atmIfCAMaxAutoSelectedVciForVpiZero OBJECT-TYPE
   SYNTAX     Unsigned32 (0..65535)
   ACCESS     read-write
   STATUS     mandatory
   DESCRIPTION
     "This attribute specifies the maximum VCI value which is 
      automatically allocated for a switched Vcc. A VCI number is 
      automatically allocated when a switched Vcc does not request a 
      specific VCI number. This value also applies to switched Vccs 
      created beneath Vpt/0."
   DEFVAL     { 767 }
::= { atmIfCAProvEntry 126 }

atmIfCAMaxAutoSelectedVciForNonZeroVpi OBJECT-TYPE
   SYNTAX     Unsigned32 (5..65535)
   ACCESS     read-write
   STATUS     mandatory
   DESCRIPTION
     "This attribute specifies the maximum VCI value which is 
      automatically allocated for a switched Vcc. A VCI number is 
      automatically allocated when a switched Vcc does not request a 
      specific VCI number. This value also applies to switched Vccs 
      created beneath non zero Vpts."
   DEFVAL     { 63 }
::= { atmIfCAProvEntry 127 }

atmIfCAOperTable OBJECT-TYPE
   SYNTAX     SEQUENCE OF AtmIfCAOperEntry
   ACCESS     not-accessible
   STATUS     mandatory
   DESCRIPTION
     "This group contains operational attributes giving statistics about the 
      ATM connections configured on an ATM interface."
::= { atmIfCA 110 }

atmIfCAOperEntry OBJECT-TYPE
   SYNTAX     AtmIfCAOperEntry
   ACCESS     not-accessible
   STATUS     mandatory
   DESCRIPTION
     "An entry in the atmIfCAOperTable."
   INDEX {
      atmIfIndex,
      atmIfCAIndex }
::= { atmIfCAOperTable 1 }

AtmIfCAOperEntry ::= SEQUENCE {
   atmIfCAPermanentVpcs
      Unsigned32,
   atmIfCAPermanentVpts
      Unsigned32,
   atmIfCAPermanentVccs
      Unsigned32,
   atmIfCASwitchedVccs
      Gauge32,
   atmIfCASwitchedMulticastBranches
      Gauge32,
   atmIfCATroubledVpcs
      Unsigned32,
   atmIfCATroubledVpts
      Unsigned32,
   atmIfCATroubledVccs
      Unsigned32,
   atmIfCAUbrAvailableConnections
      Gauge32,
   atmIfCAConnectionPoolUsage
      Gauge32,
   atmIfCASwitchedVpcs
      Gauge32,
   atmIfCAVirtualLinkRequestedBandwidth
      Unsigned32,
   atmIfCAVirtualLinkAdmittedBandwidth
      Unsigned32,
   atmIfCAVirtualLinkUnallocatedBandwidth
      Unsigned32 }

atmIfCAPermanentVpcs OBJECT-TYPE
   SYNTAX     Unsigned32 (0..4096)
   ACCESS     read-only
   STATUS     mandatory
   DESCRIPTION
     "This attribute indicates the number of permanent Vpcs that are 
      currently provisioned on this interface."
::= { atmIfCAOperEntry 10 }

atmIfCAPermanentVpts OBJECT-TYPE
   SYNTAX     Unsigned32 (0..4096)
   ACCESS     read-only
   STATUS     mandatory
   DESCRIPTION
     "This attribute indicates the number of permanent Vpts that are 
      currently provisioned on this interface."
::= { atmIfCAOperEntry 15 }

atmIfCAPermanentVccs OBJECT-TYPE
   SYNTAX     Unsigned32 (0..16384)
   ACCESS     read-only
   STATUS     mandatory
   DESCRIPTION
     "This attribute indicates the number of permanent Vccs that are 
      currently provisioned on this interface (this includes Vccs having 
      SrcPvc subcomponents). Vpt Vccs are also included in this count."
::= { atmIfCAOperEntry 20 }

atmIfCASwitchedVccs OBJECT-TYPE
   SYNTAX     Gauge32 (0..16384)
   ACCESS     read-only
   STATUS     mandatory
   DESCRIPTION
     "This attribute indicates the number of switched Vccs that are 
      currently active on this interface. Vpt Vccs are also included in this 
      count."
::= { atmIfCAOperEntry 30 }

atmIfCASwitchedMulticastBranches OBJECT-TYPE
   SYNTAX     Gauge32 (0..10752)
   ACCESS     read-only
   STATUS     mandatory
   DESCRIPTION
     "This attribute indicates the number of multicast branches used in 
      switched Vccs, including Vpt Vccs, that are currently active on this 
      interface.
      The sum of this attribute for all AtmIf components linked to an Lp 
      gives the value of multiCastBranchesUsage in the Arc component."
::= { atmIfCAOperEntry 40 }

atmIfCATroubledVpcs OBJECT-TYPE
   SYNTAX     Unsigned32 (0..4096)
   ACCESS     read-only
   STATUS     mandatory
   DESCRIPTION
     "This attribute indicates the number of troubled Vpcs on this 
      interface. A Vpc is 'troubled' if its operational troubled attribute 
      has the value yes."
::= { atmIfCAOperEntry 60 }

atmIfCATroubledVpts OBJECT-TYPE
   SYNTAX     Unsigned32 (0..4096)
   ACCESS     read-only
   STATUS     mandatory
   DESCRIPTION
     "This attribute indicates the number of troubled Vpts on this 
      interface. A Vpt is 'troubled' if its operational troubled attribute has 
      the value yes."
::= { atmIfCAOperEntry 65 }

atmIfCATroubledVccs OBJECT-TYPE
   SYNTAX     Unsigned32 (0..16384)
   ACCESS     read-only
   STATUS     mandatory
   DESCRIPTION
     "This attribute indicates the number of troubled Vccs on this 
      interface. A Vcc is 'troubled' if its operational troubled attribute 
      has the value yes."
::= { atmIfCAOperEntry 70 }

atmIfCAUbrAvailableConnections OBJECT-TYPE
   SYNTAX     Gauge32 (0..16384)
   ACCESS     read-only
   STATUS     obsolete
   DESCRIPTION
     "This attribute is historical in P6.0. Refer instead to the vccUsage 
      and vpcUsage under the AtmIf CA Ubr component.
      
      This attribute indicates the available UBR connections. Its value is 
      ubrMaxConnections minus the number of admitted connections."
::= { atmIfCAOperEntry 80 }

atmIfCAConnectionPoolUsage OBJECT-TYPE
   SYNTAX     Gauge32 (0..16384)
   ACCESS     read-only
   STATUS     mandatory
   DESCRIPTION
     "This attribute indicates the number of enabled VCCs, VPCs, and 
      VPTs in this AtmIf. An example of a VCC not in the enabled state is 
      a Vcc with a Test subcomponent where the test is not started.
      
      Each Vcc or Vpc is counted as 1 connection. Each basic Vpt is 
      counted as 2 connections and each standard Vpt is counted as 3 
      connections.
      
      Each connection appropriately reduces the number of connections 
      indicated in Arc totalConnectionPoolAvailable and increases the 
      number of connections indicated in Arc totalConnectionPoolUsage."
::= { atmIfCAOperEntry 81 }

atmIfCASwitchedVpcs OBJECT-TYPE
   SYNTAX     Gauge32 (0..4095)
   ACCESS     read-only
   STATUS     mandatory
   DESCRIPTION
     "This attribute indicates the number of switched Vpcs that are 
      currently active on this interface."
::= { atmIfCAOperEntry 82 }

atmIfCAVirtualLinkRequestedBandwidth OBJECT-TYPE
   SYNTAX     Unsigned32 (1..16384)
   ACCESS     read-only
   STATUS     mandatory
   DESCRIPTION
     "This attribute specifies the total bandwidth requested by all Virtual 
      Link VPTs for this AtmIf."
::= { atmIfCAOperEntry 130 }

atmIfCAVirtualLinkAdmittedBandwidth OBJECT-TYPE
   SYNTAX     Unsigned32 (1..16384)
   ACCESS     read-only
   STATUS     mandatory
   DESCRIPTION
     "This attribute specifies the total bandwidth allocated to all Virtual 
      Link VPTs for this AtmIf."
::= { atmIfCAOperEntry 131 }

atmIfCAVirtualLinkUnallocatedBandwidth OBJECT-TYPE
   SYNTAX     Unsigned32 (1..16384)
   ACCESS     read-only
   STATUS     mandatory
   DESCRIPTION
     "This attribute specifies the total bandwidth that has not been 
      allocated to either Virtual Link VPTs or the AtmIf."
::= { atmIfCAOperEntry 132 }

atmIfCABwPoolTable OBJECT-TYPE
   SYNTAX     SEQUENCE OF AtmIfCABwPoolEntry
   ACCESS     not-accessible
   STATUS     mandatory
   DESCRIPTION
     "Link capacity is partitioned into five bandwidth pools. This attribute 
      specifies the percentage of link bandwidth that is allowed for each 
      pool. The percentage for each pool ranges from 0% to 12,800%. 
      This allows for both under and over subscription of the link. Under 
      subscription occurs when the sum of the percentages assigned to the 
      five pools is less than 100%. Over subscription occurs when the 
      sum of the percentages for the five pools exceeds 100%."
::= { atmIfCA 293 }

atmIfCABwPoolEntry OBJECT-TYPE
   SYNTAX     AtmIfCABwPoolEntry
   ACCESS     not-accessible
   STATUS     mandatory
   DESCRIPTION
     "An entry in the atmIfCABwPoolTable."
   INDEX {
      atmIfIndex,
      atmIfCAIndex,
      atmIfCABwPoolIndex }
::= { atmIfCABwPoolTable 1 }

AtmIfCABwPoolEntry ::= SEQUENCE {
   atmIfCABwPoolIndex
      Integer32,
   atmIfCABwPoolValue
      Unsigned32 }

atmIfCABwPoolIndex OBJECT-TYPE
   SYNTAX     Integer32 (1..5)
   ACCESS     not-accessible
   STATUS     mandatory
   DESCRIPTION
     "This variable represents the atmIfCABwPoolTable
      specific index for the atmIfCABwPoolTable."
::= { atmIfCABwPoolEntry 1 }

atmIfCABwPoolValue OBJECT-TYPE
   SYNTAX     Unsigned32 (0..12800)
   ACCESS     read-write
   STATUS     mandatory
   DESCRIPTION
     "This variable represents an individual value for the
      atmIfCABwPoolTable."
::= { atmIfCABwPoolEntry 2 }

atmIfCAPoolRequBwTable OBJECT-TYPE
   SYNTAX     SEQUENCE OF AtmIfCAPoolRequBwEntry
   ACCESS     not-accessible
   STATUS     mandatory
   DESCRIPTION
     "This attribute indicates the total requested bandwidth from 
      bandwidthPool except for connections managed by a Vpt CA. Its 
      value is the sum of the equivalent cell rates (ECR) for connections 
      which are admitted, and for connections which are requesting 
      admission but have not yet been admitted."
::= { atmIfCA 296 }

atmIfCAPoolRequBwEntry OBJECT-TYPE
   SYNTAX     AtmIfCAPoolRequBwEntry
   ACCESS     not-accessible
   STATUS     mandatory
   DESCRIPTION
     "An entry in the atmIfCAPoolRequBwTable."
   INDEX {
      atmIfIndex,
      atmIfCAIndex,
      atmIfCAPoolRequBwIndex }
::= { atmIfCAPoolRequBwTable 1 }

AtmIfCAPoolRequBwEntry ::= SEQUENCE {
   atmIfCAPoolRequBwIndex
      Integer32,
   atmIfCAPoolRequBwValue
      Gauge32 }

atmIfCAPoolRequBwIndex OBJECT-TYPE
   SYNTAX     Integer32 (1..5)
   ACCESS     not-accessible
   STATUS     mandatory
   DESCRIPTION
     "This variable represents the atmIfCAPoolRequBwTable
      specific index for the atmIfCAPoolRequBwTable."
::= { atmIfCAPoolRequBwEntry 1 }

atmIfCAPoolRequBwValue OBJECT-TYPE
   SYNTAX     Gauge32 (0..2147483647)
   ACCESS     read-only
   STATUS     mandatory
   DESCRIPTION
     "This variable represents an individual value for the
      atmIfCAPoolRequBwTable."
::= { atmIfCAPoolRequBwEntry 2 }

atmIfCAPoolAdmitBwTable OBJECT-TYPE
   SYNTAX     SEQUENCE OF AtmIfCAPoolAdmitBwEntry
   ACCESS     not-accessible
   STATUS     mandatory
   DESCRIPTION
     "This attribute indicates the total admitted bandwidth in 
      bandwidthPool except for connections managed by a Vpt CA. Its 
      value is the sum of the equivalent cell rates (ECR) of the admitted 
      connections."
::= { atmIfCA 299 }

atmIfCAPoolAdmitBwEntry OBJECT-TYPE
   SYNTAX     AtmIfCAPoolAdmitBwEntry
   ACCESS     not-accessible
   STATUS     mandatory
   DESCRIPTION
     "An entry in the atmIfCAPoolAdmitBwTable."
   INDEX {
      atmIfIndex,
      atmIfCAIndex,
      atmIfCAPoolAdmitBwIndex }
::= { atmIfCAPoolAdmitBwTable 1 }

AtmIfCAPoolAdmitBwEntry ::= SEQUENCE {
   atmIfCAPoolAdmitBwIndex
      Integer32,
   atmIfCAPoolAdmitBwValue
      Gauge32 }

atmIfCAPoolAdmitBwIndex OBJECT-TYPE
   SYNTAX     Integer32 (1..5)
   ACCESS     not-accessible
   STATUS     mandatory
   DESCRIPTION
     "This variable represents the atmIfCAPoolAdmitBwTable
      specific index for the atmIfCAPoolAdmitBwTable."
::= { atmIfCAPoolAdmitBwEntry 1 }

atmIfCAPoolAdmitBwValue OBJECT-TYPE
   SYNTAX     Gauge32 (0..2147483647)
   ACCESS     read-only
   STATUS     mandatory
   DESCRIPTION
     "This variable represents an individual value for the
      atmIfCAPoolAdmitBwTable."
::= { atmIfCAPoolAdmitBwEntry 2 }

atmIfCAPoolAvailBwTable OBJECT-TYPE
   SYNTAX     SEQUENCE OF AtmIfCAPoolAvailBwEntry
   ACCESS     not-accessible
   STATUS     obsolete
   DESCRIPTION
     "This attribute indicates the total available bandwidth in 
      bandwidthPool. Its value is the link capacity reduced by the sum of 
      the equivalent cell rates (ECR) of the admitted connections."
::= { atmIfCA 300 }

atmIfCAPoolAvailBwEntry OBJECT-TYPE
   SYNTAX     AtmIfCAPoolAvailBwEntry
   ACCESS     not-accessible
   STATUS     obsolete
   DESCRIPTION
     "An entry in the atmIfCAPoolAvailBwTable."
   INDEX {
      atmIfIndex,
      atmIfCAIndex,
      atmIfCAPoolAvailBwIndex }
::= { atmIfCAPoolAvailBwTable 1 }

AtmIfCAPoolAvailBwEntry ::= SEQUENCE {
   atmIfCAPoolAvailBwIndex
      Integer32,
   atmIfCAPoolAvailBwValue
      Gauge32 }

atmIfCAPoolAvailBwIndex OBJECT-TYPE
   SYNTAX     Integer32 (1..3)
   ACCESS     not-accessible
   STATUS     obsolete
   DESCRIPTION
     "This variable represents the atmIfCAPoolAvailBwTable
      specific index for the atmIfCAPoolAvailBwTable."
::= { atmIfCAPoolAvailBwEntry 1 }

atmIfCAPoolAvailBwValue OBJECT-TYPE
   SYNTAX     Gauge32 (0..2147483647)
   ACCESS     read-only
   STATUS     obsolete
   DESCRIPTION
     "This variable represents an individual value for the
      atmIfCAPoolAvailBwTable."
::= { atmIfCAPoolAvailBwEntry 2 }

atmIfCAPoolProvBwTable OBJECT-TYPE
   SYNTAX     SEQUENCE OF AtmIfCAPoolProvBwEntry
   ACCESS     not-accessible
   STATUS     mandatory
   DESCRIPTION
     "This attribute indicates the total bandwidth from bandwidthPool 
      which is specified by provisioned connections except for those 
      managed by a Vpt CA. Its value is the sum of the equivalent cell 
      rates (ECR) of the provisioned connections. Provisioned 
      connections include provisioned AtmIf Vccs, AtmIf Vpcs, AtmIf 
      Vpts, Vpt Vccs, and Vccs or Vpcs with a Src component under them."
::= { atmIfCA 319 }

atmIfCAPoolProvBwEntry OBJECT-TYPE
   SYNTAX     AtmIfCAPoolProvBwEntry
   ACCESS     not-accessible
   STATUS     mandatory
   DESCRIPTION
     "An entry in the atmIfCAPoolProvBwTable."
   INDEX {
      atmIfIndex,
      atmIfCAIndex,
      atmIfCAPoolProvBwIndex }
::= { atmIfCAPoolProvBwTable 1 }

AtmIfCAPoolProvBwEntry ::= SEQUENCE {
   atmIfCAPoolProvBwIndex
      Integer32,
   atmIfCAPoolProvBwValue
      Gauge32 }

atmIfCAPoolProvBwIndex OBJECT-TYPE
   SYNTAX     Integer32 (1..5)
   ACCESS     not-accessible
   STATUS     mandatory
   DESCRIPTION
     "This variable represents the atmIfCAPoolProvBwTable
      specific index for the atmIfCAPoolProvBwTable."
::= { atmIfCAPoolProvBwEntry 1 }

atmIfCAPoolProvBwValue OBJECT-TYPE
   SYNTAX     Gauge32 (0..2147483647)
   ACCESS     read-only
   STATUS     mandatory
   DESCRIPTION
     "This variable represents an individual value for the
      atmIfCAPoolProvBwTable."
::= { atmIfCAPoolProvBwEntry 2 }

atmIfCAPoolWaitAdmConnsTable OBJECT-TYPE
   SYNTAX     SEQUENCE OF AtmIfCAPoolWaitAdmConnsEntry
   ACCESS     not-accessible
   STATUS     mandatory
   DESCRIPTION
     "This attribute indicates the total number of connections which have 
      currently requested admission in bandwidthPool but are not yet 
      admitted. This attribute does not include connections that are 
      managed by a Vpt CA."
::= { atmIfCA 320 }

atmIfCAPoolWaitAdmConnsEntry OBJECT-TYPE
   SYNTAX     AtmIfCAPoolWaitAdmConnsEntry
   ACCESS     not-accessible
   STATUS     mandatory
   DESCRIPTION
     "An entry in the atmIfCAPoolWaitAdmConnsTable."
   INDEX {
      atmIfIndex,
      atmIfCAIndex,
      atmIfCAPoolWaitAdmConnsIndex }
::= { atmIfCAPoolWaitAdmConnsTable 1 }

AtmIfCAPoolWaitAdmConnsEntry ::= SEQUENCE {
   atmIfCAPoolWaitAdmConnsIndex
      Integer32,
   atmIfCAPoolWaitAdmConnsValue
      Gauge32 }

atmIfCAPoolWaitAdmConnsIndex OBJECT-TYPE
   SYNTAX     Integer32 (1..5)
   ACCESS     not-accessible
   STATUS     mandatory
   DESCRIPTION
     "This variable represents the atmIfCAPoolWaitAdmConnsTable
      specific index for the atmIfCAPoolWaitAdmConnsTable."
::= { atmIfCAPoolWaitAdmConnsEntry 1 }

atmIfCAPoolWaitAdmConnsValue OBJECT-TYPE
   SYNTAX     Gauge32 (0..16384)
   ACCESS     read-only
   STATUS     mandatory
   DESCRIPTION
     "This variable represents an individual value for the
      atmIfCAPoolWaitAdmConnsTable."
::= { atmIfCAPoolWaitAdmConnsEntry 2 }

atmIfCAPoolAdmConnsTable OBJECT-TYPE
   SYNTAX     SEQUENCE OF AtmIfCAPoolAdmConnsEntry
   ACCESS     not-accessible
   STATUS     mandatory
   DESCRIPTION
     "This attribute indicates the total number of connections which are 
      currently admitted in bandwidthPool except for those managed by a 
      Vpt CA."
::= { atmIfCA 321 }

atmIfCAPoolAdmConnsEntry OBJECT-TYPE
   SYNTAX     AtmIfCAPoolAdmConnsEntry
   ACCESS     not-accessible
   STATUS     mandatory
   DESCRIPTION
     "An entry in the atmIfCAPoolAdmConnsTable."
   INDEX {
      atmIfIndex,
      atmIfCAIndex,
      atmIfCAPoolAdmConnsIndex }
::= { atmIfCAPoolAdmConnsTable 1 }

AtmIfCAPoolAdmConnsEntry ::= SEQUENCE {
   atmIfCAPoolAdmConnsIndex
      Integer32,
   atmIfCAPoolAdmConnsValue
      Gauge32 }

atmIfCAPoolAdmConnsIndex OBJECT-TYPE
   SYNTAX     Integer32 (1..5)
   ACCESS     not-accessible
   STATUS     mandatory
   DESCRIPTION
     "This variable represents the atmIfCAPoolAdmConnsTable
      specific index for the atmIfCAPoolAdmConnsTable."
::= { atmIfCAPoolAdmConnsEntry 1 }

atmIfCAPoolAdmConnsValue OBJECT-TYPE
   SYNTAX     Gauge32 (0..16384)
   ACCESS     read-only
   STATUS     mandatory
   DESCRIPTION
     "This variable represents an individual value for the
      atmIfCAPoolAdmConnsTable."
::= { atmIfCAPoolAdmConnsEntry 2 }

atmIfCAPoolAvailableBwTable OBJECT-TYPE
   SYNTAX     SEQUENCE OF AtmIfCAPoolAvailableBwEntry
   ACCESS     not-accessible
   STATUS     mandatory
   DESCRIPTION
     "This attribute indicates the total available bandwidth in 
      bandwidthPool. A positive number indicates that there is still 
      bandwidth available in the pool which has not been allocated. A 
      negative value indicates that some bandwidth-elastic provisioned 
      connections are running in reduced mode, where their allocated 
      bandwidth is below their originally allocated ECR. The negative 
      amount is equal to the sum of the bwReduction attribute for all 
      connections under this bandwidthPool."
::= { atmIfCA 326 }

atmIfCAPoolAvailableBwEntry OBJECT-TYPE
   SYNTAX     AtmIfCAPoolAvailableBwEntry
   ACCESS     not-accessible
   STATUS     mandatory
   DESCRIPTION
     "An entry in the atmIfCAPoolAvailableBwTable."
   INDEX {
      atmIfIndex,
      atmIfCAIndex,
      atmIfCAPoolAvailableBwIndex }
::= { atmIfCAPoolAvailableBwTable 1 }

AtmIfCAPoolAvailableBwEntry ::= SEQUENCE {
   atmIfCAPoolAvailableBwIndex
      Integer32,
   atmIfCAPoolAvailableBwValue
      INTEGER }

atmIfCAPoolAvailableBwIndex OBJECT-TYPE
   SYNTAX     Integer32 (1..5)
   ACCESS     not-accessible
   STATUS     mandatory
   DESCRIPTION
     "This variable represents the atmIfCAPoolAvailableBwTable
      specific index for the atmIfCAPoolAvailableBwTable."
::= { atmIfCAPoolAvailableBwEntry 1 }

atmIfCAPoolAvailableBwValue OBJECT-TYPE
   SYNTAX     INTEGER (-2147483648..2147483647)
   ACCESS     read-only
   STATUS     mandatory
   DESCRIPTION
     "This variable represents an individual value for the
      atmIfCAPoolAvailableBwTable."
::= { atmIfCAPoolAvailableBwEntry 2 }


-- AtmIf/n CA ConstantBitRate/n 
-- This component manages the default characteristics of the constant 
-- bit rate (CBR) service category.

atmIfCACbr OBJECT IDENTIFIER ::= { atmIfCA 2 }



atmIfCACbrRowStatusTable OBJECT-TYPE
   SYNTAX     SEQUENCE OF AtmIfCACbrRowStatusEntry
   ACCESS     not-accessible
   STATUS     mandatory
   DESCRIPTION
     "This entry controls the addition and deletion of 
      atmIfCACbr components."
::= { atmIfCACbr 1 }

atmIfCACbrRowStatusEntry OBJECT-TYPE
   SYNTAX     AtmIfCACbrRowStatusEntry
   ACCESS     not-accessible
   STATUS     mandatory
   DESCRIPTION
     "A single entry in the table represents a single 
      atmIfCACbr component."
   INDEX {
      atmIfIndex,
      atmIfCAIndex,
      atmIfCACbrIndex }
::= { atmIfCACbrRowStatusTable 1 }

AtmIfCACbrRowStatusEntry ::= SEQUENCE {
   atmIfCACbrRowStatus
      RowStatus,
   atmIfCACbrComponentName
      DisplayString,
   atmIfCACbrStorageType
      StorageType,
   atmIfCACbrIndex
      Integer32 }

atmIfCACbrRowStatus OBJECT-TYPE
   SYNTAX     RowStatus 
   ACCESS     read-write
   STATUS     mandatory
   DESCRIPTION
     "This variable is used as the basis for SNMP naming of
      atmIfCACbr components.
      These components can be added."
::= { atmIfCACbrRowStatusEntry 1 }

atmIfCACbrComponentName OBJECT-TYPE
   SYNTAX     DisplayString 
   ACCESS     read-only
   STATUS     mandatory
   DESCRIPTION
     "This variable provides the component's string name for
      use with the ASCII Console Interface"
::= { atmIfCACbrRowStatusEntry 2 }

atmIfCACbrStorageType OBJECT-TYPE
   SYNTAX     StorageType 
   ACCESS     read-only
   STATUS     mandatory
   DESCRIPTION
     "This variable represents the storage type value for the
      atmIfCACbr tables."
::= { atmIfCACbrRowStatusEntry 4 }

atmIfCACbrIndex OBJECT-TYPE
   SYNTAX     Integer32 (0)
   ACCESS     not-accessible
   STATUS     mandatory
   DESCRIPTION
     "This variable represents the index for the atmIfCACbr tables."
::= { atmIfCACbrRowStatusEntry 10 }

atmIfCACbrProvTable OBJECT-TYPE
   SYNTAX     SEQUENCE OF AtmIfCACbrProvEntry
   ACCESS     not-accessible
   STATUS     mandatory
   DESCRIPTION
     "This group contains provisioned attributes which control the CBR 
      service category for this interface."
::= { atmIfCACbr 100 }

atmIfCACbrProvEntry OBJECT-TYPE
   SYNTAX     AtmIfCACbrProvEntry
   ACCESS     not-accessible
   STATUS     mandatory
   DESCRIPTION
     "An entry in the atmIfCACbrProvTable."
   INDEX {
      atmIfIndex,
      atmIfCAIndex,
      atmIfCACbrIndex }
::= { atmIfCACbrProvTable 1 }

AtmIfCACbrProvEntry ::= SEQUENCE {
   atmIfCACbrProvPool
      INTEGER,
   atmIfCACbrProvCdvt
      Unsigned32,
   atmIfCACbrCdv
      Unsigned32,
   atmIfCACbrMaxCtd
      Unsigned32,
   atmIfCACbrProvClr
      Unsigned32,
   atmIfCACbrTxQueueLimit
      Unsigned32,
   atmIfCACbrHoldingPriority
      INTEGER,
   atmIfCACbrSvcHoldingPriority
      INTEGER,
   atmIfCACbrSvcMpHoldingPriority
      INTEGER,
   atmIfCACbrMinPerVcQueueLimit
      Unsigned32,
   atmIfCACbrPerVcQueueLimitReferenceRate
      Unsigned32,
   atmIfCACbrEmissionPriority
      Unsigned32,
   atmIfCACbrTrafficShaping
      INTEGER,
   atmIfCACbrShapeRecoupPolicy
      INTEGER,
   atmIfCACbrUnshapedTransmitQueueing
      INTEGER,
   atmIfCACbrWeightPolicy
      INTEGER,
   atmIfCACbrForceTagging
      INTEGER,
   atmIfCACbrUsageParameterControl
      INTEGER }

atmIfCACbrProvPool OBJECT-TYPE
   SYNTAX     INTEGER  {
                 pool1(1),
                 pool2(2),
                 pool3(3),
                 pool4(4),
                 pool5(5) }
   ACCESS     read-write
   STATUS     mandatory
   DESCRIPTION
     "This attribute specifies the bandwidth pool which is to be used to 
      support the constant bit rate (CBR) service category except for 
      connections managed by a Vpt CA. The percentage of link capacity 
      reserved for the given bandwidth pool is the maximum bandwidth 
      that can be allocated to CBR traffic. The percentage allocated to 
      each bandwidth pool can be provisioned through the bandwidthPool 
      attribute under the CA."
   DEFVAL     { pool1 }
::= { atmIfCACbrProvEntry 10 }

atmIfCACbrProvCdvt OBJECT-TYPE
   SYNTAX     Unsigned32 (1..10000)
   ACCESS     read-write
   STATUS     mandatory
   DESCRIPTION
     "This attribute specifies the default cell delay variation tolerance 
      (CDVT) for all connections of the CBR service category except 
      those managed by a Vpt CA. An override to this default may be 
      specified for a provisioned connection under the Vcd Tm or Vpd Tm 
      component.
      
      This attribute is used by the CAC function to compute the 
      equivalent cell rate (ECR) required by a given CBR connection. The 
      larger the value of CDVT, the larger is its ECR. 
      
      If Usage Parameter Control (UPC) is enabled for a connection, 
      CDVT is used by the UPC function to decide whether a cell is 
      conforming or non-conforming based on the connection's traffic 
      descriptor type. The larger the CDVT value, the more tolerant is the 
      UPC of bandwidth usage beyond the traffic contract."
   DEFVAL     { 250 }
::= { atmIfCACbrProvEntry 20 }

atmIfCACbrCdv OBJECT-TYPE
   SYNTAX     Unsigned32 (0..2147483647)
   ACCESS     read-write
   STATUS     mandatory
   DESCRIPTION
     "This attribute specifies the peak-to-peak cell delay variation (CDV) 
      which is contributed to the entire ATM Interface for CBR traffic. 
      
      The CDV is a measure of the delay jitter introduced mostly by 
      traffic buffering and cell scheduling. The worst case value of this 
      attribute can be computed as the txQueueLimit divided by the link 
      rate of this ATM Interface.
      
      The value of this attribute is used by PNNI in the Resource 
      Availability Information Group (RAIG) topology updates and route 
      selection. It is also used by CAC at connection set-up time to 
      determine whether this ATM Interface can meet the CDV 
      requirements of the connection. If so, the value of this attribute is 
      added to the cumulative CDV field of the extended QoS information 
      element."
   DEFVAL     { 250 }
::= { atmIfCACbrProvEntry 30 }

atmIfCACbrMaxCtd OBJECT-TYPE
   SYNTAX     Unsigned32 (0..2147483647)
   ACCESS     read-write
   STATUS     mandatory
   DESCRIPTION
     "This attribute specifies the maximum cell transfer delay (MaxCTD) 
      which is applied to the entire ATM Interface for CBR traffic.
      
      MaxCTD is the sum of the fixed delay and the CDV. The 
      components of the fixed delay include propagation delay through 
      the physical media, delays induced by the transmission system, and 
      fixed components of switch processing delay. 
      
      This attribute is used by PNNI in the Resource Availability 
      Information Group (RAIG) topology updates and route selection. It 
      is also used by CAC at connection set-up time to determine whether 
      this ATM Interface can meet the ATM connection's MaxCTD 
      requirement."
   DEFVAL     { 1000 }
::= { atmIfCACbrProvEntry 40 }

atmIfCACbrProvClr OBJECT-TYPE
   SYNTAX     Unsigned32 (0..15)
   ACCESS     read-write
   STATUS     mandatory
   DESCRIPTION
     "This attribute specifies the tolerable cell loss ratio (CLR) for CBR 
      traffic except for connections managed by a Vpt CA. The number is 
      the negative logarithm (base 10) of the CLR. For example, if the 
      target CLR = 1E-10 then Cbr cellLossRatio = 10. This number must 
      be the same as the RtVbr cellLossRatio since CBR and rt-VBR 
      traffic have the same discard priority. The Cbr cellLossRatio is used 
      by the Connection Admission Control (CAC) algorithm to compute 
      the required (equivalent) cell rate for CBR connections. 
      
      There is a trade-off between the service category CLR and the 
      achievable link utilization. To guarantee an excellent service 
      category, the CLR should be as small as possible (e.g., 1E-10). 
      However, a smaller CLR results in a larger equivalent cell rate for a 
      given connection and hence a lower link utilization.
      
      Setting this attribute to 0 means that a CLR of 1 can be tolerated. In 
      this case, no bandwidth is reserved for CBR connections, and CAC 
      is effectively turned off. All CBR connections are admitted."
   DEFVAL     { 10 }
::= { atmIfCACbrProvEntry 50 }

atmIfCACbrTxQueueLimit OBJECT-TYPE
   SYNTAX     Unsigned32 (0 | 5..63488)
   ACCESS     read-write
   STATUS     mandatory
   DESCRIPTION
     "This attribute specifies the default maximum queue length for the 
      emission queues used to buffer the traffic of the CBR service 
      category. It is used as the basis for setting the discard thresholds on 
      both common and per-VC queues. For the common queue, the 
      discard thresholds are set at approximately 35, 75, and 90 percent of 
      the value of this attribute for traffic at discard priority 3 (DP=3), 
      DP=2 and DP=1 respectively.
      
      For a per-VC queue, the actual limit may be reduced depending on 
      the shaping rate of the connection (for standard Vpt Vccs, this is the 
      shaping rate of the Vpt). The discard thresholds are set at 
      approximately 35, 75 and 90 percent of the scaled queue limit for 
      traffic at discard priority 3 (DP=3), DP=2 and DP=1 respectively. 
      However, a reduction will never result in a value that is less than the 
      value set for the minPerVcQueueLimit attribute. CQC-based ATM 
      cards do not support per-VC queues at the CBR service category.
      
      When this attribute is set to autoConfigure, an appropriate value is 
      selected based on the card type. It is set to 96 for all Passport ATM 
      cards (DS1, E1, IMA, JT2, DS3, E3, OC3, both CQC-based cards 
      and ATM IP cards). 
      
      For ATM IP FPs, the per-VC queue limit may be overridden for a 
      permanent connection by specifying a value in the Vcd Tm or Vpd 
      Tm txQueueLimit attribute.
      
      The operational value of the maximum length of a queue (common 
      or per-VC) is indicated by the Vcc Tm, Vpc Tm, or Vpt Tm 
      txQueueThresholds attribute.
      
      For standard Vpts, this attribute does not apply when using per-VC 
      queuing and only applies when using common queueing. When 
      using per-VC queueing, regardless of the Vpt's service category, 
      standard Vpts use the AtmIf Ca NrtVbr txQueueLimit value as their 
      default.
      
      This attribute does not apply to basic Vpts.

      VALUES (

      0 = autoConfigure

      )"
   DEFVAL     { 0 }
::= { atmIfCACbrProvEntry 60 }

atmIfCACbrHoldingPriority OBJECT-TYPE
   SYNTAX     INTEGER  {
                 n0(0),
                 n1(1),
                 n2(2),
                 n3(3),
                 n4(4) }
   ACCESS     read-write
   STATUS     mandatory
   DESCRIPTION
     "This attribute specifies the holding priority which applies to SVP 
      and SVC CBR connections. It takes a value from 0 (highest 
      priority) to 4 (lowest priority). In a situation where the link 
      bandwidth fluctuates, such as over an IMA link, holding priority is 
      used to determine which connections are held and which are 
      released. Holding priority 4 connections are the first to be released. 
      Holding priority 0 connections are the last to be released.
      
      This attribute does not apply to Vpt Vccs. When bandwidth 
      fluctuates, the entire Vpt, along with all Vpt Vccs is released as a 
      unit, according to the Vpt's holdingPriority."
   DEFVAL     { n3 }
::= { atmIfCACbrProvEntry 61 }

atmIfCACbrSvcHoldingPriority OBJECT-TYPE
   SYNTAX     INTEGER  {
                 n0(0),
                 n1(1),
                 n2(2),
                 n3(3),
                 n4(4) }
   ACCESS     read-write
   STATUS     obsolete
   DESCRIPTION
     "This attribute specifies the default holding priority which applies to 
      SVC CBR connections. It takes a value from 0 (highest priority) to 
      4 (lowest priority). In a situation where the link bandwidth 
      fluctuates, such as over an IMA link, holding priority is used to 
      determine which connections are held and which are released. 
      Holding priority 4 connections are the first to be released. Holding 
      priority 0 connections are the last to be released.
      This attribute has been obsoleted and its value migrated to 
      holdingPriority attribute."
   DEFVAL     { n3 }
::= { atmIfCACbrProvEntry 70 }

atmIfCACbrSvcMpHoldingPriority OBJECT-TYPE
   SYNTAX     INTEGER  {
                 n0(0),
                 n1(1),
                 n2(2),
                 n3(3),
                 n4(4) }
   ACCESS     read-write
   STATUS     mandatory
   DESCRIPTION
     "This attribute specifies the default holding priority which applies to 
      SVC CBR point-to-multipoint connections. It takes a value from 0 
      (highest priority) to 4 (lowest priority). In a situation where the link 
      bandwidth fluctuates, such as over an IMA link, holding priority is 
      used to determine which connections are held and which are 
      released. Holding priority 4 connections are the first to be released. 
      Holding priority 0 connections are the last to be released.
      
      This attribute does not apply to Vpt Vccs. When bandwidth 
      fluctuates, the entire Vpt, along with all Vpt Vccs is released as a 
      unit, according to the Vpt's holdingPriority."
   DEFVAL     { n3 }
::= { atmIfCACbrProvEntry 71 }

atmIfCACbrMinPerVcQueueLimit OBJECT-TYPE
   SYNTAX     Unsigned32 (5..12000)
   ACCESS     read-write
   STATUS     mandatory
   DESCRIPTION
     "This attribute specifies the minimum queue limit for the per-VC 
      queues of connections of the CBR service category. 
      
      This attribute is ignored on CQC-based ATM cards, because they do 
      not support per-VC queues at the CBR service category.
      
      The queue limit of a per-VC queue is obtained by scaling down the 
      txQueueLimit based on the shaping rate of that queue (shaping rate 
      for the connection, and for standard Vpt Vccs, the shaping rate of 
      the Vpt). This produces a constant delay for various queue lengths. 
      The txQueueLimit provides an upper bound while 
      minPerVcQueueLimit provides the lower bound. The value of this 
      attribute must not be greater than the value of the txQueueLimit 
      attribute. If this service category is used by Trunks the value of 
      minPerVcQueueLimit must be at least 88.
      
      For Vpts, this attribute does not apply. Regardless of Vpt service 
      category, standard Vpts always use the AtmIf Ca NrtVbr 
      minPerVcQueueLimit value as their default. To determine the queue 
      limit of a standard Vpt Vcc, the txQueueLimit is scaled down by the 
      Vpt shaping rate."
   DEFVAL     { 88 }
::= { atmIfCACbrProvEntry 80 }

atmIfCACbrPerVcQueueLimitReferenceRate OBJECT-TYPE
   SYNTAX     Unsigned32 (0 | 1..943396)
   ACCESS     read-write
   STATUS     mandatory
   DESCRIPTION
     "This attribute specifies the shaping rate to be used in computing the 
      tolerable delay for per-VC queues of connections of the CBR 
      service category. The delay is computed as the txQueueLimit 
      divided by the value of this attribute. 
      
      This attribute is ignored on CQC-based ATM cards, because they do 
      not support per-VC queues at the CBR service category.
      
      When the value of this attribute is autoConfigure, an appropriate 
      default is selected based on the card type. It is set to 80000 for all 
      cards which support per-VC queuing at the CBR service category 
      (3pDS3Atm2, 3pE3Atm2, 2pOC3SmAtm2, 2pOC3MmAtm2). 
      
      For Vpts, this attribute does not apply. Regardless of Vpt service 
      category, standard Vpts always use the AtmIf Ca NrtVbr 
      perVcQueueLimitReferenceRate value as their default.

      VALUES (

      0 = autoConfigure

      )"
   DEFVAL     { 0 }
::= { atmIfCACbrProvEntry 90 }

atmIfCACbrEmissionPriority OBJECT-TYPE
   SYNTAX     Unsigned32 (0..7)
   ACCESS     read-write
   STATUS     mandatory
   DESCRIPTION
     "This attribute is not applicable and is ignored for CQC-based ATM 
      cards.
      
      This attribute specifies the emission priority (EP) which is used to 
      transmit traffic of the CBR service category. A lower numerical 
      value for this attribute specifies a higher emission priority. 0 is the 
      highest EP and 7 is the lowest. Cells at a higher emission priority 
      receive higher preference for link bandwidth. EPs 0 and 1 are in the 
      absolute priority range, and are unaffected by any minimum 
      bandwidth guarantees. EPs 2 through 7 are in the guaranteed 
      bandwidth range. Minimum bandwidth guarantee is specified in the 
      AtmIf/n Ep/m component. 
      
      Emission priority setting must comply with all of the following 
      constraints: 
      1. The emission priority numbers must be in the following order: 
      CBR <= rt-VBR <= nrt-VBR <= ABR <= UBR 
      2. Two different ATM service categories may share the same EP 
      only if they are both shaped. 
      3. CBR and rt-VBR may be placed either in the absolute priority 
      range (EP 0 or 1) or in the guaranteed bandwidth range (EP 2 
      through 7). 
      4. If both CBR and rt-VBR are shaped, rt-VBR must share the 
      same EP with CBR or ABR. If either one of CBR or rt-VBR are 
      not shaped, then they cannot share the same EP. 
      5. ABR service category is always deemed to be shaped. If nrt-VBR 
      is shaped, it must share the same EP with ABR. If nrt-VBR is not 
      shaped it must have a higher EP than ABR.
      6. If UBR is shaped, it must share the same EP with ABR. If UBR 
      is not shaped, it must have a lower EP than ABR.
      
      This attribute does not apply to standard Vpt Vccs and basic Vpts."
   DEFVAL     { 0 }
::= { atmIfCACbrProvEntry 100 }

atmIfCACbrTrafficShaping OBJECT-TYPE
   SYNTAX     INTEGER  {
                 disabled(1),
                 enabled(5),
                 inverseUpc(6) }
   ACCESS     read-write
   STATUS     mandatory
   DESCRIPTION
     "This attribute specifies the default traffic shaping option for 
      connections of the CBR service category. An override to this default 
      may be specified for a provisioned connection under the Vcd Tm or 
      Vpd Tm component.
      
      When this attribute is set to disabled, traffic shaping cannot be 
      enabled for any CBR connections. 
      
      For CQC-based ATM FPs, this attribute must be set to disabled. 
      Traffic shaping is not supported for CBR connections on CQC-
      based ATM FPs. 
      
      If the Vcc Tm, Vpc Tm, or Vpt Tm txTrafficDescType indicates type 
      1 or 2, this attribute is ignored, and traffic shaping is not applicable 
      for that connection. 
      
      When this attribute is set to inverseUpc, traffic shaping for a 
      connection is enabled according to the value of the Vcc Tm, Vpc 
      Tm, or Vpt Tm txTrafficDescType. 
      
      If this attribute is set to inverseUpc, and the txTrafficDescType is 3, 
      4, or 5, linear traffic shaping is enabled. Linear traffic shaping uses 
      a single static traffic shaping rate. 
      
      If this attribute is set to inverseUpc, and the txTrafficDescType is 6, 
      7, or 8, inverse-UPC (also referred to as VBR or dual leaky bucket) 
      traffic shaping is enabled. Inverse-UPC traffic shaping can burst 
      above the sustained cell rate to the peak cell rate for the duration 
      defined by maximum burst size. Inverse-UPC traffic shaping exactly 
      conforms to the requirements of a dual leaky bucket UPC enforcer. 
      
      When this attribute is set to enabled and the txTrafficDescType is 3, 
      4, 5, 6, 7, or 8, traffic shaping for a connection is enabled using 
      linear shaping. 
      
      Enabling or disabling traffic shaping may require a matching 
      change to the emissionPriority attribute and 
      unshapedTransmitQueueing attribute for this service category. 
      Refer to those attributes for the complete description of the 
      interactions.
      
      This attribute does not apply to standard Vpt Vccs and basic Vpts."
   DEFVAL     { disabled }
::= { atmIfCACbrProvEntry 140 }

atmIfCACbrShapeRecoupPolicy OBJECT-TYPE
   SYNTAX     INTEGER  {
                 minimumCdv(0),
                 maximumEfficiency(1) }
   ACCESS     read-write
   STATUS     mandatory
   DESCRIPTION
     "This attribute specifies the shaping recoup policy for the CBR 
      service category. This is the policy which is used to recoup shaping 
      opportunities which are lost when more than one connection 
      schedules a cell for the same transmit opportunity. In this case, one 
      connection is scheduled, and the cell from the other connection is 
      delayed by one cell time. This attribute affects how the transmit 
      time is calculated for the next cell on the delayed connection. This 
      attribute is ignored if this service category is not shaped.
      
      When the connection which was delayed schedules the next cell to 
      transmit, it may calculate the time as a difference from either the 
      previous actual cell transmit time, or the time when the previous 
      cell should have been transmitted.
      
      Setting this attribute to maximumEfficiency results in each 
      connection trying to recoup or regain any delays in scheduling. The 
      transmit time from the next cell is calculated from the time when 
      the cell should originally have been sent. Cell delay variation 
      (CDV) occurs in this case since the cells are sent with less than the 
      shaping delay between them. However, in general the shaper 
      recovers (recoups) lost opportunities and improves efficiency.
      
      Setting this attribute to minimumCdv results in connections not 
      trying to recoup or regain any delays in scheduling. The transmit 
      time for the next cell is calculated from the time when the previous 
      cell was actually transmitted. This minimizes CDV, but results in 
      missed cell opportunities.
      
      This attribute does not apply to standard Vpt Vccs and basic Vpts."
   DEFVAL     { minimumCdv }
::= { atmIfCACbrProvEntry 150 }

atmIfCACbrUnshapedTransmitQueueing OBJECT-TYPE
   SYNTAX     INTEGER  {
                 perVc(0),
                 common(1) }
   ACCESS     read-write
   STATUS     mandatory
   DESCRIPTION
     "This attribute specifies the default queuing option for unshaped 
      connections of the CBR service category. On ATM IP cards, this 
      attribute controls whether common or per-VC queueing is used.
      
      Per-VC queueing means that each connection has its own buffering 
      and queue limits.
      
      Common queueing means that cells are queued in First In First Out 
      order on a common queue for this service category. The common 
      queue has one set of congestion control levels for all cells enqueued 
      on it. 
      
      For CQC-based ATM cards, this attribute must be set to common. 
      CQC-based ATM cards do not support per-VC queueing for the 
      CBR service category. 
      
      For ATM IP cards, if traffic shaping for this service category is not 
      disabled, this attribute must be set to perVc.
      
      This attribute does not apply to standard Vpt Vccs and basic Vpts."
   DEFVAL     { common }
::= { atmIfCACbrProvEntry 160 }

atmIfCACbrWeightPolicy OBJECT-TYPE
   SYNTAX     INTEGER  {
                 scr(1),
                 pcr(2),
                 ecr(3) }
   ACCESS     read-write
   STATUS     mandatory
   DESCRIPTION
     "This attribute specifies the default policy which is applied when 
      calculating the fairness weight for unshaped connections of the 
      CBR service category. The fairness weight for a connection 
      determines the relative amount of bandwidth which that connection 
      obtains, compared to other connections in the same service 
      category. Connections with equal weight get equal transmit 
      opportunities. Connections with higher weights get more transmit 
      opportunities compared with connections that have lower weights. 
      An override to this default may be specified for a provisioned 
      connection under the Vcd Tm or Vpd Tm component. 
      
      The fairness weight for a connection is directly proportional to the 
      value of one of the traffic descriptor parameters for that connection. 
      This attribute specifies which traffic descriptor parameter is used for 
      connections of the CBR service category. 
      
      This attribute is ignored on CQC-based ATM cards. This attribute is 
      also ignored on ATM IP cards if unshapedTransmitQueueing is set 
      for common queuing. 
      
      If this attribute is set to scr, the fairness weight is proportional to the 
      transmit sustained cell rate (SCR) of a connection. Connections 
      with a higher SCR have a higher fairness weight. For connections 
      with txTrafficDescType 3, which have no SCR, the sustained cell 
      rate is assumed to be equal to the peak cell rate. 
      
      If this attribute is set to pcr, the fairness weight is proportional to 
      the transmit peak cell rate (PCR) of a connection. Connections with 
      a higher PCR have a higher fairness weight. Connections with 
      txTrafficDescType 1 or 2 get a minimum weight, which is 1. 
      
      If this attribute is set to ecr, the fairness weight is proportional to 
      the equivalent cell rate (ECR) of a connection as calculated by 
      connection admission control (CAC). Connections with a higher 
      ECR have a higher fairness weight. Connections with an ECR of 0 
      get a minimum weight, which is 1. 
      
      The weight of a connection is visible in the Vcc Tm, Vpc Tm, or Vpt 
      Tm weight attribute. 
      
      This attribute does not apply to standard Vpt Vccs and basic Vpts."
   DEFVAL     { ecr }
::= { atmIfCACbrProvEntry 165 }

atmIfCACbrForceTagging OBJECT-TYPE
   SYNTAX     INTEGER  {
                 enabled(0),
                 disabled(1) }
   ACCESS     read-write
   STATUS     mandatory
   DESCRIPTION
     "This attribute specifies the default of whether to force tagging 
      (CLP=1) of all cells for all CBR connections. An override to this 
      default may be specified for a provisioned connection under the Vcd 
      Tm or Vpd Tm component. 
      
      When this attribute is set to enabled, CLP is set to 1 for all cells in 
      the transmit direction. Force tagging is only supported on ATM IP 
      FPs. 
      
      On CQC-based ATM FPs, this attribute must be set to disabled. 
      When this attribute is set to disabled, CLP is unchanged for all cells 
      in the transmit direction.
      
      This attribute never applies to any type of Vpt."
   DEFVAL     { disabled }
::= { atmIfCACbrProvEntry 169 }

atmIfCACbrUsageParameterControl OBJECT-TYPE
   SYNTAX     INTEGER  {
                 enforced(0),
                 disabled(1),
                 monitored(4) }
   ACCESS     read-write
   STATUS     mandatory
   DESCRIPTION
     "This attribute specifies the default usage parameter control (UPC) 
      option for connections of the CBR service category. This attribute is 
      ignored if the rxTrafficDescriptorType indicates 1 or 2. An override 
      to this default may be specified for a provisioned connection under 
      the Vcd Tm or Vpd Tm component. 
      
      When this attribute is set to enforced, UPC is enforced by default 
      for each connection. When UPC is enforced, non-conforming cells 
      are either tagged or discarded depending on the 
      rxTrafficDescriptorType. 
      
      On ATM IP FPs, when this attribute is set to monitored, UPC 
      conformance checking is performed, except, instead of the non-
      conforming cells being tagged or discarded, they are merely 
      counted in the UPC violations counts, and passed on unchanged. 
      
      On CQC-based ATM FPs, when this attribute is set to monitored, it 
      has the same effect as setting it to disabled. 
      
      When this attribute is set to disabled, UPC is disabled on the receive 
      path for all CBR connections.
      
      This attribute does not apply to standard Vpt Vccs and basic Vpts."
   DEFVAL     { disabled }
::= { atmIfCACbrProvEntry 170 }

atmIfCACbrOperTable OBJECT-TYPE
   SYNTAX     SEQUENCE OF AtmIfCACbrOperEntry
   ACCESS     not-accessible
   STATUS     mandatory
   DESCRIPTION
     "This group contains operational attributes for the CBR service 
      category."
::= { atmIfCACbr 110 }

atmIfCACbrOperEntry OBJECT-TYPE
   SYNTAX     AtmIfCACbrOperEntry
   ACCESS     not-accessible
   STATUS     mandatory
   DESCRIPTION
     "An entry in the atmIfCACbrOperTable."
   INDEX {
      atmIfIndex,
      atmIfCAIndex,
      atmIfCACbrIndex }
::= { atmIfCACbrOperTable 1 }

AtmIfCACbrOperEntry ::= SEQUENCE {
   atmIfCACbrEpdOffset
      Unsigned32 }

atmIfCACbrEpdOffset OBJECT-TYPE
   SYNTAX     Unsigned32 (0 | 5..1024)
   ACCESS     read-only
   STATUS     mandatory
   DESCRIPTION
     "This attribute indicates the Early Packet Discard (EPD) offset which 
      is currently in use for this service category. The EPD offset is used 
      to derive the EPD thresholds for each CC level.
      
      Any connection under this service category which requires the 
      txPacketWiseDiscard feature must specify a transmit queue limit 
      which is at least 5.71 times this offset. This ensures that the derived 
      Epd threshold will never be less than 17.5 % of the transmit queue 
      limit. If this is not done, txPacketWiseDiscard for the connection 
      will be automatically disabled.
      
      The value of this EPD offset is specified under the lp/x eng arc aqm 
      ov component."
::= { atmIfCACbrOperEntry 10 }


-- AtmIf/n CA RealTimeVariableBitRate/n 
-- This component manages the default characteristics of the real-time 
-- variable bit rate (rt-VBR) service category.

atmIfCARtVbr OBJECT IDENTIFIER ::= { atmIfCA 3 }



atmIfCARtVbrRowStatusTable OBJECT-TYPE
   SYNTAX     SEQUENCE OF AtmIfCARtVbrRowStatusEntry
   ACCESS     not-accessible
   STATUS     mandatory
   DESCRIPTION
     "This entry controls the addition and deletion of 
      atmIfCARtVbr components."
::= { atmIfCARtVbr 1 }

atmIfCARtVbrRowStatusEntry OBJECT-TYPE
   SYNTAX     AtmIfCARtVbrRowStatusEntry
   ACCESS     not-accessible
   STATUS     mandatory
   DESCRIPTION
     "A single entry in the table represents a single 
      atmIfCARtVbr component."
   INDEX {
      atmIfIndex,
      atmIfCAIndex,
      atmIfCARtVbrIndex }
::= { atmIfCARtVbrRowStatusTable 1 }

AtmIfCARtVbrRowStatusEntry ::= SEQUENCE {
   atmIfCARtVbrRowStatus
      RowStatus,
   atmIfCARtVbrComponentName
      DisplayString,
   atmIfCARtVbrStorageType
      StorageType,
   atmIfCARtVbrIndex
      Integer32 }

atmIfCARtVbrRowStatus OBJECT-TYPE
   SYNTAX     RowStatus 
   ACCESS     read-write
   STATUS     mandatory
   DESCRIPTION
     "This variable is used as the basis for SNMP naming of
      atmIfCARtVbr components.
      These components can be added."
::= { atmIfCARtVbrRowStatusEntry 1 }

atmIfCARtVbrComponentName OBJECT-TYPE
   SYNTAX     DisplayString 
   ACCESS     read-only
   STATUS     mandatory
   DESCRIPTION
     "This variable provides the component's string name for
      use with the ASCII Console Interface"
::= { atmIfCARtVbrRowStatusEntry 2 }

atmIfCARtVbrStorageType OBJECT-TYPE
   SYNTAX     StorageType 
   ACCESS     read-only
   STATUS     mandatory
   DESCRIPTION
     "This variable represents the storage type value for the
      atmIfCARtVbr tables."
::= { atmIfCARtVbrRowStatusEntry 4 }

atmIfCARtVbrIndex OBJECT-TYPE
   SYNTAX     Integer32 (0)
   ACCESS     not-accessible
   STATUS     mandatory
   DESCRIPTION
     "This variable represents the index for the atmIfCARtVbr tables."
::= { atmIfCARtVbrRowStatusEntry 10 }

atmIfCARtVbrProvTable OBJECT-TYPE
   SYNTAX     SEQUENCE OF AtmIfCARtVbrProvEntry
   ACCESS     not-accessible
   STATUS     mandatory
   DESCRIPTION
     "This group contains provisioned attributes which control the rt-VBR 
      service category for this interface."
::= { atmIfCARtVbr 100 }

atmIfCARtVbrProvEntry OBJECT-TYPE
   SYNTAX     AtmIfCARtVbrProvEntry
   ACCESS     not-accessible
   STATUS     mandatory
   DESCRIPTION
     "An entry in the atmIfCARtVbrProvTable."
   INDEX {
      atmIfIndex,
      atmIfCAIndex,
      atmIfCARtVbrIndex }
::= { atmIfCARtVbrProvTable 1 }

AtmIfCARtVbrProvEntry ::= SEQUENCE {
   atmIfCARtVbrPool
      INTEGER,
   atmIfCARtVbrCdvt
      Unsigned32,
   atmIfCARtVbrCdv
      Unsigned32,
   atmIfCARtVbrMaxCtd
      Unsigned32,
   atmIfCARtVbrCellLossRatio
      Unsigned32,
   atmIfCARtVbrTxQueueLimit
      Unsigned32,
   atmIfCARtVbrMinPerVcQueueLimit
      Unsigned32,
   atmIfCARtVbrPerVcQueueLimitReferenceRate
      Unsigned32,
   atmIfCARtVbrHoldingPriority
      INTEGER,
   atmIfCARtVbrSvcHoldingPriority
      INTEGER,
   atmIfCARtVbrSvcMpHoldingPriority
      INTEGER,
   atmIfCARtVbrEmissionPriority
      Unsigned32,
   atmIfCARtVbrTrafficShaping
      INTEGER,
   atmIfCARtVbrShapeRecoupPolicy
      INTEGER,
   atmIfCARtVbrUnshapedTransmitQueueing
      INTEGER,
   atmIfCARtVbrUsageParameterControl
      INTEGER,
   atmIfCARtVbrWeightPolicy
      INTEGER,
   atmIfCARtVbrForceTagging
      INTEGER }

atmIfCARtVbrPool OBJECT-TYPE
   SYNTAX     INTEGER  {
                 pool1(1),
                 pool2(2),
                 pool3(3),
                 pool4(4),
                 pool5(5) }
   ACCESS     read-write
   STATUS     mandatory
   DESCRIPTION
     "This attribute specifies the bandwidth pool which is to be used to 
      support the real-time variable bit rate (rt-VBR) service category 
      except for connections managed by a Vpt CA. The percentage of 
      link capacity reserved for the given bandwidth pool is the maximum 
      bandwidth that can be allocated to rt-VBR traffic. The percentage 
      allocated to each bandwidth pool can be provisioned through the 
      bandwidthPool attribute under the CA."
   DEFVAL     { pool1 }
::= { atmIfCARtVbrProvEntry 10 }

atmIfCARtVbrCdvt OBJECT-TYPE
   SYNTAX     Unsigned32 (1..1200000)
   ACCESS     read-write
   STATUS     mandatory
   DESCRIPTION
     "This attribute specifies the default cell delay variation tolerance 
      (CDVT) for all connections of the rt-VBR service category. An 
      override to this default may be specified for a provisioned 
      connection under the Vcd Tm or Vpd Tm component.
      
      If Usage Parameter Control (UPC) is enabled for a connection, 
      CDVT is used by the UPC function to decide whether a cell is 
      conforming or non-conforming based on the connection's traffic 
      descriptor type. The larger the CDVT value, the more tolerant is the 
      UPC to bandwidth usage beyond the traffic contract."
   DEFVAL     { 250 }
::= { atmIfCARtVbrProvEntry 20 }

atmIfCARtVbrCdv OBJECT-TYPE
   SYNTAX     Unsigned32 (0..2147483647)
   ACCESS     read-write
   STATUS     mandatory
   DESCRIPTION
     "This attribute specifies the peak-to-peak cell delay variation (CDV) 
      which is contributed to the entire ATM Interface for rt-VBR traffic. 
      
      The CDV is a measure of the delay jitter introduced mostly by 
      traffic buffering and cell scheduling. The worst case value of this 
      attribute can be computed as the txQueueLimit divided by the link 
      rate of this ATM Interface.
      
      The value of this attribute is used by PNNI in the Resource 
      Availability Information Group (RAIG) topology updates and route 
      selection. It is also used by CAC at connection set-up time to 
      determine whether this ATM Interface can meet the CDV 
      requirement for that connection. If so, the value of this attribute is 
      added to the cumulative CDV field of the extended QoS information 
      element."
   DEFVAL     { 1268 }
::= { atmIfCARtVbrProvEntry 30 }

atmIfCARtVbrMaxCtd OBJECT-TYPE
   SYNTAX     Unsigned32 (0..2147483647)
   ACCESS     read-write
   STATUS     mandatory
   DESCRIPTION
     "This attribute specifies the maximum cell transfer delay (MaxCTD) 
      which is applied to the entire ATM Interface for rt-VBR traffic.
      
      MaxCTD is the sum of the fixed delay and the CDV. The 
      components of the fixed delay include propagation delay through 
      the physical media, delays induced by the transmission system, and 
      fixed components of switch processing delay.
      
      This attribute is used by PNNI in the Resource Availability 
      Information Group (RAIG) topology updates and route selection. It 
      is also used by CAC at connection set-up time to determine whether 
      this ATM Interface can meet the ATM connection's MaxCTD 
      requirement."
   DEFVAL     { 2000 }
::= { atmIfCARtVbrProvEntry 40 }

atmIfCARtVbrCellLossRatio OBJECT-TYPE
   SYNTAX     Unsigned32 (0..15)
   ACCESS     read-write
   STATUS     mandatory
   DESCRIPTION
     "This attribute specifies the tolerable cell loss ratio (CLR) for rt-
      VBR traffic except for connections managed by a Vpt CA. The 
      number is the negative logarithm (base 10) of the CLR. For 
      example, if the target CLR = 1E-10 then RtVbr cellLossRatio = 10. 
      This number must be the same as the Cbr cellLossRatio since CBR 
      and rt-VBR traffic have the same discard priority. The RtVbr 
      cellLossRatio is used by the Connection Admission Control (CAC) 
      algorithm to compute the required (equivalent) cell rate for rt-VBR 
      connections. This number must be less than or equal to the NrtVbr 
      cellLossRatio, since rt-VBR traffic has a higher discard priority.
      
      There is a trade-off between the service category CLR and the 
      achievable link utilization. To guarantee an excellent service 
      category, the CLR should be as small as possible (e.g., 1E-10). 
      However, a smaller CLR results in a larger equivalent cell rate for a 
      given connection and hence a lower link utilization. 
      
      Setting this attribute to 0 means that a CLR of 1 can be tolerated. In 
      this case, no bandwidth is reserved for rt-VBR connections, and 
      CAC is effectively turned off. All rt-VBR are admitted."
   DEFVAL     { 10 }
::= { atmIfCARtVbrProvEntry 50 }

atmIfCARtVbrTxQueueLimit OBJECT-TYPE
   SYNTAX     Unsigned32 (0 | 5..63488)
   ACCESS     read-write
   STATUS     mandatory
   DESCRIPTION
     "This attribute specifies the default maximum queue length for the 
      emission queues used to buffer the traffic of the rt-VBR service 
      category. It is used as the basis for setting the discard thresholds on 
      both common and per-VC queues. For the common queue, the 
      discard thresholds are set at approximately 35, 75, and 90 percent of 
      the value of this attribute for traffic at discard priority 3 (DP=3), 
      DP=2, and DP=1 respectively. 
      
      For a per-VC queue, the actual limit may be reduced depending on 
      the shaping rate of the connection (for standard Vpt Vccs, this is the 
      shaping rate of the Vpt). The discard thresholds are set at 
      approximately 35, 75, and 90 percent of the scaled queue limit for 
      traffic at discard priority 3 (DP=3), DP=2, and DP=1, respectively. 
      However, a reduction will never result in a value that is less than the 
      value set for the minPerVcQueueLimit attribute.
      
      When the value of this attribute is autoConfigure, an appropriate 
      value is selected based on the card type. It is set to 288 for low 
      speed cards such as DS1, E1 and IMA, and set to 480 for high 
      speed cards such as JT2, DS3, E3 and OC3 (including ATM IP 
      FPs). 
      
      For ATM IP FPs, the per-VC queue limit may be overridden for a 
      permanent connection by specifying a value in the Vcd Tm or Vpd 
      Tm txQueueLimit attribute. 
      
      The operational value of the maximum length of a queue (common 
      or per-VC) is indicated by the Vcc Tm, Vpc Tm, or Vpt Tm 
      txQueueThresholds attribute.
      
      For standard Vpts, this attribute does not apply when using per-VC 
      queuing and only applies when using common queueing. When 
      using per-VC queueing, regardless of the Vpt's service category, 
      standard Vpts use the AtmIf Ca NrtVbr txQueueLimit value as their 
      default.
      
      This attribute does not apply to basic Vpts.

      VALUES (

      0 = autoConfigure

      )"
   DEFVAL     { 0 }
::= { atmIfCARtVbrProvEntry 60 }

atmIfCARtVbrMinPerVcQueueLimit OBJECT-TYPE
   SYNTAX     Unsigned32 (5..12000)
   ACCESS     read-write
   STATUS     mandatory
   DESCRIPTION
     "This attribute specifies the minimum queue limit for the per-VC 
      queues of connections of the rt-VBR service category.
      
      The queue limit of a per-VC queue is obtained by scaling down the 
      txQueueLimit based on the shaping rate of that queue (shaping rate 
      for the connection, and for standard Vpt Vccs, the shaping rate of 
      the Vpt). This produces a constant delay for various queue lengths. 
      The txQueueLimit provides an upper bound while 
      minPerVcQueueLimit provides the lower bound. The value of this 
      attribute must not be greater than the value of the txQueueLimit 
      attribute. If this service category is used by Trunks the value of 
      minPerVcQueueLimit must be at least 88.
      
      For Vpts, this attribute does not apply. Regardless of Vpt service 
      category, standard Vpts always use the AtmIf Ca NrtVbr 
      minPerVcQueueLimit value as their default. To determine the queue 
      limit of a standard Vpt Vcc, the txQueueLimit is scaled down by the 
      Vpt shaping rate."
   DEFVAL     { 88 }
::= { atmIfCARtVbrProvEntry 70 }

atmIfCARtVbrPerVcQueueLimitReferenceRate OBJECT-TYPE
   SYNTAX     Unsigned32 (0 | 1..943396)
   ACCESS     read-write
   STATUS     mandatory
   DESCRIPTION
     "This attribute specifies the shaping rate to be used in computing the 
      tolerable delay for per-VC queues of connections of the rt-VBR 
      service category. The delay is computed as the txQueueLimit 
      divided by the value of this attribute. 
      
      When the value of this attribute is autoConfigure, an appropriate 
      default is selected based on the card type. It is set to 3685 for low 
      speed cards such as DS1, E1, and IMA, and set to 14740 for high 
      speed cards such as JT2, DS3, E3 and OC3.
      
      For Vpts, this attribute does not apply. Regardless of Vpt service 
      category, standard Vpts always use the AtmIf Ca NrtVbr 
      perVcQueueLimitReferenceRate value as their default.

      VALUES (

      0 = autoConfigure

      )"
   DEFVAL     { 0 }
::= { atmIfCARtVbrProvEntry 75 }

atmIfCARtVbrHoldingPriority OBJECT-TYPE
   SYNTAX     INTEGER  {
                 n0(0),
                 n1(1),
                 n2(2),
                 n3(3),
                 n4(4) }
   ACCESS     read-write
   STATUS     mandatory
   DESCRIPTION
     "This attribute specifies the default holding priority which applies to 
      SVP and SVC rt-VBR connections. It takes a value from 0 (highest 
      priority) to 4 (lowest priority). In a situation where the link 
      bandwidth fluctuates, such as over an IMA link, holding priority is 
      used to determine which connections are held and which are 
      released. Holding priority 4 connections are the first to be released. 
      Holding priority 0 connections are the last to be released.
      
      This attribute does not apply to Vpt Vccs. When bandwidth 
      fluctuates, the entire Vpt, along with all Vpt Vccs are released as a 
      unit, according to the Vpt's holdingPriority."
   DEFVAL     { n3 }
::= { atmIfCARtVbrProvEntry 76 }

atmIfCARtVbrSvcHoldingPriority OBJECT-TYPE
   SYNTAX     INTEGER  {
                 n0(0),
                 n1(1),
                 n2(2),
                 n3(3),
                 n4(4) }
   ACCESS     read-write
   STATUS     obsolete
   DESCRIPTION
     "This attribute specifies the default holding priority which applies to 
      SVC rt-VBR connections. It takes a value from 0 (highest priority) 
      to 4 (lowest priority). In a situation where the link bandwidth 
      fluctuates, such as over an IMA link, holding priority is used to 
      determine which connections are held and which are released. 
      Holding priority 4 connections are the first to be released. Holding 
      priority 0 connections are the last to be released.
      This attribute has been obsoleted and its value migrated to 
      holdingPriority attribute."
   DEFVAL     { n3 }
::= { atmIfCARtVbrProvEntry 80 }

atmIfCARtVbrSvcMpHoldingPriority OBJECT-TYPE
   SYNTAX     INTEGER  {
                 n0(0),
                 n1(1),
                 n2(2),
                 n3(3),
                 n4(4) }
   ACCESS     read-write
   STATUS     mandatory
   DESCRIPTION
     "This attribute specifies the default holding priority which applies to 
      SVC rt-VBR point-to-multipoint connections. It takes a value from 
      0 (highest priority) to 4 (lowest priority). In a situation where the 
      link bandwidth fluctuates, such as over an IMA link, holding 
      priority is used to determine which connections are held and which 
      are released. Holding priority 4 connections are the first to be 
      released. Holding priority 0 connections are the last to be released.
      
      This attribute does not apply to Vpt Vccs. When bandwidth 
      fluctuates, the entire Vpt, along with all Vpt Vccs is released as a 
      unit, according to the Vpt's holdingPriority."
   DEFVAL     { n3 }
::= { atmIfCARtVbrProvEntry 81 }

atmIfCARtVbrEmissionPriority OBJECT-TYPE
   SYNTAX     Unsigned32 (0..7)
   ACCESS     read-write
   STATUS     mandatory
   DESCRIPTION
     "This attribute is not applicable and is ignored for CQC-based ATM 
      cards.
      
      This attribute specifies the emission priority (EP) which is used to 
      transmit traffic of the rt-VBR service category. A lower numerical 
      value for this attribute specifies a higher emission priority. 0 is the 
      highest EP and 7 is the lowest. Cells at a higher emission priority 
      receive higher preference for link bandwidth. EPs 0 and 1 are in the 
      absolute priority range, and are unaffected by any minimum 
      bandwidth guarantees. EPs 2 through 7 are in the guaranteed 
      bandwidth range. Minimum bandwidth guarantee is specified in the 
      AtmIf/n Ep/m component. 
      
      Emission priority setting must comply with all of the following 
      constraints: 
      1. The emission priority numbers must be in the following order: 
      CBR <= rt-VBR <= nrt-VBR <= ABR <= UBR 
      2. Two different ATM service categories may share the same EP 
      only if they are both shaped. 
      3. CBR and rt-VBR may be placed either in the absolute priority 
      range (EP 0 or 1) or in the guaranteed bandwidth range (EP 2 
      through 7). 
      4. If both CBR and rt-VBR are shaped, rt-VBR must share the 
      same EP with CBR or ABR. If either one of CBR or rt-VBR are 
      not shaped, then they cannot share the same EP. 
      5. ABR service category is always deemed to be shaped. If nrt-VBR 
      is shaped, it must share the same EP with ABR. If nrt-VBR is not 
      shaped it must have a higher EP than ABR.
      6. If UBR is shaped, it must share the same EP with ABR. If UBR 
      is not shaped, it must have a lower EP than ABR.
      
      This attribute does not apply to standard Vpt Vccs and basic Vpts."
   DEFVAL     { 1 }
::= { atmIfCARtVbrProvEntry 82 }

atmIfCARtVbrTrafficShaping OBJECT-TYPE
   SYNTAX     INTEGER  {
                 disabled(1),
                 enabled(5),
                 inverseUpc(6) }
   ACCESS     read-write
   STATUS     mandatory
   DESCRIPTION
     "This attribute specifies the default traffic shaping option for 
      connections of the rt-VBR service category. An override to this 
      default may be specified for a provisioned connection under the Vcd 
      Tm or Vpd Tm component.
      
      When this attribute is set to disabled, traffic shaping cannot be 
      enabled for any rt-VBR connections. 
      
      For CQC-based ATM cards, this attribute may be set to enabled 
      only if the interface supports shaping, as defined by the 
      perVcQueueInterfaces attribute in the AtmResourceControl Cqc 
      Override component. If that component does not exist, this attribute 
      must be set to disabled.
      
      If the Vcc Tm, Vpc Tm, or Vpt Tm txTrafficDescType indicates type 
      1 or 2, this attribute is ignored, and traffic shaping is not applicable 
      for that connection. 
      
      When this attribute is set to inverseUpc, traffic shaping for a 
      connection is enabled according to card type and the value of the 
      Vcc Tm, Vpc Tm, or Vpt Tm txTrafficDescType. 
      
      If this attribute is set to inverseUpc, and the txTrafficDescType is 3, 
      4, or 5, linear traffic shaping is enabled. Linear traffic shaping uses 
      a single static traffic shaping rate. 
      
      On CQC-based ATM FPs, if this attribute is set to inverseUpc, and 
      the txTrafficDescType is 6, 7, or 8, linear traffic shaping is enabled.
      
      On ATM IP FPs, if this attribute is set to inverseUpc, and the 
      txTrafficDescType is 6, 7, or 8, inverse-UPC (also referred to as 
      VBR or dual leaky bucket) traffic shaping is enabled. Inverse-UPC 
      traffic shaping can burst above the sustained cell rate to the peak 
      cell rate for the duration defined by maximum burst size. Inverse-
      UPC traffic shaping exactly conforms to the requirements of a dual 
      leaky bucket UPC enforcer. 
      
      When this attribute is set to enabled and the txTrafficDescType is 3, 
      4, 5, 6, 7, or 8, traffic shaping for a connection is enabled using 
      linear shaping. 
      
      Enabling or disabling traffic shaping may require a matching 
      change to the emissionPriority attribute and 
      unshapedTransmitQueueing attribute for this service category. 
      Refer to those attributes for the complete description of the 
      interactions.
      
      This attribute does not apply to standard Vpt Vccs and basic Vpts."
   DEFVAL     { disabled }
::= { atmIfCARtVbrProvEntry 86 }

atmIfCARtVbrShapeRecoupPolicy OBJECT-TYPE
   SYNTAX     INTEGER  {
                 minimumCdv(0),
                 maximumEfficiency(1) }
   ACCESS     read-write
   STATUS     mandatory
   DESCRIPTION
     "This attribute specifies the shaping recoup policy for the rt-VBR 
      service category. This is the policy which is used to recoup shaping 
      opportunities which are lost when more than one connection 
      schedules a cell for the same transmit opportunity. In this case, one 
      connection is scheduled, and the cell from another connection is 
      delayed by one cell time. This attribute affects how the transmit 
      time is calculated for the next cell on the delayed connection. This 
      attribute is ignored if this service category is not shaped.
      
      When the connection which was delayed schedules the next cell to 
      transmit, it may calculate the time as a difference from either the 
      previous actual cell transmit time, or the time when the previous 
      cell should have been transmitted.
      
      Setting this attribute to maximumEfficiency results in each 
      connection trying to recoup or regain delays in scheduling. The 
      transmit time from the next cell is calculated from the time when 
      the cell should originally have been sent. Cell delay variation 
      (CDV) occurs in this case since the cells are sent with less than the 
      shaping delay between them. However, in general the shaper 
      recovers (recoups) lost opportunities and improves efficiency.
      
      Setting this attribute to minimumCdv results in connections not 
      trying to recoup or regain any delays in scheduling. The transmit 
      time for the next cell is calculated from the time when the previous 
      cell was actually transmitted. This minimizes CDV, but results in 
      missed cell opportunities."
   DEFVAL     { minimumCdv }
::= { atmIfCARtVbrProvEntry 87 }

atmIfCARtVbrUnshapedTransmitQueueing OBJECT-TYPE
   SYNTAX     INTEGER  {
                 perVc(0),
                 common(1),
                 autoConfigure(2) }
   ACCESS     read-write
   STATUS     mandatory
   DESCRIPTION
     "This attribute specifies the default queuing option for unshaped 
      connections of the rt-VBR service category. This attribute controls 
      whether common or per-VC queueing is used. 
      
      Per-VC queueing means that each connection has its own buffering 
      and queue limits.
      
      Common queueing means that cells are queued in First In First Out 
      order on a common queue for this service category. The common 
      queue has one set of congestion control levels for all cells enqueued 
      on it.
      
      For ATM IP cards, if traffic shaping for this service category is 
      disabled, this attribute may take any of the three values. In this case, 
      the value autoConfigure is interpreted to mean per-VC queueing.
      
      For ATM IP cards, if traffic shaping for this service category is not 
      disabled, the only permitted values are perVc and autoConfigure. 
      In this case, the result is that all connections use per-VC queueing.
      
      For CQC-based ATM cards, if the perVcQueueInterfaces attribute 
      of the Lp Eng Arc Cqc component permits shaping for this 
      interface, then this attribute may take any of the three values. In this 
      case, the value autoConfigure is interpreted to mean per-VC 
      queueing. 
      
      For CQC-based ATM cards, if the perVcQueueInterfaces attribute 
      of the Lp Eng Arc Cqc component does not permit shaping for this 
      interface, then this attribute may take values common or 
      autoConfigure. In this case, the value autoConfigure is interpreted 
      to mean common queueing. 
      
      If this attribute is set to autoConfigure, an override to this default 
      may be specified for a provisioned connection under the Vcd Tm or 
      Vpd Tm component. 
      
      The opUnshapedTransmitQueueing attribute of this component 
      indicates whether the transmit queueing is perVc or common.
      
      This attribute does not apply to standard Vpt Vccs and basic Vpts."
   DEFVAL     { autoConfigure }
::= { atmIfCARtVbrProvEntry 88 }

atmIfCARtVbrUsageParameterControl OBJECT-TYPE
   SYNTAX     INTEGER  {
                 enforced(0),
                 disabled(1),
                 monitored(4) }
   ACCESS     read-write
   STATUS     mandatory
   DESCRIPTION
     "This attribute specifies the default usage parameter control (UPC) 
      option for connections of the rt-VBR service category. This attribute 
      is ignored if the rxTrafficDescriptorType indicates 1 or 2. An 
      override to this default may be specified for a provisioned 
      connection under the Vcd Tm or Vpd Tm component.
      
      When this attribute is set to enforced, UPC is enforced for each 
      connection. When UPC is enforced, non-conforming cells are either 
      tagged or discarded depending on the rxTrafficDescriptorType. 
      
      On ATM IP FPs, when this attribute is set to monitored, UPC 
      conformance checking is performed, except, instead of the non-
      conforming cells being tagged or discarded, they are merely 
      counted in the UPC violations counts, and passed on unchanged. 
      
      On CQC-based ATM FPs, when this attribute is set to monitored, it 
      has the same effect as setting it to disabled. 
      
      When this attribute is set to disabled, UPC is disabled on the receive 
      path for all rt-VBR connections.
      
      This attribute does not apply to standard Vpt Vccs and basic Vpts."
   DEFVAL     { disabled }
::= { atmIfCARtVbrProvEntry 89 }

atmIfCARtVbrWeightPolicy OBJECT-TYPE
   SYNTAX     INTEGER  {
                 scr(1),
                 pcr(2),
                 ecr(3) }
   ACCESS     read-write
   STATUS     mandatory
   DESCRIPTION
     "This attribute specifies the policy which is applied when calculating 
      the fairness weight for unshaped connections of the rt-VBR service 
      category. The fairness weight for a connection determines the 
      relative amount of bandwidth which that connection obtains, 
      compared to other connections in the same service category. 
      Connections with equal weight get equal transmit opportunities. 
      Connections with higher weights get more transmit opportunities 
      compared with connections that have lower weights. An override to 
      this default may be specified for a provisioned connection under the 
      Vcd Tm or Vpd Tm component. 
      
      The fairness weight for a connection is directly proportional to the 
      value of one of the traffic descriptor parameters for that connection. 
      This attribute specifies which traffic descriptor parameter is used for 
      connections of the rt-VBR service category. 
      
      This attribute is ignored on CQC-based ATM cards. This attribute is 
      also ignored on ATM IP cards if unshapedTransmitQueueing is set 
      for common queuing. 
      
      If this attribute is set to scr, the fairness weight is proportional to the 
      transmit sustained cell rate (SCR) of a connection. Connections 
      with a higher SCR have a higher fairness weight. For connections 
      with txTrafficDescType 3, which have no SCR, the sustained cell 
      rate is assumed to be equal to the peak cell rate. 
      
      If this attribute is set to pcr, the fairness weight is proportional to 
      the transmit peak cell rate (PCR) of a connection. Connections with 
      a higher PCR have a higher fairness weight. Connections with 
      txTrafficDescType 1 or 2 get a minimum weight, which is 1. 
      
      If this attribute is set to ecr, the fairness weight is proportional to 
      the equivalent cell rate (ECR) of a connection as calculated by 
      connection admission control (CAC). Connections with a higher 
      ECR have a higher fairness weight. Connections with an ECR of 0 
      get a minimum weight, which is 1. 
      
      The weight of a connection is visible in the Vcc Tm, Vpc Tm, or Vpt 
      Tm weight attribute.
      
      This attribute does not apply to standard Vpt Vccs and basic Vpts."
   DEFVAL     { ecr }
::= { atmIfCARtVbrProvEntry 90 }

atmIfCARtVbrForceTagging OBJECT-TYPE
   SYNTAX     INTEGER  {
                 enabled(0),
                 disabled(1) }
   ACCESS     read-write
   STATUS     mandatory
   DESCRIPTION
     "This attribute specifies the default of whether to force tagging 
      (CLP=1) of all cells for all rt-VBR connections. An override to this 
      default may be specified for a provisioned connection under the Vcd 
      Tm or Vpd Tm component. 
      
      When this attribute is set to enabled, CLP is set to 1 for all cells in 
      the transmit direction. Force tagging is only supported on ATM IP 
      FPs. 
      
      On CQC-based ATM FPs, this attribute must be set to disabled. 
      When this attribute is set to disabled, CLP is unchanged for all cells 
      in the transmit direction.
      
      This attribute never applies to any type of Vpt."
   DEFVAL     { disabled }
::= { atmIfCARtVbrProvEntry 91 }

atmIfCARtVbrOperTable OBJECT-TYPE
   SYNTAX     SEQUENCE OF AtmIfCARtVbrOperEntry
   ACCESS     not-accessible
   STATUS     mandatory
   DESCRIPTION
     "This group contains operational attributes for the rt-VBR service 
      category."
::= { atmIfCARtVbr 110 }

atmIfCARtVbrOperEntry OBJECT-TYPE
   SYNTAX     AtmIfCARtVbrOperEntry
   ACCESS     not-accessible
   STATUS     mandatory
   DESCRIPTION
     "An entry in the atmIfCARtVbrOperTable."
   INDEX {
      atmIfIndex,
      atmIfCAIndex,
      atmIfCARtVbrIndex }
::= { atmIfCARtVbrOperTable 1 }

AtmIfCARtVbrOperEntry ::= SEQUENCE {
   atmIfCARtVbrOpUnshapedTransmitQueueing
      INTEGER,
   atmIfCARtVbrEpdOffset
      Unsigned32 }

atmIfCARtVbrOpUnshapedTransmitQueueing OBJECT-TYPE
   SYNTAX     INTEGER  {
                 perVc(0),
                 common(1) }
   ACCESS     read-only
   STATUS     mandatory
   DESCRIPTION
     "This attribute indicates the state of transmit queueing for unshaped 
      rt-VBR connections.
      
      A value of perVc indicates that any unshaped connections use per-
      VC queueing. A value of common indicates that traffic for 
      unshaped connections uses the common queue which corresponds 
      to the EP for this service category."
::= { atmIfCARtVbrOperEntry 10 }

atmIfCARtVbrEpdOffset OBJECT-TYPE
   SYNTAX     Unsigned32 (0 | 5..1024)
   ACCESS     read-only
   STATUS     mandatory
   DESCRIPTION
     "This attribute indicates the Early Packet Discard (EPD) offset which 
      is currently in use for this service category. The EPD offset is used 
      to derive the EPD thresholds for each CC level.
      
      Any connection under this service category which requires the 
      txPacketWiseDiscard feature must specify a transmit queue limit 
      which is at least 5.71 times this offset. This ensures that the derived 
      Epd threshold will never be less than 17.5 % of the transmit queue 
      limit. If this is not done, txPacketWiseDiscard for the connection 
      will be automatically disabled.
      
      The value of this EPD offset is specified under the lp/x eng arc aqm 
      ov component."
::= { atmIfCARtVbrOperEntry 11 }


-- AtmIf/n CA NonRealTimeVariableBitRate/n 
-- This component manages the default characteristics of the non-real-
-- time variable bit rate (nrt-VBR) service category.

atmIfCANrtVbr OBJECT IDENTIFIER ::= { atmIfCA 4 }



atmIfCANrtVbrRowStatusTable OBJECT-TYPE
   SYNTAX     SEQUENCE OF AtmIfCANrtVbrRowStatusEntry
   ACCESS     not-accessible
   STATUS     mandatory
   DESCRIPTION
     "This entry controls the addition and deletion of 
      atmIfCANrtVbr components."
::= { atmIfCANrtVbr 1 }

atmIfCANrtVbrRowStatusEntry OBJECT-TYPE
   SYNTAX     AtmIfCANrtVbrRowStatusEntry
   ACCESS     not-accessible
   STATUS     mandatory
   DESCRIPTION
     "A single entry in the table represents a single 
      atmIfCANrtVbr component."
   INDEX {
      atmIfIndex,
      atmIfCAIndex,
      atmIfCANrtVbrIndex }
::= { atmIfCANrtVbrRowStatusTable 1 }

AtmIfCANrtVbrRowStatusEntry ::= SEQUENCE {
   atmIfCANrtVbrRowStatus
      RowStatus,
   atmIfCANrtVbrComponentName
      DisplayString,
   atmIfCANrtVbrStorageType
      StorageType,
   atmIfCANrtVbrIndex
      Integer32 }

atmIfCANrtVbrRowStatus OBJECT-TYPE
   SYNTAX     RowStatus 
   ACCESS     read-write
   STATUS     mandatory
   DESCRIPTION
     "This variable is used as the basis for SNMP naming of
      atmIfCANrtVbr components.
      These components can be added."
::= { atmIfCANrtVbrRowStatusEntry 1 }

atmIfCANrtVbrComponentName OBJECT-TYPE
   SYNTAX     DisplayString 
   ACCESS     read-only
   STATUS     mandatory
   DESCRIPTION
     "This variable provides the component's string name for
      use with the ASCII Console Interface"
::= { atmIfCANrtVbrRowStatusEntry 2 }

atmIfCANrtVbrStorageType OBJECT-TYPE
   SYNTAX     StorageType 
   ACCESS     read-only
   STATUS     mandatory
   DESCRIPTION
     "This variable represents the storage type value for the
      atmIfCANrtVbr tables."
::= { atmIfCANrtVbrRowStatusEntry 4 }

atmIfCANrtVbrIndex OBJECT-TYPE
   SYNTAX     Integer32 (0)
   ACCESS     not-accessible
   STATUS     mandatory
   DESCRIPTION
     "This variable represents the index for the atmIfCANrtVbr tables."
::= { atmIfCANrtVbrRowStatusEntry 10 }

atmIfCANrtVbrProvTable OBJECT-TYPE
   SYNTAX     SEQUENCE OF AtmIfCANrtVbrProvEntry
   ACCESS     not-accessible
   STATUS     mandatory
   DESCRIPTION
     "This group contains provisioned attributes which control the nrt-
      VBR service category for this interface."
::= { atmIfCANrtVbr 100 }

atmIfCANrtVbrProvEntry OBJECT-TYPE
   SYNTAX     AtmIfCANrtVbrProvEntry
   ACCESS     not-accessible
   STATUS     mandatory
   DESCRIPTION
     "An entry in the atmIfCANrtVbrProvTable."
   INDEX {
      atmIfIndex,
      atmIfCAIndex,
      atmIfCANrtVbrIndex }
::= { atmIfCANrtVbrProvTable 1 }

AtmIfCANrtVbrProvEntry ::= SEQUENCE {
   atmIfCANrtVbrPool
      INTEGER,
   atmIfCANrtVbrCdvt
      Unsigned32,
   atmIfCANrtVbrCellLossRatio
      Unsigned32,
   atmIfCANrtVbrTxQueueLimit
      Unsigned32,
   atmIfCANrtVbrSvcHoldingPriority
      INTEGER,
   atmIfCANrtVbrMinPerVcQueueLimit
      Unsigned32,
   atmIfCANrtVbrPerVcQueueLimitReferenceRate
      Unsigned32,
   atmIfCANrtVbrSvcMpHoldingPriority
      INTEGER,
   atmIfCANrtVbrHoldingPriority
      INTEGER,
   atmIfCANrtVbrEmissionPriority
      Unsigned32,
   atmIfCANrtVbrTrafficShaping
      INTEGER,
   atmIfCANrtVbrShapeRecoupPolicy
      INTEGER,
   atmIfCANrtVbrUnshapedTransmitQueueing
      INTEGER,
   atmIfCANrtVbrUsageParameterControl
      INTEGER,
   atmIfCANrtVbrWeightPolicy
      INTEGER,
   atmIfCANrtVbrForceTagging
      INTEGER }

atmIfCANrtVbrPool OBJECT-TYPE
   SYNTAX     INTEGER  {
                 pool1(1),
                 pool2(2),
                 pool3(3),
                 pool4(4),
                 pool5(5) }
   ACCESS     read-write
   STATUS     mandatory
   DESCRIPTION
     "This attribute specifies the bandwidth pool which is to be used to 
      support the non-real-time variable bit rate (nrt-VBR) service 
      category except for connections managed by a Vpt CA. The 
      percentage of link capacity reserved for the given bandwidth pool is 
      the maximum bandwidth that can be allocated to nrt-VBR traffic. 
      The percentage allocated to each bandwidth pool can be 
      provisioned through the bandwidthPool attribute under the CA."
   DEFVAL     { pool1 }
::= { atmIfCANrtVbrProvEntry 1 }

atmIfCANrtVbrCdvt OBJECT-TYPE
   SYNTAX     Unsigned32 (1..1200000)
   ACCESS     read-write
   STATUS     mandatory
   DESCRIPTION
     "This attribute specifies the default cell delay variation tolerance 
      (CDVT) for all connections of the nrt-VBR service category. An 
      override to this default may be specified for a provisioned 
      connection under the Vcd Tm or Vpd Tm component.
      
      If Usage Parameter Control (UPC) is enabled for a connection, 
      CDVT is used by the UPC function to decide whether a cell is 
      conforming or non-conforming based on the connection's traffic 
      descriptor type. The larger the CDVT value, the more tolerant is the 
      UPC of bandwidth usage beyond the traffic contract."
   DEFVAL     { 250 }
::= { atmIfCANrtVbrProvEntry 2 }

atmIfCANrtVbrCellLossRatio OBJECT-TYPE
   SYNTAX     Unsigned32 (0..15)
   ACCESS     read-write
   STATUS     mandatory
   DESCRIPTION
     "This attribute specifies the tolerable cell loss ratio (CLR) for nrt-
      VBR traffic except for connections managed by a Vpt CA. The 
      number is the negative logarithm (base 10) of the CLR. In other 
      words if the target CLR = 1E-10 then NrtVbr cellLossRatio = 10. 
      This number must be greater than or equal to RtVbr cellLossRatio 
      since rt-VBR traffic has a higher discard priority. The NrtVbr 
      cellLossRatio is used by the Connection Admission Control (CAC) 
      algorithm to compute the required (equivalent) cell rate for nrt-VBR 
      connections. 
      
      There is a trade-off between the service category CLR and the 
      achievable link utilization. To guarantee an excellent service 
      category, the CLR should be as small as possible (e.g., 1E-10). 
      However, a smaller CLR results in a larger equivalent cell rate for a 
      given connection and hence a lower link utilization. 
      
      Setting this attribute to 0 means that a CLR of 1 can be tolerated. In 
      this case no bandwidth is reserved for nrt-VBR connections, and 
      CAC is effectively turned off. All nrt-VBR connections are 
      admitted."
   DEFVAL     { 7 }
::= { atmIfCANrtVbrProvEntry 3 }

atmIfCANrtVbrTxQueueLimit OBJECT-TYPE
   SYNTAX     Unsigned32 (0 | 5..63488)
   ACCESS     read-write
   STATUS     mandatory
   DESCRIPTION
     "This attribute specifies the default maximum queue length for the 
      emission queues used to buffer the traffic of the nrt-VBR service 
      category. It is used as the basis for setting the discard thresholds on 
      both common and per-VC queues. For the common queue, the 
      discard thresholds are set at approximately 35, 75, and 90 percent of 
      the value of this attribute for traffic at discard priority 3 (DP=3), 
      DP=2, and DP=1 respectively. 
      
      For per-VC queue, the actual limit may be reduced depending on 
      the shaping rate of the connection (for standard Vpt Vccs, this is the 
      shaping rate of the Vpt). The discard thresholds are set at 
      approximately 35, 75, and 90 percent of the scaled queue limit for 
      traffic at discard priority 3 (DP=3), DP=2, and DP=1 respectively. 
      However, a reduction will never result in a value that is less than the 
      value set for the minPerVcQueueLimit attribute.
      
      When the value of this attribute is autoConfigure, an appropriate 
      value is selected based on the card type. It is set to 1792 for low 
      speed cards such as DS1, E1, and IMA, set to 2304 for high speed 
      CQC-based ATM cards such as JT2, DS3, E3 and OC3, and set to 
      10240 for high speed ATM IP cards such as 3pDS3Atm2, 
      3pE3Atm2, 2pOC3SmAtm2 and 2pOC3MmAtm2. 
      
      For ATM IP FPs, the per-VC queue limit may be overridden for a 
      permanent connection by specifying a value in the Vcd Tm or Vpd 
      Tm txQueueLimit attribute. 
      
      On CQC-based ATM cards, this attribute must be set to the same 
      value for CA NrtVbr, Abr and Ubr components.
      
      The operational value of the maximum length of a queue (common 
      or per-VC) is indicated by the Vcc Tm, Vpc Tm, or Vpt Tm 
      txQueueThresholds attribute.
      
      When using per-VC queueing, this attribute is used as the default 
      txQueueLimit for all standard Vpts, regardless of their 
      atmServiceCategory.
      
      This attribute does not apply to basic Vpts.

      VALUES (

      0 = autoConfigure

      )"
   DEFVAL     { 0 }
::= { atmIfCANrtVbrProvEntry 4 }

atmIfCANrtVbrSvcHoldingPriority OBJECT-TYPE
   SYNTAX     INTEGER  {
                 n0(0),
                 n1(1),
                 n2(2),
                 n3(3),
                 n4(4) }
   ACCESS     read-write
   STATUS     obsolete
   DESCRIPTION
     "This attribute specifies the default holding priority which applies to 
      SVC nrt-VBR connections. It takes a value from 0 (highest priority) 
      to 4 (lowest priority). In a situation where the link bandwidth 
      fluctuates, such as over an IMA link, holding priority is used to 
      determine which connections are held and which are released. 
      Holding priority 4 connections are the first to be released. Holding 
      priority 0 connections are the last to be released.
      This attribute has been obsoleted and its value migrated to 
      holdingPriority attribute."
   DEFVAL     { n3 }
::= { atmIfCANrtVbrProvEntry 5 }

atmIfCANrtVbrMinPerVcQueueLimit OBJECT-TYPE
   SYNTAX     Unsigned32 (5..30000)
   ACCESS     read-write
   STATUS     mandatory
   DESCRIPTION
     "This attribute specifies the minimum queue limit for the per-VC 
      queues of connections of the nrt-VBR service category.
      
      The queue limit of a per-VC queue is obtained by scaling down the 
      txQueueLimit based on the shaping rate of that queue (shaping rate 
      for the connection, and for standard Vpt Vccs, the shaping rate of 
      the Vpt). This produces a constant delay for various queue lengths. 
      The txQueueLimit provides an upper bound while 
      minPerVcQueueLimit provides the lower bound. The value of this 
      attribute must not be greater than the value of the txQueueLimit 
      attribute. If this service category is used by Trunks the value of 
      minPerVcQueueLimit must be at least 88.
      
      On CQC-based ATM cards, this attribute must be set to the same 
      value for CA NrtVbr, Abr and Ubr components.
      
      This attribute is used as the default minPerVcQueueLimit for all 
      standard Vpts, regardless of their atmServiceCategory.
      
      This attribute does not apply to basic Vpts."
   DEFVAL     { 88 }
::= { atmIfCANrtVbrProvEntry 6 }

atmIfCANrtVbrPerVcQueueLimitReferenceRate OBJECT-TYPE
   SYNTAX     Unsigned32 (0 | 1..943396)
   ACCESS     read-write
   STATUS     mandatory
   DESCRIPTION
     "This attribute specifies the shaping rate to be used in computing the 
      tolerable delay for per-VC queues of connections of the nrt-VBR 
      service category. The delay is computed as the txQueueLimit 
      divided by the value of this attribute. 
      
      When the value of this attribute is autoConfigure, an appropriate 
      default is selected based on the card type. It is set to 3685 for low 
      speed cards such as DS1, E1 and IMA, set to 14740 for high speed 
      CQC-based ATM cards such as JT2, DS3, E3 and OC3, and set to 
      65511 for high speed ATM IP cards such as 3pDS3Atm2, 
      3pE3Atm2, 2pOC3SmAtm2 and 2pOC3MmAtm2.
      
      On CQC-based ATM cards, this attribute must be set to the same 
      value for CA NrtVbr, Abr and Ubr components.
      
      This attribute is used as the default perVcQueueLimitReferenceRate 
      for all standard Vpts, regardless of their atmServiceCategory.
      
      This attribute does not apply to basic Vpts.

      VALUES (

      0 = autoConfigure

      )"
   DEFVAL     { 0 }
::= { atmIfCANrtVbrProvEntry 7 }

atmIfCANrtVbrSvcMpHoldingPriority OBJECT-TYPE
   SYNTAX     INTEGER  {
                 n0(0),
                 n1(1),
                 n2(2),
                 n3(3),
                 n4(4) }
   ACCESS     read-write
   STATUS     mandatory
   DESCRIPTION
     "This attribute specifies the default holding priority which applies to 
      SVC nrt-VBR point-to-multipoint connections. It takes a value from 
      0 (highest priority) to 4 (lowest priority). In a situation where the 
      link bandwidth fluctuates, such as over an IMA link, holding 
      priority is used to determine which connections are held and which 
      are released. Holding priority 4 connections are the first to be 
      released. Holding priority 0 connections are the last to be released.
      
      This attribute does not apply to Vpt Vccs. When bandwidth 
      fluctuates, the entire Vpt, along with all Vpt Vccs is released as a 
      unit, according to the Vpt's holdingPriority."
   DEFVAL     { n3 }
::= { atmIfCANrtVbrProvEntry 8 }

atmIfCANrtVbrHoldingPriority OBJECT-TYPE
   SYNTAX     INTEGER  {
                 n0(0),
                 n1(1),
                 n2(2),
                 n3(3),
                 n4(4) }
   ACCESS     read-write
   STATUS     mandatory
   DESCRIPTION
     "This attribute specifies the holding priority which applies to SVP 
      and SVC nrt-VBR connections. It takes a value from 0 (highest 
      priority) to 4 (lowest priority). In a situation where the link 
      bandwidth fluctuates, such as over an IMA link, holding priority is 
      used to determine which connections are held and which are 
      released. Holding priority 4 connections are the first to be released. 
      Holding priority 0 connections are the last to be released.
      
      This attribute does not apply to Vpt Vccs. When bandwidth 
      fluctuates, the entire Vpt, along with all Vpt Vccs is released as a 
      unit, according to the Vpt's holdingPriority."
   DEFVAL     { n3 }
::= { atmIfCANrtVbrProvEntry 9 }

atmIfCANrtVbrEmissionPriority OBJECT-TYPE
   SYNTAX     Unsigned32 (0..7)
   ACCESS     read-write
   STATUS     mandatory
   DESCRIPTION
     "This attribute is not applicable and is ignored for CQC-based ATM 
      cards.
      
      This attribute specifies the emission priority (EP) which is used to 
      transmit traffic of the nrt-VBR service category. A lower numerical 
      value for this attribute specifies a higher emission priority. 0 is the 
      highest EP and 7 is the lowest. Cells at a higher emission priority 
      receive higher preference for link bandwidth. EPs 0 and 1 are in the 
      absolute priority range, and are unaffected by any minimum 
      bandwidth guarantees. EPs 2 through 7 are in the guaranteed 
      bandwidth range. Minimum bandwidth guarantee is specified in the 
      AtmIf/n Ep/m component. 
      
      Emission priority setting must comply with all of the following 
      constraints: 
      1. The emission priority numbers must be in the following order: 
      CBR <= rt-VBR <= nrt-VBR <= ABR <= UBR 
      2. Two different ATM service categories may share the same EP 
      only if they are both shaped. 
      3. CBR and rt-VBR may be placed either in the absolute priority 
      range (EP 0 or 1) or in the guaranteed bandwidth range (EP 2 
      through 7). 
      4. If both CBR and rt-VBR are shaped, rt-VBR must share the 
      same EP with CBR or ABR. If either one of CBR or rt-VBR are 
      not shaped, then they cannot share the same EP. 
      5. ABR service category is always deemed to be shaped. If nrt-VBR 
      is shaped, it must share the same EP with ABR. If nrt-VBR is not 
      shaped it must have a higher EP than ABR.
      6. If UBR is shaped, it must share the same EP with ABR. If UBR 
      is not shaped, it must have a lower EP than ABR. 
      
      This attribute does not apply to standard Vpt Vccs and basic Vpts."
   DEFVAL     { 4 }
::= { atmIfCANrtVbrProvEntry 10 }

atmIfCANrtVbrTrafficShaping OBJECT-TYPE
   SYNTAX     INTEGER  {
                 disabled(1),
                 enabled(5),
                 inverseUpc(6) }
   ACCESS     read-write
   STATUS     mandatory
   DESCRIPTION
     "This attribute specifies the default traffic shaping option for 
      connections of the nrt-VBR service category. An override to this 
      default may be specified for a provisioned connection under the Vcd 
      Tm or Vpd Tm component.
      
      When this attribute is set to disabled, traffic shaping cannot be 
      enabled for any nrt-VBR connections. 
      
      For CQC-based ATM cards, this attribute may be set to enabled 
      only if the interface supports shaping, as defined by the 
      perVcQueueInterfaces attribute in the AtmResourceControl Cqc 
      Override component. If that component does not exist, this attribute 
      must be set to disabled.
      
      If the Vcc Tm, Vpc Tm, or Vpt Tm txTrafficDescType indicates type 
      1 or 2, this attribute is ignored, and traffic shaping is not applicable 
      for that connection. 
      
      When this attribute is set to inverseUpc, traffic shaping for a 
      connection is enabled according to card type and the value of the 
      Vcc Tm, Vpc Tm, or Vpt Tm txTrafficDescType. 
      
      If this attribute is set to inverseUpc, and the txTrafficDescType is 3, 
      4, or 5, linear traffic shaping is enabled. Linear traffic shaping uses 
      a single static traffic shaping rate. 
      
      On CQC-based ATM FPs, if this attribute is set to inverseUpc, and 
      the txTrafficDescType is 6, 7, or 8, linear traffic shaping is enabled.
      
      On ATM IP FPs, if this attribute is set to inverseUpc, and the 
      txTrafficDescType is 6, 7, or 8, inverse-UPC (also referred to as 
      VBR or dual leaky bucket) traffic shaping is enabled. Inverse-UPC 
      traffic shaping can burst above the sustained cell rate to the peak 
      cell rate for the duration defined by maximum burst size. Inverse-
      UPC traffic shaping exactly conforms to the requirements of a dual 
      leaky bucket UPC enforcer. 
      
      When this attribute is set to enabled and the txTrafficDescType is 3, 
      4, 5, 6, 7, or 8, traffic shaping for a connection is enabled using 
      linear shaping. 
      
      Enabling or disabling traffic shaping may require a matching 
      change to the emissionPriority attribute and 
      unshapedTransmitQueueing attribute for this service category. 
      Refer to those attributes for the complete description of the 
      interactions.
      
      This attribute does not apply to standard Vpt Vccs and basic Vpts."
   DEFVAL     { disabled }
::= { atmIfCANrtVbrProvEntry 14 }

atmIfCANrtVbrShapeRecoupPolicy OBJECT-TYPE
   SYNTAX     INTEGER  {
                 minimumCdv(0),
                 maximumEfficiency(1) }
   ACCESS     read-write
   STATUS     mandatory
   DESCRIPTION
     "This attribute specifies the shaping recoup policy for the nrt-VBR 
      service category. This is the policy which is used to recoup shaping 
      opportunities which are lost when more than one connection 
      schedules a cell for the same transmit opportunity. In this case, one 
      connection is scheduled, and the cell from the other connection is 
      delayed by one cell time. This attribute affects how the transmit 
      time is calculated for the next cell on the delayed connection. This 
      attribute is ignored if this service category is not shaped.
      
      When the connection which was delayed schedules the next cell to 
      transmit, it may calculate the time as a difference from either the 
      previous actual cell transmit time, or the time when the previous 
      cell should have been transmitted.
      
      Setting this attribute to maximumEfficiency results in each 
      connection trying to recoup or regain any delays in scheduling. The 
      transmit time from the next cell is calculated from the time when 
      the cell should originally have been sent. Cell delay variation 
      (CDV) occurs in this case since the cells are sent with less than the 
      shaping delay between them. However, in general the shaper 
      recovers (recoups) lost opportunities and improves efficiency.
      
      Setting this attribute to minimumCdv results in connections not 
      trying to recoup or regain any delays in scheduling. The transmit 
      time for the next cell is calculated from the time when the previous 
      cell was actually transmitted. This minimizes CDV, but results in 
      missed cell opportunities.
      
      This attribute does not apply to standard Vpt Vccs and basic Vpts."
   DEFVAL     { maximumEfficiency }
::= { atmIfCANrtVbrProvEntry 15 }

atmIfCANrtVbrUnshapedTransmitQueueing OBJECT-TYPE
   SYNTAX     INTEGER  {
                 perVc(0),
                 common(1),
                 autoConfigure(2) }
   ACCESS     read-write
   STATUS     mandatory
   DESCRIPTION
     "This attribute specifies the default queuing option for unshaped 
      connections of the nrt-VBR service category. This attribute controls 
      whether common or per-VC queueing is used. 
      
      Per-VC queueing means that each connection has its own buffering 
      and queue limits.
      
      Common queueing means that cells are queued in First In First Out 
      order on a common queue. The common queue has one set of 
      congestion control levels for all cells enqueued on it. For ATM IP 
      cards, there is one common queue for the nrt-VBR service category. 
      For CQC-based ATM cards, there is one common queue which is 
      shared by the nrt-VBR, ABR and UBR service categories. 
      
      For ATM IP cards, if traffic shaping for this service category is 
      disabled, this attribute may take any of the three values. In this case, 
      the value autoConfigure is interpreted to mean per-VC queueing.
      
      For ATM IP cards, if traffic shaping for this service category is not 
      disabled, the only permitted values are perVc and autoConfigure. 
      In this case, the result is that all connections use per-VC queueing.
      
      For CQC-based ATM cards, if the perVcQueueInterfaces attribute 
      of the Lp Eng Arc Cqc component permits shaping for this 
      interface, then this attribute may take any of the three values. In this 
      case, the value autoConfigure is interpreted to mean per-VC 
      queueing.
      
      For CQC-based ATM cards, if the perVcQueueInterfaces attribute 
      of the Lp Eng Arc Cqc component does not permit shaping for this 
      interface, then this attribute may take the values common or 
      autoConfigure. In this case, the value autoConfigure is interpreted 
      to mean common queueing. 
      
      If this attribute is set to autoConfigure, an override to this default 
      may be specified for a provisioned connection under the Vcd Tm or 
      Vpd Tm component. 
      
      The opUnshapedTransmitQueueing attribute of this component 
      indicates whether the transmit queueing is perVc or common.
      
      This attribute does not apply to standard Vpt Vccs and basic Vpts."
   DEFVAL     { autoConfigure }
::= { atmIfCANrtVbrProvEntry 16 }

atmIfCANrtVbrUsageParameterControl OBJECT-TYPE
   SYNTAX     INTEGER  {
                 enforced(0),
                 disabled(1),
                 monitored(4) }
   ACCESS     read-write
   STATUS     mandatory
   DESCRIPTION
     "This attribute specifies the default usage parameter control (UPC) 
      option for connections of the nrt-VBR service category. This 
      attribute is ignored if the rxTrafficDescriptorType indicates 1 or 2. 
      An override to this default may be specified for a provisioned 
      connection under the Vcd Tm or Vpd Tm component.
      
      When this attribute is set to enforced, UPC is enabled for each 
      connection. When UPC is enforced, non-conforming cells are either 
      tagged or discarded depending on the rxTrafficDescriptorType. 
      
      On ATM IP FPs, when this attribute is set to monitored, UPC 
      conformance checking is performed, except, instead of the non-
      conforming cells being tagged or discarded, they are merely 
      counted in the UPC violations counts, and passed on unchanged.
      
      On CQC-based ATM FPs, when this attribute is set to monitored, it 
      has the same effect as setting it to disabled. 
      
      When this attribute is set to disabled, UPC is disabled on the receive 
      path for all nrt-VBR connections.
      
      This attribute does not apply to standard Vpt Vccs and basic Vpts."
   DEFVAL     { disabled }
::= { atmIfCANrtVbrProvEntry 17 }

atmIfCANrtVbrWeightPolicy OBJECT-TYPE
   SYNTAX     INTEGER  {
                 scr(1),
                 pcr(2),
                 ecr(3) }
   ACCESS     read-write
   STATUS     mandatory
   DESCRIPTION
     "This attribute specifies the policy which is applied when calculating 
      the fairness weight for unshaped connections of the nrt-VBR 
      service category. The fairness weight for a connection determines 
      the relative amount of bandwidth which that connection obtains, 
      compared to other connections in the same service category. 
      Connections with equal weight get equal transmit opportunities. 
      Connections with higher weights get more transmit opportunities 
      compared with connections that have lower weights. An override to 
      this default may be specified for a provisioned connection under the 
      Vcd Tm or Vpd Tm component. 
      
      The fairness weight for a connection is directly proportional to the 
      value of one of the traffic descriptor parameters for that connection. 
      This attribute specifies which traffic descriptor parameter is used for 
      connections of the nrt-VBR service category. 
      
      This attribute is ignored on CQC-based ATM cards. This attribute is 
      also ignored on ATM IP cards if unshapedTransmitQueueing is set 
      for common queuing. 
      
      If this attribute is set to scr, the fairness weight is proportional to the 
      transmit sustained cell rate (SCR) of a connection. Connections 
      with a higher SCR have a higher fairness weight. For connections 
      with txTrafficDescType 3, which have no SCR, the sustained cell 
      rate is assumed to be equal to the peak cell rate. 
      
      If this attribute is set to pcr, the fairness weight is proportional to 
      the transmit peak cell rate (PCR) of a connection. Connections with 
      a higher PCR have a higher fairness weight. Connections with 
      txTrafficDescType 1 or 2 get a minimum weight, which is 1. 
      
      If this attribute is set to ecr, the fairness weight is proportional to 
      the equivalent cell rate (ECR) of a connection as calculated by 
      connection admission control (CAC). Connections with a higher 
      ECR have a higher fairness weight. Connections with an ECR of 0 
      get a minimum weight, which is 1. 
      
      The weight of a connection is visible in the Vcc Tm, Vpc Tm, or Vpt 
      Tm weight attribute.
      
      This attribute does not apply to standard Vpt Vccs and basic Vpts."
   DEFVAL     { ecr }
::= { atmIfCANrtVbrProvEntry 18 }

atmIfCANrtVbrForceTagging OBJECT-TYPE
   SYNTAX     INTEGER  {
                 enabled(0),
                 disabled(1) }
   ACCESS     read-write
   STATUS     mandatory
   DESCRIPTION
     "This attribute specifies the default of whether to force tagging 
      (CLP=1) of all cells for all nrt-VBR connections. An override to 
      this default may be specified for a provisioned connection under the 
      Vcd Tm or Vpd Tm component. 
      
      When this attribute is set to enabled, CLP is set to 1 for all cells in 
      the transmit direction. Force tagging is only supported on ATM IP 
      FPs. 
      
      On CQC-based ATM FPs, this attribute must be set to disabled. 
      When this attribute is set to disabled, CLP is unchanged for all cells 
      in the transmit direction.
      
      This attribute never applies to any type of Vpt."
   DEFVAL     { disabled }
::= { atmIfCANrtVbrProvEntry 19 }

atmIfCANrtVbrOperTable OBJECT-TYPE
   SYNTAX     SEQUENCE OF AtmIfCANrtVbrOperEntry
   ACCESS     not-accessible
   STATUS     mandatory
   DESCRIPTION
     "This group contains operational attributes for the nrt-VBR service 
      category."
::= { atmIfCANrtVbr 110 }

atmIfCANrtVbrOperEntry OBJECT-TYPE
   SYNTAX     AtmIfCANrtVbrOperEntry
   ACCESS     not-accessible
   STATUS     mandatory
   DESCRIPTION
     "An entry in the atmIfCANrtVbrOperTable."
   INDEX {
      atmIfIndex,
      atmIfCAIndex,
      atmIfCANrtVbrIndex }
::= { atmIfCANrtVbrOperTable 1 }

AtmIfCANrtVbrOperEntry ::= SEQUENCE {
   atmIfCANrtVbrOpUnshapedTransmitQueueing
      INTEGER,
   atmIfCANrtVbrEpdOffset
      Unsigned32 }

atmIfCANrtVbrOpUnshapedTransmitQueueing OBJECT-TYPE
   SYNTAX     INTEGER  {
                 perVc(0),
                 common(1) }
   ACCESS     read-only
   STATUS     mandatory
   DESCRIPTION
     "This attribute indicates the state of transmit queueing for unshaped 
      nrt-VBR connections.
      
      A value of perVc indicates that any unshaped connections use per-
      VC queueing. A value of common indicates that traffic for 
      unshaped connections uses the common queue which corresponds 
      to the EP for this service category."
::= { atmIfCANrtVbrOperEntry 10 }

atmIfCANrtVbrEpdOffset OBJECT-TYPE
   SYNTAX     Unsigned32 (0 | 5..1024)
   ACCESS     read-only
   STATUS     mandatory
   DESCRIPTION
     "This attribute indicates the Early Packet Discard (EPD) offset which 
      is currently in use for this service category. The EPD offset is used 
      to derive the EPD thresholds for each CC level.
      
      Any connection under this service category which requires the 
      txPacketWiseDiscard feature must specify a transmit queue limit 
      which is at least 5.71 times this offset. This ensures that the derived 
      Epd threshold will never be less than 17.5 % of the transmit queue 
      limit. If this is not done, txPacketWiseDiscard for the connection 
      will be automatically disabled.
      
      The value of this EPD offset is specified under the lp/x eng arc aqm 
      ov component."
::= { atmIfCANrtVbrOperEntry 11 }


-- AtmIf/n CA AvailableBitRate/n
-- This component manages the default characteristics of the available 
-- bit rate (ABR) service category. There is full support for ABR 
-- connections on ATM IP cards. On CQC-based ATM cards there is 
-- limited support for ABR connections.

atmIfCAAbr OBJECT IDENTIFIER ::= { atmIfCA 5 }



atmIfCAAbrRowStatusTable OBJECT-TYPE
   SYNTAX     SEQUENCE OF AtmIfCAAbrRowStatusEntry
   ACCESS     not-accessible
   STATUS     mandatory
   DESCRIPTION
     "This entry controls the addition and deletion of 
      atmIfCAAbr components."
::= { atmIfCAAbr 1 }

atmIfCAAbrRowStatusEntry OBJECT-TYPE
   SYNTAX     AtmIfCAAbrRowStatusEntry
   ACCESS     not-accessible
   STATUS     mandatory
   DESCRIPTION
     "A single entry in the table represents a single 
      atmIfCAAbr component."
   INDEX {
      atmIfIndex,
      atmIfCAIndex,
      atmIfCAAbrIndex }
::= { atmIfCAAbrRowStatusTable 1 }

AtmIfCAAbrRowStatusEntry ::= SEQUENCE {
   atmIfCAAbrRowStatus
      RowStatus,
   atmIfCAAbrComponentName
      DisplayString,
   atmIfCAAbrStorageType
      StorageType,
   atmIfCAAbrIndex
      Integer32 }

atmIfCAAbrRowStatus OBJECT-TYPE
   SYNTAX     RowStatus 
   ACCESS     read-write
   STATUS     mandatory
   DESCRIPTION
     "This variable is used as the basis for SNMP naming of
      atmIfCAAbr components.
      These components can be added."
::= { atmIfCAAbrRowStatusEntry 1 }

atmIfCAAbrComponentName OBJECT-TYPE
   SYNTAX     DisplayString 
   ACCESS     read-only
   STATUS     mandatory
   DESCRIPTION
     "This variable provides the component's string name for
      use with the ASCII Console Interface"
::= { atmIfCAAbrRowStatusEntry 2 }

atmIfCAAbrStorageType OBJECT-TYPE
   SYNTAX     StorageType 
   ACCESS     read-only
   STATUS     mandatory
   DESCRIPTION
     "This variable represents the storage type value for the
      atmIfCAAbr tables."
::= { atmIfCAAbrRowStatusEntry 4 }

atmIfCAAbrIndex OBJECT-TYPE
   SYNTAX     Integer32 (0)
   ACCESS     not-accessible
   STATUS     mandatory
   DESCRIPTION
     "This variable represents the index for the atmIfCAAbr tables."
::= { atmIfCAAbrRowStatusEntry 10 }

atmIfCAAbrProvTable OBJECT-TYPE
   SYNTAX     SEQUENCE OF AtmIfCAAbrProvEntry
   ACCESS     not-accessible
   STATUS     mandatory
   DESCRIPTION
     "This group contains provisioned attributes which control the ABR 
      service category for this interface."
::= { atmIfCAAbr 100 }

atmIfCAAbrProvEntry OBJECT-TYPE
   SYNTAX     AtmIfCAAbrProvEntry
   ACCESS     not-accessible
   STATUS     mandatory
   DESCRIPTION
     "An entry in the atmIfCAAbrProvTable."
   INDEX {
      atmIfIndex,
      atmIfCAIndex,
      atmIfCAAbrIndex }
::= { atmIfCAAbrProvTable 1 }

AtmIfCAAbrProvEntry ::= SEQUENCE {
   atmIfCAAbrPool
      INTEGER,
   atmIfCAAbrCdvt
      Unsigned32,
   atmIfCAAbrTxQueueLimit
      Unsigned32,
   atmIfCAAbrMinPerVcQueueLimit
      Unsigned32,
   atmIfCAAbrPerVcQueueLimitReferenceRate
      Unsigned32,
   atmIfCAAbrEmissionPriority
      Unsigned32,
   atmIfCAAbrFairnessPolicy
      INTEGER,
   atmIfCAAbrFrttPortion
      Unsigned32,
   atmIfCAAbrAbrConnectionType
      INTEGER,
   atmIfCAAbrUsageParameterControl
      INTEGER,
   atmIfCAAbrInitialCellRate
      Unsigned32,
   atmIfCAAbrRateDecreaseFactor
      Unsigned32,
   atmIfCAAbrRateIncreaseFactor
      Unsigned32,
   atmIfCAAbrMaxCellPerRmCell
      Unsigned32,
   atmIfCAAbrMaxTimeBetweenRmCells
      Unsigned32,
   atmIfCAAbrCutoffDecreaseFactor
      Unsigned32,
   atmIfCAAbrAcrDecreaseTimeFactor
      Unsigned32,
   atmIfCAAbrDgcraMaximumDelay
      Unsigned32,
   atmIfCAAbrDgcraMinimumDelay
      Unsigned32,
   atmIfCAAbrHoldingPriority
      INTEGER }

atmIfCAAbrPool OBJECT-TYPE
   SYNTAX     INTEGER  {
                 pool1(1),
                 pool2(2),
                 pool3(3),
                 pool4(4),
                 pool5(5) }
   ACCESS     read-write
   STATUS     mandatory
   DESCRIPTION
     "This attribute specifies the bandwidth pool which is to be used to 
      support the available bit rate (ABR) service category except for 
      connections managed by a Vpt CA. The percentage of link capacity 
      reserved for the given bandwidth pool is the maximum bandwidth 
      that can be allocated to ABR traffic. The percentage allocated to 
      each bandwidth pool can be provisioned through the bandwidthPool 
      attribute under the CA."
   DEFVAL     { pool1 }
::= { atmIfCAAbrProvEntry 10 }

atmIfCAAbrCdvt OBJECT-TYPE
   SYNTAX     Unsigned32 (1..1200000)
   ACCESS     read-write
   STATUS     mandatory
   DESCRIPTION
     "This attribute specifies the default cell delay variation tolerance 
      (CDVT) for all connections of the ABR service category. An 
      override to this default may be specified for a provisioned 
      connection under the Vcd Tm or Vpd Tm component, or signalled in 
      the SVC Traffic Descriptor Information Element. 
      
      This attribute is used by dynamic generic cell rate algorithm 
      (DGCRA) policer on ATM IP cards. On CQC-based ATM cards 
      ABR UPC is enforced using PCR and CDVT."
   DEFVAL     { 250 }
::= { atmIfCAAbrProvEntry 11 }

atmIfCAAbrTxQueueLimit OBJECT-TYPE
   SYNTAX     Unsigned32 (0 | 5..63488)
   ACCESS     read-write
   STATUS     mandatory
   DESCRIPTION
     "This attribute specifies the default maximum queue length for the 
      emission queues used to buffer the traffic of the ABR service 
      category. It is used as the basis for setting the discard thresholds on 
      ABR per-VC queues. 
      
      For per-VC queue, the actual limit may be reduced depending on 
      the peak cell rate. The discard thresholds are set at approximately 
      35, 75 and 90 percent of the scaled queue limit for traffic at discard 
      priority 3 (DP=3), DP=2 and DP=1 respectively. However, a 
      reduction will never result in a value that is less than the value set 
      for the minPerVcQueueLimit attribute.
      
      When the value of this attribute is autoConfigure, an appropriate 
      value is selected based on the card type. It is set to 1792 for low 
      speed cards such as DS1, E1 and IMA, set to 2304 for high speed 
      CQC-based ATM cards such as JT2, DS3, E3 and OC3, and set to 
      10240 for high speed ATM IP cards such as 3pDS3Atm2, 
      3pE3Atm2, 2pOC3SmAtm2 and 2pOC3MmAtm2. 
      
      On CQC-based ATM cards, this attribute must be set to the same 
      value for CA NrtVbr, Abr and Ubr components. 
      
      For ATM IP FPs, the per-VC queue limit may be overridden for a 
      permanent connection by specifying a value in the Vcd Tm or Vpd 
      Tm txQueueLimit attribute. 
      
      The operational value of the maximum length of a queue (common 
      or per-VC) is indicated by the Vcc Tm, Vpc Tm, or Vpt Tm 
      txQueueThresholds attribute.
      
      For standard Vpts, this attribute does not apply when using per-VC 
      queuing and only applies when using common queueing. When 
      using per-VC queueing, regardless of the Vpt's service category, 
      standard Vpts use the AtmIf Ca NrtVbr txQueueLimit value as their 
      default.
      
      This attribute does not apply to basic Vpts.

      VALUES (

      0 = autoConfigure

      )"
   DEFVAL     { 0 }
::= { atmIfCAAbrProvEntry 12 }

atmIfCAAbrMinPerVcQueueLimit OBJECT-TYPE
   SYNTAX     Unsigned32 (5..63488)
   ACCESS     read-write
   STATUS     mandatory
   DESCRIPTION
     "This attribute specifies the minimum queue limit for the per-VC 
      queues of connections of the ABR service category.
      
      The queue limit of a per-VC queue is obtained by scaling down the 
      txQueueLimit based on the peak cell rate of that queue. This 
      produces a constant delay for various queue lengths. The 
      txQueueLimit provides an upper bound while minPerVcQueueLimit 
      provides the lower bound. The value of this attribute must not be 
      greater than the value of the txQueueLimit attribute. If this service 
      category is used by Trunks the value of minPerVcQueueLimit must 
      be at least 88.
      
      On CQC-based ATM cards, this attribute must be set to the same 
      value for CA NrtVbr, Abr and Ubr components.
      
      For Vpts, this attribute does not apply. Regardless of Vpt service 
      category, standard Vpts always use the AtmIf Ca NrtVbr 
      minPerVcQueueLimit value as their default. To determine the queue 
      limit of a standard Vpt Vcc, the txQueueLimit is scaled down by the 
      Vpt shaping rate."
   DEFVAL     { 88 }
::= { atmIfCAAbrProvEntry 13 }

atmIfCAAbrPerVcQueueLimitReferenceRate OBJECT-TYPE
   SYNTAX     Unsigned32 (0 | 1..943396)
   ACCESS     read-write
   STATUS     mandatory
   DESCRIPTION
     "This attribute specifies the shaping rate to be used in computing the 
      tolerable delay for per-VC queues of connections of the ABR 
      service category. The delay is computed as the txQueueLimit 
      divided by the value of this attribute. 
      
      When the value of this attribute is autoConfigure, an appropriate 
      default is selected based on the card type. It is set to 3685 for low 
      speed cards such as DS1, E1 and IMA, set to 14740 for high speed 
      CQC-based ATM cards such as JT2, DS3, E3 and OC3, and set to 
      65511 for high speed ATM IP cards such as 3pDS3Atm2, 
      3pE3Atm2, 2pOC3SmAtm2 and 2pOC3MmAtm2. 
      
      On CQC-based ATM cards, this attribute must be set to the same 
      value for CA NrtVbr, Abr and Ubr components.
      
      For Vpts, this attribute does not apply. Regardless of Vpt service 
      category, standard Vpts always use the AtmIf Ca NrtVbr 
      perVcQueueLimitReferenceRate value as their default.

      VALUES (

      0 = autoConfigure

      )"
   DEFVAL     { 0 }
::= { atmIfCAAbrProvEntry 14 }

atmIfCAAbrEmissionPriority OBJECT-TYPE
   SYNTAX     Unsigned32 (0..7)
   ACCESS     read-write
   STATUS     mandatory
   DESCRIPTION
     "This attribute is not applicable and is ignored for CQC-based ATM 
      cards.
      
      This attribute specifies the emission priority (EP) which is used to 
      transmit traffic of the ABR service category. A lower numerical 
      value for this attribute specifies a higher emission priority. 0 is the 
      highest EP and 7 is the lowest. Cells at a higher emission priority 
      receive higher preference for link bandwidth. EPs 0 and 1 are in the 
      absolute priority range, and are unaffected by any minimum 
      bandwidth guarantees. EPs 2 through 7 are in the guaranteed 
      bandwidth range. Minimum bandwidth guarantee is specified in the 
      AtmIf/n Ep/m component. 
      
      Emission priority setting must comply with all of the following 
      constraints: 
      1. The emission priority numbers must be in the following order: 
      CBR <= rt-VBR <= nrt-VBR <= ABR <= UBR 
      2. Two different ATM service categories may share the same EP 
      only if they are both shaped. 
      3. CBR and rt-VBR may be placed either in the absolute priority 
      range (EP 0 or 1) or in the guaranteed bandwidth range (EP 2 
      through 7). 
      4. If both CBR and rt-VBR are shaped, rt-VBR must share the 
      same EP with CBR or ABR. If either one of CBR or rt-VBR are 
      not shaped, then they cannot share the same EP. 
      5. ABR service category is always deemed to be shaped. If nrt-VBR 
      is shaped, it must share the same EP with ABR. If nrt-VBR is not 
      shaped it must have a higher EP than ABR.
      6. If UBR is shaped, it must share the same EP with ABR. If UBR 
      is not shaped, it must have a lower EP than ABR.
      
      This attribute does not apply to standard Vpt Vccs and basic Vpts."
   DEFVAL     { 6 }
::= { atmIfCAAbrProvEntry 15 }

atmIfCAAbrFairnessPolicy OBJECT-TYPE
   SYNTAX     INTEGER  {
                 pcr(2),
                 pcrMinusMcr(4) }
   ACCESS     read-write
   STATUS     mandatory
   DESCRIPTION
     "This attribute specifies the fairness policy which is applied to 
      available bandwidth when performing the ER calculation in the 
      ABR service category. This applies to any connection point 
      performing explicit rate calculations. Each ABR connection is 
      assigned a weight. Connections with a higher weight get a greater 
      proportion of the available ABR bandwidth compared with 
      connections that have lower weights. This attribute is ignored on 
      CQC-based ATM cards. 
      
      If the value is mcr, the congestion fairness weight is based on the 
      Minimum Cell Rate (MCR) of the connection.
      
      If the value is pcr, the congestion fairness weight is based on the 
      Peak Cell Rate (PCR) of the connection. 
      
      If the value is pcrMinusMcr, the congestion fairness weight is 
      based on the difference between the Peak Cell Rate and the 
      Minimum Cell Rate (PCR - MCR) of the connection."
   DEFVAL     { pcrMinusMcr }
::= { atmIfCAAbrProvEntry 19 }

atmIfCAAbrFrttPortion OBJECT-TYPE
   SYNTAX     Unsigned32 (0..10000)
   ACCESS     read-write
   STATUS     mandatory
   DESCRIPTION
     "This attribute specifies the portion of the Fixed Round Trip Time 
      (FRTT) which is added to each ABR call setup which traverses this 
      interface. The FRTT for the entire call is the sum of the FRTT 
      portions for each interface traversed by the call. FRTT is used by 
      the ABR Source or Virtual Source to adjust the value of ICR 
      according to the rules specified in the ATM Forum TM Version 4.0 
      specification.
      
      The frttPortion includes propagation delay through the physical 
      media, plus delays included by the transmission system, plus fixed 
      components of switch processing delay.
      
      This attribute is used by ATM Networking at call set-up time for 
      ABR connections directed over this interface."
   DEFVAL     { 5 }
::= { atmIfCAAbrProvEntry 20 }

atmIfCAAbrAbrConnectionType OBJECT-TYPE
   SYNTAX     INTEGER  {
                 abrSwitch(0),
                 virtualSourceDest(3),
                 nonAbrInterworking(5) }
   ACCESS     read-write
   STATUS     mandatory
   DESCRIPTION
     "This attribute specifies the default type for ABR connections. It may 
      be overridden by the abrConnectionType attribute under the Vcd Tm 
      or Vpd Tm component, or by other configuration options. For 
      example, for ABR end point connections originating at this switch, 
      the Vcc Tm abrConnectionType will show sourceDest regardless of 
      the setting of this attribute. 
      
      If this attribute is set to abrSwitch, traversing ABR connections 
      default either to erSwitch or to efciSwitch, depending on the card 
      type and connection type. If the interface to which traffic is directed 
      across the backplane is configured as type virtualSourceDest and 
      this is a ATM IP FP, then connection points under this AtmIf are 
      activated as type virtualSourceDest. 
      
      If this attribute is set to virtualSourceDest, traversing ABR 
      connections may be instantiated as one of the following types: 
      erSwitch, efciSwitch, or virtualSourceDest. A Virtual Source-
      Virtual Destination (VS/VD) boundary forms a break in the end to 
      end flow of RM cells as defined in the ATM Forum Specification for 
      Traffic Management Version 4.0. On ATM IP cards, a VS/VD 
      boundary can be configured for a connection providing all of the 
      following conditions are met: 
      1. the ABR connection is traversing (not terminating at) this 
      interface; 
      2. both this interface and next hop interface to which traffic is 
      directed across the backplane are located on ATM IP cards; 
      3. one or both connecting points are configured as 
      virtualSourceDest, 
      4. the next hop interface to which traffic is directed across the 
      backplane is not configured as nonAbrInterworking,
      5. the connection is not a Vcc under a standard VPT. 
      
      If this attribute is set to nonAbrInterworking, this interface is 
      defined as a point of interworking between an ABR and a non-ABR 
      connection. In this case the next hop interface to which traffic is 
      directed across the backplane is activated as type sourceDest. 
      
      The Vcc or Vpc Tm abrConnectionType operational attribute 
      indicates what type of ABR connection was activated."
   DEFVAL     { abrSwitch }
::= { atmIfCAAbrProvEntry 21 }

atmIfCAAbrUsageParameterControl OBJECT-TYPE
   SYNTAX     INTEGER  {
                 enforced(0),
                 disabled(1),
                 monitored(4) }
   ACCESS     read-write
   STATUS     mandatory
   DESCRIPTION
     "This attribute specifies the default usage parameter control (UPC) 
      option for connections of the ABR service category. An override to 
      this default may be specified for a provisioned connection under the 
      Vcd Tm or Vpd Tm component.
      
      For ATM IP cards, if this attribute is set to enforced, UPC for ABR 
      connection is enforced as a Dynamic Generic Cell Rate Algorithm 
      (DGCRA) based on the connection traffic descriptor. 
      
      For CQC-based ATM cards, if this attribute is set to enforced, the 
      connection enforces a single GCRA policer at the defined PCR and 
      CDVT for this connection. 
      
      When UPC is enforced on an ABR connection, non-conforming 
      cells are discarded. 
      
      On ATM IP FPs, when this attribute is set to monitored, UPC 
      conformance checking is performed, except, instead of the non-
      conforming cells being discarded, they are merely counted in the 
      UPC violations counts, and passed on unchanged. 
      
      On CQC-based ATM FPs, when this attribute is set to monitored, it 
      has the same effect as setting it to disabled. 
      
      When this attribute is set to disabled, UPC is disabled on the receive 
      path for all ABR connections.
      
      This attribute does not apply to standard Vpt Vccs and basic Vpts."
   DEFVAL     { disabled }
::= { atmIfCAAbrProvEntry 22 }

atmIfCAAbrInitialCellRate OBJECT-TYPE
   SYNTAX     Unsigned32 (0..16777215 | 16777217 | 16777218)
   ACCESS     read-write
   STATUS     mandatory
   DESCRIPTION
     "This attribute specifies the default Initial Cell Rate (ICR) parameter 
      for ABR connections. An override to this default may be specified 
      for a provisioned connection under the Vcd Tm Abr or Vpd Tm Abr 
      component, or signalled in the ABR Setup Parameters Information 
      Element. 
      
      ICR is the rate at which a source should send initially and after an 
      idle period.
      
      When this attribute is set to useMcr, ICR is set to the same value as 
      the Minimum Cell Rate (MCR) for the connection.
      
      When this attribute is set to usePcr, ICR is set to the same value as 
      the Peak Cell Rate (PCR) for the connection.
      
      When this attribute is set to some explicit number, that number is 
      used as the ICR, provided it is between MCR and PCR. If the 
      explicit number is below MCR, then MCR is used as ICR. If the 
      explicit number is above PCR, then PCR is used as ICR.

      VALUES (

      16777217 = useMcr

      16777218 = usePcr

      )"
   DEFVAL     { 16777218 }
::= { atmIfCAAbrProvEntry 23 }

atmIfCAAbrRateDecreaseFactor OBJECT-TYPE
   SYNTAX     Unsigned32 (0..15)
   ACCESS     read-write
   STATUS     mandatory
   DESCRIPTION
     "This attribute specifies the default Rate Decrease Factor (RDF) for 
      ABR connections. An override to this default may be specified for a 
      provisioned connection under the Vcd Tm Abr or Vpd Tm Abr 
      component, or signalled in the ABR Setup Parameters Information 
      Element.
      
      The RDF value is computed by using the provisioned value of this 
      attribute, n, as 2 to the inverse power n. For example, if the value of 
      this attribute is 8, RDF is 2E-8 = 1/256.
      
      RDF controls the amount by which the cell transmission rate may 
      decrease upon receipt of a backward Resource Management (B-
      RM) cell. For example, if a backward RM cell is received with the 
      Congestion Indication (CI) field set to 1, the Allowed Cell Rate 
      (ACR) value would be reduced by the amount (RDF*ACR). The 
      ACR is not allowed to fall below the Minimum Cell Rate (MCR), in 
      which case the ACR is set to MCR."
   DEFVAL     { 15 }
::= { atmIfCAAbrProvEntry 24 }

atmIfCAAbrRateIncreaseFactor OBJECT-TYPE
   SYNTAX     Unsigned32 (0..15)
   ACCESS     read-write
   STATUS     mandatory
   DESCRIPTION
     "This attribute specifies the default Rate Increase Factor (RIF) for 
      ABR connections. An override to this default may be specified for a 
      provisioned connection under the Vcd Tm Abr or Vpd Tm Abr 
      component, or signalled in the ABR Setup Parameters Information 
      Element.
      
      The RIF value is computed by using the provisioned value of this 
      attribute, n, as 2 to the inverse power n. For example, if the value of 
      this attribute is 6, RIF is 2E-6 = 1/64.
      
      RIF controls the amount by which the cell transmission rate may 
      increase upon receipt of a backward Resource Management (B-RM) 
      cell. For example, if a backward RM cell is received with the 
      Congestion Indication (CI) and the No Increase (NI) fields both set 
      to 0, the Allowed Cell Rate (ACR) value would be increased by the 
      amount (RIF*ACR). The ACR is not allowed to exceed the Peak 
      Cell Rate (PCR), in which case the ACR is set to PCR."
   DEFVAL     { 0 }
::= { atmIfCAAbrProvEntry 25 }

atmIfCAAbrMaxCellPerRmCell OBJECT-TYPE
   SYNTAX     Unsigned32 (2 | 4 | 8 | 16 | 32 | 64 | 128 | 256)
   ACCESS     read-write
   STATUS     mandatory
   DESCRIPTION
     "This attribute specifies the default number of user cells per 
      Resource Management cell (NRM) for ABR connections. An 
      override to this default may be specified for a provisioned 
      connection under the Vcd Tm Abr or Vpd Tm Abr component, or 
      signalled as the NRM parameter in the ABR Additional Parameters 
      Information Element. 
      
      NRM is the maximum number of cells an ABR source may transmit 
      for each forward Resource Management (F-RM) cell. The count of 
      the cells transmitted includes user cells, OAM cells, backward RM 
      cells, and the forward RM cell.
      
      Note that a value of 2 is not recommended even though it is 
      permitted according to the ATM Forum standard. When this 
      attribute is set to a value of 2, it is possible that only one forward 
      and one backward RM cell are repeatedly transmitted, and all data 
      traffic is queued up indefinitely.
      
      This attribute is ignored under all conditions where the Vcc Tm or 
      Vpc Tm operational attribute abrConnectionType indicates 
      explicitRateMarking."
   DEFVAL     { 256 }
::= { atmIfCAAbrProvEntry 26 }

atmIfCAAbrMaxTimeBetweenRmCells OBJECT-TYPE
   SYNTAX     Unsigned32 (781 | 1563 | 3125 | 6250 | 12500 | 25000 | 50000 | 100000)
   ACCESS     read-write
   STATUS     mandatory
   DESCRIPTION
     "This attribute specifies the default time between Resource 
      Management cells (TRM) for ABR connections. An override to this 
      default may be specified for a provisioned connection under the Vcd 
      Tm Abr or Vpd Tm Abr component, or signalled in the ABR 
      Additional Parameters Information Element.
      
      TRM provides an upper bound on the time interval between forward 
      Resource Management (F-RM) cells for an ABR source. Since the 
      last F-RM cell was sent, if at least TRM time has elapsed and at 
      least 2 other cells have been sent, the next cell to be transmitted 
      would be a forward RM cell.
      
      This attribute is ignored under all conditions where the Vcc Tm or 
      Vcd Tm operational attribute abrConnectionType is displayed as 
      erSwitch.
      
      The provisioned value of 781 is signalled in the ABR Additional 
      Parameters Information Element as 0. 
      1563 is signalled as 1. 
      3125 is signalled as 2. 
      6250 is signalled as 3. 
      12500 is signalled as 4. 
      25000 is signalled as 5. 
      50000 is signalled as 6. 
      100000 is signalled as 7."
   DEFVAL     { 100000 }
::= { atmIfCAAbrProvEntry 27 }

atmIfCAAbrCutoffDecreaseFactor OBJECT-TYPE
   SYNTAX     Unsigned32 (0 | 1 | 2 | 4 | 8 | 16 | 32 | 64)
   ACCESS     read-write
   STATUS     mandatory
   DESCRIPTION
     "This attribute specifies the default Cutoff Decrease Factor (CDF) 
      parameter for ABR connections. An override to this default may be 
      specified for a provisioned connection under the Vcd Tm Abr or Vpd 
      Tm Abr component, or signalled in the ABR Additional Parameters 
      Information Element.
      
      When the value of this attribute is non-zero, CDF is computed as 
      the inverse of the value. For example, if the value is 32, the value of 
      CDF is 1/32. When the value of this attribute is 0, CDF is also zero.
      
      CDF controls the decrease in the Allowed Cell Rate (ACR) 
      associated with the CRM parameter. CRM is the limit of the 
      number of forward Resource Management (F-RM) cells which may 
      be sent in the absence of received backward RM cells. When this 
      limit is crossed, the ACR value would be decreased by the amount 
      (CDF*ACR). The ACR is not allowed to fall below the MCR, in 
      which case the ACR is set to MCR."
   DEFVAL     { 16 }
::= { atmIfCAAbrProvEntry 28 }

atmIfCAAbrAcrDecreaseTimeFactor OBJECT-TYPE
   SYNTAX     Unsigned32 (0..1023)
   ACCESS     read-write
   STATUS     mandatory
   DESCRIPTION
     "This attribute specifies the default Allowed Cell Rate Decrease 
      Time Factor (ADTF) parameter for ABR connections. An override 
      to this default may be specified for a provisioned connection under 
      the Vcd Tm Abr or Vpd Tm Abr component, or signalled in the ABR 
      Additional Parameters Information Element.
      
      ADTF is the time interval permitted between sending forward 
      Resource Management (F-RM) cells before the Allowed Cell Rate 
      (ACR) is decreased to the Initial Cell Rate (ICR). In other words, if 
      the source does not transmit a forward RM cell for a period of 
      ADTF centi-seconds (hundredths of a second), it will reduce its 
      ACR to the value of its ICR. If ACR is already at or below ICR, 
      further rate reductions are defined by the CRM ABR parameter."
   DEFVAL     { 50 }
::= { atmIfCAAbrProvEntry 29 }

atmIfCAAbrDgcraMaximumDelay OBJECT-TYPE
   SYNTAX     Unsigned32 (1..16700000)
   ACCESS     read-write
   STATUS     mandatory
   DESCRIPTION
     "This attribute specifies the default maximum delay for Dynamic 
      General Cell Rate Algorithm (DGCRA) rate changes for ABR 
      connections. An override to this default may be specified for a 
      provisioned connection under the Vcd Tm Abr or Vpd Tm Abr 
      component.
      
      This attribute specifies an upper bound on the delay after which the 
      rate change induced by a backward Resource Management (B-RM) 
      cell departing from this interface (in the backward direction) is 
      expected to be observed at the interface (in the forward connection).
      
      This upper bound may be approximated as the round trip sum of the 
      fixed and propagation delays and the maximum queueing delays 
      between the ABR source and this interface.
      
      The value of this attribute is used in policing an ABR connection 
      using the DGCRA. A larger value for this attribute implies a more 
      lenient policer. When there is a decrease in the Allowed Cell Rate 
      (ACR), the policer waits a correspondingly longer period of time 
      before it enforces the new cell rate.
      
      The value of this attribute must be greater than or equal to 
      dgcraMinimumDelay, since the maximum delay must be greater 
      than or equal to the minimum delay."
   DEFVAL     { 10000 }
::= { atmIfCAAbrProvEntry 30 }

atmIfCAAbrDgcraMinimumDelay OBJECT-TYPE
   SYNTAX     Unsigned32 (1..16700000)
   ACCESS     read-write
   STATUS     mandatory
   DESCRIPTION
     "This attribute specifies the default minimum delay for Dynamic 
      General Cell Rate Algorithm (DGCRA) rate changes for ABR 
      connections. An override to this default may be specified for a 
      provisioned connection under the Vcd Tm Abr or Vpd Tm Abr 
      component.
      
      This attribute specifies a lower bound on the delay after which the 
      rate change induced by a backward Resource Management (B-RM) 
      cell departing from this interface (in the backward direction) is 
      expected to be observed at the interface (in the forward connection).
      
      This lower bound may be approximated as the round trip sum of the 
      fixed and propagation delays between the ABR source and this 
      interface.
      
      The value of this attribute is used in policing an ABR connection 
      using the DGCRA. A smaller value for this attribute implies a more 
      lenient policer. When there is an increase in the Allowed Cell Rate 
      (ACR), the policer waits for a correspondingly shorter period of 
      time before it enforces the new cell rate.
      
      The value of this attribute must be less than or equal to 
      dgcraMaximumDelay, since the maximum delay must be greater 
      than or equal to the minimum delay."
   DEFVAL     { 1 }
::= { atmIfCAAbrProvEntry 31 }

atmIfCAAbrHoldingPriority OBJECT-TYPE
   SYNTAX     INTEGER  {
                 n0(0),
                 n1(1),
                 n2(2),
                 n3(3),
                 n4(4) }
   ACCESS     read-write
   STATUS     mandatory
   DESCRIPTION
     "This attribute specifies the default holding priority which applies to 
      SVP and SVC ABR connections. It takes a value from 0 (highest 
      priority) to 4 (lowest priority). In a situation where the link 
      bandwidth fluctuates, such as over an IMA link, holding priority is 
      used to determine which connections are held and which are 
      released. Holding priority 4 connections are the first to be released. 
      Holding priority 0 connections are the last to be released.
      
      This attribute does not apply to Vpt Vccs. When bandwidth 
      fluctuates, the entire Vpt, along with all Vpt Vccs is released as a 
      unit, according to the Vpt's holdingPriority."
   DEFVAL     { n3 }
::= { atmIfCAAbrProvEntry 32 }

atmIfCAAbrOperTable OBJECT-TYPE
   SYNTAX     SEQUENCE OF AtmIfCAAbrOperEntry
   ACCESS     not-accessible
   STATUS     mandatory
   DESCRIPTION
     "This group contains operational attributes for the ABR service 
      category."
::= { atmIfCAAbr 110 }

atmIfCAAbrOperEntry OBJECT-TYPE
   SYNTAX     AtmIfCAAbrOperEntry
   ACCESS     not-accessible
   STATUS     mandatory
   DESCRIPTION
     "An entry in the atmIfCAAbrOperTable."
   INDEX {
      atmIfIndex,
      atmIfCAIndex,
      atmIfCAAbrIndex }
::= { atmIfCAAbrOperTable 1 }

AtmIfCAAbrOperEntry ::= SEQUENCE {
   atmIfCAAbrEpdOffset
      Unsigned32 }

atmIfCAAbrEpdOffset OBJECT-TYPE
   SYNTAX     Unsigned32 (0 | 5..1024)
   ACCESS     read-only
   STATUS     mandatory
   DESCRIPTION
     "This attribute indicates the Early Packet Discard (EPD) offset which 
      is currently in use for this service category. The EPD offset is used 
      to derive the EPD thresholds for each CC level.
      
      Any connection under this service category which requires the 
      txPacketWiseDiscard feature must specify a transmit queue limit 
      which is at least 5.71 times this offset. This ensures that the derived 
      Epd threshold will never be less than 17.5 % of the transmit queue 
      limit. If this is not done, txPacketWiseDiscard for the connection 
      will be automatically disabled.
      
      The value of this EPD offset is specified under the lp/x eng arc aqm 
      ov component."
::= { atmIfCAAbrOperEntry 10 }


-- AtmIf/n CA UnspecifiedBitRate/n
-- This component manages the default characteristics of the 
-- unspecified bit rate (UBR) service category.

atmIfCAUbr OBJECT IDENTIFIER ::= { atmIfCA 6 }



atmIfCAUbrRowStatusTable OBJECT-TYPE
   SYNTAX     SEQUENCE OF AtmIfCAUbrRowStatusEntry
   ACCESS     not-accessible
   STATUS     mandatory
   DESCRIPTION
     "This entry controls the addition and deletion of 
      atmIfCAUbr components."
::= { atmIfCAUbr 1 }

atmIfCAUbrRowStatusEntry OBJECT-TYPE
   SYNTAX     AtmIfCAUbrRowStatusEntry
   ACCESS     not-accessible
   STATUS     mandatory
   DESCRIPTION
     "A single entry in the table represents a single 
      atmIfCAUbr component."
   INDEX {
      atmIfIndex,
      atmIfCAIndex,
      atmIfCAUbrIndex }
::= { atmIfCAUbrRowStatusTable 1 }

AtmIfCAUbrRowStatusEntry ::= SEQUENCE {
   atmIfCAUbrRowStatus
      RowStatus,
   atmIfCAUbrComponentName
      DisplayString,
   atmIfCAUbrStorageType
      StorageType,
   atmIfCAUbrIndex
      Integer32 }

atmIfCAUbrRowStatus OBJECT-TYPE
   SYNTAX     RowStatus 
   ACCESS     read-write
   STATUS     mandatory
   DESCRIPTION
     "This variable is used as the basis for SNMP naming of
      atmIfCAUbr components.
      These components can be added."
::= { atmIfCAUbrRowStatusEntry 1 }

atmIfCAUbrComponentName OBJECT-TYPE
   SYNTAX     DisplayString 
   ACCESS     read-only
   STATUS     mandatory
   DESCRIPTION
     "This variable provides the component's string name for
      use with the ASCII Console Interface"
::= { atmIfCAUbrRowStatusEntry 2 }

atmIfCAUbrStorageType OBJECT-TYPE
   SYNTAX     StorageType 
   ACCESS     read-only
   STATUS     mandatory
   DESCRIPTION
     "This variable represents the storage type value for the
      atmIfCAUbr tables."
::= { atmIfCAUbrRowStatusEntry 4 }

atmIfCAUbrIndex OBJECT-TYPE
   SYNTAX     Integer32 (0)
   ACCESS     not-accessible
   STATUS     mandatory
   DESCRIPTION
     "This variable represents the index for the atmIfCAUbr tables."
::= { atmIfCAUbrRowStatusEntry 10 }

atmIfCAUbrProvTable OBJECT-TYPE
   SYNTAX     SEQUENCE OF AtmIfCAUbrProvEntry
   ACCESS     not-accessible
   STATUS     mandatory
   DESCRIPTION
     "This group contains provisioned attributes for the UBR service 
      category."
::= { atmIfCAUbr 100 }

atmIfCAUbrProvEntry OBJECT-TYPE
   SYNTAX     AtmIfCAUbrProvEntry
   ACCESS     not-accessible
   STATUS     mandatory
   DESCRIPTION
     "An entry in the atmIfCAUbrProvTable."
   INDEX {
      atmIfIndex,
      atmIfCAIndex,
      atmIfCAUbrIndex }
::= { atmIfCAUbrProvTable 1 }

AtmIfCAUbrProvEntry ::= SEQUENCE {
   atmIfCAUbrMaxVpcs
      Unsigned32,
   atmIfCAUbrMaxVccs
      Unsigned32,
   atmIfCAUbrMaxVpts
      Unsigned32,
   atmIfCAUbrPool
      INTEGER,
   atmIfCAUbrMinimumCellRate
      Unsigned32,
   atmIfCAUbrTxQueueLimit
      Unsigned32,
   atmIfCAUbrMinPerVcQueueLimit
      Unsigned32,
   atmIfCAUbrPerVcQueueLimitReferenceRate
      Unsigned32,
   atmIfCAUbrEmissionPriority
      Unsigned32,
   atmIfCAUbrTrafficShaping
      INTEGER,
   atmIfCAUbrShapeRecoupPolicy
      INTEGER,
   atmIfCAUbrUnshapedTransmitQueueing
      INTEGER,
   atmIfCAUbrUsageParameterControl
      INTEGER,
   atmIfCAUbrWeightPolicy
      INTEGER,
   atmIfCAUbrForceTagging
      INTEGER,
   atmIfCAUbrCdvt
      Unsigned32,
   atmIfCAUbrHoldingPriority
      INTEGER,
   atmIfCAUbrSvcMpHoldingPriority
      INTEGER }

atmIfCAUbrMaxVpcs OBJECT-TYPE
   SYNTAX     Unsigned32 (0..4096 | 16385)
   ACCESS     read-write
   STATUS     mandatory
   DESCRIPTION
     "This attribute specifies the maximum number of UBR Vpcs that can 
      be activated on this AtmIf. The value must not exceed the maxVpcs 
      attribute of the parent CA component.
      
      If this attribute is specified as sameAsCa, the maximum number of 
      Vpcs is defined by the AtmIf/n CA maxVpcs attribute. 
      
      Changes to this attribute do not affect existing Vpcs. If the value is 
      changed to a number smaller than the current number of active 
      UBR VPCs, no new UBR VPCs are admitted until the number of 
      active UBR VPCs drops below the value of this attribute. The 
      current number of active UBR VPCs is indicated by the Ubr/0 
      vpcUsage operational attribute.

      VALUES (

      16385 = sameAsCa

      )"
   DEFVAL     { 16385 }
::= { atmIfCAUbrProvEntry 5 }

atmIfCAUbrMaxVccs OBJECT-TYPE
   SYNTAX     Unsigned32 (0..16384 | 16385)
   ACCESS     read-write
   STATUS     mandatory
   DESCRIPTION
     "This attribute specifies the maximum number of UBR Vccs that can 
      be activated on this AtmIf, including UBR Vpt Vccs. The value must 
      not exceed the maxVccs attribute of the parent CA component.
      
      If this attribute is specified as sameAsCa, the maximum number of 
      Vccs is defined by the AtmIf/n CA maxVccs attribute. 
      
      Changes to this attribute do not affect existing Vccs. If the value is 
      changed to a number smaller than the current number of active 
      UBR VCCs, no new UBR VCCs are admitted until the number of 
      active UBR VCCs drops below the value of this attribute. The 
      current number of active UBR VCCs is indicated by the Ubr/0 
      vccUsage operational attribute.

      VALUES (

      16385 = sameAsCa

      )"
   DEFVAL     { 16385 }
::= { atmIfCAUbrProvEntry 6 }

atmIfCAUbrMaxVpts OBJECT-TYPE
   SYNTAX     Unsigned32 (0..4096 | 16385)
   ACCESS     read-write
   STATUS     mandatory
   DESCRIPTION
     "This attribute specifies the maximum number of UBR Vpts that can 
      be activated on this AtmIf. The value must not exceed the maxVpts 
      attribute of the parent CA component.
      
      If this attribute is specified as sameAsCa, the maximum number of 
      Vpts is defined by the AtmIf/n CA maxVpts attribute. 
      
      Changes to this attribute do not affect existing Vpts. If the value is 
      changed to a number smaller than the current number of active 
      UBR VPTs, no new UBR VPTs are admitted until the number of 
      active UBR VPTs drops below the value of this attribute. The 
      current number of active UBR VPTs is indicated by the Ubr/0 
      vptUsage operational attribute.

      VALUES (

      16385 = sameAsCa

      )"
   DEFVAL     { 16385 }
::= { atmIfCAUbrProvEntry 7 }

atmIfCAUbrPool OBJECT-TYPE
   SYNTAX     INTEGER  {
                 pool1(1),
                 pool2(2),
                 pool3(3),
                 pool4(4),
                 pool5(5) }
   ACCESS     read-write
   STATUS     mandatory
   DESCRIPTION
     "This attribute specifies the bandwidth pool which is to be used to 
      support the unspecified bit rate (UBR) service category except for 
      connections managed by a Vpt CA. The percentage of link capacity 
      reserved for the given bandwidth pool is the maximum bandwidth 
      that can be allocated to UBR traffic. The percentage allocated to 
      each bandwidth pool can be provisioned through the bandwidthPool 
      attribute under the CA.
      
      The amount of bandwidth reserved for each UBR connection is 
      specified in the minimumCellRate attribute."
   DEFVAL     { pool1 }
::= { atmIfCAUbrProvEntry 10 }

atmIfCAUbrMinimumCellRate OBJECT-TYPE
   SYNTAX     Unsigned32 (0..2147483647)
   ACCESS     read-write
   STATUS     mandatory
   DESCRIPTION
     "This attribute specifies the minimum cell rate (MCR) which is 
      allocated from the UBR bandwidth pool for each UBR connection 
      which is admitted using Connection Admission Control (CAC) 
      except for connections managed by a Vpt CA. UBR connections 
      normally are serviced on a best effort basis, but this attribute allows 
      allocation of a default minimum bandwidth for each connection."
   DEFVAL     { 0 }
::= { atmIfCAUbrProvEntry 11 }

atmIfCAUbrTxQueueLimit OBJECT-TYPE
   SYNTAX     Unsigned32 (0 | 5..63488)
   ACCESS     read-write
   STATUS     mandatory
   DESCRIPTION
     "This attribute specifies the default maximum queue length for the 
      emission queues used to buffer the traffic of the UBR service 
      category. It is used as the basis for setting the discard thresholds on 
      both common and per-VC queues. For the common queue, the 
      discard thresholds are set at approximately 35, 75 and 90 percent of 
      the value of this attribute for traffic at discard priority 3 (DP=3), 
      DP=2 and DP=1 respectively.
      
      For per-VC queue, the actual limit may be reduced depending on 
      the shaping rate of the connection (for standard Vpt Vccs, this is the 
      shaping rate of the Vpt). The discard thresholds are set at 
      approximately 35, 75 and 90 percent of the scaled queue limit for 
      traffic at discard priority 3 (DP=3), DP=2 and DP=1 respectively. 
      However, a reduction will never result in a value that is less than the 
      value set for the minPerVcQueueLimit attribute.
      
      When the value of this attribute is autoConfigure, an appropriate 
      value is selected based on the card type. It is set to 1792 for low 
      speed cards such as DS1, E1 and IMA, set to 2304 for high speed 
      CQC-based ATM cards such as JT2, DS3, E3 and OC3, and set to 
      10240 for high speed ATM IP cards such as 3pDS3Atm2, 
      3pE3Atm2, 2pOC3SmAtm2 and 2pOC3MmAtm2.
      
      On CQC-based ATM cards, this attribute must be set to the same 
      value for CA NrtVbr, Abr and Ubr components. 
      
      For ATM IP FPs, the per-VC queue limit may be overridden for a 
      permanent connection by specifying a value in the Vcd Tm or Vpd 
      Tm txQueueLimit attribute. 
      
      The operational value of the maximum length of a queue (common 
      or per-VC) is indicated by the Vcc Tm, Vpc Tm, or Vpt Tm 
      txQueueThresholds attribute.
      
      For standard Vpts, this attribute does not apply when using per-VC 
      queuing and only applies when using common queueing. When 
      using per-VC queueing, regardless of the Vpt's service category, 
      standard Vpts use the AtmIf Ca NrtVbr txQueueLimit value as their 
      default.
      
      This attribute does not apply to basic Vpts.

      VALUES (

      0 = autoConfigure

      )"
   DEFVAL     { 0 }
::= { atmIfCAUbrProvEntry 12 }

atmIfCAUbrMinPerVcQueueLimit OBJECT-TYPE
   SYNTAX     Unsigned32 (5..30000)
   ACCESS     read-write
   STATUS     mandatory
   DESCRIPTION
     "This attribute specifies the minimum queue limit for the per-VC 
      queues of connections of the UBR service category.
      
      The queue limit of a per-VC queue is obtained by scaling down the 
      txQueueLimit based on the shaping rate of that queue (shaping rate 
      for the connection, and for standard Vpt Vccs, the shaping rate of 
      the Vpt). This produces a constant delay for various queue lengths. 
      The txQueueLimit provides an upper bound while 
      minPerVcQueueLimit provides the lower bound. The value of this 
      attribute must not be greater than the value of the txQueueLimit 
      attribute. If this service category is used by Trunks the value of 
      minPerVcQueueLimit must be at least 88.
      
      On CQC-based ATM cards, this attribute must be set to the same 
      value for CA NrtVbr, Abr and Ubr components.
      
      For Vpts, this attribute does not apply. Regardless of Vpt service 
      category, standard Vpts always use the AtmIf Ca NrtVbr 
      minPerVcQueueLimit value as their default. To determine the queue 
      limit of a standard Vpt Vcc, the txQueueLimit is scaled down by the 
      Vpt shaping rate."
   DEFVAL     { 88 }
::= { atmIfCAUbrProvEntry 13 }

atmIfCAUbrPerVcQueueLimitReferenceRate OBJECT-TYPE
   SYNTAX     Unsigned32 (0 | 1..943396)
   ACCESS     read-write
   STATUS     mandatory
   DESCRIPTION
     "This attribute specifies the shaping rate to be used in computing the 
      tolerable delay for per-VC queues of connections of the UBR 
      service category. The delay is computed as the txQueueLimit 
      divided by the value of this attribute. 
      
      When the value of this attribute is autoConfigure, an appropriate 
      default is selected based on the card type. It is set to 3685 for low 
      speed cards such as DS1, E1 and IMA, set to 14740 for high speed 
      cards such as JT2, DS3, E3 and OC3, and set to 65511 for high 
      speed ATM IP cards such as 3pDS3Atm2, 3pE3Atm2, 
      2pOC3SmAtm2 and 2pOC3MmAtm2.
      
      On CQC-based ATM cards, this attribute must be set to the same 
      value for CA NrtVbr, Abr and Ubr components.
      
      For Vpts, this attribute does not apply. Regardless of Vpt service 
      category, standard Vpts always use the AtmIf Ca NrtVbr 
      perVcQueueLimitReferenceRate value as their default.

      VALUES (

      0 = autoConfigure

      )"
   DEFVAL     { 0 }
::= { atmIfCAUbrProvEntry 14 }

atmIfCAUbrEmissionPriority OBJECT-TYPE
   SYNTAX     Unsigned32 (0..7)
   ACCESS     read-write
   STATUS     mandatory
   DESCRIPTION
     "This attribute is not applicable and is ignored for CQC-based ATM 
      cards.
      
      This attribute specifies the emission priority (EP) which is used to 
      transmit traffic of the UBR service category. A lower numerical 
      value for this attribute specifies a higher emission priority. 0 is the 
      highest EP and 7 is the lowest. Cells at a higher emission priority 
      receive higher preference for link bandwidth. EPs 0 and 1 are in the 
      absolute priority range, and are unaffected by any minimum 
      bandwidth guarantees. EPs 2 through 7 are in the guaranteed 
      bandwidth range. Minimum bandwidth guarantee is specified in the 
      AtmIf/n Ep/m component. 
      
      Emission priority setting must comply with all of the following 
      constraints: 
      1. The emission priority numbers must be in the following order: 
      CBR <= rt-VBR <= nrt-VBR <= ABR <= UBR 
      2. Two different ATM service categories may share the same EP 
      only if they are both shaped. 
      3. CBR and rt-VBR may be placed either in the absolute priority 
      range (EP 0 or 1) or in the guaranteed bandwidth range (EP 2 
      through 7). 
      4. If both CBR and rt-VBR are shaped, rt-VBR must share the 
      same EP with CBR or ABR. If either one of CBR or rt-VBR are 
      not shaped, then they cannot share the same EP. 
      5. ABR service category is always deemed to be shaped. If nrt-VBR 
      is shaped, it must share the same EP with ABR. If nrt-VBR is not 
      shaped it must have a higher EP than ABR.
      6. If UBR is shaped, it must share the same EP with ABR. If UBR 
      is not shaped, it must have a lower EP than ABR.
      
      This attribute does not apply to standard Vpt Vccs and basic Vpts."
   DEFVAL     { 7 }
::= { atmIfCAUbrProvEntry 15 }

atmIfCAUbrTrafficShaping OBJECT-TYPE
   SYNTAX     INTEGER  {
                 disabled(1),
                 enabled(5),
                 inverseUpc(6) }
   ACCESS     read-write
   STATUS     mandatory
   DESCRIPTION
     "This attribute specifies the default traffic shaping option for 
      connections of the UBR service category. An override to this default 
      may be specified for a provisioned connection under the Vcd Tm or 
      Vpd Tm component.
      
      When this attribute is set to disabled, traffic shaping cannot be 
      enabled for any UBR connection.
      
      For CQC-based ATM cards, this attribute may be set to enabled 
      only if the interface supports shaping, as defined by the 
      perVcQueueInterfaces attribute in the AtmResourceControl Cqc 
      Override component. If that component does not exist, this attribute 
      must be set to disabled.
      
      If the Vcc Tm, Vpc Tm, or Vpt Tm txTrafficDescType indicates type 
      1 or 2, this attribute is ignored, and traffic shaping is not applicable 
      for that connection. 
      
      When this attribute is set to inverseUpc, traffic shaping for a 
      connection is enabled according to card type and the value of the 
      Vcc Tm, Vpc Tm, or Vpt Tm txTrafficDescType. 
      
      If this attribute is set to inverseUpc, and the txTrafficDescType is 3, 
      4, or 5, linear traffic shaping is enabled. Linear traffic shaping uses 
      a single static traffic shaping rate. 
      
      On CQC-based ATM FPs, if this attribute is set to inverseUpc, and 
      the txTrafficDescType is 6, 7, or 8, linear traffic shaping is enabled.
      
      On ATM IP FPs, if this attribute is set to inverseUpc, and the 
      txTrafficDescType is 6, 7, or 8, inverse-UPC (also referred to as 
      VBR or dual leaky bucket) traffic shaping is enabled. Inverse-UPC 
      traffic shaping can burst above the sustained cell rate to the peak 
      cell rate for the duration defined by maximum burst size. Inverse-
      UPC traffic shaping exactly conforms to the requirements of a dual 
      leaky bucket UPC enforcer. 
      
      When this attribute is set to enabled and the txTrafficDescType is 3, 
      4, 5, 6, 7, or 8, traffic shaping for a connection is enabled using 
      linear shaping. 
      
      Enabling or disabling traffic shaping may require a matching 
      change to the emissionPriority attribute and 
      unshapedTransmitQueueing attribute for this service category. 
      Refer to those attributes for the complete description of the 
      interactions.
      
      This attribute does not apply to standard Vpt Vccs and basic Vpts."
   DEFVAL     { disabled }
::= { atmIfCAUbrProvEntry 19 }

atmIfCAUbrShapeRecoupPolicy OBJECT-TYPE
   SYNTAX     INTEGER  {
                 minimumCdv(0),
                 maximumEfficiency(1) }
   ACCESS     read-write
   STATUS     mandatory
   DESCRIPTION
     "This attribute specifies the shaping recoup policy for the UBR 
      service category. This is the policy which is used to recoup shaping 
      opportunities which are lost when more than one connection 
      schedules a cell for the same transmit opportunity. In this case, one 
      connection is scheduled, and the cell from the other connection is 
      delayed by one cell time. This attribute affects how the transmit 
      time is calculated for the next cell on the delayed connection. This 
      attribute is ignored if this service category is not shaped.
      
      When the connection which was delayed schedules the next cell to 
      transmit, it may calculate the time as a difference from either the 
      previous actual cell transmit time, or the time when the previous 
      cell should have been transmitted.
      
      Setting this attribute to maximumEfficiency results in each 
      connection trying to recoup or regain any delays in scheduling. The 
      transmit time from the next cell is calculated from the time when 
      the cell should originally have been sent. Cell delay variation 
      (CDV) occurs in this case since the cells are sent with less than the 
      shaping delay between them. However, in general the shaper 
      recovers (recoups) lost opportunities and improves efficiency.
      
      Setting this attribute to minimumCdv results in connections not 
      trying to recoup or regain any delays in scheduling. The transmit 
      time for the next cell is calculated from the time when the previous 
      cell was actually transmitted. This minimizes CDV, but results in 
      missed cell opportunities.
      
      This attribute does not apply to standard Vpt Vccs and basic Vpts."
   DEFVAL     { maximumEfficiency }
::= { atmIfCAUbrProvEntry 20 }

atmIfCAUbrUnshapedTransmitQueueing OBJECT-TYPE
   SYNTAX     INTEGER  {
                 perVc(0),
                 common(1),
                 autoConfigure(2) }
   ACCESS     read-write
   STATUS     mandatory
   DESCRIPTION
     "This attribute specifies the default queuing option for unshaped 
      connections of the UBR service category. This attribute controls 
      whether common or per-VC queueing is used. 
      
      Per-VC queueing means that each connection has its own buffering 
      and queue limits.
      
      Common queueing means that cells are queued in First In First Out 
      order on a common queue. The common queue has one set of 
      congestion control levels for all cells enqueued on it. For ATM IP 
      cards, there is one common queue for the UBR service category. 
      For CQC-based ATM cards, there is one common queue which is 
      shared by the nrt-VBR, ABR and UBR service categories.
      
      For ATM IP cards, if traffic shaping for this service category is 
      disabled, this attribute may take any of the three values. In this case, 
      the value autoConfigure is interpreted to mean per-VC queueing.
      
      For ATM IP cards, if traffic shaping for this service category is not 
      disabled, the only permitted values are perVc and autoConfigure. 
      In this case, the result is that all connections use per-VC queueing.
      
      For CQC-based ATM cards, if the perVcQueueInterfaces attribute 
      of the Lp Eng Arc Cqc component permits shaping for this 
      interface, then this attribute may take any of the three values. In this 
      case, the value autoConfigure is interpreted to mean per-VC 
      queueing.
      
      For CQC-based ATM cards, if the perVcQueueInterfaces attribute 
      of the Lp Eng Arc Cqc component does not permit shaping for this 
      interface, then this attribute may take the values common or 
      autoConfigure. In this case, the value autoConfigure is interpreted 
      to mean common queueing.
      
      If this attribute is set to autoConfigure, an override to this default 
      may be specified for a provisioned connection under the Vcd Tm or 
      Vpd Tm component. 
      
      The opUnshapedTransmitQueueing attribute of this component 
      indicates whether the transmit queueing is perVc or common.
      
      This attribute does not apply to standard Vpt Vccs and basic Vpts."
   DEFVAL     { autoConfigure }
::= { atmIfCAUbrProvEntry 21 }

atmIfCAUbrUsageParameterControl OBJECT-TYPE
   SYNTAX     INTEGER  {
                 enforced(0),
                 disabled(1),
                 monitored(4) }
   ACCESS     read-write
   STATUS     mandatory
   DESCRIPTION
     "This attribute specifies the default usage parameter control (UPC) 
      option for connections of the UBR service category. This attribute is 
      ignored if the rxTrafficDescriptorType indicates 1 or 2. An override 
      to this default may be specified for a provisioned connection under 
      the Vcd Tm or Vpd Tm component.
      
      When this attribute is set to enforced, UPC is enforced for each 
      connection. When UPC is enforced, non-conforming cells are either 
      tagged or discarded depending on the rxTrafficDescriptorType. 
      
      On ATM IP FPs, when this attribute is set to monitored, UPC 
      conformance checking is performed, except, instead of the non-
      conforming cells being tagged or discarded, they are merely 
      counted in the UPC violations counts, and passed on unchanged. 
      
      On CQC-based ATM FPs, when this attribute is set to monitored, it 
      has the same effect as setting it to disabled. 
      
      When this attribute is set to disabled, UPC is disabled on the receive 
      path for all UBR connections.
      
      This attribute does not apply to standard Vpt Vccs and basic Vpts."
   DEFVAL     { disabled }
::= { atmIfCAUbrProvEntry 22 }

atmIfCAUbrWeightPolicy OBJECT-TYPE
   SYNTAX     INTEGER  {
                 mcr(0),
                 pcr(2),
                 ecr(3) }
   ACCESS     read-write
   STATUS     mandatory
   DESCRIPTION
     "This attribute specifies the policy which is applied when calculating 
      the fairness weight for unshaped connections of the UBR service 
      category. The fairness weight for a connection determines the 
      relative amount of bandwidth which that connection obtains, 
      compared to other connections in the same service category. 
      Connections with equal weight get equal transmit opportunities. 
      Connections with higher weights get more transmit opportunities 
      compared with connections that have lower weights. An override to 
      this default may be specified for a provisioned connection under the 
      Vcd Tm or Vpd Tm component. 
      
      The fairness weight for a connection is directly proportional to the 
      value of one of the traffic descriptor parameters for that connection. 
      This attribute specifies which traffic descriptor parameter is used for 
      connections of the UBR service category. 
      
      This attribute is ignored on CQC-based ATM cards. This attribute is 
      also ignored on ATM IP cards if unshapedTransmitQueueing is set 
      for common queuing. 
      
      If this attribute is set to mcr, the fairness weight is proportional to 
      the default minimum cell rate (MCR) for UBR connections. If the 
      default minimum cell rate is 0, all UBR connections get a minimum 
      weight, which is 1. 
      
      If this attribute is set to pcr, the fairness weight is proportional to 
      the transmit peak cell rate (PCR) of a connection. Connections with 
      a higher PCR have a higher fairness weight. Connections with 
      txTrafficDescType 1 or 2 get a minimum weight, which is 1. 
      
      If this attribute is set to ecr, the fairness weight is proportional to 
      the equivalent cell rate (ECR) of a connection as calculated by 
      connection admission control (CAC). Connections with a higher 
      ECR have a higher fairness weight. Connections with an ECR of 0 
      get a minimum weight, which is 1. 
      
      The weight of a connection is visible in the Vcc Tm, Vpc Tm, or Vpt 
      Tm weight attribute.
      
      This attribute does not apply to standard Vpt Vccs and basic Vpts."
   DEFVAL     { pcr }
::= { atmIfCAUbrProvEntry 23 }

atmIfCAUbrForceTagging OBJECT-TYPE
   SYNTAX     INTEGER  {
                 enabled(0),
                 disabled(1) }
   ACCESS     read-write
   STATUS     mandatory
   DESCRIPTION
     "This attribute specifies the default of whether to force tagging 
      (CLP=1) of all cells for all UBR connections. An override to this 
      default may be specified for a provisioned connection under the Vcd 
      Tm or Vpd Tm component. 
      
      When this attribute is set to enabled, CLP is set to 1 for all cells in 
      the transmit direction. This is in conformance with the ATM Forum 
      TM4.0 UBR.2 service definition. Force tagging is only supported 
      on ATM IP FPs. 
      
      On CQC-based ATM FPs, this attribute must be set to disabled. 
      When this attribute is set to disabled, CLP is unchanged for all cells 
      in the transmit direction. This is in conformance with the ATM 
      Forum TM4.0 UBR.1 service definition. 
      
      This attribute never applies to any type of Vpt."
   DEFVAL     { disabled }
::= { atmIfCAUbrProvEntry 24 }

atmIfCAUbrCdvt OBJECT-TYPE
   SYNTAX     Unsigned32 (1..1200000)
   ACCESS     read-write
   STATUS     mandatory
   DESCRIPTION
     "This attribute specifies the default cell delay variation tolerance 
      (CDVT) for all connections of the UBR service category. An 
      override to this default may be specified for a provisioned 
      connection under the Vcd Tm or Vpd Tm component.
      
      If Usage Parameter Control (UPC) is enabled for a connection, 
      CDVT is used by the UPC function to decide whether a cell is 
      conforming or non-conforming based on the connection's traffic 
      descriptor type. The larger the CDVT value, the more tolerant is the 
      UPC of bandwidth usage beyond the traffic contract."
   DEFVAL     { 250 }
::= { atmIfCAUbrProvEntry 30 }

atmIfCAUbrHoldingPriority OBJECT-TYPE
   SYNTAX     INTEGER  {
                 n0(0),
                 n1(1),
                 n2(2),
                 n3(3),
                 n4(4) }
   ACCESS     read-write
   STATUS     mandatory
   DESCRIPTION
     "This attribute specifies the default holding priority which applies to 
      SVP and SVC UBR connections. It takes a value from 0 (highest 
      priority) to 4 (lowest priority). In a situation where the link 
      bandwidth fluctuates, such as over an IMA link, holding priority is 
      used to determine which connections are held and which are 
      released. Holding priority 4 connections are the first to be released. 
      Holding priority 0 connections are the last to be released.
      
      This attribute does not apply to Vpt Vccs. When bandwidth 
      fluctuates, the entire Vpt, along with all Vpt Vccs is released as a 
      unit, according to the Vpt's holdingPriority."
   DEFVAL     { n3 }
::= { atmIfCAUbrProvEntry 40 }

atmIfCAUbrSvcMpHoldingPriority OBJECT-TYPE
   SYNTAX     INTEGER  {
                 n0(0),
                 n1(1),
                 n2(2),
                 n3(3),
                 n4(4) }
   ACCESS     read-write
   STATUS     mandatory
   DESCRIPTION
     "This attribute specifies the default holding priority which applies to 
      SVC UBR point-to-multipoint connections. It takes a value from 0 
      (highest priority) to 4 (lowest priority). In a situation where the link 
      bandwidth fluctuates, such as over an IMA link, holding priority is 
      used to determine which connections are held and which are 
      released. Holding priority 4 connections are the first to be released. 
      Holding priority 0 connections are the last to be released.
      
      This attribute does not apply to Vpt Vccs. When bandwidth 
      fluctuates, the entire Vpt, along with all Vpt Vccs is released as a 
      unit, according to the Vpt's holdingPriority."
   DEFVAL     { n3 }
::= { atmIfCAUbrProvEntry 50 }

atmIfCAUbrOperTable OBJECT-TYPE
   SYNTAX     SEQUENCE OF AtmIfCAUbrOperEntry
   ACCESS     not-accessible
   STATUS     mandatory
   DESCRIPTION
     "This group contains operational attributes for the UBR service 
      category."
::= { atmIfCAUbr 110 }

atmIfCAUbrOperEntry OBJECT-TYPE
   SYNTAX     AtmIfCAUbrOperEntry
   ACCESS     not-accessible
   STATUS     mandatory
   DESCRIPTION
     "An entry in the atmIfCAUbrOperTable."
   INDEX {
      atmIfIndex,
      atmIfCAIndex,
      atmIfCAUbrIndex }
::= { atmIfCAUbrOperTable 1 }

AtmIfCAUbrOperEntry ::= SEQUENCE {
   atmIfCAUbrOpUnshapedTransmitQueueing
      INTEGER,
   atmIfCAUbrVpcUsage
      Unsigned32,
   atmIfCAUbrVccUsage
      Unsigned32,
   atmIfCAUbrVptUsage
      Unsigned32,
   atmIfCAUbrEpdOffset
      Unsigned32 }

atmIfCAUbrOpUnshapedTransmitQueueing OBJECT-TYPE
   SYNTAX     INTEGER  {
                 perVc(0),
                 common(1) }
   ACCESS     read-only
   STATUS     mandatory
   DESCRIPTION
     "This attribute indicates the state of transmit queueing for unshaped 
      UBR connections.
      
      A value of perVc indicates that any unshaped connections use per-
      VC queueing. A value of common indicates that traffic for 
      unshaped connections uses the common queue which corresponds 
      to the EP for this service category."
::= { atmIfCAUbrOperEntry 10 }

atmIfCAUbrVpcUsage OBJECT-TYPE
   SYNTAX     Unsigned32 (0..4096)
   ACCESS     read-only
   STATUS     mandatory
   DESCRIPTION
     "This attribute indicates the number of active UBR Vpcs under this 
      interface. It includes switched and permanent connections."
::= { atmIfCAUbrOperEntry 11 }

atmIfCAUbrVccUsage OBJECT-TYPE
   SYNTAX     Unsigned32 (0..16384)
   ACCESS     read-only
   STATUS     mandatory
   DESCRIPTION
     "This attribute indicates the number of active UBR Vccs under this 
      interface. It includes switched and permanent connections, and Vpt 
      Vccs."
::= { atmIfCAUbrOperEntry 12 }

atmIfCAUbrVptUsage OBJECT-TYPE
   SYNTAX     Unsigned32 (0..4096)
   ACCESS     read-only
   STATUS     mandatory
   DESCRIPTION
     "This attribute indicates the number of active UBR Vpts under this 
      interface."
::= { atmIfCAUbrOperEntry 13 }

atmIfCAUbrEpdOffset OBJECT-TYPE
   SYNTAX     Unsigned32 (0 | 5..1024)
   ACCESS     read-only
   STATUS     mandatory
   DESCRIPTION
     "This attribute indicates the Early Packet Discard (EPD) offset which 
      is currently in use for this service category. The EPD offset is used 
      to derive the EPD thresholds for each CC level.
      
      Any connection under this service category which requires the 
      txPacketWiseDiscard feature must specify a transmit queue limit 
      which is at least 5.71 times this offset. This ensures that the derived 
      Epd threshold will never be less than 17.5 % of the transmit queue 
      limit. If this is not done, txPacketWiseDiscard for the connection 
      will be automatically disabled.
      
      The value of this EPD offset is specified under the lp/x eng arc aqm 
      ov component."
::= { atmIfCAUbrOperEntry 14 }


-- AtmIf/n VirtualPathConnection/vpi
-- This component represents a virtual path connection (VPC). The 
-- instance value defines the VPI value for this connectionfor 
-- example, Vpc/120 defines a path with a VPI of 120.
-- 
-- A VPC is always a relay point. and as such can only have a either a 
-- NRP or a Loop subcomponent.

atmIfVpc OBJECT IDENTIFIER ::= { atmIf 4 }



atmIfVpcRowStatusTable OBJECT-TYPE
   SYNTAX     SEQUENCE OF AtmIfVpcRowStatusEntry
   ACCESS     not-accessible
   STATUS     mandatory
   DESCRIPTION
     "This entry controls the addition and deletion of 
      atmIfVpc components."
::= { atmIfVpc 1 }

atmIfVpcRowStatusEntry OBJECT-TYPE
   SYNTAX     AtmIfVpcRowStatusEntry
   ACCESS     not-accessible
   STATUS     mandatory
   DESCRIPTION
     "A single entry in the table represents a single 
      atmIfVpc component."
   INDEX {
      atmIfIndex,
      atmIfVpcIndex }
::= { atmIfVpcRowStatusTable 1 }

AtmIfVpcRowStatusEntry ::= SEQUENCE {
   atmIfVpcRowStatus
      RowStatus,
   atmIfVpcComponentName
      DisplayString,
   atmIfVpcStorageType
      StorageType,
   atmIfVpcIndex
      Integer32 }

atmIfVpcRowStatus OBJECT-TYPE
   SYNTAX     RowStatus 
   ACCESS     read-write
   STATUS     mandatory
   DESCRIPTION
     "This variable is used as the basis for SNMP naming of
      atmIfVpc components.
      These components can be added and deleted."
::= { atmIfVpcRowStatusEntry 1 }

atmIfVpcComponentName OBJECT-TYPE
   SYNTAX     DisplayString 
   ACCESS     read-only
   STATUS     mandatory
   DESCRIPTION
     "This variable provides the component's string name for
      use with the ASCII Console Interface"
::= { atmIfVpcRowStatusEntry 2 }

atmIfVpcStorageType OBJECT-TYPE
   SYNTAX     StorageType 
   ACCESS     read-only
   STATUS     mandatory
   DESCRIPTION
     "This variable represents the storage type value for the
      atmIfVpc tables."
::= { atmIfVpcRowStatusEntry 4 }

atmIfVpcIndex OBJECT-TYPE
   SYNTAX     Integer32 (0..4095)
   ACCESS     not-accessible
   STATUS     mandatory
   DESCRIPTION
     "This variable represents the index for the atmIfVpc tables."
::= { atmIfVpcRowStatusEntry 10 }

atmIfVpcStateTable OBJECT-TYPE
   SYNTAX     SEQUENCE OF AtmIfVpcStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { atmIfVpc 100 }

atmIfVpcStateEntry OBJECT-TYPE
   SYNTAX     AtmIfVpcStateEntry
   ACCESS     not-accessible
   STATUS     mandatory
   DESCRIPTION
     "An entry in the atmIfVpcStateTable."
   INDEX {
      atmIfIndex,
      atmIfVpcIndex }
::= { atmIfVpcStateTable 1 }

AtmIfVpcStateEntry ::= SEQUENCE {
   atmIfVpcAdminState
      INTEGER,
   atmIfVpcOperationalState
      INTEGER,
   atmIfVpcUsageState
      INTEGER }

atmIfVpcAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { atmIfVpcStateEntry 1 }

atmIfVpcOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { atmIfVpcStateEntry 2 }

atmIfVpcUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { atmIfVpcStateEntry 3 }

atmIfVpcOperTable OBJECT-TYPE
   SYNTAX     SEQUENCE OF AtmIfVpcOperEntry
   ACCESS     not-accessible
   STATUS     mandatory
   DESCRIPTION
     "This group contains operational information for a Vcc, Vpc, or Vpt 
      component."
::= { atmIfVpc 110 }

atmIfVpcOperEntry OBJECT-TYPE
   SYNTAX     AtmIfVpcOperEntry
   ACCESS     not-accessible
   STATUS     mandatory
   DESCRIPTION
     "An entry in the atmIfVpcOperTable."
   INDEX {
      atmIfIndex,
      atmIfVpcIndex }
::= { atmIfVpcOperTable 1 }

AtmIfVpcOperEntry ::= SEQUENCE {
   atmIfVpcConnectionPointType
      INTEGER }

atmIfVpcConnectionPointType OBJECT-TYPE
   SYNTAX     INTEGER  {
                 connectionEndPoint(0),
                 segmentEndPoint(1),
                 connectingPoint(2),
                 unknown(3) }
   ACCESS     read-only
   STATUS     mandatory
   DESCRIPTION
     "This attribute reflects the role of the connection component at this 
      interface.
      
      A value of connectionEndPoint indicates that user cells, end-to-end 
      OAM cells, and segment OAM cells are processed by the 
      connection component.
      
      A value of segmentEndPoint indicates that user cells and end-to-
      end OAM cells are relayed by the connection component, while 
      segment OAM cells are processed by the connection component.
      
      A value of connectingPoint indicates that user cells, end-to-end 
      OAM cells, and segment OAM cells are relayed by the connection 
      component.
      
      A value of unknown indicates that the connection component is 
      inactive."
::= { atmIfVpcOperEntry 10 }

atmIfVpcStatusTable OBJECT-TYPE
   SYNTAX     SEQUENCE OF AtmIfVpcStatusEntry
   ACCESS     not-accessible
   STATUS     mandatory
   DESCRIPTION
     "This group contains operational status information for a Vcc, Vpc, 
      or Vpt component."
::= { atmIfVpc 120 }

atmIfVpcStatusEntry OBJECT-TYPE
   SYNTAX     AtmIfVpcStatusEntry
   ACCESS     not-accessible
   STATUS     mandatory
   DESCRIPTION
     "An entry in the atmIfVpcStatusTable."
   INDEX {
      atmIfIndex,
      atmIfVpcIndex }
::= { atmIfVpcStatusTable 1 }

AtmIfVpcStatusEntry ::= SEQUENCE {
   atmIfVpcOperStatus
      INTEGER,
   atmIfVpcLocalFailureCause
      INTEGER,
   atmIfVpcTroubled
      INTEGER,
   atmIfVpcSegLinkSideLoopbackState
      INTEGER,
   atmIfVpcSegSwitchSideLoopbackState
      INTEGER,
   atmIfVpcEndToEndLoopbackState
      INTEGER,
   atmIfVpcRxOamCellCongestionState
      INTEGER,
   atmIfVpcAisState
      INTEGER,
   atmIfVpcRdiState
      INTEGER }

atmIfVpcOperStatus OBJECT-TYPE
   SYNTAX     INTEGER  {
                 unknown(0),
                 end2endUp(1),
                 end2endDown(2),
                 localUpEnd2endUnknown(3),
                 localDown(4) }
   ACCESS     read-only
   STATUS     mandatory
   DESCRIPTION
     "This attribute indicates the present operational status of the Vcc, 
      Vpc, or Vpt component. Its value is dependent upon the current state 
      of the segLinkSideLoopbackState and endToEndLoopbackState 
      attributes.
      
      The value is end2endUp when the endToEndLoopbackState is good 
      and the segLinkSideLoopbackState is either good or unknown.
      
      The value is end2endDown when the endToEndLoopbackState is 
      bad and the segLinkSideLoopbackState is either good or unknown.
      
      The value is localUpEnd2endUnknown when the 
      endToEndLoopbackState is unknown and the 
      segLinkSideLoopbackState is good.
      
      The value is localDown when segLinkSideLoopbackState is bad.
      
      The value is localUpEnd2endUnknown when the 
      endToEndLoopbackState is notApplicable and the 
      segLinkSideLoopbackState is good.
      
      The value is unknown when the endToEndLoopbackState is either 
      unknown or notApplicable and the segLinkSideLoopbackState is 
      unknown."
::= { atmIfVpcStatusEntry 20 }

atmIfVpcLocalFailureCause OBJECT-TYPE
   SYNTAX     INTEGER  {
                 noFailure(0),
                 localBwLoss(1),
                 portDown(2),
                 notAdmitted(3),
                 appNotRegistered(4),
                 disabledByApp(5),
                 bwReduced(6),
                 vpDown(7) }
   ACCESS     read-only
   STATUS     mandatory
   DESCRIPTION
     "This attribute indicates the failure cause of the Vcc, Vpc, or Vpt 
      component. noFailure indicates that there is currently no 
      bandwidth related failure for this connection. 
      
      portDown indicates that the interface corresponding to the parent 
      AtmIf is down. 
      
      localBwLoss indicates that the Ima corresponding to this AtmIf has 
      lost some, but not all bandwidth, and as a result, this connection has 
      been released.
      
      notAdmitted indicates that this connection has failed to be admitted 
      by the Connection Admission Control (CAC) algorithm.
      
      appNotRegistered indicates that there is no application registered to 
      use this connection. This may be the case, for example when there 
      is a Vcc Test application, but the test has not been started. Check the 
      status of the application to determine why it is not functional.
      
      disabledByApp indicates that the application using this connection 
      has requested that the connection be disabled. An example is a 
      connection used by a trunk application where the trunk has timed 
      out on an attempt to stage. Check the application to determine why 
      it is not fully functional.
      
      bwReduced indicates that this connection is operating in a reduced 
      bandwidth state. It is a bandwidth elastic connection which 
      currently has been allocated less than the requested (equivalent) 
      bandwidth.
      
      vpDown indicates that this connection has been notified of a fault 
      detected at the associated VP-layer. vpDown is applicable for Vpt 
      Vccs only."
::= { atmIfVpcStatusEntry 25 }

atmIfVpcTroubled OBJECT-TYPE
   SYNTAX     INTEGER  {
                 no(0),
                 yes(1) }
   ACCESS     read-only
   STATUS     mandatory
   DESCRIPTION
     "This attribute indicates whether or not the connection is in a 
      troubled state. Connections become troubled because of OAM 
      failures; when one of the attributes segLinkSideLoopbackState, 
      segSwitchSideLoopbackState, endToEndLoopbackState, aisState 
      (when receiving AIS cells only) or rdiState go bad, this attribute is 
      set to yes; otherwise it is set to no."
   DEFVAL     { no }
::= { atmIfVpcStatusEntry 28 }

atmIfVpcSegLinkSideLoopbackState OBJECT-TYPE
   SYNTAX     INTEGER  {
                 good(0),
                 bad(1),
                 unknown(2),
                 notApplicable(3) }
   ACCESS     read-only
   STATUS     mandatory
   DESCRIPTION
     "This attribute contains the current state of the link-side segment 
      loopback for this connection. Link-side segment loopback cells are 
      transmitted (inserted) by a connection component in the direction of 
      the link (port). The value of this attribute is dependent upon the 
      current setting of the segLinkSideLoopback provisionable attribute, 
      the connection point type as specified by the connectionPointType 
      attribute, and the current loopback state (if applicable).
      
      The value is notApplicable when the connectionPointType is a 
      connectingPoint. 
      
      The value is notApplicable when the distributionType is 
      pointToMultipoint.
      
      The value is good when the segLinkSideLoopback is on, the 
      connectionPointType is a segmentEndPoint or a 
      connectionEndPoint, and the segment link side loopback is 
      working.
      
      The value is bad when the segLinkSideLoopback is on, the 
      connectionPointType is a segmentEndPoint or a 
      connectionEndPoint, and the link side segment loopback is not 
      working.
      
      The value is unknown when the segLinkSideLoopback is off.
      
      The value is unknown when the segLinkSideLoopback is on, the 
      connectionPointType is a segmentEndPoint and the segment switch 
      side loopback has not yet been determined.
      
      The state of this attribute determines, in part, the value of the 
      operStatus attribute."
::= { atmIfVpcStatusEntry 30 }

atmIfVpcSegSwitchSideLoopbackState OBJECT-TYPE
   SYNTAX     INTEGER  {
                 good(0),
                 bad(1),
                 unknown(2),
                 notApplicable(3) }
   ACCESS     read-only
   STATUS     mandatory
   DESCRIPTION
     "This attribute contains the current state of the switch-side segment 
      loopback for this connection. Switch-side segment loopback cells 
      are transmitted (inserted) by a connection component in the 
      direction of the bus. The value of this attribute is dependent upon 
      the current setting of the segSwitchSideLoopback provisionable 
      attribute, the connection point type as specified by the 
      connectionPointType attribute, and the current loopback state (if 
      applicable).
      
      The value is only applicable when the connectionPointType is a 
      segmentEndPoint. 
      
      The value is notApplicable when the connectionPointType is a 
      connectingPoint or connectionEndPoint. 
      
      The value is notApplicable when the distributionType is 
      pointToMultipoint.
      
      The value is good when the segSwitchSideLoopback is on, the 
      connectionPointType is a segmentEndPoint and the segment switch 
      side loopback is working.
      
      The value is bad when the segSwitchSideLoopback is on, the 
      connectionPointType is a segmentEndPoint and the switch side 
      segment loopback is not working.
      
      The value is unknown when the segSwitchSideLoopback is off.
      
      The value is unknown when the segSwitchSideLoopback is on, the 
      connectionPointType is a segmentEndPoint and the segment switch 
      side loopback has not been determined."
::= { atmIfVpcStatusEntry 40 }

atmIfVpcEndToEndLoopbackState OBJECT-TYPE
   SYNTAX     INTEGER  {
                 good(0),
                 bad(1),
                 unknown(2),
                 notApplicable(3) }
   ACCESS     read-only
   STATUS     mandatory
   DESCRIPTION
     "This attribute contains the current state of the end-to-end loopback 
      for this connection. Its value is dependent upon the current setting 
      of the endToEndLoopback provisionable attribute and the 
      connection point type as specified by the connectionPointType 
      attribute.
      
      The value is only applicable when the connectionPointType is a 
      connectionEndPoint. 
      
      The value is notApplicable when the connectionPointType is a 
      connectingPoint or segmentEndPoint. 
      
      The value is notApplicable when the distributionType is a 
      pointToMultipoint.
      
      The value is good when the endToEndLoopback is on, the 
      connectionPointType is a connectionEndPoint and the end-to-end 
      loopback is working.
      
      The value is bad when the endToEndLoopback is on, the 
      connectionPointType is a connectionEndPoint and the end-to-end 
      loopback is not working.
      
      The value is unknown when the endToEndLoopback is off.
      
      The value is unknown when the endToEndLoopback is on, the 
      connectionPointType is a connectionEndPoint and the end-to-end 
      loopback status has not been determined.
      
      The state of this attribute determines, in part, the value of the 
      operStatus attribute."
::= { atmIfVpcStatusEntry 50 }

atmIfVpcRxOamCellCongestionState OBJECT-TYPE
   SYNTAX     INTEGER  {
                 good(0),
                 bad(1),
                 unknown(2),
                 notApplicable(3) }
   ACCESS     read-only
   STATUS     mandatory
   DESCRIPTION
     "This attribute contains the current state of the receive side OAM cell 
      congestion for this connection. Its value reflects whether the rate of 
      received OAM cells for this connection is below a specified 
      threshold. The connection maintains a count of the number of OAM 
      cells which are terminated per second. Once that count exceeds the 
      specified threshold, extraction of all OAM cells for this connection 
      is disabled for a period of one minute. This is a congestion 
      management mechanism to prevent the processor from being 
      overloaded with handling OAM cells for a particular connection. 
      This mechanism ensures that tasks, such as trunks obtain enough 
      processor cycles to remain in service, and are not adversely affected 
      by excessive rate of OAM cells on a particular connection.
      
      The value is good when the rate of received OAM cells is less than 
      the allowed threshold.
      
      The value is bad when the arrival rate has exceeded the allowed 
      threshold. It remains bad for one minute, before returning to good 
      again. During this timeout, extraction of all OAM cells is disabled 
      for this connection. As a result, other loopback failure conditions 
      may occur.
      
      The value is unknown when the application has not yet begun to 
      use this connection. An example is the Test component before a test 
      has been started.
      
      Each type of OAM cell is counted separately. The threshold for AIS 
      cells is three cells per second. If more than three AIS cells are 
      received within a one second interval, this attribute is set to bad. 
      The threshold for RDI cells and each loopback type is also three, 
      but the threshold for trace cells is 250 per second.
      
      The state of this attribute has no direct effect on the value of the 
      operStatus attribute or on the number of troubled connections."
::= { atmIfVpcStatusEntry 55 }

atmIfVpcAisState OBJECT-TYPE
   SYNTAX     INTEGER  {
                 good(0),
                 bad(1),
                 unknown(2),
                 notApplicable(3) }
   ACCESS     read-only
   STATUS     mandatory
   DESCRIPTION
     "This attribute contains the current state of the Alarm Indication 
      Signal for this connection.
      
      A value of good indicates that the connection's application is active 
      and no alarm has occurred.
      
      A value of bad indicates that the connection's application is active 
      and an alarm has occurred.
      
      A value of unknown indicates that the connection's application is 
      inactive.
      
      A value of notApplicable occurs when the connectionPointType is 
      either a segmentEndPoint or a connectingPoint."
::= { atmIfVpcStatusEntry 60 }

atmIfVpcRdiState OBJECT-TYPE
   SYNTAX     INTEGER  {
                 good(0),
                 bad(1),
                 unknown(2),
                 notApplicable(3) }
   ACCESS     read-only
   STATUS     mandatory
   DESCRIPTION
     "This attribute indicates the current state of the Remote Defect 
      Indication for this connection.
      
      A value of good indicates that the connection's application is active 
      and no alarm has occurred.
      
      A value of bad indicates that the connection's application is active 
      and an alarm has occurred.
      
      A value of unknown indicates that the connection's application is 
      inactive.
      
      A value of notApplicable occurs when the connectionPointType is 
      either a segmentEndPoint or a connectingPoint."
::= { atmIfVpcStatusEntry 70 }

atmIfVpcTrafficTable OBJECT-TYPE
   SYNTAX     SEQUENCE OF AtmIfVpcTrafficEntry
   ACCESS     not-accessible
   STATUS     mandatory
   DESCRIPTION
     "This group is HISTORICAL. Please refer to the group AtmTmOper;
      
      This attribute group contains attributes for the Vcc and Vpc 
      components to reflect operational traffic attributes."
::= { atmIfVpc 130 }

atmIfVpcTrafficEntry OBJECT-TYPE
   SYNTAX     AtmIfVpcTrafficEntry
   ACCESS     not-accessible
   STATUS     mandatory
   DESCRIPTION
     "An entry in the atmIfVpcTrafficTable."
   INDEX {
      atmIfIndex,
      atmIfVpcIndex }
::= { atmIfVpcTrafficTable 1 }

AtmIfVpcTrafficEntry ::= SEQUENCE {
   atmIfVpcTxTrafficDescType
      INTEGER,
   atmIfVpcTxQosClass
      INTEGER,
   atmIfVpcFwdQosClass
      INTEGER,
   atmIfVpcTxQueueLength
      INTEGER,
   atmIfVpcTxQueueCongestionState
      INTEGER,
   atmIfVpcHoldingPriority
      INTEGER,
   atmIfVpcRxTrafficDescType
      INTEGER,
   atmIfVpcRxQosClass
      INTEGER,
   atmIfVpcBwdQosClass
      INTEGER,
   atmIfVpcAtmServiceCategory
      INTEGER,
   atmIfVpcTrafficShaping
      INTEGER,
   atmIfVpcBearerClassBbc
      INTEGER,
   atmIfVpcTransferCapabilityBbc
      INTEGER,
   atmIfVpcClippingBbc
      INTEGER,
   atmIfVpcUnshapedTransmitQueueing
      INTEGER,
   atmIfVpcBestEffort
      INTEGER,
   atmIfVpcUsageParameterControl
      INTEGER,
   atmIfVpcTxFrameDiscard
      OCTET STRING,
   atmIfVpcRxFrameDiscard
      OCTET STRING,
   atmIfVpcBandwidthElastic
      INTEGER,
   atmIfVpcBandwidthReduction
      INTEGER }

atmIfVpcTxTrafficDescType OBJECT-TYPE
   SYNTAX     INTEGER  {
                 n1(1),
                 n2(2),
                 n3(3),
                 n4(4),
                 n5(5),
                 n6(6),
                 n7(7),
                 n8(8) }
   ACCESS     read-only
   STATUS     obsolete
   DESCRIPTION
     "This attribute is HISTORICAL. Please refer to the attribute of the 
      same name in the group AtmTmOper.
      
      This attribute indicates the type of traffic management which is 
      applied to the transmit direction of this connection as defined in the 
      ATM Forum. The txTrafficDescType determines the number and 
      meaning of the parameters in the txTrafficDescParm attribute."
::= { atmIfVpcTrafficEntry 10 }

atmIfVpcTxQosClass OBJECT-TYPE
   SYNTAX     INTEGER  {
                 unspecified(0),
                 constantBitRate(1),
                 variableBitRate(2),
                 connectionOriented(3),
                 connectionless(4) }
   ACCESS     read-only
   STATUS     obsolete
   DESCRIPTION
     "This attribute indicates the quality of service for the transmit 
      direction for this connection.
      
      The constantBitRate class refers to traffic offered on services such 
      as a constant bit rate video service. This traffic is highest priority.
      
      The variableBitRate class refers to traffic offered on services such 
      as packetized audio and video.
      
      The connectionOriented class refers to connection-oriented traffic 
      such as Frame Relay or X.25 traffic. 
      
      The connectionless traffic refers to traffic offered through 
      connectionless trunks such as certain LAN protocols.
      
      The unspecified class supports a 'best effort' type of service, where 
      there is a minimum guarantee of bandwidth. This traffic is lowest 
      priority.
      
      This attribute is obsolete, replaced by the UNI 4.0 attribute 
      atmServiceCategory."
::= { atmIfVpcTrafficEntry 30 }

atmIfVpcFwdQosClass OBJECT-TYPE
   SYNTAX     INTEGER  {
                 n0(0),
                 n1(1),
                 n2(2),
                 n3(3),
                 n4(4),
                 notApplicable(14) }
   ACCESS     read-only
   STATUS     obsolete
   DESCRIPTION
     "This attribute is HISTORICAL. Please refer to the attribute of the 
      same name in the group AtmTmOper.
      
      This attribute indicates the quality of service for the calling to called 
      direction for this connection. This is only applicable to Soft PVC 
      and SVC connections. 
      
      Class 1 supports a QOS that meets Service Class A performance 
      requirements (Circuit emulation, constant bit rate video).
      
      Class 2 supports a QOS that meets Service Class B performance 
      requirements (Variable bit rate audio and video).
      
      Class 3 supports a QOS that meets Service Class C performance 
      requirements (Connection-Oriented Data Transfer).
      
      Class 4 supports a QOS that meets Service Class D performance 
      requirements (Connectionless Data Transfer).
      
      Class 0 is the unspecified QOS class; no objective is specified for 
      the performance parameters.
      
      A value of notApplicable is displayed in the case of nailed-up PVCs 
      for which this attribute has no significance."
::= { atmIfVpcTrafficEntry 31 }

atmIfVpcTxQueueLength OBJECT-TYPE
   SYNTAX     INTEGER (0..30720)
   ACCESS     read-only
   STATUS     obsolete
   DESCRIPTION
     "This attribute is HISTORICAL. Please refer to the attribute of the 
      same name in the group AtmTmOper.
      
      This attribute indicates the current length of the transmit queue for 
      this connection. If this connection has traffic shaping disabled, then 
      this attribute displays the common queue length. If traffic shaping is 
      enabled, then this attribute displays the per-VC queue length."
::= { atmIfVpcTrafficEntry 32 }

atmIfVpcTxQueueCongestionState OBJECT-TYPE
   SYNTAX     INTEGER (0..3)
   ACCESS     read-only
   STATUS     obsolete
   DESCRIPTION
     "This attribute is HISTORICAL. Please refer to the attribute of the 
      same name in the group AtmTmOper.
      
      This attribute indicates the congestion state of the transmit queue 
      for this connection. If the connection has traffic shaping disabled, 
      then this attribute displays the common queue congestion state. If 
      traffic shaping is enabled, then this attribute displays the per-VC 
      queue congestion state.
      
      The congestion state of a queue is indicated by a numeric value 
      ranging from 0 to 3. When a queue is in a congested state x, only 
      traffic with discard priority (DP) 0 to x are enqueued. Traffic with 
      DP > x is discarded. 
      
      Therefore, if the congestion state is 3, there is no congestion and all 
      traffic is enqueued. Likewise, when the congestion state is 0, there 
      is maximum congestion and only traffic with DP=0 is enqueued on 
      that queue."
::= { atmIfVpcTrafficEntry 33 }

atmIfVpcHoldingPriority OBJECT-TYPE
   SYNTAX     INTEGER  {
                 n0(0),
                 n1(1),
                 n2(2),
                 n3(3),
                 n4(4),
                 notApplicable(6) }
   ACCESS     read-only
   STATUS     obsolete
   DESCRIPTION
     "This attribute is HISTORICAL. Please refer to the attribute of the 
      same name in the group AtmTmOper.
      
      This attribute indicates the actual holding priority in effect for this 
      connection. In a situation where the link bandwidth fluctuates, such 
      as over an IMA link, holding priority is used to determine which 
      connections are held and which are released. Holding priority 4 
      connections are the first to be released. Holding priority 0 
      connections are the last to be released. Some applications, for 
      example Vcc Test, may override the provisioned holding priority. 
      
      A value of notApplicable is displayed when this is an elastic 
      connection. Holding priority does not apply to bandwidth elastic 
      connections.
      
      Holding priority has no effect for ubr atmServiceCategory or 
      txTrafficDescriptorType 1 or 2 connections."
::= { atmIfVpcTrafficEntry 35 }

atmIfVpcRxTrafficDescType OBJECT-TYPE
   SYNTAX     INTEGER  {
                 n1(1),
                 n2(2),
                 n3(3),
                 n4(4),
                 n5(5),
                 n6(6),
                 n7(7),
                 n8(8) }
   ACCESS     read-only
   STATUS     obsolete
   DESCRIPTION
     "This attribute is HISTORICAL. Please refer to the attribute of the 
      same name in the group AtmTmOper.
      
      This attribute indicates the type of traffic management which is 
      applied to the receive direction of this connection as defined in the 
      ATM Forum. The rxTrafficDescType determines the number and 
      meaning of the parameters in the rxTrafficDescParm attribute."
::= { atmIfVpcTrafficEntry 40 }

atmIfVpcRxQosClass OBJECT-TYPE
   SYNTAX     INTEGER  {
                 unspecified(0),
                 constantBitRate(1),
                 variableBitRate(2),
                 connectionOriented(3),
                 connectionless(4) }
   ACCESS     read-only
   STATUS     obsolete
   DESCRIPTION
     "This attribute reflects the value of the provisioned attribute in the 
      Vcd or Vpd. Refer to that attribute for more detailed explanation. 
      
      This attribute is obsolete replaced by the UNI 4.0 attribute 
      atmServiceCategory."
::= { atmIfVpcTrafficEntry 60 }

atmIfVpcBwdQosClass OBJECT-TYPE
   SYNTAX     INTEGER  {
                 n0(0),
                 n1(1),
                 n2(2),
                 n3(3),
                 n4(4),
                 notApplicable(14) }
   ACCESS     read-only
   STATUS     obsolete
   DESCRIPTION
     "This attribute is HISTORICAL. Please refer to the attribute of the 
      same name in the group AtmTmOper.
      
      This attribute indicates the quality of service for the called to calling 
      direction for this connection. This is only applicable to Soft PVC 
      and SVC connections. 
      
      Class 1 supports a QOS that meets Service Class A performance 
      requirements (Circuit emulation, constant bit rate video).
      
      Class 2 supports a QOS that meets Service Class B performance 
      requirements (Variable bit rate audio and video).
      
      Class 3 supports a QOS that meets Service Class C performance 
      requirements (Connection-Oriented Data Transfer).
      
      Class 4 supports a QOS that meets Service Class D performance 
      requirements (Connectionless Data Transfer).
      
      Class 0 is the unspecified QOS class; no objective is specified for 
      the performance parameters.
      
      A value of notApplicable is displayed in the case of nailed-up PVCs 
      for which this attribute has no significance."
::= { atmIfVpcTrafficEntry 61 }

atmIfVpcAtmServiceCategory OBJECT-TYPE
   SYNTAX     INTEGER  {
                 unspecifiedBitRate(0),
                 constantBitRate(1),
                 rtVariableBitRate(2),
                 nrtVariableBitRate(3) }
   ACCESS     read-only
   STATUS     obsolete
   DESCRIPTION
     "This attribute is HISTORICAL. Please refer to the attribute of the 
      same name in the group AtmTmOper.
      
      This attribute indicates the ATM service category used for traffic in 
      both directions of the connection. 
      
      The constantBitRate service category is intended for real time 
      applications, that is, those requiring tightly constrained delay and 
      delay variation, as would be appropriate for voice and video 
      applications. The consistent availability of a fixed quantity of 
      bandwidth is considered appropriate for CBR service. Cells which 
      are delayed beyond the value specified by Cell Transfer Delay are 
      assumed to have significantly reduced value of the application.
      
      The rtVariableBitRate service category is intended for real time 
      applications; that is those requiring tightly constrained delay and 
      delay variation, as would be appropriate for voice and video 
      applications. Sources are expected to transmit at a rate which varies 
      with time. Equivalently, the source can be described as 'bursty'. 
      Cells which are delayed beyond the value specified by Cell Transfer 
      Delay are assumed to be of significantly reduced value to the 
      application. Real time VBR service may support statistical 
      multiplexing of real time sources.
      
      The nrtVariableBitRate service category is intended for non-real 
      time applications which have bursty traffic characteristics and which 
      can be characterized in terms of a PCR, SCR, and MBS. For those 
      cells which are transferred within the traffic contract, the application 
      expects a low cell loss ratio. For all connections, it expects a bound 
      on the mean cell transfer delay. Non-real time VBR service may 
      support statistical multiplexing of connections.
      
      The unspecifiedBitRate service is intended for non-real time 
      applications, that is those not requiring tightly constrained delay 
      and delay variation. UBR sources are expected to be bursty. UBR 
      service supports a high degree of statistical multiplexing among 
      sources. UBR service does not specify traffic related service 
      guarantees. No numerical commitments are made with respect to 
      the cell loss ratio experienced by a UBR connection, or as to the 
      cell transfer delay experienced by cells on the connection."
::= { atmIfVpcTrafficEntry 62 }

atmIfVpcTrafficShaping OBJECT-TYPE
   SYNTAX     INTEGER  {
                 enabled(0),
                 disabled(1),
                 notApplicable(4) }
   ACCESS     read-only
   STATUS     obsolete
   DESCRIPTION
     "This attribute is HISTORICAL. Please refer to the attribute of the 
      same name in the group AtmTmOper.
      
      This attribute indicates the traffic shaping state of the connection.
      
      A value of notApplicable indicates that traffic shaping is not 
      applicable or not supported for this connection. This is the case 
      when the atmServiceCategory is constantBitRate, or when the 
      txTrafficDescType is 1 or 2. In these cases, the value of 
      notApplicable is set regardless of whether traffic shaping is enabled 
      or disabled in the provisioning data.
      
      A value of disabled indicates that traffic shaping is applicable and 
      supported for the type of connection but has been turned off in the 
      provisioning data.
      
      A value of enabled indicates that traffic shaping is applicable and 
      supported for the type of connection and has been turned on in the 
      provisioning data. This is the only case that indicates that traffic 
      shaping is performed on the connection. In this case, the actual 
      shaping rate is reflected in the txTrafficDescParm attribute, 
      parameter number 4."
::= { atmIfVpcTrafficEntry 70 }

atmIfVpcBearerClassBbc OBJECT-TYPE
   SYNTAX     INTEGER  {
                 a(1),
                 c(3),
                 x(16),
                 vp(24),
                 notApplicable(30) }
   ACCESS     read-only
   STATUS     obsolete
   DESCRIPTION
     "This attribute is HISTORICAL. Please refer to the attribute of the 
      same name in the group AtmTmOper.
      
      This attribute indicates the bearer capability for this connection.
      
      Class a service is a connection-oriented, constant bit rate ATM 
      transport service. Class a service has end to end timing 
      requirements and may require stringent cell loss, cell delay and cell 
      delay variation performance.When a is displayed, the user is 
      requesting more than an ATM only service. The network may look 
      at the AAL to provide interworking based upon its contents. 
      
      Class c service is a connection-oriented, variable bit rate ATM 
      transport service. Class c service has no end-to-end timing 
      requirements.When c is displayed, the user is requesting more than 
      an ATM only service. The network interworking function may look 
      at the AAL and provide service based on it.
      
      Class x service is a connection-oriented ATM transport service 
      where the AAL, trafficType (cbr or vbr) and timing requirements 
      are user defined (that is, transparent to the network). When the 
      value of this attribute is x, the user is requesting an ATM only 
      service from the network. In this case, the network shall not process 
      any higher layer protocol.
      
      Class vp service is used to indicate a transparent VP service when 
      the user is requesting an ATM only service from the network. In this 
      case, the network does not process any higher layer protocol. This 
      service differs from class x service in that with the class vp service 
      both the VCI field (except for VCI values 0, 3, 4, and 6 through 15) 
      and Payload Type field are transported transparently by the network. 
      This attribute value is only applicable to SPVP and SVP 
      connections.
      
      A value of notApplicable is displayed in the case of nailed-up PVCs 
      for which this attribute has no significance."
::= { atmIfVpcTrafficEntry 71 }

atmIfVpcTransferCapabilityBbc OBJECT-TYPE
   SYNTAX     INTEGER  {
                 n0(0),
                 n1(1),
                 n2(2),
                 n5(5),
                 n8(8),
                 n9(9),
                 n10(10),
                 notApplicable(30) }
   ACCESS     read-only
   STATUS     obsolete
   DESCRIPTION
     "This attribute is HISTORICAL. Please refer to the attribute of the 
      same name in the group AtmTmOper.
      
      This attribute indicates the transfer capability for this connection. 
      Uni 3.0/3.1 traffic type and end-to-end timing parameters are 
      mapped into this parameter as follows:
      <transferCapability: TrafficType, Timing>
      0: NoIndication, NoIndication
      1: NoIndication, yes
      2: NoIndication, no
      5: CBR, yes
      8: VBR, NoIndication
      9: VBR, yes
      10: VBR, no
      
      A value of notApplicable is displayed in the case of nailed-up PVCs 
      for which this attribute has no significance, or in the case that the 
      transfer capability in the call request was set to NoIndication.
      
      The CBR traffic type refers to traffic offered on services such as a 
      constant bit rate video service or a circuit emulation.
      
      The VBR traffic type refers to traffic offered on services such as 
      packetized audio and video, or data.
      
      The value NoIndication for traffic type is used if the user has not set 
      the traffic type; similarly for end-to-end timing.
      
      The value yes for end-to-end timing indicates that end-to-end 
      timing is required for the connection.
      
      The value no for end-to-end timing indicates that end-to-end timing 
      is not required for the connection."
::= { atmIfVpcTrafficEntry 72 }

atmIfVpcClippingBbc OBJECT-TYPE
   SYNTAX     INTEGER  {
                 no(0),
                 yes(1),
                 notApplicable(14) }
   ACCESS     read-only
   STATUS     obsolete
   DESCRIPTION
     "This attribute is HISTORICAL. Please refer to the attribute of the 
      same name in the group AtmTmOper.
      
      This attribute indicates the value of the clipping susceptibility 
      parameter in the BBC Information Element.
      
      Clipping is an impairment in which the first fraction of a second of 
      information to be transferred is lost. It occurs after a call is 
      answered and before an associated connection is switched through.
      
      A value of notApplicable is displayed in the case of nailed-up PVCs 
      for which this attribute has no significance."
::= { atmIfVpcTrafficEntry 74 }

atmIfVpcUnshapedTransmitQueueing OBJECT-TYPE
   SYNTAX     INTEGER  {
                 perVc(0),
                 common(1),
                 notApplicable(4) }
   ACCESS     read-only
   STATUS     obsolete
   DESCRIPTION
     "This attribute is HISTORICAL. Please refer to the attribute of the 
      same name in the group AtmTmOper.
      
      This attribute indicates the unshaped transmit queuing state of the 
      connection.
      
      A value of common indicates that transmit traffic is being enqueued 
      onto common transmit queues. 
      
      A value of perVc indicates that transmit traffic is being enqueued 
      onto a per-VC queue for this connection. This is the case when 
      trafficShaping is disabled, but per-VC queueing has been 
      configured for this connection. 
      
      A value of notApplicable indicates that transmit traffic is being 
      shaped for this connection. Transmit traffic for a shaped connection 
      is enqueued onto a per-VC queue, but this attribute is only 
      applicable for unshaped connections."
::= { atmIfVpcTrafficEntry 75 }

atmIfVpcBestEffort OBJECT-TYPE
   SYNTAX     INTEGER  {
                 indicated(0),
                 notIndicated(1),
                 notApplicable(14) }
   ACCESS     read-only
   STATUS     obsolete
   DESCRIPTION
     "This attribute is HISTORICAL. Please refer to the attribute of the 
      same name in the group AtmTmOper.
      
      This attribute indicates value of best effort parameter in the ATM 
      Traffic Descriptor Information Element.
      
      The value indicated implies that the quality of service for this 
      connection is not guaranteed.
      
      The value notIndicated implies that the quality of service for this 
      connection is guaranteed.
      
      A value of notApplicable is displayed in the case of nailed-up PVCs 
      for which this attribute has no significance."
::= { atmIfVpcTrafficEntry 76 }

atmIfVpcUsageParameterControl OBJECT-TYPE
   SYNTAX     INTEGER  {
                 enabled(0),
                 disabled(1),
                 notApplicable(3) }
   ACCESS     read-only
   STATUS     obsolete
   DESCRIPTION
     "This attribute is HISTORICAL. Please refer to the attribute of the 
      same name in the group AtmTmOper.
      
      This attribute indicates the UPC state of the connection.
      
      A value of notApplicable indicates that UPC is not applicable or not 
      supported for the connection. This is the case when the connection's 
      rxTrafficDescType is 1 or 2. A value of notApplicable is set 
      regardless of whether UPC is disabled or enabled in provisioning 
      data.
      
      A value of disabled indicates that UPC is applicable and supported 
      for the type of connection but has been turned off in the 
      provisioning data.
      
      A value of enabled indicates that UPC is applicable and supported 
      for the type of connection and has been turned on in the 
      provisioning data. This is the only case that indicates that UPC is 
      enforced on the connection. In this case the traffic descriptor 
      parameters used for UPC enforcement are reflected in the 
      rxTrafficDescParms of the connection."
::= { atmIfVpcTrafficEntry 80 }

atmIfVpcTxFrameDiscard OBJECT-TYPE
   SYNTAX     OCTET STRING (SIZE (1))
   ACCESS     read-only
   STATUS     obsolete
   DESCRIPTION
     "This attribute is HISTORICAL. Please refer to the attribute of the 
      same name in the group AtmTmOper.
      
      This attribute indicates the set of current frame discard functions in 
      effect in the transmit data direction at this connection point.
      
      A value of ppd indicates that the Partial Packet Discard (PPD) 
      function is in effect. PPD may be applied at an interim connecting 
      point for a connection which is transporting frame traffic (AAL5 at 
      the endpoint). PPD is controlled by provisioning for PVCs and 
      SPVCs, and by call setup parameters in the AAL and Traffic 
      Descriptor Information Elements.
      
      A value of epd indicates that the Early Packet Discard (EPD) 
      function is in effect at this connection endpoint. PPD and EPD are 
      enabled by default at a connection endpoint which is performing 
      AAL5 segmentation and assembly.
      
      Frame discard functions are not applicable for Virtual Path 
      Connections (VPCs).

      Description of bits:
      ppd(0)
      epd(1)"
::= { atmIfVpcTrafficEntry 85 }

atmIfVpcRxFrameDiscard OBJECT-TYPE
   SYNTAX     OCTET STRING (SIZE (1))
   ACCESS     read-only
   STATUS     obsolete
   DESCRIPTION
     "This attribute is HISTORICAL. Please refer to the attribute of the 
      same name in the group AtmTmOper.
      
      This attribute indicates the set of current frame discard functions in 
      effect in the receive data direction at this connection point.
      
      A value of ppd indicates that the Partial Packet Discard (PPD) 
      function is in effect. PPD may be applied at an interim connecting 
      point for a connection which is transporting frame traffic (AAL5 at 
      the endpoint). PPD is controlled by provisioning for PVCs and 
      SPVCs, and by call setup parameters in the AAL and Traffic 
      Descriptor Information Elements.
      
      A value of epd indicates that the Early Packet Discard (EPD) 
      function is in effect at this connection endpoint. PPD and EPD are 
      enabled by default at a connection endpoint which is performing 
      AAL5 segmentation and assembly.
      
      Frame discard functions are not applicable for Virtual Path 
      Connections (VPCs).

      Description of bits:
      ppd(0)
      epd(1)"
::= { atmIfVpcTrafficEntry 86 }

atmIfVpcBandwidthElastic OBJECT-TYPE
   SYNTAX     INTEGER  {
                 no(0),
                 yes(1) }
   ACCESS     read-only
   STATUS     obsolete
   DESCRIPTION
     "This attribute is HISTORICAL. Please refer to the attribute of the 
      same name in the group AtmTmOper.
      
      This attribute is only of importance for connections which are 
      carried on a link with a variable bandwidth. For example, the 
      bandwidth may be reduced in the event that one or more physical 
      links in the IMA group fail, such that the originally requested 
      bandwidth cannot be maintained. This attribute shows whether the 
      application (for example, Trunk) running on this connection can 
      continue to operate if the bandwidth is reduced. If the bandwidth is 
      reduced, the amount by which it is reduced is displayed in the 
      bandwidthReduction attribute. 
      
      A value of yes, indicates that this connection is elastic, and the 
      bandwidth may be reduced but the connection is not released. 
      
      A value of no indicates that the bandwidth for this connection is not 
      reduced in the event of link bandwidth reduction. However, this 
      connection may be released based on its holdingPriority.
      
      Bandwidth elasticity has no effect for ubr atmServiceCategory or 
      txTrafficDescriptorType 1 or 2 connections."
::= { atmIfVpcTrafficEntry 90 }

atmIfVpcBandwidthReduction OBJECT-TYPE
   SYNTAX     INTEGER (0..2147483647)
   ACCESS     read-only
   STATUS     obsolete
   DESCRIPTION
     "This attribute is HISTORICAL. Please refer to the attribute of the 
      same name in the group AtmTmOper.
      
      This attribute shows the amount by which the bandwidth has been 
      reduced for this connection. This value is non-zero only for 
      connections which have bandwidthElastic displayed as yes, and 
      which are also operating in a reduced bandwidth mode. This is 
      typically be the case for selected connections running over an IMA 
      link. This attribute takes a value from 0 (no reduction) up to the 
      ECR. All connections which are running at their full allocated 
      bandwidth, bwReduction have the value 0. Connections which have 
      been reduced in allocated bandwidth have a positive number for this 
      attribute. The bwReduction may be subtracted from the ECR (which 
      is displayed as txTrafficDescParm 5) to determine the actual 
      bandwidth allocated to this connection."
::= { atmIfVpcTrafficEntry 100 }

atmIfVpcStatsTable OBJECT-TYPE
   SYNTAX     SEQUENCE OF AtmIfVpcStatsEntry
   ACCESS     not-accessible
   STATUS     mandatory
   DESCRIPTION
     "This group contains traffic statistics for a Vcc, Vpc, or Vpt 
      component."
::= { atmIfVpc 140 }

atmIfVpcStatsEntry OBJECT-TYPE
   SYNTAX     AtmIfVpcStatsEntry
   ACCESS     not-accessible
   STATUS     mandatory
   DESCRIPTION
     "An entry in the atmIfVpcStatsTable."
   INDEX {
      atmIfIndex,
      atmIfVpcIndex }
::= { atmIfVpcStatsTable 1 }

AtmIfVpcStatsEntry ::= SEQUENCE {
   atmIfVpcStatsTxCell
      PassportCounter64,
   atmIfVpcStatsTxCellClp
      PassportCounter64,
   atmIfVpcTxDiscard
      PassportCounter64,
   atmIfVpcTxDiscardClp
      PassportCounter64,
   atmIfVpcStatsTxCellDiscard
      PassportCounter64,
   atmIfVpcStatsTxCellDiscardClp
      PassportCounter64,
   atmIfVpcStatsTxFrameDiscard
      PassportCounter64,
   atmIfVpcStatsTxFrameDiscardClp
      PassportCounter64,
   atmIfVpcTxUtilization
      Gauge32,
   atmIfVpcStatsRxCell
      PassportCounter64,
   atmIfVpcStatsRxCellClp
      PassportCounter64,
   atmIfVpcRxDiscard
      PassportCounter64,
   atmIfVpcRxDiscardClp
      PassportCounter64,
   atmIfVpcStatsRxCellDiscard
      PassportCounter64,
   atmIfVpcStatsRxCellDiscardClp
      PassportCounter64,
   atmIfVpcStatsRxFrameDiscard
      PassportCounter64,
   atmIfVpcStatsRxFrameDiscardClp
      PassportCounter64,
   atmIfVpcRxUtilization
      Gauge32,
   atmIfVpcStatsRxUpcViolationOnEnforcer1
      PassportCounter64,
   atmIfVpcStatsRxUpcViolationOnEnforcer2
      PassportCounter64,
   atmIfVpcStatsRxAal5FrameError
      PassportCounter64,
   atmIfVpcStatsRxAal5FrameAbort
      PassportCounter64 }

atmIfVpcStatsTxCell OBJECT-TYPE
   SYNTAX     PassportCounter64 
   ACCESS     read-only
   STATUS     mandatory
   DESCRIPTION
     "This attribute counts the number of cells that have been transmitted 
      from the interface on this connection. The counter wraps to zero if it 
      exceeds its maximum value of (2**64)-1."
::= { atmIfVpcStatsEntry 10 }

atmIfVpcStatsTxCellClp OBJECT-TYPE
   SYNTAX     PassportCounter64 
   ACCESS     read-only
   STATUS     mandatory
   DESCRIPTION
     "This attribute counts the number of cells that have been transmitted 
      from the interface on this connection with the CLP=1. The counter 
      wraps to zero if it exceeds its maximum value of (2**64)-1."
::= { atmIfVpcStatsEntry 20 }

atmIfVpcTxDiscard OBJECT-TYPE
   SYNTAX     PassportCounter64 
   ACCESS     read-only
   STATUS     obsolete
   DESCRIPTION
     "This attribute is replaced by new attributes txCellDiscard and 
      txFrameDiscard.
      
      This attribute counts the number of cells or frames received from 
      the bus on this connection that have been discarded.
      
      If the connection segments frames into cells, the counter indicates 
      the number of frames discarded. Connections which segment 
      frames into cells have a connectionPointType of 
      connectionEndPoint.
      
      If the connection relays cells without adaptation, the counter 
      indicates the number of cells discarded. Connections which relay 
      cells without adaptation have a connectionPointType of 
      segmentEndPoint or connectingPoint.
      
      AAL1 connections are an exception to this rule; although they have 
      a connectionPointType of connectionEndPoint, they do not do 
      adaptation at this point. Thus, in the AAL1 case, this attribute 
      counts discarded cells.
      
      Discards are done due to congestion or when the connection's 
      interface is disabled.
      
      The counter wraps to zero if it exceeds its maximum value of 
      (2**64)-1."
::= { atmIfVpcStatsEntry 30 }

atmIfVpcTxDiscardClp OBJECT-TYPE
   SYNTAX     PassportCounter64 
   ACCESS     read-only
   STATUS     obsolete
   DESCRIPTION
     "This attribute is replaced by new attributes txCellDiscardClp and 
      txFrameDiscardClp.
      
      This attribute counts the number of cells or frames received from 
      the bus on this connection with CLP=1 that have been discarded.
      
      If the connection segments frames into cells, the counter indicates 
      the number of frames discarded. Connections which segment 
      frames into cells have a connectionPointType of 
      connectionEndPoint.
      
      If the connection relays cells without adaptation, the counter 
      indicates the number of cells discarded. Connections which relay 
      cells without adaptation have a connectionPointType of 
      segmentEndPoint or connectingPoint.
      
      AAL1 connections are an exception to this rule; although they have 
      a connectionPointType of connectionEndPoint, they do not do 
      adaptation at this point. Thus, in the AAL1 case, this attribute 
      counts discarded cells.
      
      Discards are done due to congestion or when the connection's 
      interface is disabled.
      
      The counter wraps to zero if it exceeds its maximum value of 
      (2**64)-1."
::= { atmIfVpcStatsEntry 40 }

atmIfVpcStatsTxCellDiscard OBJECT-TYPE
   SYNTAX     PassportCounter64 
   ACCESS     read-only
   STATUS     mandatory
   DESCRIPTION
     "This attribute counts the number of cells received from the bus on 
      this connection that have been discarded.
      
      Discarded cells are not counted in the txCell attribute.
      
      Cells are discarded due to transmit congestion, Partial Packet 
      Discard (PPD), Early Packet Discard (EPD), and Weighted Random 
      Early Detection (W-RED) mechanisms, or when the connection's 
      interface is disabled.
      
      For CQC-based ATM cards, this attribute is applicable only to 
      connections that relay cells without adaptation. Such connections 
      usually have a connectionPointType of segmentEndPoint or 
      connectingPoint. AAL1 connections are an exception to this rule; 
      although they have a connectionPointType of connectionEndPoint, 
      they do not do adaptation at this point. For Vpts, this attribute 
      provides an aggregated total of all txCellDiscard values for all such 
      connections associated with the Vpt.
      
      For Vccs on CQC-based ATM cards, if the connection segments 
      frames into cells, this attribute is not applicable and is not 
      displayed.
      
      The counter wraps to zero if it exceeds its maximum value of 
      (2**64)-1."
::= { atmIfVpcStatsEntry 42 }

atmIfVpcStatsTxCellDiscardClp OBJECT-TYPE
   SYNTAX     PassportCounter64 
   ACCESS     read-only
   STATUS     mandatory
   DESCRIPTION
     "This attribute counts the number of cells received from the bus on 
      this connection with CLP=1 that have been discarded.
      
      This count is included in the txCellDiscard attribute. Discarded 
      cells are not counted in the txCellClp attribute.
      
      Cells are discarded due to transmit congestion, Partial Packet 
      Discard (PPD), Early Packet Discard (EPD), and Weighted Random 
      Early Detection (W-RED) mechanisms, or when the connection's 
      interface is disabled.
      
      For CQC-based ATM cards, this attribute is applicable only to 
      connections that relay cells without adaptation. Such connections 
      have a connectionPointType of segmentEndPoint or 
      connectingPoint. AAL1 connections are an exception to this rule; 
      although they have a connectionPointType of connectionEndPoint, 
      they do not do adaptation at this point. For Vpts, this attribute 
      provides an aggregated total of all txCellDiscardClp values for all 
      such connections associated with the Vpt.
      
      For Vccs on CQC-based ATM cards, if the connection segments 
      frames into cells, this attribute is not applicable and is not 
      displayed.
      
      The counter wraps to zero if it exceeds its maximum value of 
      (2**64)-1."
::= { atmIfVpcStatsEntry 43 }

atmIfVpcStatsTxFrameDiscard OBJECT-TYPE
   SYNTAX     PassportCounter64 
   ACCESS     read-only
   STATUS     mandatory
   DESCRIPTION
     "This attribute counts the number of frames received from the bus on 
      this connection that have been discarded.
      
      Frames are discarded due to congestion, Partial Packet Discard 
      (PPD), Early Packet Discard (EPD), and Weighted Random Early 
      Detection (W-RED) mechanisms, or when the connection interface 
      is disabled.
      
      This count is independent of the txCell or txCellDiscard attribute.
      
      For CQC-based ATM cards, this attribute is applicable only to 
      connections that segment frames into cells. Such connections have a 
      connectionPointType of connectionEndPoint. AAL1 connections 
      are an exception to this rule; although they have a 
      connectionPointType of connectionEndPoint, they do not do 
      adaptation at this point. For Vpts, this attribute provides an 
      aggregated total of all txFrameDiscard values for all such 
      connections associated with the Vpt.
      
      For CQC-based ATM cards, for Vpcs, and Vccs that relay cells 
      without adaptation, this attribute is not applicable and is not 
      displayed.
      
      Discards due to EPD, PPD, and W-RED for a standard Vpt Vcc are 
      not included in this attribute. These discards are counted in the 
      Vcc's parent Vpt txFrameDiscard attribute.
      
      The counter wraps to zero if it exceeds its maximum value of 
      (2**64)-1."
::= { atmIfVpcStatsEntry 46 }

atmIfVpcStatsTxFrameDiscardClp OBJECT-TYPE
   SYNTAX     PassportCounter64 
   ACCESS     read-only
   STATUS     mandatory
   DESCRIPTION
     "This attribute counts the number of discarded frames on this 
      connection that were received from the bus and composed of one or 
      more CLP=1 cells.
      
      Frames are discarded due to congestion, Partial Packet Discard 
      (PPD), Early Packet Discard (EPD), and Weighted Random Early 
      Detection (W-RED) mechanisms, or when the connection interface 
      is disabled.
      
      This count is included in the txFrameDiscard attribute.
      
      For CQC-based ATM cards, this attribute is applicable only to 
      connections that segment frames into cells. Such connections have a 
      connectionPointType of connectionEndPoint. AAL1 connections 
      are an exception to this rule; although they have a 
      connectionPointType of connectionEndPoint, they do not do 
      adaptation at this point. For Vpts, this attribute provides an 
      aggregated total of all txFrameDiscardClp values for all such 
      connections associated with the Vpt.
      
      For CQC-based ATM cards, for Vpcs, and Vccs that relay cells 
      without adaptation, this attribute is not applicable and is not 
      displayed.
      
      Discards due to EPD, PPD, and W-RED for a standard Vpt Vcc are 
      not included in this attribute. These discards are counted in the 
      Vcc's parent Vpt txFrameDiscardClp attribute.
      
      The counter wraps to zero if it exceeds its maximum value of 
      (2**64)-1."
::= { atmIfVpcStatsEntry 47 }

atmIfVpcTxUtilization OBJECT-TYPE
   SYNTAX     Gauge32 (0..200 | 255)
   ACCESS     read-only
   STATUS     mandatory
   DESCRIPTION
     "This attribute indicates the current transmit utilization during the 
      most recent minute, expressed as a percentage of the total 
      bandwidth which can be carried by this connection. This attribute is 
      only applicable for Vpts and not for Vpcs or Vccs.
      
      When the Vpt is shaped, the value of this attribute is calculated 
      using its actual shaping rate (ASR) and should not exceed 100.
      
      When the Vpt is unshaped, the value of this attribute is calculated 
      using its peak cell rate (PCR) and should not exceed 200. If the 
      PCR is 0, the value 255 is used."
::= { atmIfVpcStatsEntry 48 }

atmIfVpcStatsRxCell OBJECT-TYPE
   SYNTAX     PassportCounter64 
   ACCESS     read-only
   STATUS     mandatory
   DESCRIPTION
     "This attribute counts cells that have been received from the interface 
      on this connection. The counter wraps to zero if it exceeds its 
      maximum value of (2**64)-1."
::= { atmIfVpcStatsEntry 50 }

atmIfVpcStatsRxCellClp OBJECT-TYPE
   SYNTAX     PassportCounter64 
   ACCESS     read-only
   STATUS     mandatory
   DESCRIPTION
     "This attribute counts cells that have been received from the interface 
      on this connection with the CLP=1. The counter wraps to zero if it 
      exceeds its maximum value of (2**64)-1."
::= { atmIfVpcStatsEntry 60 }

atmIfVpcRxDiscard OBJECT-TYPE
   SYNTAX     PassportCounter64 
   ACCESS     read-only
   STATUS     obsolete
   DESCRIPTION
     "This attribute is replaced by new attributes rxCellDiscard and 
      rxFrameDiscard.
      
      This attribute counts the number of cells or frames received from 
      the interface on this connection that have been discarded.
      
      If the connection segments frames into cells, the counter indicates 
      the number of frames discarded. Connections which segment 
      frames into cells have a connectionPointType of 
      connectionEndPoint.
      
      If the connection relays cells without adaptation, the counter 
      indicates the number of cells discarded. Connections which relay 
      cells without adaptation have a connectionPointType of 
      segmentEndPoint or connectingPoint.
      
      AAL1 connections are an exception to this rule; although they have 
      a connectionPointType of connectionEndPoint, they do not do 
      adaptation at this point. Thus, in the AAL1 case, this attribute 
      counts discarded cells.
      
      Discards are done due to congestion, non-conformance with UPC or 
      AAL reassembly problems.
      
      The counter wraps to zero if it exceeds its maximum value of 
      (2**64)-1."
::= { atmIfVpcStatsEntry 70 }

atmIfVpcRxDiscardClp OBJECT-TYPE
   SYNTAX     PassportCounter64 
   ACCESS     read-only
   STATUS     obsolete
   DESCRIPTION
     "This attribute is replaced by new attributes rxCellDiscardClp and 
      rxFrameDiscardClp.
      
      This attribute counts the number of cells or frames received from 
      the interface on this connection with CLP=1 that have been 
      discarded.
      
      If the connection segments frames into cells, the counter indicates 
      the number of frames discarded. Connections which segment 
      frames into cells have a connectionPointType of 
      connectionEndPoint.
      
      If the connection relays cells without adaptation, the counter 
      indicates the number of cells discarded. Connections which relay 
      cells without adaptation have a connectionPointType of 
      segmentEndPoint or connectingPoint.
      
      AAL1 connections are an exception to this rule; although they have 
      a connectionPointType of connectionEndPoint, they do not do 
      adaptation at this point. Thus, in the AAL1 case, this attribute 
      counts discarded cells.
      
      Discards are done due to congestion, non-conformance with UPC or 
      AAL reassembly problems.
      
      The counter wraps to zero if it exceeds its maximum value of 
      (2**64)-1."
::= { atmIfVpcStatsEntry 80 }

atmIfVpcStatsRxCellDiscard OBJECT-TYPE
   SYNTAX     PassportCounter64 
   ACCESS     read-only
   STATUS     mandatory
   DESCRIPTION
     "This attribute counts the number of cells received from the interface 
      on this connection that have been discarded. This count is included 
      in the rxCell attribute.
      
      This count includes cells discarded due to non-conformance with 
      UPC, cells which are part of a frame which has been discarded due 
      to an AAL5 frame reassembly error, cells which are discarded due 
      to congestion, or cells which are received while the next hop 
      connection to which the traffic is directed across the backplane is 
      down. The next hop connection is the Vcc or Vpc identified by the 
      nextHop attribute of the Nrp or Rp component. 
      
      For CQC-based ATM cards, this attribute is applicable only to 
      connections that relay cells without adaptation. Such connections 
      have a connectionPointType of connectionEndPoint or 
      connectingPoint. AAL1 connections are an exception to this rule; 
      although they have a connectionPointType of connectionEndPoint, 
      they do not do adaptation at this point. For Vpts, this attribute 
      provides an aggregated total of all rxCellDiscard values for all such 
      connections associated with the Vpt.
      
      For CQC-based ATM cards, for Vpcs, and Vccs that relay cells 
      without adaptation, this attribute is not applicable and is not 
      displayed.
      
      Discards due to non-conformance with UPC at the VP layer, for a 
      standard Vpt Vcc, are not included in this attribute. These discards 
      are counted in the Vcc's parent Vpt rxCellDiscard attribute.
      
      The counter wraps to zero if it exceeds its maximum value of 
      (2**64)-1."
::= { atmIfVpcStatsEntry 82 }

atmIfVpcStatsRxCellDiscardClp OBJECT-TYPE
   SYNTAX     PassportCounter64 
   ACCESS     read-only
   STATUS     mandatory
   DESCRIPTION
     "This attribute counts the number of cells received from the interface 
      on this connection with CLP=1 that have been discarded. This count 
      is included in the rxCell and rxCellDiscard attributes.
      
      This count includes cells discarded due to non-conformance with 
      UPC, cells which are part of a frame which has been discarded due 
      to an AAL5 frame reassembly error, cells which are discarded due 
      to congestion, or cells which are received while the next hop 
      connection to which the traffic is directed across the backplane is 
      down. The next hop connection is the Vcc or Vpc identified by the 
      nextHop attribute of the Nrp or Rp component. 
      
      For CQC-based ATM cards, this attribute is applicable only to 
      connections that relay cells without adaptation. Such connections 
      have a connectionPointType of connectionEndPoint or 
      connectingPoint. AAL1 connections are an exception to this rule; 
      although they have a connectionPointType of connectionEndPoint, 
      they do not do adaptation at this point. For Vpts, this attribute 
      provides an aggregated total of all rxCellDiscardClp values for all 
      such connections associated with the Vpt.
      
      For CQC-based ATM cards, for Vpcs, and Vccs that relay cells 
      without adaptation, this attribute is not applicable and is not 
      displayed.
      
      Discards due to non-conformance with UPC at the VP layer, for a 
      standard Vpt Vcc, are not included in this attribute. These discards 
      are counted in the Vcc's parent Vpt rxCellDiscardClp attribute.
      
      The counter wraps to zero if it exceeds its maximum value of 
      (2**64)-1."
::= { atmIfVpcStatsEntry 83 }

atmIfVpcStatsRxFrameDiscard OBJECT-TYPE
   SYNTAX     PassportCounter64 
   ACCESS     read-only
   STATUS     mandatory
   DESCRIPTION
     "This attribute counts the number of frames received from the 
      interface on this connection that have been discarded. This count is 
      independent of the rxCellDiscard attribute.
      
      This count includes frames discarded due to an AAL5 frame 
      reassembly error, frames discarded due to early packet discard 
      (EPD), and frames discarded due to processor (CPU) congestion. 
      This attribute is applicable only for connections that reassemble 
      incoming cells into frames. Connections which reassemble cells 
      into frames have a connectionPointType of connectionEndPoint. 
      AAL1 connections are an exception to this rule; even though they 
      have a connectionPointType of connectionEndPoint, they do not 
      do adaptation at this point. For Vpts, this attribute provides an 
      aggregated total of all rxFrameDiscard values for all applicable 
      connections associated with the Vpt.
      
      For Vpcs, and for Vccs that relay cells without adaptation, this 
      attribute is not applicable and is not displayed.
      
      The counter wraps to zero if it exceeds its maximum value of 
      (2**64)-1."
::= { atmIfVpcStatsEntry 86 }

atmIfVpcStatsRxFrameDiscardClp OBJECT-TYPE
   SYNTAX     PassportCounter64 
   ACCESS     read-only
   STATUS     mandatory
   DESCRIPTION
     "This attribute counts the number of discarded frames on this 
      connection that were received from the interface and composed of 
      one or more CLP1 cells. This count is included in the 
      rxFrameDiscard attribute. It is independent of the rxCellDiscard 
      attribute.
      
      This count includes frames discarded due to an AAL5 frame 
      reassembly error, frames discarded due to early packet discard 
      (EPD), and frames discarded due to processor (CPU) congestion. 
      This attribute is applicable only for connections that reassemble 
      incoming cells into frames. Connections which reassemble cells 
      into frames have a connectionPointType of connectionEndPoint. 
      AAL1 connections are an exception to this rule; even though they 
      have a connectionPointType of connectionEndPoint, they do not 
      do adaptation at this point. For Vpts, this attribute provides an 
      aggregated total of all rxFrameDiscardClp values for all applicable 
      connections associated with the Vpt.
      
      For Vpcs, and for Vccs that relay cells without adaptation, this 
      attribute is not applicable and is not displayed.
      
      The counter wraps to zero if it exceeds its maximum value of 
      (2**64)-1."
::= { atmIfVpcStatsEntry 88 }

atmIfVpcRxUtilization OBJECT-TYPE
   SYNTAX     Gauge32 (0..200 | 255)
   ACCESS     read-only
   STATUS     mandatory
   DESCRIPTION
     "This attribute indicates the current receive utilization during the 
      most recent minute, expressed as a percentage of the total 
      bandwidth which can be carried by this connection. This attribute is 
      only applicable for Vpts and not for Vpcs or Vccs.
      
      When the Vpt is shaped, the value of this attribute is calculated 
      using its actual shaping rate (ASR) and should not exceed 100.
      
      When the Vpt is unshaped, the value of this attribute is calculated 
      using its peak cell rate (PCR) and should not exceed 200. If the 
      PCR is 0, the value 255 is used."
::= { atmIfVpcStatsEntry 89 }

atmIfVpcStatsRxUpcViolationOnEnforcer1 OBJECT-TYPE
   SYNTAX     PassportCounter64 
   ACCESS     read-only
   STATUS     mandatory
   DESCRIPTION
     "This attribute counts the number of UPC violations observed by the 
      Generic Cell Rate Algorithm (GCRA) Enforcer 1. This attribute is 
      only applicable if UPC is enforced or monitored. This attribute is 
      not applicable for standard Vpt Vccs. This attribute is not applicable 
      and is not displayed on CQC-based ATM cards.
      
      When the value of rxTrafficDescType for this connection is 3, 4, 5, 
      6, 7 or 8, Enforcer 1 enforces conformance of traffic received from 
      the interface to PCR CLP0+1.
      
      When the value of rxTrafficDescType for this connection is 9, 
      Enforcer 1 performs the Dynamic Generic Cell Rate Algorithm 
      (DGCRA) used for the Available Bit Rate (ABR) service category.
      
      If UPC is enforced all non-conforming cells are discarded by this 
      enforcer. These discarded cells are included in rxCellDiscard. 
      
      For basic Vpts, this attribute provides an aggregated total of all 
      rxUpcViolationOnEnforcer1 values for the Vccs associated with the 
      Vpt.
      
      The counter wraps to zero if it exceeds its maximum value of 
      (2**64)-1."
::= { atmIfVpcStatsEntry 90 }

atmIfVpcStatsRxUpcViolationOnEnforcer2 OBJECT-TYPE
   SYNTAX     PassportCounter64 
   ACCESS     read-only
   STATUS     mandatory
   DESCRIPTION
     "This attribute counts the number of UPC violations observed by the 
      Generic Cell Rate Algorithm (GCRA) Enforcer 2. This attribute is 
      only applicable if UPC is enforced or monitored. This attribute is 
      not applicable for standard Vpt Vccs. This attribute is not applicable 
      and is not displayed on CQC-based ATM cards.
      
      Enforcer2 is applicable only if the rxTrafficDescType for this 
      connection is 4, 5, 6, 7 or 8.
      
      When the value of rxTrafficDescType 4 or 5, Enforcer 2 enforces 
      conformance of traffic received from the interface to PCR CLP0.
      
      When the value of rxTrafficDescType 6, Enforcer 2 enforces 
      conformance of traffic received from the interface to SCR CLP0+1.
      
      When the value of rxTrafficDescType 7 or 8, Enforcer 2 enforces 
      conformance of traffic received from the interface to SCR CLP0.
      
      If UPC is enforced, enforcer 2 discards non-conforming cells for 
      rxTrafficDescType values of 4, 6 and 7. It tags non-conforming cells 
      for rxTrafficDescType values of 5 and 8. Discarded cells are 
      counted in the rxCellDiscard attribute. 
      
      For basic Vpts, this attribute provides an aggregated total of all 
      rxUpcViolationOnEnforcer2 values for the Vccs associated with the 
      Vpt.
      
      The counter wraps to zero if it exceeds its maximum value of 
      (2**64)-1."
::= { atmIfVpcStatsEntry 92 }

atmIfVpcStatsRxAal5FrameError OBJECT-TYPE
   SYNTAX     PassportCounter64 
   ACCESS     read-only
   STATUS     mandatory
   DESCRIPTION
     "This attribute counts the number of frames received from the 
      interface on this connection that have AAL5 length errors or AAL5 
      CRC errors. 
      
      This attribute is not applicable and is not displayed on CQC-based 
      ATM cards.
      
      AAL5 length or CRC errors typically occur because of cell discards 
      due to congestion, UPC, or due to corruption of data between the 
      AAL5 segmentation and reassembly end points.
      
      This attribute is applicable only to connections that reassemble 
      incoming cells into frames. Such connections have a 
      connectionPointType of connectionEndPoint. AAL1 connections 
      are an exception to this rule; although they have a 
      connectionPointType of connectionEndPoint, they do not do 
      adaptation at this point. For Vpts, this attribute provides an 
      aggregated total of all rxAal5FrameError values for all applicable 
      connections associated with the Vpt.
      
      For Vpcs, and for Vccs that relay cells without adaptation, this 
      attribute is not applicable and is not displayed.
      
      The counter wraps to zero if it exceeds its maximum value of 
      (2**64)-1."
::= { atmIfVpcStatsEntry 100 }

atmIfVpcStatsRxAal5FrameAbort OBJECT-TYPE
   SYNTAX     PassportCounter64 
   ACCESS     read-only
   STATUS     mandatory
   DESCRIPTION
     "This attribute counts the number of frames received from the 
      interface on this connection that have the AAL5 length field set to 
      zero. 
      
      This attribute is not applicable and is not displayed for CQC-based 
      ATM cards.
      
      An AAL5 length of zero is an indication by the far end 
      segmentation point to this reassembly point that the frame is to be 
      discarded without reassembly. This mechanism is typically used by 
      a segmentation point if it detects an error in a frame after some of 
      the cells belonging to that frame have already been transmitted.
      
      This attribute is applicable only to connections that reassemble 
      incoming cells into frames. Such connections have a 
      connectionPointType of connectionEndPoint. AAL1 connections 
      are an exception to this rule; although they have a 
      connectionPointType of connectionEndPoint, they do not do 
      adaptation at this point. For Vpts, this attribute provides an 
      aggregated total of all rxAal5FrameAbort values for all applicable 
      connections associated with the Vpt.
      
      For Vpcs, and for Vccs that relay cells without adaptation, this 
      attribute is not applicable and is not displayed.
      
      The counter wraps to zero if it exceeds its maximum value of 
      (2**64)-1."
::= { atmIfVpcStatsEntry 102 }

atmIfVpcTxTdpTable OBJECT-TYPE
   SYNTAX     SEQUENCE OF AtmIfVpcTxTdpEntry
   ACCESS     not-accessible
   STATUS     obsolete
   DESCRIPTION
     "This attribute is HISTORICAL. Please refer to the attribute of the 
      same name in the group AtmTmOper.
      
      This attribute is a vector of five transmit traffic parameters. The first 
      three elements reflect the settings of the first three elements of the 
      txTrafficDescParm attribute in the AtmTrafficProv group. 
      
      When txTrafficDescType is 1 or 2, parameters 1 through 5 are 
      unused.
      
      In this description, PCR is the greater of either the PCR or the 
      requested shaping rate (parameter 1 or parameter 5) specified in the 
      Traffic group under the Vcd or Vpd.
      
      When txTrafficDescType is 3, parameter 1 represents the PCR for 
      CLP equal to 0 or 1 traffic; parameters 2 and 3 are unused.
      
      When txTrafficDescType is 4, parameter 1 represents the PCR for 
      CLP equal to 0 and 1 traffic; parameter 2 represents the PCR for 
      CLP equal to 0 traffic with cell discard.
      
      When txTrafficDescType is 5, parameter 1 represents the PCR for 
      CLP equal to 0 and 1 traffic; parameter 2 represents the PCR for 
      CLP equal to 0 traffic with cell tagging.
      
      When txTrafficDescType is 6, parameter 1 represents the PCR for 
      CLP equal to 0 and 1 traffic; parameter 2 represents the SCR for 
      CLP equal to 0 and 1 traffic; parameter 3 represents the MBS for 
      CLP equal to 0 and 1 traffic.
      
      When txTrafficDescType is 7, parameter 1 represents the PCR for 
      CLP equal to 0 and 1 traffic; parameter 2 represents the SCR for 
      CLP equal to 0 traffic with cell discard; parameter 3 represents the 
      MBS for CLP equal to 0 traffic.
      
      When txTrafficDescType is 8, parameter 1 represents the PCR for 
      CLP equal to 0 and 1 traffic; parameter 2 represents the SCR for 
      CLP equal to 0 traffic with cell tagging; parameter 3 represents the 
      MBS for CLP equal to 0 traffic
      
      When txTrafficDescType is 3, 4, 5, 6, 7 or 8, parameter 4 reflects 
      the actual shaping rate in cell/s for this connection. This rate is one 
      of the set of available shaping rates for this type of ATM-FP, based 
      on the number of interfaces doing shaping (attribute 
      perVcQueueInterfaces), the provisioned cell rate, the 
      shapingScalingFactor attribute of the AtmResourceControl 
      component, and whether traffic shaping is enabled. A rate of zero 
      (0) indicates that shaping is not performed. 
      
      When txTrafficDescType is 3, 4, 5, 6, 7 or 8, parameter 5 reflects 
      the equivalent cell rate in cell/s for this connection as determined by 
      the Connection Admission Control (CAC) algorithm. The 
      equivalent cell rate is useful in determining the admission 
      characteristics of this connection."
::= { atmIfVpc 294 }

atmIfVpcTxTdpEntry OBJECT-TYPE
   SYNTAX     AtmIfVpcTxTdpEntry
   ACCESS     not-accessible
   STATUS     obsolete
   DESCRIPTION
     "An entry in the atmIfVpcTxTdpTable."
   INDEX {
      atmIfIndex,
      atmIfVpcIndex,
      atmIfVpcTxTdpIndex }
::= { atmIfVpcTxTdpTable 1 }

AtmIfVpcTxTdpEntry ::= SEQUENCE {
   atmIfVpcTxTdpIndex
      Integer32,
   atmIfVpcTxTdpValue
      Unsigned32 }

atmIfVpcTxTdpIndex OBJECT-TYPE
   SYNTAX     Integer32 (1..5)
   ACCESS     not-accessible
   STATUS     obsolete
   DESCRIPTION
     "This variable represents the atmIfVpcTxTdpTable
      specific index for the atmIfVpcTxTdpTable."
::= { atmIfVpcTxTdpEntry 1 }

atmIfVpcTxTdpValue OBJECT-TYPE
   SYNTAX     Unsigned32 (0..2147483647)
   ACCESS     read-only
   STATUS     obsolete
   DESCRIPTION
     "This variable represents an individual value for the
      atmIfVpcTxTdpTable."
::= { atmIfVpcTxTdpEntry 2 }

atmIfVpcRxTdpTable OBJECT-TYPE
   SYNTAX     SEQUENCE OF AtmIfVpcRxTdpEntry
   ACCESS     not-accessible
   STATUS     obsolete
   DESCRIPTION
     "This attribute is HISTORICAL. Please refer to the attribute of the 
      same name in the group AtmTmOper.
      
      This attribute is a vector of four traffic parameters whose meanings 
      are defined by the rxTrafficDescType attribute. The values of peak 
      cell rate (PCR), sustained cell rate (SCR) are expressed in cells/s. 
      Maximum burst size (MBS) is expressed in cells. Cell Delay 
      Variation Tolerance (CDVT) is expressed in microseconds.
      
      When rxTrafficDescType is 1 or 2, none of the parameters are used.
      
      When rxTrafficDescType is 3, parameter 1 represents the PCR for 
      CLP equal to 0 and 1 traffic; parameter 4 represents the CDVT.
      
      When rxTrafficDescType is 4, parameter 1 represents the PCR for 
      CLP equal to 0 and 1 traffic; parameter 2 represents the PCR for 
      CLP equal to 0 traffic with cell discard; parameter 4 represents the 
      CDVT.
      
      When rxTrafficDescType is 5, parameter 1 represents the PCR for 
      CLP equal to 0 and 1 traffic; parameter 2 represents the PCR for 
      CLP equal to 0 traffic with cell tagging; parameter 4 represents the 
      CDVT.
      
      When rxTrafficDescType is a 6, parameter 1 represents the PCR for 
      CLP equal to 0 and 1 traffic; parameter 2 represents the SCR for 
      CLP equal to 0 and 1 traffic; parameter 3 represents the MBS for 
      CLP equal to 0 and 1 traffic; parameter 4 represents the CDVT. 
      
      When rxTrafficDescType is 7, parameter 1 represents the PCR for 
      CLP equal to 0 and 1 traffic; parameter 2 represents the SCR for 
      CLP equal to 0 traffic with cell discard; parameter 3 represents the 
      MBS for CLP equal to 0 traffic; parameter 4 represents the CDVT.
      
      When rxTrafficDescType is 8, parameter 1 represents the PCR for 
      CLP equal to 0 and 1 traffic; parameter 2 represents the SCR for 
      CLP equal to 0 traffic with cell tagging; parameter 3 represents the 
      MBS for CLP equal to 0 traffic; parameter 4 represents the CDVT. 
      
      If Upc is disabled for this connection, the values of PCR, SCR, 
      MBS and CDVT is a combination of provisioned parameters. If Upc 
      is enabled, the values of PCR, SCR, MBS, and CDVT is exactly the 
      values used by the usage parameter control hardware in policing the 
      arriving traffic. These may vary slightly from the provisioned values 
      due to granularity of the hardware. In the case where the PCR is 
      equal to the SCR, the effective MBS is zero."
::= { atmIfVpc 295 }

atmIfVpcRxTdpEntry OBJECT-TYPE
   SYNTAX     AtmIfVpcRxTdpEntry
   ACCESS     not-accessible
   STATUS     obsolete
   DESCRIPTION
     "An entry in the atmIfVpcRxTdpTable."
   INDEX {
      atmIfIndex,
      atmIfVpcIndex,
      atmIfVpcRxTdpIndex }
::= { atmIfVpcRxTdpTable 1 }

AtmIfVpcRxTdpEntry ::= SEQUENCE {
   atmIfVpcRxTdpIndex
      Integer32,
   atmIfVpcRxTdpValue
      Unsigned32 }

atmIfVpcRxTdpIndex OBJECT-TYPE
   SYNTAX     Integer32 (1..4)
   ACCESS     not-accessible
   STATUS     obsolete
   DESCRIPTION
     "This variable represents the atmIfVpcRxTdpTable
      specific index for the atmIfVpcRxTdpTable."
::= { atmIfVpcRxTdpEntry 1 }

atmIfVpcRxTdpValue OBJECT-TYPE
   SYNTAX     Unsigned32 (0..2147483647)
   ACCESS     read-only
   STATUS     obsolete
   DESCRIPTION
     "This variable represents an individual value for the
      atmIfVpcRxTdpTable."
::= { atmIfVpcRxTdpEntry 2 }

atmIfVpcTxQThreshTable OBJECT-TYPE
   SYNTAX     SEQUENCE OF AtmIfVpcTxQThreshEntry
   ACCESS     not-accessible
   STATUS     obsolete
   DESCRIPTION
     "This attribute is HISTORICAL. Please refer to the attribute of the 
      same name in the group AtmTmOper.
      
      This attribute indicates the queue limit and the discard thresholds 
      for the transmit queue of this connection. 
      
      The first element indicates the queue limit. Depending upon the 
      atmServiceCategory of the connection, the provisioned value of the 
      transmit queue limit is derived from the txQueueLimit attribute 
      under one of the subcomponents of the AtmIf CA component. If the 
      connection has traffic shaping disabled, then this attribute relates to 
      the common queue. If traffic shaping is enabled, then this attribute 
      relates to the per-VC queue.
      
      The second element is the threshold that marks the transition from 
      congestion state 1 to congestion state 0. This is the threshold at 
      which traffic with discard priority (DP) = 1 is discarded. This 
      threshold is set approximately at 90 percent of the first parameter, 
      the operational queue limit.
      
      The third element is the threshold that marks the transition from 
      congestion state 2 to congestion state 1. This is the threshold at 
      which traffic with DP = 2 is discarded. This threshold is set 
      approximately at 75 percent of the first parameter, the operational 
      queue limit.
      
      The fourth element is the threshold that marks the transition from 
      congestion state 3 to congestion state 2. This is the threshold at 
      which traffic with DP = 3 is discarded. This threshold is set 
      approximately at 35 percent of the first parameter, the operational 
      queue limit."
::= { atmIfVpc 352 }

atmIfVpcTxQThreshEntry OBJECT-TYPE
   SYNTAX     AtmIfVpcTxQThreshEntry
   ACCESS     not-accessible
   STATUS     obsolete
   DESCRIPTION
     "An entry in the atmIfVpcTxQThreshTable."
   INDEX {
      atmIfIndex,
      atmIfVpcIndex,
      atmIfVpcTxQThreshIndex }
::= { atmIfVpcTxQThreshTable 1 }

AtmIfVpcTxQThreshEntry ::= SEQUENCE {
   atmIfVpcTxQThreshIndex
      Integer32,
   atmIfVpcTxQThreshValue
      Unsigned32 }

atmIfVpcTxQThreshIndex OBJECT-TYPE
   SYNTAX     Integer32 (0..3)
   ACCESS     not-accessible
   STATUS     obsolete
   DESCRIPTION
     "This variable represents the atmIfVpcTxQThreshTable
      specific index for the atmIfVpcTxQThreshTable."
::= { atmIfVpcTxQThreshEntry 1 }

atmIfVpcTxQThreshValue OBJECT-TYPE
   SYNTAX     Unsigned32 (0..30720)
   ACCESS     read-only
   STATUS     obsolete
   DESCRIPTION
     "This variable represents an individual value for the
      atmIfVpcTxQThreshTable."
::= { atmIfVpcTxQThreshEntry 2 }

atmIfVpcFqpTable OBJECT-TYPE
   SYNTAX     SEQUENCE OF AtmIfVpcFqpEntry
   ACCESS     not-accessible
   STATUS     obsolete
   DESCRIPTION
     "This attribute is HISTORICAL. Please refer to the attribute of the 
      same name in the group AtmTmOper.
      
      This attribute is a vector of three elements that indicate the quality 
      of service parameters for the forward direction for this connection. 
      This attribute is used for SPVC and SVC connections on a PNNI 
      interface.
      
      The cdv element indicates the acceptable peak-to-peak Cell Delay 
      Variation (CDV) of real-time connections (CBR, and rt-VBR). 
      
      The ctd element indicates the acceptable maximum Cell Transfer 
      Delay (maxCtd) of real-time connections (CBR, and rt-VBR). 
      
      The clr element indicates the acceptable Cell Loss Ratio (CLR) of 
      CBR, rt-VBR, and nrt-VBR connections."
::= { atmIfVpc 357 }

atmIfVpcFqpEntry OBJECT-TYPE
   SYNTAX     AtmIfVpcFqpEntry
   ACCESS     not-accessible
   STATUS     obsolete
   DESCRIPTION
     "An entry in the atmIfVpcFqpTable."
   INDEX {
      atmIfIndex,
      atmIfVpcIndex,
      atmIfVpcFqpIndex }
::= { atmIfVpcFqpTable 1 }

AtmIfVpcFqpEntry ::= SEQUENCE {
   atmIfVpcFqpIndex
      INTEGER,
   atmIfVpcFqpValue
      Unsigned32 }

atmIfVpcFqpIndex OBJECT-TYPE
   SYNTAX     INTEGER  {
                 cdv(0),
                 ctd(1),
                 clr(2) }
   ACCESS     not-accessible
   STATUS     obsolete
   DESCRIPTION
     "This variable represents the atmIfVpcFqpTable
      specific index for the atmIfVpcFqpTable."
::= { atmIfVpcFqpEntry 1 }

atmIfVpcFqpValue OBJECT-TYPE
   SYNTAX     Unsigned32 (0..2147483647)
   ACCESS     read-only
   STATUS     obsolete
   DESCRIPTION
     "This variable represents an individual value for the
      atmIfVpcFqpTable."
::= { atmIfVpcFqpEntry 2 }

atmIfVpcBqpTable OBJECT-TYPE
   SYNTAX     SEQUENCE OF AtmIfVpcBqpEntry
   ACCESS     not-accessible
   STATUS     obsolete
   DESCRIPTION
     "This attribute is HISTORICAL. Please refer to the attribute of the 
      same name in the group AtmTmOper.
      
      This attribute is a vector of three elements that indicate the quality 
      of service parameters for the backward direction for this 
      connection. This attribute is used for SPVC and SVC connections 
      on a PNNI interface.
      
      The cdv element indicates the acceptable peak-to-peak Cell Delay 
      Variation (CDV) of real-time connections (CBR, and rt-VBR). 
      
      The ctd element indicates the acceptable maximum Cell Transfer 
      Delay (maxCtd) of real-time connections (CBR, and rt-VBR). 
      
      The clr element indicates the acceptable Cell Loss Ratio (CLR) of 
      CBR, rt-VBR, and nrt-VBR connections."
::= { atmIfVpc 358 }

atmIfVpcBqpEntry OBJECT-TYPE
   SYNTAX     AtmIfVpcBqpEntry
   ACCESS     not-accessible
   STATUS     obsolete
   DESCRIPTION
     "An entry in the atmIfVpcBqpTable."
   INDEX {
      atmIfIndex,
      atmIfVpcIndex,
      atmIfVpcBqpIndex }
::= { atmIfVpcBqpTable 1 }

AtmIfVpcBqpEntry ::= SEQUENCE {
   atmIfVpcBqpIndex
      INTEGER,
   atmIfVpcBqpValue
      Unsigned32 }

atmIfVpcBqpIndex OBJECT-TYPE
   SYNTAX     INTEGER  {
                 cdv(0),
                 ctd(1),
                 clr(2) }
   ACCESS     not-accessible
   STATUS     obsolete
   DESCRIPTION
     "This variable represents the atmIfVpcBqpTable
      specific index for the atmIfVpcBqpTable."
::= { atmIfVpcBqpEntry 1 }

atmIfVpcBqpValue OBJECT-TYPE
   SYNTAX     Unsigned32 (0..2147483647)
   ACCESS     read-only
   STATUS     obsolete
   DESCRIPTION
     "This variable represents an individual value for the
      atmIfVpcBqpTable."
::= { atmIfVpcBqpEntry 2 }


-- AtmIf/n Vpc/vpi VirtualPathDescriptor
-- The Vpd component contains provisioning information about its 
-- parent Vpc component.

atmIfVpcVpd OBJECT IDENTIFIER ::= { atmIfVpc 2 }



atmIfVpcVpdRowStatusTable OBJECT-TYPE
   SYNTAX     SEQUENCE OF AtmIfVpcVpdRowStatusEntry
   ACCESS     not-accessible
   STATUS     mandatory
   DESCRIPTION
     "This entry controls the addition and deletion of 
      atmIfVpcVpd components."
::= { atmIfVpcVpd 1 }

atmIfVpcVpdRowStatusEntry OBJECT-TYPE
   SYNTAX     AtmIfVpcVpdRowStatusEntry
   ACCESS     not-accessible
   STATUS     mandatory
   DESCRIPTION
     "A single entry in the table represents a single 
      atmIfVpcVpd component."
   INDEX {
      atmIfIndex,
      atmIfVpcIndex,
      atmIfVpcVpdIndex }
::= { atmIfVpcVpdRowStatusTable 1 }

AtmIfVpcVpdRowStatusEntry ::= SEQUENCE {
   atmIfVpcVpdRowStatus
      RowStatus,
   atmIfVpcVpdComponentName
      DisplayString,
   atmIfVpcVpdStorageType
      StorageType,
   atmIfVpcVpdIndex
      NonReplicated }

atmIfVpcVpdRowStatus OBJECT-TYPE
   SYNTAX     RowStatus 
   ACCESS     read-only
   STATUS     mandatory
   DESCRIPTION
     "This variable is used as the basis for SNMP naming of
      atmIfVpcVpd components.
      These components cannot be added nor deleted."
::= { atmIfVpcVpdRowStatusEntry 1 }

atmIfVpcVpdComponentName OBJECT-TYPE
   SYNTAX     DisplayString 
   ACCESS     read-only
   STATUS     mandatory
   DESCRIPTION
     "This variable provides the component's string name for
      use with the ASCII Console Interface"
::= { atmIfVpcVpdRowStatusEntry 2 }

atmIfVpcVpdStorageType OBJECT-TYPE
   SYNTAX     StorageType 
   ACCESS     read-only
   STATUS     mandatory
   DESCRIPTION
     "This variable represents the storage type value for the
      atmIfVpcVpd tables."
::= { atmIfVpcVpdRowStatusEntry 4 }

atmIfVpcVpdIndex OBJECT-TYPE
   SYNTAX     NonReplicated 
   ACCESS     not-accessible
   STATUS     mandatory
   DESCRIPTION
     "This variable represents the index for the atmIfVpcVpd tables."
::= { atmIfVpcVpdRowStatusEntry 10 }

atmIfVpcVpdLbkTable OBJECT-TYPE
   SYNTAX     SEQUENCE OF AtmIfVpcVpdLbkEntry
   ACCESS     not-accessible
   STATUS     mandatory
   DESCRIPTION
     "This group contains the provisionable loopback attributes for a Vcc, 
      Vpc, or Vpt component.
      
      Note that certain loopback requests may not be possible on a given 
      connection. In such cases, the corresponding operational loopback 
      attribute in the Status group of the Vcc, Vpc, or Vpt component is 
      set to notApplicable and the requested loopback is not performed.
      
      If loopbacks are provisioned to be on, and for any reason the 
      segment or end-to-end OAM loopback cells are not relayed, the 
      connection component becomes troubled, and user cell traffic may 
      be discarded. If loopbacks are provisioned to be on, all of the nodes 
      in the segment, and external networks which are in the end-to-end 
      connection must relay the OAM loopback cells."
::= { atmIfVpcVpd 100 }

atmIfVpcVpdLbkEntry OBJECT-TYPE
   SYNTAX     AtmIfVpcVpdLbkEntry
   ACCESS     not-accessible
   STATUS     mandatory
   DESCRIPTION
     "An entry in the atmIfVpcVpdLbkTable."
   INDEX {
      atmIfIndex,
      atmIfVpcIndex,
      atmIfVpcVpdIndex }
::= { atmIfVpcVpdLbkTable 1 }

AtmIfVpcVpdLbkEntry ::= SEQUENCE {
   atmIfVpcVpdSegLinkSideLoopback
      INTEGER,
   atmIfVpcVpdSegSwitchSideLoopback
      INTEGER,
   atmIfVpcVpdEndToEndLoopback
      INTEGER,
   atmIfVpcVpdLoopbackMonitoring
      INTEGER }

atmIfVpcVpdSegLinkSideLoopback OBJECT-TYPE
   SYNTAX     INTEGER  {
                 on(0),
                 off(1),
                 sameAsInterface(2) }
   ACCESS     read-write
   STATUS     mandatory
   DESCRIPTION
     "This attribute specifies whether link-side segment loopback 
      insertion should be performed on this connection. 
      
      When sameAsInterface is selected, the link-side segment loopback 
      insertion for the connection is based on the segLinkSideLoopback 
      attribute of the connection's parent AtmIf componentif the ATM 
      interface has link-side segment loopback insertion turned on, then 
      link-side segment loopback insertion is also on for the connection. 
      
      When on or off is selected, link-side segment loopback insertion is 
      turned on or off respectively for the connection regardless of the 
      provisioning of the parent AtmIf component.
      
      Note that link-side segment loopback insertion is not possible if the 
      connectionPointType attribute of the Vcc or Vpc component is 
      connectingPoint. Link-side segment loopback insertion is also not 
      possible if the distributionType of the Vcc is pointToMultipoint. In 
      such cases, the associated segLinkSideLoopbackState attribute 
      indicates notApplicable and link-side segment loopback insertion is 
      not performed. Link-side segment loopback insertion is always 
      possible on a Vpt."
   DEFVAL     { sameAsInterface }
::= { atmIfVpcVpdLbkEntry 10 }

atmIfVpcVpdSegSwitchSideLoopback OBJECT-TYPE
   SYNTAX     INTEGER  {
                 on(0),
                 off(1),
                 sameAsInterface(2) }
   ACCESS     read-write
   STATUS     mandatory
   DESCRIPTION
     "This attribute specifies whether switch-side segment loopback 
      insertion should be performed on this connection.
      
      When sameAsInterface is selected, the switch-side segment 
      loopback for the connection is based on the segSwitchSideLoopback 
      attribute of the connection's parent AtmIf componentif the ATM 
      interface has switch-side segment loopback insertion turned on, 
      then switch-side segment loopback insertion is also on for the 
      connection. 
      
      When on or off is selected, switch-side segment loopback insertion 
      is turned on or off respectively for the connection regardless of the 
      provisioning of the parent AtmIf component.
      
      Note that switch-side segment loopback insertion is not possible if 
      the connectionPointType attribute of the Vcc or Vpc component is 
      connectingPoint or connectionEndPoint. Switch-side segment 
      loopback insertion is also not possible if the distributionType of the 
      Vcc is pointToMultipoint In such cases, the associated 
      segSwitchSideLoopbackState attribute indicates notApplicable and 
      switch-side segment loopback insertion is not performed. Switch-
      side segment loopback is never possible on a Vpt."
   DEFVAL     { sameAsInterface }
::= { atmIfVpcVpdLbkEntry 20 }

atmIfVpcVpdEndToEndLoopback OBJECT-TYPE
   SYNTAX     INTEGER  {
                 on(0),
                 off(1),
                 sameAsInterface(2) }
   ACCESS     read-write
   STATUS     mandatory
   DESCRIPTION
     "This attribute specifies whether end-to-end loopback insertion 
      should be performed on this connection.
      
      When sameAsInterface is selected, the end-to-end loopback for the 
      connection is based on the endToEndLoopback attribute of the 
      connection's parent AtmIf componentif the ATM interface has 
      end-to-end loopback insertion turned on, then end-to-end loopback 
      insertion is also on for the connection. 
      
      When on or off is selected, end-to-end loopback insertion is turned 
      on or off respectively for the connection regardless of the 
      provisioning of the parent AtmIf component.
      
      Note that end-to-end loopback insertion is not possible if the 
      connectionPointType attribute of the Vcc or Vpc component is 
      connectingPoint or segmentEndPoint. End-to-end loopback 
      insertion is also not possible if the distributionType of the Vcc is 
      pointToMultipoint. In such cases, the associated 
      endToEndLoopbackState attribute indicates notApplicable and end-
      to-end loopback insertion is not performed. End-to-end loopback 
      insertion is always possible on a Vpt."
   DEFVAL     { sameAsInterface }
::= { atmIfVpcVpdLbkEntry 30 }

atmIfVpcVpdLoopbackMonitoring OBJECT-TYPE
   SYNTAX     INTEGER  {
                 on(0),
                 off(1),
                 sameAsInterface(2) }
   ACCESS     read-write
   STATUS     mandatory
   DESCRIPTION
     "This attribute specifies whether or not a connection monitors the 
      OAM stream for loopback cells. Currently this attributed is only 
      applied to Passport-specific trace cells and only affects 
      connectingPoints.
      
      When sameAsInterface is selected, the trace visibility for the 
      connection is based on the traceVisible attribute of the connection's 
      parent AtmIf componentif the ATM interface is trace visible, then 
      the connection is also trace visible. 
      
      When on or off is selected, the connection is nor isn't visible to 
      trace cells respectively for the connection regardless of the 
      provisioning of the parent AtmIf component.
      
      Note that trace visibility only affects connections whose 
      connectionPointType attribute of the Vcc or Vpc component is 
      connectingPoint. Trace visibility is also not possible if the 
      distributionType of the Vcc is pointToMultipoint."
   DEFVAL     { sameAsInterface }
::= { atmIfVpcVpdLbkEntry 1000 }

atmIfVpcVpdTrafficTable OBJECT-TYPE
   SYNTAX     SEQUENCE OF AtmIfVpcVpdTrafficEntry
   ACCESS     not-accessible
   STATUS     mandatory
   DESCRIPTION
     "This group contains traffic related provisionable attributes for the 
      Vcc and Vpc components. The attributes' operational values are 
      reflected in the Traffic group for these components. Changing any 
      of the attributes in this group causes a service interruption on the 
      Vcc or Vpc component."
::= { atmIfVpcVpd 110 }

atmIfVpcVpdTrafficEntry OBJECT-TYPE
   SYNTAX     AtmIfVpcVpdTrafficEntry
   ACCESS     not-accessible
   STATUS     mandatory
   DESCRIPTION
     "An entry in the atmIfVpcVpdTrafficTable."
   INDEX {
      atmIfIndex,
      atmIfVpcIndex,
      atmIfVpcVpdIndex }
::= { atmIfVpcVpdTrafficTable 1 }

AtmIfVpcVpdTrafficEntry ::= SEQUENCE {
   atmIfVpcVpdTxTrafficDescType
      INTEGER,
   atmIfVpcVpdTxQosClass
      INTEGER,
   atmIfVpcVpdFwdQosClass
      INTEGER,
   atmIfVpcVpdHoldingPriority
      INTEGER,
   atmIfVpcVpdRxTrafficDescType
      INTEGER,
   atmIfVpcVpdRxQosClass
      INTEGER,
   atmIfVpcVpdBwdQosClass
      INTEGER,
   atmIfVpcVpdAtmServiceCategory
      INTEGER,
   atmIfVpcVpdTrafficShaping
      INTEGER,
   atmIfVpcVpdUnshapedTransmitQueueing
      INTEGER,
   atmIfVpcVpdUsageParameterControl
      INTEGER,
   atmIfVpcVpdBearerClassBbc
      INTEGER,
   atmIfVpcVpdTransferCapabilityBbc
      INTEGER,
   atmIfVpcVpdClippingBbc
      INTEGER,
   atmIfVpcVpdBestEffort
      INTEGER,
   atmIfVpcVpdFwdFrameDiscard
      INTEGER,
   atmIfVpcVpdBwdFrameDiscard
      INTEGER }

atmIfVpcVpdTxTrafficDescType OBJECT-TYPE
   SYNTAX     INTEGER  {
                 n1(1),
                 n2(2),
                 n3(3),
                 n4(4),
                 n5(5),
                 n6(6),
                 n7(7),
                 n8(8),
                 n9(9) }
   ACCESS     read-write
   STATUS     obsolete
   DESCRIPTION
     "This attribute is migrated to the AtmTmProv group.
      
      This attribute specifies the type of traffic management which is 
      applied to the transmit direction of this connection as defined in the 
      ATM Forum. The txTrafficDescType determines the number and 
      meaning of the parameters in the txTrafficDescParm attribute."
   DEFVAL     { n1 }
::= { atmIfVpcVpdTrafficEntry 10 }

atmIfVpcVpdTxQosClass OBJECT-TYPE
   SYNTAX     INTEGER  {
                 unspecified(0),
                 constantBitRate(1),
                 variableBitRate(2),
                 connectionOriented(3),
                 connectionless(4) }
   ACCESS     read-write
   STATUS     obsolete
   DESCRIPTION
     "This attribute specifies the quality of service for the transmit 
      direction for this connection.
      
      The constantBitRate class refers to traffic offered on services such 
      as a constant bit rate video service. This traffic is highest priority.
      
      The variableBitRate class refers to traffic offered on services such 
      as packetized audio and video.
      
      The connectionOriented class refers to connection-oriented traffic 
      such as Frame Relay or X.25 traffic. 
      
      The connectionless traffic refers to traffic offered through 
      connectionless trunks such as certain LAN protocols.
      
      The unspecified class supports a 'best effort' type of service, where 
      there is a minimum guarantee of bandwidth. This traffic is lowest 
      priority.
      
      This attribute is obsolete. The value is migrated into 
      atmServiceCategory. The atmServiceCategory applies in both 
      transmit and receive directions.
      
      unspecified maps to unspecifiedBitRate;
      constantBitRate maps to constantBitRate;
      variableBitRate maps to variableBitRateRt;
      connectionOriented maps to variableBitRateNrt
      connectionless maps to variableBitRateNrt"
   DEFVAL     { connectionOriented }
::= { atmIfVpcVpdTrafficEntry 20 }

atmIfVpcVpdFwdQosClass OBJECT-TYPE
   SYNTAX     INTEGER  {
                 n0(0),
                 n1(1),
                 n2(2),
                 n3(3),
                 n4(4) }
   ACCESS     read-write
   STATUS     obsolete
   DESCRIPTION
     "This attribute is migrated to the AtmTmProv group.
      
      This attribute specifies the quality of service for the forward 
      direction for this connection. This attribute is only used for SPVC 
      connections.
      
      Class 1 supports a QOS that meets Service Class A performance 
      requirements (Circuit emulation, constant bit rate video).
      
      Class 2 supports a QOS that meets Service Class B performance 
      requirements (Variable bit rate audio and video).
      
      Class 3 supports a QOS that meets Service Class C performance 
      requirements (Connection-Oriented Data Transfer).
      
      Class 4 supports a QOS that meets Service Class D performance 
      requirements (Connectionless Data Transfer).
      
      Class 0 is the unspecified bit rate QOS class; no objective is 
      specified for the performance parameters."
   DEFVAL     { n0 }
::= { atmIfVpcVpdTrafficEntry 21 }

atmIfVpcVpdHoldingPriority OBJECT-TYPE
   SYNTAX     INTEGER  {
                 n0(0),
                 n1(1),
                 n2(2),
                 n3(3),
                 n4(4) }
   ACCESS     read-write
   STATUS     obsolete
   DESCRIPTION
     "This attribute is migrated to the AtmTmProv group.
      
      This attribute specifies the holding priority of this connection. In a 
      situation where the link bandwidth fluctuates, such as over an IMA 
      link, holding priority is used to determine which connections are 
      held and which are released. Holding priority 4 connections are the 
      first to be released. Holding priority 0 connections are the last to be 
      released. This value provisioned in the Vcd or Vpd may be 
      overridden by certain applications, for example Vcc Test, which run 
      over this connection. The default holding priority for a provisioned 
      connection is higher then default holding priorities for dynamic 
      (SVC) connections."
   DEFVAL     { n2 }
::= { atmIfVpcVpdTrafficEntry 25 }

atmIfVpcVpdRxTrafficDescType OBJECT-TYPE
   SYNTAX     INTEGER  {
                 n1(1),
                 n2(2),
                 n3(3),
                 n4(4),
                 n5(5),
                 n6(6),
                 n7(7),
                 n8(8),
                 sameAsTx(15) }
   ACCESS     read-write
   STATUS     obsolete
   DESCRIPTION
     "This attribute is migrated to the AtmTmProv group.
      
      This attribute specifies the type of traffic management which is 
      applied to the receive direction of this connection as defined in the 
      ATM Forum. The rxTrafficDescType determines the number and 
      meaning of the parameters in the rxTrafficDescParm attribute
      
      When sameAsTx is selected, the rxTrafficDescType as well as the 
      rxTrafficDescParm are taken from the transmit values."
   DEFVAL     { sameAsTx }
::= { atmIfVpcVpdTrafficEntry 30 }

atmIfVpcVpdRxQosClass OBJECT-TYPE
   SYNTAX     INTEGER  {
                 unspecified(0),
                 constantBitRate(1),
                 variableBitRate(2),
                 connectionOriented(3),
                 connectionless(4),
                 sameAsTx(15) }
   ACCESS     read-write
   STATUS     obsolete
   DESCRIPTION
     "This attribute specifies the quality of service for the receive 
      direction for this connection.
      
      The constantBitRate class refers to traffic offered on services such 
      as a constant bit rate video service. 
      
      The variableBitRate class refers to traffic offered on services such 
      as packetized audio and video. 
      
      The connectionOriented class refers to connection-oriented traffic.
      
      The connectionless traffic refers to traffic offered through 
      connectionless trunks. 
      
      The unspecified class supports a 'best effort' type of service, where 
      there is a minimum guarantee of bandwidth. 
      
      The sameAsTx selection sets the receive quality of service to be the 
      same as the transmit quality of service.
      
      This attribute is obsolete. The value of txQosClass is migrated into 
      atmServiceCategory. The value of this attribute is ignored. 
      AtmServiceCategory applies in both transmit and receive directions."
   DEFVAL     { sameAsTx }
::= { atmIfVpcVpdTrafficEntry 40 }

atmIfVpcVpdBwdQosClass OBJECT-TYPE
   SYNTAX     INTEGER  {
                 n0(0),
                 n1(1),
                 n2(2),
                 n3(3),
                 n4(4),
                 sameAsFwd(15) }
   ACCESS     read-write
   STATUS     obsolete
   DESCRIPTION
     "This attribute is migrated to the AtmTmProv group.
      
      This attribute specifies the quality of service for the backward 
      direction for this connection. This attribute is only used for SPVC 
      connections.
      
      Class 1 supports a QOS that meets Service Class A performance 
      requirements (Circuit emulation, constant bit rate video).
      
      Class 2 supports a QOS that meets Service Class B performance 
      requirements (Variable bit rate audio and video).
      
      Class 3 supports a QOS that meets Service Class C performance 
      requirements (Connection-Oriented Data Transfer).
      
      Class 4 supports a QOS that meets Service Class D performance 
      requirements (Connectionless Data Transfer).
      
      Class 0 is the unspecified bit rate QOS class; no objective is 
      specified for the performance parameters.
      
      The sameAsFwd selection sets the backward quality of service to 
      be the same as the forward quality of service."
   DEFVAL     { sameAsFwd }
::= { atmIfVpcVpdTrafficEntry 41 }

atmIfVpcVpdAtmServiceCategory OBJECT-TYPE
   SYNTAX     INTEGER  {
                 unspecifiedBitRate(0),
                 constantBitRate(1),
                 rtVariableBitRate(2),
                 nrtVariableBitRate(3),
                 derivedFromBBC(15) }
   ACCESS     read-write
   STATUS     obsolete
   DESCRIPTION
     "This attribute is migrated to the AtmTmProv group.
      
      This attribute specifies the ATM service category for both directions 
      of the connection. 
      
      The value derivedFromBBC may only be used if the SrcPvc 
      component is provisioned under this Vcc.Otherwise a specific ATM 
      service category must be specified. 
      
      If this attribute is set to derivedFromBBC, the Broadband Bearer 
      Capability (BBC) and bestEffort attributes are used to determine the 
      atmServiceCategory of this connection. 
      
      If this attribute is set to other than derivedFromBBC, the value of 
      this attribute is used to override the provisioned BBC Information 
      Element parameters. In those cases, the BBC attributes are not used. 
      
      The constantBitRate service category is intended for real time 
      applications, that is those requiring tightly constrained delay and 
      delay variation, as would be appropriate for voice and video 
      applications. The consistent availability of a fixed quantity of 
      bandwidth is considered appropriate for CBR service. Cells which 
      are delayed beyond the value specified by Cell Transfer Delay are 
      assumed to be of significantly reduce value to the application.
      
      The rtVariableBitRate service category is intended for real time 
      applications, that is those requiring tightly constrained delay and 
      delay variation, as would be appropriate for voice and video 
      applications. Sources are expected to transmit at a rate which varies 
      with time. Equivalently, the source can be described as 'bursty'. 
      Cells which are delayed beyond the value specified by CTD are 
      assumed to be of significantly reduced value to the application. Real 
      time VBR service may support statistical multiplexing of real time 
      sources.
      
      The nrtVariableBitRate service category is intended for non-real 
      time applications which have bursty traffic characteristics and which 
      can be characterized in terms of a PCR, SCR, and MBS. For those 
      cells which are transferred within the traffic contract, the application 
      expects a low cell loss ratio. For all connections, it expects a bound 
      on the mean cell transfer delay. Non-real time VBR service may 
      support statistical multiplexing of connections.
      
      The unspecifiedBitRate service is intended for non-real time 
      applications; that is, those not requiring tightly constrained delay 
      and delay variation. UBR sources are expected to be bursty. UBR 
      service supports a high degree of statistical multiplexing among 
      sources. UBR service does not specify traffic related service 
      guarantees. No numerical commitments are made with respect to 
      the cell loss ratio experienced by a UBR connection, or as to the 
      cell transfer delay experienced by cells on the connection."
   DEFVAL     { unspecifiedBitRate }
::= { atmIfVpcVpdTrafficEntry 42 }

atmIfVpcVpdTrafficShaping OBJECT-TYPE
   SYNTAX     INTEGER  {
                 disabled(1),
                 sameAsInterface(2) }
   ACCESS     read-write
   STATUS     obsolete
   DESCRIPTION
     "This attribute is migrated to the AtmTmProv group.
      
      This attribute specifies whether this connection uses traffic shaping 
      when transmitting traffic to the ATM interface.
      
      When sameAsInterface is selected, traffic shaping for the 
      connection is based on the trafficShaping attribute of the 
      connection's parent AtmIf componentif the ATM interface has 
      traffic shaping enabled, then traffic shaping is enabled for the 
      connection. Note that enabling traffic shaping may have no effect 
      under certain cases. These cases are listed in the description of the 
      trafficShaping operational attribute, which is under the Vcc and Vpc 
      components.
      
      When disabled is selected, traffic shaping for this connection is 
      disabled regardless of the provisioning of the parent AtmIf 
      component."
   DEFVAL     { sameAsInterface }
::= { atmIfVpcVpdTrafficEntry 50 }

atmIfVpcVpdUnshapedTransmitQueueing OBJECT-TYPE
   SYNTAX     INTEGER  {
                 common(1),
                 sameAsInterface(3) }
   ACCESS     read-write
   STATUS     obsolete
   DESCRIPTION
     "This attribute is migrated to the AtmTmProv group.
      
      This attribute only applies when this connection is unshaped. This 
      attribute defines the transmit queueing method for this connection if 
      it is unshaped. Refer to the unshapedTransmitQueueing attribute 
      under the AtmIf for more details on the meaning of this attribute. 
      
      When this attribute is set to sameAsInterface, the value from the 
      AtmIf is used. 
      
      When this attribute is set to common, transmit traffic on this 
      unshaped connection is destined for the common queue."
   DEFVAL     { sameAsInterface }
::= { atmIfVpcVpdTrafficEntry 60 }

atmIfVpcVpdUsageParameterControl OBJECT-TYPE
   SYNTAX     INTEGER  {
                 disabled(1),
                 sameAsInterface(2) }
   ACCESS     read-write
   STATUS     obsolete
   DESCRIPTION
     "This attribute is migrated to the AtmTmProv group.
      
      This attribute specifies whether this connection enforces usage 
      parameter control when receiving traffic from the ATM interface.
      
      When sameAsInterface is selected, UPC for the connection is 
      based on the usageParameterControl attribute of the connection's 
      parent AtmIf componentif the ATM interface has UPC enabled, 
      then UPC is enabled for the connection. Note that enabling UPC 
      may have no effect under certain cases. These cases are listed in the 
      description of the usageParameterControl operational attribute, 
      which is under the Vcc and Vpc components.
      
      When disabled is selected, UPC for this connection is disabled 
      regardless of the provisioning of the parent AtmIf component."
   DEFVAL     { sameAsInterface }
::= { atmIfVpcVpdTrafficEntry 70 }

atmIfVpcVpdBearerClassBbc OBJECT-TYPE
   SYNTAX     INTEGER  {
                 a(1),
                 c(3),
                 x(16),
                 vp(24),
                 derivedFromServiceCategory(31) }
   ACCESS     read-write
   STATUS     obsolete
   DESCRIPTION
     "This attribute is migrated to the AtmTmProv group.
      
      This attribute specifies the bearer capability. This attribute is only 
      used for SPVC and SPVP connections. It is one of the Broadband 
      Bearer Capability (BBC) attributes. The purpose of the BBC 
      information element is to indicate a requested broadband 
      connection-oriented bearer service to be provided by the network.
      
      The value derivedFromServiceCategory specifies that the actual 
      value which is used for this connection is derived from the value of 
      the atmServiceCategory. Either, this attribute must be set to 
      derivedFromServiceCategory, or the atmServiceCategory attribute 
      must be set to derivedFromBBC, but not both.
      
      Class a service is a connection-oriented, constant bit rate ATM 
      transport service. Class a service has end to end timing 
      requirements and may require stringent cell loss, cell delay and cell 
      delay variation performance.When a is set, the user is requesting 
      more than an ATM only service. The network may look at the AAL 
      to provide interworking based upon its contents. 
      
      Class c service is a connection-oriented, variable bit rate ATM 
      transport service. Class c service has no end-to-end timing 
      requirements. When c is set, the user is requesting more than an 
      ATM only service. The network interworking function may look at 
      the AAL and provide service based on it.
      
      Class x service is a connection-oriented ATM transport service 
      where the AAL, trafficType (vbr or cbr) and timing requirements 
      are user defined (that is, transparent to the network).When x is set 
      the user is requesting an ATM only service from the network.
      
      Class vp service is used to specify a transparent VP service. When 
      the value of this attribute is vp, the user is requesting an ATM only 
      service from the network. In this case, the network shall not process 
      any higher layer protocol. This service differs from class x service 
      in that with the class vp service both the VCI field (except or VCI 
      values 0, 3, 4, and 6 through 15) and Payload Type field are 
      transported transparently by the network. This attribute value is 
      only applicable to SPVP connections."
   DEFVAL     { derivedFromServiceCategory }
::= { atmIfVpcVpdTrafficEntry 71 }

atmIfVpcVpdTransferCapabilityBbc OBJECT-TYPE
   SYNTAX     INTEGER  {
                 n0(0),
                 n1(1),
                 n2(2),
                 n5(5),
                 n8(8),
                 n9(9),
                 n10(10),
                 notApplicable(30),
                 derivedFromServiceCategory(31) }
   ACCESS     read-write
   STATUS     obsolete
   DESCRIPTION
     "This attribute is migrated to the AtmTmProv group.
      
      This attribute specifies the transfer capability for this connection. 
      Uni 3.0/3.1 traffic type and end-to-end timing parameters are 
      mapped into this parameter as follows:
      <transferCapability: TrafficType, Timing>
      0: NoIndication, NoIndication
      1: NoIndication, yes
      2: NoIndication, no
      5: CBR, yes
      8: VBR, NoIndication
      9: VBR, yes
      10: VBR, no
      
      NotApplicable specifies that the user does not want to specify the 
      transfer capability.
      
      The CBR traffic type refers to traffic offered on services such as a 
      constant bit rate video service or a circuit emulation.
      
      The VBR traffic type refers to traffic offered on services such as 
      packetized audio and video, or data.
      
      The value no indication for traffic type is used if the user has not set 
      the traffic type; similarly for end-to-end timing.
      
      The value yes for end-to-end timing indicates that end-to-end 
      timing is required.
      
      The value no for end-to-end timing indicates that end-to-end timing 
      is not required.
      
      The value derivedFromServiceCategory specifies that the actual 
      value which is used for this connection is derived from the value of 
      the atmServiceCategory. Either, this attribute must be set to 
      derivedFromServiceCategory, or the atmServiceCategory attribute 
      must be set to derivedFromBBC, but not both."
   DEFVAL     { derivedFromServiceCategory }
::= { atmIfVpcVpdTrafficEntry 72 }

atmIfVpcVpdClippingBbc OBJECT-TYPE
   SYNTAX     INTEGER  {
                 no(0),
                 yes(1) }
   ACCESS     read-write
   STATUS     obsolete
   DESCRIPTION
     "This attribute is migrated to the AtmTmProv group.
      
      This attribute specifies the value for the clipping susceptibility 
      parameter in the BBC Information Element. This attribute is only 
      used for SPVC connections. It is one of the Broadband Bearer 
      Capability attributes.
      
      Clipping is an impairment in which the first fraction of a second of 
      information to be transferred is lost. It occurs after a call is 
      answered and before an associated connection is switched through."
   DEFVAL     { no }
::= { atmIfVpcVpdTrafficEntry 74 }

atmIfVpcVpdBestEffort OBJECT-TYPE
   SYNTAX     INTEGER  {
                 indicated(0),
                 notIndicated(1),
                 derivedFromServiceCategory(15) }
   ACCESS     read-write
   STATUS     obsolete
   DESCRIPTION
     "This attribute is migrated to the AtmTmProv group.
      
      This attribute specifies the value of the best effort parameter in the 
      ATM Traffic Descriptor Information Element. This attribute is only 
      used for Soft PVC connections. It is one of the Broadband Bearer 
      Capability attributes.
      
      The value indicated implies that the quality of service for this 
      connection is not guaranteed.
      
      The value notIndicated implies that the quality of service for this 
      connection is guaranteed.
      
      The value derivedFromServiceCategory specifies that the actual 
      value which is used for this connection is derived from the value of 
      the atmServiceCategory. Either, this attribute must be set to 
      derivedFromServiceCategory, or the atmServiceCategory attribute 
      must be set to derivedFromBBC, but not both."
   DEFVAL     { derivedFromServiceCategory }
::= { atmIfVpcVpdTrafficEntry 75 }

atmIfVpcVpdFwdFrameDiscard OBJECT-TYPE
   SYNTAX     INTEGER  {
                 notIndicated(0),
                 indicated(1) }
   ACCESS     read-write
   STATUS     obsolete
   DESCRIPTION
     "This attribute specifies the activation of frame discard functionality 
      in the forward data direction, at relay points, for this connection. It 
      applies to each hop of the connection. Frame discard functions 
      should not be requested if this connection is not transferring frame 
      (AAL5) traffic. Setting the value to indicated for any other traffic 
      type results in all traffic being discarded.
      
      If this connection point is a permanent (provisioned) VCC mid-
      point, this attribute specifies whether the Partial Packet 
      Discard (PPD) function is to be enabled or disabled in the transmit 
      direction at this connecting point. The PPD function allows the 
      connecting point to discard the remainder of a cell-forwarded AAL5 
      frame if one cell of this frame has been discarded. The PPD 
      function increases the 'goodput' of the link, since cells which are 
      only going to be discarded by the AAL5 reassembly are not 
      transmitted.
      
      At a permanent VCC connecting point which is not a connection 
      endpoint, when this attribute is set to indicated, the PPD function is 
      applied to transmit traffic at this connecting point. It should not be 
      indicated for connections whose end points are not performing 
      AAL5 segmentation and reassembly. When this attribute is set to 
      notIndicated, the PPD feature is not applied to transmit traffic at 
      this connecting point.
      
      At a SPVC origin on a PNNI interface, a value of indicated 
      specifies that frame discard is requested in the forward direction. 
      The frame discard function for SPVCs consists of PPD at the SPVC 
      origin and at all intermediate connecting points. When this attribute 
      is set to notIndicated, forward frame discard is not requested in the 
      SPVC call setup. Thus PPD is not enabled at the SPVC origin nor at 
      any intermediate connecting point.
      
      At all points along a VPC, this setting is ignored.
      
      At a permanent VCC connection endpoint, this value is ignored. If 
      AAL5 segmentation and reassembly has been requested, PPD and 
      Early Packet Discard (EPD) are automatically enabled.
      
      This attribute has been migrated to txFrameDiscard."
   DEFVAL     { notIndicated }
::= { atmIfVpcVpdTrafficEntry 76 }

atmIfVpcVpdBwdFrameDiscard OBJECT-TYPE
   SYNTAX     INTEGER  {
                 notIndicated(0),
                 indicated(1) }
   ACCESS     read-write
   STATUS     obsolete
   DESCRIPTION
     "This attribute specifies the activation of frame discard functionality 
      in the backward data direction, at relay points, for this connection. 
      It applies to each hop of the connection. Frame discard functions 
      should not be requested if this connection is not transferring frame 
      (AAL5) traffic. Setting the value to indicated for any other traffic 
      type results in all traffic being discarded.
      
      If this connection point is a permanent (provisioned) VCC mid-
      point, this attribute specifies whether the Partial Packet Discard 
      (PPD) function is to be enabled or disabled in the receive direction 
      at this connecting point. The PPD function allows the connecting 
      point to discard the remainder of a cell-forwarded AAL5 frame if 
      one cell of this frame has been discarded. The PPD function 
      increases the 'goodput' of the link, since cells which are only going 
      to be discarded by the AAL5 reassembly are not received.
      
      At a permanent VCC connecting point which is not a connection 
      endpoint, when this attribute is set to indicated, the PPD function is 
      applied to receive traffic at this connecting point. It should not be 
      indicated for connections whose end points are not performing 
      AAL5 segmentation and reassembly. When this attribute is set to 
      notIndicated, the PPD feature is not applied to receive traffic at this 
      connecting point.
      
      At a SPVC origin on a PNNI interface, a value of indicated 
      specifies that frame discard is requested in the backward direction. 
      The frame discard function for SPVCs consists of PPD at the SPVC 
      origin and at all intermediate connecting points. When this attribute 
      is set to notIndicated, backwards frame discard is not requested in 
      the SPVC call setup. Thus PPD is not enabled at the SPVC origin 
      nor at any intermediate connecting point.
      
      At all points along a VPC, this setting is ignored.
      
      At a permanent VCC connection endpoint, this value is ignored. If 
      AAL5 segmentation and reassembly has been requested, PPD and 
      Early Packet Discard (EPD) are automatically enabled.
      
      This attribute has been migrated to rxFrameDiscard."
   DEFVAL     { notIndicated }
::= { atmIfVpcVpdTrafficEntry 77 }

atmIfVpcVpdAcctTable OBJECT-TYPE
   SYNTAX     SEQUENCE OF AtmIfVpcVpdAcctEntry
   ACCESS     not-accessible
   STATUS     mandatory
   DESCRIPTION
     "This group contains the provisionable ATM accounting attributes 
      for a Vcc, Vpc, or Vpt component."
::= { atmIfVpcVpd 111 }

atmIfVpcVpdAcctEntry OBJECT-TYPE
   SYNTAX     AtmIfVpcVpdAcctEntry
   ACCESS     not-accessible
   STATUS     mandatory
   DESCRIPTION
     "An entry in the atmIfVpcVpdAcctTable."
   INDEX {
      atmIfIndex,
      atmIfVpcIndex,
      atmIfVpcVpdIndex }
::= { atmIfVpcVpdAcctTable 1 }

AtmIfVpcVpdAcctEntry ::= SEQUENCE {
   atmIfVpcVpdCorrelationTag
      AsciiString }

atmIfVpcVpdCorrelationTag OBJECT-TYPE
   SYNTAX     AsciiString (SIZE (0..32))
   ACCESS     read-write
   STATUS     mandatory
   DESCRIPTION
     "This attribute specifies a unique indentifier for each end of a PVC. It 
      that may be used by downstream processing systems to correlate 
      accounting records issued at different nodes in the network. The 
      attribute can be up to 32 bytes long. If it is less than 32 bytes, it is 
      zero filled on the right to create a 32 byte value. The resulting value 
      is recorded in the attribute callConnId for this PVC's ATM 
      accounting records.
      If the attribute is a null string then this PVC does not have any 
      accounting records generated for it."
   DEFVAL     { ''H }  -- ""
::= { atmIfVpcVpdAcctEntry 10 }

atmIfVpcVpdTxTdpTable OBJECT-TYPE
   SYNTAX     SEQUENCE OF AtmIfVpcVpdTxTdpEntry
   ACCESS     not-accessible
   STATUS     obsolete
   DESCRIPTION
     "This attribute is migrated to the AtmTmProv group.
      
      This attribute is a vector of five traffic parameters whose meanings 
      are defined by the txTrafficDescType attribute. The values of peak 
      cell rate (PCR), sustained cell rate (SCR) and requested shaping rate 
      are expressed in cell/s. Maximum burst size (MBS) is expressed in 
      cells. CDVT is expressed in microseconds. The values of PCR, 
      SCR, MBS and CDVT are used for connection admission control 
      (CAC). The value of CDVT is only used for connections where the 
      atmServiceCategory is constantBitRate. For all other values of 
      atmServiceCategory, CDVT is ignored. The values of PCR, SCR 
      and requested shaping rate are used to determine the actual shaping 
      rate where traffic shaping is enabled.
      
      When txTrafficDescType is 1 or 2, all of the parameters must be set 
      to zero.
      
      When txTrafficDescType is 3, parameter 1 represents the PCR for 
      CLP equal to 0 and 1 traffic; parameter 4 represents the CDVT; and 
      parameter 5 represents the requested shaping rate. A non-zero value 
      in parameter 5 overrides any value in parameter 1. This result is 
      used as the PCR. Parameter 1 must be non-zero. Parameters 2 and 3 
      must be zero.
      
      When txTrafficDescType is 4, parameter 1 represents the PCR for 
      CLP equal to 0 and 1 traffic with cell discard; parameter 2 
      represents the PCR for CLP equal to 0 traffic; parameter 4 
      represents the CDVT; and parameter 5 represents the requested 
      shaping rate. A non-zero value in parameter 5 overrides any value in 
      parameter 1. This result is used as the PCR. Parameter 1 must be 
      greater than or equal to parameter 2. Parameters 1 and 2 must be 
      non-zero. Parameter 3 must be zero.
      
      When txTrafficDescType is 5, parameter 1 represents the PCR for 
      CLP equal to 0 and 1 traffic with cell tagging; parameter 2 
      represents the PCR for CLP equal to 0 traffic; parameter 4 
      represents the CDVT; and parameter 5 represents the requested 
      shaping rate. A non-zero value in parameter 5 overrides any value in 
      parameter 1. This result is used as the PCR. Parameter 1 must be 
      greater than or equal to parameter 2. Parameters 1 and 2 must be 
      non-zero. Parameter 3 must be zero.
      
      When txTrafficDescType is 6, parameter 1 represents the PCR for 
      CLP equal to 0 and 1 traffic; parameter 2 represents the SCR for 
      CLP equal to 0 and 1 traffic; parameter 3 represents the MBS for 
      CLP equal to 0 and 1 traffic; parameter 4 represents the CDVT; and 
      parameter 5 represents the requested shaping rate. A non-zero value 
      in parameter 5 overrides any value in parameter 1. This result is 
      used as the PCR. Parameters 1, 2 and 3 must be non-zero. 
      Parameter 1 must be greater than or equal to parameter 2. Parameter 
      5, must either be zero (unused) or greater than or equal to parameter 
      2.
      
      When txTrafficDescType is 7, parameter 1 represents the PCR for 
      CLP equal to 0 and 1 traffic; parameter 2 represents the SCR for 
      CLP equal to 0 with cell discard; parameter 3 represents the MBS 
      for CLP equal to 0 traffic; parameter 4 represents the CDVT; and 
      parameter 5 represents the requested shaping rate. A non-zero value 
      in parameter 5 overrides any value in parameter 1. This result is 
      used as the PCR. Parameters 1, 2 and 3 must be non-zero. 
      Parameter 1 must be greater than or equal to parameter 2. Parameter 
      5, must either be zero (unused) or greater than or equal to parameter 
      2.
      
      When txTrafficDescType is 8, parameter 1 represents the PCR for 
      CLP equal to 0 and 1 traffic; parameter 2 represents the SCR for 
      CLP equal to 0 traffic with cell tagging; parameter 3 represents the 
      MBS for CLP equal to 0 traffic; parameter 4 represents the CDVT; 
      and parameter 5 represents the requested shaping rate. A non-zero 
      value in parameter 5 overrides any value in parameter 1. This result 
      is used as the PCR. Parameters 1, 2 and 3 must be non-zero. 
      Parameter 1 must be greater than or equal to parameter 2. Parameter 
      5, must either be zero (unused) or greater than or equal to parameter 
      2.
      
      Whenever it is valid for PCR to be specified, parameter 5 may also 
      be used to specify a requested shaping rate. A non-zero value in 
      parameter 5 overrides the value in parameter 1 and is used as the 
      peak cell rate in calculations of CAC and shaping rate.
      
      For txTrafficDescType 3, 4 and 5, the transmit traffic is shaped at 
      the next rate less than the PCR. 
      
      For txTrafficDescType 6, 7 and 8, the transmit traffic is shaped at 
      the highest available rate which is between PCR and SCR. 
      However, if there is no available shaping rate between PCR and 
      SCR, traffic is shaped at the next rate above the PCR."
::= { atmIfVpcVpd 297 }

atmIfVpcVpdTxTdpEntry OBJECT-TYPE
   SYNTAX     AtmIfVpcVpdTxTdpEntry
   ACCESS     not-accessible
   STATUS     obsolete
   DESCRIPTION
     "An entry in the atmIfVpcVpdTxTdpTable."
   INDEX {
      atmIfIndex,
      atmIfVpcIndex,
      atmIfVpcVpdIndex,
      atmIfVpcVpdTxTdpIndex }
::= { atmIfVpcVpdTxTdpTable 1 }

AtmIfVpcVpdTxTdpEntry ::= SEQUENCE {
   atmIfVpcVpdTxTdpIndex
      Integer32,
   atmIfVpcVpdTxTdpValue
      Unsigned32 }

atmIfVpcVpdTxTdpIndex OBJECT-TYPE
   SYNTAX     Integer32 (1..5)
   ACCESS     not-accessible
   STATUS     obsolete
   DESCRIPTION
     "This variable represents the atmIfVpcVpdTxTdpTable
      specific index for the atmIfVpcVpdTxTdpTable."
::= { atmIfVpcVpdTxTdpEntry 1 }

atmIfVpcVpdTxTdpValue OBJECT-TYPE
   SYNTAX     Unsigned32 (0..2147483647)
   ACCESS     read-write
   STATUS     obsolete
   DESCRIPTION
     "This variable represents an individual value for the
      atmIfVpcVpdTxTdpTable."
::= { atmIfVpcVpdTxTdpEntry 2 }

atmIfVpcVpdRxTdpTable OBJECT-TYPE
   SYNTAX     SEQUENCE OF AtmIfVpcVpdRxTdpEntry
   ACCESS     not-accessible
   STATUS     obsolete
   DESCRIPTION
     "This attribute is migrated to the AtmTmProv group.
      
      This attribute is a vector of four traffic parameters whose meanings 
      are defined by the rxTrafficDescType attribute. The values of peak 
      cell rate (PCR) and sustained cell rate (SCR) are expressed in 
      cell/s. Maximum burst size (MBS) is expressed in cells. The value 
      of CDVT is expressed in microseconds. The values of PCR, SCR, 
      MBS and CDVT are used for usage parameter control (UPC).
      
      When rxTrafficDescType is 1 or 2, all of the parameters must be set 
      to zero (unused).
      
      When rxTrafficDescType is 3, parameter 1 represents the PCR for 
      CLP equal to 0 and 1 traffic. Parameter 1 must be non-zero. 
      Parameters 2 and 3 must be set to zero (unused).
      
      When rxTrafficDescType is 4, parameter 1 represents the PCR for 
      CLP equal to 0 and 1 traffic; parameter 2 represents the PCR for 
      CLP equal to 0 traffic with cell discard. Parameters 1 and 2 must be 
      non-zero. Parameter 3 must be set to zero (unused). Parameter 1 
      must be greater than or equal to parameter 2.
      
      When rxTrafficDescType is 5, parameter 1 represents the PCR for 
      CLP equal to 0 and 1 traffic; parameter 2 represents the PCR for 
      CLP equal to 0 traffic with cell tagging. Parameters 1 and 2 must be 
      non-zero. Parameter 3 must be set to zero (unused). Parameter 1 
      must be greater than or equal to parameter 2.
      
      When rxTrafficDescType is a 6, parameter 1 represents the PCR for 
      CLP equal to 0 and 1 traffic; parameter 2 represents the SCR for 
      CLP equal to 0 and 1 traffic; parameter 3 represents the MBS for 
      CLP equal to 0 and 1 traffic. Parameters 1, 2 and 3 must be non-
      zero. Parameter 1 must be greater than or equal to Parameter 2. 
      
      When rxTrafficDescType is 7, parameter 1 represents the PCR for 
      CLP equal to 0 and 1 traffic; parameter 2 represents the SCR for 
      CLP equal to 0 traffic with cell discard; parameter 3 represents the 
      MBS for CLP equal to 0 traffic. Parameters 1, 2 and 3 must be non-
      zero. Parameter 1 must be greater than or equal to parameter 2. 
      
      When rxTrafficDescType is 8, parameter 1 represents the PCR for 
      CLP equal to 0 and 1 traffic; parameter 2 represents the SCR for 
      CLP equal to 0 traffic with cell tagging; parameter 3 represents the 
      MBS for CLP equal to 0 traffic. Parameter 1, 2 and 3 must be non-
      zero. Parameter 1 must be greater than or equal to parameter 2.
      
      When rxTrafficDescType is any value from 3 through 8, parameter 
      4 represents the CDVT. If this value is zero, the CDVT is taken 
      from the ConnectionAdministrator defaults for the particular 
      atmServiceCategory of this connection.
      
      When rxTrafficDescriptorType is 3 through 8, there are certain 
      extreme combinations of rxTrafficDescParm which are outside the 
      capabilities of the UPC hardware. The check prov command detects 
      such cases and generates an error message. If this happens, adjust 
      the parameters until they fall within the supported limits. 
      
      To calculate the limits, use the following formulae:
      I1 = 1 000 000 000 / PCR
      L1 = CDVT * 1000
      I2 = 1 000 000 000 / SCR
      L2 = CDVT + (MBS - 1) * (I2 - I1)
      I1 and I2 must be less than or equal to 335 523 840. I1 + L1 must 
      be less than or equal to 1 342 156 800. I2 + L2 must be less than or 
      equal to 1 342 156 800. Note that I2 and L2 only apply when the 
      rxTrafficDescriptorType is 6 through 8.
      
      If the values of I1, L1, I2 or L2 are closer to the limits described 
      above, a further restriction applies. Specifically, if either:
      I1 > 41 940 480 or
      I2 > 41 940 480 or
      I1 + L1 > 167 769 600 or
      I2 + L2 > 167 769 600
      then both I1 and I2 must be greater than 20 480. 
      
      Parameter 5 of the rxTrafficDescParm is always unused. 
      
      If the rxTrafficDescType is sameAsTx, the values in this attribute 
      are taken from the txTrafficDescParm."
::= { atmIfVpcVpd 298 }

atmIfVpcVpdRxTdpEntry OBJECT-TYPE
   SYNTAX     AtmIfVpcVpdRxTdpEntry
   ACCESS     not-accessible
   STATUS     obsolete
   DESCRIPTION
     "An entry in the atmIfVpcVpdRxTdpTable."
   INDEX {
      atmIfIndex,
      atmIfVpcIndex,
      atmIfVpcVpdIndex,
      atmIfVpcVpdRxTdpIndex }
::= { atmIfVpcVpdRxTdpTable 1 }

AtmIfVpcVpdRxTdpEntry ::= SEQUENCE {
   atmIfVpcVpdRxTdpIndex
      Integer32,
   atmIfVpcVpdRxTdpValue
      Unsigned32 }

atmIfVpcVpdRxTdpIndex OBJECT-TYPE
   SYNTAX     Integer32 (1..5)
   ACCESS     not-accessible
   STATUS     obsolete
   DESCRIPTION
     "This variable represents the atmIfVpcVpdRxTdpTable
      specific index for the atmIfVpcVpdRxTdpTable."
::= { atmIfVpcVpdRxTdpEntry 1 }

atmIfVpcVpdRxTdpValue OBJECT-TYPE
   SYNTAX     Unsigned32 (0..2147483647)
   ACCESS     read-write
   STATUS     obsolete
   DESCRIPTION
     "This variable represents an individual value for the
      atmIfVpcVpdRxTdpTable."
::= { atmIfVpcVpdRxTdpEntry 2 }

atmIfVpcVpdFqpTable OBJECT-TYPE
   SYNTAX     SEQUENCE OF AtmIfVpcVpdFqpEntry
   ACCESS     not-accessible
   STATUS     obsolete
   DESCRIPTION
     "This attribute is migrated to the AtmTmProv group.
      
      This attribute is a vector of three elements that specify the quality of 
      service parameters for the forward direction for this connection. 
      This attribute is used for SPVC connections.
      
      The cdv element specifies the acceptable peak-to-peak Cell Delay 
      Variation (CDV) of real-time connections (CBR, and rt-VBR). It is 
      signalled through the extended QoS information element.
      
      The ctd specifies the acceptable maximum Cell Transfer Delay 
      (maxCtd) of real-time connections (CBR, and rt-VBR). 
      It is signalled through the end to end transit delay information 
      element.
      
      The clr specifies the acceptable Cell Loss Ratio (CLR) of CBR, rt-
      VBR, and nrt-VBR connections. It is signalled through the extended 
      QoS information element."
::= { atmIfVpcVpd 359 }

atmIfVpcVpdFqpEntry OBJECT-TYPE
   SYNTAX     AtmIfVpcVpdFqpEntry
   ACCESS     not-accessible
   STATUS     obsolete
   DESCRIPTION
     "An entry in the atmIfVpcVpdFqpTable."
   INDEX {
      atmIfIndex,
      atmIfVpcIndex,
      atmIfVpcVpdIndex,
      atmIfVpcVpdFqpIndex }
::= { atmIfVpcVpdFqpTable 1 }

AtmIfVpcVpdFqpEntry ::= SEQUENCE {
   atmIfVpcVpdFqpIndex
      INTEGER,
   atmIfVpcVpdFqpValue
      Unsigned32 }

atmIfVpcVpdFqpIndex OBJECT-TYPE
   SYNTAX     INTEGER  {
                 cdv(0),
                 ctd(1),
                 clr(2) }
   ACCESS     not-accessible
   STATUS     obsolete
   DESCRIPTION
     "This variable represents the atmIfVpcVpdFqpTable
      specific index for the atmIfVpcVpdFqpTable."
::= { atmIfVpcVpdFqpEntry 1 }

atmIfVpcVpdFqpValue OBJECT-TYPE
   SYNTAX     Unsigned32 (0..2147483647)
   ACCESS     read-write
   STATUS     obsolete
   DESCRIPTION
     "This variable represents an individual value for the
      atmIfVpcVpdFqpTable."
::= { atmIfVpcVpdFqpEntry 2 }

atmIfVpcVpdBqpTable OBJECT-TYPE
   SYNTAX     SEQUENCE OF AtmIfVpcVpdBqpEntry
   ACCESS     not-accessible
   STATUS     obsolete
   DESCRIPTION
     "This attribute is migrated to the AtmTmProv group.
      
      This attribute is a vector of three elements that specify the quality of 
      service parameters for the backward direction for this connection. 
      This attribute is used for SPVC connections.
      
      The cdv element specifies the acceptable peak-to-peak Cell Delay 
      Variation (CDV) of real-time connections (CBR, and rt-VBR). 
      
      It is signalled through the extended QoS information element.
      
      The ctd specifies the acceptable maximum Cell Transfer Delay 
      (maxCtd) of real-time connections (CBR, and rt-VBR). It is 
      signalled through the end to end transit delay information element.
      
      The clr specifies the acceptable Cell Loss Ratio (CLR) of CBR, rt-
      VBR, and nrt-VBR connections. It is signalled through the extended 
      QoS information element."
::= { atmIfVpcVpd 360 }

atmIfVpcVpdBqpEntry OBJECT-TYPE
   SYNTAX     AtmIfVpcVpdBqpEntry
   ACCESS     not-accessible
   STATUS     obsolete
   DESCRIPTION
     "An entry in the atmIfVpcVpdBqpTable."
   INDEX {
      atmIfIndex,
      atmIfVpcIndex,
      atmIfVpcVpdIndex,
      atmIfVpcVpdBqpIndex }
::= { atmIfVpcVpdBqpTable 1 }

AtmIfVpcVpdBqpEntry ::= SEQUENCE {
   atmIfVpcVpdBqpIndex
      INTEGER,
   atmIfVpcVpdBqpValue
      Unsigned32 }

atmIfVpcVpdBqpIndex OBJECT-TYPE
   SYNTAX     INTEGER  {
                 cdv(0),
                 ctd(1),
                 clr(2) }
   ACCESS     not-accessible
   STATUS     obsolete
   DESCRIPTION
     "This variable represents the atmIfVpcVpdBqpTable
      specific index for the atmIfVpcVpdBqpTable."
::= { atmIfVpcVpdBqpEntry 1 }

atmIfVpcVpdBqpValue OBJECT-TYPE
   SYNTAX     Unsigned32 (0..2147483647)
   ACCESS     read-write
   STATUS     obsolete
   DESCRIPTION
     "This variable represents an individual value for the
      atmIfVpcVpdBqpTable."
::= { atmIfVpcVpdBqpEntry 2 }


-- AtmIf/n Vcc/vpi.vci Vcd TrafficManagement, 
-- AtmIf/n Vpc/vci Vpd TrafficManagement,
-- AtmIf/n Vpt/vpi Vpd TrafficManagement,
-- AtmIf/n Vpt/vpi Vcc/vci Vcd TrafficManagement
-- This component contains provisioned traffic management attributes 
-- of a connection. It is added automatically when a Vcc, Vpc, or Vpt is 
-- added in provisioning mode. It is a mandatory subcomponent of the 
-- Vcd or Vpd component.

atmIfVpcVpdTm OBJECT IDENTIFIER ::= { atmIfVpcVpd 2 }



atmIfVpcVpdTmRowStatusTable OBJECT-TYPE
   SYNTAX     SEQUENCE OF AtmIfVpcVpdTmRowStatusEntry
   ACCESS     not-accessible
   STATUS     mandatory
   DESCRIPTION
     "This entry controls the addition and deletion of 
      atmIfVpcVpdTm components."
::= { atmIfVpcVpdTm 1 }

atmIfVpcVpdTmRowStatusEntry OBJECT-TYPE
   SYNTAX     AtmIfVpcVpdTmRowStatusEntry
   ACCESS     not-accessible
   STATUS     mandatory
   DESCRIPTION
     "A single entry in the table represents a single 
      atmIfVpcVpdTm component."
   INDEX {
      atmIfIndex,
      atmIfVpcIndex,
      atmIfVpcVpdIndex,
      atmIfVpcVpdTmIndex }
::= { atmIfVpcVpdTmRowStatusTable 1 }

AtmIfVpcVpdTmRowStatusEntry ::= SEQUENCE {
   atmIfVpcVpdTmRowStatus
      RowStatus,
   atmIfVpcVpdTmComponentName
      DisplayString,
   atmIfVpcVpdTmStorageType
      StorageType,
   atmIfVpcVpdTmIndex
      NonReplicated }

atmIfVpcVpdTmRowStatus OBJECT-TYPE
   SYNTAX     RowStatus 
   ACCESS     read-only
   STATUS     mandatory
   DESCRIPTION
     "This variable is used as the basis for SNMP naming of
      atmIfVpcVpdTm components.
      These components cannot be added nor deleted."
::= { atmIfVpcVpdTmRowStatusEntry 1 }

atmIfVpcVpdTmComponentName OBJECT-TYPE
   SYNTAX     DisplayString 
   ACCESS     read-only
   STATUS     mandatory
   DESCRIPTION
     "This variable provides the component's string name for
      use with the ASCII Console Interface"
::= { atmIfVpcVpdTmRowStatusEntry 2 }

atmIfVpcVpdTmStorageType OBJECT-TYPE
   SYNTAX     StorageType 
   ACCESS     read-only
   STATUS     mandatory
   DESCRIPTION
     "This variable represents the storage type value for the
      atmIfVpcVpdTm tables."
::= { atmIfVpcVpdTmRowStatusEntry 4 }

atmIfVpcVpdTmIndex OBJECT-TYPE
   SYNTAX     NonReplicated 
   ACCESS     not-accessible
   STATUS     mandatory
   DESCRIPTION
     "This variable represents the index for the atmIfVpcVpdTm tables."
::= { atmIfVpcVpdTmRowStatusEntry 10 }

atmIfVpcVpdTmProvTable OBJECT-TYPE
   SYNTAX     SEQUENCE OF AtmIfVpcVpdTmProvEntry
   ACCESS     not-accessible
   STATUS     mandatory
   DESCRIPTION
     "This group contains traffic related provisionable attributes for the 
      Vcc, Vpc, and Vpt components. Changing any of the attributes in 
      this group causes a service interruption on the Vcc, Vpc, or Vpt 
      component."
::= { atmIfVpcVpdTm 100 }

atmIfVpcVpdTmProvEntry OBJECT-TYPE
   SYNTAX     AtmIfVpcVpdTmProvEntry
   ACCESS     not-accessible
   STATUS     mandatory
   DESCRIPTION
     "An entry in the atmIfVpcVpdTmProvTable."
   INDEX {
      atmIfIndex,
      atmIfVpcIndex,
      atmIfVpcVpdIndex,
      atmIfVpcVpdTmIndex }
::= { atmIfVpcVpdTmProvTable 1 }

AtmIfVpcVpdTmProvEntry ::= SEQUENCE {
   atmIfVpcVpdTmTxTrafficDescType
      INTEGER,
   atmIfVpcVpdTmFwdQosClass
      INTEGER,
   atmIfVpcVpdTmTxQueueLimit
      Unsigned32,
   atmIfVpcVpdTmHoldingPriority
      INTEGER,
   atmIfVpcVpdTmRxTrafficDescType
      INTEGER,
   atmIfVpcVpdTmBwdQosClass
      INTEGER,
   atmIfVpcVpdTmAtmServiceCategory
      INTEGER,
   atmIfVpcVpdTmTrafficShaping
      INTEGER,
   atmIfVpcVpdTmUnshapedTransmitQueueing
      INTEGER,
   atmIfVpcVpdTmWeight
      Unsigned32,
   atmIfVpcVpdTmForceTagging
      INTEGER,
   atmIfVpcVpdTmUsageParameterControl
      INTEGER,
   atmIfVpcVpdTmBearerClassBbc
      INTEGER,
   atmIfVpcVpdTmTransferCapabilityBbc
      INTEGER,
   atmIfVpcVpdTmTxWredThreshold
      Unsigned32,
   atmIfVpcVpdTmClippingBbc
      INTEGER,
   atmIfVpcVpdTmBestEffort
      INTEGER,
   atmIfVpcVpdTmTxPacketWiseDiscard
      INTEGER,
   atmIfVpcVpdTmTxWredMode
      INTEGER,
   atmIfVpcVpdTmRxPacketWiseDiscard
      INTEGER,
   atmIfVpcVpdTmAbrConnectionType
      INTEGER }

atmIfVpcVpdTmTxTrafficDescType OBJECT-TYPE
   SYNTAX     INTEGER  {
                 n1(1),
                 n2(2),
                 n3(3),
                 n4(4),
                 n5(5),
                 n6(6),
                 n7(7),
                 n8(8),
                 n9(9) }
   ACCESS     read-write
   STATUS     mandatory
   DESCRIPTION
     "This attribute specifies the type of traffic management which is 
      applied to the transmit direction of this connection as defined in the 
      ATM Forum. The txTrafficDescType determines the number and 
      meaning of the parameters in the txTrafficDescParm attribute.
      
      This attribute can have a value of 9 if and only if the 
      atmServiceCategory is availableBitRate."
   DEFVAL     { n1 }
::= { atmIfVpcVpdTmProvEntry 10 }

atmIfVpcVpdTmFwdQosClass OBJECT-TYPE
   SYNTAX     INTEGER  {
                 n0(0),
                 n1(1),
                 n2(2),
                 n3(3),
                 n4(4) }
   ACCESS     read-write
   STATUS     mandatory
   DESCRIPTION
     "This attribute specifies the quality of service for the forward 
      direction for this connection. This attribute is only used for SPVC 
      connections.
      
      Class 1 supports a QOS that meets Service Class A performance 
      requirements (circuit emulation, constant bit rate video).
      
      Class 2 supports a QOS that meets Service Class B performance 
      requirements (variable bit rate audio and video).
      
      Class 3 supports a QOS that meets Service Class C performance 
      requirements (Connection-Oriented Data Transfer).
      
      Class 4 supports a QOS that meets Service Class D performance 
      requirements (Connectionless Data Transfer).
      
      Class 0 is the unspecified bit rate QOS class; no objective is 
      specified for the performance parameters."
   DEFVAL     { n0 }
::= { atmIfVpcVpdTmProvEntry 21 }

atmIfVpcVpdTmTxQueueLimit OBJECT-TYPE
   SYNTAX     Unsigned32 (0 | 5..63488)
   ACCESS     read-write
   STATUS     mandatory
   DESCRIPTION
     "This attribute specifies an override to the default transmit queue 
      limit for this connection. A value other than sameAsCa may be 
      specified only for ATM IP cards. This attribute is not applicable for 
      basic Vpts.
      
      A value of sameAsCa means to use the default common or per-VC 
      transmit queue limit as defined by the CA service category for this 
      connection. 
      
      A value from 5 to 63,488 indicates that a specific transmit queue 
      limit is requested which differs from the default which is defined 
      under the CA component for this service category. A specific value 
      is ignored for connections where common queuing is specified for 
      the service category.
      
      The actual transmit queue limit for a connection is visible in the Vcc 
      Tm, Vpc Tm, or Vpt Tm txQueueThresholds attribute.

      VALUES (

      0 = sameAsCa

      )"
   DEFVAL     { 0 }
::= { atmIfVpcVpdTmProvEntry 22 }

atmIfVpcVpdTmHoldingPriority OBJECT-TYPE
   SYNTAX     INTEGER  {
                 n0(0),
                 n1(1),
                 n2(2),
                 n3(3),
                 n4(4) }
   ACCESS     read-write
   STATUS     mandatory
   DESCRIPTION
     "This attribute specifies the holding priority of this connection. In a 
      situation where the link bandwidth fluctuates, such as over an IMA 
      link, holding priority is used to determine which connections are 
      held and which are released. Holding priority 4 connections are the 
      first to be released. Holding priority 0 connections are the last to be 
      released. This value provisioned in the Vcd or Vpd may be 
      overridden by certain applications, for example Vcc Test, which run 
      over this connection. The default holding priority for a provisioned 
      connection is higher then default holding priorities for dynamic 
      (SVC) connections. 
      
      This attribute is not applicable for Vpt Vccs."
   DEFVAL     { n2 }
::= { atmIfVpcVpdTmProvEntry 25 }

atmIfVpcVpdTmRxTrafficDescType OBJECT-TYPE
   SYNTAX     INTEGER  {
                 n1(1),
                 n2(2),
                 n3(3),
                 n4(4),
                 n5(5),
                 n6(6),
                 n7(7),
                 n8(8),
                 n9(9),
                 sameAsTx(15) }
   ACCESS     read-write
   STATUS     mandatory
   DESCRIPTION
     "This attribute specifies the type of traffic management which is 
      applied to the receive direction of this connection as defined in the 
      ATM Forum. The rxTrafficDescType determines the number and 
      meaning of the parameters in the rxTrafficDescParm attribute.
      
      When this attribute is set to sameAsTx, the rxTrafficDescType as 
      well as the rxTrafficDescParm are taken from the 
      txTrafficDescType and txTrafficDescParm values."
   DEFVAL     { sameAsTx }
::= { atmIfVpcVpdTmProvEntry 30 }

atmIfVpcVpdTmBwdQosClass OBJECT-TYPE
   SYNTAX     INTEGER  {
                 n0(0),
                 n1(1),
                 n2(2),
                 n3(3),
                 n4(4),
                 sameAsFwd(15) }
   ACCESS     read-write
   STATUS     mandatory
   DESCRIPTION
     "This attribute specifies the quality of service for the backward 
      direction for this connection. This attribute is only used for SPVC 
      connections.
      
      Class 1 supports a QOS that meets Service Class A performance 
      requirements (Circuit emulation, constant bit rate video).
      
      Class 2 supports a QOS that meets Service Class B performance 
      requirements (Variable bit rate audio and video).
      
      Class 3 supports a QOS that meets Service Class C performance 
      requirements (Connection-Oriented Data Transfer).
      
      Class 4 supports a QOS that meets Service Class D performance 
      requirements (Connectionless Data Transfer).
      
      Class 0 is the unspecified bit rate QOS class; no objective is 
      specified for the performance parameters.
      
      The sameAsFwd selection sets the backward quality of service to 
      be the same as the forward quality of service."
   DEFVAL     { sameAsFwd }
::= { atmIfVpcVpdTmProvEntry 41 }

atmIfVpcVpdTmAtmServiceCategory OBJECT-TYPE
   SYNTAX     INTEGER  {
                 unspecifiedBitRate(0),
                 constantBitRate(1),
                 rtVariableBitRate(2),
                 nrtVariableBitRate(3),
                 availableBitRate(4),
                 derivedFromBBC(15) }
   ACCESS     read-write
   STATUS     mandatory
   DESCRIPTION
     "This attribute specifies the ATM service category for both directions 
      of the connection. 
      
      The value derivedFromBBC may only be used if the SrcPvc 
      component is provisioned under this Vcc. Otherwise a specific 
      ATM service category must be specified. 
      
      If this attribute is set to derivedFromBBC, the Broadband Bearer 
      Capability (BBC) and bestEffort attributes are used to determine the 
      atmServiceCategory of this connection. 
      
      If this attribute is set to other than derivedFromBBC, the value of 
      this attribute is used to override the provisioned BBC Information 
      Element parameters. In those cases, the BBC attributes are not used. 
      
      The constantBitRate service category is intended for real time 
      applications, that is those requiring tightly constrained delay and 
      delay variation, as would be appropriate for voice and video 
      applications. The consistent availability of a fixed quantity of 
      bandwidth is considered appropriate for CBR service. Cells which 
      are delayed beyond the value specified by Cell Transfer Delay are 
      assumed to be of significantly reduced value to the application.
      
      The rtVariableBitRate service category is intended for real time 
      applications, that is those requiring tightly constrained delay and 
      delay variation, as would be appropriate for voice and video 
      applications. Sources are expected to transmit at a rate which varies 
      with time. Equivalently, the source can be described as 'bursty'. 
      Cells which are delayed beyond the value specified by CTD are 
      assumed to be of significantly reduced value to the application. Real 
      time VBR service may support statistical multiplexing of real time 
      sources.
      
      The nrtVariableBitRate service category is intended for non-real 
      time applications which have bursty traffic characteristics and which 
      can be characterized in terms of a PCR, SCR, and MBS. For those 
      cells which are transferred within the traffic contract, the application 
      expects a low cell loss ratio. For all connections, it expects a bound 
      on the mean cell transfer delay. Non-real time VBR service may 
      support statistical multiplexing of connections. 
      
      The availableBitRate service is an ATM layer service category for 
      which the limiting ATM layer transfer characteristics provided by 
      the network may change subsequent to connection establishment. 
      ABR service has a flow control mechanism which supports several 
      types of feedback to control the source rate in response to changing 
      ATM layer transfer characteristics. ABR service is not intended to 
      support real-time applications. 
      
      The unspecifiedBitRate service is intended for non-real time 
      applications; that is, those not requiring tightly constrained delay 
      and delay variation. UBR sources are expected to be bursty. UBR 
      service supports a high degree of statistical multiplexing among 
      sources. UBR service does not specify traffic related service 
      guarantees. No numerical commitments are made with respect to 
      the cell loss ratio experienced by a UBR connection, or as to the 
      cell transfer delay experienced by cells on the connection."
   DEFVAL     { unspecifiedBitRate }
::= { atmIfVpcVpdTmProvEntry 42 }

atmIfVpcVpdTmTrafficShaping OBJECT-TYPE
   SYNTAX     INTEGER  {
                 disabled(1),
                 sameAsCa(2) }
   ACCESS     read-write
   STATUS     mandatory
   DESCRIPTION
     "This attribute specifies whether this connection uses traffic shaping 
      when transmitting traffic to the ATM interface.
      
      This attribute is ignored if the atmServiceCategory is 
      availableBitRate.
      
      When sameAsCa is selected, traffic shaping for the connection is 
      based on the trafficShaping attribute of the connection's service 
      category component under the CA. If the service category has 
      trafficShaping set to enabled or inverseUpc, then traffic shaping is 
      enabled for the connection. Note that enabling traffic shaping may 
      have no effect under certain cases. These cases are listed in the 
      description of the trafficShaping operational attribute, which is 
      under the Vcc Tm, Vpc Tm, or Vpt Tm components.
      
      When disabled is selected, traffic shaping for this connection is 
      disabled regardless of the provisioning of the connection's service 
      category component."
   DEFVAL     { sameAsCa }
::= { atmIfVpcVpdTmProvEntry 50 }

atmIfVpcVpdTmUnshapedTransmitQueueing OBJECT-TYPE
   SYNTAX     INTEGER  {
                 common(1),
                 sameAsCa(3) }
   ACCESS     read-write
   STATUS     mandatory
   DESCRIPTION
     "This attribute only applies when this connection is unshaped. This 
      attribute specifies the transmit queueing method for this connection 
      if it is unshaped. The two possible methods are per-VC queuing and 
      common queuing. 
      
      On ATM IP FPs, this attribute must be set to sameAsCa. 
      
      This attribute is ignored in the following situations:
      - if the connection has trafficShaping enabled or inverseUpc, or 
      - if the atmServiceCategory is availableBitRate, or
      - if the atmServiceCategory is constantBitRate and this is a CQC-
      based ATM FP.
      - for basic Vpts and standard Vpt Vccs
      
      When this attribute is set to sameAsCa, the transmit queueing 
      method for the connection is based on the 
      unshapedTransmitQueueing attribute of the connection's service 
      category component under the CA. 
      
      When this attribute is set to common, transmit traffic on this 
      unshaped connection is destined for the common queue."
   DEFVAL     { sameAsCa }
::= { atmIfVpcVpdTmProvEntry 60 }

atmIfVpcVpdTmWeight OBJECT-TYPE
   SYNTAX     Unsigned32 (0 | 1..4095 | 65535)
   ACCESS     read-write
   STATUS     mandatory
   DESCRIPTION
     "This attribute specifies an override for the weight of this unshaped 
      connection. This attribute is ignored for shaped connections, for 
      ABR connections, for connections on a CQC-based ATM FP, and 
      basic Vpts. 
      
      When the value is set to sameAsCa, the weight is determined by the 
      fairnessWeight attribute under the CA service category component 
      for all but standard Vpt Vccs. For standard Vpt Vccs, the weight is 
      determined by the Vcc's service category, when the value is set to 
      sameAsCa.
      
      When this attribute is set to a value from 1 to 4095, that value is 
      used for the fairness weight of this connection relative to other 
      connections. For all but standard Vpt Vccs, fairness weight 
      determines the proportion of transmit cell opportunities which are 
      allocated to this connection, compared to other connections in the 
      same service category. For standard Vpt Vccs, fairness weight 
      determines the proportion of transmit cell opportunities which are 
      allocated to this connection, compared to other connections 
      associated with the Vpt.
      
      When the value is set to upToQueueLimit, the fairness weight is 
      limited only by the txQueueLimit.

      VALUES (

      0 = upToQueueLimit

      65535 = sameAsCa

      )"
   DEFVAL     { 65535 }
::= { atmIfVpcVpdTmProvEntry 61 }

atmIfVpcVpdTmForceTagging OBJECT-TYPE
   SYNTAX     INTEGER  {
                 enabled(0),
                 disabled(1),
                 sameAsCa(2) }
   ACCESS     read-write
   STATUS     mandatory
   DESCRIPTION
     "This attribute specifies whether force tagging is enforced for this 
      connection for cells in the transmit direction. 
      
      On CQC-based ATM cards, and for Vpts, this attribute is not 
      applicable and is ignored. 
      
      When the value is set to sameAsCa, the force tagging functionality 
      is determined by the forceTagging attribute under the CA service 
      category component. 
      
      When the value is set to enabled, force tagging is enabled for cells 
      in the transmit direction on this connection. When this option is 
      selected, the CLP bit is set to 1 for all cells in the transmit direction. 
      Cells which are tagged are counted in the txCellClp attribute. 
      
      When the value is set to disabled, force tagging is disabled for cells 
      in the transmit direction on this connection. When this option is 
      selected, the CLP bit is unchanged for cells in the transmit 
      direction."
   DEFVAL     { sameAsCa }
::= { atmIfVpcVpdTmProvEntry 62 }

atmIfVpcVpdTmUsageParameterControl OBJECT-TYPE
   SYNTAX     INTEGER  {
                 enforced(0),
                 disabled(1),
                 sameAsCa(2),
                 monitored(4) }
   ACCESS     read-write
   STATUS     mandatory
   DESCRIPTION
     "This attribute specifies whether this connection enforces usage 
      parameter control when receiving traffic from the ATM interface.
      
      When sameAsCa is selected, UPC for the connection is based on 
      the usageParameterControl attribute of the service category 
      component under the AtmIf CA. If the service category has UPC 
      enforced or monitored, then UPC is set to that value for the 
      connection. 
      
      When disabled is selected, UPC for this connection is disabled 
      regardless of the provisioning of the service category. 
      
      When enforced is selected, UPC for this connection is enforced 
      regardless of the provisioning of the service category. 
      
      ATM IP cards provide the ability to monitor UPC violations without 
      tagging or discarding. When monitored is selected, UPC is actively 
      checking conformance for the connection and counting the 
      violations, but is not discarding or tagging cells which do not 
      conform to the connection traffic contract. 
      
      If this is a connection of serviceCategory abr on an ATM IP card, 
      and the abrConnectionType is sourceDest, virtualSourceDest or 
      explicitRate, selecting enforced enables dynamic generic cell rate 
      algorithm (DGCRA) to discard violating cells. Selecting monitored 
      enables DGCRA to count violating cells. 
      
      Note that setting UPC to enforced or monitored may have no effect 
      under certain cases. These cases are listed in the description of the 
      usageParameterControl operational attribute, which is under the 
      Vcc, Vpc, and Vpt components."
   DEFVAL     { sameAsCa }
::= { atmIfVpcVpdTmProvEntry 70 }

atmIfVpcVpdTmBearerClassBbc OBJECT-TYPE
   SYNTAX     INTEGER  {
                 a(1),
                 c(3),
                 x(16),
                 vp(24),
                 derivedFromServiceCategory(31) }
   ACCESS     read-write
   STATUS     mandatory
   DESCRIPTION
     "This attribute specifies the bearer capability. This attribute is only 
      used for SPVC and SPVP connections. It is one of the Broadband 
      Bearer Capability (BBC) attributes. The purpose of the BBC 
      information element is to indicate a requested broadband 
      connection-oriented bearer service to be provided by the network.
      
      The value derivedFromServiceCategory specifies that the actual 
      value which is used for this connection is derived from the value of 
      the atmServiceCategory. Either, this attribute must be set to 
      derivedFromServiceCategory, or the atmServiceCategory attribute 
      must be set to derivedFromBBC, but not both.
      
      Class a service is a connection-oriented, constant bit rate ATM 
      transport service. Class a service has end to end timing 
      requirements and may require stringent cell loss, cell delay and cell 
      delay variation performance.When a is set, the user is requesting 
      more than an ATM only service. The network may look at the AAL 
      to provide interworking based upon its contents. 
      
      Class c service is a connection-oriented, variable bit rate ATM 
      transport service. Class c service has no end-to-end timing 
      requirements. When c is set, the user is requesting more than an 
      ATM only service. The network interworking function may look at 
      the AAL and provide service based on it.
      
      Class x service is a connection-oriented ATM transport service 
      where the AAL, trafficType (vbr or cbr) and timing requirements 
      are user defined (that is, transparent to the network).When x is set 
      the user is requesting an ATM only service from the network. In this 
      case, the network shall not process any higher layer protocol.
      
      Class vp service is used to specify a transparent VP service. When 
      the value of this attribute is vp, the user is requesting an ATM only 
      service from the network. In this case, the network shall not process 
      any higher layer protocol. This service differs from class x service 
      in that with the class vp service both the VCI field (except or VCI 
      values 0, 3, 4, and 6 through 15) and Payload Type field are 
      transported transparently by the network. This attribute value is 
      only applicable to SPVP connections."
   DEFVAL     { derivedFromServiceCategory }
::= { atmIfVpcVpdTmProvEntry 71 }

atmIfVpcVpdTmTransferCapabilityBbc OBJECT-TYPE
   SYNTAX     INTEGER  {
                 n0(0),
                 n1(1),
                 n2(2),
                 n5(5),
                 n8(8),
                 n9(9),
                 n10(10),
                 notApplicable(30),
                 derivedFromServiceCategory(31) }
   ACCESS     read-write
   STATUS     mandatory
   DESCRIPTION
     "This attribute specifies the transfer capability for this connection. 
      Uni 3.0/3.1 traffic type and end-to-end timing parameters are 
      mapped into this parameter as follows:
      <transferCapability: TrafficType, Timing>
      0: NoIndication, NoIndication
      1: NoIndication, yes
      2: NoIndication, no
      5: CBR, yes
      8: VBR, NoIndication
      9: VBR, yes
      10: VBR, no
      
      notApplicable specifies that the user does not want to specify the 
      transfer capability.
      
      The CBR traffic type refers to traffic offered on services such as a 
      constant bit rate video service or a circuit emulation.
      The VBR traffic type refers to traffic offered on services such as 
      packetized audio and video, or data.
      
      The value no indication for traffic type is used if the user has not set 
      the traffic type; similarly for end-to-end timing.
      
      The value yes for end-to-end timing indicates that end-to-end 
      timing is required.
      
      The value no for end-to-end timing indicates that end-to-end timing 
      is not required.
      
      The value derivedFromServiceCategory specifies that the actual 
      value which is used for this connection is derived from the value of 
      the atmServiceCategory. Either, this attribute must be set to 
      derivedFromServiceCategory, or the atmServiceCategory attribute 
      must be set to derivedFromBBC, but not both."
   DEFVAL     { derivedFromServiceCategory }
::= { atmIfVpcVpdTmProvEntry 72 }

atmIfVpcVpdTmTxWredThreshold OBJECT-TYPE
   SYNTAX     Unsigned32 (25 | 50 | 75)
   ACCESS     read-write
   STATUS     mandatory
   DESCRIPTION
     "This attribute determines at what percentage of the queue being at 
      the EPD threshold, WRED starts. When the value is set to 25%, 
      WRED starts as soon as the queue is 25% of the way to the EPD 
      threshold. When the value is set to 50%, WRED starts later, after 
      the queue is 50% of the way to the EPD threshold. When the value 
      is set to 75%, WRED starts only when the queue is 75% of the way 
      to the EPD threshold. The EPD threshold is 85% of the transmit 
      queue length.
      
      This attribue is ignored if txWredMode or txPacketWiseDiscard is 
      disabled. It is always ignored on CQC-based ATM FP."
   DEFVAL     { 25 }
::= { atmIfVpcVpdTmProvEntry 73 }

atmIfVpcVpdTmClippingBbc OBJECT-TYPE
   SYNTAX     INTEGER  {
                 no(0),
                 yes(1) }
   ACCESS     read-write
   STATUS     mandatory
   DESCRIPTION
     "This attribute specifies the value for the clipping susceptibility 
      parameter in the BBC Information Element. This attribute is only 
      used for SPVC connections. It is one of the Broadband Bearer 
      Capability attributes.
      
      Clipping is an impairment in which the first fraction of a second of 
      information to be transferred is lost. It occurs after a call is 
      answered and before an associated connection is switched through."
   DEFVAL     { no }
::= { atmIfVpcVpdTmProvEntry 74 }

atmIfVpcVpdTmBestEffort OBJECT-TYPE
   SYNTAX     INTEGER  {
                 indicated(0),
                 notIndicated(1),
                 derivedFromServiceCategory(15) }
   ACCESS     read-write
   STATUS     mandatory
   DESCRIPTION
     "This attribute specifies the value of the best effort parameter in the 
      ATM Traffic Descriptor Information Element. This attribute is only 
      used for Soft PVC connections. It is one of the Broadband Bearer 
      Capability attributes.
      
      The value indicated implies that the quality of service for this 
      connection is not guaranteed.
      
      The value notIndicated implies that the quality of service for this 
      connection is guaranteed.
      
      The value derivedFromServiceCategory specifies that the actual 
      value which is used for this connection is derived from the value of 
      the atmServiceCategory. Either, this attribute must be set to 
      derivedFromServiceCategory, or the atmServiceCategory attribute 
      must be set to derivedFromBBC, but not both."
   DEFVAL     { derivedFromServiceCategory }
::= { atmIfVpcVpdTmProvEntry 75 }

atmIfVpcVpdTmTxPacketWiseDiscard OBJECT-TYPE
   SYNTAX     INTEGER  {
                 disabled(0),
                 enabled(1) }
   ACCESS     read-write
   STATUS     mandatory
   DESCRIPTION
     "This attribute specifies whether packet-wise discard functions are to 
      be enabled or disabled in the transmit data direction for this 
      connection. Packet-wise discard functions should only be requested 
      if this connection is transferring AAL5 frame traffic. This attribute 
      is not applicable for Vpts.
      
      Packet-wise functions increase the 'goodput' of the link. The 
      transmit packet-wise functions are Early Packet Discard (EPD) and 
      Partial Packet Discard (PPD). 
      
      EPD allows the connection to discard an entire frame once the 
      transmit queue has reached the EPD threshold. EPD increases the 
      'goodput' of a link, since discarding an entire frame means that 
      some queue capacity is guarded for some other frame which is 
      already partially transmitted. All cells of the frame are discarded 
      from the Beginning of Message (BOM) cell up to and including the 
      End of Message (EOM) cell. 
      
      PPD allows the connection to discard the remainder of a cell-
      forwarded AAL5 frame if one cell of this frame has been discarded. 
      All cells are discarded up to but not including the EOM cell. The 
      PPD function increases the 'goodput' of the link, since cells which 
      are only going to be discarded at the AAL5 reassembly point are 
      not transmitted.
      
      On CQC-based ATM cards, the packet-wise discard functions are 
      PPD and EPD. PPD is available at VCC cell-transfer points. PPD is 
      not applicable at frame-cell conversion points, and is not applicable 
      for Vpcs. PPD is configured by this attribute. Packet-wise discard 
      should only be enabled for connections carrying AAL5 
      segmentation traffic. Setting the value to enabled for any other 
      traffic type may result in all traffic being discarded. On CQC-based 
      ATM FPs, EPD is automatically enabled at frame-to-cell conversion 
      points, independent of the setting of this attribute. 
      
      On ATM IP cards, packet-wise discard functions include EPD and 
      PPD. PPD and EPD apply to individual VCCs and VCCs within 
      VPCs at all connection points, including tandem VPC connections. 
      Both PPD and EPD are controlled by this attribute. This attribute 
      may safely be set to enabled for any connection (Vcc or Vpc) on 
      ATM IP FPs since they have the ability to automatically detect 
      AAL5-segmented traffic on a connection, and only enable packet-
      wise discards if AAL5-segmented traffic is detected.
      
      When this attribute is set to enabled, packet-wise discard functions 
      are applied to transmit traffic at this connection point. When this 
      attribute is set to disabled, packet-wise discard functions are not 
      applied to transmit traffic at this connection point.
      
      At a SPVC origin on a PNNI interface, a value of enabled specifies 
      that frame discard is requested in the backward direction. When this 
      attribute is set to disabled, backward frame discard is not requested 
      in the SPVC call setup. 
      
      The transmit packet-wise discard functions that are active are 
      visible in the Vcc/Vpc Tm txPacketWiseDiscard operational 
      attribute."
   DEFVAL     { disabled }
::= { atmIfVpcVpdTmProvEntry 76 }

atmIfVpcVpdTmTxWredMode OBJECT-TYPE
   SYNTAX     INTEGER  {
                 disabled(0),
                 enabled(1),
                 perFlow(2) }
   ACCESS     read-write
   STATUS     mandatory
   DESCRIPTION
     "This attribute specifies the activation of weighted random early 
      detection (WRED) functionality. WRED is only available on ATM 
      IP FPs. On CQC-based ATM FPs, this attribute is ignored. If 
      txPacketWiseDiscard is set to disabled this attribute is ignored. This 
      attribute is not applicable for Vpts or Vpt Vccs.
      
      WRED is applied in the transmit direction for this connection. 
      WRED function should be enabled only for connections which are 
      transferring TCP/IP traffic. WRED acts to prevent synchronization 
      of multiple TCP/IP sources by randomly discarding a small 
      percentage of frames when transmit queue congestion reaches the 
      designated level. W-RED may also be used to differentiate service 
      on VCC's by preferentially discarding one VCC before another. 
      Discards start at 0% of cells, when the queue is part-way to the 
      Early Packet Discard (EPD) threshold, and rise to 100% of cells 
      discarded at the EPD threshold. WRED discards all the cells in a 
      frame. 
      
      If this attribute is set to enabled, WRED is enabled for all 
      applications linked to the given Vcc. If it is set to perFlow, each 
      TCP application has individual control over whether to enable or 
      disable WRED
      
      If txPacketWiseDiscard is set to disabled, or if this attribute is set to 
      disabled, WRED functionality is disabled. 
      
      If WRED is active, it is visible in the Vcc/Vpc Tm 
      txPacketWiseDiscard operational attribute."
   DEFVAL     { disabled }
::= { atmIfVpcVpdTmProvEntry 77 }

atmIfVpcVpdTmRxPacketWiseDiscard OBJECT-TYPE
   SYNTAX     INTEGER  {
                 disabled(0),
                 enabled(1) }
   ACCESS     read-write
   STATUS     mandatory
   DESCRIPTION
     "This attribute specifies whether packet-wise discard functions are to 
      be enabled or disabled in the receive data direction for this 
      connection. Packet-wise discard functions should only be requested 
      if this connection is transferring AAL5 frame traffic. This attribute 
      is not applicable for Vpts.
      
      Packet-wise functions increase the 'goodput' of the link. The 
      receive packet-wise function is Partial Packet Discard (PPD). 
      
      PPD allows the connection to discard the remainder of a cell-
      forwarded AAL5 frame if one cell of this frame has been discarded, 
      for example due to UPC. All cells are discarded up to but not 
      including the EOM cell. The PPD function increases the 'goodput' 
      of the link, since cells which are only going to be discarded at the 
      AAL5 reassembly point are not transmitted.
      
      PPD is available at all VCC connection points where UPC may be 
      activated. PPD is not applicable for Vpcs. 
      
      On CQC-based ATM FPs, packet-wise discards should only be 
      enabled for connections carrying AAL5 segmentation traffic. 
      Setting the value to enabled for any other traffic type may result in 
      traffic being discarded. 
      
      On ATM IP cards, this attribute may safely be set to enabled for any 
      connection (Vcc or Vpc) since they have the ability to automatically 
      detect AAL5-segmented traffic on a connection, and only enables 
      packet-wise discards if AAL5-segmented traffic is detected.
      
      When this attribute is set to enabled, packet-wise discard functions 
      are applied to receive traffic at this connection point. When this 
      attribute is set to disabled, packet-wise discard functions are not 
      applied to receive traffic at this connection point.
      
      At a SPVC origin on a PNNI interface, a value of enabled specifies 
      that frame discard is requested in the forward direction. When this 
      attribute is set to disabled, forward frame discard is not requested in 
      the SPVC call setup. 
      
      The receive packet-wise discard functions that are active are visible 
      in the Vcc/Vpc Tm rxPacketWiseDiscard operational attribute."
   DEFVAL     { disabled }
::= { atmIfVpcVpdTmProvEntry 78 }

atmIfVpcVpdTmAbrConnectionType OBJECT-TYPE
   SYNTAX     INTEGER  {
                 abrSwitch(0),
                 virtualSourceDest(3),
                 sourceDest(4),
                 nonAbrInterworking(5),
                 sameAsCa(14) }
   ACCESS     read-write
   STATUS     mandatory
   DESCRIPTION
     "This attribute specifies the type of ABR behavior which is to be 
      enforced at this connection. This attribute is only applicable if the 
      atmServiceCategory attribute is availableBitRate. If the 
      atmServicecategory attribute is not availableBitRate, this attribute 
      value is ignored.
      
      The actual ABR functionality which is in effect is visible in the 
      Vcc/Vpc/Vpt Tm abrConnectionType operational attribute.
      
      For CQC-based ATM cards, the only allowable values are 
      sameAsCa, nonAbrInterworking or abrSwitch. If abrSwitch is 
      selected, the CQC implements EFCI marking behavior.
      
      sameAsCa is used to request the default behavior as specified in the 
      CA Abr component for this Vcc. Otherwise, this attribute overrides 
      the default behavior. 
      
      virtualSourceDest is used to request that this connection point 
      function as a virtual source/virtual destination. VS/VD functionality 
      is only supported on ATM IP FPs.
      
      sourceDest requires that this connection point function as a S/D for 
      RM cells. S/D mode is automatically invoked at this connection 
      point either if this is a connection end point, or if the next hop 
      connection point is configured as nonAbrInterworking.
      
      nonAbrInterworking is used to request that this connection point 
      function as an interworking between ABR and non-ABR service 
      categories. This means that there are no RM cells on the link side of 
      this connection, and that the next hop connection point is 
      performing as an ABR sourceDest.
      
      abrSwitch is used to request ABR switch behavior for this 
      connection point. The ABR switch behavior is first, to confirm to 
      virtualSourceDest or nonAbrInterworking setting on the next hop, 
      and otherwise to implement ABR ER switch behavior. For CQC-
      based FPs, ABR switch behavior is implemented as EFCI marking."
   DEFVAL     { sameAsCa }
::= { atmIfVpcVpdTmProvEntry 90 }

atmIfVpcVpdTmTxTdpTable OBJECT-TYPE
   SYNTAX     SEQUENCE OF AtmIfVpcVpdTmTxTdpEntry
   ACCESS     not-accessible
   STATUS     mandatory
   DESCRIPTION
     "This attribute is a vector of five traffic parameters whose meanings 
      are defined by the txTrafficDescType attribute. 
      
      The values of peak cell rate (PCR), sustained cell rate (SCR), 
      Minimum Cell Rate (MCR) and requested shaping rate are 
      expressed in cell/s. Maximum burst size (MBS) is expressed in 
      cells. CDVT is expressed in microseconds. The values of PCR, 
      SCR, MCR, MBS and CDVT are used for connection admission 
      control (CAC). The value of CDVT is only used for connections 
      where the atmServiceCategory is constantBitRate. For all other 
      values of atmServiceCategory, CDVT is ignored. The values of 
      PCR, SCR, MCR and requested shaping rate are used to determine 
      the actual shaping rate where traffic shaping is enabled.
      
      When txTrafficDescType is 1 or 2, all of the parameters must be set 
      to zero.
      
      When txTrafficDescType is 3, parameter 1 represents the PCR for 
      CLP equal to 0 and 1 traffic; parameter 4 represents the CDVT; and 
      parameter 5 represents the requested shaping rate. A non-zero value 
      in parameter 5 overrides any value in parameter 1. This result is 
      used as the PCR. Parameter 1 must be non-zero. Parameters 2 and 3 
      must be zero.
      
      When txTrafficDescType is 4, parameter 1 represents the PCR for 
      CLP equal to 0 and 1 traffic with cell discard; parameter 2 
      represents the PCR for CLP equal to 0 traffic; parameter 4 
      represents the CDVT; and parameter 5 represents the requested 
      shaping rate. A non-zero value in parameter 5 overrides any value in 
      parameter 1. This result is used as the PCR. Parameter 1 must be 
      greater than or equal to parameter 2. Parameters 1 and 2 must be 
      non-zero. Parameter 3 must be zero.
      
      When txTrafficDescType is 5, parameter 1 represents the PCR for 
      CLP equal to 0 and 1 traffic with cell tagging; parameter 2 
      represents the PCR for CLP equal to 0 traffic; parameter 4 
      represents the CDVT; and parameter 5 represents the requested 
      shaping rate. A non-zero value in parameter 5 overrides any value in 
      parameter 1. This result is used as the PCR. Parameter 1 must be 
      greater than or equal to parameter 2. Parameters 1 and 2 must be 
      non-zero. Parameter 3 must be zero.
      
      When txTrafficDescType is 6, parameter 1 represents the PCR for 
      CLP equal to 0 and 1 traffic; parameter 2 represents the SCR for 
      CLP equal to 0 and 1 traffic; parameter 3 represents the MBS for 
      CLP equal to 0 and 1 traffic; parameter 4 represents the CDVT; and 
      parameter 5 represents the requested shaping rate. A non-zero value 
      in parameter 5 overrides any value in parameter 1. This result is 
      used as the PCR. Parameters 1, 2 and 3 must be non-zero. 
      Parameter 1 must be greater than or equal to parameter 2. Parameter 
      5, must either be zero (unused) or greater than or equal to parameter 
      2.
      
      When txTrafficDescType is 7, parameter 1 represents the PCR for 
      CLP equal to 0 and 1 traffic; parameter 2 represents the SCR for 
      CLP equal to 0 with cell discard; parameter 3 represents the MBS 
      for CLP equal to 0 traffic; parameter 4 represents the CDVT; and 
      parameter 5 represents the requested shaping rate. A non-zero value 
      in parameter 5 overrides any value in parameter 1. This result is 
      used as the PCR. Parameters 1, 2 and 3 must be non-zero. 
      Parameter 1 must be greater than or equal to parameter 2. Parameter 
      5, must either be zero (unused) or greater than or equal to parameter 
      2.
      
      When txTrafficDescType is 8, parameter 1 represents the PCR for 
      CLP equal to 0 and 1 traffic; parameter 2 represents the SCR for 
      CLP equal to 0 traffic with cell tagging; parameter 3 represents the 
      MBS for CLP equal to 0 traffic; parameter 4 represents the CDVT; 
      and parameter 5 represents the requested shaping rate. A non-zero 
      value in parameter 5 overrides any value in parameter 1. This result 
      is used as the PCR. Parameters 1, 2 and 3 must be non-zero. 
      Parameter 1 must be greater than or equal to parameter 2. Parameter 
      5, must either be zero (unused) or greater than or equal to parameter 
      2.
      
      When txTrafficDescType is 9, parameter 1 represents the PCR; 
      parameter 2 represents the CDVT; parameter 3 represents the MCR; 
      parameter 4 and parameter 5 represent are not used and must be 
      zero. Parameter 1 must be non-zero and must be greater than or 
      equal to parameter 3. Parameter 3 may be optionally zero.
      
      Whenever it is valid for PCR to be specified, parameter 5 may also 
      be used to specify a requested shaping rate. A non-zero value in 
      parameter 5 overrides the value in parameter 1 and is used as the 
      peak cell rate in calculations of CAC and shaping rate. When the 
      atmServiceCategory is availableBitRate (ABR), the shaping rate is 
      dynamically chosen, based on the ABR flow control mechanism, as 
      a value between the MCR and the PCR or the requested shaping 
      rate if applicable.
      
      For txTrafficDescType 3, 4 and 5, the transmit traffic is shaped at 
      the next available shaping rate less than the PCR. 
      
      For txTrafficDescType 6, 7 and 8 if linear traffic shaping is selected, 
      the transmit traffic is shaped at the highest available rate which is 
      between PCR and SCR. However, if there is no available shaping 
      rate between PCR and SCR, traffic is shaped at the next rate above 
      the PCR. 
      
      For txTrafficDescType 6, 7 and 8 if inverse-UPC traffic shaping is 
      selected, the transmit traffic is shaped at a variable rate which 
      conforms to the PCR, SCR and MBS of the connection traffic 
      descriptor. Inverse-UPC traffic shaping is available only on ATM IP 
      cards."
::= { atmIfVpcVpdTm 456 }

atmIfVpcVpdTmTxTdpEntry OBJECT-TYPE
   SYNTAX     AtmIfVpcVpdTmTxTdpEntry
   ACCESS     not-accessible
   STATUS     mandatory
   DESCRIPTION
     "An entry in the atmIfVpcVpdTmTxTdpTable."
   INDEX {
      atmIfIndex,
      atmIfVpcIndex,
      atmIfVpcVpdIndex,
      atmIfVpcVpdTmIndex,
      atmIfVpcVpdTmTxTdpIndex }
::= { atmIfVpcVpdTmTxTdpTable 1 }

AtmIfVpcVpdTmTxTdpEntry ::= SEQUENCE {
   atmIfVpcVpdTmTxTdpIndex
      Integer32,
   atmIfVpcVpdTmTxTdpValue
      Unsigned32 }

atmIfVpcVpdTmTxTdpIndex OBJECT-TYPE
   SYNTAX     Integer32 (1..5)
   ACCESS     not-accessible
   STATUS     mandatory
   DESCRIPTION
     "This variable represents the atmIfVpcVpdTmTxTdpTable
      specific index for the atmIfVpcVpdTmTxTdpTable."
::= { atmIfVpcVpdTmTxTdpEntry 1 }

atmIfVpcVpdTmTxTdpValue OBJECT-TYPE
   SYNTAX     Unsigned32 (0..2147483647)
   ACCESS     read-write
   STATUS     mandatory
   DESCRIPTION
     "This variable represents an individual value for the
      atmIfVpcVpdTmTxTdpTable."
::= { atmIfVpcVpdTmTxTdpEntry 2 }

atmIfVpcVpdTmRxTdpTable OBJECT-TYPE
   SYNTAX     SEQUENCE OF AtmIfVpcVpdTmRxTdpEntry
   ACCESS     not-accessible
   STATUS     mandatory
   DESCRIPTION
     "This attribute is a vector of four traffic parameters whose meanings 
      are defined by the rxTrafficDescType attribute. The values of peak 
      cell rate (PCR), sustained cell rate (SCR) and Minimum Cell Rate 
      (MCR) are expressed in cell/s. Maximum burst size (MBS) is 
      expressed in cells. The value of CDVT is expressed in 
      microseconds. The values of PCR, SCR, MCR, MBS and CDVT 
      are used for usage parameter control (UPC).
      
      When rxTrafficDescType is 1 or 2, all of the parameters must be set 
      to zero (unused).
      
      When rxTrafficDescType is 3, parameter 1 represents the PCR for 
      CLP equal to 0 and 1 traffic. Parameter 1 must be non-zero. 
      Parameters 2 and 3 must be set to zero (unused).
      
      When rxTrafficDescType is 4, parameter 1 represents the PCR 
      for CLP equal to 0 and 1 traffic; parameter 2 represents the PCR for 
      CLP equal to 0 traffic with cell discard. Parameters 1 and 2 must be 
      non-zero. Parameter 3 must be set to zero (unused). Parameter 1 
      must be greater than or equal to parameter 2.
      
      When rxTrafficDescType is 5, parameter 1 represents the PCR for 
      CLP equal to 0 and 1 traffic; parameter 2 represents the PCR for 
      CLP equal to 0 traffic with cell tagging. Parameters 1 and 2 must be 
      non-zero. Parameter 3 must be set to zero (unused). Parameter 1 
      must be greater than or equal to parameter 2.
      
      When rxTrafficDescType is a 6, parameter 1 represents the PCR for 
      CLP equal to 0 and 1 traffic; parameter 2 represents the SCR for 
      CLP equal to 0 and 1 traffic; parameter 3 represents the MBS for 
      CLP equal to 0 and 1 traffic. Parameters 1, 2 and 3 must be non-
      zero. Parameter 1 must be greater than or equal to Parameter 2. 
      
      When rxTrafficDescType is 7, parameter 1 represents the PCR for 
      CLP equal to 0 and 1 traffic; parameter 2 represents the SCR for 
      CLP equal to 0 traffic with cell discard; parameter 3 represents the 
      MBS for CLP equal to 0 traffic. Parameters 1, 2 and 3 must be non-
      zero. Parameter 1 must be greater than or equal to parameter 2. 
      
      When rxTrafficDescType is 8, parameter 1 represents the PCR for 
      CLP equal to 0 and 1 traffic; parameter 2 represents the SCR for 
      CLP equal to 0 traffic with cell tagging; parameter 3 represents the 
      MBS for CLP equal to 0 traffic. Parameter 1, 2 and 3 must be non-
      zero. Parameter 1 must be greater than or equal to parameter 2.
      
      When rxTrafficDescType is 9, parameter 1 represents the PCR; 
      parameter 2 represents the CDVT; parameter 3 represents the MCR. 
      Parameter 4 is not used and must be zero. Parameter 1,must be non-
      zero and must be greater than or equal to parameter 3. Parameter 3 
      may optionally be zero.
      
      When rxTrafficDescType is any value from 3 through 8, parameter 
      4 represents the CDVT. 
      
      If the value of CDVT either in parameter 2 or in parameter 4 is zero, 
      the CDVT is taken from the CA defaults for the particular 
      atmServiceCategory of this connection.
      
      On a CQC-based ATM card, when rxTrafficDescriptorType is 3 
      through 8, there are certain extreme combinations of 
      rxTrafficDescParm which are outside the capabilities of the UPC 
      hardware. The check prov command detects such cases and 
      generates an error message. If this happens, adjust the parameters 
      until they fall within the supported limits. 
      
      To calculate the limits, use the following formulae:
      I1 = 1 000 000 000 / PCR
      L1 = CDVT * 1000
      I2 = 1,000,000,000 / SCR
      L2 = CDVT + (MBS - 1) * (I2 - I1)
      I1 and I2 must be less than or equal to 335,523,840. I1 + L1 must 
      be less than or equal to 1,342,156,800. I2 + L2 must be less than or 
      equal to 1,342,156,800. Note that I2 and L2 only apply when the 
      rxTrafficDescriptorType is 6 through 8.
      
      If the values of I1, L1, I2 or L2 are closer to the limits described 
      above, a further restriction applies. Specifically, if either:
      I1 > 41,940,480 or
      I2 > 41,940,480 or
      I1 + L1 > 167,769,600 or
      I2 + L2 > 167,769,600
      then both I1 and I2 must be greater than 20,480. 
      
      Parameter 5 of the rxTrafficDescParm is always unused. 
      
      If the rxTrafficDescType is sameAsTx, the values provisioned in 
      this attribute are ignored. The traffic parameters for the receive 
      direction are taken from the txTrafficDescParm."
::= { atmIfVpcVpdTm 457 }

atmIfVpcVpdTmRxTdpEntry OBJECT-TYPE
   SYNTAX     AtmIfVpcVpdTmRxTdpEntry
   ACCESS     not-accessible
   STATUS     mandatory
   DESCRIPTION
     "An entry in the atmIfVpcVpdTmRxTdpTable."
   INDEX {
      atmIfIndex,
      atmIfVpcIndex,
      atmIfVpcVpdIndex,
      atmIfVpcVpdTmIndex,
      atmIfVpcVpdTmRxTdpIndex }
::= { atmIfVpcVpdTmRxTdpTable 1 }

AtmIfVpcVpdTmRxTdpEntry ::= SEQUENCE {
   atmIfVpcVpdTmRxTdpIndex
      Integer32,
   atmIfVpcVpdTmRxTdpValue
      Unsigned32 }

atmIfVpcVpdTmRxTdpIndex OBJECT-TYPE
   SYNTAX     Integer32 (1..5)
   ACCESS     not-accessible
   STATUS     mandatory
   DESCRIPTION
     "This variable represents the atmIfVpcVpdTmRxTdpTable
      specific index for the atmIfVpcVpdTmRxTdpTable."
::= { atmIfVpcVpdTmRxTdpEntry 1 }

atmIfVpcVpdTmRxTdpValue OBJECT-TYPE
   SYNTAX     Unsigned32 (0..2147483647)
   ACCESS     read-write
   STATUS     mandatory
   DESCRIPTION
     "This variable represents an individual value for the
      atmIfVpcVpdTmRxTdpTable."
::= { atmIfVpcVpdTmRxTdpEntry 2 }

atmIfVpcVpdTmFqpTable OBJECT-TYPE
   SYNTAX     SEQUENCE OF AtmIfVpcVpdTmFqpEntry
   ACCESS     not-accessible
   STATUS     mandatory
   DESCRIPTION
     "This attribute is a vector of three elements that specify the quality of 
      service parameters for the forward direction for this connection. 
      This attribute is used for SPVC connections.
      
      The cdv element specifies the acceptable peak-to-peak Cell Delay 
      Variation (CDV) of real-time connections (CBR and rt-VBR). It is 
      signalled through the extended QoS information element.
      
      The ctd specifies the acceptable maximum Cell Transfer Delay 
      (maxCtd) of real-time connections (CBR and rt-VBR). 
      It is signalled through the end to end transit delay information 
      element.
      
      The clr specifies the acceptable Cell Loss Ratio (CLR) of CBR, rt-
      VBR, and nrt-VBR connections. It is signalled through the extended 
      QoS information element."
::= { atmIfVpcVpdTm 458 }

atmIfVpcVpdTmFqpEntry OBJECT-TYPE
   SYNTAX     AtmIfVpcVpdTmFqpEntry
   ACCESS     not-accessible
   STATUS     mandatory
   DESCRIPTION
     "An entry in the atmIfVpcVpdTmFqpTable."
   INDEX {
      atmIfIndex,
      atmIfVpcIndex,
      atmIfVpcVpdIndex,
      atmIfVpcVpdTmIndex,
      atmIfVpcVpdTmFqpIndex }
::= { atmIfVpcVpdTmFqpTable 1 }

AtmIfVpcVpdTmFqpEntry ::= SEQUENCE {
   atmIfVpcVpdTmFqpIndex
      INTEGER,
   atmIfVpcVpdTmFqpValue
      Unsigned32 }

atmIfVpcVpdTmFqpIndex OBJECT-TYPE
   SYNTAX     INTEGER  {
                 cdv(0),
                 ctd(1),
                 clr(2) }
   ACCESS     not-accessible
   STATUS     mandatory
   DESCRIPTION
     "This variable represents the atmIfVpcVpdTmFqpTable
      specific index for the atmIfVpcVpdTmFqpTable."
::= { atmIfVpcVpdTmFqpEntry 1 }

atmIfVpcVpdTmFqpValue OBJECT-TYPE
   SYNTAX     Unsigned32 (0..16777215)
   ACCESS     read-write
   STATUS     mandatory
   DESCRIPTION
     "This variable represents an individual value for the
      atmIfVpcVpdTmFqpTable."
::= { atmIfVpcVpdTmFqpEntry 2 }

atmIfVpcVpdTmBqpTable OBJECT-TYPE
   SYNTAX     SEQUENCE OF AtmIfVpcVpdTmBqpEntry
   ACCESS     not-accessible
   STATUS     mandatory
   DESCRIPTION
     "This attribute is a vector of two elements that specify the quality of 
      service parameters for the backward direction for this connection. 
      This attribute is used for SPVC connections.
      
      The cdv element specifies the acceptable peak-to-peak Cell Delay 
      Variation (CDV) of real-time connections (CBR and rt-VBR). It is 
      signalled through the extended QoS information element.
      
      The clr specifies the acceptable Cell Loss Ratio (CLR) of CBR, rt-
      VBR, and nrt-VBR connections. It is signalled through the extended 
      QoS information element."
::= { atmIfVpcVpdTm 459 }

atmIfVpcVpdTmBqpEntry OBJECT-TYPE
   SYNTAX     AtmIfVpcVpdTmBqpEntry
   ACCESS     not-accessible
   STATUS     mandatory
   DESCRIPTION
     "An entry in the atmIfVpcVpdTmBqpTable."
   INDEX {
      atmIfIndex,
      atmIfVpcIndex,
      atmIfVpcVpdIndex,
      atmIfVpcVpdTmIndex,
      atmIfVpcVpdTmBqpIndex }
::= { atmIfVpcVpdTmBqpTable 1 }

AtmIfVpcVpdTmBqpEntry ::= SEQUENCE {
   atmIfVpcVpdTmBqpIndex
      INTEGER,
   atmIfVpcVpdTmBqpValue
      Unsigned32 }

atmIfVpcVpdTmBqpIndex OBJECT-TYPE
   SYNTAX     INTEGER  {
                 cdv(0),
                 clr(2) }
   ACCESS     not-accessible
   STATUS     mandatory
   DESCRIPTION
     "This variable represents the atmIfVpcVpdTmBqpTable
      specific index for the atmIfVpcVpdTmBqpTable."
::= { atmIfVpcVpdTmBqpEntry 1 }

atmIfVpcVpdTmBqpValue OBJECT-TYPE
   SYNTAX     Unsigned32 (0..16777215)
   ACCESS     read-write
   STATUS     mandatory
   DESCRIPTION
     "This variable represents an individual value for the
      atmIfVpcVpdTmBqpTable."
::= { atmIfVpcVpdTmBqpEntry 2 }


-- AtmIf/n Vcc/vpi.vci Vcd Tm AvailableBitRate, 
-- AtmIf/n Vpc/vci Vpd Tm AvailableBitRate,
-- AtmIf/n Vpt/vpi Vpd Tm AvailableBitRate,
-- AtmIf/n Vpt/vpi Vcc/vci Vcd Tm AvailableBitRate
-- This component contains provisioned ABR-related attributes of a 
-- connection. It is an optional subcomponent of the Vcd Tm and Vpd 
-- Tm component. It is used to override DGCRA-related defaults in 
-- the CA Abr component. It contains the specific configuration for the 
-- ABR connection at this connection point. If this is the source of an 
-- SPVC connection, this component also contains the ABR 
-- parameters required for the SPVC call request.

atmIfVpcVpdTmAbr OBJECT IDENTIFIER ::= { atmIfVpcVpdTm 2 }



atmIfVpcVpdTmAbrRowStatusTable OBJECT-TYPE
   SYNTAX     SEQUENCE OF AtmIfVpcVpdTmAbrRowStatusEntry
   ACCESS     not-accessible
   STATUS     mandatory
   DESCRIPTION
     "This entry controls the addition and deletion of 
      atmIfVpcVpdTmAbr components."
::= { atmIfVpcVpdTmAbr 1 }

atmIfVpcVpdTmAbrRowStatusEntry OBJECT-TYPE
   SYNTAX     AtmIfVpcVpdTmAbrRowStatusEntry
   ACCESS     not-accessible
   STATUS     mandatory
   DESCRIPTION
     "A single entry in the table represents a single 
      atmIfVpcVpdTmAbr component."
   INDEX {
      atmIfIndex,
      atmIfVpcIndex,
      atmIfVpcVpdIndex,
      atmIfVpcVpdTmIndex,
      atmIfVpcVpdTmAbrIndex }
::= { atmIfVpcVpdTmAbrRowStatusTable 1 }

AtmIfVpcVpdTmAbrRowStatusEntry ::= SEQUENCE {
   atmIfVpcVpdTmAbrRowStatus
      RowStatus,
   atmIfVpcVpdTmAbrComponentName
      DisplayString,
   atmIfVpcVpdTmAbrStorageType
      StorageType,
   atmIfVpcVpdTmAbrIndex
      NonReplicated }

atmIfVpcVpdTmAbrRowStatus OBJECT-TYPE
   SYNTAX     RowStatus 
   ACCESS     read-write
   STATUS     mandatory
   DESCRIPTION
     "This variable is used as the basis for SNMP naming of
      atmIfVpcVpdTmAbr components.
      These components can be added and deleted."
::= { atmIfVpcVpdTmAbrRowStatusEntry 1 }

atmIfVpcVpdTmAbrComponentName OBJECT-TYPE
   SYNTAX     DisplayString 
   ACCESS     read-only
   STATUS     mandatory
   DESCRIPTION
     "This variable provides the component's string name for
      use with the ASCII Console Interface"
::= { atmIfVpcVpdTmAbrRowStatusEntry 2 }

atmIfVpcVpdTmAbrStorageType OBJECT-TYPE
   SYNTAX     StorageType 
   ACCESS     read-only
   STATUS     mandatory
   DESCRIPTION
     "This variable represents the storage type value for the
      atmIfVpcVpdTmAbr tables."
::= { atmIfVpcVpdTmAbrRowStatusEntry 4 }

atmIfVpcVpdTmAbrIndex OBJECT-TYPE
   SYNTAX     NonReplicated 
   ACCESS     not-accessible
   STATUS     mandatory
   DESCRIPTION
     "This variable represents the index for the atmIfVpcVpdTmAbr tables."
::= { atmIfVpcVpdTmAbrRowStatusEntry 10 }

atmIfVpcVpdTmAbrProvTable OBJECT-TYPE
   SYNTAX     SEQUENCE OF AtmIfVpcVpdTmAbrProvEntry
   ACCESS     not-accessible
   STATUS     mandatory
   DESCRIPTION
     "This group contains provisioned attributes for the ABR ATM 
      connections configured on an ATM interface."
::= { atmIfVpcVpdTmAbr 110 }

atmIfVpcVpdTmAbrProvEntry OBJECT-TYPE
   SYNTAX     AtmIfVpcVpdTmAbrProvEntry
   ACCESS     not-accessible
   STATUS     mandatory
   DESCRIPTION
     "An entry in the atmIfVpcVpdTmAbrProvTable."
   INDEX {
      atmIfIndex,
      atmIfVpcIndex,
      atmIfVpcVpdIndex,
      atmIfVpcVpdTmIndex,
      atmIfVpcVpdTmAbrIndex }
::= { atmIfVpcVpdTmAbrProvTable 1 }

AtmIfVpcVpdTmAbrProvEntry ::= SEQUENCE {
   atmIfVpcVpdTmAbrInitialCellRate
      Unsigned32,
   atmIfVpcVpdTmAbrTransientBufferExposure
      Unsigned32,
   atmIfVpcVpdTmAbrFixedRoundTripTime
      Unsigned32,
   atmIfVpcVpdTmAbrRateDecreaseFactor
      Unsigned32,
   atmIfVpcVpdTmAbrRateIncreaseFactor
      Unsigned32,
   atmIfVpcVpdTmAbrMaxCellPerRmCell
      Unsigned32,
   atmIfVpcVpdTmAbrMaxTimeBetweenRmCells
      Unsigned32,
   atmIfVpcVpdTmAbrCutoffDecreaseFactor
      Unsigned32,
   atmIfVpcVpdTmAbrAcrDecreaseTimeFactor
      Unsigned32,
   atmIfVpcVpdTmAbrDgcraMaximumDelay
      Unsigned32,
   atmIfVpcVpdTmAbrDgcraMinimumDelay
      Unsigned32,
   atmIfVpcVpdTmAbrFarEndAcrDecreaseTimeFactor
      Unsigned32,
   atmIfVpcVpdTmAbrFarEndInitialCellRate
      Unsigned32 }

atmIfVpcVpdTmAbrInitialCellRate OBJECT-TYPE
   SYNTAX     Unsigned32 (0..16777215 | 16777216 | 16777217 | 16777218)
   ACCESS     read-write
   STATUS     mandatory
   DESCRIPTION
     "This attribute specifies the Initial Cell Rate (ICR) parameter for this 
      connection. ICR is the rate at which a source should send initially 
      and after an idle period.
      
      When this attribute is set to sameAsCa, the initial cell rate is 
      determined by the AtmIf CA Abr/0 icr attribute. When the value of 
      this attribute is set to useMcr, ICR is set to the same value as the 
      Minimum Cell Rate (MCR) for the connection.
      
      When the value of this attribute is set to usePcr, ICR is set to the 
      same value as the Peak Cell Rate (PCR) for the connection.
      
      If this attribute is specified less than the MCR of the connection, 
      then the MCR is used as the ICR. If this attribute is specified more 
      than PCR of the connection, then PCR is used as the ICR.
      
      This attribute is ignored under all conditions where the operational 
      attribute abrConnectionType indicates erSwitch or efciSwitch.

      VALUES (

      16777216 = sameAsCa

      16777217 = useMcr

      16777218 = usePcr

      )"
   DEFVAL     { 16777216 }
::= { atmIfVpcVpdTmAbrProvEntry 10 }

atmIfVpcVpdTmAbrTransientBufferExposure OBJECT-TYPE
   SYNTAX     Unsigned32 (0..16777215)
   ACCESS     read-write
   STATUS     mandatory
   DESCRIPTION
     "This attribute specifies the Transient Buffer Exposure (TBE) for this 
      connection. TBE is the negotiated number of cells that the network 
      would like to limit the source to send during start-up periods, before 
      the first Resource Management (RM) cell returns.
      
      TBE divided by fixedRoundTripTime determines an upper bound 
      for the operational value of initialCellRate, the rate at which a 
      source should send initially and after an idle period.
      
      TBE divided by maxCellsPerRmCell specifies the operational value 
      of forwardRmCellLimit, the limit of the number of forward 
      Resource Management (RM) cells which may be sent in the 
      absence of received backward RM cells.
      
      This attribute is ignored under all conditions where the operational 
      attribute abrConnectionType is set to erSwitch."
   DEFVAL     { 16777215 }
::= { atmIfVpcVpdTmAbrProvEntry 11 }

atmIfVpcVpdTmAbrFixedRoundTripTime OBJECT-TYPE
   SYNTAX     Unsigned32 (0..16700000)
   ACCESS     read-write
   STATUS     mandatory
   DESCRIPTION
     "This attribute specifies the Fixed Round-Trip Time (FRTT) 
      parameter for this connection. FRTT is the sum of the fixed and 
      propagation delays from the source to a destination and back.
      
      The value of transientBufferExposure divided by the value of FRTT 
      (in seconds) determines an upper bound for the operational value of 
      initialCellRate, the rate at which a source should send initially and 
      after an idle period.
      
      This attribute is ignored under all conditions where the operational 
      attribute abrConnectionType indicates erSwitch or efciSwitch."
   DEFVAL     { 5000000 }
::= { atmIfVpcVpdTmAbrProvEntry 12 }

atmIfVpcVpdTmAbrRateDecreaseFactor OBJECT-TYPE
   SYNTAX     Unsigned32 (0..15 | 16777216)
   ACCESS     read-write
   STATUS     mandatory
   DESCRIPTION
     "This attribute specifies the Rate Decrease Factor (RDF) for this 
      connection. The RDF value is computed by using the provisioned 
      value of this attribute, n, as 2 to the inverse power n. For example, if 
      the value of this attribute is 8, RDF is 2E-8 = 1/256.
      
      RDF controls the amount by which the cell transmission rate may 
      decrease upon receipt of a backward Resource Management (RM) 
      cell. For example, if a backward RM cell is received with the 
      Congestion Indication (CI) field set to 1, the Allowed Cell Rate 
      (ACR) value would be reduced by the amount (RDF*ACR). The 
      ACR is not allowed to fall below the Minimum Cell Rate (MCR), in 
      which case the ACR is set to MCR.
      
      This attribute is ignored under all conditions where the operational 
      attribute abrConnectionType has the value erSwitch.

      VALUES (

      16777216 = sameAsCa

      )"
   DEFVAL     { 16777216 }
::= { atmIfVpcVpdTmAbrProvEntry 13 }

atmIfVpcVpdTmAbrRateIncreaseFactor OBJECT-TYPE
   SYNTAX     Unsigned32 (0..15 | 16777216)
   ACCESS     read-write
   STATUS     mandatory
   DESCRIPTION
     "This attribute specifies the Rate Increase Factor (RIF) for this 
      connection. The RIF value is computed by using the provisioned 
      value of this attribute, n, as 2 to the inverse power n. For example, if 
      the value of this attribute is 6, RIF is 2E-6 = 1/64.
      
      RIF controls the amount by which the cell transmission rate may 
      increase upon receipt of a backward Resource Management (RM) 
      cell. For example, if a backward RM cell is received with the 
      Congestion Indication (CI) and the No Increase (NI) fields both set 
      to 0, the Allowed Cell Rate (ACR) value would be increased by the 
      amount (RIF*ACR). The ACR is not allowed to exceed the Peak 
      Cell Rate (PCR), in which case the ACR is set to PCR.
      
      This attribute is ignored under all conditions where the operational 
      attribute abrConnectionType has the value erSwitch.

      VALUES (

      16777216 = sameAsCa

      )"
   DEFVAL     { 16777216 }
::= { atmIfVpcVpdTmAbrProvEntry 14 }

atmIfVpcVpdTmAbrMaxCellPerRmCell OBJECT-TYPE
   SYNTAX     Unsigned32 (2 | 4 | 8 | 16 | 32 | 64 | 128 | 256 | 16777216)
   ACCESS     read-write
   STATUS     mandatory
   DESCRIPTION
     "This attribute specifies the maximum number of cells an ABR 
      source may transmit for each forward Resource Management (RM) 
      cell. The count of the cells transmitted includes data cells, OAM 
      cells, backward RM cells, and the forward RM cell.
      
      A value of 2 is not recommended although it is permitted according 
      to the ATM Forum standard. When this attribute is set to a value of 
      2, it is possible that only one forward and one backward RM cell 
      are repeatedly transmitted, and all data traffic is queued up 
      indefinitely.
      
      This attribute is ignored under all conditions where the operational 
      attribute abrConnectionType has the value erSwitch.

      VALUES (

      16777216 = sameAsCa

      )"
   DEFVAL     { 16777216 }
::= { atmIfVpcVpdTmAbrProvEntry 15 }

atmIfVpcVpdTmAbrMaxTimeBetweenRmCells OBJECT-TYPE
   SYNTAX     Unsigned32 (781 | 1563 | 3125 | 6250 | 12500 | 25000 | 50000 | 100000 | 16777216)
   ACCESS     read-write
   STATUS     mandatory
   DESCRIPTION
     "This attribute specifies the TRM parameter for this connection.
      
      TRM provides an lower bound on the time interval between forward 
      Resource Management (RM) cells for an ABR source. Since the last 
      forward RM cell was sent, if at least TRM time has elapsed since 
      and at least two other cells have been sent, then the next cell to be 
      transmitted would be a forward RM cell.
      
      This attribute is ignored under all conditions where the operational 
      attribute abrConnectionType has the value erSwitch.
      
      The provisioned value of 781 is signalled as TRM = 0, in the ABR 
      Additional Parameters Information Element. 
      1563 is signalled as TRM = 1. 
      3125 is signalled as TRM = 2. 
      6250 is signalled as TRM = 3. 
      12500 is signalled as TRM = 4 
      25000 is signalled as TRM = 5. 
      50000 is signalled as TRM = 6. 
      100000 is signalled as TRM = 7.

      VALUES (

      16777216 = sameAsCa

      )"
   DEFVAL     { 16777216 }
::= { atmIfVpcVpdTmAbrProvEntry 16 }

atmIfVpcVpdTmAbrCutoffDecreaseFactor OBJECT-TYPE
   SYNTAX     Unsigned32 (0 | 1 | 2 | 4 | 8 | 16 | 32 | 64 | 16777216)
   ACCESS     read-write
   STATUS     mandatory
   DESCRIPTION
     "This attribute specifies the Cutoff Decrease Factor (CDF) parameter 
      for this connection. When the value of this attribute is non-zero, 
      CDF is computed as the inverse of the value. For example, if the 
      value is 32, the value of CDF is 1/32. When the value of this 
      attribute is 0, CDF is also zero.
      
      CDF controls the decrease in the Allowed Cell Rate (ACR) 
      associated with the CRM parameter, the limit of the number of 
      forward Resource Management (RM) cells which may be sent in 
      the absence of received backward RM cells. When this limit is 
      crossed, the ACR value would be decreased by the amount 
      (CDF*ACR). The ACR is not allowed to fall below the Minimum 
      Cell Rate (MCR), in which case the ACR is set to MCR.
      
      The value of CRM is indicated by the forwardRmCellLimit 
      attribute.
      
      This attribute is ignored under all conditions where the operational 
      attribute abrConnectionType indicates erSwitch or efciSwitch.

      VALUES (

      16777216 = sameAsCa

      )"
   DEFVAL     { 16777216 }
::= { atmIfVpcVpdTmAbrProvEntry 17 }

atmIfVpcVpdTmAbrAcrDecreaseTimeFactor OBJECT-TYPE
   SYNTAX     Unsigned32 (0..1023 | 16777216)
   ACCESS     read-write
   STATUS     mandatory
   DESCRIPTION
     "This attribute specifies the Allowed Cell Rate Decrease Time Factor 
      (ADTF) parameter for this connection.
      
      ADTF is the maximum time interval permitted between sending 
      forward Resource Management (RM) cells before the Allowed Cell 
      Rate (ACR) is decreased to initialCellRate. In other words, if the 
      source does not transit a forward RM cell for the period specified by 
      adtf, it reduces its ACR to the value of its initialCellRate.
      
      This attribute is ignored under all conditions where the operational 
      attribute abrConnectionType indicates erSwitch or efciSwitch.

      VALUES (

      16777216 = sameAsCa

      )"
   DEFVAL     { 16777216 }
::= { atmIfVpcVpdTmAbrProvEntry 18 }

atmIfVpcVpdTmAbrDgcraMaximumDelay OBJECT-TYPE
   SYNTAX     Unsigned32 (1..16700000 | 16777216)
   ACCESS     read-write
   STATUS     mandatory
   DESCRIPTION
     "This attribute specifies an upper bound on the delay after which the 
      rate change induced by a backward Resource Management (RM) 
      cell departing from this connection point (in the backward 
      direction) is expected to be observed at this connection point (in the 
      forward direction).
      
      This upper bound may be approximated as the sum of the round trip 
      fixed and propagation delays and the maximum queuing delays 
      between the ABR source and this interface.
      
      The value of this attribute is used in policing an ABR connection 
      using the Dynamic General Cell Rate Algorithm (DGCRA). A 
      larger value for this attribute implies a more lenient policer. When 
      there is a reduction in the Allowed Cell Rate (ACR), the policer 
      waits for a correspondingly longer period of time before it enforces 
      at the new cell rate.
      
      The value of this attribute must not be less than the 
      dgcraMinimumDelay attribute.

      VALUES (

      16777216 = sameAsCa

      )"
   DEFVAL     { 16777216 }
::= { atmIfVpcVpdTmAbrProvEntry 19 }

atmIfVpcVpdTmAbrDgcraMinimumDelay OBJECT-TYPE
   SYNTAX     Unsigned32 (1..16700000 | 16777216)
   ACCESS     read-write
   STATUS     mandatory
   DESCRIPTION
     "This attribute specifies a lower bound on the delay after which the 
      rate change induced by a backward Resource Management (RM) 
      cell departing from this connection point (in the backward 
      direction) is expected to be observed at this connection point (in the 
      forward connection).
      
      This lower bound may be approximated as the sum of the round trip 
      fixed and propagation delays between the ABR source and this 
      interface.
      
      The value of this attribute is used in policing an ABR connection 
      using the Dynamic General Cell Rate Algorithm (DGCRA). A 
      smaller value for this attribute implies a more lenient policer. When 
      there is a increase in the Allowed Cell Rate (ACR), the policer waits 
      for a correspondingly shorter period of time before it enforces at the 
      new cell rate.

      VALUES (

      16777216 = sameAsCa

      )"
   DEFVAL     { 16777216 }
::= { atmIfVpcVpdTmAbrProvEntry 20 }

atmIfVpcVpdTmAbrFarEndAcrDecreaseTimeFactor OBJECT-TYPE
   SYNTAX     Unsigned32 (0..1023 | 1024)
   ACCESS     read-write
   STATUS     mandatory
   DESCRIPTION
     "This attribute specifies the Allowed Cell Rate Decrease Time Factor 
      (ADTF) of the far end ABR source. The value specified should be 
      the same as the ADTF parameter at the far end of this ABR 
      connection. 
      
      The value of this attribute is used in policing an ABR connection 
      using the Dynamic Generic Cell Rate Algorithm (DGCRA). A 
      larger value for this attribute implies a more lenient policer. When 
      the delay between two consecutive forward Resource Management 
      (RM) cells received at this interface corresponds to a value greater 
      than the value of this attribute, the policer begins to limit enforce 
      the incoming traffic at the initial cell rate (ICR) of the far end, as 
      specified by the farEndInitialCellRate attribute.

      VALUES (

      1024 = sameAsLocal

      )"
   DEFVAL     { 1024 }
::= { atmIfVpcVpdTmAbrProvEntry 21 }

atmIfVpcVpdTmAbrFarEndInitialCellRate OBJECT-TYPE
   SYNTAX     Unsigned32 (0..16777215 | 16777219)
   ACCESS     read-write
   STATUS     mandatory
   DESCRIPTION
     "This attribute specifies the Initial Cell Rate (ICR) of the far end 
      ABR source. The value specified should be the same as the ICR 
      parameter at the far end of this ABR connection. 
      
      The value of this attribute is used in policing an ABR connection 
      using the Dynamic Generic Cell Rate Algorithm (DGCRA). A 
      larger value for this attribute implies a more lenient policer. When 
      the delay between two consecutive forward Resource Management 
      (RM) cells received at this interface corresponds to a value greater 
      than the farEndAcrDecreaseTimeFactor attribute, the policer begins 
      to enforce the incoming traffic at the value of this attribute.
      
      If this attribute is specified less than the MCR of the connection, 
      then the MCR is used as the feIcr. If this attribute is more than the 
      PCR of the connection, then PCR is used as the feIcr.

      VALUES (

      16777219 = sameAsLocal

      )"
   DEFVAL     { 16777219 }
::= { atmIfVpcVpdTmAbrProvEntry 22 }


-- AtmIf/n Vcc/vpi.vci Loop
-- The Loop component configures an ATM connection so that cells 
-- received from the ATM interface are retransmitted back to the 
-- interface through that connection. The Loop component requires 
-- exclusive use of its parent Vcc or Vpc and cannot co-exist with other 
-- ATM service components (such as Nep, Nrp, and Test).

atmIfVpcLoop OBJECT IDENTIFIER ::= { atmIfVpc 3 }



atmIfVpcLoopRowStatusTable OBJECT-TYPE
   SYNTAX     SEQUENCE OF AtmIfVpcLoopRowStatusEntry
   ACCESS     not-accessible
   STATUS     mandatory
   DESCRIPTION
     "This entry controls the addition and deletion of 
      atmIfVpcLoop components."
::= { atmIfVpcLoop 1 }

atmIfVpcLoopRowStatusEntry OBJECT-TYPE
   SYNTAX     AtmIfVpcLoopRowStatusEntry
   ACCESS     not-accessible
   STATUS     mandatory
   DESCRIPTION
     "A single entry in the table represents a single 
      atmIfVpcLoop component."
   INDEX {
      atmIfIndex,
      atmIfVpcIndex,
      atmIfVpcLoopIndex }
::= { atmIfVpcLoopRowStatusTable 1 }

AtmIfVpcLoopRowStatusEntry ::= SEQUENCE {
   atmIfVpcLoopRowStatus
      RowStatus,
   atmIfVpcLoopComponentName
      DisplayString,
   atmIfVpcLoopStorageType
      StorageType,
   atmIfVpcLoopIndex
      NonReplicated }

atmIfVpcLoopRowStatus OBJECT-TYPE
   SYNTAX     RowStatus 
   ACCESS     read-write
   STATUS     mandatory
   DESCRIPTION
     "This variable is used as the basis for SNMP naming of
      atmIfVpcLoop components.
      These components can be added and deleted."
::= { atmIfVpcLoopRowStatusEntry 1 }

atmIfVpcLoopComponentName OBJECT-TYPE
   SYNTAX     DisplayString 
   ACCESS     read-only
   STATUS     mandatory
   DESCRIPTION
     "This variable provides the component's string name for
      use with the ASCII Console Interface"
::= { atmIfVpcLoopRowStatusEntry 2 }

atmIfVpcLoopStorageType OBJECT-TYPE
   SYNTAX     StorageType 
   ACCESS     read-only
   STATUS     mandatory
   DESCRIPTION
     "This variable represents the storage type value for the
      atmIfVpcLoop tables."
::= { atmIfVpcLoopRowStatusEntry 4 }

atmIfVpcLoopIndex OBJECT-TYPE
   SYNTAX     NonReplicated 
   ACCESS     not-accessible
   STATUS     mandatory
   DESCRIPTION
     "This variable represents the index for the atmIfVpcLoop tables."
::= { atmIfVpcLoopRowStatusEntry 10 }


-- AtmIf/n Vpc/vpi TrafficManagement, 
-- AtmIf/n Vcc/vpi.vci TrafficManagement,
-- AtmIf/n Vpt/vpi TrafficManagement,
-- AtmIf/n Vpt/vpi Vcc/vci TrafficManagement
-- The Tm subcomponent contains the operational traffic management 
-- attributes of a connection. It is created dynamically for each 
-- activated Vcc, Vpc, or Vpt component.

atmIfVpcTm OBJECT IDENTIFIER ::= { atmIfVpc 9 }



atmIfVpcTmRowStatusTable OBJECT-TYPE
   SYNTAX     SEQUENCE OF AtmIfVpcTmRowStatusEntry
   ACCESS     not-accessible
   STATUS     mandatory
   DESCRIPTION
     "This entry controls the addition and deletion of 
      atmIfVpcTm components."
::= { atmIfVpcTm 1 }

atmIfVpcTmRowStatusEntry OBJECT-TYPE
   SYNTAX     AtmIfVpcTmRowStatusEntry
   ACCESS     not-accessible
   STATUS     mandatory
   DESCRIPTION
     "A single entry in the table represents a single 
      atmIfVpcTm component."
   INDEX {
      atmIfIndex,
      atmIfVpcIndex,
      atmIfVpcTmIndex }
::= { atmIfVpcTmRowStatusTable 1 }

AtmIfVpcTmRowStatusEntry ::= SEQUENCE {
   atmIfVpcTmRowStatus
      RowStatus,
   atmIfVpcTmComponentName
      DisplayString,
   atmIfVpcTmStorageType
      StorageType,
   atmIfVpcTmIndex
      NonReplicated }

atmIfVpcTmRowStatus OBJECT-TYPE
   SYNTAX     RowStatus 
   ACCESS     read-only
   STATUS     mandatory
   DESCRIPTION
     "This variable is used as the basis for SNMP naming of
      atmIfVpcTm components.
      These components cannot be added nor deleted."
::= { atmIfVpcTmRowStatusEntry 1 }

atmIfVpcTmComponentName OBJECT-TYPE
   SYNTAX     DisplayString 
   ACCESS     read-only
   STATUS     mandatory
   DESCRIPTION
     "This variable provides the component's string name for
      use with the ASCII Console Interface"
::= { atmIfVpcTmRowStatusEntry 2 }

atmIfVpcTmStorageType OBJECT-TYPE
   SYNTAX     StorageType 
   ACCESS     read-only
   STATUS     mandatory
   DESCRIPTION
     "This variable represents the storage type value for the
      atmIfVpcTm tables."
::= { atmIfVpcTmRowStatusEntry 4 }

atmIfVpcTmIndex OBJECT-TYPE
   SYNTAX     NonReplicated 
   ACCESS     not-accessible
   STATUS     mandatory
   DESCRIPTION
     "This variable represents the index for the atmIfVpcTm tables."
::= { atmIfVpcTmRowStatusEntry 10 }

atmIfVpcTmOperTable OBJECT-TYPE
   SYNTAX     SEQUENCE OF AtmIfVpcTmOperEntry
   ACCESS     not-accessible
   STATUS     mandatory
   DESCRIPTION
     "This group contains attributes for the Tm component to reflect 
      operational traffic attributes."
::= { atmIfVpcTm 100 }

atmIfVpcTmOperEntry OBJECT-TYPE
   SYNTAX     AtmIfVpcTmOperEntry
   ACCESS     not-accessible
   STATUS     mandatory
   DESCRIPTION
     "An entry in the atmIfVpcTmOperTable."
   INDEX {
      atmIfIndex,
      atmIfVpcIndex,
      atmIfVpcTmIndex }
::= { atmIfVpcTmOperTable 1 }

AtmIfVpcTmOperEntry ::= SEQUENCE {
   atmIfVpcTmTxTrafficDescType
      INTEGER,
   atmIfVpcTmTxQosClass
      INTEGER,
   atmIfVpcTmTxQueueLength
      Unsigned32,
   atmIfVpcTmTxQueueCongestionState
      Unsigned32,
   atmIfVpcTmHoldingPriority
      INTEGER,
   atmIfVpcTmRxTrafficDescType
      INTEGER,
   atmIfVpcTmRxQosClass
      INTEGER,
   atmIfVpcTmAtmServiceCategory
      INTEGER,
   atmIfVpcTmTrafficShaping
      INTEGER,
   atmIfVpcTmBearerClassBbc
      INTEGER,
   atmIfVpcTmTransferCapabilityBbc
      INTEGER,
   atmIfVpcTmClippingBbc
      INTEGER,
   atmIfVpcTmUnshapedTransmitQueueing
      INTEGER,
   atmIfVpcTmBestEffort
      INTEGER,
   atmIfVpcTmForceTagging
      INTEGER,
   atmIfVpcTmWeight
      Unsigned32,
   atmIfVpcTmUsageParameterControl
      INTEGER,
   atmIfVpcTmTxPacketWiseDiscard
      OCTET STRING,
   atmIfVpcTmRxPacketWiseDiscard
      OCTET STRING,
   atmIfVpcTmBandwidthElastic
      INTEGER,
   atmIfVpcTmBandwidthReduction
      Unsigned32,
   atmIfVpcTmAbrConnectionType
      INTEGER }

atmIfVpcTmTxTrafficDescType OBJECT-TYPE
   SYNTAX     INTEGER  {
                 n1(1),
                 n2(2),
                 n3(3),
                 n4(4),
                 n5(5),
                 n6(6),
                 n7(7),
                 n8(8),
                 n9(9) }
   ACCESS     read-only
   STATUS     mandatory
   DESCRIPTION
     "T his attribute indicates the type of traffic management which is 
      applied to the transmit direction of this connection as defined in the 
      ATM Forum. The txTrafficDescType determines the number and 
      meaning of the parameters in the txTrafficDescParm attribute."
::= { atmIfVpcTmOperEntry 10 }

atmIfVpcTmTxQosClass OBJECT-TYPE
   SYNTAX     INTEGER  {
                 n0(0),
                 n1(1),
                 n2(2),
                 n3(3),
                 n4(4),
                 notApplicable(14) }
   ACCESS     read-only
   STATUS     mandatory
   DESCRIPTION
     "This attribute indicates the quality of service for the calling to called 
      direction for this connection. This is only applicable to Soft PVC 
      and SVC connections. 
      
      Class 1 supports a QOS that meets Service Class A performance 
      requirements (Circuit emulation, constant bit rate video).
      
      Class 2 supports a QOS that meets Service Class B performance 
      requirements (Variable bit rate audio and video).
      
      Class 3 supports a QOS that meets Service Class C performance 
      requirements (Connection-Oriented Data Transfer).
      
      Class 4 supports a QOS that meets Service Class D performance 
      requirements (Connectionless Data Transfer).
      
      Class 0 is the unspecified QOS class; no objective is specified for 
      the performance parameters.
      
      A value of notApplicable is displayed in the case of nailed-up PVCs 
      for which this attribute has no significance."
::= { atmIfVpcTmOperEntry 31 }

atmIfVpcTmTxQueueLength OBJECT-TYPE
   SYNTAX     Unsigned32 (0..30720)
   ACCESS     read-only
   STATUS     mandatory
   DESCRIPTION
     "This attribute indicates the current number of cells in the transmit 
      queue for this connection. 
      
      If this connection has unshapedTransmitQueueing attribute 
      displayed as common, this attribute displays the length of the 
      common queue which is used for this atm service category. 
      
      If this connection has unshapedTransmitQueueing attribute 
      displayed as fifo, this attribute indicates the number of cells for this 
      connection which are enqueued in a first-in-first-out queuing 
      method for this atm service category. This will only occur for 
      connections on ATM IP cards with atmServiceCategory of nrtVbr 
      or ubr. 
      
      If this connection has unshapedTransmitQueueing attribute 
      displayed as perVc or as notApplicable, this attribute displays the 
      length of the per-VC queue.
      
      This attribute does not apply to basic Vpts."
::= { atmIfVpcTmOperEntry 32 }

atmIfVpcTmTxQueueCongestionState OBJECT-TYPE
   SYNTAX     Unsigned32 (0..3)
   ACCESS     read-only
   STATUS     mandatory
   DESCRIPTION
     "This attribute indicates the congestion state of the transmit queue 
      for this connection. 
      
      If this connection has unshapedTransmitQueueing attribute 
      displayed as common, this attribute displays the congestion state of 
      the common queue. If this connection has 
      unshapedTransmitQueueing attribute displayed as perVc or as 
      notApplicable, this attribute displays the congestion state of the per-
      VC queue.
      
      The congestion state of a queue is indicated by a numeric value 
      ranging from 0 to 3. When a queue is in a congested state x, only 
      traffic with discard priority (DP) 0 to x are enqueued. Traffic with 
      DP > x is discarded. 
      
      For example, if the congestion state is 3, there is no congestion and 
      all traffic is enqueued. Likewise, when the congestion state is 0, 
      there is maximum congestion and only traffic with DP=0 is 
      enqueued on that queue.
      
      This attribute does not apply to basic Vpts."
::= { atmIfVpcTmOperEntry 33 }

atmIfVpcTmHoldingPriority OBJECT-TYPE
   SYNTAX     INTEGER  {
                 n0(0),
                 n1(1),
                 n2(2),
                 n3(3),
                 n4(4),
                 notApplicable(6) }
   ACCESS     read-only
   STATUS     mandatory
   DESCRIPTION
     "This attribute indicates the actual holding priority in effect for this 
      connection. In a situation where the link bandwidth fluctuates, such 
      as over an IMA link, holding priority is used to determine which 
      connections are held and which are released. Holding priority 4 
      connections are the first to be released. Holding priority 0 
      connections are the last to be released. Some applications, for 
      example Vcc Test, may override the provisioned holding priority. 
      
      A value of notApplicable is displayed when this is an elastic 
      connection. Holding priority does not apply to bandwidth elastic 
      connections.
      
      Holding priority has no effect if the equivalent cell rate (ECR) for a 
      connection is zero.
      
      This attribute does not apply to Vpt Vccs."
::= { atmIfVpcTmOperEntry 35 }

atmIfVpcTmRxTrafficDescType OBJECT-TYPE
   SYNTAX     INTEGER  {
                 n1(1),
                 n2(2),
                 n3(3),
                 n4(4),
                 n5(5),
                 n6(6),
                 n7(7),
                 n8(8),
                 n9(9) }
   ACCESS     read-only
   STATUS     mandatory
   DESCRIPTION
     "This attribute indicates the type of traffic management which is 
      applied to the receive direction of this connection as defined in the 
      ATM Forum. The rxTrafficDescType determines the number and 
      meaning of the parameters in the rxTrafficDescParm attribute."
::= { atmIfVpcTmOperEntry 40 }

atmIfVpcTmRxQosClass OBJECT-TYPE
   SYNTAX     INTEGER  {
                 n0(0),
                 n1(1),
                 n2(2),
                 n3(3),
                 n4(4),
                 notApplicable(14) }
   ACCESS     read-only
   STATUS     mandatory
   DESCRIPTION
     "This attribute indicates the quality of service for the called to calling 
      direction for this connection. This is only applicable to Soft PVC 
      and SVC connections. 
      
      Class 1 supports a QOS that meets Service Class A performance 
      requirements (circuit emulation, constant bit rate video).
      
      Class 2 supports a QOS that meets Service Class B performance 
      requirements (variable bit rate audio and video).
      
      Class 3 supports a QOS that meets Service Class C performance 
      requirements (Connection-Oriented Data Transfer).
      
      Class 4 supports a QOS that meets Service Class D performance 
      requirements (Connectionless Data Transfer).
      
      Class 0 is the unspecified QOS class; no objective is specified for 
      the performance parameters.
      
      A value of notApplicable is displayed in the case of nailed-up PVCs 
      for which this attribute has no significance."
::= { atmIfVpcTmOperEntry 61 }

atmIfVpcTmAtmServiceCategory OBJECT-TYPE
   SYNTAX     INTEGER  {
                 unspecifiedBitRate(0),
                 constantBitRate(1),
                 rtVariableBitRate(2),
                 nrtVariableBitRate(3),
                 availableBitRate(4) }
   ACCESS     read-only
   STATUS     mandatory
   DESCRIPTION
     "This attribute indicates the ATM service category used for traffic in 
      both directions of the connection. This attribute does not apply to 
      Virtual Link VPTs and will always be displayed as 
      constantBitRate.
      
      The constantBitRate service category is intended for real time 
      applications, that is, those requiring tightly constrained delay and 
      delay variation, as would be appropriate for voice and video 
      applications. The consistent availability of a fixed quantity of 
      bandwidth is considered appropriate for CBR service. Cells which 
      are delayed beyond the value specified by Cell Transfer Delay are 
      assumed to have significantly reduced value for the application.
      
      The rtVariableBitRate service category is intended for real time 
      applications; that is those requiring tightly constrained delay and 
      delay variation, as would be appropriate for voice and video 
      applications. Sources are expected to transmit at a rate which varies 
      with time. Equivalently, the source can be described as 'bursty'. 
      Cells which are delayed beyond the value specified by Cell Transfer 
      Delay are assumed to be of significantly reduced value to the 
      application. Real time VBR service may support statistical 
      multiplexing of real time sources.
      
      The nrtVariableBitRate service category is intended for non-real 
      time applications which have bursty traffic characteristics and which 
      can be characterized in terms of a PCR, SCR, and MBS. For those 
      cells which are transferred within the traffic contract, the application 
      expects a low cell loss ratio. For all connections, it expects a bound 
      on the mean cell transfer delay. Non-real time VBR service may 
      support statistical multiplexing of connections.
      
      The availableBitRate service is an ATM layer service category for 
      which the limiting ATM layer transfer characteristics provided by 
      the network may change subsequent to connection establishment. 
      ABR service has a flow control mechanism which supports several 
      types of feedback to control the source rate in response to changing 
      ATM layer transfer characteristics. ABR service is not intended to 
      support real-time applications.
      
      The unspecifiedBitRate service is intended for non-real time 
      applications, that is those not requiring tightly constrained delay 
      and delay variation. UBR sources are expected to be bursty. UBR 
      service supports a high degree of statistical multiplexing among 
      sources. UBR service does not specify traffic related service 
      guarantees. No numerical commitments are made with respect to 
      the cell loss ratio experienced by a UBR connection, or as to the 
      cell transfer delay experienced by cells on the connection."
::= { atmIfVpcTmOperEntry 62 }

atmIfVpcTmTrafficShaping OBJECT-TYPE
   SYNTAX     INTEGER  {
                 disabled(1),
                 notApplicable(4),
                 linear(5),
                 inverseUpc(6),
                 dynamic(7) }
   ACCESS     read-only
   STATUS     mandatory
   DESCRIPTION
     "This attribute indicates the traffic shaping state of the connection.
      
      A value of notApplicable indicates that traffic shaping is not 
      applicable or not supported for this connection. This is the case:
      - when the txTrafficDescType is 1 or 2.
      - for standard Vpt Vccs and basic Vpts.
      - for CQC-based ATM cards, when the atmServiceCategory is 
      constantBitRate.
      
      In these cases, the value of notApplicable is set regardless of 
      whether traffic shaping is enabled or disabled in the provisioning 
      data.
      
      A value of disabled indicates that traffic shaping is applicable and 
      supported for the type of connection but has been turned off in the 
      provisioning data.
      
      A value of linear or inverseUpc indicates that traffic shaping is 
      applicable and supported for the type of connection and has been 
      turned on in the provisioning data. This is the only case that 
      indicates that traffic shaping is performed on the connection. In this 
      case, the actual shaping rate is reflected in the txTrafficDescParm 
      attribute, parameter number 4. A value of linear indicates that 
      traffic is being shaped at the constant rate indicated in 
      txTrafficDescParm 4.
      
      A value of inverseUpc is possible only on ATM IP cards. This value 
      indicates that the shaper strictly conforms to the requirements of a 
      dual leaky bucket UPC enforcer. This value is indicated if traffic 
      shaping is enabled, and the txTrafficDescType for this connection is 
      6, 7 or 8.
      
      Traffic shaping for connections with atmServiceCategory as 
      availableBitRate (txTrafficDescType 9) depends upon the 
      abrConnectionType attribute. If abrConnectionType is sourceDest 
      or virtualSourceDest, the value of this attribute is dynamic. If 
      abrConnectionType is erSwitch or efciSwitch, this attribute is 
      notApplicable."
::= { atmIfVpcTmOperEntry 70 }

atmIfVpcTmBearerClassBbc OBJECT-TYPE
   SYNTAX     INTEGER  {
                 a(1),
                 c(3),
                 x(16),
                 vp(24),
                 notApplicable(30) }
   ACCESS     read-only
   STATUS     mandatory
   DESCRIPTION
     "This attribute indicates the bearer capability for this connection.
      
      Class a service is a connection-oriented, constant bit rate ATM 
      transport service. Class a service has end to end timing 
      requirements and may require stringent cell loss, cell delay and cell 
      delay variation performance.When a is displayed, the user is 
      requesting more than an ATM only service. The network may look 
      at the AAL to provide interworking based upon its contents. 
      
      Class c service is a connection-oriented, variable bit rate ATM 
      transport service. Class c service has no end-to-end timing 
      requirements.When c is displayed, the user is requesting more than 
      an ATM only service. The network interworking function may look 
      at the AAL and provide service based on it.
      
      Class x service is a connection-oriented ATM transport service 
      where the AAL, trafficType (cbr or vbr), and timing requirements 
      are user defined (that is, transparent to the network). When the 
      value of this attribute is x, the user is requesting an ATM only 
      service from the network. In this case, the network shall not process 
      any higher layer protocol.
      
      Class vp service is used to indicate a transparent VP service when 
      the user is requesting an ATM only service from the network. In this 
      case, the network does not process any higher layer protocol. This 
      service differs from class x service in that with the class vp service 
      both the VCI field (except for VCI values 0, 3, 4, and 6 through 15) 
      and Payload Type field are transported transparently by the network. 
      This attribute value is only applicable to SPVP and SVP 
      connections.
      
      A value of notApplicable is displayed in the case of nailed-up PVCs 
      for which this attribute has no significance."
::= { atmIfVpcTmOperEntry 71 }

atmIfVpcTmTransferCapabilityBbc OBJECT-TYPE
   SYNTAX     INTEGER  {
                 n0(0),
                 n1(1),
                 n2(2),
                 n5(5),
                 n8(8),
                 n9(9),
                 n10(10),
                 notApplicable(30) }
   ACCESS     read-only
   STATUS     mandatory
   DESCRIPTION
     "This attribute indicates the transfer capability for this connection. 
      Uni 3.0/3.1 traffic type and end-to-end timing parameters are 
      mapped into this parameter as follows:
      <transferCapability: TrafficType, Timing>
      0: NoIndication, NoIndication
      1: NoIndication, yes
      2: NoIndication, no
      5: CBR, yes
      8: VBR, NoIndication
      9: VBR, yes
      10: VBR, no
      
      A value of notApplicable is displayed in the case of nailed-up PVCs 
      for which this attribute has no significance, or in the case that the 
      transfer capability in the call request was set to NoIndication.
      
      The CBR traffic type refers to traffic offered on services such as a 
      constant bit rate video service or a circuit emulation.
      
      The VBR traffic type refers to traffic offered on services such as 
      packetized audio and video, or data.
      
      The value NoIndication for traffic type is used if the user has not set 
      the traffic type; similarly for end-to-end timing.
      
      The value yes for end-to-end timing indicates that end-to-end 
      timing is required for the connection.
      
      The value no for end-to-end timing indicates that end-to-end timing 
      is not required for the connection."
::= { atmIfVpcTmOperEntry 72 }

atmIfVpcTmClippingBbc OBJECT-TYPE
   SYNTAX     INTEGER  {
                 no(0),
                 yes(1),
                 notApplicable(14) }
   ACCESS     read-only
   STATUS     mandatory
   DESCRIPTION
     "This attribute indicates the value of the clipping susceptibility 
      parameter in the broadband bearer capability (BBC) Information 
      Element.
      
      Clipping is an impairment in which the first fraction of a second of 
      information to be transferred is lost. It occurs after a call is 
      answered and before an associated connection is switched through.
      
      A value of notApplicable is displayed in the case of nailed-up PVCs 
      for which this attribute has no significance."
::= { atmIfVpcTmOperEntry 74 }

atmIfVpcTmUnshapedTransmitQueueing OBJECT-TYPE
   SYNTAX     INTEGER  {
                 perVc(0),
                 common(1),
                 notApplicable(4),
                 fifo(5) }
   ACCESS     read-only
   STATUS     mandatory
   DESCRIPTION
     "This attribute indicates the unshaped transmit queuing state of the 
      connection.
      
      A value of common indicates that transmit traffic is being enqueued 
      onto the common transmit queue for this service category. 
      The txQueueLength attribute indicates the current length of the 
      common transmit queue.
      
      A value of fifo indicates that transmit traffic is being queued in a 
      first-in-first-out basis for this service category. This is similar to 
      common queueing, but the txQueueLength attribute indicates the 
      number of cells in this connection queue. A value of fifo will only 
      be indicated for connections on ATM IP cards with 
      atmServiceCategory of nrtVbr or ubr. 
      A value of perVc indicates that transmit traffic is being enqueued 
      onto a per-VC queue for this connection.
      
      A value of notApplicable indicates that transmit traffic is being 
      shaped for this connection, or that unshaped transmit queuing is not 
      applicable for this type of connection. Transmit traffic for a shaped 
      connection is enqueued onto a per-VC queue, but this attribute is 
      only applicable for unshaped connections. Unshaped transmit 
      queuing is not applicable for basic Vpts."
::= { atmIfVpcTmOperEntry 75 }

atmIfVpcTmBestEffort OBJECT-TYPE
   SYNTAX     INTEGER  {
                 indicated(0),
                 notIndicated(1),
                 notApplicable(14) }
   ACCESS     read-only
   STATUS     mandatory
   DESCRIPTION
     "This attribute indicates value of best effort parameter in the ATM 
      Traffic Descriptor Information Element.
      
      The value indicated implies that the quality of service for this 
      connection is not guaranteed.
      
      The value notIndicated implies that the quality of service for this 
      connection is guaranteed.
      
      A value of notApplicable is displayed in the case of nailed-up PVCs 
      for which this attribute has no significance."
::= { atmIfVpcTmOperEntry 76 }

atmIfVpcTmForceTagging OBJECT-TYPE
   SYNTAX     INTEGER  {
                 enabled(0),
                 disabled(1) }
   ACCESS     read-only
   STATUS     mandatory
   DESCRIPTION
     "This attribute indicates the state of force tagging option for this 
      connection. Force tagging refers to setting the CLP bit for all cells 
      on a connection. 
      
      For CQC-based ATM cards, this attribute is not applicable and is 
      not displayed.
      
      A value of enabled indicates that the CLP bit is being set to 1 for all 
      cells in the transmit direction on this connection. 
      
      A value of disabled indicates that the CLP bit is unchanged for cells 
      in the transmit direction on this connection. disabled is always 
      displayed for Vpts since forced tagging is applied on a per Vpt Vcc 
      basis."
::= { atmIfVpcTmOperEntry 78 }

atmIfVpcTmWeight OBJECT-TYPE
   SYNTAX     Unsigned32 (0 | 1..4095 | 65534)
   ACCESS     read-only
   STATUS     mandatory
   DESCRIPTION
     "This attribute indicates the relative weight of this unshaped 
      connection. Connections with a larger weight get a larger proportion 
      of the link bandwidth, or in the case of standard Vpt Vccs, the Vpt 
      bandwidth. 
      
      For all but standard Vpt Vccs, the default connection weight is 
      determined by the weight policy for a service category and the 
      traffic descriptor for a connection. For standard Vpt Vccs, the 
      default connection weight is determined by the Vcc's service 
      category.
      
      For CQC-based ATM cards, this attribute is not applicable and is 
      not displayed.
      
      A value from 1 to 4095 indicates an actual weight. The value 
      upToQueueLimit indicates that the weight of a connection is up to 
      the transmit queue limit for this connection. upToQueueLimit is 
      used with common (first-in-first-out) queueing. 
      
      This attribute is displayed as notApplicable if:
      - this connection has trafficShaping displayed as linear or 
      inverseUpc.
      - this is a basic Vpt.

      VALUES (

      0 = upToQueueLimit

      65534 = notApplicable

      )"
::= { atmIfVpcTmOperEntry 79 }

atmIfVpcTmUsageParameterControl OBJECT-TYPE
   SYNTAX     INTEGER  {
                 enforced(0),
                 disabled(1),
                 notApplicable(3),
                 monitored(4),
                 abrMonitored(5),
                 abrEnforced(6) }
   ACCESS     read-only
   STATUS     mandatory
   DESCRIPTION
     "This attribute indicates the UPC state of the connection.
      
      A value of notApplicable indicates that UPC is not applicable or not 
      supported for the connection. This is the case:
      - when the connection's rxTrafficDescType is 1 or 2. 
      - for standard Vpt Vccs and basic Vpts.
      
      A value of notApplicable is set regardless of whether UPC is 
      disabled or enabled in provisioning data.
      
      A value of disabled indicates that UPC is applicable and supported 
      for the type of connection but has been turned off in the 
      provisioning data.
      
      A value of enforced indicates that UPC is actively checking 
      conformance for the connection and is discarding or tagging cells 
      which do not conform to the connection traffic contract. The traffic 
      descriptor parameters used for UPC conformance are reflected in 
      the rxTrafficDescParms of the connection. On ATM IP cards, the 
      counts of UPC violations are visible in the Vcc, Vpc, or Vpt 
      rxUpcViolationsOnEnforcer1 or rxUpcViolationsOnEnforcer2 
      attributes. 
      
      ATM IP cards provide the ability to monitor UPC violations without 
      tagging or discarding. A value of monitored indicates that UPC is 
      actively checking conformance for the connection and counting the 
      violations, but is not discarding or tagging cells which do not 
      conform to the connection traffic contract. The traffic descriptor 
      parameters used for UPC conformance are reflected in the 
      rxTrafficDescParms of the connection. The counts of UPC 
      violations are visible in the Vcc, Vpc, or Vpt 
      rxUpcViolationsOnEnforcer1 or rxUpcViolationsOnEnforcer2 
      attributes. The value of monitored appears only on ATM IP cards. 
      
      If the atmServiceCategory for this connection indicates 
      availableBitRate, a value of abrEnforced indicates that Dynamic 
      Generic Cell Rate Algorithm (DGCRA) is active for the connection 
      and that violating cells are discarded. The cell rate which is in effect 
      at any particular instant is indicated in rxTrafficDescParm 4 of the 
      connection. 
      
      If the atmServiceCategory for this connection indicates 
      availableBitRate, a value of abrMonitored indicates that Dynamic 
      Generic Cell Rate Algorithm (DGCRA) is active for the connection 
      but that violating cells are counted only. The cell rate which is in 
      effect at any particular instant is indicated in rxTrafficDescParm 4 
      of the connection."
::= { atmIfVpcTmOperEntry 80 }

atmIfVpcTmTxPacketWiseDiscard OBJECT-TYPE
   SYNTAX     OCTET STRING (SIZE (1))
   ACCESS     read-only
   STATUS     mandatory
   DESCRIPTION
     "This attribute indicates the current set of packet-wise discard 
      functions in effect in the transmit data direction at this connection 
      point.
      
      A value of ppd indicates that the Partial Packet Discard (PPD) 
      function is in effect. PPD may be applied at an intermediate 
      connecting point for a connection which is transporting frame traffic 
      (AAL5 at the endpoint). PPD is controlled by provisioning for 
      PVCs and SPVCs, and by call setup parameters in the AAL and 
      Traffic Descriptor Information Elements.
      
      A value of epd indicates that the Early Packet Discard (EPD) 
      function is in effect at this connection endpoint. On CQC-based 
      ATM cards, PPD and EPD are enabled by default at a connection 
      endpoint which is performing AAL5 segmentation and assembly.
      
      A value of wred indicates that Weighted Random Early Detection is 
      in effect at this connection point. W-RED can be enabled by 
      provisioning for PVCs and SPVCs.
      
      On ATM IP cards, all packet-wise discard functions also apply to 
      provisioned virtual path connections (VPCs). On CQC-based ATM 
      cards, packet-wise functions are not applicable for VPCs.
      
      This attribute is not applicable for Vpts.

      Description of bits:
      ppd(0)
      epd(1)
      wred(2)"
::= { atmIfVpcTmOperEntry 85 }

atmIfVpcTmRxPacketWiseDiscard OBJECT-TYPE
   SYNTAX     OCTET STRING (SIZE (1))
   ACCESS     read-only
   STATUS     mandatory
   DESCRIPTION
     "This attribute indicates the current set of packet-wise discard 
      functions in effect in the receive data direction at this connection 
      point.
      
      A value of ppd indicates that the Partial Packet Discard (PPD) 
      function is in effect. PPD may be applied at an intermediate 
      connecting point for a connection which is transporting frame traffic 
      (AAL5 at the endpoint). PPD is controlled by provisioning for 
      PVCs and SPVCs, and by call setup parameters in the AAL and 
      Traffic Descriptor Information Elements.
      
      A value of epd indicates that the Early Packet Discard (EPD) 
      function is in effect at this connection endpoint. PPD and EPD are 
      enabled by default at a connection endpoint which is performing 
      AAL5 segmentation and assembly.
      
      On ATM IP cards, all packet-wise discard functions also apply to 
      provisioned virtual path connections (VPCs). On CQC-based ATM 
      cards, packet-wise functions are not applicable for VPCs.
      
      This attribute is not applicable for Vpts.

      Description of bits:
      ppd(0)
      epd(1)"
::= { atmIfVpcTmOperEntry 86 }

atmIfVpcTmBandwidthElastic OBJECT-TYPE
   SYNTAX     INTEGER  {
                 no(0),
                 yes(1) }
   ACCESS     read-only
   STATUS     mandatory
   DESCRIPTION
     "This attribute is only of importance for connections which are 
      carried on a link with a variable bandwidth. For example, the 
      bandwidth may be reduced in the event that one or more physical 
      links in the IMA group fail, such that the originally requested 
      bandwidth cannot be maintained. This attribute shows whether the 
      application (for example, Trunk) running on this connection can 
      continue to operate if the bandwidth is reduced. If the bandwidth is 
      reduced, the amount by which it is reduced is displayed in the 
      bandwidthReduction attribute. 
      
      A value of yes, indicates that this connection is elastic, and the 
      bandwidth may be reduced but the connection is not released. 
      
      A value of no indicates that the bandwidth for this connection is not 
      reduced in the event of link bandwidth reduction. However, this 
      connection may be released based on its holdingPriority.
      
      Bandwidth elasticity has no effect for connections which have an 
      equivalent cell rate (ECR) of zero. 
      
      This attribute is not applicable for Vpts and Vpt Vccs."
::= { atmIfVpcTmOperEntry 90 }

atmIfVpcTmBandwidthReduction OBJECT-TYPE
   SYNTAX     Unsigned32 (0..2147483647)
   ACCESS     read-only
   STATUS     mandatory
   DESCRIPTION
     "This attribute shows the amount by which the bandwidth has been 
      reduced for this connection. This value is non-zero only for 
      connections which have bandwidthElastic displayed as yes, and 
      which are also operating in a reduced bandwidth mode. This is 
      typically the case for selected connections running over an IMA 
      link. This attribute takes a value from 0 (no reduction) up to the 
      ECR. For all connections which are running at their full allocated 
      bandwidth, bwReduction has the value 0. Connections which have 
      been reduced in allocated bandwidth have a positive number for this 
      attribute. The bwReduction may be subtracted from the ECR (which 
      is displayed as txTrafficDescParm 5) to determine the actual 
      bandwidth allocated to this connection."
::= { atmIfVpcTmOperEntry 100 }

atmIfVpcTmAbrConnectionType OBJECT-TYPE
   SYNTAX     INTEGER  {
                 erSwitch(1),
                 efciSwitch(2),
                 virtualSourceDest(3),
                 sourceDest(4),
                 nonAbrInterworking(5),
                 notApplicable(15) }
   ACCESS     read-only
   STATUS     mandatory
   DESCRIPTION
     "This attribute indicates the type of ABR behavior which is in effect 
      at this connection. This attribute is only applicable if the 
      atmServiceCategory attribute is availableBitRate. If the 
      atmServiceCategory attribute is not availableBitRate, or if the 
      connection is not active, this attribute value is displayed as 
      notApplicable.
      
      For CQC-based ATM cards, the only possible values are 
      notApplicable, efciSwitch or nonAbrInterworking. In EFCI 
      marking mode, the Explicit Forward Congestion Indication (EFCI) 
      field in the data cell headers is used to indicate transmit queue 
      congestion. 
      
      For ATM IP cards, if the connectionPointType is displayed as 
      connectionEndPoint, this attribute has the value sourceDest. In this 
      mode, the ABR Source and Destination behavior is in effect at this 
      connection. This attribute is also sourceDest in the case where the 
      next hop connection is specified as nonAbrInterworking. The next 
      hop connection is the Vcc or Vpc identified by the nextHop attribute 
      of the Nrp or Rp component. 
      
      If the connectionPointType is not connectionEndPoint, the value of 
      this attribute depends upon the abrConnectionType provisioning 
      and the card type to which the traffic is forwarded on the backplane. 
      The default abrConnectionType is provisioned at the CA Abr 
      abrConnectionType attribute, and may be overridden for a 
      provisioned connection in the Vcd Tm abrConnectionType or Vpd 
      Tm abrConnectionType attribute. If the CA Abr abrConnectionType 
      attribute is virtualSourceDest at either one of the two connection 
      points, and if both the connection points are defined on ATM IP 
      cards, virtual source and destination behavior is applied to the 
      connection. In this instance, the attribute displays the value 
      virtualSourceDest.
      
      This attribute has the value erSwitch if ABR explicit rate 
      functionality is in effect at this connection. In this mode, the switch 
      may modify the Explicit Rate (ER) field of backward Resource 
      Management (RM) cells to indicate the status of congestion at this 
      connection point.
      
      This attribute has the value nonAbrInterworking in the case where 
      this connection point is functioning as an SPVC origin for an ABR 
      connection where the link side of this connection is configured as a 
      non-ABR ATM service category. This means that there are no RM 
      cells on the link side of this connection, and that the next hop 
      connection point is performing as an ABR sourceDest."
::= { atmIfVpcTmOperEntry 110 }

atmIfVpcTmTxTdpTable OBJECT-TYPE
   SYNTAX     SEQUENCE OF AtmIfVpcTmTxTdpEntry
   ACCESS     not-accessible
   STATUS     mandatory
   DESCRIPTION
     "This attribute is a vector of five transmit traffic parameters whose 
      mapping is defined by the txTrafficDescType attribute. 
      
      The values of peak cell rate (PCR), sustained cell rate (SCR), 
      Minimum Cell Rate (MCR), actual cell rate (ACR), explicit rate 
      (ER), equivalent cell rate (ECR), and actual shaping rate are 
      expressed in cell/s. Maximum burst size (MBS) is expressed in 
      cells. CDVT is expressed in microseconds. 
      
      When txTrafficDescType is 1 or 2, parameters 1 through 5 are 
      unused.
      
      In this description, PCR is the greater of either the PCR or the 
      requested shaping rate (parameter 1 or parameter 5) specified in the 
      txTrafficDescParm attribute under the Vcd Tm or Vpd Tm 
      component.
      
      When txTrafficDescType is 3, parameter 1 represents the PCR for 
      CLP equal to 0 or 1 traffic; parameters 2 and 3 are unused.
      
      When txTrafficDescType is 4, parameter 1 represents the PCR for 
      CLP equal to 0 and 1 traffic; parameter 2 represents the PCR for 
      CLP equal to 0 traffic with cell discard.
      
      When txTrafficDescType is 5, parameter 1 represents the PCR for 
      CLP equal to 0 and 1 traffic; parameter 2 represents the PCR for 
      CLP equal to 0 traffic with cell tagging.
      
      When txTrafficDescType is 6, parameter 1 represents the PCR for 
      CLP equal to 0 and 1 traffic; parameter 2 represents the SCR for 
      CLP equal to 0 and 1 traffic; parameter 3 represents the MBS for 
      CLP equal to 0 and 1 traffic.
      
      When txTrafficDescType is 7, parameter 1 represents the PCR for 
      CLP equal to 0 and 1 traffic; parameter 2 represents the SCR for 
      CLP equal to 0 traffic with cell discard; parameter 3 represents the 
      MBS for CLP equal to 0 traffic.
      
      When txTrafficDescType is 8, parameter 1 represents the PCR for 
      CLP equal to 0 and 1 traffic; parameter 2 represents the SCR for 
      CLP equal to 0 traffic with cell tagging; parameter 3 represents the 
      MBS for CLP equal to 0 traffic.
      
      When txTrafficDescType is 3, 4, 5, 6, 7, or 8, parameter 4 reflects 
      the actual shaping rate in cell/s for this connection. For CQC-based 
      ATM cards, the set of available shaping rates is based on the 
      number of interfaces doing shaping (attribute 
      perVcQueueInterfaces), and the shapingScalingFactor attribute of 
      the Arc Cqc Override component. A rate of zero (0) indicates that 
      shaping is not performed, or that the interface is down. 
      
      When txTrafficDescType is 9, parameter 1 represents the PCR; 
      parameter 2 represents the Cell Delay Variation Toleration (CDVT); 
      parameter 3 represents the Minimum Cell Rate (MCR); the meaning 
      of parameter 4 depends upon the value of the abrConnectionType 
      attribute. if abrConnectionType is sourceDest or 
      virtualSourceDest, parameter 4 represents the Allowed Cell Rate 
      (ACR); If abrConnectionType is erSwitch, parameter 4 represents 
      the Explicit Rate (ER); and if abrConnectionType is efciSwitch, 
      parameter 4 reflects the actual shaping rate in cell/s for this 
      connection.
      
      When txTrafficDescType is 3, 4, 5, 6, 7, 8, or 9, parameter 5 reflects 
      the equivalent cell rate in cell/s for this connection as determined by 
      the Connection Admission Control (CAC) algorithm. The 
      equivalent cell rate is useful in determining the admission 
      characteristics of this connection."
::= { atmIfVpcTm 451 }

atmIfVpcTmTxTdpEntry OBJECT-TYPE
   SYNTAX     AtmIfVpcTmTxTdpEntry
   ACCESS     not-accessible
   STATUS     mandatory
   DESCRIPTION
     "An entry in the atmIfVpcTmTxTdpTable."
   INDEX {
      atmIfIndex,
      atmIfVpcIndex,
      atmIfVpcTmIndex,
      atmIfVpcTmTxTdpIndex }
::= { atmIfVpcTmTxTdpTable 1 }

AtmIfVpcTmTxTdpEntry ::= SEQUENCE {
   atmIfVpcTmTxTdpIndex
      Integer32,
   atmIfVpcTmTxTdpValue
      Unsigned32 }

atmIfVpcTmTxTdpIndex OBJECT-TYPE
   SYNTAX     Integer32 (1..5)
   ACCESS     not-accessible
   STATUS     mandatory
   DESCRIPTION
     "This variable represents the atmIfVpcTmTxTdpTable
      specific index for the atmIfVpcTmTxTdpTable."
::= { atmIfVpcTmTxTdpEntry 1 }

atmIfVpcTmTxTdpValue OBJECT-TYPE
   SYNTAX     Unsigned32 (0..2147483647)
   ACCESS     read-only
   STATUS     mandatory
   DESCRIPTION
     "This variable represents an individual value for the
      atmIfVpcTmTxTdpTable."
::= { atmIfVpcTmTxTdpEntry 2 }

atmIfVpcTmTxQThreshTable OBJECT-TYPE
   SYNTAX     SEQUENCE OF AtmIfVpcTmTxQThreshEntry
   ACCESS     not-accessible
   STATUS     mandatory
   DESCRIPTION
     "This attribute indicates the queue limit and the discard thresholds 
      for the transmit queue of this connection. 
      
      If this connection has unshapedTransmitQueueing attribute 
      displayed as common, this attribute displays the thresholds of the 
      common queue. If this connection has unshapedTransmitQueueing 
      attribute displayed as perVc or as notApplicable, this attribute 
      displays the thresholds of the per-VC queue.
      
      The first element indicates the queue limit. 
      
      The second element is the threshold that marks the transition from 
      congestion state 1 to congestion state 0. This is the threshold at 
      which traffic with discard priority (DP) = 1 is discarded. This 
      threshold is set at approximately 90 percent of the first parameter, 
      the operational queue limit.
      
      The third element is the threshold that marks the transition from 
      congestion state 2 to congestion state 1. This is the threshold at 
      which traffic with DP = 2 is discarded. This threshold is set at 
      approximately 75 percent of the first parameter, the operational 
      queue limit.
      
      The fourth element is the threshold that marks the transition from 
      congestion state 3 to congestion state 2. This is the threshold at 
      which traffic with DP = 3 is discarded. This threshold is set at 
      approximately 35 percent of the first parameter, the operational 
      queue limit.
      
      This attribute does not apply to basic Vpts."
::= { atmIfVpcTm 452 }

atmIfVpcTmTxQThreshEntry OBJECT-TYPE
   SYNTAX     AtmIfVpcTmTxQThreshEntry
   ACCESS     not-accessible
   STATUS     mandatory
   DESCRIPTION
     "An entry in the atmIfVpcTmTxQThreshTable."
   INDEX {
      atmIfIndex,
      atmIfVpcIndex,
      atmIfVpcTmIndex,
      atmIfVpcTmTxQThreshIndex }
::= { atmIfVpcTmTxQThreshTable 1 }

AtmIfVpcTmTxQThreshEntry ::= SEQUENCE {
   atmIfVpcTmTxQThreshIndex
      Integer32,
   atmIfVpcTmTxQThreshValue
      Unsigned32 }

atmIfVpcTmTxQThreshIndex OBJECT-TYPE
   SYNTAX     Integer32 (0..3)
   ACCESS     not-accessible
   STATUS     mandatory
   DESCRIPTION
     "This variable represents the atmIfVpcTmTxQThreshTable
      specific index for the atmIfVpcTmTxQThreshTable."
::= { atmIfVpcTmTxQThreshEntry 1 }

atmIfVpcTmTxQThreshValue OBJECT-TYPE
   SYNTAX     Unsigned32 (0..30720)
   ACCESS     read-only
   STATUS     mandatory
   DESCRIPTION
     "This variable represents an individual value for the
      atmIfVpcTmTxQThreshTable."
::= { atmIfVpcTmTxQThreshEntry 2 }

atmIfVpcTmRxTdpTable OBJECT-TYPE
   SYNTAX     SEQUENCE OF AtmIfVpcTmRxTdpEntry
   ACCESS     not-accessible
   STATUS     mandatory
   DESCRIPTION
     "This attribute is a vector of four traffic parameters whose meanings 
      are defined by the rxTrafficDescType attribute. The values of peak 
      cell rate (PCR), sustained cell rate (SCR), minimum cell rate 
      (MCR) are expressed in cell/s. Maximum burst size (MBS) is 
      expressed in cells. Cell delay variation tolerance (CDVT) is 
      expressed in microseconds.
      
      When rxTrafficDescType is 1 or 2, none of the parameters are used.
      
      When rxTrafficDescType is 3, parameter 1 represents the PCR for 
      CLP equal to 0 and 1 traffic; parameter 4 represents the CDVT.
      
      When rxTrafficDescType is 4, parameter 1 represents the PCR for 
      CLP equal to 0 and 1 traffic; parameter 2 represents the PCR for 
      CLP equal to 0 traffic with cell discard; parameter 4 represents the 
      CDVT.
      
      When rxTrafficDescType is 5, parameter 1 represents the PCR for 
      CLP equal to 0 and 1 traffic; parameter 2 represents the PCR for 
      CLP equal to 0 traffic with cell tagging; parameter 4 represents the 
      CDVT.
      
      When rxTrafficDescType is 6, parameter 1 represents the PCR for 
      CLP equal to 0 and 1 traffic; parameter 2 represents the SCR for 
      CLP equal to 0 and 1 traffic; parameter 3 represents the MBS for 
      CLP equal to 0 and 1 traffic; parameter 4 represents the CDVT. 
      
      When rxTrafficDescType is 7, parameter 1 represents the PCR for 
      CLP equal to 0 and 1 traffic; parameter 2 represents the SCR for 
      CLP equal to 0 traffic with cell discard; parameter 3 represents the 
      MBS for CLP equal to 0 traffic; parameter 4 represents the CDVT.
      
      When rxTrafficDescType is 8, parameter 1 represents the PCR for 
      CLP equal to 0 and 1 traffic; parameter 2 represents the SCR for 
      CLP equal to 0 traffic with cell tagging; parameter 3 represents the 
      MBS for CLP equal to 0 traffic; parameter 4 represents the CDVT. 
      
      When rxTrafficDescType is 9, parameter 1 represents the PCR; 
      parameter 2 represents CDVT; parameter 3 represents the MCR; 
      parameter 4 indicates the instantaneous rate at which dynamic 
      generic cell rate algorithm (DGCRA) is in effect. 
      
      If upc is disabled for this connection, the values of PCR, SCR, 
      MBS and CDVT are the provisioned parameters.
      
      If upc is enabled, the values of PCR, SCR, MBS, and CDVT are 
      exactly the values used by the usage parameter control hardware in 
      policing the arriving traffic. These may vary slightly from the 
      provisioned values due to granularity of the hardware. In the case 
      where the PCR is equal to the SCR, the effective MBS is zero."
::= { atmIfVpcTm 453 }

atmIfVpcTmRxTdpEntry OBJECT-TYPE
   SYNTAX     AtmIfVpcTmRxTdpEntry
   ACCESS     not-accessible
   STATUS     mandatory
   DESCRIPTION
     "An entry in the atmIfVpcTmRxTdpTable."
   INDEX {
      atmIfIndex,
      atmIfVpcIndex,
      atmIfVpcTmIndex,
      atmIfVpcTmRxTdpIndex }
::= { atmIfVpcTmRxTdpTable 1 }

AtmIfVpcTmRxTdpEntry ::= SEQUENCE {
   atmIfVpcTmRxTdpIndex
      Integer32,
   atmIfVpcTmRxTdpValue
      Unsigned32 }

atmIfVpcTmRxTdpIndex OBJECT-TYPE
   SYNTAX     Integer32 (1..4)
   ACCESS     not-accessible
   STATUS     mandatory
   DESCRIPTION
     "This variable represents the atmIfVpcTmRxTdpTable
      specific index for the atmIfVpcTmRxTdpTable."
::= { atmIfVpcTmRxTdpEntry 1 }

atmIfVpcTmRxTdpValue OBJECT-TYPE
   SYNTAX     Unsigned32 (0..2147483647)
   ACCESS     read-only
   STATUS     mandatory
   DESCRIPTION
     "This variable represents an individual value for the
      atmIfVpcTmRxTdpTable."
::= { atmIfVpcTmRxTdpEntry 2 }

atmIfVpcTmTqpTable OBJECT-TYPE
   SYNTAX     SEQUENCE OF AtmIfVpcTmTqpEntry
   ACCESS     not-accessible
   STATUS     mandatory
   DESCRIPTION
     "This attribute is a vector of three elements that indicate the quality 
      of service parameters for the forward direction for this connection. 
      This attribute is used for SPVC and SVC connections on a PNNI 
      interface.
      
      The cdv element indicates the acceptable peak-to-peak Cell Delay 
      Variation (CDV) of real-time connections (CBR and rt-VBR). 
      
      The ctd element indicates the acceptable maximum Cell Transfer 
      Delay (maxCtd) of real-time connections (CBR and rt-VBR). 
      
      The clr element indicates the acceptable Cell Loss Ratio (CLR) of 
      CBR, rt-VBR, and nrt-VBR connections."
::= { atmIfVpcTm 454 }

atmIfVpcTmTqpEntry OBJECT-TYPE
   SYNTAX     AtmIfVpcTmTqpEntry
   ACCESS     not-accessible
   STATUS     mandatory
   DESCRIPTION
     "An entry in the atmIfVpcTmTqpTable."
   INDEX {
      atmIfIndex,
      atmIfVpcIndex,
      atmIfVpcTmIndex,
      atmIfVpcTmTqpIndex }
::= { atmIfVpcTmTqpTable 1 }

AtmIfVpcTmTqpEntry ::= SEQUENCE {
   atmIfVpcTmTqpIndex
      INTEGER,
   atmIfVpcTmTqpValue
      Unsigned32 }

atmIfVpcTmTqpIndex OBJECT-TYPE
   SYNTAX     INTEGER  {
                 cdv(0),
                 ctd(1),
                 clr(2) }
   ACCESS     not-accessible
   STATUS     mandatory
   DESCRIPTION
     "This variable represents the atmIfVpcTmTqpTable
      specific index for the atmIfVpcTmTqpTable."
::= { atmIfVpcTmTqpEntry 1 }

atmIfVpcTmTqpValue OBJECT-TYPE
   SYNTAX     Unsigned32 (0..2147483647)
   ACCESS     read-only
   STATUS     mandatory
   DESCRIPTION
     "This variable represents an individual value for the
      atmIfVpcTmTqpTable."
::= { atmIfVpcTmTqpEntry 2 }

atmIfVpcTmRqpTable OBJECT-TYPE
   SYNTAX     SEQUENCE OF AtmIfVpcTmRqpEntry
   ACCESS     not-accessible
   STATUS     mandatory
   DESCRIPTION
     "This attribute is a vector of three elements that indicate the quality 
      of service parameters for the backward direction for this 
      connection. This attribute is used for SPVC and SVC connections 
      on a PNNI interface.
      
      The cdv element indicates the acceptable peak-to-peak Cell Delay 
      Variation (CDV) of real-time connections (CBR and rt-VBR). 
      
      The ctd element indicates the acceptable maximum Cell Transfer 
      Delay (maxCtd) of real-time connections (CBR and rt-VBR). 
      
      The clr element indicates the acceptable Cell Loss Ratio (CLR) of 
      CBR, rt-VBR, and nrt-VBR connections."
::= { atmIfVpcTm 455 }

atmIfVpcTmRqpEntry OBJECT-TYPE
   SYNTAX     AtmIfVpcTmRqpEntry
   ACCESS     not-accessible
   STATUS     mandatory
   DESCRIPTION
     "An entry in the atmIfVpcTmRqpTable."
   INDEX {
      atmIfIndex,
      atmIfVpcIndex,
      atmIfVpcTmIndex,
      atmIfVpcTmRqpIndex }
::= { atmIfVpcTmRqpTable 1 }

AtmIfVpcTmRqpEntry ::= SEQUENCE {
   atmIfVpcTmRqpIndex
      INTEGER,
   atmIfVpcTmRqpValue
      Unsigned32 }

atmIfVpcTmRqpIndex OBJECT-TYPE
   SYNTAX     INTEGER  {
                 cdv(0),
                 ctd(1),
                 clr(2) }
   ACCESS     not-accessible
   STATUS     mandatory
   DESCRIPTION
     "This variable represents the atmIfVpcTmRqpTable
      specific index for the atmIfVpcTmRqpTable."
::= { atmIfVpcTmRqpEntry 1 }

atmIfVpcTmRqpValue OBJECT-TYPE
   SYNTAX     Unsigned32 (0..2147483647)
   ACCESS     read-only
   STATUS     mandatory
   DESCRIPTION
     "This variable represents an individual value for the
      atmIfVpcTmRqpTable."
::= { atmIfVpcTmRqpEntry 2 }


-- AtmIf/n Vpc/vpi Tm AvailableBitRate, 
-- AtmIf/n Vcc/vpi.vci Tm AvailableBitRate,
-- AtmIf/n Vpt/vpi Tm AvailableBitRate,
-- AtmIf/n Vpt/vpi Vcc/vci Tm AvailableBitRate
-- This component contains ABR-related operational attributes of a 
-- connection. It is dynamically created for connections where the 
-- atmServiceCategory is availableBitRate, and where 
-- abrConnectionType is sourceDest or virtualSourceDest.

atmIfVpcTmAbr OBJECT IDENTIFIER ::= { atmIfVpcTm 2 }



atmIfVpcTmAbrRowStatusTable OBJECT-TYPE
   SYNTAX     SEQUENCE OF AtmIfVpcTmAbrRowStatusEntry
   ACCESS     not-accessible
   STATUS     mandatory
   DESCRIPTION
     "This entry controls the addition and deletion of 
      atmIfVpcTmAbr components."
::= { atmIfVpcTmAbr 1 }

atmIfVpcTmAbrRowStatusEntry OBJECT-TYPE
   SYNTAX     AtmIfVpcTmAbrRowStatusEntry
   ACCESS     not-accessible
   STATUS     mandatory
   DESCRIPTION
     "A single entry in the table represents a single 
      atmIfVpcTmAbr component."
   INDEX {
      atmIfIndex,
      atmIfVpcIndex,
      atmIfVpcTmIndex,
      atmIfVpcTmAbrIndex }
::= { atmIfVpcTmAbrRowStatusTable 1 }

AtmIfVpcTmAbrRowStatusEntry ::= SEQUENCE {
   atmIfVpcTmAbrRowStatus
      RowStatus,
   atmIfVpcTmAbrComponentName
      DisplayString,
   atmIfVpcTmAbrStorageType
      StorageType,
   atmIfVpcTmAbrIndex
      NonReplicated }

atmIfVpcTmAbrRowStatus OBJECT-TYPE
   SYNTAX     RowStatus 
   ACCESS     read-only
   STATUS     mandatory
   DESCRIPTION
     "This variable is used as the basis for SNMP naming of
      atmIfVpcTmAbr components.
      These components cannot be added nor deleted."
::= { atmIfVpcTmAbrRowStatusEntry 1 }

atmIfVpcTmAbrComponentName OBJECT-TYPE
   SYNTAX     DisplayString 
   ACCESS     read-only
   STATUS     mandatory
   DESCRIPTION
     "This variable provides the component's string name for
      use with the ASCII Console Interface"
::= { atmIfVpcTmAbrRowStatusEntry 2 }

atmIfVpcTmAbrStorageType OBJECT-TYPE
   SYNTAX     StorageType 
   ACCESS     read-only
   STATUS     mandatory
   DESCRIPTION
     "This variable represents the storage type value for the
      atmIfVpcTmAbr tables."
::= { atmIfVpcTmAbrRowStatusEntry 4 }

atmIfVpcTmAbrIndex OBJECT-TYPE
   SYNTAX     NonReplicated 
   ACCESS     not-accessible
   STATUS     mandatory
   DESCRIPTION
     "This variable represents the index for the atmIfVpcTmAbr tables."
::= { atmIfVpcTmAbrRowStatusEntry 10 }

atmIfVpcTmAbrOperTable OBJECT-TYPE
   SYNTAX     SEQUENCE OF AtmIfVpcTmAbrOperEntry
   ACCESS     not-accessible
   STATUS     mandatory
   DESCRIPTION
     "This group contains operational attributes for connections using 
      ABR service category."
::= { atmIfVpcTmAbr 110 }

atmIfVpcTmAbrOperEntry OBJECT-TYPE
   SYNTAX     AtmIfVpcTmAbrOperEntry
   ACCESS     not-accessible
   STATUS     mandatory
   DESCRIPTION
     "An entry in the atmIfVpcTmAbrOperTable."
   INDEX {
      atmIfIndex,
      atmIfVpcIndex,
      atmIfVpcTmIndex,
      atmIfVpcTmAbrIndex }
::= { atmIfVpcTmAbrOperTable 1 }

AtmIfVpcTmAbrOperEntry ::= SEQUENCE {
   atmIfVpcTmAbrInitialCellRate
      Unsigned32,
   atmIfVpcTmAbrTransientBufferExposure
      Unsigned32,
   atmIfVpcTmAbrFixedRoundTripTime
      Unsigned32,
   atmIfVpcTmAbrRateDecreaseFactor
      Unsigned32,
   atmIfVpcTmAbrRateIncreaseFactor
      Unsigned32,
   atmIfVpcTmAbrMaxCellPerRmCell
      Unsigned32,
   atmIfVpcTmAbrMaxTimeBetweenRmCell
      Unsigned32,
   atmIfVpcTmAbrCutoffDecreaseFactor
      Unsigned32,
   atmIfVpcTmAbrAcrDecreaseTimeFactor
      Unsigned32,
   atmIfVpcTmAbrForwardRmCellLimit
      Unsigned32,
   atmIfVpcTmAbrTxRateChangeInfo
      INTEGER,
   atmIfVpcTmAbrAcrRateChangeInfo
      INTEGER,
   atmIfVpcTmAbrTxFwdRmCells
      Unsigned32,
   atmIfVpcTmAbrRxEfci
      INTEGER,
   atmIfVpcTmAbrBrmRateChangeInfo
      OCTET STRING,
   atmIfVpcTmAbrBrmExplicitRate
      Unsigned32 }

atmIfVpcTmAbrInitialCellRate OBJECT-TYPE
   SYNTAX     Unsigned32 (0..16777215)
   ACCESS     read-only
   STATUS     mandatory
   DESCRIPTION
     "This attribute is applicable and is displayed only for connections for 
      which the operational Tm abrConnectionType is displayed as 
      sourceDest or virtualSourceDest. 
      
      This attribute indicates the Initial Cell Rate (ICR) parameter for this 
      connection. ICR is the rate at which a source should send initially 
      and after an idle period.
      
      For nailed-up connections, this attribute is determined by the 
      provisioned value of the initialCellRate attribute. For signalled 
      connections, it is indicated in the ABR Setup Parameters 
      Information Element.
      
      The ICR for a connection is a value between the MCR and the PCR. 
      Furthermore, ICR has an upper bound determined by the 
      transientBufferExposure divided by fixedRoundTripTime."
::= { atmIfVpcTmAbrOperEntry 10 }

atmIfVpcTmAbrTransientBufferExposure OBJECT-TYPE
   SYNTAX     Unsigned32 (0..16777215)
   ACCESS     read-only
   STATUS     mandatory
   DESCRIPTION
     "This attribute is applicable and is displayed only for connections for 
      which the operational Tm abrConnectionType is displayed as 
      sourceDest or virtualSourceDest. 
      
      This attribute indicates the Transient Buffer Exposure (TBE) for 
      this connection. TBE is the negotiated number of cells that the 
      network would like to limit the resource to send during start-up 
      periods, before the first Resource Management (RM) cell returns.
      
      For nailed-up connections, this attribute is determined by the 
      provisioned value of the transientBufferExposure attribute. For 
      signalled connections, it is indicated in the ABR Setup Parameters 
      Information Element."
::= { atmIfVpcTmAbrOperEntry 11 }

atmIfVpcTmAbrFixedRoundTripTime OBJECT-TYPE
   SYNTAX     Unsigned32 (0..16700000)
   ACCESS     read-only
   STATUS     mandatory
   DESCRIPTION
     "This attribute is applicable and is displayed only for connections for 
      which the operational Tm abrConnectionType is displayed as 
      sourceDest or virtualSourceDest. 
      
      This attribute indicates the Fixed Round-Trip Time (FRTT) 
      parameter for this connection. FRTT is the sum of the fixed and 
      propagation delays from the source to a destination and back.
      
      For nailed-up connections, this attribute is determined by the 
      provisioned value of the fixedRoundTripTime attribute. For 
      signalled connections, it is indicated in the ABR Setup Parameters 
      Information Element."
::= { atmIfVpcTmAbrOperEntry 12 }

atmIfVpcTmAbrRateDecreaseFactor OBJECT-TYPE
   SYNTAX     Unsigned32 (0..15)
   ACCESS     read-only
   STATUS     mandatory
   DESCRIPTION
     "This attribute is applicable and is displayed only for connections for 
      which the operational Tm abrConnectionType is displayed as 
      sourceDest or virtualSourceDest. 
      
      This attribute indicates the Rate Decrease Factor (RDF) for this 
      connection. The RDF value is computed by using the operational 
      value of this attribute, n, as 2 to the inverse power n. For example, if 
      the value of this attribute is 8, RDF is 2E-8 = 1/256.
      
      RDF controls the amount by which the cell transmission rate may 
      decrease upon receipt of a backward Resource Management (RM) 
      cell. For example, if a backward RM cell is received with the 
      Congestion Indication (CI) field set to 1, the Allowed Cell Rate 
      (ACR) value would be reduced by the amount (RDF*ACR). The 
      ACR is not allowed to fall below the Minimum Cell Rate (MCR), in 
      which case the ACR is set to MCR.
      
      For nailed-up connections, this attribute is determined by the 
      provisioned value of the rateDecreaseFactor attribute. For signalled 
      connections, it is indicated in the ABR Setup Parameters 
      Information Element."
::= { atmIfVpcTmAbrOperEntry 13 }

atmIfVpcTmAbrRateIncreaseFactor OBJECT-TYPE
   SYNTAX     Unsigned32 (0..15)
   ACCESS     read-only
   STATUS     mandatory
   DESCRIPTION
     "This attribute is applicable and is displayed only for connections for 
      which the operational Tm abrConnectionType is displayed as 
      sourceDest or virtualSourceDest. 
      
      This attribute indicates the Rate Increase Factor (RIF) for this 
      connection. The RIF value is computed by using the operational 
      value of this attribute, n, as 2 to the inverse power n. For example, if 
      the value of this attribute is 6, RIF is 2E-6 = 1/64.
      
      RIF controls the amount by which the cell transmission rate may 
      increase upon receipt of a backward Resource Management (RM) 
      cell. For example, if a backward RM cell is received with the 
      Congestion Indication (CI) and the No Increase (NI) fields both set 
      to 0, the Allowed Cell Rate (ACR) value would be increased by the 
      amount (RIF*ACR). The ACR is not allowed to exceed the Peak 
      Cell Rate (PCR), in which case the ACR is set to PCR.
      
      For nailed-up connections, this attribute is determined by the 
      provisioned value of the rateIncreaseFactor attribute. For signalled 
      connections, it is indicated in the ABR Setup Parameters 
      Information Element."
::= { atmIfVpcTmAbrOperEntry 14 }

atmIfVpcTmAbrMaxCellPerRmCell OBJECT-TYPE
   SYNTAX     Unsigned32 (2 | 4 | 8 | 16 | 32 | 64 | 128 | 256)
   ACCESS     read-only
   STATUS     mandatory
   DESCRIPTION
     "This attribute is applicable and is displayed only for connections for 
      which the operational Tm abrConnectionType is displayed as 
      sourceDest or virtualSourceDest. 
      
      This attribute indicates the maximum number of cells an ABR 
      source may transmit for each forward Resource Management (RM) 
      cell. The count of the cells transmitted includes data cells, OAM 
      cells, backward RM cells, and the forward RM cell.
      
      For nailed-up connections, this attribute is determined by the 
      provisioned value of the maxCellsPerRmCell attribute. For 
      signalled connections, it is indicated in the ABR Additional 
      Parameters Information Element."
::= { atmIfVpcTmAbrOperEntry 15 }

atmIfVpcTmAbrMaxTimeBetweenRmCell OBJECT-TYPE
   SYNTAX     Unsigned32 (781 | 1563 | 3125 | 6250 | 12500 | 25000 | 50000 | 100000)
   ACCESS     read-only
   STATUS     mandatory
   DESCRIPTION
     "This attribute is applicable and is displayed only for connections for 
      which the operational Tm abrConnectionType is displayed as 
      sourceDest or virtualSourceDest. 
      
      This attribute indicates the TRM parameter for this connection.
      
      TRM provides an upper bound on the time interval between forward 
      Resource Management (RM) cells for an ABR source. Since the last 
      forward RM cell was sent, if at least TRM time has elapsed since 
      and at least 2 other cells have been sent, the next cell to be 
      transmitted would be a forward RM cell.
      
      For nailed-up connections, this attribute is determined by the 
      provisioned value of the maxTimeBetweenRmCell attribute. For 
      signalled connections, it is indicated in the ABR Additional 
      Parameters Information Element."
::= { atmIfVpcTmAbrOperEntry 16 }

atmIfVpcTmAbrCutoffDecreaseFactor OBJECT-TYPE
   SYNTAX     Unsigned32 (0 | 1 | 2 | 4 | 8 | 16 | 32 | 64)
   ACCESS     read-only
   STATUS     mandatory
   DESCRIPTION
     "This attribute is applicable and is displayed only for connections for 
      which the operational Tm abrConnectionType is displayed as 
      sourceDest or virtualSourceDest. 
      
      This attribute indicates the Cutoff Decrease Factor (CDF) parameter 
      for this connection. When the value of this attribute is non-zero, 
      CDF is computed as the inverse of the value. For example, if the 
      value is 32, the value of CDF is 1/32. When the value of this 
      attribute is 0, CDF is also zero.
      
      CDF controls the decrease in the Allowed Cell Rate (ACR) 
      associated with the forwardRmCellLimit attribute, the limit of the 
      number of forward Resource Management (RM) cells which may 
      be sent in the absence of received backward RM cells. When this 
      limit is crossed, the ACR value would be decreased by the amount 
      (CDF*ACR). The ACR is not allowed to fall below the Minimum 
      Cell Rate (MCR), in which case the ACR is set to MCR.
      
      For nailed-up connections, this attribute is determined by the 
      provisioned value of the cutoffDecreaseFactor attribute. For 
      signalled connections, it is indicated in the ABR Additional 
      Parameters Information Element."
::= { atmIfVpcTmAbrOperEntry 17 }

atmIfVpcTmAbrAcrDecreaseTimeFactor OBJECT-TYPE
   SYNTAX     Unsigned32 (0..1023)
   ACCESS     read-only
   STATUS     mandatory
   DESCRIPTION
     "This attribute is applicable and is displayed only for connections for 
      which the operational Tm abrConnectionType is displayed as 
      sourceDest or virtualSourceDest. 
      
      This attribute indicates the Allowed Cell Rate Decrease Time Factor 
      (ADTF) parameter for this connection.
      
      ADTF is the time interval permitted between sending forward 
      Resource Management (RM) cells before the Allowed Cell Rate 
      (ACR) is decreased to initialCellRate. In other words, if the source 
      does not transit a forward RM cell for the period specified by adtf, it 
      reduces its ACR to the value of its initialCellRate.
      
      For nailed-up connections, this attribute is determined by the 
      provisioned value of the acrDecreaseTimeFactor attribute. For 
      signalled connections, it is indicated in the ABR Additional 
      Parameters Information Element."
::= { atmIfVpcTmAbrOperEntry 18 }

atmIfVpcTmAbrForwardRmCellLimit OBJECT-TYPE
   SYNTAX     Unsigned32 (1 | 3 | 7 | 15 | 31 | 63 | 127 | 255 | 511 | 1023 | 2047 | 4095)
   ACCESS     read-only
   STATUS     mandatory
   DESCRIPTION
     "This attribute is applicable and is displayed only for connections for 
      which the operational Tm abrConnectionType is displayed as 
      sourceDest or virtualSourceDest. 
      
      This attribute indicates the CRM parameter for this connection.
      
      CRM is the limit of the number of forward Resource Management 
      (RM) cells which may be sent in the absence of received backward 
      RM cells. When this limit is crossed, the Allowed Cell Rate (ACR) 
      value would be decreased by the amount (CDF*ACR), where CDF 
      is determined by the cutoffDecreaseFactor. The ACR is not allowed 
      to fall below the Minimum Cell Rate (MCR), in which case the 
      ACR is set to MCR.
      
      The value of CRM is obtained as transientBufferExposure divided 
      by maxCellsPerRmCell."
::= { atmIfVpcTmAbrOperEntry 19 }

atmIfVpcTmAbrTxRateChangeInfo OBJECT-TYPE
   SYNTAX     INTEGER  {
                 congestionIndicated(0),
                 noIncreaseIndicated(1),
                 explicitRateIndicated(2) }
   ACCESS     read-only
   STATUS     obsolete
   DESCRIPTION
     "THIS ATTRIBUTE IS HISTORICAL:This attribute indicates the 
      rate change information put into the last forward Resource 
      Management (RM) cell turned around as a backward-RM cell. For 
      connections configured as an ABR Source or Destination, the 
      turned around backward-RM cell is sent over the interface. For 
      connections configured as an ABR Virtual Source or Virtual 
      Destination, the turned around backward-RM cell is sent over the 
      backplane."
::= { atmIfVpcTmAbrOperEntry 20 }

atmIfVpcTmAbrAcrRateChangeInfo OBJECT-TYPE
   SYNTAX     INTEGER  {
                 noChange(0),
                 decreasedByRdf(1),
                 increasedByRif(2),
                 setToExplicitRate(3),
                 notApplicable(15) }
   ACCESS     read-only
   STATUS     mandatory
   DESCRIPTION
     "This attribute is applicable and is displayed only for connections for 
      which the operational Tm abrConnectionType is displayed as 
      sourceDest or virtualSourceDest. 
      
      This attribute indicates the type of change in the Allowed Cell Rate 
      (ACR) as a result of the information in the last backward Resource 
      Management (B-RM) cell received from the interface.
      
      This attribute value is only applicable when the Vcc Tm or Vpc Tm 
      abrConnectionType attribute is sourceDest or VirtualSourceDest. 
      In all other cases, this attribute value is notApplicable.
      
      A value of noChange indicates that the rate did not change as a 
      result of the last backward RM cell received.
      
      A value of decreasedByRdf or increasedByRif indicates that the 
      ACR was increased or decreased by the corresponding factor. This 
      change is as a result of the CI or NI bit setting in the last backward 
      RM cell, or an ADTF timeout.
      
      A value of setToExplicitRate indicates that the ACR was set to the 
      ER value in the last backward RM cell."
::= { atmIfVpcTmAbrOperEntry 21 }

atmIfVpcTmAbrTxFwdRmCells OBJECT-TYPE
   SYNTAX     Unsigned32 (0..4095)
   ACCESS     read-only
   STATUS     mandatory
   DESCRIPTION
     "This attribute is applicable and is displayed only for connections for 
      which the operational Tm abrConnectionType is displayed as 
      sourceDest or virtualSourceDest. 
      
      This attribute counts the number of forward Resource Management 
      (RM) cells sent over the interface since the last backward RM-cell 
      was received from the interface. If the value of this attribute is 
      greater than or equal to the value of forwardRmCellLimit, the 
      Allowed Cell Rate (ACR) value would be decreased by the amount 
      (CDF*ACR), where CDF is determined by the 
      cutoffDecreaseFactor.
      
      This counter is reset to zero each time a backward-RM cell is 
      received.
      
      This counter does not wrap to zero if it reaches its maximum value 
      of 4095 in order to indicate that no backward RM cell has been 
      received."
::= { atmIfVpcTmAbrOperEntry 22 }

atmIfVpcTmAbrRxEfci OBJECT-TYPE
   SYNTAX     INTEGER  {
                 notIndicated(0),
                 indicated(1) }
   ACCESS     read-only
   STATUS     mandatory
   DESCRIPTION
     "This attribute is applicable and is displayed only for connections for 
      which the operational Tm abrConnectionType is displayed as 
      sourceDest or virtualSourceDest. 
      
      This attribute indicates the value of the Explicit Forward 
      Congestion Indication (EFCI) bit of the last data cell received from 
      the interface.
      
      When a forward Resource Management (RM) cell is turned around 
      as a backward-RM cell, the Congestion Indication (CI) field of the 
      backward-RM cell is set to 1, if the value of this attribute is 
      indicated.
      
      This attribute is set to notIndicated each time a backward-RM cell 
      is transmitted."
::= { atmIfVpcTmAbrOperEntry 23 }

atmIfVpcTmAbrBrmRateChangeInfo OBJECT-TYPE
   SYNTAX     OCTET STRING (SIZE (1))
   ACCESS     read-only
   STATUS     mandatory
   DESCRIPTION
     "This attribute is applicable and is displayed only for connections for 
      which the operational Tm abrConnectionType is displayed as 
      sourceDest, virtualSourceDest or explicitRate. 
      
      This attribute indicates the values of key fields which affect the rate 
      change. These fields are from the most recent Backward Resource 
      Management (B-RM) cell on this connection. These fields may have 
      been set by a connection point at some switch prior to the B-RM 
      cell arriving at this connection point. 
      
      A value of ci indicates that the Congestion Indication (CI) field is 
      set in the B-RM cell. A value of ni indicates that the No Increase 
      (NI) field is set in the B-RM cell. A value of er indicates that a rate 
      decrease is indicated by the Explicit Rate in the B-RM cell having a 
      value lower than the Current Cell Rate (CCR) field in the B-RM 
      cell. The actual explicit rate from the B-RM cell is shown in the 
      brmEr attribute of this component.

      Description of bits:
      ci(0)
      ni(1)
      er(2)"
::= { atmIfVpcTmAbrOperEntry 24 }

atmIfVpcTmAbrBrmExplicitRate OBJECT-TYPE
   SYNTAX     Unsigned32 (0..16777215)
   ACCESS     read-only
   STATUS     mandatory
   DESCRIPTION
     "This attribute is applicable and is displayed only for connections for 
      which the operational Tm abrConnectionType is displayed as 
      sourceDest, virtualSourceDest or explicitRate. 
      
      This attribute indicates the value of the Explicit Rate field from the 
      most recent Backward Resource Management (B-RM) cell on this 
      connection. This is the rate from the B-RM cell which may be 
      different from the explicit rate (ER) offered at this connection point. 
      Specifically, this attribute may indicate the ER which has been set in 
      the B-RM cell by some connection point before the B-RM cell 
      arrived at this connection point."
::= { atmIfVpcTmAbrOperEntry 25 }


-- AtmIf/n VirtualChannelConnection/vpi.vci 
-- This component represents a virtual channel connection (VCC).
-- 
-- For Vccs directly beneath the AtmIf, the instance value defines the 
-- VPI and VCI values for this connectionfor example, Vcc/16.32 
-- would define a connection with a VPI of 16 and a VCI of 32.
-- 
-- The VPI can be in the range of 0 to 4095 and the VCI can be in the 
-- range of 0 to 65535. Note that a Vcc instance of 0.0 is invalid as 
-- defined in the ATM Forum.

atmIfVcc OBJECT IDENTIFIER ::= { atmIf 5 }



atmIfVccRowStatusTable OBJECT-TYPE
   SYNTAX     SEQUENCE OF AtmIfVccRowStatusEntry
   ACCESS     not-accessible
   STATUS     mandatory
   DESCRIPTION
     "This entry controls the addition and deletion of 
      atmIfVcc components."
::= { atmIfVcc 1 }

atmIfVccRowStatusEntry OBJECT-TYPE
   SYNTAX     AtmIfVccRowStatusEntry
   ACCESS     not-accessible
   STATUS     mandatory
   DESCRIPTION
     "A single entry in the table represents a single 
      atmIfVcc component."
   INDEX {
      atmIfIndex,
      atmIfVccIndex }
::= { atmIfVccRowStatusTable 1 }

AtmIfVccRowStatusEntry ::= SEQUENCE {
   atmIfVccRowStatus
      RowStatus,
   atmIfVccComponentName
      DisplayString,
   atmIfVccStorageType
      StorageType,
   atmIfVccIndex
      AsciiStringIndex }

atmIfVccRowStatus OBJECT-TYPE
   SYNTAX     RowStatus 
   ACCESS     read-write
   STATUS     mandatory
   DESCRIPTION
     "This variable is used as the basis for SNMP naming of
      atmIfVcc components.
      These components can be added and deleted."
::= { atmIfVccRowStatusEntry 1 }

atmIfVccComponentName OBJECT-TYPE
   SYNTAX     DisplayString 
   ACCESS     read-only
   STATUS     mandatory
   DESCRIPTION
     "This variable provides the component's string name for
      use with the ASCII Console Interface"
::= { atmIfVccRowStatusEntry 2 }

atmIfVccStorageType OBJECT-TYPE
   SYNTAX     StorageType 
   ACCESS     read-only
   STATUS     mandatory
   DESCRIPTION
     "This variable represents the storage type value for the
      atmIfVcc tables."
::= { atmIfVccRowStatusEntry 4 }

atmIfVccIndex OBJECT-TYPE
   SYNTAX     AsciiStringIndex (SIZE (3..10))
   ACCESS     not-accessible
   STATUS     mandatory
   DESCRIPTION
     "This variable represents the index for the atmIfVcc tables."
::= { atmIfVccRowStatusEntry 10 }

atmIfVccStateTable OBJECT-TYPE
   SYNTAX     SEQUENCE OF AtmIfVccStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { atmIfVcc 100 }

atmIfVccStateEntry OBJECT-TYPE
   SYNTAX     AtmIfVccStateEntry
   ACCESS     not-accessible
   STATUS     mandatory
   DESCRIPTION
     "An entry in the atmIfVccStateTable."
   INDEX {
      atmIfIndex,
      atmIfVccIndex }
::= { atmIfVccStateTable 1 }

AtmIfVccStateEntry ::= SEQUENCE {
   atmIfVccAdminState
      INTEGER,
   atmIfVccOperationalState
      INTEGER,
   atmIfVccUsageState
      INTEGER }

atmIfVccAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { atmIfVccStateEntry 1 }

atmIfVccOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { atmIfVccStateEntry 2 }

atmIfVccUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { atmIfVccStateEntry 3 }

atmIfVccOperTable OBJECT-TYPE
   SYNTAX     SEQUENCE OF AtmIfVccOperEntry
   ACCESS     not-accessible
   STATUS     mandatory
   DESCRIPTION
     "This group contains operational information for a Vcc, Vpc, or Vpt 
      component."
::= { atmIfVcc 110 }

atmIfVccOperEntry OBJECT-TYPE
   SYNTAX     AtmIfVccOperEntry
   ACCESS     not-accessible
   STATUS     mandatory
   DESCRIPTION
     "An entry in the atmIfVccOperTable."
   INDEX {
      atmIfIndex,
      atmIfVccIndex }
::= { atmIfVccOperTable 1 }

AtmIfVccOperEntry ::= SEQUENCE {
   atmIfVccConnectionPointType
      INTEGER }

atmIfVccConnectionPointType OBJECT-TYPE
   SYNTAX     INTEGER  {
                 connectionEndPoint(0),
                 segmentEndPoint(1),
                 connectingPoint(2),
                 unknown(3) }
   ACCESS     read-only
   STATUS     mandatory
   DESCRIPTION
     "This attribute reflects the role of the connection component at this 
      interface.
      
      A value of connectionEndPoint indicates that user cells, end-to-end 
      OAM cells, and segment OAM cells are processed by the 
      connection component.
      
      A value of segmentEndPoint indicates that user cells and end-to-
      end OAM cells are relayed by the connection component, while 
      segment OAM cells are processed by the connection component.
      
      A value of connectingPoint indicates that user cells, end-to-end 
      OAM cells, and segment OAM cells are relayed by the connection 
      component.
      
      A value of unknown indicates that the connection component is 
      inactive."
::= { atmIfVccOperEntry 10 }

atmIfVccConnInfoTable OBJECT-TYPE
   SYNTAX     SEQUENCE OF AtmIfVccConnInfoEntry
   ACCESS     not-accessible
   STATUS     mandatory
   DESCRIPTION
     "This group contains operational connection characteristics 
      information for a Vcc component."
::= { atmIfVcc 115 }

atmIfVccConnInfoEntry OBJECT-TYPE
   SYNTAX     AtmIfVccConnInfoEntry
   ACCESS     not-accessible
   STATUS     mandatory
   DESCRIPTION
     "An entry in the atmIfVccConnInfoTable."
   INDEX {
      atmIfIndex,
      atmIfVccIndex }
::= { atmIfVccConnInfoTable 1 }

AtmIfVccConnInfoEntry ::= SEQUENCE {
   atmIfVccDistributionType
      INTEGER,
   atmIfVccNumLeaves
      Gauge32,
   atmIfVccCallDirection
      INTEGER }

atmIfVccDistributionType OBJECT-TYPE
   SYNTAX     INTEGER  {
                 pointToPoint(0),
                 pointToMultipoint(1) }
   ACCESS     read-only
   STATUS     mandatory
   DESCRIPTION
     "This attribute indicates the way data is distributed in the connection.
      
      A value of pointToPoint indicates this connection point is part of a 
      point-to-point connection.
      
      A value of pointToMultipoint indicates this connection point is part 
      of a point-to-multipoint connection."
   DEFVAL     { pointToPoint }
::= { atmIfVccConnInfoEntry 11 }

atmIfVccNumLeaves OBJECT-TYPE
   SYNTAX     Gauge32 (0..2147483647)
   ACCESS     read-only
   STATUS     mandatory
   DESCRIPTION
     "This attribute indicates the number of destination leaves of the 
      connection. If the distributionType is pointToPoint the value of this 
      attribute is 0."
   DEFVAL     { 0 }
::= { atmIfVccConnInfoEntry 12 }

atmIfVccCallDirection OBJECT-TYPE
   SYNTAX     INTEGER  {
                 fromLink(0),
                 toLink(1),
                 notApplicable(2) }
   ACCESS     read-only
   STATUS     mandatory
   DESCRIPTION
     "This attribute indicates the direction of the call setup request for an 
      SVC.
      
      A value of fromLink means that the call setup originated from the 
      link.
      
      A value of toLink means that the call setup was directed to the link.
      
      For PVC connections, the value of this attribute is notApplicable.
      
      For SPVC connections, the value of this attribute is notApplicable 
      for Vccs with the SourcePVC and DestinationPVC subcomponents.
      
      For Signalling channels, the value of this attribute is notApplicable."
   DEFVAL     { notApplicable }
::= { atmIfVccConnInfoEntry 13 }

atmIfVccStatusTable OBJECT-TYPE
   SYNTAX     SEQUENCE OF AtmIfVccStatusEntry
   ACCESS     not-accessible
   STATUS     mandatory
   DESCRIPTION
     "This group contains operational status information for a Vcc, Vpc, 
      or Vpt component."
::= { atmIfVcc 120 }

atmIfVccStatusEntry OBJECT-TYPE
   SYNTAX     AtmIfVccStatusEntry
   ACCESS     not-accessible
   STATUS     mandatory
   DESCRIPTION
     "An entry in the atmIfVccStatusTable."
   INDEX {
      atmIfIndex,
      atmIfVccIndex }
::= { atmIfVccStatusTable 1 }

AtmIfVccStatusEntry ::= SEQUENCE {
   atmIfVccOperStatus
      INTEGER,
   atmIfVccLocalFailureCause
      INTEGER,
   atmIfVccTroubled
      INTEGER,
   atmIfVccSegLinkSideLoopbackState
      INTEGER,
   atmIfVccSegSwitchSideLoopbackState
      INTEGER,
   atmIfVccEndToEndLoopbackState
      INTEGER,
   atmIfVccRxOamCellCongestionState
      INTEGER,
   atmIfVccAisState
      INTEGER,
   atmIfVccRdiState
      INTEGER }

atmIfVccOperStatus OBJECT-TYPE
   SYNTAX     INTEGER  {
                 unknown(0),
                 end2endUp(1),
                 end2endDown(2),
                 localUpEnd2endUnknown(3),
                 localDown(4) }
   ACCESS     read-only
   STATUS     mandatory
   DESCRIPTION
     "This attribute indicates the present operational status of the Vcc, 
      Vpc, or Vpt component. Its value is dependent upon the current state 
      of the segLinkSideLoopbackState and endToEndLoopbackState 
      attributes.
      
      The value is end2endUp when the endToEndLoopbackState is good 
      and the segLinkSideLoopbackState is either good or unknown.
      
      The value is end2endDown when the endToEndLoopbackState is 
      bad and the segLinkSideLoopbackState is either good or unknown.
      
      The value is localUpEnd2endUnknown when the 
      endToEndLoopbackState is unknown and the 
      segLinkSideLoopbackState is good.
      
      The value is localDown when segLinkSideLoopbackState is bad.
      
      The value is localUpEnd2endUnknown when the 
      endToEndLoopbackState is notApplicable and the 
      segLinkSideLoopbackState is good.
      
      The value is unknown when the endToEndLoopbackState is either 
      unknown or notApplicable and the segLinkSideLoopbackState is 
      unknown."
::= { atmIfVccStatusEntry 20 }

atmIfVccLocalFailureCause OBJECT-TYPE
   SYNTAX     INTEGER  {
                 noFailure(0),
                 localBwLoss(1),
                 portDown(2),
                 notAdmitted(3),
                 appNotRegistered(4),
                 disabledByApp(5),
                 bwReduced(6),
                 vpDown(7) }
   ACCESS     read-only
   STATUS     mandatory
   DESCRIPTION
     "This attribute indicates the failure cause of the Vcc, Vpc, or Vpt 
      component. noFailure indicates that there is currently no 
      bandwidth related failure for this connection. 
      
      portDown indicates that the interface corresponding to the parent 
      AtmIf is down. 
      
      localBwLoss indicates that the Ima corresponding to this AtmIf has 
      lost some, but not all bandwidth, and as a result, this connection has 
      been released.
      
      notAdmitted indicates that this connection has failed to be admitted 
      by the Connection Admission Control (CAC) algorithm.
      
      appNotRegistered indicates that there is no application registered to 
      use this connection. This may be the case, for example when there 
      is a Vcc Test application, but the test has not been started. Check the 
      status of the application to determine why it is not functional.
      
      disabledByApp indicates that the application using this connection 
      has requested that the connection be disabled. An example is a 
      connection used by a trunk application where the trunk has timed 
      out on an attempt to stage. Check the application to determine why 
      it is not fully functional.
      
      bwReduced indicates that this connection is operating in a reduced 
      bandwidth state. It is a bandwidth elastic connection which 
      currently has been allocated less than the requested (equivalent) 
      bandwidth.
      
      vpDown indicates that this connection has been notified of a fault 
      detected at the associated VP-layer. vpDown is applicable for Vpt 
      Vccs only."
::= { atmIfVccStatusEntry 25 }

atmIfVccTroubled OBJECT-TYPE
   SYNTAX     INTEGER  {
                 no(0),
                 yes(1) }
   ACCESS     read-only
   STATUS     mandatory
   DESCRIPTION
     "This attribute indicates whether or not the connection is in a 
      troubled state. Connections become troubled because of OAM 
      failures; when one of the attributes segLinkSideLoopbackState, 
      segSwitchSideLoopbackState, endToEndLoopbackState, aisState 
      (when receiving AIS cells only) or rdiState go bad, this attribute is 
      set to yes; otherwise it is set to no."
   DEFVAL     { no }
::= { atmIfVccStatusEntry 28 }

atmIfVccSegLinkSideLoopbackState OBJECT-TYPE
   SYNTAX     INTEGER  {
                 good(0),
                 bad(1),
                 unknown(2),
                 notApplicable(3) }
   ACCESS     read-only
   STATUS     mandatory
   DESCRIPTION
     "This attribute contains the current state of the link-side segment 
      loopback for this connection. Link-side segment loopback cells are 
      transmitted (inserted) by a connection component in the direction of 
      the link (port). The value of this attribute is dependent upon the 
      current setting of the segLinkSideLoopback provisionable attribute, 
      the connection point type as specified by the connectionPointType 
      attribute, and the current loopback state (if applicable).
      
      The value is notApplicable when the connectionPointType is a 
      connectingPoint. 
      
      The value is notApplicable when the distributionType is 
      pointToMultipoint.
      
      The value is good when the segLinkSideLoopback is on, the 
      connectionPointType is a segmentEndPoint or a 
      connectionEndPoint, and the segment link side loopback is 
      working.
      
      The value is bad when the segLinkSideLoopback is on, the 
      connectionPointType is a segmentEndPoint or a 
      connectionEndPoint, and the link side segment loopback is not 
      working.
      
      The value is unknown when the segLinkSideLoopback is off.
      
      The value is unknown when the segLinkSideLoopback is on, the 
      connectionPointType is a segmentEndPoint and the segment switch 
      side loopback has not yet been determined.
      
      The state of this attribute determines, in part, the value of the 
      operStatus attribute."
::= { atmIfVccStatusEntry 30 }

atmIfVccSegSwitchSideLoopbackState OBJECT-TYPE
   SYNTAX     INTEGER  {
                 good(0),
                 bad(1),
                 unknown(2),
                 notApplicable(3) }
   ACCESS     read-only
   STATUS     mandatory
   DESCRIPTION
     "This attribute contains the current state of the switch-side segment 
      loopback for this connection. Switch-side segment loopback cells 
      are transmitted (inserted) by a connection component in the 
      direction of the bus. The value of this attribute is dependent upon 
      the current setting of the segSwitchSideLoopback provisionable 
      attribute, the connection point type as specified by the 
      connectionPointType attribute, and the current loopback state (if 
      applicable).
      
      The value is only applicable when the connectionPointType is a 
      segmentEndPoint. 
      
      The value is notApplicable when the connectionPointType is a 
      connectingPoint or connectionEndPoint. 
      
      The value is notApplicable when the distributionType is 
      pointToMultipoint.
      
      The value is good when the segSwitchSideLoopback is on, the 
      connectionPointType is a segmentEndPoint and the segment switch 
      side loopback is working.
      
      The value is bad when the segSwitchSideLoopback is on, the 
      connectionPointType is a segmentEndPoint and the switch side 
      segment loopback is not working.
      
      The value is unknown when the segSwitchSideLoopback is off.
      
      The value is unknown when the segSwitchSideLoopback is on, the 
      connectionPointType is a segmentEndPoint and the segment switch 
      side loopback has not been determined."
::= { atmIfVccStatusEntry 40 }

atmIfVccEndToEndLoopbackState OBJECT-TYPE
   SYNTAX     INTEGER  {
                 good(0),
                 bad(1),
                 unknown(2),
                 notApplicable(3) }
   ACCESS     read-only
   STATUS     mandatory
   DESCRIPTION
     "This attribute contains the current state of the end-to-end loopback 
      for this connection. Its value is dependent upon the current setting 
      of the endToEndLoopback provisionable attribute and the 
      connection point type as specified by the connectionPointType 
      attribute.
      
      The value is only applicable when the connectionPointType is a 
      connectionEndPoint. 
      
      The value is notApplicable when the connectionPointType is a 
      connectingPoint or segmentEndPoint. 
      
      The value is notApplicable when the distributionType is a 
      pointToMultipoint.
      
      The value is good when the endToEndLoopback is on, the 
      connectionPointType is a connectionEndPoint and the end-to-end 
      loopback is working.
      
      The value is bad when the endToEndLoopback is on, the 
      connectionPointType is a connectionEndPoint and the end-to-end 
      loopback is not working.
      
      The value is unknown when the endToEndLoopback is off.
      
      The value is unknown when the endToEndLoopback is on, the 
      connectionPointType is a connectionEndPoint and the end-to-end 
      loopback status has not been determined.
      
      The state of this attribute determines, in part, the value of the 
      operStatus attribute."
::= { atmIfVccStatusEntry 50 }

atmIfVccRxOamCellCongestionState OBJECT-TYPE
   SYNTAX     INTEGER  {
                 good(0),
                 bad(1),
                 unknown(2),
                 notApplicable(3) }
   ACCESS     read-only
   STATUS     mandatory
   DESCRIPTION
     "This attribute contains the current state of the receive side OAM cell 
      congestion for this connection. Its value reflects whether the rate of 
      received OAM cells for this connection is below a specified 
      threshold. The connection maintains a count of the number of OAM 
      cells which are terminated per second. Once that count exceeds the 
      specified threshold, extraction of all OAM cells for this connection 
      is disabled for a period of one minute. This is a congestion 
      management mechanism to prevent the processor from being 
      overloaded with handling OAM cells for a particular connection. 
      This mechanism ensures that tasks, such as trunks obtain enough 
      processor cycles to remain in service, and are not adversely affected 
      by excessive rate of OAM cells on a particular connection.
      
      The value is good when the rate of received OAM cells is less than 
      the allowed threshold.
      
      The value is bad when the arrival rate has exceeded the allowed 
      threshold. It remains bad for one minute, before returning to good 
      again. During this timeout, extraction of all OAM cells is disabled 
      for this connection. As a result, other loopback failure conditions 
      may occur.
      
      The value is unknown when the application has not yet begun to 
      use this connection. An example is the Test component before a test 
      has been started.
      
      Each type of OAM cell is counted separately. The threshold for AIS 
      cells is three cells per second. If more than three AIS cells are 
      received within a one second interval, this attribute is set to bad. 
      The threshold for RDI cells and each loopback type is also three, 
      but the threshold for trace cells is 250 per second.
      
      The state of this attribute has no direct effect on the value of the 
      operStatus attribute or on the number of troubled connections."
::= { atmIfVccStatusEntry 55 }

atmIfVccAisState OBJECT-TYPE
   SYNTAX     INTEGER  {
                 good(0),
                 bad(1),
                 unknown(2),
                 notApplicable(3) }
   ACCESS     read-only
   STATUS     mandatory
   DESCRIPTION
     "This attribute contains the current state of the Alarm Indication 
      Signal for this connection.
      
      A value of good indicates that the connection's application is active 
      and no alarm has occurred.
      
      A value of bad indicates that the connection's application is active 
      and an alarm has occurred.
      
      A value of unknown indicates that the connection's application is 
      inactive.
      
      A value of notApplicable occurs when the connectionPointType is 
      either a segmentEndPoint or a connectingPoint."
::= { atmIfVccStatusEntry 60 }

atmIfVccRdiState OBJECT-TYPE
   SYNTAX     INTEGER  {
                 good(0),
                 bad(1),
                 unknown(2),
                 notApplicable(3) }
   ACCESS     read-only
   STATUS     mandatory
   DESCRIPTION
     "This attribute indicates the current state of the Remote Defect 
      Indication for this connection.
      
      A value of good indicates that the connection's application is active 
      and no alarm has occurred.
      
      A value of bad indicates that the connection's application is active 
      and an alarm has occurred.
      
      A value of unknown indicates that the connection's application is 
      inactive.
      
      A value of notApplicable occurs when the connectionPointType is 
      either a segmentEndPoint or a connectingPoint."
::= { atmIfVccStatusEntry 70 }

atmIfVccTrafficTable OBJECT-TYPE
   SYNTAX     SEQUENCE OF AtmIfVccTrafficEntry
   ACCESS     not-accessible
   STATUS     mandatory
   DESCRIPTION
     "This group is HISTORICAL. Please refer to the group AtmTmOper;
      
      This attribute group contains attributes for the Vcc and Vpc 
      components to reflect operational traffic attributes."
::= { atmIfVcc 130 }

atmIfVccTrafficEntry OBJECT-TYPE
   SYNTAX     AtmIfVccTrafficEntry
   ACCESS     not-accessible
   STATUS     mandatory
   DESCRIPTION
     "An entry in the atmIfVccTrafficTable."
   INDEX {
      atmIfIndex,
      atmIfVccIndex }
::= { atmIfVccTrafficTable 1 }

AtmIfVccTrafficEntry ::= SEQUENCE {
   atmIfVccTxTrafficDescType
      INTEGER,
   atmIfVccTxQosClass
      INTEGER,
   atmIfVccFwdQosClass
      INTEGER,
   atmIfVccTxQueueLength
      INTEGER,
   atmIfVccTxQueueCongestionState
      INTEGER,
   atmIfVccHoldingPriority
      INTEGER,
   atmIfVccRxTrafficDescType
      INTEGER,
   atmIfVccRxQosClass
      INTEGER,
   atmIfVccBwdQosClass
      INTEGER,
   atmIfVccAtmServiceCategory
      INTEGER,
   atmIfVccTrafficShaping
      INTEGER,
   atmIfVccBearerClassBbc
      INTEGER,
   atmIfVccTransferCapabilityBbc
      INTEGER,
   atmIfVccClippingBbc
      INTEGER,
   atmIfVccUnshapedTransmitQueueing
      INTEGER,
   atmIfVccBestEffort
      INTEGER,
   atmIfVccUsageParameterControl
      INTEGER,
   atmIfVccTxFrameDiscard
      OCTET STRING,
   atmIfVccRxFrameDiscard
      OCTET STRING,
   atmIfVccBandwidthElastic
      INTEGER,
   atmIfVccBandwidthReduction
      INTEGER }

atmIfVccTxTrafficDescType OBJECT-TYPE
   SYNTAX     INTEGER  {
                 n1(1),
                 n2(2),
                 n3(3),
                 n4(4),
                 n5(5),
                 n6(6),
                 n7(7),
                 n8(8) }
   ACCESS     read-only
   STATUS     obsolete
   DESCRIPTION
     "This attribute is HISTORICAL. Please refer to the attribute of the 
      same name in the group AtmTmOper.
      
      This attribute indicates the type of traffic management which is 
      applied to the transmit direction of this connection as defined in the 
      ATM Forum. The txTrafficDescType determines the number and 
      meaning of the parameters in the txTrafficDescParm attribute."
::= { atmIfVccTrafficEntry 10 }

atmIfVccTxQosClass OBJECT-TYPE
   SYNTAX     INTEGER  {
                 unspecified(0),
                 constantBitRate(1),
                 variableBitRate(2),
                 connectionOriented(3),
                 connectionless(4) }
   ACCESS     read-only
   STATUS     obsolete
   DESCRIPTION
     "This attribute indicates the quality of service for the transmit 
      direction for this connection.
      
      The constantBitRate class refers to traffic offered on services such 
      as a constant bit rate video service. This traffic is highest priority.
      
      The variableBitRate class refers to traffic offered on services such 
      as packetized audio and video.
      
      The connectionOriented class refers to connection-oriented traffic 
      such as Frame Relay or X.25 traffic. 
      
      The connectionless traffic refers to traffic offered through 
      connectionless trunks such as certain LAN protocols.
      
      The unspecified class supports a 'best effort' type of service, where 
      there is a minimum guarantee of bandwidth. This traffic is lowest 
      priority.
      
      This attribute is obsolete, replaced by the UNI 4.0 attribute 
      atmServiceCategory."
::= { atmIfVccTrafficEntry 30 }

atmIfVccFwdQosClass OBJECT-TYPE
   SYNTAX     INTEGER  {
                 n0(0),
                 n1(1),
                 n2(2),
                 n3(3),
                 n4(4),
                 notApplicable(14) }
   ACCESS     read-only
   STATUS     obsolete
   DESCRIPTION
     "This attribute is HISTORICAL. Please refer to the attribute of the 
      same name in the group AtmTmOper.
      
      This attribute indicates the quality of service for the calling to called 
      direction for this connection. This is only applicable to Soft PVC 
      and SVC connections. 
      
      Class 1 supports a QOS that meets Service Class A performance 
      requirements (Circuit emulation, constant bit rate video).
      
      Class 2 supports a QOS that meets Service Class B performance 
      requirements (Variable bit rate audio and video).
      
      Class 3 supports a QOS that meets Service Class C performance 
      requirements (Connection-Oriented Data Transfer).
      
      Class 4 supports a QOS that meets Service Class D performance 
      requirements (Connectionless Data Transfer).
      
      Class 0 is the unspecified QOS class; no objective is specified for 
      the performance parameters.
      
      A value of notApplicable is displayed in the case of nailed-up PVCs 
      for which this attribute has no significance."
::= { atmIfVccTrafficEntry 31 }

atmIfVccTxQueueLength OBJECT-TYPE
   SYNTAX     INTEGER (0..30720)
   ACCESS     read-only
   STATUS     obsolete
   DESCRIPTION
     "This attribute is HISTORICAL. Please refer to the attribute of the 
      same name in the group AtmTmOper.
      
      This attribute indicates the current length of the transmit queue for 
      this connection. If this connection has traffic shaping disabled, then 
      this attribute displays the common queue length. If traffic shaping is 
      enabled, then this attribute displays the per-VC queue length."
::= { atmIfVccTrafficEntry 32 }

atmIfVccTxQueueCongestionState OBJECT-TYPE
   SYNTAX     INTEGER (0..3)
   ACCESS     read-only
   STATUS     obsolete
   DESCRIPTION
     "This attribute is HISTORICAL. Please refer to the attribute of the 
      same name in the group AtmTmOper.
      
      This attribute indicates the congestion state of the transmit queue 
      for this connection. If the connection has traffic shaping disabled, 
      then this attribute displays the common queue congestion state. If 
      traffic shaping is enabled, then this attribute displays the per-VC 
      queue congestion state.
      
      The congestion state of a queue is indicated by a numeric value 
      ranging from 0 to 3. When a queue is in a congested state x, only 
      traffic with discard priority (DP) 0 to x are enqueued. Traffic with 
      DP > x is discarded. 
      
      Therefore, if the congestion state is 3, there is no congestion and all 
      traffic is enqueued. Likewise, when the congestion state is 0, there 
      is maximum congestion and only traffic with DP=0 is enqueued on 
      that queue."
::= { atmIfVccTrafficEntry 33 }

atmIfVccHoldingPriority OBJECT-TYPE
   SYNTAX     INTEGER  {
                 n0(0),
                 n1(1),
                 n2(2),
                 n3(3),
                 n4(4),
                 notApplicable(6) }
   ACCESS     read-only
   STATUS     obsolete
   DESCRIPTION
     "This attribute is HISTORICAL. Please refer to the attribute of the 
      same name in the group AtmTmOper.
      
      This attribute indicates the actual holding priority in effect for this 
      connection. In a situation where the link bandwidth fluctuates, such 
      as over an IMA link, holding priority is used to determine which 
      connections are held and which are released. Holding priority 4 
      connections are the first to be released. Holding priority 0 
      connections are the last to be released. Some applications, for 
      example Vcc Test, may override the provisioned holding priority. 
      
      A value of notApplicable is displayed when this is an elastic 
      connection. Holding priority does not apply to bandwidth elastic 
      connections.
      
      Holding priority has no effect for ubr atmServiceCategory or 
      txTrafficDescriptorType 1 or 2 connections."
::= { atmIfVccTrafficEntry 35 }

atmIfVccRxTrafficDescType OBJECT-TYPE
   SYNTAX     INTEGER  {
                 n1(1),
                 n2(2),
                 n3(3),
                 n4(4),
                 n5(5),
                 n6(6),
                 n7(7),
                 n8(8) }
   ACCESS     read-only
   STATUS     obsolete
   DESCRIPTION
     "This attribute is HISTORICAL. Please refer to the attribute of the 
      same name in the group AtmTmOper.
      
      This attribute indicates the type of traffic management which is 
      applied to the receive direction of this connection as defined in the 
      ATM Forum. The rxTrafficDescType determines the number and 
      meaning of the parameters in the rxTrafficDescParm attribute."
::= { atmIfVccTrafficEntry 40 }

atmIfVccRxQosClass OBJECT-TYPE
   SYNTAX     INTEGER  {
                 unspecified(0),
                 constantBitRate(1),
                 variableBitRate(2),
                 connectionOriented(3),
                 connectionless(4) }
   ACCESS     read-only
   STATUS     obsolete
   DESCRIPTION
     "This attribute reflects the value of the provisioned attribute in the 
      Vcd or Vpd. Refer to that attribute for more detailed explanation. 
      
      This attribute is obsolete replaced by the UNI 4.0 attribute 
      atmServiceCategory."
::= { atmIfVccTrafficEntry 60 }

atmIfVccBwdQosClass OBJECT-TYPE
   SYNTAX     INTEGER  {
                 n0(0),
                 n1(1),
                 n2(2),
                 n3(3),
                 n4(4),
                 notApplicable(14) }
   ACCESS     read-only
   STATUS     obsolete
   DESCRIPTION
     "This attribute is HISTORICAL. Please refer to the attribute of the 
      same name in the group AtmTmOper.
      
      This attribute indicates the quality of service for the called to calling 
      direction for this connection. This is only applicable to Soft PVC 
      and SVC connections. 
      
      Class 1 supports a QOS that meets Service Class A performance 
      requirements (Circuit emulation, constant bit rate video).
      
      Class 2 supports a QOS that meets Service Class B performance 
      requirements (Variable bit rate audio and video).
      
      Class 3 supports a QOS that meets Service Class C performance 
      requirements (Connection-Oriented Data Transfer).
      
      Class 4 supports a QOS that meets Service Class D performance 
      requirements (Connectionless Data Transfer).
      
      Class 0 is the unspecified QOS class; no objective is specified for 
      the performance parameters.
      
      A value of notApplicable is displayed in the case of nailed-up PVCs 
      for which this attribute has no significance."
::= { atmIfVccTrafficEntry 61 }

atmIfVccAtmServiceCategory OBJECT-TYPE
   SYNTAX     INTEGER  {
                 unspecifiedBitRate(0),
                 constantBitRate(1),
                 rtVariableBitRate(2),
                 nrtVariableBitRate(3) }
   ACCESS     read-only
   STATUS     obsolete
   DESCRIPTION
     "This attribute is HISTORICAL. Please refer to the attribute of the 
      same name in the group AtmTmOper.
      
      This attribute indicates the ATM service category used for traffic in 
      both directions of the connection. 
      
      The constantBitRate service category is intended for real time 
      applications, that is, those requiring tightly constrained delay and 
      delay variation, as would be appropriate for voice and video 
      applications. The consistent availability of a fixed quantity of 
      bandwidth is considered appropriate for CBR service. Cells which 
      are delayed beyond the value specified by Cell Transfer Delay are 
      assumed to have significantly reduced value of the application.
      
      The rtVariableBitRate service category is intended for real time 
      applications; that is those requiring tightly constrained delay and 
      delay variation, as would be appropriate for voice and video 
      applications. Sources are expected to transmit at a rate which varies 
      with time. Equivalently, the source can be described as 'bursty'. 
      Cells which are delayed beyond the value specified by Cell Transfer 
      Delay are assumed to be of significantly reduced value to the 
      application. Real time VBR service may support statistical 
      multiplexing of real time sources.
      
      The nrtVariableBitRate service category is intended for non-real 
      time applications which have bursty traffic characteristics and which 
      can be characterized in terms of a PCR, SCR, and MBS. For those 
      cells which are transferred within the traffic contract, the application 
      expects a low cell loss ratio. For all connections, it expects a bound 
      on the mean cell transfer delay. Non-real time VBR service may 
      support statistical multiplexing of connections.
      
      The unspecifiedBitRate service is intended for non-real time 
      applications, that is those not requiring tightly constrained delay 
      and delay variation. UBR sources are expected to be bursty. UBR 
      service supports a high degree of statistical multiplexing among 
      sources. UBR service does not specify traffic related service 
      guarantees. No numerical commitments are made with respect to 
      the cell loss ratio experienced by a UBR connection, or as to the 
      cell transfer delay experienced by cells on the connection."
::= { atmIfVccTrafficEntry 62 }

atmIfVccTrafficShaping OBJECT-TYPE
   SYNTAX     INTEGER  {
                 enabled(0),
                 disabled(1),
                 notApplicable(4) }
   ACCESS     read-only
   STATUS     obsolete
   DESCRIPTION
     "This attribute is HISTORICAL. Please refer to the attribute of the 
      same name in the group AtmTmOper.
      
      This attribute indicates the traffic shaping state of the connection.
      
      A value of notApplicable indicates that traffic shaping is not 
      applicable or not supported for this connection. This is the case 
      when the atmServiceCategory is constantBitRate, or when the 
      txTrafficDescType is 1 or 2. In these cases, the value of 
      notApplicable is set regardless of whether traffic shaping is enabled 
      or disabled in the provisioning data.
      
      A value of disabled indicates that traffic shaping is applicable and 
      supported for the type of connection but has been turned off in the 
      provisioning data.
      
      A value of enabled indicates that traffic shaping is applicable and 
      supported for the type of connection and has been turned on in the 
      provisioning data. This is the only case that indicates that traffic 
      shaping is performed on the connection. In this case, the actual 
      shaping rate is reflected in the txTrafficDescParm attribute, 
      parameter number 4."
::= { atmIfVccTrafficEntry 70 }

atmIfVccBearerClassBbc OBJECT-TYPE
   SYNTAX     INTEGER  {
                 a(1),
                 c(3),
                 x(16),
                 vp(24),
                 notApplicable(30) }
   ACCESS     read-only
   STATUS     obsolete
   DESCRIPTION
     "This attribute is HISTORICAL. Please refer to the attribute of the 
      same name in the group AtmTmOper.
      
      This attribute indicates the bearer capability for this connection.
      
      Class a service is a connection-oriented, constant bit rate ATM 
      transport service. Class a service has end to end timing 
      requirements and may require stringent cell loss, cell delay and cell 
      delay variation performance.When a is displayed, the user is 
      requesting more than an ATM only service. The network may look 
      at the AAL to provide interworking based upon its contents. 
      
      Class c service is a connection-oriented, variable bit rate ATM 
      transport service. Class c service has no end-to-end timing 
      requirements.When c is displayed, the user is requesting more than 
      an ATM only service. The network interworking function may look 
      at the AAL and provide service based on it.
      
      Class x service is a connection-oriented ATM transport service 
      where the AAL, trafficType (cbr or vbr) and timing requirements 
      are user defined (that is, transparent to the network). When the 
      value of this attribute is x, the user is requesting an ATM only 
      service from the network. In this case, the network shall not process 
      any higher layer protocol.
      
      Class vp service is used to indicate a transparent VP service when 
      the user is requesting an ATM only service from the network. In this 
      case, the network does not process any higher layer protocol. This 
      service differs from class x service in that with the class vp service 
      both the VCI field (except for VCI values 0, 3, 4, and 6 through 15) 
      and Payload Type field are transported transparently by the network. 
      This attribute value is only applicable to SPVP and SVP 
      connections.
      
      A value of notApplicable is displayed in the case of nailed-up PVCs 
      for which this attribute has no significance."
::= { atmIfVccTrafficEntry 71 }

atmIfVccTransferCapabilityBbc OBJECT-TYPE
   SYNTAX     INTEGER  {
                 n0(0),
                 n1(1),
                 n2(2),
                 n5(5),
                 n8(8),
                 n9(9),
                 n10(10),
                 notApplicable(30) }
   ACCESS     read-only
   STATUS     obsolete
   DESCRIPTION
     "This attribute is HISTORICAL. Please refer to the attribute of the 
      same name in the group AtmTmOper.
      
      This attribute indicates the transfer capability for this connection. 
      Uni 3.0/3.1 traffic type and end-to-end timing parameters are 
      mapped into this parameter as follows:
      <transferCapability: TrafficType, Timing>
      0: NoIndication, NoIndication
      1: NoIndication, yes
      2: NoIndication, no
      5: CBR, yes
      8: VBR, NoIndication
      9: VBR, yes
      10: VBR, no
      
      A value of notApplicable is displayed in the case of nailed-up PVCs 
      for which this attribute has no significance, or in the case that the 
      transfer capability in the call request was set to NoIndication.
      
      The CBR traffic type refers to traffic offered on services such as a 
      constant bit rate video service or a circuit emulation.
      
      The VBR traffic type refers to traffic offered on services such as 
      packetized audio and video, or data.
      
      The value NoIndication for traffic type is used if the user has not set 
      the traffic type; similarly for end-to-end timing.
      
      The value yes for end-to-end timing indicates that end-to-end 
      timing is required for the connection.
      
      The value no for end-to-end timing indicates that end-to-end timing 
      is not required for the connection."
::= { atmIfVccTrafficEntry 72 }

atmIfVccClippingBbc OBJECT-TYPE
   SYNTAX     INTEGER  {
                 no(0),
                 yes(1),
                 notApplicable(14) }
   ACCESS     read-only
   STATUS     obsolete
   DESCRIPTION
     "This attribute is HISTORICAL. Please refer to the attribute of the 
      same name in the group AtmTmOper.
      
      This attribute indicates the value of the clipping susceptibility 
      parameter in the BBC Information Element.
      
      Clipping is an impairment in which the first fraction of a second of 
      information to be transferred is lost. It occurs after a call is 
      answered and before an associated connection is switched through.
      
      A value of notApplicable is displayed in the case of nailed-up PVCs 
      for which this attribute has no significance."
::= { atmIfVccTrafficEntry 74 }

atmIfVccUnshapedTransmitQueueing OBJECT-TYPE
   SYNTAX     INTEGER  {
                 perVc(0),
                 common(1),
                 notApplicable(4) }
   ACCESS     read-only
   STATUS     obsolete
   DESCRIPTION
     "This attribute is HISTORICAL. Please refer to the attribute of the 
      same name in the group AtmTmOper.
      
      This attribute indicates the unshaped transmit queuing state of the 
      connection.
      
      A value of common indicates that transmit traffic is being enqueued 
      onto common transmit queues. 
      
      A value of perVc indicates that transmit traffic is being enqueued 
      onto a per-VC queue for this connection. This is the case when 
      trafficShaping is disabled, but per-VC queueing has been 
      configured for this connection. 
      
      A value of notApplicable indicates that transmit traffic is being 
      shaped for this connection. Transmit traffic for a shaped connection 
      is enqueued onto a per-VC queue, but this attribute is only 
      applicable for unshaped connections."
::= { atmIfVccTrafficEntry 75 }

atmIfVccBestEffort OBJECT-TYPE
   SYNTAX     INTEGER  {
                 indicated(0),
                 notIndicated(1),
                 notApplicable(14) }
   ACCESS     read-only
   STATUS     obsolete
   DESCRIPTION
     "This attribute is HISTORICAL. Please refer to the attribute of the 
      same name in the group AtmTmOper.
      
      This attribute indicates value of best effort parameter in the ATM 
      Traffic Descriptor Information Element.
      
      The value indicated implies that the quality of service for this 
      connection is not guaranteed.
      
      The value notIndicated implies that the quality of service for this 
      connection is guaranteed.
      
      A value of notApplicable is displayed in the case of nailed-up PVCs 
      for which this attribute has no significance."
::= { atmIfVccTrafficEntry 76 }

atmIfVccUsageParameterControl OBJECT-TYPE
   SYNTAX     INTEGER  {
                 enabled(0),
                 disabled(1),
                 notApplicable(3) }
   ACCESS     read-only
   STATUS     obsolete
   DESCRIPTION
     "This attribute is HISTORICAL. Please refer to the attribute of the 
      same name in the group AtmTmOper.
      
      This attribute indicates the UPC state of the connection.
      
      A value of notApplicable indicates that UPC is not applicable or not 
      supported for the connection. This is the case when the connection's 
      rxTrafficDescType is 1 or 2. A value of notApplicable is set 
      regardless of whether UPC is disabled or enabled in provisioning 
      data.
      
      A value of disabled indicates that UPC is applicable and supported 
      for the type of connection but has been turned off in the 
      provisioning data.
      
      A value of enabled indicates that UPC is applicable and supported 
      for the type of connection and has been turned on in the 
      provisioning data. This is the only case that indicates that UPC is 
      enforced on the connection. In this case the traffic descriptor 
      parameters used for UPC enforcement are reflected in the 
      rxTrafficDescParms of the connection."
::= { atmIfVccTrafficEntry 80 }

atmIfVccTxFrameDiscard OBJECT-TYPE
   SYNTAX     OCTET STRING (SIZE (1))
   ACCESS     read-only
   STATUS     obsolete
   DESCRIPTION
     "This attribute is HISTORICAL. Please refer to the attribute of the 
      same name in the group AtmTmOper.
      
      This attribute indicates the set of current frame discard functions in 
      effect in the transmit data direction at this connection point.
      
      A value of ppd indicates that the Partial Packet Discard (PPD) 
      function is in effect. PPD may be applied at an interim connecting 
      point for a connection which is transporting frame traffic (AAL5 at 
      the endpoint). PPD is controlled by provisioning for PVCs and 
      SPVCs, and by call setup parameters in the AAL and Traffic 
      Descriptor Information Elements.
      
      A value of epd indicates that the Early Packet Discard (EPD) 
      function is in effect at this connection endpoint. PPD and EPD are 
      enabled by default at a connection endpoint which is performing 
      AAL5 segmentation and assembly.
      
      Frame discard functions are not applicable for Virtual Path 
      Connections (VPCs).

      Description of bits:
      ppd(0)
      epd(1)"
::= { atmIfVccTrafficEntry 85 }

atmIfVccRxFrameDiscard OBJECT-TYPE
   SYNTAX     OCTET STRING (SIZE (1))
   ACCESS     read-only
   STATUS     obsolete
   DESCRIPTION
     "This attribute is HISTORICAL. Please refer to the attribute of the 
      same name in the group AtmTmOper.
      
      This attribute indicates the set of current frame discard functions in 
      effect in the receive data direction at this connection point.
      
      A value of ppd indicates that the Partial Packet Discard (PPD) 
      function is in effect. PPD may be applied at an interim connecting 
      point for a connection which is transporting frame traffic (AAL5 at 
      the endpoint). PPD is controlled by provisioning for PVCs and 
      SPVCs, and by call setup parameters in the AAL and Traffic 
      Descriptor Information Elements.
      
      A value of epd indicates that the Early Packet Discard (EPD) 
      function is in effect at this connection endpoint. PPD and EPD are 
      enabled by default at a connection endpoint which is performing 
      AAL5 segmentation and assembly.
      
      Frame discard functions are not applicable for Virtual Path 
      Connections (VPCs).

      Description of bits:
      ppd(0)
      epd(1)"
::= { atmIfVccTrafficEntry 86 }

atmIfVccBandwidthElastic OBJECT-TYPE
   SYNTAX     INTEGER  {
                 no(0),
                 yes(1) }
   ACCESS     read-only
   STATUS     obsolete
   DESCRIPTION
     "This attribute is HISTORICAL. Please refer to the attribute of the 
      same name in the group AtmTmOper.
      
      This attribute is only of importance for connections which are 
      carried on a link with a variable bandwidth. For example, the 
      bandwidth may be reduced in the event that one or more physical 
      links in the IMA group fail, such that the originally requested 
      bandwidth cannot be maintained. This attribute shows whether the 
      application (for example, Trunk) running on this connection can 
      continue to operate if the bandwidth is reduced. If the bandwidth is 
      reduced, the amount by which it is reduced is displayed in the 
      bandwidthReduction attribute. 
      
      A value of yes, indicates that this connection is elastic, and the 
      bandwidth may be reduced but the connection is not released. 
      
      A value of no indicates that the bandwidth for this connection is not 
      reduced in the event of link bandwidth reduction. However, this 
      connection may be released based on its holdingPriority.
      
      Bandwidth elasticity has no effect for ubr atmServiceCategory or 
      txTrafficDescriptorType 1 or 2 connections."
::= { atmIfVccTrafficEntry 90 }

atmIfVccBandwidthReduction OBJECT-TYPE
   SYNTAX     INTEGER (0..2147483647)
   ACCESS     read-only
   STATUS     obsolete
   DESCRIPTION
     "This attribute is HISTORICAL. Please refer to the attribute of the 
      same name in the group AtmTmOper.
      
      This attribute shows the amount by which the bandwidth has been 
      reduced for this connection. This value is non-zero only for 
      connections which have bandwidthElastic displayed as yes, and 
      which are also operating in a reduced bandwidth mode. This is 
      typically be the case for selected connections running over an IMA 
      link. This attribute takes a value from 0 (no reduction) up to the 
      ECR. All connections which are running at their full allocated 
      bandwidth, bwReduction have the value 0. Connections which have 
      been reduced in allocated bandwidth have a positive number for this 
      attribute. The bwReduction may be subtracted from the ECR (which 
      is displayed as txTrafficDescParm 5) to determine the actual 
      bandwidth allocated to this connection."
::= { atmIfVccTrafficEntry 100 }

atmIfVccStatsTable OBJECT-TYPE
   SYNTAX     SEQUENCE OF AtmIfVccStatsEntry
   ACCESS     not-accessible
   STATUS     mandatory
   DESCRIPTION
     "This group contains traffic statistics for a Vcc, Vpc, or Vpt 
      component."
::= { atmIfVcc 140 }

atmIfVccStatsEntry OBJECT-TYPE
   SYNTAX     AtmIfVccStatsEntry
   ACCESS     not-accessible
   STATUS     mandatory
   DESCRIPTION
     "An entry in the atmIfVccStatsTable."
   INDEX {
      atmIfIndex,
      atmIfVccIndex }
::= { atmIfVccStatsTable 1 }

AtmIfVccStatsEntry ::= SEQUENCE {
   atmIfVccStatsTxCell
      PassportCounter64,
   atmIfVccStatsTxCellClp
      PassportCounter64,
   atmIfVccTxDiscard
      PassportCounter64,
   atmIfVccTxDiscardClp
      PassportCounter64,
   atmIfVccStatsTxCellDiscard
      PassportCounter64,
   atmIfVccStatsTxCellDiscardClp
      PassportCounter64,
   atmIfVccStatsTxFrameDiscard
      PassportCounter64,
   atmIfVccStatsTxFrameDiscardClp
      PassportCounter64,
   atmIfVccTxUtilization
      Gauge32,
   atmIfVccStatsRxCell
      PassportCounter64,
   atmIfVccStatsRxCellClp
      PassportCounter64,
   atmIfVccRxDiscard
      PassportCounter64,
   atmIfVccRxDiscardClp
      PassportCounter64,
   atmIfVccStatsRxCellDiscard
      PassportCounter64,
   atmIfVccStatsRxCellDiscardClp
      PassportCounter64,
   atmIfVccStatsRxFrameDiscard
      PassportCounter64,
   atmIfVccStatsRxFrameDiscardClp
      PassportCounter64,
   atmIfVccRxUtilization
      Gauge32,
   atmIfVccStatsRxUpcViolationOnEnforcer1
      PassportCounter64,
   atmIfVccStatsRxUpcViolationOnEnforcer2
      PassportCounter64,
   atmIfVccStatsRxAal5FrameError
      PassportCounter64,
   atmIfVccStatsRxAal5FrameAbort
      PassportCounter64 }

atmIfVccStatsTxCell OBJECT-TYPE
   SYNTAX     PassportCounter64 
   ACCESS     read-only
   STATUS     mandatory
   DESCRIPTION
     "This attribute counts the number of cells that have been transmitted 
      from the interface on this connection. The counter wraps to zero if it 
      exceeds its maximum value of (2**64)-1."
::= { atmIfVccStatsEntry 10 }

atmIfVccStatsTxCellClp OBJECT-TYPE
   SYNTAX     PassportCounter64 
   ACCESS     read-only
   STATUS     mandatory
   DESCRIPTION
     "This attribute counts the number of cells that have been transmitted 
      from the interface on this connection with the CLP=1. The counter 
      wraps to zero if it exceeds its maximum value of (2**64)-1."
::= { atmIfVccStatsEntry 20 }

atmIfVccTxDiscard OBJECT-TYPE
   SYNTAX     PassportCounter64 
   ACCESS     read-only
   STATUS     obsolete
   DESCRIPTION
     "This attribute is replaced by new attributes txCellDiscard and 
      txFrameDiscard.
      
      This attribute counts the number of cells or frames received from 
      the bus on this connection that have been discarded.
      
      If the connection segments frames into cells, the counter indicates 
      the number of frames discarded. Connections which segment 
      frames into cells have a connectionPointType of 
      connectionEndPoint.
      
      If the connection relays cells without adaptation, the counter 
      indicates the number of cells discarded. Connections which relay 
      cells without adaptation have a connectionPointType of 
      segmentEndPoint or connectingPoint.
      
      AAL1 connections are an exception to this rule; although they have 
      a connectionPointType of connectionEndPoint, they do not do 
      adaptation at this point. Thus, in the AAL1 case, this attribute 
      counts discarded cells.
      
      Discards are done due to congestion or when the connection's 
      interface is disabled.
      
      The counter wraps to zero if it exceeds its maximum value of 
      (2**64)-1."
::= { atmIfVccStatsEntry 30 }

atmIfVccTxDiscardClp OBJECT-TYPE
   SYNTAX     PassportCounter64 
   ACCESS     read-only
   STATUS     obsolete
   DESCRIPTION
     "This attribute is replaced by new attributes txCellDiscardClp and 
      txFrameDiscardClp.
      
      This attribute counts the number of cells or frames received from 
      the bus on this connection with CLP=1 that have been discarded.
      
      If the connection segments frames into cells, the counter indicates 
      the number of frames discarded. Connections which segment 
      frames into cells have a connectionPointType of 
      connectionEndPoint.
      
      If the connection relays cells without adaptation, the counter 
      indicates the number of cells discarded. Connections which relay 
      cells without adaptation have a connectionPointType of 
      segmentEndPoint or connectingPoint.
      
      AAL1 connections are an exception to this rule; although they have 
      a connectionPointType of connectionEndPoint, they do not do 
      adaptation at this point. Thus, in the AAL1 case, this attribute 
      counts discarded cells.
      
      Discards are done due to congestion or when the connection's 
      interface is disabled.
      
      The counter wraps to zero if it exceeds its maximum value of 
      (2**64)-1."
::= { atmIfVccStatsEntry 40 }

atmIfVccStatsTxCellDiscard OBJECT-TYPE
   SYNTAX     PassportCounter64 
   ACCESS     read-only
   STATUS     mandatory
   DESCRIPTION
     "This attribute counts the number of cells received from the bus on 
      this connection that have been discarded.
      
      Discarded cells are not counted in the txCell attribute.
      
      Cells are discarded due to transmit congestion, Partial Packet 
      Discard (PPD), Early Packet Discard (EPD), and Weighted Random 
      Early Detection (W-RED) mechanisms, or when the connection's 
      interface is disabled.
      
      For CQC-based ATM cards, this attribute is applicable only to 
      connections that relay cells without adaptation. Such connections 
      usually have a connectionPointType of segmentEndPoint or 
      connectingPoint. AAL1 connections are an exception to this rule; 
      although they have a connectionPointType of connectionEndPoint, 
      they do not do adaptation at this point. For Vpts, this attribute 
      provides an aggregated total of all txCellDiscard values for all such 
      connections associated with the Vpt.
      
      For Vccs on CQC-based ATM cards, if the connection segments 
      frames into cells, this attribute is not applicable and is not 
      displayed.
      
      The counter wraps to zero if it exceeds its maximum value of 
      (2**64)-1."
::= { atmIfVccStatsEntry 42 }

atmIfVccStatsTxCellDiscardClp OBJECT-TYPE
   SYNTAX     PassportCounter64 
   ACCESS     read-only
   STATUS     mandatory
   DESCRIPTION
     "This attribute counts the number of cells received from the bus on 
      this connection with CLP=1 that have been discarded.
      
      This count is included in the txCellDiscard attribute. Discarded 
      cells are not counted in the txCellClp attribute.
      
      Cells are discarded due to transmit congestion, Partial Packet 
      Discard (PPD), Early Packet Discard (EPD), and Weighted Random 
      Early Detection (W-RED) mechanisms, or when the connection's 
      interface is disabled.
      
      For CQC-based ATM cards, this attribute is applicable only to 
      connections that relay cells without adaptation. Such connections 
      have a connectionPointType of segmentEndPoint or 
      connectingPoint. AAL1 connections are an exception to this rule; 
      although they have a connectionPointType of connectionEndPoint, 
      they do not do adaptation at this point. For Vpts, this attribute 
      provides an aggregated total of all txCellDiscardClp values for all 
      such connections associated with the Vpt.
      
      For Vccs on CQC-based ATM cards, if the connection segments 
      frames into cells, this attribute is not applicable and is not 
      displayed.
      
      The counter wraps to zero if it exceeds its maximum value of 
      (2**64)-1."
::= { atmIfVccStatsEntry 43 }

atmIfVccStatsTxFrameDiscard OBJECT-TYPE
   SYNTAX     PassportCounter64 
   ACCESS     read-only
   STATUS     mandatory
   DESCRIPTION
     "This attribute counts the number of frames received from the bus on 
      this connection that have been discarded.
      
      Frames are discarded due to congestion, Partial Packet Discard 
      (PPD), Early Packet Discard (EPD), and Weighted Random Early 
      Detection (W-RED) mechanisms, or when the connection interface 
      is disabled.
      
      This count is independent of the txCell or txCellDiscard attribute.
      
      For CQC-based ATM cards, this attribute is applicable only to 
      connections that segment frames into cells. Such connections have a 
      connectionPointType of connectionEndPoint. AAL1 connections 
      are an exception to this rule; although they have a 
      connectionPointType of connectionEndPoint, they do not do 
      adaptation at this point. For Vpts, this attribute provides an 
      aggregated total of all txFrameDiscard values for all such 
      connections associated with the Vpt.
      
      For CQC-based ATM cards, for Vpcs, and Vccs that relay cells 
      without adaptation, this attribute is not applicable and is not 
      displayed.
      
      Discards due to EPD, PPD, and W-RED for a standard Vpt Vcc are 
      not included in this attribute. These discards are counted in the 
      Vcc's parent Vpt txFrameDiscard attribute.
      
      The counter wraps to zero if it exceeds its maximum value of 
      (2**64)-1."
::= { atmIfVccStatsEntry 46 }

atmIfVccStatsTxFrameDiscardClp OBJECT-TYPE
   SYNTAX     PassportCounter64 
   ACCESS     read-only
   STATUS     mandatory
   DESCRIPTION
     "This attribute counts the number of discarded frames on this 
      connection that were received from the bus and composed of one or 
      more CLP=1 cells.
      
      Frames are discarded due to congestion, Partial Packet Discard 
      (PPD), Early Packet Discard (EPD), and Weighted Random Early 
      Detection (W-RED) mechanisms, or when the connection interface 
      is disabled.
      
      This count is included in the txFrameDiscard attribute.
      
      For CQC-based ATM cards, this attribute is applicable only to 
      connections that segment frames into cells. Such connections have a 
      connectionPointType of connectionEndPoint. AAL1 connections 
      are an exception to this rule; although they have a 
      connectionPointType of connectionEndPoint, they do not do 
      adaptation at this point. For Vpts, this attribute provides an 
      aggregated total of all txFrameDiscardClp values for all such 
      connections associated with the Vpt.
      
      For CQC-based ATM cards, for Vpcs, and Vccs that relay cells 
      without adaptation, this attribute is not applicable and is not 
      displayed.
      
      Discards due to EPD, PPD, and W-RED for a standard Vpt Vcc are 
      not included in this attribute. These discards are counted in the 
      Vcc's parent Vpt txFrameDiscardClp attribute.
      
      The counter wraps to zero if it exceeds its maximum value of 
      (2**64)-1."
::= { atmIfVccStatsEntry 47 }

atmIfVccTxUtilization OBJECT-TYPE
   SYNTAX     Gauge32 (0..200 | 255)
   ACCESS     read-only
   STATUS     mandatory
   DESCRIPTION
     "This attribute indicates the current transmit utilization during the 
      most recent minute, expressed as a percentage of the total 
      bandwidth which can be carried by this connection. This attribute is 
      only applicable for Vpts and not for Vpcs or Vccs.
      
      When the Vpt is shaped, the value of this attribute is calculated 
      using its actual shaping rate (ASR) and should not exceed 100.
      
      When the Vpt is unshaped, the value of this attribute is calculated 
      using its peak cell rate (PCR) and should not exceed 200. If the 
      PCR is 0, the value 255 is used."
::= { atmIfVccStatsEntry 48 }

atmIfVccStatsRxCell OBJECT-TYPE
   SYNTAX     PassportCounter64 
   ACCESS     read-only
   STATUS     mandatory
   DESCRIPTION
     "This attribute counts cells that have been received from the interface 
      on this connection. The counter wraps to zero if it exceeds its 
      maximum value of (2**64)-1."
::= { atmIfVccStatsEntry 50 }

atmIfVccStatsRxCellClp OBJECT-TYPE
   SYNTAX     PassportCounter64 
   ACCESS     read-only
   STATUS     mandatory
   DESCRIPTION
     "This attribute counts cells that have been received from the interface 
      on this connection with the CLP=1. The counter wraps to zero if it 
      exceeds its maximum value of (2**64)-1."
::= { atmIfVccStatsEntry 60 }

atmIfVccRxDiscard OBJECT-TYPE
   SYNTAX     PassportCounter64 
   ACCESS     read-only
   STATUS     obsolete
   DESCRIPTION
     "This attribute is replaced by new attributes rxCellDiscard and 
      rxFrameDiscard.
      
      This attribute counts the number of cells or frames received from 
      the interface on this connection that have been discarded.
      
      If the connection segments frames into cells, the counter indicates 
      the number of frames discarded. Connections which segment 
      frames into cells have a connectionPointType of 
      connectionEndPoint.
      
      If the connection relays cells without adaptation, the counter 
      indicates the number of cells discarded. Connections which relay 
      cells without adaptation have a connectionPointType of 
      segmentEndPoint or connectingPoint.
      
      AAL1 connections are an exception to this rule; although they have 
      a connectionPointType of connectionEndPoint, they do not do 
      adaptation at this point. Thus, in the AAL1 case, this attribute 
      counts discarded cells.
      
      Discards are done due to congestion, non-conformance with UPC or 
      AAL reassembly problems.
      
      The counter wraps to zero if it exceeds its maximum value of 
      (2**64)-1."
::= { atmIfVccStatsEntry 70 }

atmIfVccRxDiscardClp OBJECT-TYPE
   SYNTAX     PassportCounter64 
   ACCESS     read-only
   STATUS     obsolete
   DESCRIPTION
     "This attribute is replaced by new attributes rxCellDiscardClp and 
      rxFrameDiscardClp.
      
      This attribute counts the number of cells or frames received from 
      the interface on this connection with CLP=1 that have been 
      discarded.
      
      If the connection segments frames into cells, the counter indicates 
      the number of frames discarded. Connections which segment 
      frames into cells have a connectionPointType of 
      connectionEndPoint.
      
      If the connection relays cells without adaptation, the counter 
      indicates the number of cells discarded. Connections which relay 
      cells without adaptation have a connectionPointType of 
      segmentEndPoint or connectingPoint.
      
      AAL1 connections are an exception to this rule; although they have 
      a connectionPointType of connectionEndPoint, they do not do 
      adaptation at this point. Thus, in the AAL1 case, this attribute 
      counts discarded cells.
      
      Discards are done due to congestion, non-conformance with UPC or 
      AAL reassembly problems.
      
      The counter wraps to zero if it exceeds its maximum value of 
      (2**64)-1."
::= { atmIfVccStatsEntry 80 }

atmIfVccStatsRxCellDiscard OBJECT-TYPE
   SYNTAX     PassportCounter64 
   ACCESS     read-only
   STATUS     mandatory
   DESCRIPTION
     "This attribute counts the number of cells received from the interface 
      on this connection that have been discarded. This count is included 
      in the rxCell attribute.
      
      This count includes cells discarded due to non-conformance with 
      UPC, cells which are part of a frame which has been discarded due 
      to an AAL5 frame reassembly error, cells which are discarded due 
      to congestion, or cells which are received while the next hop 
      connection to which the traffic is directed across the backplane is 
      down. The next hop connection is the Vcc or Vpc identified by the 
      nextHop attribute of the Nrp or Rp component. 
      
      For CQC-based ATM cards, this attribute is applicable only to 
      connections that relay cells without adaptation. Such connections 
      have a connectionPointType of connectionEndPoint or 
      connectingPoint. AAL1 connections are an exception to this rule; 
      although they have a connectionPointType of connectionEndPoint, 
      they do not do adaptation at this point. For Vpts, this attribute 
      provides an aggregated total of all rxCellDiscard values for all such 
      connections associated with the Vpt.
      
      For CQC-based ATM cards, for Vpcs, and Vccs that relay cells 
      without adaptation, this attribute is not applicable and is not 
      displayed.
      
      Discards due to non-conformance with UPC at the VP layer, for a 
      standard Vpt Vcc, are not included in this attribute. These discards 
      are counted in the Vcc's parent Vpt rxCellDiscard attribute.
      
      The counter wraps to zero if it exceeds its maximum value of 
      (2**64)-1."
::= { atmIfVccStatsEntry 82 }

atmIfVccStatsRxCellDiscardClp OBJECT-TYPE
   SYNTAX     PassportCounter64 
   ACCESS     read-only
   STATUS     mandatory
   DESCRIPTION
     "This attribute counts the number of cells received from the interface 
      on this connection with CLP=1 that have been discarded. This count 
      is included in the rxCell and rxCellDiscard attributes.
      
      This count includes cells discarded due to non-conformance with 
      UPC, cells which are part of a frame which has been discarded due 
      to an AAL5 frame reassembly error, cells which are discarded due 
      to congestion, or cells which are received while the next hop 
      connection to which the traffic is directed across the backplane is 
      down. The next hop connection is the Vcc or Vpc identified by the 
      nextHop attribute of the Nrp or Rp component. 
      
      For CQC-based ATM cards, this attribute is applicable only to 
      connections that relay cells without adaptation. Such connections 
      have a connectionPointType of connectionEndPoint or 
      connectingPoint. AAL1 connections are an exception to this rule; 
      although they have a connectionPointType of connectionEndPoint, 
      they do not do adaptation at this point. For Vpts, this attribute 
      provides an aggregated total of all rxCellDiscardClp values for all 
      such connections associated with the Vpt.
      
      For CQC-based ATM cards, for Vpcs, and Vccs that relay cells 
      without adaptation, this attribute is not applicable and is not 
      displayed.
      
      Discards due to non-conformance with UPC at the VP layer, for a 
      standard Vpt Vcc, are not included in this attribute. These discards 
      are counted in the Vcc's parent Vpt rxCellDiscardClp attribute.
      
      The counter wraps to zero if it exceeds its maximum value of 
      (2**64)-1."
::= { atmIfVccStatsEntry 83 }

atmIfVccStatsRxFrameDiscard OBJECT-TYPE
   SYNTAX     PassportCounter64 
   ACCESS     read-only
   STATUS     mandatory
   DESCRIPTION
     "This attribute counts the number of frames received from the 
      interface on this connection that have been discarded. This count is 
      independent of the rxCellDiscard attribute.
      
      This count includes frames discarded due to an AAL5 frame 
      reassembly error, frames discarded due to early packet discard 
      (EPD), and frames discarded due to processor (CPU) congestion. 
      This attribute is applicable only for connections that reassemble 
      incoming cells into frames. Connections which reassemble cells 
      into frames have a connectionPointType of connectionEndPoint. 
      AAL1 connections are an exception to this rule; even though they 
      have a connectionPointType of connectionEndPoint, they do not 
      do adaptation at this point. For Vpts, this attribute provides an 
      aggregated total of all rxFrameDiscard values for all applicable 
      connections associated with the Vpt.
      
      For Vpcs, and for Vccs that relay cells without adaptation, this 
      attribute is not applicable and is not displayed.
      
      The counter wraps to zero if it exceeds its maximum value of 
      (2**64)-1."
::= { atmIfVccStatsEntry 86 }

atmIfVccStatsRxFrameDiscardClp OBJECT-TYPE
   SYNTAX     PassportCounter64 
   ACCESS     read-only
   STATUS     mandatory
   DESCRIPTION
     "This attribute counts the number of discarded frames on this 
      connection that were received from the interface and composed of 
      one or more CLP1 cells. This count is included in the 
      rxFrameDiscard attribute. It is independent of the rxCellDiscard 
      attribute.
      
      This count includes frames discarded due to an AAL5 frame 
      reassembly error, frames discarded due to early packet discard 
      (EPD), and frames discarded due to processor (CPU) congestion. 
      This attribute is applicable only for connections that reassemble 
      incoming cells into frames. Connections which reassemble cells 
      into frames have a connectionPointType of connectionEndPoint. 
      AAL1 connections are an exception to this rule; even though they 
      have a connectionPointType of connectionEndPoint, they do not 
      do adaptation at this point. For Vpts, this attribute provides an 
      aggregated total of all rxFrameDiscardClp values for all applicable 
      connections associated with the Vpt.
      
      For Vpcs, and for Vccs that relay cells without adaptation, this 
      attribute is not applicable and is not displayed.
      
      The counter wraps to zero if it exceeds its maximum value of 
      (2**64)-1."
::= { atmIfVccStatsEntry 88 }

atmIfVccRxUtilization OBJECT-TYPE
   SYNTAX     Gauge32 (0..200 | 255)
   ACCESS     read-only
   STATUS     mandatory
   DESCRIPTION
     "This attribute indicates the current receive utilization during the 
      most recent minute, expressed as a percentage of the total 
      bandwidth which can be carried by this connection. This attribute is 
      only applicable for Vpts and not for Vpcs or Vccs.
      
      When the Vpt is shaped, the value of this attribute is calculated 
      using its actual shaping rate (ASR) and should not exceed 100.
      
      When the Vpt is unshaped, the value of this attribute is calculated 
      using its peak cell rate (PCR) and should not exceed 200. If the 
      PCR is 0, the value 255 is used."
::= { atmIfVccStatsEntry 89 }

atmIfVccStatsRxUpcViolationOnEnforcer1 OBJECT-TYPE
   SYNTAX     PassportCounter64 
   ACCESS     read-only
   STATUS     mandatory
   DESCRIPTION
     "This attribute counts the number of UPC violations observed by the 
      Generic Cell Rate Algorithm (GCRA) Enforcer 1. This attribute is 
      only applicable if UPC is enforced or monitored. This attribute is 
      not applicable for standard Vpt Vccs. This attribute is not applicable 
      and is not displayed on CQC-based ATM cards.
      
      When the value of rxTrafficDescType for this connection is 3, 4, 5, 
      6, 7 or 8, Enforcer 1 enforces conformance of traffic received from 
      the interface to PCR CLP0+1.
      
      When the value of rxTrafficDescType for this connection is 9, 
      Enforcer 1 performs the Dynamic Generic Cell Rate Algorithm 
      (DGCRA) used for the Available Bit Rate (ABR) service category.
      
      If UPC is enforced all non-conforming cells are discarded by this 
      enforcer. These discarded cells are included in rxCellDiscard. 
      
      For basic Vpts, this attribute provides an aggregated total of all 
      rxUpcViolationOnEnforcer1 values for the Vccs associated with the 
      Vpt.
      
      The counter wraps to zero if it exceeds its maximum value of 
      (2**64)-1."
::= { atmIfVccStatsEntry 90 }

atmIfVccStatsRxUpcViolationOnEnforcer2 OBJECT-TYPE
   SYNTAX     PassportCounter64 
   ACCESS     read-only
   STATUS     mandatory
   DESCRIPTION
     "This attribute counts the number of UPC violations observed by the 
      Generic Cell Rate Algorithm (GCRA) Enforcer 2. This attribute is 
      only applicable if UPC is enforced or monitored. This attribute is 
      not applicable for standard Vpt Vccs. This attribute is not applicable 
      and is not displayed on CQC-based ATM cards.
      
      Enforcer2 is applicable only if the rxTrafficDescType for this 
      connection is 4, 5, 6, 7 or 8.
      
      When the value of rxTrafficDescType 4 or 5, Enforcer 2 enforces 
      conformance of traffic received from the interface to PCR CLP0.
      
      When the value of rxTrafficDescType 6, Enforcer 2 enforces 
      conformance of traffic received from the interface to SCR CLP0+1.
      
      When the value of rxTrafficDescType 7 or 8, Enforcer 2 enforces 
      conformance of traffic received from the interface to SCR CLP0.
      
      If UPC is enforced, enforcer 2 discards non-conforming cells for 
      rxTrafficDescType values of 4, 6 and 7. It tags non-conforming cells 
      for rxTrafficDescType values of 5 and 8. Discarded cells are 
      counted in the rxCellDiscard attribute. 
      
      For basic Vpts, this attribute provides an aggregated total of all 
      rxUpcViolationOnEnforcer2 values for the Vccs associated with the 
      Vpt.
      
      The counter wraps to zero if it exceeds its maximum value of 
      (2**64)-1."
::= { atmIfVccStatsEntry 92 }

atmIfVccStatsRxAal5FrameError OBJECT-TYPE
   SYNTAX     PassportCounter64 
   ACCESS     read-only
   STATUS     mandatory
   DESCRIPTION
     "This attribute counts the number of frames received from the 
      interface on this connection that have AAL5 length errors or AAL5 
      CRC errors. 
      
      This attribute is not applicable and is not displayed on CQC-based 
      ATM cards.
      
      AAL5 length or CRC errors typically occur because of cell discards 
      due to congestion, UPC, or due to corruption of data between the 
      AAL5 segmentation and reassembly end points.
      
      This attribute is applicable only to connections that reassemble 
      incoming cells into frames. Such connections have a 
      connectionPointType of connectionEndPoint. AAL1 connections 
      are an exception to this rule; although they have a 
      connectionPointType of connectionEndPoint, they do not do 
      adaptation at this point. For Vpts, this attribute provides an 
      aggregated total of all rxAal5FrameError values for all applicable 
      connections associated with the Vpt.
      
      For Vpcs, and for Vccs that relay cells without adaptation, this 
      attribute is not applicable and is not displayed.
      
      The counter wraps to zero if it exceeds its maximum value of 
      (2**64)-1."
::= { atmIfVccStatsEntry 100 }

atmIfVccStatsRxAal5FrameAbort OBJECT-TYPE
   SYNTAX     PassportCounter64 
   ACCESS     read-only
   STATUS     mandatory
   DESCRIPTION
     "This attribute counts the number of frames received from the 
      interface on this connection that have the AAL5 length field set to 
      zero. 
      
      This attribute is not applicable and is not displayed for CQC-based 
      ATM cards.
      
      An AAL5 length of zero is an indication by the far end 
      segmentation point to this reassembly point that the frame is to be 
      discarded without reassembly. This mechanism is typically used by 
      a segmentation point if it detects an error in a frame after some of 
      the cells belonging to that frame have already been transmitted.
      
      This attribute is applicable only to connections that reassemble 
      incoming cells into frames. Such connections have a 
      connectionPointType of connectionEndPoint. AAL1 connections 
      are an exception to this rule; although they have a 
      connectionPointType of connectionEndPoint, they do not do 
      adaptation at this point. For Vpts, this attribute provides an 
      aggregated total of all rxAal5FrameAbort values for all applicable 
      connections associated with the Vpt.
      
      For Vpcs, and for Vccs that relay cells without adaptation, this 
      attribute is not applicable and is not displayed.
      
      The counter wraps to zero if it exceeds its maximum value of 
      (2**64)-1."
::= { atmIfVccStatsEntry 102 }

atmIfVccTxTdpTable OBJECT-TYPE
   SYNTAX     SEQUENCE OF AtmIfVccTxTdpEntry
   ACCESS     not-accessible
   STATUS     obsolete
   DESCRIPTION
     "This attribute is HISTORICAL. Please refer to the attribute of the 
      same name in the group AtmTmOper.
      
      This attribute is a vector of five transmit traffic parameters. The first 
      three elements reflect the settings of the first three elements of the 
      txTrafficDescParm attribute in the AtmTrafficProv group. 
      
      When txTrafficDescType is 1 or 2, parameters 1 through 5 are 
      unused.
      
      In this description, PCR is the greater of either the PCR or the 
      requested shaping rate (parameter 1 or parameter 5) specified in the 
      Traffic group under the Vcd or Vpd.
      
      When txTrafficDescType is 3, parameter 1 represents the PCR for 
      CLP equal to 0 or 1 traffic; parameters 2 and 3 are unused.
      
      When txTrafficDescType is 4, parameter 1 represents the PCR for 
      CLP equal to 0 and 1 traffic; parameter 2 represents the PCR for 
      CLP equal to 0 traffic with cell discard.
      
      When txTrafficDescType is 5, parameter 1 represents the PCR for 
      CLP equal to 0 and 1 traffic; parameter 2 represents the PCR for 
      CLP equal to 0 traffic with cell tagging.
      
      When txTrafficDescType is 6, parameter 1 represents the PCR for 
      CLP equal to 0 and 1 traffic; parameter 2 represents the SCR for 
      CLP equal to 0 and 1 traffic; parameter 3 represents the MBS for 
      CLP equal to 0 and 1 traffic.
      
      When txTrafficDescType is 7, parameter 1 represents the PCR for 
      CLP equal to 0 and 1 traffic; parameter 2 represents the SCR for 
      CLP equal to 0 traffic with cell discard; parameter 3 represents the 
      MBS for CLP equal to 0 traffic.
      
      When txTrafficDescType is 8, parameter 1 represents the PCR for 
      CLP equal to 0 and 1 traffic; parameter 2 represents the SCR for 
      CLP equal to 0 traffic with cell tagging; parameter 3 represents the 
      MBS for CLP equal to 0 traffic
      
      When txTrafficDescType is 3, 4, 5, 6, 7 or 8, parameter 4 reflects 
      the actual shaping rate in cell/s for this connection. This rate is one 
      of the set of available shaping rates for this type of ATM-FP, based 
      on the number of interfaces doing shaping (attribute 
      perVcQueueInterfaces), the provisioned cell rate, the 
      shapingScalingFactor attribute of the AtmResourceControl 
      component, and whether traffic shaping is enabled. A rate of zero 
      (0) indicates that shaping is not performed. 
      
      When txTrafficDescType is 3, 4, 5, 6, 7 or 8, parameter 5 reflects 
      the equivalent cell rate in cell/s for this connection as determined by 
      the Connection Admission Control (CAC) algorithm. The 
      equivalent cell rate is useful in determining the admission 
      characteristics of this connection."
::= { atmIfVcc 294 }

atmIfVccTxTdpEntry OBJECT-TYPE
   SYNTAX     AtmIfVccTxTdpEntry
   ACCESS     not-accessible
   STATUS     obsolete
   DESCRIPTION
     "An entry in the atmIfVccTxTdpTable."
   INDEX {
      atmIfIndex,
      atmIfVccIndex,
      atmIfVccTxTdpIndex }
::= { atmIfVccTxTdpTable 1 }

AtmIfVccTxTdpEntry ::= SEQUENCE {
   atmIfVccTxTdpIndex
      Integer32,
   atmIfVccTxTdpValue
      Unsigned32 }

atmIfVccTxTdpIndex OBJECT-TYPE
   SYNTAX     Integer32 (1..5)
   ACCESS     not-accessible
   STATUS     obsolete
   DESCRIPTION
     "This variable represents the atmIfVccTxTdpTable
      specific index for the atmIfVccTxTdpTable."
::= { atmIfVccTxTdpEntry 1 }

atmIfVccTxTdpValue OBJECT-TYPE
   SYNTAX     Unsigned32 (0..2147483647)
   ACCESS     read-only
   STATUS     obsolete
   DESCRIPTION
     "This variable represents an individual value for the
      atmIfVccTxTdpTable."
::= { atmIfVccTxTdpEntry 2 }

atmIfVccRxTdpTable OBJECT-TYPE
   SYNTAX     SEQUENCE OF AtmIfVccRxTdpEntry
   ACCESS     not-accessible
   STATUS     obsolete
   DESCRIPTION
     "This attribute is HISTORICAL. Please refer to the attribute of the 
      same name in the group AtmTmOper.
      
      This attribute is a vector of four traffic parameters whose meanings 
      are defined by the rxTrafficDescType attribute. The values of peak 
      cell rate (PCR), sustained cell rate (SCR) are expressed in cells/s. 
      Maximum burst size (MBS) is expressed in cells. Cell Delay 
      Variation Tolerance (CDVT) is expressed in microseconds.
      
      When rxTrafficDescType is 1 or 2, none of the parameters are used.
      
      When rxTrafficDescType is 3, parameter 1 represents the PCR for 
      CLP equal to 0 and 1 traffic; parameter 4 represents the CDVT.
      
      When rxTrafficDescType is 4, parameter 1 represents the PCR for 
      CLP equal to 0 and 1 traffic; parameter 2 represents the PCR for 
      CLP equal to 0 traffic with cell discard; parameter 4 represents the 
      CDVT.
      
      When rxTrafficDescType is 5, parameter 1 represents the PCR for 
      CLP equal to 0 and 1 traffic; parameter 2 represents the PCR for 
      CLP equal to 0 traffic with cell tagging; parameter 4 represents the 
      CDVT.
      
      When rxTrafficDescType is a 6, parameter 1 represents the PCR for 
      CLP equal to 0 and 1 traffic; parameter 2 represents the SCR for 
      CLP equal to 0 and 1 traffic; parameter 3 represents the MBS for 
      CLP equal to 0 and 1 traffic; parameter 4 represents the CDVT. 
      
      When rxTrafficDescType is 7, parameter 1 represents the PCR for 
      CLP equal to 0 and 1 traffic; parameter 2 represents the SCR for 
      CLP equal to 0 traffic with cell discard; parameter 3 represents the 
      MBS for CLP equal to 0 traffic; parameter 4 represents the CDVT.
      
      When rxTrafficDescType is 8, parameter 1 represents the PCR for 
      CLP equal to 0 and 1 traffic; parameter 2 represents the SCR for 
      CLP equal to 0 traffic with cell tagging; parameter 3 represents the 
      MBS for CLP equal to 0 traffic; parameter 4 represents the CDVT. 
      
      If Upc is disabled for this connection, the values of PCR, SCR, 
      MBS and CDVT is a combination of provisioned parameters. If Upc 
      is enabled, the values of PCR, SCR, MBS, and CDVT is exactly the 
      values used by the usage parameter control hardware in policing the 
      arriving traffic. These may vary slightly from the provisioned values 
      due to granularity of the hardware. In the case where the PCR is 
      equal to the SCR, the effective MBS is zero."
::= { atmIfVcc 295 }

atmIfVccRxTdpEntry OBJECT-TYPE
   SYNTAX     AtmIfVccRxTdpEntry
   ACCESS     not-accessible
   STATUS     obsolete
   DESCRIPTION
     "An entry in the atmIfVccRxTdpTable."
   INDEX {
      atmIfIndex,
      atmIfVccIndex,
      atmIfVccRxTdpIndex }
::= { atmIfVccRxTdpTable 1 }

AtmIfVccRxTdpEntry ::= SEQUENCE {
   atmIfVccRxTdpIndex
      Integer32,
   atmIfVccRxTdpValue
      Unsigned32 }

atmIfVccRxTdpIndex OBJECT-TYPE
   SYNTAX     Integer32 (1..4)
   ACCESS     not-accessible
   STATUS     obsolete
   DESCRIPTION
     "This variable represents the atmIfVccRxTdpTable
      specific index for the atmIfVccRxTdpTable."
::= { atmIfVccRxTdpEntry 1 }

atmIfVccRxTdpValue OBJECT-TYPE
   SYNTAX     Unsigned32 (0..2147483647)
   ACCESS     read-only
   STATUS     obsolete
   DESCRIPTION
     "This variable represents an individual value for the
      atmIfVccRxTdpTable."
::= { atmIfVccRxTdpEntry 2 }

atmIfVccTxQThreshTable OBJECT-TYPE
   SYNTAX     SEQUENCE OF AtmIfVccTxQThreshEntry
   ACCESS     not-accessible
   STATUS     obsolete
   DESCRIPTION
     "This attribute is HISTORICAL. Please refer to the attribute of the 
      same name in the group AtmTmOper.
      
      This attribute indicates the queue limit and the discard thresholds 
      for the transmit queue of this connection. 
      
      The first element indicates the queue limit. Depending upon the 
      atmServiceCategory of the connection, the provisioned value of the 
      transmit queue limit is derived from the txQueueLimit attribute 
      under one of the subcomponents of the AtmIf CA component. If the 
      connection has traffic shaping disabled, then this attribute relates to 
      the common queue. If traffic shaping is enabled, then this attribute 
      relates to the per-VC queue.
      
      The second element is the threshold that marks the transition from 
      congestion state 1 to congestion state 0. This is the threshold at 
      which traffic with discard priority (DP) = 1 is discarded. This 
      threshold is set approximately at 90 percent of the first parameter, 
      the operational queue limit.
      
      The third element is the threshold that marks the transition from 
      congestion state 2 to congestion state 1. This is the threshold at 
      which traffic with DP = 2 is discarded. This threshold is set 
      approximately at 75 percent of the first parameter, the operational 
      queue limit.
      
      The fourth element is the threshold that marks the transition from 
      congestion state 3 to congestion state 2. This is the threshold at 
      which traffic with DP = 3 is discarded. This threshold is set 
      approximately at 35 percent of the first parameter, the operational 
      queue limit."
::= { atmIfVcc 352 }

atmIfVccTxQThreshEntry OBJECT-TYPE
   SYNTAX     AtmIfVccTxQThreshEntry
   ACCESS     not-accessible
   STATUS     obsolete
   DESCRIPTION
     "An entry in the atmIfVccTxQThreshTable."
   INDEX {
      atmIfIndex,
      atmIfVccIndex,
      atmIfVccTxQThreshIndex }
::= { atmIfVccTxQThreshTable 1 }

AtmIfVccTxQThreshEntry ::= SEQUENCE {
   atmIfVccTxQThreshIndex
      Integer32,
   atmIfVccTxQThreshValue
      Unsigned32 }

atmIfVccTxQThreshIndex OBJECT-TYPE
   SYNTAX     Integer32 (0..3)
   ACCESS     not-accessible
   STATUS     obsolete
   DESCRIPTION
     "This variable represents the atmIfVccTxQThreshTable
      specific index for the atmIfVccTxQThreshTable."
::= { atmIfVccTxQThreshEntry 1 }

atmIfVccTxQThreshValue OBJECT-TYPE
   SYNTAX     Unsigned32 (0..30720)
   ACCESS     read-only
   STATUS     obsolete
   DESCRIPTION
     "This variable represents an individual value for the
      atmIfVccTxQThreshTable."
::= { atmIfVccTxQThreshEntry 2 }

atmIfVccFqpTable OBJECT-TYPE
   SYNTAX     SEQUENCE OF AtmIfVccFqpEntry
   ACCESS     not-accessible
   STATUS     obsolete
   DESCRIPTION
     "This attribute is HISTORICAL. Please refer to the attribute of the 
      same name in the group AtmTmOper.
      
      This attribute is a vector of three elements that indicate the quality 
      of service parameters for the forward direction for this connection. 
      This attribute is used for SPVC and SVC connections on a PNNI 
      interface.
      
      The cdv element indicates the acceptable peak-to-peak Cell Delay 
      Variation (CDV) of real-time connections (CBR, and rt-VBR). 
      
      The ctd element indicates the acceptable maximum Cell Transfer 
      Delay (maxCtd) of real-time connections (CBR, and rt-VBR). 
      
      The clr element indicates the acceptable Cell Loss Ratio (CLR) of 
      CBR, rt-VBR, and nrt-VBR connections."
::= { atmIfVcc 357 }

atmIfVccFqpEntry OBJECT-TYPE
   SYNTAX     AtmIfVccFqpEntry
   ACCESS     not-accessible
   STATUS     obsolete
   DESCRIPTION
     "An entry in the atmIfVccFqpTable."
   INDEX {
      atmIfIndex,
      atmIfVccIndex,
      atmIfVccFqpIndex }
::= { atmIfVccFqpTable 1 }

AtmIfVccFqpEntry ::= SEQUENCE {
   atmIfVccFqpIndex
      INTEGER,
   atmIfVccFqpValue
      Unsigned32 }

atmIfVccFqpIndex OBJECT-TYPE
   SYNTAX     INTEGER  {
                 cdv(0),
                 ctd(1),
                 clr(2) }
   ACCESS     not-accessible
   STATUS     obsolete
   DESCRIPTION
     "This variable represents the atmIfVccFqpTable
      specific index for the atmIfVccFqpTable."
::= { atmIfVccFqpEntry 1 }

atmIfVccFqpValue OBJECT-TYPE
   SYNTAX     Unsigned32 (0..2147483647)
   ACCESS     read-only
   STATUS     obsolete
   DESCRIPTION
     "This variable represents an individual value for the
      atmIfVccFqpTable."
::= { atmIfVccFqpEntry 2 }

atmIfVccBqpTable OBJECT-TYPE
   SYNTAX     SEQUENCE OF AtmIfVccBqpEntry
   ACCESS     not-accessible
   STATUS     obsolete
   DESCRIPTION
     "This attribute is HISTORICAL. Please refer to the attribute of the 
      same name in the group AtmTmOper.
      
      This attribute is a vector of three elements that indicate the quality 
      of service parameters for the backward direction for this 
      connection. This attribute is used for SPVC and SVC connections 
      on a PNNI interface.
      
      The cdv element indicates the acceptable peak-to-peak Cell Delay 
      Variation (CDV) of real-time connections (CBR, and rt-VBR). 
      
      The ctd element indicates the acceptable maximum Cell Transfer 
      Delay (maxCtd) of real-time connections (CBR, and rt-VBR). 
      
      The clr element indicates the acceptable Cell Loss Ratio (CLR) of 
      CBR, rt-VBR, and nrt-VBR connections."
::= { atmIfVcc 358 }

atmIfVccBqpEntry OBJECT-TYPE
   SYNTAX     AtmIfVccBqpEntry
   ACCESS     not-accessible
   STATUS     obsolete
   DESCRIPTION
     "An entry in the atmIfVccBqpTable."
   INDEX {
      atmIfIndex,
      atmIfVccIndex,
      atmIfVccBqpIndex }
::= { atmIfVccBqpTable 1 }

AtmIfVccBqpEntry ::= SEQUENCE {
   atmIfVccBqpIndex
      INTEGER,
   atmIfVccBqpValue
      Unsigned32 }

atmIfVccBqpIndex OBJECT-TYPE
   SYNTAX     INTEGER  {
                 cdv(0),
                 ctd(1),
                 clr(2) }
   ACCESS     not-accessible
   STATUS     obsolete
   DESCRIPTION
     "This variable represents the atmIfVccBqpTable
      specific index for the atmIfVccBqpTable."
::= { atmIfVccBqpEntry 1 }

atmIfVccBqpValue OBJECT-TYPE
   SYNTAX     Unsigned32 (0..2147483647)
   ACCESS     read-only
   STATUS     obsolete
   DESCRIPTION
     "This variable represents an individual value for the
      atmIfVccBqpTable."
::= { atmIfVccBqpEntry 2 }


-- AtmIf/n Vcc/vpi.vci VirtualChannelDescriptor,
-- AtmIf/n Vpt/vpi Vcc/vci VirtualChannelDescriptor
-- The Vcd component contains provisioning information about its 
-- parent Vcc component.

atmIfVccVcd OBJECT IDENTIFIER ::= { atmIfVcc 2 }



atmIfVccVcdRowStatusTable OBJECT-TYPE
   SYNTAX     SEQUENCE OF AtmIfVccVcdRowStatusEntry
   ACCESS     not-accessible
   STATUS     mandatory
   DESCRIPTION
     "This entry controls the addition and deletion of 
      atmIfVccVcd components."
::= { atmIfVccVcd 1 }

atmIfVccVcdRowStatusEntry OBJECT-TYPE
   SYNTAX     AtmIfVccVcdRowStatusEntry
   ACCESS     not-accessible
   STATUS     mandatory
   DESCRIPTION
     "A single entry in the table represents a single 
      atmIfVccVcd component."
   INDEX {
      atmIfIndex,
      atmIfVccIndex,
      atmIfVccVcdIndex }
::= { atmIfVccVcdRowStatusTable 1 }

AtmIfVccVcdRowStatusEntry ::= SEQUENCE {
   atmIfVccVcdRowStatus
      RowStatus,
   atmIfVccVcdComponentName
      DisplayString,
   atmIfVccVcdStorageType
      StorageType,
   atmIfVccVcdIndex
      NonReplicated }

atmIfVccVcdRowStatus OBJECT-TYPE
   SYNTAX     RowStatus 
   ACCESS     read-only
   STATUS     mandatory
   DESCRIPTION
     "This variable is used as the basis for SNMP naming of
      atmIfVccVcd components.
      These components cannot be added nor deleted."
::= { atmIfVccVcdRowStatusEntry 1 }

atmIfVccVcdComponentName OBJECT-TYPE
   SYNTAX     DisplayString 
   ACCESS     read-only
   STATUS     mandatory
   DESCRIPTION
     "This variable provides the component's string name for
      use with the ASCII Console Interface"
::= { atmIfVccVcdRowStatusEntry 2 }

atmIfVccVcdStorageType OBJECT-TYPE
   SYNTAX     StorageType 
   ACCESS     read-only
   STATUS     mandatory
   DESCRIPTION
     "This variable represents the storage type value for the
      atmIfVccVcd tables."
::= { atmIfVccVcdRowStatusEntry 4 }

atmIfVccVcdIndex OBJECT-TYPE
   SYNTAX     NonReplicated 
   ACCESS     not-accessible
   STATUS     mandatory
   DESCRIPTION
     "This variable represents the index for the atmIfVccVcd tables."
::= { atmIfVccVcdRowStatusEntry 10 }

atmIfVccVcdLbkTable OBJECT-TYPE
   SYNTAX     SEQUENCE OF AtmIfVccVcdLbkEntry
   ACCESS     not-accessible
   STATUS     mandatory
   DESCRIPTION
     "This group contains the provisionable loopback attributes for a Vcc, 
      Vpc, or Vpt component.
      
      Note that certain loopback requests may not be possible on a given 
      connection. In such cases, the corresponding operational loopback 
      attribute in the Status group of the Vcc, Vpc, or Vpt component is 
      set to notApplicable and the requested loopback is not performed.
      
      If loopbacks are provisioned to be on, and for any reason the 
      segment or end-to-end OAM loopback cells are not relayed, the 
      connection component becomes troubled, and user cell traffic may 
      be discarded. If loopbacks are provisioned to be on, all of the nodes 
      in the segment, and external networks which are in the end-to-end 
      connection must relay the OAM loopback cells."
::= { atmIfVccVcd 100 }

atmIfVccVcdLbkEntry OBJECT-TYPE
   SYNTAX     AtmIfVccVcdLbkEntry
   ACCESS     not-accessible
   STATUS     mandatory
   DESCRIPTION
     "An entry in the atmIfVccVcdLbkTable."
   INDEX {
      atmIfIndex,
      atmIfVccIndex,
      atmIfVccVcdIndex }
::= { atmIfVccVcdLbkTable 1 }

AtmIfVccVcdLbkEntry ::= SEQUENCE {
   atmIfVccVcdSegLinkSideLoopback
      INTEGER,
   atmIfVccVcdSegSwitchSideLoopback
      INTEGER,
   atmIfVccVcdEndToEndLoopback
      INTEGER,
   atmIfVccVcdLoopbackMonitoring
      INTEGER }

atmIfVccVcdSegLinkSideLoopback OBJECT-TYPE
   SYNTAX     INTEGER  {
                 on(0),
                 off(1),
                 sameAsInterface(2) }
   ACCESS     read-write
   STATUS     mandatory
   DESCRIPTION
     "This attribute specifies whether link-side segment loopback 
      insertion should be performed on this connection. 
      
      When sameAsInterface is selected, the link-side segment loopback 
      insertion for the connection is based on the segLinkSideLoopback 
      attribute of the connection's parent AtmIf componentif the ATM 
      interface has link-side segment loopback insertion turned on, then 
      link-side segment loopback insertion is also on for the connection. 
      
      When on or off is selected, link-side segment loopback insertion is 
      turned on or off respectively for the connection regardless of the 
      provisioning of the parent AtmIf component.
      
      Note that link-side segment loopback insertion is not possible if the 
      connectionPointType attribute of the Vcc or Vpc component is 
      connectingPoint. Link-side segment loopback insertion is also not 
      possible if the distributionType of the Vcc is pointToMultipoint. In 
      such cases, the associated segLinkSideLoopbackState attribute 
      indicates notApplicable and link-side segment loopback insertion is 
      not performed. Link-side segment loopback insertion is always 
      possible on a Vpt."
   DEFVAL     { sameAsInterface }
::= { atmIfVccVcdLbkEntry 10 }

atmIfVccVcdSegSwitchSideLoopback OBJECT-TYPE
   SYNTAX     INTEGER  {
                 on(0),
                 off(1),
                 sameAsInterface(2) }
   ACCESS     read-write
   STATUS     mandatory
   DESCRIPTION
     "This attribute specifies whether switch-side segment loopback 
      insertion should be performed on this connection.
      
      When sameAsInterface is selected, the switch-side segment 
      loopback for the connection is based on the segSwitchSideLoopback 
      attribute of the connection's parent AtmIf componentif the ATM 
      interface has switch-side segment loopback insertion turned on, 
      then switch-side segment loopback insertion is also on for the 
      connection. 
      
      When on or off is selected, switch-side segment loopback insertion 
      is turned on or off respectively for the connection regardless of the 
      provisioning of the parent AtmIf component.
      
      Note that switch-side segment loopback insertion is not possible if 
      the connectionPointType attribute of the Vcc or Vpc component is 
      connectingPoint or connectionEndPoint. Switch-side segment 
      loopback insertion is also not possible if the distributionType of the 
      Vcc is pointToMultipoint In such cases, the associated 
      segSwitchSideLoopbackState attribute indicates notApplicable and 
      switch-side segment loopback insertion is not performed. Switch-
      side segment loopback is never possible on a Vpt."
   DEFVAL     { sameAsInterface }
::= { atmIfVccVcdLbkEntry 20 }

atmIfVccVcdEndToEndLoopback OBJECT-TYPE
   SYNTAX     INTEGER  {
                 on(0),
                 off(1),
                 sameAsInterface(2) }
   ACCESS     read-write
   STATUS     mandatory
   DESCRIPTION
     "This attribute specifies whether end-to-end loopback insertion 
      should be performed on this connection.
      
      When sameAsInterface is selected, the end-to-end loopback for the 
      connection is based on the endToEndLoopback attribute of the 
      connection's parent AtmIf componentif the ATM interface has 
      end-to-end loopback insertion turned on, then end-to-end loopback 
      insertion is also on for the connection. 
      
      When on or off is selected, end-to-end loopback insertion is turned 
      on or off respectively for the connection regardless of the 
      provisioning of the parent AtmIf component.
      
      Note that end-to-end loopback insertion is not possible if the 
      connectionPointType attribute of the Vcc or Vpc component is 
      connectingPoint or segmentEndPoint. End-to-end loopback 
      insertion is also not possible if the distributionType of the Vcc is 
      pointToMultipoint. In such cases, the associated 
      endToEndLoopbackState attribute indicates notApplicable and end-
      to-end loopback insertion is not performed. End-to-end loopback 
      insertion is always possible on a Vpt."
   DEFVAL     { sameAsInterface }
::= { atmIfVccVcdLbkEntry 30 }

atmIfVccVcdLoopbackMonitoring OBJECT-TYPE
   SYNTAX     INTEGER  {
                 on(0),
                 off(1),
                 sameAsInterface(2) }
   ACCESS     read-write
   STATUS     mandatory
   DESCRIPTION
     "This attribute specifies whether or not a connection monitors the 
      OAM stream for loopback cells. Currently this attributed is only 
      applied to Passport-specific trace cells and only affects 
      connectingPoints.
      
      When sameAsInterface is selected, the trace visibility for the 
      connection is based on the traceVisible attribute of the connection's 
      parent AtmIf componentif the ATM interface is trace visible, then 
      the connection is also trace visible. 
      
      When on or off is selected, the connection is nor isn't visible to 
      trace cells respectively for the connection regardless of the 
      provisioning of the parent AtmIf component.
      
      Note that trace visibility only affects connections whose 
      connectionPointType attribute of the Vcc or Vpc component is 
      connectingPoint. Trace visibility is also not possible if the 
      distributionType of the Vcc is pointToMultipoint."
   DEFVAL     { sameAsInterface }
::= { atmIfVccVcdLbkEntry 1000 }

atmIfVccVcdTrafficTable OBJECT-TYPE
   SYNTAX     SEQUENCE OF AtmIfVccVcdTrafficEntry
   ACCESS     not-accessible
   STATUS     mandatory
   DESCRIPTION
     "This group contains traffic related provisionable attributes for the 
      Vcc and Vpc components. The attributes' operational values are 
      reflected in the Traffic group for these components. Changing any 
      of the attributes in this group causes a service interruption on the 
      Vcc or Vpc component."
::= { atmIfVccVcd 110 }

atmIfVccVcdTrafficEntry OBJECT-TYPE
   SYNTAX     AtmIfVccVcdTrafficEntry
   ACCESS     not-accessible
   STATUS     mandatory
   DESCRIPTION
     "An entry in the atmIfVccVcdTrafficTable."
   INDEX {
      atmIfIndex,
      atmIfVccIndex,
      atmIfVccVcdIndex }
::= { atmIfVccVcdTrafficTable 1 }

AtmIfVccVcdTrafficEntry ::= SEQUENCE {
   atmIfVccVcdTxTrafficDescType
      INTEGER,
   atmIfVccVcdTxQosClass
      INTEGER,
   atmIfVccVcdFwdQosClass
      INTEGER,
   atmIfVccVcdHoldingPriority
      INTEGER,
   atmIfVccVcdRxTrafficDescType
      INTEGER,
   atmIfVccVcdRxQosClass
      INTEGER,
   atmIfVccVcdBwdQosClass
      INTEGER,
   atmIfVccVcdAtmServiceCategory
      INTEGER,
   atmIfVccVcdTrafficShaping
      INTEGER,
   atmIfVccVcdUnshapedTransmitQueueing
      INTEGER,
   atmIfVccVcdUsageParameterControl
      INTEGER,
   atmIfVccVcdBearerClassBbc
      INTEGER,
   atmIfVccVcdTransferCapabilityBbc
      INTEGER,
   atmIfVccVcdClippingBbc
      INTEGER,
   atmIfVccVcdBestEffort
      INTEGER,
   atmIfVccVcdFwdFrameDiscard
      INTEGER,
   atmIfVccVcdBwdFrameDiscard
      INTEGER }

atmIfVccVcdTxTrafficDescType OBJECT-TYPE
   SYNTAX     INTEGER  {
                 n1(1),
                 n2(2),
                 n3(3),
                 n4(4),
                 n5(5),
                 n6(6),
                 n7(7),
                 n8(8),
                 n9(9) }
   ACCESS     read-write
   STATUS     obsolete
   DESCRIPTION
     "This attribute is migrated to the AtmTmProv group.
      
      This attribute specifies the type of traffic management which is 
      applied to the transmit direction of this connection as defined in the 
      ATM Forum. The txTrafficDescType determines the number and 
      meaning of the parameters in the txTrafficDescParm attribute."
   DEFVAL     { n1 }
::= { atmIfVccVcdTrafficEntry 10 }

atmIfVccVcdTxQosClass OBJECT-TYPE
   SYNTAX     INTEGER  {
                 unspecified(0),
                 constantBitRate(1),
                 variableBitRate(2),
                 connectionOriented(3),
                 connectionless(4) }
   ACCESS     read-write
   STATUS     obsolete
   DESCRIPTION
     "This attribute specifies the quality of service for the transmit 
      direction for this connection.
      
      The constantBitRate class refers to traffic offered on services such 
      as a constant bit rate video service. This traffic is highest priority.
      
      The variableBitRate class refers to traffic offered on services such 
      as packetized audio and video.
      
      The connectionOriented class refers to connection-oriented traffic 
      such as Frame Relay or X.25 traffic. 
      
      The connectionless traffic refers to traffic offered through 
      connectionless trunks such as certain LAN protocols.
      
      The unspecified class supports a 'best effort' type of service, where 
      there is a minimum guarantee of bandwidth. This traffic is lowest 
      priority.
      
      This attribute is obsolete. The value is migrated into 
      atmServiceCategory. The atmServiceCategory applies in both 
      transmit and receive directions.
      
      unspecified maps to unspecifiedBitRate;
      constantBitRate maps to constantBitRate;
      variableBitRate maps to variableBitRateRt;
      connectionOriented maps to variableBitRateNrt
      connectionless maps to variableBitRateNrt"
   DEFVAL     { connectionOriented }
::= { atmIfVccVcdTrafficEntry 20 }

atmIfVccVcdFwdQosClass OBJECT-TYPE
   SYNTAX     INTEGER  {
                 n0(0),
                 n1(1),
                 n2(2),
                 n3(3),
                 n4(4) }
   ACCESS     read-write
   STATUS     obsolete
   DESCRIPTION
     "This attribute is migrated to the AtmTmProv group.
      
      This attribute specifies the quality of service for the forward 
      direction for this connection. This attribute is only used for SPVC 
      connections.
      
      Class 1 supports a QOS that meets Service Class A performance 
      requirements (Circuit emulation, constant bit rate video).
      
      Class 2 supports a QOS that meets Service Class B performance 
      requirements (Variable bit rate audio and video).
      
      Class 3 supports a QOS that meets Service Class C performance 
      requirements (Connection-Oriented Data Transfer).
      
      Class 4 supports a QOS that meets Service Class D performance 
      requirements (Connectionless Data Transfer).
      
      Class 0 is the unspecified bit rate QOS class; no objective is 
      specified for the performance parameters."
   DEFVAL     { n0 }
::= { atmIfVccVcdTrafficEntry 21 }

atmIfVccVcdHoldingPriority OBJECT-TYPE
   SYNTAX     INTEGER  {
                 n0(0),
                 n1(1),
                 n2(2),
                 n3(3),
                 n4(4) }
   ACCESS     read-write
   STATUS     obsolete
   DESCRIPTION
     "This attribute is migrated to the AtmTmProv group.
      
      This attribute specifies the holding priority of this connection. In a 
      situation where the link bandwidth fluctuates, such as over an IMA 
      link, holding priority is used to determine which connections are 
      held and which are released. Holding priority 4 connections are the 
      first to be released. Holding priority 0 connections are the last to be 
      released. This value provisioned in the Vcd or Vpd may be 
      overridden by certain applications, for example Vcc Test, which run 
      over this connection. The default holding priority for a provisioned 
      connection is higher then default holding priorities for dynamic 
      (SVC) connections."
   DEFVAL     { n2 }
::= { atmIfVccVcdTrafficEntry 25 }

atmIfVccVcdRxTrafficDescType OBJECT-TYPE
   SYNTAX     INTEGER  {
                 n1(1),
                 n2(2),
                 n3(3),
                 n4(4),
                 n5(5),
                 n6(6),
                 n7(7),
                 n8(8),
                 sameAsTx(15) }
   ACCESS     read-write
   STATUS     obsolete
   DESCRIPTION
     "This attribute is migrated to the AtmTmProv group.
      
      This attribute specifies the type of traffic management which is 
      applied to the receive direction of this connection as defined in the 
      ATM Forum. The rxTrafficDescType determines the number and 
      meaning of the parameters in the rxTrafficDescParm attribute
      
      When sameAsTx is selected, the rxTrafficDescType as well as the 
      rxTrafficDescParm are taken from the transmit values."
   DEFVAL     { sameAsTx }
::= { atmIfVccVcdTrafficEntry 30 }

atmIfVccVcdRxQosClass OBJECT-TYPE
   SYNTAX     INTEGER  {
                 unspecified(0),
                 constantBitRate(1),
                 variableBitRate(2),
                 connectionOriented(3),
                 connectionless(4),
                 sameAsTx(15) }
   ACCESS     read-write
   STATUS     obsolete
   DESCRIPTION
     "This attribute specifies the quality of service for the receive 
      direction for this connection.
      
      The constantBitRate class refers to traffic offered on services such 
      as a constant bit rate video service. 
      
      The variableBitRate class refers to traffic offered on services such 
      as packetized audio and video. 
      
      The connectionOriented class refers to connection-oriented traffic.
      
      The connectionless traffic refers to traffic offered through 
      connectionless trunks. 
      
      The unspecified class supports a 'best effort' type of service, where 
      there is a minimum guarantee of bandwidth. 
      
      The sameAsTx selection sets the receive quality of service to be the 
      same as the transmit quality of service.
      
      This attribute is obsolete. The value of txQosClass is migrated into 
      atmServiceCategory. The value of this attribute is ignored. 
      AtmServiceCategory applies in both transmit and receive directions."
   DEFVAL     { sameAsTx }
::= { atmIfVccVcdTrafficEntry 40 }

atmIfVccVcdBwdQosClass OBJECT-TYPE
   SYNTAX     INTEGER  {
                 n0(0),
                 n1(1),
                 n2(2),
                 n3(3),
                 n4(4),
                 sameAsFwd(15) }
   ACCESS     read-write
   STATUS     obsolete
   DESCRIPTION
     "This attribute is migrated to the AtmTmProv group.
      
      This attribute specifies the quality of service for the backward 
      direction for this connection. This attribute is only used for SPVC 
      connections.
      
      Class 1 supports a QOS that meets Service Class A performance 
      requirements (Circuit emulation, constant bit rate video).
      
      Class 2 supports a QOS that meets Service Class B performance 
      requirements (Variable bit rate audio and video).
      
      Class 3 supports a QOS that meets Service Class C performance 
      requirements (Connection-Oriented Data Transfer).
      
      Class 4 supports a QOS that meets Service Class D performance 
      requirements (Connectionless Data Transfer).
      
      Class 0 is the unspecified bit rate QOS class; no objective is 
      specified for the performance parameters.
      
      The sameAsFwd selection sets the backward quality of service to 
      be the same as the forward quality of service."
   DEFVAL     { sameAsFwd }
::= { atmIfVccVcdTrafficEntry 41 }

atmIfVccVcdAtmServiceCategory OBJECT-TYPE
   SYNTAX     INTEGER  {
                 unspecifiedBitRate(0),
                 constantBitRate(1),
                 rtVariableBitRate(2),
                 nrtVariableBitRate(3),
                 derivedFromBBC(15) }
   ACCESS     read-write
   STATUS     obsolete
   DESCRIPTION
     "This attribute is migrated to the AtmTmProv group.
      
      This attribute specifies the ATM service category for both directions 
      of the connection. 
      
      The value derivedFromBBC may only be used if the SrcPvc 
      component is provisioned under this Vcc.Otherwise a specific ATM 
      service category must be specified. 
      
      If this attribute is set to derivedFromBBC, the Broadband Bearer 
      Capability (BBC) and bestEffort attributes are used to determine the 
      atmServiceCategory of this connection. 
      
      If this attribute is set to other than derivedFromBBC, the value of 
      this attribute is used to override the provisioned BBC Information 
      Element parameters. In those cases, the BBC attributes are not used. 
      
      The constantBitRate service category is intended for real time 
      applications, that is those requiring tightly constrained delay and 
      delay variation, as would be appropriate for voice and video 
      applications. The consistent availability of a fixed quantity of 
      bandwidth is considered appropriate for CBR service. Cells which 
      are delayed beyond the value specified by Cell Transfer Delay are 
      assumed to be of significantly reduce value to the application.
      
      The rtVariableBitRate service category is intended for real time 
      applications, that is those requiring tightly constrained delay and 
      delay variation, as would be appropriate for voice and video 
      applications. Sources are expected to transmit at a rate which varies 
      with time. Equivalently, the source can be described as 'bursty'. 
      Cells which are delayed beyond the value specified by CTD are 
      assumed to be of significantly reduced value to the application. Real 
      time VBR service may support statistical multiplexing of real time 
      sources.
      
      The nrtVariableBitRate service category is intended for non-real 
      time applications which have bursty traffic characteristics and which 
      can be characterized in terms of a PCR, SCR, and MBS. For those 
      cells which are transferred within the traffic contract, the application 
      expects a low cell loss ratio. For all connections, it expects a bound 
      on the mean cell transfer delay. Non-real time VBR service may 
      support statistical multiplexing of connections.
      
      The unspecifiedBitRate service is intended for non-real time 
      applications; that is, those not requiring tightly constrained delay 
      and delay variation. UBR sources are expected to be bursty. UBR 
      service supports a high degree of statistical multiplexing among 
      sources. UBR service does not specify traffic related service 
      guarantees. No numerical commitments are made with respect to 
      the cell loss ratio experienced by a UBR connection, or as to the 
      cell transfer delay experienced by cells on the connection."
   DEFVAL     { unspecifiedBitRate }
::= { atmIfVccVcdTrafficEntry 42 }

atmIfVccVcdTrafficShaping OBJECT-TYPE
   SYNTAX     INTEGER  {
                 disabled(1),
                 sameAsInterface(2) }
   ACCESS     read-write
   STATUS     obsolete
   DESCRIPTION
     "This attribute is migrated to the AtmTmProv group.
      
      This attribute specifies whether this connection uses traffic shaping 
      when transmitting traffic to the ATM interface.
      
      When sameAsInterface is selected, traffic shaping for the 
      connection is based on the trafficShaping attribute of the 
      connection's parent AtmIf componentif the ATM interface has 
      traffic shaping enabled, then traffic shaping is enabled for the 
      connection. Note that enabling traffic shaping may have no effect 
      under certain cases. These cases are listed in the description of the 
      trafficShaping operational attribute, which is under the Vcc and Vpc 
      components.
      
      When disabled is selected, traffic shaping for this connection is 
      disabled regardless of the provisioning of the parent AtmIf 
      component."
   DEFVAL     { sameAsInterface }
::= { atmIfVccVcdTrafficEntry 50 }

atmIfVccVcdUnshapedTransmitQueueing OBJECT-TYPE
   SYNTAX     INTEGER  {
                 common(1),
                 sameAsInterface(3) }
   ACCESS     read-write
   STATUS     obsolete
   DESCRIPTION
     "This attribute is migrated to the AtmTmProv group.
      
      This attribute only applies when this connection is unshaped. This 
      attribute defines the transmit queueing method for this connection if 
      it is unshaped. Refer to the unshapedTransmitQueueing attribute 
      under the AtmIf for more details on the meaning of this attribute. 
      
      When this attribute is set to sameAsInterface, the value from the 
      AtmIf is used. 
      
      When this attribute is set to common, transmit traffic on this 
      unshaped connection is destined for the common queue."
   DEFVAL     { sameAsInterface }
::= { atmIfVccVcdTrafficEntry 60 }

atmIfVccVcdUsageParameterControl OBJECT-TYPE
   SYNTAX     INTEGER  {
                 disabled(1),
                 sameAsInterface(2) }
   ACCESS     read-write
   STATUS     obsolete
   DESCRIPTION
     "This attribute is migrated to the AtmTmProv group.
      
      This attribute specifies whether this connection enforces usage 
      parameter control when receiving traffic from the ATM interface.
      
      When sameAsInterface is selected, UPC for the connection is 
      based on the usageParameterControl attribute of the connection's 
      parent AtmIf componentif the ATM interface has UPC enabled, 
      then UPC is enabled for the connection. Note that enabling UPC 
      may have no effect under certain cases. These cases are listed in the 
      description of the usageParameterControl operational attribute, 
      which is under the Vcc and Vpc components.
      
      When disabled is selected, UPC for this connection is disabled 
      regardless of the provisioning of the parent AtmIf component."
   DEFVAL     { sameAsInterface }
::= { atmIfVccVcdTrafficEntry 70 }

atmIfVccVcdBearerClassBbc OBJECT-TYPE
   SYNTAX     INTEGER  {
                 a(1),
                 c(3),
                 x(16),
                 vp(24),
                 derivedFromServiceCategory(31) }
   ACCESS     read-write
   STATUS     obsolete
   DESCRIPTION
     "This attribute is migrated to the AtmTmProv group.
      
      This attribute specifies the bearer capability. This attribute is only 
      used for SPVC and SPVP connections. It is one of the Broadband 
      Bearer Capability (BBC) attributes. The purpose of the BBC 
      information element is to indicate a requested broadband 
      connection-oriented bearer service to be provided by the network.
      
      The value derivedFromServiceCategory specifies that the actual 
      value which is used for this connection is derived from the value of 
      the atmServiceCategory. Either, this attribute must be set to 
      derivedFromServiceCategory, or the atmServiceCategory attribute 
      must be set to derivedFromBBC, but not both.
      
      Class a service is a connection-oriented, constant bit rate ATM 
      transport service. Class a service has end to end timing 
      requirements and may require stringent cell loss, cell delay and cell 
      delay variation performance.When a is set, the user is requesting 
      more than an ATM only service. The network may look at the AAL 
      to provide interworking based upon its contents. 
      
      Class c service is a connection-oriented, variable bit rate ATM 
      transport service. Class c service has no end-to-end timing 
      requirements. When c is set, the user is requesting more than an 
      ATM only service. The network interworking function may look at 
      the AAL and provide service based on it.
      
      Class x service is a connection-oriented ATM transport service 
      where the AAL, trafficType (vbr or cbr) and timing requirements 
      are user defined (that is, transparent to the network).When x is set 
      the user is requesting an ATM only service from the network.
      
      Class vp service is used to specify a transparent VP service. When 
      the value of this attribute is vp, the user is requesting an ATM only 
      service from the network. In this case, the network shall not process 
      any higher layer protocol. This service differs from class x service 
      in that with the class vp service both the VCI field (except or VCI 
      values 0, 3, 4, and 6 through 15) and Payload Type field are 
      transported transparently by the network. This attribute value is 
      only applicable to SPVP connections."
   DEFVAL     { derivedFromServiceCategory }
::= { atmIfVccVcdTrafficEntry 71 }

atmIfVccVcdTransferCapabilityBbc OBJECT-TYPE
   SYNTAX     INTEGER  {
                 n0(0),
                 n1(1),
                 n2(2),
                 n5(5),
                 n8(8),
                 n9(9),
                 n10(10),
                 notApplicable(30),
                 derivedFromServiceCategory(31) }
   ACCESS     read-write
   STATUS     obsolete
   DESCRIPTION
     "This attribute is migrated to the AtmTmProv group.
      
      This attribute specifies the transfer capability for this connection. 
      Uni 3.0/3.1 traffic type and end-to-end timing parameters are 
      mapped into this parameter as follows:
      <transferCapability: TrafficType, Timing>
      0: NoIndication, NoIndication
      1: NoIndication, yes
      2: NoIndication, no
      5: CBR, yes
      8: VBR, NoIndication
      9: VBR, yes
      10: VBR, no
      
      NotApplicable specifies that the user does not want to specify the 
      transfer capability.
      
      The CBR traffic type refers to traffic offered on services such as a 
      constant bit rate video service or a circuit emulation.
      
      The VBR traffic type refers to traffic offered on services such as 
      packetized audio and video, or data.
      
      The value no indication for traffic type is used if the user has not set 
      the traffic type; similarly for end-to-end timing.
      
      The value yes for end-to-end timing indicates that end-to-end 
      timing is required.
      
      The value no for end-to-end timing indicates that end-to-end timing 
      is not required.
      
      The value derivedFromServiceCategory specifies that the actual 
      value which is used for this connection is derived from the value of 
      the atmServiceCategory. Either, this attribute must be set to 
      derivedFromServiceCategory, or the atmServiceCategory attribute 
      must be set to derivedFromBBC, but not both."
   DEFVAL     { derivedFromServiceCategory }
::= { atmIfVccVcdTrafficEntry 72 }

atmIfVccVcdClippingBbc OBJECT-TYPE
   SYNTAX     INTEGER  {
                 no(0),
                 yes(1) }
   ACCESS     read-write
   STATUS     obsolete
   DESCRIPTION
     "This attribute is migrated to the AtmTmProv group.
      
      This attribute specifies the value for the clipping susceptibility 
      parameter in the BBC Information Element. This attribute is only 
      used for SPVC connections. It is one of the Broadband Bearer 
      Capability attributes.
      
      Clipping is an impairment in which the first fraction of a second of 
      information to be transferred is lost. It occurs after a call is 
      answered and before an associated connection is switched through."
   DEFVAL     { no }
::= { atmIfVccVcdTrafficEntry 74 }

atmIfVccVcdBestEffort OBJECT-TYPE
   SYNTAX     INTEGER  {
                 indicated(0),
                 notIndicated(1),
                 derivedFromServiceCategory(15) }
   ACCESS     read-write
   STATUS     obsolete
   DESCRIPTION
     "This attribute is migrated to the AtmTmProv group.
      
      This attribute specifies the value of the best effort parameter in the 
      ATM Traffic Descriptor Information Element. This attribute is only 
      used for Soft PVC connections. It is one of the Broadband Bearer 
      Capability attributes.
      
      The value indicated implies that the quality of service for this 
      connection is not guaranteed.
      
      The value notIndicated implies that the quality of service for this 
      connection is guaranteed.
      
      The value derivedFromServiceCategory specifies that the actual 
      value which is used for this connection is derived from the value of 
      the atmServiceCategory. Either, this attribute must be set to 
      derivedFromServiceCategory, or the atmServiceCategory attribute 
      must be set to derivedFromBBC, but not both."
   DEFVAL     { derivedFromServiceCategory }
::= { atmIfVccVcdTrafficEntry 75 }

atmIfVccVcdFwdFrameDiscard OBJECT-TYPE
   SYNTAX     INTEGER  {
                 notIndicated(0),
                 indicated(1) }
   ACCESS     read-write
   STATUS     obsolete
   DESCRIPTION
     "This attribute specifies the activation of frame discard functionality 
      in the forward data direction, at relay points, for this connection. It 
      applies to each hop of the connection. Frame discard functions 
      should not be requested if this connection is not transferring frame 
      (AAL5) traffic. Setting the value to indicated for any other traffic 
      type results in all traffic being discarded.
      
      If this connection point is a permanent (provisioned) VCC mid-
      point, this attribute specifies whether the Partial Packet 
      Discard (PPD) function is to be enabled or disabled in the transmit 
      direction at this connecting point. The PPD function allows the 
      connecting point to discard the remainder of a cell-forwarded AAL5 
      frame if one cell of this frame has been discarded. The PPD 
      function increases the 'goodput' of the link, since cells which are 
      only going to be discarded by the AAL5 reassembly are not 
      transmitted.
      
      At a permanent VCC connecting point which is not a connection 
      endpoint, when this attribute is set to indicated, the PPD function is 
      applied to transmit traffic at this connecting point. It should not be 
      indicated for connections whose end points are not performing 
      AAL5 segmentation and reassembly. When this attribute is set to 
      notIndicated, the PPD feature is not applied to transmit traffic at 
      this connecting point.
      
      At a SPVC origin on a PNNI interface, a value of indicated 
      specifies that frame discard is requested in the forward direction. 
      The frame discard function for SPVCs consists of PPD at the SPVC 
      origin and at all intermediate connecting points. When this attribute 
      is set to notIndicated, forward frame discard is not requested in the 
      SPVC call setup. Thus PPD is not enabled at the SPVC origin nor at 
      any intermediate connecting point.
      
      At all points along a VPC, this setting is ignored.
      
      At a permanent VCC connection endpoint, this value is ignored. If 
      AAL5 segmentation and reassembly has been requested, PPD and 
      Early Packet Discard (EPD) are automatically enabled.
      
      This attribute has been migrated to txFrameDiscard."
   DEFVAL     { notIndicated }
::= { atmIfVccVcdTrafficEntry 76 }

atmIfVccVcdBwdFrameDiscard OBJECT-TYPE
   SYNTAX     INTEGER  {
                 notIndicated(0),
                 indicated(1) }
   ACCESS     read-write
   STATUS     obsolete
   DESCRIPTION
     "This attribute specifies the activation of frame discard functionality 
      in the backward data direction, at relay points, for this connection. 
      It applies to each hop of the connection. Frame discard functions 
      should not be requested if this connection is not transferring frame 
      (AAL5) traffic. Setting the value to indicated for any other traffic 
      type results in all traffic being discarded.
      
      If this connection point is a permanent (provisioned) VCC mid-
      point, this attribute specifies whether the Partial Packet Discard 
      (PPD) function is to be enabled or disabled in the receive direction 
      at this connecting point. The PPD function allows the connecting 
      point to discard the remainder of a cell-forwarded AAL5 frame if 
      one cell of this frame has been discarded. The PPD function 
      increases the 'goodput' of the link, since cells which are only going 
      to be discarded by the AAL5 reassembly are not received.
      
      At a permanent VCC connecting point which is not a connection 
      endpoint, when this attribute is set to indicated, the PPD function is 
      applied to receive traffic at this connecting point. It should not be 
      indicated for connections whose end points are not performing 
      AAL5 segmentation and reassembly. When this attribute is set to 
      notIndicated, the PPD feature is not applied to receive traffic at this 
      connecting point.
      
      At a SPVC origin on a PNNI interface, a value of indicated 
      specifies that frame discard is requested in the backward direction. 
      The frame discard function for SPVCs consists of PPD at the SPVC 
      origin and at all intermediate connecting points. When this attribute 
      is set to notIndicated, backwards frame discard is not requested in 
      the SPVC call setup. Thus PPD is not enabled at the SPVC origin 
      nor at any intermediate connecting point.
      
      At all points along a VPC, this setting is ignored.
      
      At a permanent VCC connection endpoint, this value is ignored. If 
      AAL5 segmentation and reassembly has been requested, PPD and 
      Early Packet Discard (EPD) are automatically enabled.
      
      This attribute has been migrated to rxFrameDiscard."
   DEFVAL     { notIndicated }
::= { atmIfVccVcdTrafficEntry 77 }

atmIfVccVcdAcctTable OBJECT-TYPE
   SYNTAX     SEQUENCE OF AtmIfVccVcdAcctEntry
   ACCESS     not-accessible
   STATUS     mandatory
   DESCRIPTION
     "This group contains the provisionable ATM accounting attributes 
      for a Vcc, Vpc, or Vpt component."
::= { atmIfVccVcd 111 }

atmIfVccVcdAcctEntry OBJECT-TYPE
   SYNTAX     AtmIfVccVcdAcctEntry
   ACCESS     not-accessible
   STATUS     mandatory
   DESCRIPTION
     "An entry in the atmIfVccVcdAcctTable."
   INDEX {
      atmIfIndex,
      atmIfVccIndex,
      atmIfVccVcdIndex }
::= { atmIfVccVcdAcctTable 1 }

AtmIfVccVcdAcctEntry ::= SEQUENCE {
   atmIfVccVcdCorrelationTag
      AsciiString }

atmIfVccVcdCorrelationTag OBJECT-TYPE
   SYNTAX     AsciiString (SIZE (0..32))
   ACCESS     read-write
   STATUS     mandatory
   DESCRIPTION
     "This attribute specifies a unique indentifier for each end of a PVC. It 
      that may be used by downstream processing systems to correlate 
      accounting records issued at different nodes in the network. The 
      attribute can be up to 32 bytes long. If it is less than 32 bytes, it is 
      zero filled on the right to create a 32 byte value. The resulting value 
      is recorded in the attribute callConnId for this PVC's ATM 
      accounting records.
      If the attribute is a null string then this PVC does not have any 
      accounting records generated for it."
   DEFVAL     { ''H }  -- ""
::= { atmIfVccVcdAcctEntry 10 }

atmIfVccVcdTxTdpTable OBJECT-TYPE
   SYNTAX     SEQUENCE OF AtmIfVccVcdTxTdpEntry
   ACCESS     not-accessible
   STATUS     obsolete
   DESCRIPTION
     "This attribute is migrated to the AtmTmProv group.
      
      This attribute is a vector of five traffic parameters whose meanings 
      are defined by the txTrafficDescType attribute. The values of peak 
      cell rate (PCR), sustained cell rate (SCR) and requested shaping rate 
      are expressed in cell/s. Maximum burst size (MBS) is expressed in 
      cells. CDVT is expressed in microseconds. The values of PCR, 
      SCR, MBS and CDVT are used for connection admission control 
      (CAC). The value of CDVT is only used for connections where the 
      atmServiceCategory is constantBitRate. For all other values of 
      atmServiceCategory, CDVT is ignored. The values of PCR, SCR 
      and requested shaping rate are used to determine the actual shaping 
      rate where traffic shaping is enabled.
      
      When txTrafficDescType is 1 or 2, all of the parameters must be set 
      to zero.
      
      When txTrafficDescType is 3, parameter 1 represents the PCR for 
      CLP equal to 0 and 1 traffic; parameter 4 represents the CDVT; and 
      parameter 5 represents the requested shaping rate. A non-zero value 
      in parameter 5 overrides any value in parameter 1. This result is 
      used as the PCR. Parameter 1 must be non-zero. Parameters 2 and 3 
      must be zero.
      
      When txTrafficDescType is 4, parameter 1 represents the PCR for 
      CLP equal to 0 and 1 traffic with cell discard; parameter 2 
      represents the PCR for CLP equal to 0 traffic; parameter 4 
      represents the CDVT; and parameter 5 represents the requested 
      shaping rate. A non-zero value in parameter 5 overrides any value in 
      parameter 1. This result is used as the PCR. Parameter 1 must be 
      greater than or equal to parameter 2. Parameters 1 and 2 must be 
      non-zero. Parameter 3 must be zero.
      
      When txTrafficDescType is 5, parameter 1 represents the PCR for 
      CLP equal to 0 and 1 traffic with cell tagging; parameter 2 
      represents the PCR for CLP equal to 0 traffic; parameter 4 
      represents the CDVT; and parameter 5 represents the requested 
      shaping rate. A non-zero value in parameter 5 overrides any value in 
      parameter 1. This result is used as the PCR. Parameter 1 must be 
      greater than or equal to parameter 2. Parameters 1 and 2 must be 
      non-zero. Parameter 3 must be zero.
      
      When txTrafficDescType is 6, parameter 1 represents the PCR for 
      CLP equal to 0 and 1 traffic; parameter 2 represents the SCR for 
      CLP equal to 0 and 1 traffic; parameter 3 represents the MBS for 
      CLP equal to 0 and 1 traffic; parameter 4 represents the CDVT; and 
      parameter 5 represents the requested shaping rate. A non-zero value 
      in parameter 5 overrides any value in parameter 1. This result is 
      used as the PCR. Parameters 1, 2 and 3 must be non-zero. 
      Parameter 1 must be greater than or equal to parameter 2. Parameter 
      5, must either be zero (unused) or greater than or equal to parameter 
      2.
      
      When txTrafficDescType is 7, parameter 1 represents the PCR for 
      CLP equal to 0 and 1 traffic; parameter 2 represents the SCR for 
      CLP equal to 0 with cell discard; parameter 3 represents the MBS 
      for CLP equal to 0 traffic; parameter 4 represents the CDVT; and 
      parameter 5 represents the requested shaping rate. A non-zero value 
      in parameter 5 overrides any value in parameter 1. This result is 
      used as the PCR. Parameters 1, 2 and 3 must be non-zero. 
      Parameter 1 must be greater than or equal to parameter 2. Parameter 
      5, must either be zero (unused) or greater than or equal to parameter 
      2.
      
      When txTrafficDescType is 8, parameter 1 represents the PCR for 
      CLP equal to 0 and 1 traffic; parameter 2 represents the SCR for 
      CLP equal to 0 traffic with cell tagging; parameter 3 represents the 
      MBS for CLP equal to 0 traffic; parameter 4 represents the CDVT; 
      and parameter 5 represents the requested shaping rate. A non-zero 
      value in parameter 5 overrides any value in parameter 1. This result 
      is used as the PCR. Parameters 1, 2 and 3 must be non-zero. 
      Parameter 1 must be greater than or equal to parameter 2. Parameter 
      5, must either be zero (unused) or greater than or equal to parameter 
      2.
      
      Whenever it is valid for PCR to be specified, parameter 5 may also 
      be used to specify a requested shaping rate. A non-zero value in 
      parameter 5 overrides the value in parameter 1 and is used as the 
      peak cell rate in calculations of CAC and shaping rate.
      
      For txTrafficDescType 3, 4 and 5, the transmit traffic is shaped at 
      the next rate less than the PCR. 
      
      For txTrafficDescType 6, 7 and 8, the transmit traffic is shaped at 
      the highest available rate which is between PCR and SCR. 
      However, if there is no available shaping rate between PCR and 
      SCR, traffic is shaped at the next rate above the PCR."
::= { atmIfVccVcd 297 }

atmIfVccVcdTxTdpEntry OBJECT-TYPE
   SYNTAX     AtmIfVccVcdTxTdpEntry
   ACCESS     not-accessible
   STATUS     obsolete
   DESCRIPTION
     "An entry in the atmIfVccVcdTxTdpTable."
   INDEX {
      atmIfIndex,
      atmIfVccIndex,
      atmIfVccVcdIndex,
      atmIfVccVcdTxTdpIndex }
::= { atmIfVccVcdTxTdpTable 1 }

AtmIfVccVcdTxTdpEntry ::= SEQUENCE {
   atmIfVccVcdTxTdpIndex
      Integer32,
   atmIfVccVcdTxTdpValue
      Unsigned32 }

atmIfVccVcdTxTdpIndex OBJECT-TYPE
   SYNTAX     Integer32 (1..5)
   ACCESS     not-accessible
   STATUS     obsolete
   DESCRIPTION
     "This variable represents the atmIfVccVcdTxTdpTable
      specific index for the atmIfVccVcdTxTdpTable."
::= { atmIfVccVcdTxTdpEntry 1 }

atmIfVccVcdTxTdpValue OBJECT-TYPE
   SYNTAX     Unsigned32 (0..2147483647)
   ACCESS     read-write
   STATUS     obsolete
   DESCRIPTION
     "This variable represents an individual value for the
      atmIfVccVcdTxTdpTable."
::= { atmIfVccVcdTxTdpEntry 2 }

atmIfVccVcdRxTdpTable OBJECT-TYPE
   SYNTAX     SEQUENCE OF AtmIfVccVcdRxTdpEntry
   ACCESS     not-accessible
   STATUS     obsolete
   DESCRIPTION
     "This attribute is migrated to the AtmTmProv group.
      
      This attribute is a vector of four traffic parameters whose meanings 
      are defined by the rxTrafficDescType attribute. The values of peak 
      cell rate (PCR) and sustained cell rate (SCR) are expressed in 
      cell/s. Maximum burst size (MBS) is expressed in cells. The value 
      of CDVT is expressed in microseconds. The values of PCR, SCR, 
      MBS and CDVT are used for usage parameter control (UPC).
      
      When rxTrafficDescType is 1 or 2, all of the parameters must be set 
      to zero (unused).
      
      When rxTrafficDescType is 3, parameter 1 represents the PCR for 
      CLP equal to 0 and 1 traffic. Parameter 1 must be non-zero. 
      Parameters 2 and 3 must be set to zero (unused).
      
      When rxTrafficDescType is 4, parameter 1 represents the PCR for 
      CLP equal to 0 and 1 traffic; parameter 2 represents the PCR for 
      CLP equal to 0 traffic with cell discard. Parameters 1 and 2 must be 
      non-zero. Parameter 3 must be set to zero (unused). Parameter 1 
      must be greater than or equal to parameter 2.
      
      When rxTrafficDescType is 5, parameter 1 represents the PCR for 
      CLP equal to 0 and 1 traffic; parameter 2 represents the PCR for 
      CLP equal to 0 traffic with cell tagging. Parameters 1 and 2 must be 
      non-zero. Parameter 3 must be set to zero (unused). Parameter 1 
      must be greater than or equal to parameter 2.
      
      When rxTrafficDescType is a 6, parameter 1 represents the PCR for 
      CLP equal to 0 and 1 traffic; parameter 2 represents the SCR for 
      CLP equal to 0 and 1 traffic; parameter 3 represents the MBS for 
      CLP equal to 0 and 1 traffic. Parameters 1, 2 and 3 must be non-
      zero. Parameter 1 must be greater than or equal to Parameter 2. 
      
      When rxTrafficDescType is 7, parameter 1 represents the PCR for 
      CLP equal to 0 and 1 traffic; parameter 2 represents the SCR for 
      CLP equal to 0 traffic with cell discard; parameter 3 represents the 
      MBS for CLP equal to 0 traffic. Parameters 1, 2 and 3 must be non-
      zero. Parameter 1 must be greater than or equal to parameter 2. 
      
      When rxTrafficDescType is 8, parameter 1 represents the PCR for 
      CLP equal to 0 and 1 traffic; parameter 2 represents the SCR for 
      CLP equal to 0 traffic with cell tagging; parameter 3 represents the 
      MBS for CLP equal to 0 traffic. Parameter 1, 2 and 3 must be non-
      zero. Parameter 1 must be greater than or equal to parameter 2.
      
      When rxTrafficDescType is any value from 3 through 8, parameter 
      4 represents the CDVT. If this value is zero, the CDVT is taken 
      from the ConnectionAdministrator defaults for the particular 
      atmServiceCategory of this connection.
      
      When rxTrafficDescriptorType is 3 through 8, there are certain 
      extreme combinations of rxTrafficDescParm which are outside the 
      capabilities of the UPC hardware. The check prov command detects 
      such cases and generates an error message. If this happens, adjust 
      the parameters until they fall within the supported limits. 
      
      To calculate the limits, use the following formulae:
      I1 = 1 000 000 000 / PCR
      L1 = CDVT * 1000
      I2 = 1 000 000 000 / SCR
      L2 = CDVT + (MBS - 1) * (I2 - I1)
      I1 and I2 must be less than or equal to 335 523 840. I1 + L1 must 
      be less than or equal to 1 342 156 800. I2 + L2 must be less than or 
      equal to 1 342 156 800. Note that I2 and L2 only apply when the 
      rxTrafficDescriptorType is 6 through 8.
      
      If the values of I1, L1, I2 or L2 are closer to the limits described 
      above, a further restriction applies. Specifically, if either:
      I1 > 41 940 480 or
      I2 > 41 940 480 or
      I1 + L1 > 167 769 600 or
      I2 + L2 > 167 769 600
      then both I1 and I2 must be greater than 20 480. 
      
      Parameter 5 of the rxTrafficDescParm is always unused. 
      
      If the rxTrafficDescType is sameAsTx, the values in this attribute 
      are taken from the txTrafficDescParm."
::= { atmIfVccVcd 298 }

atmIfVccVcdRxTdpEntry OBJECT-TYPE
   SYNTAX     AtmIfVccVcdRxTdpEntry
   ACCESS     not-accessible
   STATUS     obsolete
   DESCRIPTION
     "An entry in the atmIfVccVcdRxTdpTable."
   INDEX {
      atmIfIndex,
      atmIfVccIndex,
      atmIfVccVcdIndex,
      atmIfVccVcdRxTdpIndex }
::= { atmIfVccVcdRxTdpTable 1 }

AtmIfVccVcdRxTdpEntry ::= SEQUENCE {
   atmIfVccVcdRxTdpIndex
      Integer32,
   atmIfVccVcdRxTdpValue
      Unsigned32 }

atmIfVccVcdRxTdpIndex OBJECT-TYPE
   SYNTAX     Integer32 (1..5)
   ACCESS     not-accessible
   STATUS     obsolete
   DESCRIPTION
     "This variable represents the atmIfVccVcdRxTdpTable
      specific index for the atmIfVccVcdRxTdpTable."
::= { atmIfVccVcdRxTdpEntry 1 }

atmIfVccVcdRxTdpValue OBJECT-TYPE
   SYNTAX     Unsigned32 (0..2147483647)
   ACCESS     read-write
   STATUS     obsolete
   DESCRIPTION
     "This variable represents an individual value for the
      atmIfVccVcdRxTdpTable."
::= { atmIfVccVcdRxTdpEntry 2 }

atmIfVccVcdFqpTable OBJECT-TYPE
   SYNTAX     SEQUENCE OF AtmIfVccVcdFqpEntry
   ACCESS     not-accessible
   STATUS     obsolete
   DESCRIPTION
     "This attribute is migrated to the AtmTmProv group.
      
      This attribute is a vector of three elements that specify the quality of 
      service parameters for the forward direction for this connection. 
      This attribute is used for SPVC connections.
      
      The cdv element specifies the acceptable peak-to-peak Cell Delay 
      Variation (CDV) of real-time connections (CBR, and rt-VBR). It is 
      signalled through the extended QoS information element.
      
      The ctd specifies the acceptable maximum Cell Transfer Delay 
      (maxCtd) of real-time connections (CBR, and rt-VBR). 
      It is signalled through the end to end transit delay information 
      element.
      
      The clr specifies the acceptable Cell Loss Ratio (CLR) of CBR, rt-
      VBR, and nrt-VBR connections. It is signalled through the extended 
      QoS information element."
::= { atmIfVccVcd 359 }

atmIfVccVcdFqpEntry OBJECT-TYPE
   SYNTAX     AtmIfVccVcdFqpEntry
   ACCESS     not-accessible
   STATUS     obsolete
   DESCRIPTION
     "An entry in the atmIfVccVcdFqpTable."
   INDEX {
      atmIfIndex,
      atmIfVccIndex,
      atmIfVccVcdIndex,
      atmIfVccVcdFqpIndex }
::= { atmIfVccVcdFqpTable 1 }

AtmIfVccVcdFqpEntry ::= SEQUENCE {
   atmIfVccVcdFqpIndex
      INTEGER,
   atmIfVccVcdFqpValue
      Unsigned32 }

atmIfVccVcdFqpIndex OBJECT-TYPE
   SYNTAX     INTEGER  {
                 cdv(0),
                 ctd(1),
                 clr(2) }
   ACCESS     not-accessible
   STATUS     obsolete
   DESCRIPTION
     "This variable represents the atmIfVccVcdFqpTable
      specific index for the atmIfVccVcdFqpTable."
::= { atmIfVccVcdFqpEntry 1 }

atmIfVccVcdFqpValue OBJECT-TYPE
   SYNTAX     Unsigned32 (0..2147483647)
   ACCESS     read-write
   STATUS     obsolete
   DESCRIPTION
     "This variable represents an individual value for the
      atmIfVccVcdFqpTable."
::= { atmIfVccVcdFqpEntry 2 }

atmIfVccVcdBqpTable OBJECT-TYPE
   SYNTAX     SEQUENCE OF AtmIfVccVcdBqpEntry
   ACCESS     not-accessible
   STATUS     obsolete
   DESCRIPTION
     "This attribute is migrated to the AtmTmProv group.
      
      This attribute is a vector of three elements that specify the quality of 
      service parameters for the backward direction for this connection. 
      This attribute is used for SPVC connections.
      
      The cdv element specifies the acceptable peak-to-peak Cell Delay 
      Variation (CDV) of real-time connections (CBR, and rt-VBR). 
      
      It is signalled through the extended QoS information element.
      
      The ctd specifies the acceptable maximum Cell Transfer Delay 
      (maxCtd) of real-time connections (CBR, and rt-VBR). It is 
      signalled through the end to end transit delay information element.
      
      The clr specifies the acceptable Cell Loss Ratio (CLR) of CBR, rt-
      VBR, and nrt-VBR connections. It is signalled through the extended 
      QoS information element."
::= { atmIfVccVcd 360 }

atmIfVccVcdBqpEntry OBJECT-TYPE
   SYNTAX     AtmIfVccVcdBqpEntry
   ACCESS     not-accessible
   STATUS     obsolete
   DESCRIPTION
     "An entry in the atmIfVccVcdBqpTable."
   INDEX {
      atmIfIndex,
      atmIfVccIndex,
      atmIfVccVcdIndex,
      atmIfVccVcdBqpIndex }
::= { atmIfVccVcdBqpTable 1 }

AtmIfVccVcdBqpEntry ::= SEQUENCE {
   atmIfVccVcdBqpIndex
      INTEGER,
   atmIfVccVcdBqpValue
      Unsigned32 }

atmIfVccVcdBqpIndex OBJECT-TYPE
   SYNTAX     INTEGER  {
                 cdv(0),
                 ctd(1),
                 clr(2) }
   ACCESS     not-accessible
   STATUS     obsolete
   DESCRIPTION
     "This variable represents the atmIfVccVcdBqpTable
      specific index for the atmIfVccVcdBqpTable."
::= { atmIfVccVcdBqpEntry 1 }

atmIfVccVcdBqpValue OBJECT-TYPE
   SYNTAX     Unsigned32 (0..2147483647)
   ACCESS     read-write
   STATUS     obsolete
   DESCRIPTION
     "This variable represents an individual value for the
      atmIfVccVcdBqpTable."
::= { atmIfVccVcdBqpEntry 2 }


-- AtmIf/n Vcc/vpi.vci Vcd TrafficManagement, 
-- AtmIf/n Vpc/vci Vpd TrafficManagement,
-- AtmIf/n Vpt/vpi Vpd TrafficManagement,
-- AtmIf/n Vpt/vpi Vcc/vci Vcd TrafficManagement
-- This component contains provisioned traffic management attributes 
-- of a connection. It is added automatically when a Vcc, Vpc, or Vpt is 
-- added in provisioning mode. It is a mandatory subcomponent of the 
-- Vcd or Vpd component.

atmIfVccVcdTm OBJECT IDENTIFIER ::= { atmIfVccVcd 2 }



atmIfVccVcdTmRowStatusTable OBJECT-TYPE
   SYNTAX     SEQUENCE OF AtmIfVccVcdTmRowStatusEntry
   ACCESS     not-accessible
   STATUS     mandatory
   DESCRIPTION
     "This entry controls the addition and deletion of 
      atmIfVccVcdTm components."
::= { atmIfVccVcdTm 1 }

atmIfVccVcdTmRowStatusEntry OBJECT-TYPE
   SYNTAX     AtmIfVccVcdTmRowStatusEntry
   ACCESS     not-accessible
   STATUS     mandatory
   DESCRIPTION
     "A single entry in the table represents a single 
      atmIfVccVcdTm component."
   INDEX {
      atmIfIndex,
      atmIfVccIndex,
      atmIfVccVcdIndex,
      atmIfVccVcdTmIndex }
::= { atmIfVccVcdTmRowStatusTable 1 }

AtmIfVccVcdTmRowStatusEntry ::= SEQUENCE {
   atmIfVccVcdTmRowStatus
      RowStatus,
   atmIfVccVcdTmComponentName
      DisplayString,
   atmIfVccVcdTmStorageType
      StorageType,
   atmIfVccVcdTmIndex
      NonReplicated }

atmIfVccVcdTmRowStatus OBJECT-TYPE
   SYNTAX     RowStatus 
   ACCESS     read-only
   STATUS     mandatory
   DESCRIPTION
     "This variable is used as the basis for SNMP naming of
      atmIfVccVcdTm components.
      These components cannot be added nor deleted."
::= { atmIfVccVcdTmRowStatusEntry 1 }

atmIfVccVcdTmComponentName OBJECT-TYPE
   SYNTAX     DisplayString 
   ACCESS     read-only
   STATUS     mandatory
   DESCRIPTION
     "This variable provides the component's string name for
      use with the ASCII Console Interface"
::= { atmIfVccVcdTmRowStatusEntry 2 }

atmIfVccVcdTmStorageType OBJECT-TYPE
   SYNTAX     StorageType 
   ACCESS     read-only
   STATUS     mandatory
   DESCRIPTION
     "This variable represents the storage type value for the
      atmIfVccVcdTm tables."
::= { atmIfVccVcdTmRowStatusEntry 4 }

atmIfVccVcdTmIndex OBJECT-TYPE
   SYNTAX     NonReplicated 
   ACCESS     not-accessible
   STATUS     mandatory
   DESCRIPTION
     "This variable represents the index for the atmIfVccVcdTm tables."
::= { atmIfVccVcdTmRowStatusEntry 10 }

atmIfVccVcdTmProvTable OBJECT-TYPE
   SYNTAX     SEQUENCE OF AtmIfVccVcdTmProvEntry
   ACCESS     not-accessible
   STATUS     mandatory
   DESCRIPTION
     "This group contains traffic related provisionable attributes for the 
      Vcc, Vpc, and Vpt components. Changing any of the attributes in 
      this group causes a service interruption on the Vcc, Vpc, or Vpt 
      component."
::= { atmIfVccVcdTm 100 }

atmIfVccVcdTmProvEntry OBJECT-TYPE
   SYNTAX     AtmIfVccVcdTmProvEntry
   ACCESS     not-accessible
   STATUS     mandatory
   DESCRIPTION
     "An entry in the atmIfVccVcdTmProvTable."
   INDEX {
      atmIfIndex,
      atmIfVccIndex,
      atmIfVccVcdIndex,
      atmIfVccVcdTmIndex }
::= { atmIfVccVcdTmProvTable 1 }

AtmIfVccVcdTmProvEntry ::= SEQUENCE {
   atmIfVccVcdTmTxTrafficDescType
      INTEGER,
   atmIfVccVcdTmFwdQosClass
      INTEGER,
   atmIfVccVcdTmTxQueueLimit
      Unsigned32,
   atmIfVccVcdTmHoldingPriority
      INTEGER,
   atmIfVccVcdTmRxTrafficDescType
      INTEGER,
   atmIfVccVcdTmBwdQosClass
      INTEGER,
   atmIfVccVcdTmAtmServiceCategory
      INTEGER,
   atmIfVccVcdTmTrafficShaping
      INTEGER,
   atmIfVccVcdTmUnshapedTransmitQueueing
      INTEGER,
   atmIfVccVcdTmWeight
      Unsigned32,
   atmIfVccVcdTmForceTagging
      INTEGER,
   atmIfVccVcdTmUsageParameterControl
      INTEGER,
   atmIfVccVcdTmBearerClassBbc
      INTEGER,
   atmIfVccVcdTmTransferCapabilityBbc
      INTEGER,
   atmIfVccVcdTmTxWredThreshold
      Unsigned32,
   atmIfVccVcdTmClippingBbc
      INTEGER,
   atmIfVccVcdTmBestEffort
      INTEGER,
   atmIfVccVcdTmTxPacketWiseDiscard
      INTEGER,
   atmIfVccVcdTmTxWredMode
      INTEGER,
   atmIfVccVcdTmRxPacketWiseDiscard
      INTEGER,
   atmIfVccVcdTmAbrConnectionType
      INTEGER }

atmIfVccVcdTmTxTrafficDescType OBJECT-TYPE
   SYNTAX     INTEGER  {
                 n1(1),
                 n2(2),
                 n3(3),
                 n4(4),
                 n5(5),
                 n6(6),
                 n7(7),
                 n8(8),
                 n9(9) }
   ACCESS     read-write
   STATUS     mandatory
   DESCRIPTION
     "This attribute specifies the type of traffic management which is 
      applied to the transmit direction of this connection as defined in the 
      ATM Forum. The txTrafficDescType determines the number and 
      meaning of the parameters in the txTrafficDescParm attribute.
      
      This attribute can have a value of 9 if and only if the 
      atmServiceCategory is availableBitRate."
   DEFVAL     { n1 }
::= { atmIfVccVcdTmProvEntry 10 }

atmIfVccVcdTmFwdQosClass OBJECT-TYPE
   SYNTAX     INTEGER  {
                 n0(0),
                 n1(1),
                 n2(2),
                 n3(3),
                 n4(4) }
   ACCESS     read-write
   STATUS     mandatory
   DESCRIPTION
     "This attribute specifies the quality of service for the forward 
      direction for this connection. This attribute is only used for SPVC 
      connections.
      
      Class 1 supports a QOS that meets Service Class A performance 
      requirements (circuit emulation, constant bit rate video).
      
      Class 2 supports a QOS that meets Service Class B performance 
      requirements (variable bit rate audio and video).
      
      Class 3 supports a QOS that meets Service Class C performance 
      requirements (Connection-Oriented Data Transfer).
      
      Class 4 supports a QOS that meets Service Class D performance 
      requirements (Connectionless Data Transfer).
      
      Class 0 is the unspecified bit rate QOS class; no objective is 
      specified for the performance parameters."
   DEFVAL     { n0 }
::= { atmIfVccVcdTmProvEntry 21 }

atmIfVccVcdTmTxQueueLimit OBJECT-TYPE
   SYNTAX     Unsigned32 (0 | 5..63488)
   ACCESS     read-write
   STATUS     mandatory
   DESCRIPTION
     "This attribute specifies an override to the default transmit queue 
      limit for this connection. A value other than sameAsCa may be 
      specified only for ATM IP cards. This attribute is not applicable for 
      basic Vpts.
      
      A value of sameAsCa means to use the default common or per-VC 
      transmit queue limit as defined by the CA service category for this 
      connection. 
      
      A value from 5 to 63,488 indicates that a specific transmit queue 
      limit is requested which differs from the default which is defined 
      under the CA component for this service category. A specific value 
      is ignored for connections where common queuing is specified for 
      the service category.
      
      The actual transmit queue limit for a connection is visible in the Vcc 
      Tm, Vpc Tm, or Vpt Tm txQueueThresholds attribute.

      VALUES (

      0 = sameAsCa

      )"
   DEFVAL     { 0 }
::= { atmIfVccVcdTmProvEntry 22 }

atmIfVccVcdTmHoldingPriority OBJECT-TYPE
   SYNTAX     INTEGER  {
                 n0(0),
                 n1(1),
                 n2(2),
                 n3(3),
                 n4(4) }
   ACCESS     read-write
   STATUS     mandatory
   DESCRIPTION
     "This attribute specifies the holding priority of this connection. In a 
      situation where the link bandwidth fluctuates, such as over an IMA 
      link, holding priority is used to determine which connections are 
      held and which are released. Holding priority 4 connections are the 
      first to be released. Holding priority 0 connections are the last to be 
      released. This value provisioned in the Vcd or Vpd may be 
      overridden by certain applications, for example Vcc Test, which run 
      over this connection. The default holding priority for a provisioned 
      connection is higher then default holding priorities for dynamic 
      (SVC) connections. 
      
      This attribute is not applicable for Vpt Vccs."
   DEFVAL     { n2 }
::= { atmIfVccVcdTmProvEntry 25 }

atmIfVccVcdTmRxTrafficDescType OBJECT-TYPE
   SYNTAX     INTEGER  {
                 n1(1),
                 n2(2),
                 n3(3),
                 n4(4),
                 n5(5),
                 n6(6),
                 n7(7),
                 n8(8),
                 n9(9),
                 sameAsTx(15) }
   ACCESS     read-write
   STATUS     mandatory
   DESCRIPTION
     "This attribute specifies the type of traffic management which is 
      applied to the receive direction of this connection as defined in the 
      ATM Forum. The rxTrafficDescType determines the number and 
      meaning of the parameters in the rxTrafficDescParm attribute.
      
      When this attribute is set to sameAsTx, the rxTrafficDescType as 
      well as the rxTrafficDescParm are taken from the 
      txTrafficDescType and txTrafficDescParm values."
   DEFVAL     { sameAsTx }
::= { atmIfVccVcdTmProvEntry 30 }

atmIfVccVcdTmBwdQosClass OBJECT-TYPE
   SYNTAX     INTEGER  {
                 n0(0),
                 n1(1),
                 n2(2),
                 n3(3),
                 n4(4),
                 sameAsFwd(15) }
   ACCESS     read-write
   STATUS     mandatory
   DESCRIPTION
     "This attribute specifies the quality of service for the backward 
      direction for this connection. This attribute is only used for SPVC 
      connections.
      
      Class 1 supports a QOS that meets Service Class A performance 
      requirements (Circuit emulation, constant bit rate video).
      
      Class 2 supports a QOS that meets Service Class B performance 
      requirements (Variable bit rate audio and video).
      
      Class 3 supports a QOS that meets Service Class C performance 
      requirements (Connection-Oriented Data Transfer).
      
      Class 4 supports a QOS that meets Service Class D performance 
      requirements (Connectionless Data Transfer).
      
      Class 0 is the unspecified bit rate QOS class; no objective is 
      specified for the performance parameters.
      
      The sameAsFwd selection sets the backward quality of service to 
      be the same as the forward quality of service."
   DEFVAL     { sameAsFwd }
::= { atmIfVccVcdTmProvEntry 41 }

atmIfVccVcdTmAtmServiceCategory OBJECT-TYPE
   SYNTAX     INTEGER  {
                 unspecifiedBitRate(0),
                 constantBitRate(1),
                 rtVariableBitRate(2),
                 nrtVariableBitRate(3),
                 availableBitRate(4),
                 derivedFromBBC(15) }
   ACCESS     read-write
   STATUS     mandatory
   DESCRIPTION
     "This attribute specifies the ATM service category for both directions 
      of the connection. 
      
      The value derivedFromBBC may only be used if the SrcPvc 
      component is provisioned under this Vcc. Otherwise a specific 
      ATM service category must be specified. 
      
      If this attribute is set to derivedFromBBC, the Broadband Bearer 
      Capability (BBC) and bestEffort attributes are used to determine the 
      atmServiceCategory of this connection. 
      
      If this attribute is set to other than derivedFromBBC, the value of 
      this attribute is used to override the provisioned BBC Information 
      Element parameters. In those cases, the BBC attributes are not used. 
      
      The constantBitRate service category is intended for real time 
      applications, that is those requiring tightly constrained delay and 
      delay variation, as would be appropriate for voice and video 
      applications. The consistent availability of a fixed quantity of 
      bandwidth is considered appropriate for CBR service. Cells which 
      are delayed beyond the value specified by Cell Transfer Delay are 
      assumed to be of significantly reduced value to the application.
      
      The rtVariableBitRate service category is intended for real time 
      applications, that is those requiring tightly constrained delay and 
      delay variation, as would be appropriate for voice and video 
      applications. Sources are expected to transmit at a rate which varies 
      with time. Equivalently, the source can be described as 'bursty'. 
      Cells which are delayed beyond the value specified by CTD are 
      assumed to be of significantly reduced value to the application. Real 
      time VBR service may support statistical multiplexing of real time 
      sources.
      
      The nrtVariableBitRate service category is intended for non-real 
      time applications which have bursty traffic characteristics and which 
      can be characterized in terms of a PCR, SCR, and MBS. For those 
      cells which are transferred within the traffic contract, the application 
      expects a low cell loss ratio. For all connections, it expects a bound 
      on the mean cell transfer delay. Non-real time VBR service may 
      support statistical multiplexing of connections. 
      
      The availableBitRate service is an ATM layer service category for 
      which the limiting ATM layer transfer characteristics provided by 
      the network may change subsequent to connection establishment. 
      ABR service has a flow control mechanism which supports several 
      types of feedback to control the source rate in response to changing 
      ATM layer transfer characteristics. ABR service is not intended to 
      support real-time applications. 
      
      The unspecifiedBitRate service is intended for non-real time 
      applications; that is, those not requiring tightly constrained delay 
      and delay variation. UBR sources are expected to be bursty. UBR 
      service supports a high degree of statistical multiplexing among 
      sources. UBR service does not specify traffic related service 
      guarantees. No numerical commitments are made with respect to 
      the cell loss ratio experienced by a UBR connection, or as to the 
      cell transfer delay experienced by cells on the connection."
   DEFVAL     { unspecifiedBitRate }
::= { atmIfVccVcdTmProvEntry 42 }

atmIfVccVcdTmTrafficShaping OBJECT-TYPE
   SYNTAX     INTEGER  {
                 disabled(1),
                 sameAsCa(2) }
   ACCESS     read-write
   STATUS     mandatory
   DESCRIPTION
     "This attribute specifies whether this connection uses traffic shaping 
      when transmitting traffic to the ATM interface.
      
      This attribute is ignored if the atmServiceCategory is 
      availableBitRate.
      
      When sameAsCa is selected, traffic shaping for the connection is 
      based on the trafficShaping attribute of the connection's service 
      category component under the CA. If the service category has 
      trafficShaping set to enabled or inverseUpc, then traffic shaping is 
      enabled for the connection. Note that enabling traffic shaping may 
      have no effect under certain cases. These cases are listed in the 
      description of the trafficShaping operational attribute, which is 
      under the Vcc Tm, Vpc Tm, or Vpt Tm components.
      
      When disabled is selected, traffic shaping for this connection is 
      disabled regardless of the provisioning of the connection's service 
      category component."
   DEFVAL     { sameAsCa }
::= { atmIfVccVcdTmProvEntry 50 }

atmIfVccVcdTmUnshapedTransmitQueueing OBJECT-TYPE
   SYNTAX     INTEGER  {
                 common(1),
                 sameAsCa(3) }
   ACCESS     read-write
   STATUS     mandatory
   DESCRIPTION
     "This attribute only applies when this connection is unshaped. This 
      attribute specifies the transmit queueing method for this connection 
      if it is unshaped. The two possible methods are per-VC queuing and 
      common queuing. 
      
      On ATM IP FPs, this attribute must be set to sameAsCa. 
      
      This attribute is ignored in the following situations:
      - if the connection has trafficShaping enabled or inverseUpc, or 
      - if the atmServiceCategory is availableBitRate, or
      - if the atmServiceCategory is constantBitRate and this is a CQC-
      based ATM FP.
      - for basic Vpts and standard Vpt Vccs
      
      When this attribute is set to sameAsCa, the transmit queueing 
      method for the connection is based on the 
      unshapedTransmitQueueing attribute of the connection's service 
      category component under the CA. 
      
      When this attribute is set to common, transmit traffic on this 
      unshaped connection is destined for the common queue."
   DEFVAL     { sameAsCa }
::= { atmIfVccVcdTmProvEntry 60 }

atmIfVccVcdTmWeight OBJECT-TYPE
   SYNTAX     Unsigned32 (0 | 1..4095 | 65535)
   ACCESS     read-write
   STATUS     mandatory
   DESCRIPTION
     "This attribute specifies an override for the weight of this unshaped 
      connection. This attribute is ignored for shaped connections, for 
      ABR connections, for connections on a CQC-based ATM FP, and 
      basic Vpts. 
      
      When the value is set to sameAsCa, the weight is determined by the 
      fairnessWeight attribute under the CA service category component 
      for all but standard Vpt Vccs. For standard Vpt Vccs, the weight is 
      determined by the Vcc's service category, when the value is set to 
      sameAsCa.
      
      When this attribute is set to a value from 1 to 4095, that value is 
      used for the fairness weight of this connection relative to other 
      connections. For all but standard Vpt Vccs, fairness weight 
      determines the proportion of transmit cell opportunities which are 
      allocated to this connection, compared to other connections in the 
      same service category. For standard Vpt Vccs, fairness weight 
      determines the proportion of transmit cell opportunities which are 
      allocated to this connection, compared to other connections 
      associated with the Vpt.
      
      When the value is set to upToQueueLimit, the fairness weight is 
      limited only by the txQueueLimit.

      VALUES (

      0 = upToQueueLimit

      65535 = sameAsCa

      )"
   DEFVAL     { 65535 }
::= { atmIfVccVcdTmProvEntry 61 }

atmIfVccVcdTmForceTagging OBJECT-TYPE
   SYNTAX     INTEGER  {
                 enabled(0),
                 disabled(1),
                 sameAsCa(2) }
   ACCESS     read-write
   STATUS     mandatory
   DESCRIPTION
     "This attribute specifies whether force tagging is enforced for this 
      connection for cells in the transmit direction. 
      
      On CQC-based ATM cards, and for Vpts, this attribute is not 
      applicable and is ignored. 
      
      When the value is set to sameAsCa, the force tagging functionality 
      is determined by the forceTagging attribute under the CA service 
      category component. 
      
      When the value is set to enabled, force tagging is enabled for cells 
      in the transmit direction on this connection. When this option is 
      selected, the CLP bit is set to 1 for all cells in the transmit direction. 
      Cells which are tagged are counted in the txCellClp attribute. 
      
      When the value is set to disabled, force tagging is disabled for cells 
      in the transmit direction on this connection. When this option is 
      selected, the CLP bit is unchanged for cells in the transmit 
      direction."
   DEFVAL     { sameAsCa }
::= { atmIfVccVcdTmProvEntry 62 }

atmIfVccVcdTmUsageParameterControl OBJECT-TYPE
   SYNTAX     INTEGER  {
                 enforced(0),
                 disabled(1),
                 sameAsCa(2),
                 monitored(4) }
   ACCESS     read-write
   STATUS     mandatory
   DESCRIPTION
     "This attribute specifies whether this connection enforces usage 
      parameter control when receiving traffic from the ATM interface.
      
      When sameAsCa is selected, UPC for the connection is based on 
      the usageParameterControl attribute of the service category 
      component under the AtmIf CA. If the service category has UPC 
      enforced or monitored, then UPC is set to that value for the 
      connection. 
      
      When disabled is selected, UPC for this connection is disabled 
      regardless of the provisioning of the service category. 
      
      When enforced is selected, UPC for this connection is enforced 
      regardless of the provisioning of the service category. 
      
      ATM IP cards provide the ability to monitor UPC violations without 
      tagging or discarding. When monitored is selected, UPC is actively 
      checking conformance for the connection and counting the 
      violations, but is not discarding or tagging cells which do not 
      conform to the connection traffic contract. 
      
      If this is a connection of serviceCategory abr on an ATM IP card, 
      and the abrConnectionType is sourceDest, virtualSourceDest or 
      explicitRate, selecting enforced enables dynamic generic cell rate 
      algorithm (DGCRA) to discard violating cells. Selecting monitored 
      enables DGCRA to count violating cells. 
      
      Note that setting UPC to enforced or monitored may have no effect 
      under certain cases. These cases are listed in the description of the 
      usageParameterControl operational attribute, which is under the 
      Vcc, Vpc, and Vpt components."
   DEFVAL     { sameAsCa }
::= { atmIfVccVcdTmProvEntry 70 }

atmIfVccVcdTmBearerClassBbc OBJECT-TYPE
   SYNTAX     INTEGER  {
                 a(1),
                 c(3),
                 x(16),
                 vp(24),
                 derivedFromServiceCategory(31) }
   ACCESS     read-write
   STATUS     mandatory
   DESCRIPTION
     "This attribute specifies the bearer capability. This attribute is only 
      used for SPVC and SPVP connections. It is one of the Broadband 
      Bearer Capability (BBC) attributes. The purpose of the BBC 
      information element is to indicate a requested broadband 
      connection-oriented bearer service to be provided by the network.
      
      The value derivedFromServiceCategory specifies that the actual 
      value which is used for this connection is derived from the value of 
      the atmServiceCategory. Either, this attribute must be set to 
      derivedFromServiceCategory, or the atmServiceCategory attribute 
      must be set to derivedFromBBC, but not both.
      
      Class a service is a connection-oriented, constant bit rate ATM 
      transport service. Class a service has end to end timing 
      requirements and may require stringent cell loss, cell delay and cell 
      delay variation performance.When a is set, the user is requesting 
      more than an ATM only service. The network may look at the AAL 
      to provide interworking based upon its contents. 
      
      Class c service is a connection-oriented, variable bit rate ATM 
      transport service. Class c service has no end-to-end timing 
      requirements. When c is set, the user is requesting more than an 
      ATM only service. The network interworking function may look at 
      the AAL and provide service based on it.
      
      Class x service is a connection-oriented ATM transport service 
      where the AAL, trafficType (vbr or cbr) and timing requirements 
      are user defined (that is, transparent to the network).When x is set 
      the user is requesting an ATM only service from the network. In this 
      case, the network shall not process any higher layer protocol.
      
      Class vp service is used to specify a transparent VP service. When 
      the value of this attribute is vp, the user is requesting an ATM only 
      service from the network. In this case, the network shall not process 
      any higher layer protocol. This service differs from class x service 
      in that with the class vp service both the VCI field (except or VCI 
      values 0, 3, 4, and 6 through 15) and Payload Type field are 
      transported transparently by the network. This attribute value is 
      only applicable to SPVP connections."
   DEFVAL     { derivedFromServiceCategory }
::= { atmIfVccVcdTmProvEntry 71 }

atmIfVccVcdTmTransferCapabilityBbc OBJECT-TYPE
   SYNTAX     INTEGER  {
                 n0(0),
                 n1(1),
                 n2(2),
                 n5(5),
                 n8(8),
                 n9(9),
                 n10(10),
                 notApplicable(30),
                 derivedFromServiceCategory(31) }
   ACCESS     read-write
   STATUS     mandatory
   DESCRIPTION
     "This attribute specifies the transfer capability for this connection. 
      Uni 3.0/3.1 traffic type and end-to-end timing parameters are 
      mapped into this parameter as follows:
      <transferCapability: TrafficType, Timing>
      0: NoIndication, NoIndication
      1: NoIndication, yes
      2: NoIndication, no
      5: CBR, yes
      8: VBR, NoIndication
      9: VBR, yes
      10: VBR, no
      
      notApplicable specifies that the user does not want to specify the 
      transfer capability.
      
      The CBR traffic type refers to traffic offered on services such as a 
      constant bit rate video service or a circuit emulation.
      The VBR traffic type refers to traffic offered on services such as 
      packetized audio and video, or data.
      
      The value no indication for traffic type is used if the user has not set 
      the traffic type; similarly for end-to-end timing.
      
      The value yes for end-to-end timing indicates that end-to-end 
      timing is required.
      
      The value no for end-to-end timing indicates that end-to-end timing 
      is not required.
      
      The value derivedFromServiceCategory specifies that the actual 
      value which is used for this connection is derived from the value of 
      the atmServiceCategory. Either, this attribute must be set to 
      derivedFromServiceCategory, or the atmServiceCategory attribute 
      must be set to derivedFromBBC, but not both."
   DEFVAL     { derivedFromServiceCategory }
::= { atmIfVccVcdTmProvEntry 72 }

atmIfVccVcdTmTxWredThreshold OBJECT-TYPE
   SYNTAX     Unsigned32 (25 | 50 | 75)
   ACCESS     read-write
   STATUS     mandatory
   DESCRIPTION
     "This attribute determines at what percentage of the queue being at 
      the EPD threshold, WRED starts. When the value is set to 25%, 
      WRED starts as soon as the queue is 25% of the way to the EPD 
      threshold. When the value is set to 50%, WRED starts later, after 
      the queue is 50% of the way to the EPD threshold. When the value 
      is set to 75%, WRED starts only when the queue is 75% of the way 
      to the EPD threshold. The EPD threshold is 85% of the transmit 
      queue length.
      
      This attribue is ignored if txWredMode or txPacketWiseDiscard is 
      disabled. It is always ignored on CQC-based ATM FP."
   DEFVAL     { 25 }
::= { atmIfVccVcdTmProvEntry 73 }

atmIfVccVcdTmClippingBbc OBJECT-TYPE
   SYNTAX     INTEGER  {
                 no(0),
                 yes(1) }
   ACCESS     read-write
   STATUS     mandatory
   DESCRIPTION
     "This attribute specifies the value for the clipping susceptibility 
      parameter in the BBC Information Element. This attribute is only 
      used for SPVC connections. It is one of the Broadband Bearer 
      Capability attributes.
      
      Clipping is an impairment in which the first fraction of a second of 
      information to be transferred is lost. It occurs after a call is 
      answered and before an associated connection is switched through."
   DEFVAL     { no }
::= { atmIfVccVcdTmProvEntry 74 }

atmIfVccVcdTmBestEffort OBJECT-TYPE
   SYNTAX     INTEGER  {
                 indicated(0),
                 notIndicated(1),
                 derivedFromServiceCategory(15) }
   ACCESS     read-write
   STATUS     mandatory
   DESCRIPTION
     "This attribute specifies the value of the best effort parameter in the 
      ATM Traffic Descriptor Information Element. This attribute is only 
      used for Soft PVC connections. It is one of the Broadband Bearer 
      Capability attributes.
      
      The value indicated implies that the quality of service for this 
      connection is not guaranteed.
      
      The value notIndicated implies that the quality of service for this 
      connection is guaranteed.
      
      The value derivedFromServiceCategory specifies that the actual 
      value which is used for this connection is derived from the value of 
      the atmServiceCategory. Either, this attribute must be set to 
      derivedFromServiceCategory, or the atmServiceCategory attribute 
      must be set to derivedFromBBC, but not both."
   DEFVAL     { derivedFromServiceCategory }
::= { atmIfVccVcdTmProvEntry 75 }

atmIfVccVcdTmTxPacketWiseDiscard OBJECT-TYPE
   SYNTAX     INTEGER  {
                 disabled(0),
                 enabled(1) }
   ACCESS     read-write
   STATUS     mandatory
   DESCRIPTION
     "This attribute specifies whether packet-wise discard functions are to 
      be enabled or disabled in the transmit data direction for this 
      connection. Packet-wise discard functions should only be requested 
      if this connection is transferring AAL5 frame traffic. This attribute 
      is not applicable for Vpts.
      
      Packet-wise functions increase the 'goodput' of the link. The 
      transmit packet-wise functions are Early Packet Discard (EPD) and 
      Partial Packet Discard (PPD). 
      
      EPD allows the connection to discard an entire frame once the 
      transmit queue has reached the EPD threshold. EPD increases the 
      'goodput' of a link, since discarding an entire frame means that 
      some queue capacity is guarded for some other frame which is 
      already partially transmitted. All cells of the frame are discarded 
      from the Beginning of Message (BOM) cell up to and including the 
      End of Message (EOM) cell. 
      
      PPD allows the connection to discard the remainder of a cell-
      forwarded AAL5 frame if one cell of this frame has been discarded. 
      All cells are discarded up to but not including the EOM cell. The 
      PPD function increases the 'goodput' of the link, since cells which 
      are only going to be discarded at the AAL5 reassembly point are 
      not transmitted.
      
      On CQC-based ATM cards, the packet-wise discard functions are 
      PPD and EPD. PPD is available at VCC cell-transfer points. PPD is 
      not applicable at frame-cell conversion points, and is not applicable 
      for Vpcs. PPD is configured by this attribute. Packet-wise discard 
      should only be enabled for connections carrying AAL5 
      segmentation traffic. Setting the value to enabled for any other 
      traffic type may result in all traffic being discarded. On CQC-based 
      ATM FPs, EPD is automatically enabled at frame-to-cell conversion 
      points, independent of the setting of this attribute. 
      
      On ATM IP cards, packet-wise discard functions include EPD and 
      PPD. PPD and EPD apply to individual VCCs and VCCs within 
      VPCs at all connection points, including tandem VPC connections. 
      Both PPD and EPD are controlled by this attribute. This attribute 
      may safely be set to enabled for any connection (Vcc or Vpc) on 
      ATM IP FPs since they have the ability to automatically detect 
      AAL5-segmented traffic on a connection, and only enable packet-
      wise discards if AAL5-segmented traffic is detected.
      
      When this attribute is set to enabled, packet-wise discard functions 
      are applied to transmit traffic at this connection point. When this 
      attribute is set to disabled, packet-wise discard functions are not 
      applied to transmit traffic at this connection point.
      
      At a SPVC origin on a PNNI interface, a value of enabled specifies 
      that frame discard is requested in the backward direction. When this 
      attribute is set to disabled, backward frame discard is not requested 
      in the SPVC call setup. 
      
      The transmit packet-wise discard functions that are active are 
      visible in the Vcc/Vpc Tm txPacketWiseDiscard operational 
      attribute."
   DEFVAL     { disabled }
::= { atmIfVccVcdTmProvEntry 76 }

atmIfVccVcdTmTxWredMode OBJECT-TYPE
   SYNTAX     INTEGER  {
                 disabled(0),
                 enabled(1),
                 perFlow(2) }
   ACCESS     read-write
   STATUS     mandatory
   DESCRIPTION
     "This attribute specifies the activation of weighted random early 
      detection (WRED) functionality. WRED is only available on ATM 
      IP FPs. On CQC-based ATM FPs, this attribute is ignored. If 
      txPacketWiseDiscard is set to disabled this attribute is ignored. This 
      attribute is not applicable for Vpts or Vpt Vccs.
      
      WRED is applied in the transmit direction for this connection. 
      WRED function should be enabled only for connections which are 
      transferring TCP/IP traffic. WRED acts to prevent synchronization 
      of multiple TCP/IP sources by randomly discarding a small 
      percentage of frames when transmit queue congestion reaches the 
      designated level. W-RED may also be used to differentiate service 
      on VCC's by preferentially discarding one VCC before another. 
      Discards start at 0% of cells, when the queue is part-way to the 
      Early Packet Discard (EPD) threshold, and rise to 100% of cells 
      discarded at the EPD threshold. WRED discards all the cells in a 
      frame. 
      
      If this attribute is set to enabled, WRED is enabled for all 
      applications linked to the given Vcc. If it is set to perFlow, each 
      TCP application has individual control over whether to enable or 
      disable WRED
      
      If txPacketWiseDiscard is set to disabled, or if this attribute is set to 
      disabled, WRED functionality is disabled. 
      
      If WRED is active, it is visible in the Vcc/Vpc Tm 
      txPacketWiseDiscard operational attribute."
   DEFVAL     { disabled }
::= { atmIfVccVcdTmProvEntry 77 }

atmIfVccVcdTmRxPacketWiseDiscard OBJECT-TYPE
   SYNTAX     INTEGER  {
                 disabled(0),
                 enabled(1) }
   ACCESS     read-write
   STATUS     mandatory
   DESCRIPTION
     "This attribute specifies whether packet-wise discard functions are to 
      be enabled or disabled in the receive data direction for this 
      connection. Packet-wise discard functions should only be requested 
      if this connection is transferring AAL5 frame traffic. This attribute 
      is not applicable for Vpts.
      
      Packet-wise functions increase the 'goodput' of the link. The 
      receive packet-wise function is Partial Packet Discard (PPD). 
      
      PPD allows the connection to discard the remainder of a cell-
      forwarded AAL5 frame if one cell of this frame has been discarded, 
      for example due to UPC. All cells are discarded up to but not 
      including the EOM cell. The PPD function increases the 'goodput' 
      of the link, since cells which are only going to be discarded at the 
      AAL5 reassembly point are not transmitted.
      
      PPD is available at all VCC connection points where UPC may be 
      activated. PPD is not applicable for Vpcs. 
      
      On CQC-based ATM FPs, packet-wise discards should only be 
      enabled for connections carrying AAL5 segmentation traffic. 
      Setting the value to enabled for any other traffic type may result in 
      traffic being discarded. 
      
      On ATM IP cards, this attribute may safely be set to enabled for any 
      connection (Vcc or Vpc) since they have the ability to automatically 
      detect AAL5-segmented traffic on a connection, and only enables 
      packet-wise discards if AAL5-segmented traffic is detected.
      
      When this attribute is set to enabled, packet-wise discard functions 
      are applied to receive traffic at this connection point. When this 
      attribute is set to disabled, packet-wise discard functions are not 
      applied to receive traffic at this connection point.
      
      At a SPVC origin on a PNNI interface, a value of enabled specifies 
      that frame discard is requested in the forward direction. When this 
      attribute is set to disabled, forward frame discard is not requested in 
      the SPVC call setup. 
      
      The receive packet-wise discard functions that are active are visible 
      in the Vcc/Vpc Tm rxPacketWiseDiscard operational attribute."
   DEFVAL     { disabled }
::= { atmIfVccVcdTmProvEntry 78 }

atmIfVccVcdTmAbrConnectionType OBJECT-TYPE
   SYNTAX     INTEGER  {
                 abrSwitch(0),
                 virtualSourceDest(3),
                 sourceDest(4),
                 nonAbrInterworking(5),
                 sameAsCa(14) }
   ACCESS     read-write
   STATUS     mandatory
   DESCRIPTION
     "This attribute specifies the type of ABR behavior which is to be 
      enforced at this connection. This attribute is only applicable if the 
      atmServiceCategory attribute is availableBitRate. If the 
      atmServicecategory attribute is not availableBitRate, this attribute 
      value is ignored.
      
      The actual ABR functionality which is in effect is visible in the 
      Vcc/Vpc/Vpt Tm abrConnectionType operational attribute.
      
      For CQC-based ATM cards, the only allowable values are 
      sameAsCa, nonAbrInterworking or abrSwitch. If abrSwitch is 
      selected, the CQC implements EFCI marking behavior.
      
      sameAsCa is used to request the default behavior as specified in the 
      CA Abr component for this Vcc. Otherwise, this attribute overrides 
      the default behavior. 
      
      virtualSourceDest is used to request that this connection point 
      function as a virtual source/virtual destination. VS/VD functionality 
      is only supported on ATM IP FPs.
      
      sourceDest requires that this connection point function as a S/D for 
      RM cells. S/D mode is automatically invoked at this connection 
      point either if this is a connection end point, or if the next hop 
      connection point is configured as nonAbrInterworking.
      
      nonAbrInterworking is used to request that this connection point 
      function as an interworking between ABR and non-ABR service 
      categories. This means that there are no RM cells on the link side of 
      this connection, and that the next hop connection point is 
      performing as an ABR sourceDest.
      
      abrSwitch is used to request ABR switch behavior for this 
      connection point. The ABR switch behavior is first, to confirm to 
      virtualSourceDest or nonAbrInterworking setting on the next hop, 
      and otherwise to implement ABR ER switch behavior. For CQC-
      based FPs, ABR switch behavior is implemented as EFCI marking."
   DEFVAL     { sameAsCa }
::= { atmIfVccVcdTmProvEntry 90 }

atmIfVccVcdTmTxTdpTable OBJECT-TYPE
   SYNTAX     SEQUENCE OF AtmIfVccVcdTmTxTdpEntry
   ACCESS     not-accessible
   STATUS     mandatory
   DESCRIPTION
     "This attribute is a vector of five traffic parameters whose meanings 
      are defined by the txTrafficDescType attribute. 
      
      The values of peak cell rate (PCR), sustained cell rate (SCR), 
      Minimum Cell Rate (MCR) and requested shaping rate are 
      expressed in cell/s. Maximum burst size (MBS) is expressed in 
      cells. CDVT is expressed in microseconds. The values of PCR, 
      SCR, MCR, MBS and CDVT are used for connection admission 
      control (CAC). The value of CDVT is only used for connections 
      where the atmServiceCategory is constantBitRate. For all other 
      values of atmServiceCategory, CDVT is ignored. The values of 
      PCR, SCR, MCR and requested shaping rate are used to determine 
      the actual shaping rate where traffic shaping is enabled.
      
      When txTrafficDescType is 1 or 2, all of the parameters must be set 
      to zero.
      
      When txTrafficDescType is 3, parameter 1 represents the PCR for 
      CLP equal to 0 and 1 traffic; parameter 4 represents the CDVT; and 
      parameter 5 represents the requested shaping rate. A non-zero value 
      in parameter 5 overrides any value in parameter 1. This result is 
      used as the PCR. Parameter 1 must be non-zero. Parameters 2 and 3 
      must be zero.
      
      When txTrafficDescType is 4, parameter 1 represents the PCR for 
      CLP equal to 0 and 1 traffic with cell discard; parameter 2 
      represents the PCR for CLP equal to 0 traffic; parameter 4 
      represents the CDVT; and parameter 5 represents the requested 
      shaping rate. A non-zero value in parameter 5 overrides any value in 
      parameter 1. This result is used as the PCR. Parameter 1 must be 
      greater than or equal to parameter 2. Parameters 1 and 2 must be 
      non-zero. Parameter 3 must be zero.
      
      When txTrafficDescType is 5, parameter 1 represents the PCR for 
      CLP equal to 0 and 1 traffic with cell tagging; parameter 2 
      represents the PCR for CLP equal to 0 traffic; parameter 4 
      represents the CDVT; and parameter 5 represents the requested 
      shaping rate. A non-zero value in parameter 5 overrides any value in 
      parameter 1. This result is used as the PCR. Parameter 1 must be 
      greater than or equal to parameter 2. Parameters 1 and 2 must be 
      non-zero. Parameter 3 must be zero.
      
      When txTrafficDescType is 6, parameter 1 represents the PCR for 
      CLP equal to 0 and 1 traffic; parameter 2 represents the SCR for 
      CLP equal to 0 and 1 traffic; parameter 3 represents the MBS for 
      CLP equal to 0 and 1 traffic; parameter 4 represents the CDVT; and 
      parameter 5 represents the requested shaping rate. A non-zero value 
      in parameter 5 overrides any value in parameter 1. This result is 
      used as the PCR. Parameters 1, 2 and 3 must be non-zero. 
      Parameter 1 must be greater than or equal to parameter 2. Parameter 
      5, must either be zero (unused) or greater than or equal to parameter 
      2.
      
      When txTrafficDescType is 7, parameter 1 represents the PCR for 
      CLP equal to 0 and 1 traffic; parameter 2 represents the SCR for 
      CLP equal to 0 with cell discard; parameter 3 represents the MBS 
      for CLP equal to 0 traffic; parameter 4 represents the CDVT; and 
      parameter 5 represents the requested shaping rate. A non-zero value 
      in parameter 5 overrides any value in parameter 1. This result is 
      used as the PCR. Parameters 1, 2 and 3 must be non-zero. 
      Parameter 1 must be greater than or equal to parameter 2. Parameter 
      5, must either be zero (unused) or greater than or equal to parameter 
      2.
      
      When txTrafficDescType is 8, parameter 1 represents the PCR for 
      CLP equal to 0 and 1 traffic; parameter 2 represents the SCR for 
      CLP equal to 0 traffic with cell tagging; parameter 3 represents the 
      MBS for CLP equal to 0 traffic; parameter 4 represents the CDVT; 
      and parameter 5 represents the requested shaping rate. A non-zero 
      value in parameter 5 overrides any value in parameter 1. This result 
      is used as the PCR. Parameters 1, 2 and 3 must be non-zero. 
      Parameter 1 must be greater than or equal to parameter 2. Parameter 
      5, must either be zero (unused) or greater than or equal to parameter 
      2.
      
      When txTrafficDescType is 9, parameter 1 represents the PCR; 
      parameter 2 represents the CDVT; parameter 3 represents the MCR; 
      parameter 4 and parameter 5 represent are not used and must be 
      zero. Parameter 1 must be non-zero and must be greater than or 
      equal to parameter 3. Parameter 3 may be optionally zero.
      
      Whenever it is valid for PCR to be specified, parameter 5 may also 
      be used to specify a requested shaping rate. A non-zero value in 
      parameter 5 overrides the value in parameter 1 and is used as the 
      peak cell rate in calculations of CAC and shaping rate. When the 
      atmServiceCategory is availableBitRate (ABR), the shaping rate is 
      dynamically chosen, based on the ABR flow control mechanism, as 
      a value between the MCR and the PCR or the requested shaping 
      rate if applicable.
      
      For txTrafficDescType 3, 4 and 5, the transmit traffic is shaped at 
      the next available shaping rate less than the PCR. 
      
      For txTrafficDescType 6, 7 and 8 if linear traffic shaping is selected, 
      the transmit traffic is shaped at the highest available rate which is 
      between PCR and SCR. However, if there is no available shaping 
      rate between PCR and SCR, traffic is shaped at the next rate above 
      the PCR. 
      
      For txTrafficDescType 6, 7 and 8 if inverse-UPC traffic shaping is 
      selected, the transmit traffic is shaped at a variable rate which 
      conforms to the PCR, SCR and MBS of the connection traffic 
      descriptor. Inverse-UPC traffic shaping is available only on ATM IP 
      cards."
::= { atmIfVccVcdTm 456 }

atmIfVccVcdTmTxTdpEntry OBJECT-TYPE
   SYNTAX     AtmIfVccVcdTmTxTdpEntry
   ACCESS     not-accessible
   STATUS     mandatory
   DESCRIPTION
     "An entry in the atmIfVccVcdTmTxTdpTable."
   INDEX {
      atmIfIndex,
      atmIfVccIndex,
      atmIfVccVcdIndex,
      atmIfVccVcdTmIndex,
      atmIfVccVcdTmTxTdpIndex }
::= { atmIfVccVcdTmTxTdpTable 1 }

AtmIfVccVcdTmTxTdpEntry ::= SEQUENCE {
   atmIfVccVcdTmTxTdpIndex
      Integer32,
   atmIfVccVcdTmTxTdpValue
      Unsigned32 }

atmIfVccVcdTmTxTdpIndex OBJECT-TYPE
   SYNTAX     Integer32 (1..5)
   ACCESS     not-accessible
   STATUS     mandatory
   DESCRIPTION
     "This variable represents the atmIfVccVcdTmTxTdpTable
      specific index for the atmIfVccVcdTmTxTdpTable."
::= { atmIfVccVcdTmTxTdpEntry 1 }

atmIfVccVcdTmTxTdpValue OBJECT-TYPE
   SYNTAX     Unsigned32 (0..2147483647)
   ACCESS     read-write
   STATUS     mandatory
   DESCRIPTION
     "This variable represents an individual value for the
      atmIfVccVcdTmTxTdpTable."
::= { atmIfVccVcdTmTxTdpEntry 2 }

atmIfVccVcdTmRxTdpTable OBJECT-TYPE
   SYNTAX     SEQUENCE OF AtmIfVccVcdTmRxTdpEntry
   ACCESS     not-accessible
   STATUS     mandatory
   DESCRIPTION
     "This attribute is a vector of four traffic parameters whose meanings 
      are defined by the rxTrafficDescType attribute. The values of peak 
      cell rate (PCR), sustained cell rate (SCR) and Minimum Cell Rate 
      (MCR) are expressed in cell/s. Maximum burst size (MBS) is 
      expressed in cells. The value of CDVT is expressed in 
      microseconds. The values of PCR, SCR, MCR, MBS and CDVT 
      are used for usage parameter control (UPC).
      
      When rxTrafficDescType is 1 or 2, all of the parameters must be set 
      to zero (unused).
      
      When rxTrafficDescType is 3, parameter 1 represents the PCR for 
      CLP equal to 0 and 1 traffic. Parameter 1 must be non-zero. 
      Parameters 2 and 3 must be set to zero (unused).
      
      When rxTrafficDescType is 4, parameter 1 represents the PCR 
      for CLP equal to 0 and 1 traffic; parameter 2 represents the PCR for 
      CLP equal to 0 traffic with cell discard. Parameters 1 and 2 must be 
      non-zero. Parameter 3 must be set to zero (unused). Parameter 1 
      must be greater than or equal to parameter 2.
      
      When rxTrafficDescType is 5, parameter 1 represents the PCR for 
      CLP equal to 0 and 1 traffic; parameter 2 represents the PCR for 
      CLP equal to 0 traffic with cell tagging. Parameters 1 and 2 must be 
      non-zero. Parameter 3 must be set to zero (unused). Parameter 1 
      must be greater than or equal to parameter 2.
      
      When rxTrafficDescType is a 6, parameter 1 represents the PCR for 
      CLP equal to 0 and 1 traffic; parameter 2 represents the SCR for 
      CLP equal to 0 and 1 traffic; parameter 3 represents the MBS for 
      CLP equal to 0 and 1 traffic. Parameters 1, 2 and 3 must be non-
      zero. Parameter 1 must be greater than or equal to Parameter 2. 
      
      When rxTrafficDescType is 7, parameter 1 represents the PCR for 
      CLP equal to 0 and 1 traffic; parameter 2 represents the SCR for 
      CLP equal to 0 traffic with cell discard; parameter 3 represents the 
      MBS for CLP equal to 0 traffic. Parameters 1, 2 and 3 must be non-
      zero. Parameter 1 must be greater than or equal to parameter 2. 
      
      When rxTrafficDescType is 8, parameter 1 represents the PCR for 
      CLP equal to 0 and 1 traffic; parameter 2 represents the SCR for 
      CLP equal to 0 traffic with cell tagging; parameter 3 represents the 
      MBS for CLP equal to 0 traffic. Parameter 1, 2 and 3 must be non-
      zero. Parameter 1 must be greater than or equal to parameter 2.
      
      When rxTrafficDescType is 9, parameter 1 represents the PCR; 
      parameter 2 represents the CDVT; parameter 3 represents the MCR. 
      Parameter 4 is not used and must be zero. Parameter 1,must be non-
      zero and must be greater than or equal to parameter 3. Parameter 3 
      may optionally be zero.
      
      When rxTrafficDescType is any value from 3 through 8, parameter 
      4 represents the CDVT. 
      
      If the value of CDVT either in parameter 2 or in parameter 4 is zero, 
      the CDVT is taken from the CA defaults for the particular 
      atmServiceCategory of this connection.
      
      On a CQC-based ATM card, when rxTrafficDescriptorType is 3 
      through 8, there are certain extreme combinations of 
      rxTrafficDescParm which are outside the capabilities of the UPC 
      hardware. The check prov command detects such cases and 
      generates an error message. If this happens, adjust the parameters 
      until they fall within the supported limits. 
      
      To calculate the limits, use the following formulae:
      I1 = 1 000 000 000 / PCR
      L1 = CDVT * 1000
      I2 = 1,000,000,000 / SCR
      L2 = CDVT + (MBS - 1) * (I2 - I1)
      I1 and I2 must be less than or equal to 335,523,840. I1 + L1 must 
      be less than or equal to 1,342,156,800. I2 + L2 must be less than or 
      equal to 1,342,156,800. Note that I2 and L2 only apply when the 
      rxTrafficDescriptorType is 6 through 8.
      
      If the values of I1, L1, I2 or L2 are closer to the limits described 
      above, a further restriction applies. Specifically, if either:
      I1 > 41,940,480 or
      I2 > 41,940,480 or
      I1 + L1 > 167,769,600 or
      I2 + L2 > 167,769,600
      then both I1 and I2 must be greater than 20,480. 
      
      Parameter 5 of the rxTrafficDescParm is always unused. 
      
      If the rxTrafficDescType is sameAsTx, the values provisioned in 
      this attribute are ignored. The traffic parameters for the receive 
      direction are taken from the txTrafficDescParm."
::= { atmIfVccVcdTm 457 }

atmIfVccVcdTmRxTdpEntry OBJECT-TYPE
   SYNTAX     AtmIfVccVcdTmRxTdpEntry
   ACCESS     not-accessible
   STATUS     mandatory
   DESCRIPTION
     "An entry in the atmIfVccVcdTmRxTdpTable."
   INDEX {
      atmIfIndex,
      atmIfVccIndex,
      atmIfVccVcdIndex,
      atmIfVccVcdTmIndex,
      atmIfVccVcdTmRxTdpIndex }
::= { atmIfVccVcdTmRxTdpTable 1 }

AtmIfVccVcdTmRxTdpEntry ::= SEQUENCE {
   atmIfVccVcdTmRxTdpIndex
      Integer32,
   atmIfVccVcdTmRxTdpValue
      Unsigned32 }

atmIfVccVcdTmRxTdpIndex OBJECT-TYPE
   SYNTAX     Integer32 (1..5)
   ACCESS     not-accessible
   STATUS     mandatory
   DESCRIPTION
     "This variable represents the atmIfVccVcdTmRxTdpTable
      specific index for the atmIfVccVcdTmRxTdpTable."
::= { atmIfVccVcdTmRxTdpEntry 1 }

atmIfVccVcdTmRxTdpValue OBJECT-TYPE
   SYNTAX     Unsigned32 (0..2147483647)
   ACCESS     read-write
   STATUS     mandatory
   DESCRIPTION
     "This variable represents an individual value for the
      atmIfVccVcdTmRxTdpTable."
::= { atmIfVccVcdTmRxTdpEntry 2 }

atmIfVccVcdTmFqpTable OBJECT-TYPE
   SYNTAX     SEQUENCE OF AtmIfVccVcdTmFqpEntry
   ACCESS     not-accessible
   STATUS     mandatory
   DESCRIPTION
     "This attribute is a vector of three elements that specify the quality of 
      service parameters for the forward direction for this connection. 
      This attribute is used for SPVC connections.
      
      The cdv element specifies the acceptable peak-to-peak Cell Delay 
      Variation (CDV) of real-time connections (CBR and rt-VBR). It is 
      signalled through the extended QoS information element.
      
      The ctd specifies the acceptable maximum Cell Transfer Delay 
      (maxCtd) of real-time connections (CBR and rt-VBR). 
      It is signalled through the end to end transit delay information 
      element.
      
      The clr specifies the acceptable Cell Loss Ratio (CLR) of CBR, rt-
      VBR, and nrt-VBR connections. It is signalled through the extended 
      QoS information element."
::= { atmIfVccVcdTm 458 }

atmIfVccVcdTmFqpEntry OBJECT-TYPE
   SYNTAX     AtmIfVccVcdTmFqpEntry
   ACCESS     not-accessible
   STATUS     mandatory
   DESCRIPTION
     "An entry in the atmIfVccVcdTmFqpTable."
   INDEX {
      atmIfIndex,
      atmIfVccIndex,
      atmIfVccVcdIndex,
      atmIfVccVcdTmIndex,
      atmIfVccVcdTmFqpIndex }
::= { atmIfVccVcdTmFqpTable 1 }

AtmIfVccVcdTmFqpEntry ::= SEQUENCE {
   atmIfVccVcdTmFqpIndex
      INTEGER,
   atmIfVccVcdTmFqpValue
      Unsigned32 }

atmIfVccVcdTmFqpIndex OBJECT-TYPE
   SYNTAX     INTEGER  {
                 cdv(0),
                 ctd(1),
                 clr(2) }
   ACCESS     not-accessible
   STATUS     mandatory
   DESCRIPTION
     "This variable represents the atmIfVccVcdTmFqpTable
      specific index for the atmIfVccVcdTmFqpTable."
::= { atmIfVccVcdTmFqpEntry 1 }

atmIfVccVcdTmFqpValue OBJECT-TYPE
   SYNTAX     Unsigned32 (0..16777215)
   ACCESS     read-write
   STATUS     mandatory
   DESCRIPTION
     "This variable represents an individual value for the
      atmIfVccVcdTmFqpTable."
::= { atmIfVccVcdTmFqpEntry 2 }

atmIfVccVcdTmBqpTable OBJECT-TYPE
   SYNTAX     SEQUENCE OF AtmIfVccVcdTmBqpEntry
   ACCESS     not-accessible
   STATUS     mandatory
   DESCRIPTION
     "This attribute is a vector of two elements that specify the quality of 
      service parameters for the backward direction for this connection. 
      This attribute is used for SPVC connections.
      
      The cdv element specifies the acceptable peak-to-peak Cell Delay 
      Variation (CDV) of real-time connections (CBR and rt-VBR). It is 
      signalled through the extended QoS information element.
      
      The clr specifies the acceptable Cell Loss Ratio (CLR) of CBR, rt-
      VBR, and nrt-VBR connections. It is signalled through the extended 
      QoS information element."
::= { atmIfVccVcdTm 459 }

atmIfVccVcdTmBqpEntry OBJECT-TYPE
   SYNTAX     AtmIfVccVcdTmBqpEntry
   ACCESS     not-accessible
   STATUS     mandatory
   DESCRIPTION
     "An entry in the atmIfVccVcdTmBqpTable."
   INDEX {
      atmIfIndex,
      atmIfVccIndex,
      atmIfVccVcdIndex,
      atmIfVccVcdTmIndex,
      atmIfVccVcdTmBqpIndex }
::= { atmIfVccVcdTmBqpTable 1 }

AtmIfVccVcdTmBqpEntry ::= SEQUENCE {
   atmIfVccVcdTmBqpIndex
      INTEGER,
   atmIfVccVcdTmBqpValue
      Unsigned32 }

atmIfVccVcdTmBqpIndex OBJECT-TYPE
   SYNTAX     INTEGER  {
                 cdv(0),
                 clr(2) }
   ACCESS     not-accessible
   STATUS     mandatory
   DESCRIPTION
     "This variable represents the atmIfVccVcdTmBqpTable
      specific index for the atmIfVccVcdTmBqpTable."
::= { atmIfVccVcdTmBqpEntry 1 }

atmIfVccVcdTmBqpValue OBJECT-TYPE
   SYNTAX     Unsigned32 (0..16777215)
   ACCESS     read-write
   STATUS     mandatory
   DESCRIPTION
     "This variable represents an individual value for the
      atmIfVccVcdTmBqpTable."
::= { atmIfVccVcdTmBqpEntry 2 }


-- AtmIf/n Vcc/vpi.vci Vcd Tm AvailableBitRate, 
-- AtmIf/n Vpc/vci Vpd Tm AvailableBitRate,
-- AtmIf/n Vpt/vpi Vpd Tm AvailableBitRate,
-- AtmIf/n Vpt/vpi Vcc/vci Vcd Tm AvailableBitRate
-- This component contains provisioned ABR-related attributes of a 
-- connection. It is an optional subcomponent of the Vcd Tm and Vpd 
-- Tm component. It is used to override DGCRA-related defaults in 
-- the CA Abr component. It contains the specific configuration for the 
-- ABR connection at this connection point. If this is the source of an 
-- SPVC connection, this component also contains the ABR 
-- parameters required for the SPVC call request.

atmIfVccVcdTmAbr OBJECT IDENTIFIER ::= { atmIfVccVcdTm 2 }



atmIfVccVcdTmAbrRowStatusTable OBJECT-TYPE
   SYNTAX     SEQUENCE OF AtmIfVccVcdTmAbrRowStatusEntry
   ACCESS     not-accessible
   STATUS     mandatory
   DESCRIPTION
     "This entry controls the addition and deletion of 
      atmIfVccVcdTmAbr components."
::= { atmIfVccVcdTmAbr 1 }

atmIfVccVcdTmAbrRowStatusEntry OBJECT-TYPE
   SYNTAX     AtmIfVccVcdTmAbrRowStatusEntry
   ACCESS     not-accessible
   STATUS     mandatory
   DESCRIPTION
     "A single entry in the table represents a single 
      atmIfVccVcdTmAbr component."
   INDEX {
      atmIfIndex,
      atmIfVccIndex,
      atmIfVccVcdIndex,
      atmIfVccVcdTmIndex,
      atmIfVccVcdTmAbrIndex }
::= { atmIfVccVcdTmAbrRowStatusTable 1 }

AtmIfVccVcdTmAbrRowStatusEntry ::= SEQUENCE {
   atmIfVccVcdTmAbrRowStatus
      RowStatus,
   atmIfVccVcdTmAbrComponentName
      DisplayString,
   atmIfVccVcdTmAbrStorageType
      StorageType,
   atmIfVccVcdTmAbrIndex
      NonReplicated }

atmIfVccVcdTmAbrRowStatus OBJECT-TYPE
   SYNTAX     RowStatus 
   ACCESS     read-write
   STATUS     mandatory
   DESCRIPTION
     "This variable is used as the basis for SNMP naming of
      atmIfVccVcdTmAbr components.
      These components can be added and deleted."
::= { atmIfVccVcdTmAbrRowStatusEntry 1 }

atmIfVccVcdTmAbrComponentName OBJECT-TYPE
   SYNTAX     DisplayString 
   ACCESS     read-only
   STATUS     mandatory
   DESCRIPTION
     "This variable provides the component's string name for
      use with the ASCII Console Interface"
::= { atmIfVccVcdTmAbrRowStatusEntry 2 }

atmIfVccVcdTmAbrStorageType OBJECT-TYPE
   SYNTAX     StorageType 
   ACCESS     read-only
   STATUS     mandatory
   DESCRIPTION
     "This variable represents the storage type value for the
      atmIfVccVcdTmAbr tables."
::= { atmIfVccVcdTmAbrRowStatusEntry 4 }

atmIfVccVcdTmAbrIndex OBJECT-TYPE
   SYNTAX     NonReplicated 
   ACCESS     not-accessible
   STATUS     mandatory
   DESCRIPTION
     "This variable represents the index for the atmIfVccVcdTmAbr tables."
::= { atmIfVccVcdTmAbrRowStatusEntry 10 }

atmIfVccVcdTmAbrProvTable OBJECT-TYPE
   SYNTAX     SEQUENCE OF AtmIfVccVcdTmAbrProvEntry
   ACCESS     not-accessible
   STATUS     mandatory
   DESCRIPTION
     "This group contains provisioned attributes for the ABR ATM 
      connections configured on an ATM interface."
::= { atmIfVccVcdTmAbr 110 }

atmIfVccVcdTmAbrProvEntry OBJECT-TYPE
   SYNTAX     AtmIfVccVcdTmAbrProvEntry
   ACCESS     not-accessible
   STATUS     mandatory
   DESCRIPTION
     "An entry in the atmIfVccVcdTmAbrProvTable."
   INDEX {
      atmIfIndex,
      atmIfVccIndex,
      atmIfVccVcdIndex,
      atmIfVccVcdTmIndex,
      atmIfVccVcdTmAbrIndex }
::= { atmIfVccVcdTmAbrProvTable 1 }

AtmIfVccVcdTmAbrProvEntry ::= SEQUENCE {
   atmIfVccVcdTmAbrInitialCellRate
      Unsigned32,
   atmIfVccVcdTmAbrTransientBufferExposure
      Unsigned32,
   atmIfVccVcdTmAbrFixedRoundTripTime
      Unsigned32,
   atmIfVccVcdTmAbrRateDecreaseFactor
      Unsigned32,
   atmIfVccVcdTmAbrRateIncreaseFactor
      Unsigned32,
   atmIfVccVcdTmAbrMaxCellPerRmCell
      Unsigned32,
   atmIfVccVcdTmAbrMaxTimeBetweenRmCells
      Unsigned32,
   atmIfVccVcdTmAbrCutoffDecreaseFactor
      Unsigned32,
   atmIfVccVcdTmAbrAcrDecreaseTimeFactor
      Unsigned32,
   atmIfVccVcdTmAbrDgcraMaximumDelay
      Unsigned32,
   atmIfVccVcdTmAbrDgcraMinimumDelay
      Unsigned32,
   atmIfVccVcdTmAbrFarEndAcrDecreaseTimeFactor
      Unsigned32,
   atmIfVccVcdTmAbrFarEndInitialCellRate
      Unsigned32 }

atmIfVccVcdTmAbrInitialCellRate OBJECT-TYPE
   SYNTAX     Unsigned32 (0..16777215 | 16777216 | 16777217 | 16777218)
   ACCESS     read-write
   STATUS     mandatory
   DESCRIPTION
     "This attribute specifies the Initial Cell Rate (ICR) parameter for this 
      connection. ICR is the rate at which a source should send initially 
      and after an idle period.
      
      When this attribute is set to sameAsCa, the initial cell rate is 
      determined by the AtmIf CA Abr/0 icr attribute. When the value of 
      this attribute is set to useMcr, ICR is set to the same value as the 
      Minimum Cell Rate (MCR) for the connection.
      
      When the value of this attribute is set to usePcr, ICR is set to the 
      same value as the Peak Cell Rate (PCR) for the connection.
      
      If this attribute is specified less than the MCR of the connection, 
      then the MCR is used as the ICR. If this attribute is specified more 
      than PCR of the connection, then PCR is used as the ICR.
      
      This attribute is ignored under all conditions where the operational 
      attribute abrConnectionType indicates erSwitch or efciSwitch.

      VALUES (

      16777216 = sameAsCa

      16777217 = useMcr

      16777218 = usePcr

      )"
   DEFVAL     { 16777216 }
::= { atmIfVccVcdTmAbrProvEntry 10 }

atmIfVccVcdTmAbrTransientBufferExposure OBJECT-TYPE
   SYNTAX     Unsigned32 (0..16777215)
   ACCESS     read-write
   STATUS     mandatory
   DESCRIPTION
     "This attribute specifies the Transient Buffer Exposure (TBE) for this 
      connection. TBE is the negotiated number of cells that the network 
      would like to limit the source to send during start-up periods, before 
      the first Resource Management (RM) cell returns.
      
      TBE divided by fixedRoundTripTime determines an upper bound 
      for the operational value of initialCellRate, the rate at which a 
      source should send initially and after an idle period.
      
      TBE divided by maxCellsPerRmCell specifies the operational value 
      of forwardRmCellLimit, the limit of the number of forward 
      Resource Management (RM) cells which may be sent in the 
      absence of received backward RM cells.
      
      This attribute is ignored under all conditions where the operational 
      attribute abrConnectionType is set to erSwitch."
   DEFVAL     { 16777215 }
::= { atmIfVccVcdTmAbrProvEntry 11 }

atmIfVccVcdTmAbrFixedRoundTripTime OBJECT-TYPE
   SYNTAX     Unsigned32 (0..16700000)
   ACCESS     read-write
   STATUS     mandatory
   DESCRIPTION
     "This attribute specifies the Fixed Round-Trip Time (FRTT) 
      parameter for this connection. FRTT is the sum of the fixed and 
      propagation delays from the source to a destination and back.
      
      The value of transientBufferExposure divided by the value of FRTT 
      (in seconds) determines an upper bound for the operational value of 
      initialCellRate, the rate at which a source should send initially and 
      after an idle period.
      
      This attribute is ignored under all conditions where the operational 
      attribute abrConnectionType indicates erSwitch or efciSwitch."
   DEFVAL     { 5000000 }
::= { atmIfVccVcdTmAbrProvEntry 12 }

atmIfVccVcdTmAbrRateDecreaseFactor OBJECT-TYPE
   SYNTAX     Unsigned32 (0..15 | 16777216)
   ACCESS     read-write
   STATUS     mandatory
   DESCRIPTION
     "This attribute specifies the Rate Decrease Factor (RDF) for this 
      connection. The RDF value is computed by using the provisioned 
      value of this attribute, n, as 2 to the inverse power n. For example, if 
      the value of this attribute is 8, RDF is 2E-8 = 1/256.
      
      RDF controls the amount by which the cell transmission rate may 
      decrease upon receipt of a backward Resource Management (RM) 
      cell. For example, if a backward RM cell is received with the 
      Congestion Indication (CI) field set to 1, the Allowed Cell Rate 
      (ACR) value would be reduced by the amount (RDF*ACR). The 
      ACR is not allowed to fall below the Minimum Cell Rate (MCR), in 
      which case the ACR is set to MCR.
      
      This attribute is ignored under all conditions where the operational 
      attribute abrConnectionType has the value erSwitch.

      VALUES (

      16777216 = sameAsCa

      )"
   DEFVAL     { 16777216 }
::= { atmIfVccVcdTmAbrProvEntry 13 }

atmIfVccVcdTmAbrRateIncreaseFactor OBJECT-TYPE
   SYNTAX     Unsigned32 (0..15 | 16777216)
   ACCESS     read-write
   STATUS     mandatory
   DESCRIPTION
     "This attribute specifies the Rate Increase Factor (RIF) for this 
      connection. The RIF value is computed by using the provisioned 
      value of this attribute, n, as 2 to the inverse power n. For example, if 
      the value of this attribute is 6, RIF is 2E-6 = 1/64.
      
      RIF controls the amount by which the cell transmission rate may 
      increase upon receipt of a backward Resource Management (RM) 
      cell. For example, if a backward RM cell is received with the 
      Congestion Indication (CI) and the No Increase (NI) fields both set 
      to 0, the Allowed Cell Rate (ACR) value would be increased by the 
      amount (RIF*ACR). The ACR is not allowed to exceed the Peak 
      Cell Rate (PCR), in which case the ACR is set to PCR.
      
      This attribute is ignored under all conditions where the operational 
      attribute abrConnectionType has the value erSwitch.

      VALUES (

      16777216 = sameAsCa

      )"
   DEFVAL     { 16777216 }
::= { atmIfVccVcdTmAbrProvEntry 14 }

atmIfVccVcdTmAbrMaxCellPerRmCell OBJECT-TYPE
   SYNTAX     Unsigned32 (2 | 4 | 8 | 16 | 32 | 64 | 128 | 256 | 16777216)
   ACCESS     read-write
   STATUS     mandatory
   DESCRIPTION
     "This attribute specifies the maximum number of cells an ABR 
      source may transmit for each forward Resource Management (RM) 
      cell. The count of the cells transmitted includes data cells, OAM 
      cells, backward RM cells, and the forward RM cell.
      
      A value of 2 is not recommended although it is permitted according 
      to the ATM Forum standard. When this attribute is set to a value of 
      2, it is possible that only one forward and one backward RM cell 
      are repeatedly transmitted, and all data traffic is queued up 
      indefinitely.
      
      This attribute is ignored under all conditions where the operational 
      attribute abrConnectionType has the value erSwitch.

      VALUES (

      16777216 = sameAsCa

      )"
   DEFVAL     { 16777216 }
::= { atmIfVccVcdTmAbrProvEntry 15 }

atmIfVccVcdTmAbrMaxTimeBetweenRmCells OBJECT-TYPE
   SYNTAX     Unsigned32 (781 | 1563 | 3125 | 6250 | 12500 | 25000 | 50000 | 100000 | 16777216)
   ACCESS     read-write
   STATUS     mandatory
   DESCRIPTION
     "This attribute specifies the TRM parameter for this connection.
      
      TRM provides an lower bound on the time interval between forward 
      Resource Management (RM) cells for an ABR source. Since the last 
      forward RM cell was sent, if at least TRM time has elapsed since 
      and at least two other cells have been sent, then the next cell to be 
      transmitted would be a forward RM cell.
      
      This attribute is ignored under all conditions where the operational 
      attribute abrConnectionType has the value erSwitch.
      
      The provisioned value of 781 is signalled as TRM = 0, in the ABR 
      Additional Parameters Information Element. 
      1563 is signalled as TRM = 1. 
      3125 is signalled as TRM = 2. 
      6250 is signalled as TRM = 3. 
      12500 is signalled as TRM = 4 
      25000 is signalled as TRM = 5. 
      50000 is signalled as TRM = 6. 
      100000 is signalled as TRM = 7.

      VALUES (

      16777216 = sameAsCa

      )"
   DEFVAL     { 16777216 }
::= { atmIfVccVcdTmAbrProvEntry 16 }

atmIfVccVcdTmAbrCutoffDecreaseFactor OBJECT-TYPE
   SYNTAX     Unsigned32 (0 | 1 | 2 | 4 | 8 | 16 | 32 | 64 | 16777216)
   ACCESS     read-write
   STATUS     mandatory
   DESCRIPTION
     "This attribute specifies the Cutoff Decrease Factor (CDF) parameter 
      for this connection. When the value of this attribute is non-zero, 
      CDF is computed as the inverse of the value. For example, if the 
      value is 32, the value of CDF is 1/32. When the value of this 
      attribute is 0, CDF is also zero.
      
      CDF controls the decrease in the Allowed Cell Rate (ACR) 
      associated with the CRM parameter, the limit of the number of 
      forward Resource Management (RM) cells which may be sent in 
      the absence of received backward RM cells. When this limit is 
      crossed, the ACR value would be decreased by the amount 
      (CDF*ACR). The ACR is not allowed to fall below the Minimum 
      Cell Rate (MCR), in which case the ACR is set to MCR.
      
      The value of CRM is indicated by the forwardRmCellLimit 
      attribute.
      
      This attribute is ignored under all conditions where the operational 
      attribute abrConnectionType indicates erSwitch or efciSwitch.

      VALUES (

      16777216 = sameAsCa

      )"
   DEFVAL     { 16777216 }
::= { atmIfVccVcdTmAbrProvEntry 17 }

atmIfVccVcdTmAbrAcrDecreaseTimeFactor OBJECT-TYPE
   SYNTAX     Unsigned32 (0..1023 | 16777216)
   ACCESS     read-write
   STATUS     mandatory
   DESCRIPTION
     "This attribute specifies the Allowed Cell Rate Decrease Time Factor 
      (ADTF) parameter for this connection.
      
      ADTF is the maximum time interval permitted between sending 
      forward Resource Management (RM) cells before the Allowed Cell 
      Rate (ACR) is decreased to initialCellRate. In other words, if the 
      source does not transit a forward RM cell for the period specified by 
      adtf, it reduces its ACR to the value of its initialCellRate.
      
      This attribute is ignored under all conditions where the operational 
      attribute abrConnectionType indicates erSwitch or efciSwitch.

      VALUES (

      16777216 = sameAsCa

      )"
   DEFVAL     { 16777216 }
::= { atmIfVccVcdTmAbrProvEntry 18 }

atmIfVccVcdTmAbrDgcraMaximumDelay OBJECT-TYPE
   SYNTAX     Unsigned32 (1..16700000 | 16777216)
   ACCESS     read-write
   STATUS     mandatory
   DESCRIPTION
     "This attribute specifies an upper bound on the delay after which the 
      rate change induced by a backward Resource Management (RM) 
      cell departing from this connection point (in the backward 
      direction) is expected to be observed at this connection point (in the 
      forward direction).
      
      This upper bound may be approximated as the sum of the round trip 
      fixed and propagation delays and the maximum queuing delays 
      between the ABR source and this interface.
      
      The value of this attribute is used in policing an ABR connection 
      using the Dynamic General Cell Rate Algorithm (DGCRA). A 
      larger value for this attribute implies a more lenient policer. When 
      there is a reduction in the Allowed Cell Rate (ACR), the policer 
      waits for a correspondingly longer period of time before it enforces 
      at the new cell rate.
      
      The value of this attribute must not be less than the 
      dgcraMinimumDelay attribute.

      VALUES (

      16777216 = sameAsCa

      )"
   DEFVAL     { 16777216 }
::= { atmIfVccVcdTmAbrProvEntry 19 }

atmIfVccVcdTmAbrDgcraMinimumDelay OBJECT-TYPE
   SYNTAX     Unsigned32 (1..16700000 | 16777216)
   ACCESS     read-write
   STATUS     mandatory
   DESCRIPTION
     "This attribute specifies a lower bound on the delay after which the 
      rate change induced by a backward Resource Management (RM) 
      cell departing from this connection point (in the backward 
      direction) is expected to be observed at this connection point (in the 
      forward connection).
      
      This lower bound may be approximated as the sum of the round trip 
      fixed and propagation delays between the ABR source and this 
      interface.
      
      The value of this attribute is used in policing an ABR connection 
      using the Dynamic General Cell Rate Algorithm (DGCRA). A 
      smaller value for this attribute implies a more lenient policer. When 
      there is a increase in the Allowed Cell Rate (ACR), the policer waits 
      for a correspondingly shorter period of time before it enforces at the 
      new cell rate.

      VALUES (

      16777216 = sameAsCa

      )"
   DEFVAL     { 16777216 }
::= { atmIfVccVcdTmAbrProvEntry 20 }

atmIfVccVcdTmAbrFarEndAcrDecreaseTimeFactor OBJECT-TYPE
   SYNTAX     Unsigned32 (0..1023 | 1024)
   ACCESS     read-write
   STATUS     mandatory
   DESCRIPTION
     "This attribute specifies the Allowed Cell Rate Decrease Time Factor 
      (ADTF) of the far end ABR source. The value specified should be 
      the same as the ADTF parameter at the far end of this ABR 
      connection. 
      
      The value of this attribute is used in policing an ABR connection 
      using the Dynamic Generic Cell Rate Algorithm (DGCRA). A 
      larger value for this attribute implies a more lenient policer. When 
      the delay between two consecutive forward Resource Management 
      (RM) cells received at this interface corresponds to a value greater 
      than the value of this attribute, the policer begins to limit enforce 
      the incoming traffic at the initial cell rate (ICR) of the far end, as 
      specified by the farEndInitialCellRate attribute.

      VALUES (

      1024 = sameAsLocal

      )"
   DEFVAL     { 1024 }
::= { atmIfVccVcdTmAbrProvEntry 21 }

atmIfVccVcdTmAbrFarEndInitialCellRate OBJECT-TYPE
   SYNTAX     Unsigned32 (0..16777215 | 16777219)
   ACCESS     read-write
   STATUS     mandatory
   DESCRIPTION
     "This attribute specifies the Initial Cell Rate (ICR) of the far end 
      ABR source. The value specified should be the same as the ICR 
      parameter at the far end of this ABR connection. 
      
      The value of this attribute is used in policing an ABR connection 
      using the Dynamic Generic Cell Rate Algorithm (DGCRA). A 
      larger value for this attribute implies a more lenient policer. When 
      the delay between two consecutive forward Resource Management 
      (RM) cells received at this interface corresponds to a value greater 
      than the farEndAcrDecreaseTimeFactor attribute, the policer begins 
      to enforce the incoming traffic at the value of this attribute.
      
      If this attribute is specified less than the MCR of the connection, 
      then the MCR is used as the feIcr. If this attribute is more than the 
      PCR of the connection, then PCR is used as the feIcr.

      VALUES (

      16777219 = sameAsLocal

      )"
   DEFVAL     { 16777219 }
::= { atmIfVccVcdTmAbrProvEntry 22 }


-- AtmIf/n Vcc/vpi.vci Loop
-- The Loop component configures an ATM connection so that cells 
-- received from the ATM interface are retransmitted back to the 
-- interface through that connection. The Loop component requires 
-- exclusive use of its parent Vcc or Vpc and cannot co-exist with other 
-- ATM service components (such as Nep, Nrp, and Test).

atmIfVccLoop OBJECT IDENTIFIER ::= { atmIfVcc 3 }



atmIfVccLoopRowStatusTable OBJECT-TYPE
   SYNTAX     SEQUENCE OF AtmIfVccLoopRowStatusEntry
   ACCESS     not-accessible
   STATUS     mandatory
   DESCRIPTION
     "This entry controls the addition and deletion of 
      atmIfVccLoop components."
::= { atmIfVccLoop 1 }

atmIfVccLoopRowStatusEntry OBJECT-TYPE
   SYNTAX     AtmIfVccLoopRowStatusEntry
   ACCESS     not-accessible
   STATUS     mandatory
   DESCRIPTION
     "A single entry in the table represents a single 
      atmIfVccLoop component."
   INDEX {
      atmIfIndex,
      atmIfVccIndex,
      atmIfVccLoopIndex }
::= { atmIfVccLoopRowStatusTable 1 }

AtmIfVccLoopRowStatusEntry ::= SEQUENCE {
   atmIfVccLoopRowStatus
      RowStatus,
   atmIfVccLoopComponentName
      DisplayString,
   atmIfVccLoopStorageType
      StorageType,
   atmIfVccLoopIndex
      NonReplicated }

atmIfVccLoopRowStatus OBJECT-TYPE
   SYNTAX     RowStatus 
   ACCESS     read-write
   STATUS     mandatory
   DESCRIPTION
     "This variable is used as the basis for SNMP naming of
      atmIfVccLoop components.
      These components can be added and deleted."
::= { atmIfVccLoopRowStatusEntry 1 }

atmIfVccLoopComponentName OBJECT-TYPE
   SYNTAX     DisplayString 
   ACCESS     read-only
   STATUS     mandatory
   DESCRIPTION
     "This variable provides the component's string name for
      use with the ASCII Console Interface"
::= { atmIfVccLoopRowStatusEntry 2 }

atmIfVccLoopStorageType OBJECT-TYPE
   SYNTAX     StorageType 
   ACCESS     read-only
   STATUS     mandatory
   DESCRIPTION
     "This variable represents the storage type value for the
      atmIfVccLoop tables."
::= { atmIfVccLoopRowStatusEntry 4 }

atmIfVccLoopIndex OBJECT-TYPE
   SYNTAX     NonReplicated 
   ACCESS     not-accessible
   STATUS     mandatory
   DESCRIPTION
     "This variable represents the index for the atmIfVccLoop tables."
::= { atmIfVccLoopRowStatusEntry 10 }


-- AtmIf/n Vcc/vpi.vci Nep
-- The NailedUpEndPoint component is used to link a VCC to an 
-- application that sends and receives frames using the connection. 
-- The Nep component requires exclusive use of its parent Vcc and 
-- cannot co-exist with other ATM service components (such as Nrp, 
-- Test, and Loop).

atmIfVccNep OBJECT IDENTIFIER ::= { atmIfVcc 5 }



atmIfVccNepRowStatusTable OBJECT-TYPE
   SYNTAX     SEQUENCE OF AtmIfVccNepRowStatusEntry
   ACCESS     not-accessible
   STATUS     mandatory
   DESCRIPTION
     "This entry controls the addition and deletion of 
      atmIfVccNep components."
::= { atmIfVccNep 1 }

atmIfVccNepRowStatusEntry OBJECT-TYPE
   SYNTAX     AtmIfVccNepRowStatusEntry
   ACCESS     not-accessible
   STATUS     mandatory
   DESCRIPTION
     "A single entry in the table represents a single 
      atmIfVccNep component."
   INDEX {
      atmIfIndex,
      atmIfVccIndex,
      atmIfVccNepIndex }
::= { atmIfVccNepRowStatusTable 1 }

AtmIfVccNepRowStatusEntry ::= SEQUENCE {
   atmIfVccNepRowStatus
      RowStatus,
   atmIfVccNepComponentName
      DisplayString,
   atmIfVccNepStorageType
      StorageType,
   atmIfVccNepIndex
      NonReplicated }

atmIfVccNepRowStatus OBJECT-TYPE
   SYNTAX     RowStatus 
   ACCESS     read-write
   STATUS     mandatory
   DESCRIPTION
     "This variable is used as the basis for SNMP naming of
      atmIfVccNep components.
      These components can be added and deleted."
::= { atmIfVccNepRowStatusEntry 1 }

atmIfVccNepComponentName OBJECT-TYPE
   SYNTAX     DisplayString 
   ACCESS     read-only
   STATUS     mandatory
   DESCRIPTION
     "This variable provides the component's string name for
      use with the ASCII Console Interface"
::= { atmIfVccNepRowStatusEntry 2 }

atmIfVccNepStorageType OBJECT-TYPE
   SYNTAX     StorageType 
   ACCESS     read-only
   STATUS     mandatory
   DESCRIPTION
     "This variable represents the storage type value for the
      atmIfVccNep tables."
::= { atmIfVccNepRowStatusEntry 4 }

atmIfVccNepIndex OBJECT-TYPE
   SYNTAX     NonReplicated 
   ACCESS     not-accessible
   STATUS     mandatory
   DESCRIPTION
     "This variable represents the index for the atmIfVccNep tables."
::= { atmIfVccNepRowStatusEntry 10 }

atmIfVccNepProvTable OBJECT-TYPE
   SYNTAX     SEQUENCE OF AtmIfVccNepProvEntry
   ACCESS     not-accessible
   STATUS     mandatory
   DESCRIPTION
     "This group contains provisionable attributes for the Nep component."
::= { atmIfVccNep 100 }

atmIfVccNepProvEntry OBJECT-TYPE
   SYNTAX     AtmIfVccNepProvEntry
   ACCESS     not-accessible
   STATUS     mandatory
   DESCRIPTION
     "An entry in the atmIfVccNepProvTable."
   INDEX {
      atmIfIndex,
      atmIfVccIndex,
      atmIfVccNepIndex }
::= { atmIfVccNepProvTable 1 }

AtmIfVccNepProvEntry ::= SEQUENCE {
   atmIfVccNepApplicationName
      Link }

atmIfVccNepApplicationName OBJECT-TYPE
   SYNTAX     Link 
   ACCESS     read-only
   STATUS     mandatory
   DESCRIPTION
     "This attribute specifies the application that sends and receives 
      frames using the VCC. This attribute is set, for example, by 
      provisioning the Trunk AtmAccess AtmConnection attribute. If it is 
      properly configured, this attribute will show a value such as
      'Trk/22 AtmAccess'."
::= { atmIfVccNepProvEntry 10 }


-- AtmIf/n Vcc/vpi.vci Test
-- The Test component allows test traffic to be sent over an ATM 
-- connection. It is used to verify the integrity of hardware carrying 
-- ATM traffic, and provides test capabilities similar to those provided 
-- by non-ATM port and line tests. The Test component requires 
-- exclusive use of its parent Vcc and cannot co-exist with other ATM 
-- service components (such as Nep, Nrp, and Loop).
-- 
-- An ATM connection test circulates traffic through a VCC having a 
-- Test component at one end and the other end configured to loop 
-- back ATM cells. The Test component generates test frames, 
-- transforms them into ATM cells using AAL5 segmentation, and 
-- transmits them through the VCC; the returned cells are received by 
-- the Test component, reassembled back into frames, and the frames 
-- are consumed.
-- 
-- The test frames generated by the test are grouped into two 
-- independent streams.
-- 1) The loading frame stream circulates a set of "loading frames" 
-- through the connection as rapidly as possible. The intent of this 
-- stream is to verify the operation of the connection under a 
-- controlled load.
-- 2) The verification stream transmits a series of "verification frames" 
-- through the connection; as each frame is returned, the Test 
-- component verifies its contents and the next verification frame in 
-- the series is transmitted. The intent of this stream is to verify that 
-- frames are not being corrupted.
-- The test can be configured to send frames from either or both 
-- streams. The size and content of the test frames can also be 
-- controlled.

atmIfVccTest OBJECT IDENTIFIER ::= { atmIfVcc 6 }



atmIfVccTestRowStatusTable OBJECT-TYPE
   SYNTAX     SEQUENCE OF AtmIfVccTestRowStatusEntry
   ACCESS     not-accessible
   STATUS     mandatory
   DESCRIPTION
     "This entry controls the addition and deletion of 
      atmIfVccTest components."
::= { atmIfVccTest 1 }

atmIfVccTestRowStatusEntry OBJECT-TYPE
   SYNTAX     AtmIfVccTestRowStatusEntry
   ACCESS     not-accessible
   STATUS     mandatory
   DESCRIPTION
     "A single entry in the table represents a single 
      atmIfVccTest component."
   INDEX {
      atmIfIndex,
      atmIfVccIndex,
      atmIfVccTestIndex }
::= { atmIfVccTestRowStatusTable 1 }

AtmIfVccTestRowStatusEntry ::= SEQUENCE {
   atmIfVccTestRowStatus
      RowStatus,
   atmIfVccTestComponentName
      DisplayString,
   atmIfVccTestStorageType
      StorageType,
   atmIfVccTestIndex
      NonReplicated }

atmIfVccTestRowStatus OBJECT-TYPE
   SYNTAX     RowStatus 
   ACCESS     read-write
   STATUS     mandatory
   DESCRIPTION
     "This variable is used as the basis for SNMP naming of
      atmIfVccTest components.
      These components can be added and deleted."
::= { atmIfVccTestRowStatusEntry 1 }

atmIfVccTestComponentName OBJECT-TYPE
   SYNTAX     DisplayString 
   ACCESS     read-only
   STATUS     mandatory
   DESCRIPTION
     "This variable provides the component's string name for
      use with the ASCII Console Interface"
::= { atmIfVccTestRowStatusEntry 2 }

atmIfVccTestStorageType OBJECT-TYPE
   SYNTAX     StorageType 
   ACCESS     read-only
   STATUS     mandatory
   DESCRIPTION
     "This variable represents the storage type value for the
      atmIfVccTest tables."
::= { atmIfVccTestRowStatusEntry 4 }

atmIfVccTestIndex OBJECT-TYPE
   SYNTAX     NonReplicated 
   ACCESS     not-accessible
   STATUS     mandatory
   DESCRIPTION
     "This variable represents the index for the atmIfVccTest tables."
::= { atmIfVccTestRowStatusEntry 10 }

atmIfVccTestStateTable OBJECT-TYPE
   SYNTAX     SEQUENCE OF AtmIfVccTestStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { atmIfVccTest 100 }

atmIfVccTestStateEntry OBJECT-TYPE
   SYNTAX     AtmIfVccTestStateEntry
   ACCESS     not-accessible
   STATUS     mandatory
   DESCRIPTION
     "An entry in the atmIfVccTestStateTable."
   INDEX {
      atmIfIndex,
      atmIfVccIndex,
      atmIfVccTestIndex }
::= { atmIfVccTestStateTable 1 }

AtmIfVccTestStateEntry ::= SEQUENCE {
   atmIfVccTestAdminState
      INTEGER,
   atmIfVccTestOperationalState
      INTEGER,
   atmIfVccTestUsageState
      INTEGER }

atmIfVccTestAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { atmIfVccTestStateEntry 1 }

atmIfVccTestOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { atmIfVccTestStateEntry 2 }

atmIfVccTestUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { atmIfVccTestStateEntry 3 }

atmIfVccTestSetupTable OBJECT-TYPE
   SYNTAX     SEQUENCE OF AtmIfVccTestSetupEntry
   ACCESS     not-accessible
   STATUS     mandatory
   DESCRIPTION
     "This group contains attributes that govern the operation of an ATM 
      connection test. These attributes cannot be changed while the test is 
      running."
::= { atmIfVccTest 110 }

atmIfVccTestSetupEntry OBJECT-TYPE
   SYNTAX     AtmIfVccTestSetupEntry
   ACCESS     not-accessible
   STATUS     mandatory
   DESCRIPTION
     "An entry in the atmIfVccTestSetupTable."
   INDEX {
      atmIfIndex,
      atmIfVccIndex,
      atmIfVccTestIndex }
::= { atmIfVccTestSetupTable 1 }

AtmIfVccTestSetupEntry ::= SEQUENCE {
   atmIfVccTestFrmTypes
      OCTET STRING,
   atmIfVccTestFrmSize
      Unsigned32,
   atmIfVccTestFrmPatternType
      INTEGER,
   atmIfVccTestCustomizedPattern
      Hex,
   atmIfVccTestDuration
      Unsigned32,
   atmIfVccTestBandwidthElastic
      INTEGER,
   atmIfVccTestOverrideHoldingPriority
      INTEGER }

atmIfVccTestFrmTypes OBJECT-TYPE
   SYNTAX     OCTET STRING (SIZE (1))
   ACCESS     read-write
   STATUS     mandatory
   DESCRIPTION
     "This attribute specifies the types of the test frames to be transmitted 
      during the ATM connection test. It must contain at least one of the 
      following:
      loading: A set of 'loading frames' is circulated over the link as 
      rapidly as possible. This frame type should be selected when the 
      test is intended to verify the operation of the connection under a 
      specified load. These frames are not checked for bit errors.
      verification: A single 'verification frame' is transmitted over the 
      link; when the frame is returned, its contents are verified and the 
      next verification frame in the series is transmitted. This frame type 
      should be selected when the test is intended to verify that frames are 
      not being corrupted as they pass over the connection.

      Description of bits:
      loading(0)
      verification(1)"
   DEFVAL     { 'c0'H }
::= { atmIfVccTestSetupEntry 10 }

atmIfVccTestFrmSize OBJECT-TYPE
   SYNTAX     Unsigned32 (4..4096)
   ACCESS     read-write
   STATUS     mandatory
   DESCRIPTION
     "This attribute defines the size of the test frames used in an ATM 
      connection test."
   DEFVAL     { 1024 }
::= { atmIfVccTestSetupEntry 20 }

atmIfVccTestFrmPatternType OBJECT-TYPE
   SYNTAX     INTEGER  {
                 ccitt32kBitPattern(0),
                 ccitt8MBitPattern(1),
                 customizedPattern(2) }
   ACCESS     read-write
   STATUS     mandatory
   DESCRIPTION
     "This attribute specifies the bit sequence used to fill the frames used 
      in the ATM connection test. It must contain one of the following 
      values:
      ccitt32kBitPattern: a pseudo-random sequence of 32 Kbit is used
      ccitt8MBitPattern: a pseudo-random sequence of 8Mbit is used
      customizedPattern: the pattern defined in the customizedPattern 
      attribute is used"
   DEFVAL     { ccitt32kBitPattern }
::= { atmIfVccTestSetupEntry 30 }

atmIfVccTestCustomizedPattern OBJECT-TYPE
   SYNTAX     Hex (0..4294967295)
   ACCESS     read-write
   STATUS     mandatory
   DESCRIPTION
     "This attribute specifies a 32 bit sequence to be used to fill frames 
      when the framePatternType attribute is set to customizedPattern. 
      The default value gives a pattern of alternating 0 and 1 bits."
   DEFVAL     { 1431655765 }
::= { atmIfVccTestSetupEntry 40 }

atmIfVccTestDuration OBJECT-TYPE
   SYNTAX     Unsigned32 (1..30240)
   ACCESS     read-write
   STATUS     mandatory
   DESCRIPTION
     "This attribute specifies the maximum number of minutes that the 
      ATM connection test is allowed to run. The maximum allowed 
      value permits the test to be run for up to 21 days."
   DEFVAL     { 1 }
::= { atmIfVccTestSetupEntry 50 }

atmIfVccTestBandwidthElastic OBJECT-TYPE
   SYNTAX     INTEGER  {
                 no(0),
                 yes(1) }
   ACCESS     read-write
   STATUS     mandatory
   DESCRIPTION
     "This attribute specifies whether the connection (VCC) should be 
      configured with elastic bandwidth or not. Elastic bandwidth is of 
      importance in conjuction with IMA links, where some links fail and 
      the resulting bandwidth is less than the requested bandwidth for all 
      connections. In that case, some connections may be reduced in 
      bandwidth based on the setting of the bwElastic attribute.
      
      If this attribute is set to yes, the Test application signals to the 
      connection that the bandwidth for this connection is elastic, and 
      may be reduced in the case of IMA link failures. If the bandwidth is 
      reduced, the rate of test cells which can be handled by the 
      connection will also be reduced. 
      
      If this attribute is set to no, the Test application signals to the 
      connection that the bandwidth for this connection must be 
      maintained at the requested level. If the connection cannot maintain 
      the full bandwidth, the connection may be released (cleared) based 
      on the holding priority of the connection."
   DEFVAL     { no }
::= { atmIfVccTestSetupEntry 60 }

atmIfVccTestOverrideHoldingPriority OBJECT-TYPE
   SYNTAX     INTEGER  {
                 n0(0),
                 n1(1),
                 n2(2),
                 n3(3),
                 n4(4),
                 noOverride(6) }
   ACCESS     read-write
   STATUS     mandatory
   DESCRIPTION
     "This attribute specifies the override holding priority which should 
      be signalled to the VCC connection at the start of the test. Holding 
      priority is of importance in conjuction with IMA links, where some 
      links fail and the resulting bandwidth is less than the requested 
      bandwidth for all connections. In that case, some connections may 
      be released based on the connection's holding priority.
      
      Zero (0) is thie highest holding priority, and four (4) is the lowest 
      priority. A setting of zero to four overrides whatever holding 
      priority that has been configured at the connection (VCC). A setting 
      of noOverride means that the connection should use its internally 
      configured holding priority."
   DEFVAL     { noOverride }
::= { atmIfVccTestSetupEntry 70 }

atmIfVccTestResultsTable OBJECT-TYPE
   SYNTAX     SEQUENCE OF AtmIfVccTestResultsEntry
   ACCESS     not-accessible
   STATUS     mandatory
   DESCRIPTION
     "This group contains attributes that show the result of an ATM 
      connection test; if no test is running, the attribute group contains the 
      results of the most recently completed test. The attributes of the 
      Results group are reset to their inital values whenever a test is 
      started or any attribute of the Setup group is set."
::= { atmIfVccTest 120 }

atmIfVccTestResultsEntry OBJECT-TYPE
   SYNTAX     AtmIfVccTestResultsEntry
   ACCESS     not-accessible
   STATUS     mandatory
   DESCRIPTION
     "An entry in the atmIfVccTestResultsTable."
   INDEX {
      atmIfIndex,
      atmIfVccIndex,
      atmIfVccTestIndex }
::= { atmIfVccTestResultsTable 1 }

AtmIfVccTestResultsEntry ::= SEQUENCE {
   atmIfVccTestElapsedTime
      Unsigned32,
   atmIfVccTestTimeRemaining
      Unsigned32,
   atmIfVccTestCauseOfTermination
      INTEGER,
   atmIfVccTestBytesTx
      PassportCounter64,
   atmIfVccTestBytesRx
      PassportCounter64,
   atmIfVccTestLoadingFrmTx
      PassportCounter64,
   atmIfVccTestLoadingFrmRx
      PassportCounter64,
   atmIfVccTestLoadingFrmLost
      PassportCounter64,
   atmIfVccTestVerificationFrmTx
      PassportCounter64,
   atmIfVccTestVerificationFrmRx
      PassportCounter64,
   atmIfVccTestVerificationFrmBad
      PassportCounter64,
   atmIfVccTestUnrecognizableFrmRx
      PassportCounter64 }

atmIfVccTestElapsedTime OBJECT-TYPE
   SYNTAX     Unsigned32 (0..30240)
   ACCESS     read-only
   STATUS     mandatory
   DESCRIPTION
     "This attribute displays the number of minutes that the test has been 
      running."
   DEFVAL     { 0 }
::= { atmIfVccTestResultsEntry 10 }

atmIfVccTestTimeRemaining OBJECT-TYPE
   SYNTAX     Unsigned32 (0..30240)
   ACCESS     read-only
   STATUS     mandatory
   DESCRIPTION
     "This attribute displays the number of minutes that the test will 
      continue to run before stopping automatically."
   DEFVAL     { 0 }
::= { atmIfVccTestResultsEntry 20 }

atmIfVccTestCauseOfTermination OBJECT-TYPE
   SYNTAX     INTEGER  {
                 testTimeExpired(0),
                 stoppedByOperator(1),
                 neverStarted(2),
                 testRunning(3) }
   ACCESS     read-only
   STATUS     mandatory
   DESCRIPTION
     "This attribute displays the reason the test ended. It contains one fo 
      the following values.
      testTimeExpired: the test ran for the specified duration
      stoppedByOperator: a STOP command was issued
      neverStarted: the test has not been started
      testRunning: the test is currently running"
   DEFVAL     { neverStarted }
::= { atmIfVccTestResultsEntry 30 }

atmIfVccTestBytesTx OBJECT-TYPE
   SYNTAX     PassportCounter64 
   ACCESS     read-only
   STATUS     mandatory
   DESCRIPTION
     "This attribute displays the number of bytes sent during the test. The 
      counter wraps to zero if it exceeds its maximum value of (2**64)-1."
::= { atmIfVccTestResultsEntry 40 }

atmIfVccTestBytesRx OBJECT-TYPE
   SYNTAX     PassportCounter64 
   ACCESS     read-only
   STATUS     mandatory
   DESCRIPTION
     "This attribute displays the number of bytes received during the test. 
      The counter wraps to zero if it exceeds its maximum value of 
      (2**64)-1."
::= { atmIfVccTestResultsEntry 50 }

atmIfVccTestLoadingFrmTx OBJECT-TYPE
   SYNTAX     PassportCounter64 
   ACCESS     read-only
   STATUS     mandatory
   DESCRIPTION
     "This attribute displays the number of loading frames sent during the 
      test. The counter wraps to zero if it exceeds its maximum value of 
      (2**64)-1."
::= { atmIfVccTestResultsEntry 60 }

atmIfVccTestLoadingFrmRx OBJECT-TYPE
   SYNTAX     PassportCounter64 
   ACCESS     read-only
   STATUS     mandatory
   DESCRIPTION
     "This attribute displays the number of loading frames received 
      during the test. The counter wraps to zero if it exceeds its maximum 
      value of (2**64)-1."
::= { atmIfVccTestResultsEntry 70 }

atmIfVccTestLoadingFrmLost OBJECT-TYPE
   SYNTAX     PassportCounter64 
   ACCESS     read-only
   STATUS     mandatory
   DESCRIPTION
     "This attribute displays the number of loading frames that were lost 
      during the test. The counter wraps to zero if it exceeds its maximum 
      value of (2**64)-1."
::= { atmIfVccTestResultsEntry 80 }

atmIfVccTestVerificationFrmTx OBJECT-TYPE
   SYNTAX     PassportCounter64 
   ACCESS     read-only
   STATUS     mandatory
   DESCRIPTION
     "This attribute displays the number of verification frames sent during 
      the test. The counter wraps to zero if it exceeds its maximum value 
      of (2**64)-1."
::= { atmIfVccTestResultsEntry 90 }

atmIfVccTestVerificationFrmRx OBJECT-TYPE
   SYNTAX     PassportCounter64 
   ACCESS     read-only
   STATUS     mandatory
   DESCRIPTION
     "This attribute displays the number of verification frames received 
      during the test (including errored verification frames). The counter 
      wraps to zero if it exceeds its maximum value of (2**64)-1.
      
      Note that the number of verification frames lost during the test can 
      be computed by the expression verificationFrmTx - 
      verificationFrmRx."
::= { atmIfVccTestResultsEntry 100 }

atmIfVccTestVerificationFrmBad OBJECT-TYPE
   SYNTAX     PassportCounter64 
   ACCESS     read-only
   STATUS     mandatory
   DESCRIPTION
     "This attribute displays the number of errored verification frames 
      received during the test. A verification frame is considered to be 
      errored if it contains a recognizable verification frame header, but 
      does not match the transmitted frame bit for bit. (Thus, a 
      verification frame that returns after the succeeding verification 
      frame has been transmitted is considered to be errored.) The counter 
      wraps to zero if it exceeds its maximum value of (2**64)-1.
      
      Note that the number of correct verification frames received during 
      the test can be computed by the expression verificationFrmRx - 
      verificationFrmBad."
::= { atmIfVccTestResultsEntry 110 }

atmIfVccTestUnrecognizableFrmRx OBJECT-TYPE
   SYNTAX     PassportCounter64 
   ACCESS     read-only
   STATUS     mandatory
   DESCRIPTION
     "This attribute displays the number of frames received during the test 
      which do not contain a valid loading frame header or verification 
      frame header. The counter wraps to zero if it exceeds its maximum 
      value of (2**64)-1."
::= { atmIfVccTestResultsEntry 120 }


-- AtmIf/n Vpc/vpi TrafficManagement, 
-- AtmIf/n Vcc/vpi.vci TrafficManagement,
-- AtmIf/n Vpt/vpi TrafficManagement,
-- AtmIf/n Vpt/vpi Vcc/vci TrafficManagement
-- The Tm subcomponent contains the operational traffic management 
-- attributes of a connection. It is created dynamically for each 
-- activated Vcc, Vpc, or Vpt component.

atmIfVccTm OBJECT IDENTIFIER ::= { atmIfVcc 7 }



atmIfVccTmRowStatusTable OBJECT-TYPE
   SYNTAX     SEQUENCE OF AtmIfVccTmRowStatusEntry
   ACCESS     not-accessible
   STATUS     mandatory
   DESCRIPTION
     "This entry controls the addition and deletion of 
      atmIfVccTm components."
::= { atmIfVccTm 1 }

atmIfVccTmRowStatusEntry OBJECT-TYPE
   SYNTAX     AtmIfVccTmRowStatusEntry
   ACCESS     not-accessible
   STATUS     mandatory
   DESCRIPTION
     "A single entry in the table represents a single 
      atmIfVccTm component."
   INDEX {
      atmIfIndex,
      atmIfVccIndex,
      atmIfVccTmIndex }
::= { atmIfVccTmRowStatusTable 1 }

AtmIfVccTmRowStatusEntry ::= SEQUENCE {
   atmIfVccTmRowStatus
      RowStatus,
   atmIfVccTmComponentName
      DisplayString,
   atmIfVccTmStorageType
      StorageType,
   atmIfVccTmIndex
      NonReplicated }

atmIfVccTmRowStatus OBJECT-TYPE
   SYNTAX     RowStatus 
   ACCESS     read-only
   STATUS     mandatory
   DESCRIPTION
     "This variable is used as the basis for SNMP naming of
      atmIfVccTm components.
      These components cannot be added nor deleted."
::= { atmIfVccTmRowStatusEntry 1 }

atmIfVccTmComponentName OBJECT-TYPE
   SYNTAX     DisplayString 
   ACCESS     read-only
   STATUS     mandatory
   DESCRIPTION
     "This variable provides the component's string name for
      use with the ASCII Console Interface"
::= { atmIfVccTmRowStatusEntry 2 }

atmIfVccTmStorageType OBJECT-TYPE
   SYNTAX     StorageType 
   ACCESS     read-only
   STATUS     mandatory
   DESCRIPTION
     "This variable represents the storage type value for the
      atmIfVccTm tables."
::= { atmIfVccTmRowStatusEntry 4 }

atmIfVccTmIndex OBJECT-TYPE
   SYNTAX     NonReplicated 
   ACCESS     not-accessible
   STATUS     mandatory
   DESCRIPTION
     "This variable represents the index for the atmIfVccTm tables."
::= { atmIfVccTmRowStatusEntry 10 }

atmIfVccTmOperTable OBJECT-TYPE
   SYNTAX     SEQUENCE OF AtmIfVccTmOperEntry
   ACCESS     not-accessible
   STATUS     mandatory
   DESCRIPTION
     "This group contains attributes for the Tm component to reflect 
      operational traffic attributes."
::= { atmIfVccTm 100 }

atmIfVccTmOperEntry OBJECT-TYPE
   SYNTAX     AtmIfVccTmOperEntry
   ACCESS     not-accessible
   STATUS     mandatory
   DESCRIPTION
     "An entry in the atmIfVccTmOperTable."
   INDEX {
      atmIfIndex,
      atmIfVccIndex,
      atmIfVccTmIndex }
::= { atmIfVccTmOperTable 1 }

AtmIfVccTmOperEntry ::= SEQUENCE {
   atmIfVccTmTxTrafficDescType
      INTEGER,
   atmIfVccTmTxQosClass
      INTEGER,
   atmIfVccTmTxQueueLength
      Unsigned32,
   atmIfVccTmTxQueueCongestionState
      Unsigned32,
   atmIfVccTmHoldingPriority
      INTEGER,
   atmIfVccTmRxTrafficDescType
      INTEGER,
   atmIfVccTmRxQosClass
      INTEGER,
   atmIfVccTmAtmServiceCategory
      INTEGER,
   atmIfVccTmTrafficShaping
      INTEGER,
   atmIfVccTmBearerClassBbc
      INTEGER,
   atmIfVccTmTransferCapabilityBbc
      INTEGER,
   atmIfVccTmClippingBbc
      INTEGER,
   atmIfVccTmUnshapedTransmitQueueing
      INTEGER,
   atmIfVccTmBestEffort
      INTEGER,
   atmIfVccTmForceTagging
      INTEGER,
   atmIfVccTmWeight
      Unsigned32,
   atmIfVccTmUsageParameterControl
      INTEGER,
   atmIfVccTmTxPacketWiseDiscard
      OCTET STRING,
   atmIfVccTmRxPacketWiseDiscard
      OCTET STRING,
   atmIfVccTmBandwidthElastic
      INTEGER,
   atmIfVccTmBandwidthReduction
      Unsigned32,
   atmIfVccTmAbrConnectionType
      INTEGER }

atmIfVccTmTxTrafficDescType OBJECT-TYPE
   SYNTAX     INTEGER  {
                 n1(1),
                 n2(2),
                 n3(3),
                 n4(4),
                 n5(5),
                 n6(6),
                 n7(7),
                 n8(8),
                 n9(9) }
   ACCESS     read-only
   STATUS     mandatory
   DESCRIPTION
     "T his attribute indicates the type of traffic management which is 
      applied to the transmit direction of this connection as defined in the 
      ATM Forum. The txTrafficDescType determines the number and 
      meaning of the parameters in the txTrafficDescParm attribute."
::= { atmIfVccTmOperEntry 10 }

atmIfVccTmTxQosClass OBJECT-TYPE
   SYNTAX     INTEGER  {
                 n0(0),
                 n1(1),
                 n2(2),
                 n3(3),
                 n4(4),
                 notApplicable(14) }
   ACCESS     read-only
   STATUS     mandatory
   DESCRIPTION
     "This attribute indicates the quality of service for the calling to called 
      direction for this connection. This is only applicable to Soft PVC 
      and SVC connections. 
      
      Class 1 supports a QOS that meets Service Class A performance 
      requirements (Circuit emulation, constant bit rate video).
      
      Class 2 supports a QOS that meets Service Class B performance 
      requirements (Variable bit rate audio and video).
      
      Class 3 supports a QOS that meets Service Class C performance 
      requirements (Connection-Oriented Data Transfer).
      
      Class 4 supports a QOS that meets Service Class D performance 
      requirements (Connectionless Data Transfer).
      
      Class 0 is the unspecified QOS class; no objective is specified for 
      the performance parameters.
      
      A value of notApplicable is displayed in the case of nailed-up PVCs 
      for which this attribute has no significance."
::= { atmIfVccTmOperEntry 31 }

atmIfVccTmTxQueueLength OBJECT-TYPE
   SYNTAX     Unsigned32 (0..30720)
   ACCESS     read-only
   STATUS     mandatory
   DESCRIPTION
     "This attribute indicates the current number of cells in the transmit 
      queue for this connection. 
      
      If this connection has unshapedTransmitQueueing attribute 
      displayed as common, this attribute displays the length of the 
      common queue which is used for this atm service category. 
      
      If this connection has unshapedTransmitQueueing attribute 
      displayed as fifo, this attribute indicates the number of cells for this 
      connection which are enqueued in a first-in-first-out queuing 
      method for this atm service category. This will only occur for 
      connections on ATM IP cards with atmServiceCategory of nrtVbr 
      or ubr. 
      
      If this connection has unshapedTransmitQueueing attribute 
      displayed as perVc or as notApplicable, this attribute displays the 
      length of the per-VC queue.
      
      This attribute does not apply to basic Vpts."
::= { atmIfVccTmOperEntry 32 }

atmIfVccTmTxQueueCongestionState OBJECT-TYPE
   SYNTAX     Unsigned32 (0..3)
   ACCESS     read-only
   STATUS     mandatory
   DESCRIPTION
     "This attribute indicates the congestion state of the transmit queue 
      for this connection. 
      
      If this connection has unshapedTransmitQueueing attribute 
      displayed as common, this attribute displays the congestion state of 
      the common queue. If this connection has 
      unshapedTransmitQueueing attribute displayed as perVc or as 
      notApplicable, this attribute displays the congestion state of the per-
      VC queue.
      
      The congestion state of a queue is indicated by a numeric value 
      ranging from 0 to 3. When a queue is in a congested state x, only 
      traffic with discard priority (DP) 0 to x are enqueued. Traffic with 
      DP > x is discarded. 
      
      For example, if the congestion state is 3, there is no congestion and 
      all traffic is enqueued. Likewise, when the congestion state is 0, 
      there is maximum congestion and only traffic with DP=0 is 
      enqueued on that queue.
      
      This attribute does not apply to basic Vpts."
::= { atmIfVccTmOperEntry 33 }

atmIfVccTmHoldingPriority OBJECT-TYPE
   SYNTAX     INTEGER  {
                 n0(0),
                 n1(1),
                 n2(2),
                 n3(3),
                 n4(4),
                 notApplicable(6) }
   ACCESS     read-only
   STATUS     mandatory
   DESCRIPTION
     "This attribute indicates the actual holding priority in effect for this 
      connection. In a situation where the link bandwidth fluctuates, such 
      as over an IMA link, holding priority is used to determine which 
      connections are held and which are released. Holding priority 4 
      connections are the first to be released. Holding priority 0 
      connections are the last to be released. Some applications, for 
      example Vcc Test, may override the provisioned holding priority. 
      
      A value of notApplicable is displayed when this is an elastic 
      connection. Holding priority does not apply to bandwidth elastic 
      connections.
      
      Holding priority has no effect if the equivalent cell rate (ECR) for a 
      connection is zero.
      
      This attribute does not apply to Vpt Vccs."
::= { atmIfVccTmOperEntry 35 }

atmIfVccTmRxTrafficDescType OBJECT-TYPE
   SYNTAX     INTEGER  {
                 n1(1),
                 n2(2),
                 n3(3),
                 n4(4),
                 n5(5),
                 n6(6),
                 n7(7),
                 n8(8),
                 n9(9) }
   ACCESS     read-only
   STATUS     mandatory
   DESCRIPTION
     "This attribute indicates the type of traffic management which is 
      applied to the receive direction of this connection as defined in the 
      ATM Forum. The rxTrafficDescType determines the number and 
      meaning of the parameters in the rxTrafficDescParm attribute."
::= { atmIfVccTmOperEntry 40 }

atmIfVccTmRxQosClass OBJECT-TYPE
   SYNTAX     INTEGER  {
                 n0(0),
                 n1(1),
                 n2(2),
                 n3(3),
                 n4(4),
                 notApplicable(14) }
   ACCESS     read-only
   STATUS     mandatory
   DESCRIPTION
     "This attribute indicates the quality of service for the called to calling 
      direction for this connection. This is only applicable to Soft PVC 
      and SVC connections. 
      
      Class 1 supports a QOS that meets Service Class A performance 
      requirements (circuit emulation, constant bit rate video).
      
      Class 2 supports a QOS that meets Service Class B performance 
      requirements (variable bit rate audio and video).
      
      Class 3 supports a QOS that meets Service Class C performance 
      requirements (Connection-Oriented Data Transfer).
      
      Class 4 supports a QOS that meets Service Class D performance 
      requirements (Connectionless Data Transfer).
      
      Class 0 is the unspecified QOS class; no objective is specified for 
      the performance parameters.
      
      A value of notApplicable is displayed in the case of nailed-up PVCs 
      for which this attribute has no significance."
::= { atmIfVccTmOperEntry 61 }

atmIfVccTmAtmServiceCategory OBJECT-TYPE
   SYNTAX     INTEGER  {
                 unspecifiedBitRate(0),
                 constantBitRate(1),
                 rtVariableBitRate(2),
                 nrtVariableBitRate(3),
                 availableBitRate(4) }
   ACCESS     read-only
   STATUS     mandatory
   DESCRIPTION
     "This attribute indicates the ATM service category used for traffic in 
      both directions of the connection. This attribute does not apply to 
      Virtual Link VPTs and will always be displayed as 
      constantBitRate.
      
      The constantBitRate service category is intended for real time 
      applications, that is, those requiring tightly constrained delay and 
      delay variation, as would be appropriate for voice and video 
      applications. The consistent availability of a fixed quantity of 
      bandwidth is considered appropriate for CBR service. Cells which 
      are delayed beyond the value specified by Cell Transfer Delay are 
      assumed to have significantly reduced value for the application.
      
      The rtVariableBitRate service category is intended for real time 
      applications; that is those requiring tightly constrained delay and 
      delay variation, as would be appropriate for voice and video 
      applications. Sources are expected to transmit at a rate which varies 
      with time. Equivalently, the source can be described as 'bursty'. 
      Cells which are delayed beyond the value specified by Cell Transfer 
      Delay are assumed to be of significantly reduced value to the 
      application. Real time VBR service may support statistical 
      multiplexing of real time sources.
      
      The nrtVariableBitRate service category is intended for non-real 
      time applications which have bursty traffic characteristics and which 
      can be characterized in terms of a PCR, SCR, and MBS. For those 
      cells which are transferred within the traffic contract, the application 
      expects a low cell loss ratio. For all connections, it expects a bound 
      on the mean cell transfer delay. Non-real time VBR service may 
      support statistical multiplexing of connections.
      
      The availableBitRate service is an ATM layer service category for 
      which the limiting ATM layer transfer characteristics provided by 
      the network may change subsequent to connection establishment. 
      ABR service has a flow control mechanism which supports several 
      types of feedback to control the source rate in response to changing 
      ATM layer transfer characteristics. ABR service is not intended to 
      support real-time applications.
      
      The unspecifiedBitRate service is intended for non-real time 
      applications, that is those not requiring tightly constrained delay 
      and delay variation. UBR sources are expected to be bursty. UBR 
      service supports a high degree of statistical multiplexing among 
      sources. UBR service does not specify traffic related service 
      guarantees. No numerical commitments are made with respect to 
      the cell loss ratio experienced by a UBR connection, or as to the 
      cell transfer delay experienced by cells on the connection."
::= { atmIfVccTmOperEntry 62 }

atmIfVccTmTrafficShaping OBJECT-TYPE
   SYNTAX     INTEGER  {
                 disabled(1),
                 notApplicable(4),
                 linear(5),
                 inverseUpc(6),
                 dynamic(7) }
   ACCESS     read-only
   STATUS     mandatory
   DESCRIPTION
     "This attribute indicates the traffic shaping state of the connection.
      
      A value of notApplicable indicates that traffic shaping is not 
      applicable or not supported for this connection. This is the case:
      - when the txTrafficDescType is 1 or 2.
      - for standard Vpt Vccs and basic Vpts.
      - for CQC-based ATM cards, when the atmServiceCategory is 
      constantBitRate.
      
      In these cases, the value of notApplicable is set regardless of 
      whether traffic shaping is enabled or disabled in the provisioning 
      data.
      
      A value of disabled indicates that traffic shaping is applicable and 
      supported for the type of connection but has been turned off in the 
      provisioning data.
      
      A value of linear or inverseUpc indicates that traffic shaping is 
      applicable and supported for the type of connection and has been 
      turned on in the provisioning data. This is the only case that 
      indicates that traffic shaping is performed on the connection. In this 
      case, the actual shaping rate is reflected in the txTrafficDescParm 
      attribute, parameter number 4. A value of linear indicates that 
      traffic is being shaped at the constant rate indicated in 
      txTrafficDescParm 4.
      
      A value of inverseUpc is possible only on ATM IP cards. This value 
      indicates that the shaper strictly conforms to the requirements of a 
      dual leaky bucket UPC enforcer. This value is indicated if traffic 
      shaping is enabled, and the txTrafficDescType for this connection is 
      6, 7 or 8.
      
      Traffic shaping for connections with atmServiceCategory as 
      availableBitRate (txTrafficDescType 9) depends upon the 
      abrConnectionType attribute. If abrConnectionType is sourceDest 
      or virtualSourceDest, the value of this attribute is dynamic. If 
      abrConnectionType is erSwitch or efciSwitch, this attribute is 
      notApplicable."
::= { atmIfVccTmOperEntry 70 }

atmIfVccTmBearerClassBbc OBJECT-TYPE
   SYNTAX     INTEGER  {
                 a(1),
                 c(3),
                 x(16),
                 vp(24),
                 notApplicable(30) }
   ACCESS     read-only
   STATUS     mandatory
   DESCRIPTION
     "This attribute indicates the bearer capability for this connection.
      
      Class a service is a connection-oriented, constant bit rate ATM 
      transport service. Class a service has end to end timing 
      requirements and may require stringent cell loss, cell delay and cell 
      delay variation performance.When a is displayed, the user is 
      requesting more than an ATM only service. The network may look 
      at the AAL to provide interworking based upon its contents. 
      
      Class c service is a connection-oriented, variable bit rate ATM 
      transport service. Class c service has no end-to-end timing 
      requirements.When c is displayed, the user is requesting more than 
      an ATM only service. The network interworking function may look 
      at the AAL and provide service based on it.
      
      Class x service is a connection-oriented ATM transport service 
      where the AAL, trafficType (cbr or vbr), and timing requirements 
      are user defined (that is, transparent to the network). When the 
      value of this attribute is x, the user is requesting an ATM only 
      service from the network. In this case, the network shall not process 
      any higher layer protocol.
      
      Class vp service is used to indicate a transparent VP service when 
      the user is requesting an ATM only service from the network. In this 
      case, the network does not process any higher layer protocol. This 
      service differs from class x service in that with the class vp service 
      both the VCI field (except for VCI values 0, 3, 4, and 6 through 15) 
      and Payload Type field are transported transparently by the network. 
      This attribute value is only applicable to SPVP and SVP 
      connections.
      
      A value of notApplicable is displayed in the case of nailed-up PVCs 
      for which this attribute has no significance."
::= { atmIfVccTmOperEntry 71 }

atmIfVccTmTransferCapabilityBbc OBJECT-TYPE
   SYNTAX     INTEGER  {
                 n0(0),
                 n1(1),
                 n2(2),
                 n5(5),
                 n8(8),
                 n9(9),
                 n10(10),
                 notApplicable(30) }
   ACCESS     read-only
   STATUS     mandatory
   DESCRIPTION
     "This attribute indicates the transfer capability for this connection. 
      Uni 3.0/3.1 traffic type and end-to-end timing parameters are 
      mapped into this parameter as follows:
      <transferCapability: TrafficType, Timing>
      0: NoIndication, NoIndication
      1: NoIndication, yes
      2: NoIndication, no
      5: CBR, yes
      8: VBR, NoIndication
      9: VBR, yes
      10: VBR, no
      
      A value of notApplicable is displayed in the case of nailed-up PVCs 
      for which this attribute has no significance, or in the case that the 
      transfer capability in the call request was set to NoIndication.
      
      The CBR traffic type refers to traffic offered on services such as a 
      constant bit rate video service or a circuit emulation.
      
      The VBR traffic type refers to traffic offered on services such as 
      packetized audio and video, or data.
      
      The value NoIndication for traffic type is used if the user has not set 
      the traffic type; similarly for end-to-end timing.
      
      The value yes for end-to-end timing indicates that end-to-end 
      timing is required for the connection.
      
      The value no for end-to-end timing indicates that end-to-end timing 
      is not required for the connection."
::= { atmIfVccTmOperEntry 72 }

atmIfVccTmClippingBbc OBJECT-TYPE
   SYNTAX     INTEGER  {
                 no(0),
                 yes(1),
                 notApplicable(14) }
   ACCESS     read-only
   STATUS     mandatory
   DESCRIPTION
     "This attribute indicates the value of the clipping susceptibility 
      parameter in the broadband bearer capability (BBC) Information 
      Element.
      
      Clipping is an impairment in which the first fraction of a second of 
      information to be transferred is lost. It occurs after a call is 
      answered and before an associated connection is switched through.
      
      A value of notApplicable is displayed in the case of nailed-up PVCs 
      for which this attribute has no significance."
::= { atmIfVccTmOperEntry 74 }

atmIfVccTmUnshapedTransmitQueueing OBJECT-TYPE
   SYNTAX     INTEGER  {
                 perVc(0),
                 common(1),
                 notApplicable(4),
                 fifo(5) }
   ACCESS     read-only
   STATUS     mandatory
   DESCRIPTION
     "This attribute indicates the unshaped transmit queuing state of the 
      connection.
      
      A value of common indicates that transmit traffic is being enqueued 
      onto the common transmit queue for this service category. 
      The txQueueLength attribute indicates the current length of the 
      common transmit queue.
      
      A value of fifo indicates that transmit traffic is being queued in a 
      first-in-first-out basis for this service category. This is similar to 
      common queueing, but the txQueueLength attribute indicates the 
      number of cells in this connection queue. A value of fifo will only 
      be indicated for connections on ATM IP cards with 
      atmServiceCategory of nrtVbr or ubr. 
      A value of perVc indicates that transmit traffic is being enqueued 
      onto a per-VC queue for this connection.
      
      A value of notApplicable indicates that transmit traffic is being 
      shaped for this connection, or that unshaped transmit queuing is not 
      applicable for this type of connection. Transmit traffic for a shaped 
      connection is enqueued onto a per-VC queue, but this attribute is 
      only applicable for unshaped connections. Unshaped transmit 
      queuing is not applicable for basic Vpts."
::= { atmIfVccTmOperEntry 75 }

atmIfVccTmBestEffort OBJECT-TYPE
   SYNTAX     INTEGER  {
                 indicated(0),
                 notIndicated(1),
                 notApplicable(14) }
   ACCESS     read-only
   STATUS     mandatory
   DESCRIPTION
     "This attribute indicates value of best effort parameter in the ATM 
      Traffic Descriptor Information Element.
      
      The value indicated implies that the quality of service for this 
      connection is not guaranteed.
      
      The value notIndicated implies that the quality of service for this 
      connection is guaranteed.
      
      A value of notApplicable is displayed in the case of nailed-up PVCs 
      for which this attribute has no significance."
::= { atmIfVccTmOperEntry 76 }

atmIfVccTmForceTagging OBJECT-TYPE
   SYNTAX     INTEGER  {
                 enabled(0),
                 disabled(1) }
   ACCESS     read-only
   STATUS     mandatory
   DESCRIPTION
     "This attribute indicates the state of force tagging option for this 
      connection. Force tagging refers to setting the CLP bit for all cells 
      on a connection. 
      
      For CQC-based ATM cards, this attribute is not applicable and is 
      not displayed.
      
      A value of enabled indicates that the CLP bit is being set to 1 for all 
      cells in the transmit direction on this connection. 
      
      A value of disabled indicates that the CLP bit is unchanged for cells 
      in the transmit direction on this connection. disabled is always 
      displayed for Vpts since forced tagging is applied on a per Vpt Vcc 
      basis."
::= { atmIfVccTmOperEntry 78 }

atmIfVccTmWeight OBJECT-TYPE
   SYNTAX     Unsigned32 (0 | 1..4095 | 65534)
   ACCESS     read-only
   STATUS     mandatory
   DESCRIPTION
     "This attribute indicates the relative weight of this unshaped 
      connection. Connections with a larger weight get a larger proportion 
      of the link bandwidth, or in the case of standard Vpt Vccs, the Vpt 
      bandwidth. 
      
      For all but standard Vpt Vccs, the default connection weight is 
      determined by the weight policy for a service category and the 
      traffic descriptor for a connection. For standard Vpt Vccs, the 
      default connection weight is determined by the Vcc's service 
      category.
      
      For CQC-based ATM cards, this attribute is not applicable and is 
      not displayed.
      
      A value from 1 to 4095 indicates an actual weight. The value 
      upToQueueLimit indicates that the weight of a connection is up to 
      the transmit queue limit for this connection. upToQueueLimit is 
      used with common (first-in-first-out) queueing. 
      
      This attribute is displayed as notApplicable if:
      - this connection has trafficShaping displayed as linear or 
      inverseUpc.
      - this is a basic Vpt.

      VALUES (

      0 = upToQueueLimit

      65534 = notApplicable

      )"
::= { atmIfVccTmOperEntry 79 }

atmIfVccTmUsageParameterControl OBJECT-TYPE
   SYNTAX     INTEGER  {
                 enforced(0),
                 disabled(1),
                 notApplicable(3),
                 monitored(4),
                 abrMonitored(5),
                 abrEnforced(6) }
   ACCESS     read-only
   STATUS     mandatory
   DESCRIPTION
     "This attribute indicates the UPC state of the connection.
      
      A value of notApplicable indicates that UPC is not applicable or not 
      supported for the connection. This is the case:
      - when the connection's rxTrafficDescType is 1 or 2. 
      - for standard Vpt Vccs and basic Vpts.
      
      A value of notApplicable is set regardless of whether UPC is 
      disabled or enabled in provisioning data.
      
      A value of disabled indicates that UPC is applicable and supported 
      for the type of connection but has been turned off in the 
      provisioning data.
      
      A value of enforced indicates that UPC is actively checking 
      conformance for the connection and is discarding or tagging cells 
      which do not conform to the connection traffic contract. The traffic 
      descriptor parameters used for UPC conformance are reflected in 
      the rxTrafficDescParms of the connection. On ATM IP cards, the 
      counts of UPC violations are visible in the Vcc, Vpc, or Vpt 
      rxUpcViolationsOnEnforcer1 or rxUpcViolationsOnEnforcer2 
      attributes. 
      
      ATM IP cards provide the ability to monitor UPC violations without 
      tagging or discarding. A value of monitored indicates that UPC is 
      actively checking conformance for the connection and counting the 
      violations, but is not discarding or tagging cells which do not 
      conform to the connection traffic contract. The traffic descriptor 
      parameters used for UPC conformance are reflected in the 
      rxTrafficDescParms of the connection. The counts of UPC 
      violations are visible in the Vcc, Vpc, or Vpt 
      rxUpcViolationsOnEnforcer1 or rxUpcViolationsOnEnforcer2 
      attributes. The value of monitored appears only on ATM IP cards. 
      
      If the atmServiceCategory for this connection indicates 
      availableBitRate, a value of abrEnforced indicates that Dynamic 
      Generic Cell Rate Algorithm (DGCRA) is active for the connection 
      and that violating cells are discarded. The cell rate which is in effect 
      at any particular instant is indicated in rxTrafficDescParm 4 of the 
      connection. 
      
      If the atmServiceCategory for this connection indicates 
      availableBitRate, a value of abrMonitored indicates that Dynamic 
      Generic Cell Rate Algorithm (DGCRA) is active for the connection 
      but that violating cells are counted only. The cell rate which is in 
      effect at any particular instant is indicated in rxTrafficDescParm 4 
      of the connection."
::= { atmIfVccTmOperEntry 80 }

atmIfVccTmTxPacketWiseDiscard OBJECT-TYPE
   SYNTAX     OCTET STRING (SIZE (1))
   ACCESS     read-only
   STATUS     mandatory
   DESCRIPTION
     "This attribute indicates the current set of packet-wise discard 
      functions in effect in the transmit data direction at this connection 
      point.
      
      A value of ppd indicates that the Partial Packet Discard (PPD) 
      function is in effect. PPD may be applied at an intermediate 
      connecting point for a connection which is transporting frame traffic 
      (AAL5 at the endpoint). PPD is controlled by provisioning for 
      PVCs and SPVCs, and by call setup parameters in the AAL and 
      Traffic Descriptor Information Elements.
      
      A value of epd indicates that the Early Packet Discard (EPD) 
      function is in effect at this connection endpoint. On CQC-based 
      ATM cards, PPD and EPD are enabled by default at a connection 
      endpoint which is performing AAL5 segmentation and assembly.
      
      A value of wred indicates that Weighted Random Early Detection is 
      in effect at this connection point. W-RED can be enabled by 
      provisioning for PVCs and SPVCs.
      
      On ATM IP cards, all packet-wise discard functions also apply to 
      provisioned virtual path connections (VPCs). On CQC-based ATM 
      cards, packet-wise functions are not applicable for VPCs.
      
      This attribute is not applicable for Vpts.

      Description of bits:
      ppd(0)
      epd(1)
      wred(2)"
::= { atmIfVccTmOperEntry 85 }

atmIfVccTmRxPacketWiseDiscard OBJECT-TYPE
   SYNTAX     OCTET STRING (SIZE (1))
   ACCESS     read-only
   STATUS     mandatory
   DESCRIPTION
     "This attribute indicates the current set of packet-wise discard 
      functions in effect in the receive data direction at this connection 
      point.
      
      A value of ppd indicates that the Partial Packet Discard (PPD) 
      function is in effect. PPD may be applied at an intermediate 
      connecting point for a connection which is transporting frame traffic 
      (AAL5 at the endpoint). PPD is controlled by provisioning for 
      PVCs and SPVCs, and by call setup parameters in the AAL and 
      Traffic Descriptor Information Elements.
      
      A value of epd indicates that the Early Packet Discard (EPD) 
      function is in effect at this connection endpoint. PPD and EPD are 
      enabled by default at a connection endpoint which is performing 
      AAL5 segmentation and assembly.
      
      On ATM IP cards, all packet-wise discard functions also apply to 
      provisioned virtual path connections (VPCs). On CQC-based ATM 
      cards, packet-wise functions are not applicable for VPCs.
      
      This attribute is not applicable for Vpts.

      Description of bits:
      ppd(0)
      epd(1)"
::= { atmIfVccTmOperEntry 86 }

atmIfVccTmBandwidthElastic OBJECT-TYPE
   SYNTAX     INTEGER  {
                 no(0),
                 yes(1) }
   ACCESS     read-only
   STATUS     mandatory
   DESCRIPTION
     "This attribute is only of importance for connections which are 
      carried on a link with a variable bandwidth. For example, the 
      bandwidth may be reduced in the event that one or more physical 
      links in the IMA group fail, such that the originally requested 
      bandwidth cannot be maintained. This attribute shows whether the 
      application (for example, Trunk) running on this connection can 
      continue to operate if the bandwidth is reduced. If the bandwidth is 
      reduced, the amount by which it is reduced is displayed in the 
      bandwidthReduction attribute. 
      
      A value of yes, indicates that this connection is elastic, and the 
      bandwidth may be reduced but the connection is not released. 
      
      A value of no indicates that the bandwidth for this connection is not 
      reduced in the event of link bandwidth reduction. However, this 
      connection may be released based on its holdingPriority.
      
      Bandwidth elasticity has no effect for connections which have an 
      equivalent cell rate (ECR) of zero. 
      
      This attribute is not applicable for Vpts and Vpt Vccs."
::= { atmIfVccTmOperEntry 90 }

atmIfVccTmBandwidthReduction OBJECT-TYPE
   SYNTAX     Unsigned32 (0..2147483647)
   ACCESS     read-only
   STATUS     mandatory
   DESCRIPTION
     "This attribute shows the amount by which the bandwidth has been 
      reduced for this connection. This value is non-zero only for 
      connections which have bandwidthElastic displayed as yes, and 
      which are also operating in a reduced bandwidth mode. This is 
      typically the case for selected connections running over an IMA 
      link. This attribute takes a value from 0 (no reduction) up to the 
      ECR. For all connections which are running at their full allocated 
      bandwidth, bwReduction has the value 0. Connections which have 
      been reduced in allocated bandwidth have a positive number for this 
      attribute. The bwReduction may be subtracted from the ECR (which 
      is displayed as txTrafficDescParm 5) to determine the actual 
      bandwidth allocated to this connection."
::= { atmIfVccTmOperEntry 100 }

atmIfVccTmAbrConnectionType OBJECT-TYPE
   SYNTAX     INTEGER  {
                 erSwitch(1),
                 efciSwitch(2),
                 virtualSourceDest(3),
                 sourceDest(4),
                 nonAbrInterworking(5),
                 notApplicable(15) }
   ACCESS     read-only
   STATUS     mandatory
   DESCRIPTION
     "This attribute indicates the type of ABR behavior which is in effect 
      at this connection. This attribute is only applicable if the 
      atmServiceCategory attribute is availableBitRate. If the 
      atmServiceCategory attribute is not availableBitRate, or if the 
      connection is not active, this attribute value is displayed as 
      notApplicable.
      
      For CQC-based ATM cards, the only possible values are 
      notApplicable, efciSwitch or nonAbrInterworking. In EFCI 
      marking mode, the Explicit Forward Congestion Indication (EFCI) 
      field in the data cell headers is used to indicate transmit queue 
      congestion. 
      
      For ATM IP cards, if the connectionPointType is displayed as 
      connectionEndPoint, this attribute has the value sourceDest. In this 
      mode, the ABR Source and Destination behavior is in effect at this 
      connection. This attribute is also sourceDest in the case where the 
      next hop connection is specified as nonAbrInterworking. The next 
      hop connection is the Vcc or Vpc identified by the nextHop attribute 
      of the Nrp or Rp component. 
      
      If the connectionPointType is not connectionEndPoint, the value of 
      this attribute depends upon the abrConnectionType provisioning 
      and the card type to which the traffic is forwarded on the backplane. 
      The default abrConnectionType is provisioned at the CA Abr 
      abrConnectionType attribute, and may be overridden for a 
      provisioned connection in the Vcd Tm abrConnectionType or Vpd 
      Tm abrConnectionType attribute. If the CA Abr abrConnectionType 
      attribute is virtualSourceDest at either one of the two connection 
      points, and if both the connection points are defined on ATM IP 
      cards, virtual source and destination behavior is applied to the 
      connection. In this instance, the attribute displays the value 
      virtualSourceDest.
      
      This attribute has the value erSwitch if ABR explicit rate 
      functionality is in effect at this connection. In this mode, the switch 
      may modify the Explicit Rate (ER) field of backward Resource 
      Management (RM) cells to indicate the status of congestion at this 
      connection point.
      
      This attribute has the value nonAbrInterworking in the case where 
      this connection point is functioning as an SPVC origin for an ABR 
      connection where the link side of this connection is configured as a 
      non-ABR ATM service category. This means that there are no RM 
      cells on the link side of this connection, and that the next hop 
      connection point is performing as an ABR sourceDest."
::= { atmIfVccTmOperEntry 110 }

atmIfVccTmTxTdpTable OBJECT-TYPE
   SYNTAX     SEQUENCE OF AtmIfVccTmTxTdpEntry
   ACCESS     not-accessible
   STATUS     mandatory
   DESCRIPTION
     "This attribute is a vector of five transmit traffic parameters whose 
      mapping is defined by the txTrafficDescType attribute. 
      
      The values of peak cell rate (PCR), sustained cell rate (SCR), 
      Minimum Cell Rate (MCR), actual cell rate (ACR), explicit rate 
      (ER), equivalent cell rate (ECR), and actual shaping rate are 
      expressed in cell/s. Maximum burst size (MBS) is expressed in 
      cells. CDVT is expressed in microseconds. 
      
      When txTrafficDescType is 1 or 2, parameters 1 through 5 are 
      unused.
      
      In this description, PCR is the greater of either the PCR or the 
      requested shaping rate (parameter 1 or parameter 5) specified in the 
      txTrafficDescParm attribute under the Vcd Tm or Vpd Tm 
      component.
      
      When txTrafficDescType is 3, parameter 1 represents the PCR for 
      CLP equal to 0 or 1 traffic; parameters 2 and 3 are unused.
      
      When txTrafficDescType is 4, parameter 1 represents the PCR for 
      CLP equal to 0 and 1 traffic; parameter 2 represents the PCR for 
      CLP equal to 0 traffic with cell discard.
      
      When txTrafficDescType is 5, parameter 1 represents the PCR for 
      CLP equal to 0 and 1 traffic; parameter 2 represents the PCR for 
      CLP equal to 0 traffic with cell tagging.
      
      When txTrafficDescType is 6, parameter 1 represents the PCR for 
      CLP equal to 0 and 1 traffic; parameter 2 represents the SCR for 
      CLP equal to 0 and 1 traffic; parameter 3 represents the MBS for 
      CLP equal to 0 and 1 traffic.
      
      When txTrafficDescType is 7, parameter 1 represents the PCR for 
      CLP equal to 0 and 1 traffic; parameter 2 represents the SCR for 
      CLP equal to 0 traffic with cell discard; parameter 3 represents the 
      MBS for CLP equal to 0 traffic.
      
      When txTrafficDescType is 8, parameter 1 represents the PCR for 
      CLP equal to 0 and 1 traffic; parameter 2 represents the SCR for 
      CLP equal to 0 traffic with cell tagging; parameter 3 represents the 
      MBS for CLP equal to 0 traffic.
      
      When txTrafficDescType is 3, 4, 5, 6, 7, or 8, parameter 4 reflects 
      the actual shaping rate in cell/s for this connection. For CQC-based 
      ATM cards, the set of available shaping rates is based on the 
      number of interfaces doing shaping (attribute 
      perVcQueueInterfaces), and the shapingScalingFactor attribute of 
      the Arc Cqc Override component. A rate of zero (0) indicates that 
      shaping is not performed, or that the interface is down. 
      
      When txTrafficDescType is 9, parameter 1 represents the PCR; 
      parameter 2 represents the Cell Delay Variation Toleration (CDVT); 
      parameter 3 represents the Minimum Cell Rate (MCR); the meaning 
      of parameter 4 depends upon the value of the abrConnectionType 
      attribute. if abrConnectionType is sourceDest or 
      virtualSourceDest, parameter 4 represents the Allowed Cell Rate 
      (ACR); If abrConnectionType is erSwitch, parameter 4 represents 
      the Explicit Rate (ER); and if abrConnectionType is efciSwitch, 
      parameter 4 reflects the actual shaping rate in cell/s for this 
      connection.
      
      When txTrafficDescType is 3, 4, 5, 6, 7, 8, or 9, parameter 5 reflects 
      the equivalent cell rate in cell/s for this connection as determined by 
      the Connection Admission Control (CAC) algorithm. The 
      equivalent cell rate is useful in determining the admission 
      characteristics of this connection."
::= { atmIfVccTm 451 }

atmIfVccTmTxTdpEntry OBJECT-TYPE
   SYNTAX     AtmIfVccTmTxTdpEntry
   ACCESS     not-accessible
   STATUS     mandatory
   DESCRIPTION
     "An entry in the atmIfVccTmTxTdpTable."
   INDEX {
      atmIfIndex,
      atmIfVccIndex,
      atmIfVccTmIndex,
      atmIfVccTmTxTdpIndex }
::= { atmIfVccTmTxTdpTable 1 }

AtmIfVccTmTxTdpEntry ::= SEQUENCE {
   atmIfVccTmTxTdpIndex
      Integer32,
   atmIfVccTmTxTdpValue
      Unsigned32 }

atmIfVccTmTxTdpIndex OBJECT-TYPE
   SYNTAX     Integer32 (1..5)
   ACCESS     not-accessible
   STATUS     mandatory
   DESCRIPTION
     "This variable represents the atmIfVccTmTxTdpTable
      specific index for the atmIfVccTmTxTdpTable."
::= { atmIfVccTmTxTdpEntry 1 }

atmIfVccTmTxTdpValue OBJECT-TYPE
   SYNTAX     Unsigned32 (0..2147483647)
   ACCESS     read-only
   STATUS     mandatory
   DESCRIPTION
     "This variable represents an individual value for the
      atmIfVccTmTxTdpTable."
::= { atmIfVccTmTxTdpEntry 2 }

atmIfVccTmTxQThreshTable OBJECT-TYPE
   SYNTAX     SEQUENCE OF AtmIfVccTmTxQThreshEntry
   ACCESS     not-accessible
   STATUS     mandatory
   DESCRIPTION
     "This attribute indicates the queue limit and the discard thresholds 
      for the transmit queue of this connection. 
      
      If this connection has unshapedTransmitQueueing attribute 
      displayed as common, this attribute displays the thresholds of the 
      common queue. If this connection has unshapedTransmitQueueing 
      attribute displayed as perVc or as notApplicable, this attribute 
      displays the thresholds of the per-VC queue.
      
      The first element indicates the queue limit. 
      
      The second element is the threshold that marks the transition from 
      congestion state 1 to congestion state 0. This is the threshold at 
      which traffic with discard priority (DP) = 1 is discarded. This 
      threshold is set at approximately 90 percent of the first parameter, 
      the operational queue limit.
      
      The third element is the threshold that marks the transition from 
      congestion state 2 to congestion state 1. This is the threshold at 
      which traffic with DP = 2 is discarded. This threshold is set at 
      approximately 75 percent of the first parameter, the operational 
      queue limit.
      
      The fourth element is the threshold that marks the transition from 
      congestion state 3 to congestion state 2. This is the threshold at 
      which traffic with DP = 3 is discarded. This threshold is set at 
      approximately 35 percent of the first parameter, the operational 
      queue limit.
      
      This attribute does not apply to basic Vpts."
::= { atmIfVccTm 452 }

atmIfVccTmTxQThreshEntry OBJECT-TYPE
   SYNTAX     AtmIfVccTmTxQThreshEntry
   ACCESS     not-accessible
   STATUS     mandatory
   DESCRIPTION
     "An entry in the atmIfVccTmTxQThreshTable."
   INDEX {
      atmIfIndex,
      atmIfVccIndex,
      atmIfVccTmIndex,
      atmIfVccTmTxQThreshIndex }
::= { atmIfVccTmTxQThreshTable 1 }

AtmIfVccTmTxQThreshEntry ::= SEQUENCE {
   atmIfVccTmTxQThreshIndex
      Integer32,
   atmIfVccTmTxQThreshValue
      Unsigned32 }

atmIfVccTmTxQThreshIndex OBJECT-TYPE
   SYNTAX     Integer32 (0..3)
   ACCESS     not-accessible
   STATUS     mandatory
   DESCRIPTION
     "This variable represents the atmIfVccTmTxQThreshTable
      specific index for the atmIfVccTmTxQThreshTable."
::= { atmIfVccTmTxQThreshEntry 1 }

atmIfVccTmTxQThreshValue OBJECT-TYPE
   SYNTAX     Unsigned32 (0..30720)
   ACCESS     read-only
   STATUS     mandatory
   DESCRIPTION
     "This variable represents an individual value for the
      atmIfVccTmTxQThreshTable."
::= { atmIfVccTmTxQThreshEntry 2 }

atmIfVccTmRxTdpTable OBJECT-TYPE
   SYNTAX     SEQUENCE OF AtmIfVccTmRxTdpEntry
   ACCESS     not-accessible
   STATUS     mandatory
   DESCRIPTION
     "This attribute is a vector of four traffic parameters whose meanings 
      are defined by the rxTrafficDescType attribute. The values of peak 
      cell rate (PCR), sustained cell rate (SCR), minimum cell rate 
      (MCR) are expressed in cell/s. Maximum burst size (MBS) is 
      expressed in cells. Cell delay variation tolerance (CDVT) is 
      expressed in microseconds.
      
      When rxTrafficDescType is 1 or 2, none of the parameters are used.
      
      When rxTrafficDescType is 3, parameter 1 represents the PCR for 
      CLP equal to 0 and 1 traffic; parameter 4 represents the CDVT.
      
      When rxTrafficDescType is 4, parameter 1 represents the PCR for 
      CLP equal to 0 and 1 traffic; parameter 2 represents the PCR for 
      CLP equal to 0 traffic with cell discard; parameter 4 represents the 
      CDVT.
      
      When rxTrafficDescType is 5, parameter 1 represents the PCR for 
      CLP equal to 0 and 1 traffic; parameter 2 represents the PCR for 
      CLP equal to 0 traffic with cell tagging; parameter 4 represents the 
      CDVT.
      
      When rxTrafficDescType is 6, parameter 1 represents the PCR for 
      CLP equal to 0 and 1 traffic; parameter 2 represents the SCR for 
      CLP equal to 0 and 1 traffic; parameter 3 represents the MBS for 
      CLP equal to 0 and 1 traffic; parameter 4 represents the CDVT. 
      
      When rxTrafficDescType is 7, parameter 1 represents the PCR for 
      CLP equal to 0 and 1 traffic; parameter 2 represents the SCR for 
      CLP equal to 0 traffic with cell discard; parameter 3 represents the 
      MBS for CLP equal to 0 traffic; parameter 4 represents the CDVT.
      
      When rxTrafficDescType is 8, parameter 1 represents the PCR for 
      CLP equal to 0 and 1 traffic; parameter 2 represents the SCR for 
      CLP equal to 0 traffic with cell tagging; parameter 3 represents the 
      MBS for CLP equal to 0 traffic; parameter 4 represents the CDVT. 
      
      When rxTrafficDescType is 9, parameter 1 represents the PCR; 
      parameter 2 represents CDVT; parameter 3 represents the MCR; 
      parameter 4 indicates the instantaneous rate at which dynamic 
      generic cell rate algorithm (DGCRA) is in effect. 
      
      If upc is disabled for this connection, the values of PCR, SCR, 
      MBS and CDVT are the provisioned parameters.
      
      If upc is enabled, the values of PCR, SCR, MBS, and CDVT are 
      exactly the values used by the usage parameter control hardware in 
      policing the arriving traffic. These may vary slightly from the 
      provisioned values due to granularity of the hardware. In the case 
      where the PCR is equal to the SCR, the effective MBS is zero."
::= { atmIfVccTm 453 }

atmIfVccTmRxTdpEntry OBJECT-TYPE
   SYNTAX     AtmIfVccTmRxTdpEntry
   ACCESS     not-accessible
   STATUS     mandatory
   DESCRIPTION
     "An entry in the atmIfVccTmRxTdpTable."
   INDEX {
      atmIfIndex,
      atmIfVccIndex,
      atmIfVccTmIndex,
      atmIfVccTmRxTdpIndex }
::= { atmIfVccTmRxTdpTable 1 }

AtmIfVccTmRxTdpEntry ::= SEQUENCE {
   atmIfVccTmRxTdpIndex
      Integer32,
   atmIfVccTmRxTdpValue
      Unsigned32 }

atmIfVccTmRxTdpIndex OBJECT-TYPE
   SYNTAX     Integer32 (1..4)
   ACCESS     not-accessible
   STATUS     mandatory
   DESCRIPTION
     "This variable represents the atmIfVccTmRxTdpTable
      specific index for the atmIfVccTmRxTdpTable."
::= { atmIfVccTmRxTdpEntry 1 }

atmIfVccTmRxTdpValue OBJECT-TYPE
   SYNTAX     Unsigned32 (0..2147483647)
   ACCESS     read-only
   STATUS     mandatory
   DESCRIPTION
     "This variable represents an individual value for the
      atmIfVccTmRxTdpTable."
::= { atmIfVccTmRxTdpEntry 2 }

atmIfVccTmTqpTable OBJECT-TYPE
   SYNTAX     SEQUENCE OF AtmIfVccTmTqpEntry
   ACCESS     not-accessible
   STATUS     mandatory
   DESCRIPTION
     "This attribute is a vector of three elements that indicate the quality 
      of service parameters for the forward direction for this connection. 
      This attribute is used for SPVC and SVC connections on a PNNI 
      interface.
      
      The cdv element indicates the acceptable peak-to-peak Cell Delay 
      Variation (CDV) of real-time connections (CBR and rt-VBR). 
      
      The ctd element indicates the acceptable maximum Cell Transfer 
      Delay (maxCtd) of real-time connections (CBR and rt-VBR). 
      
      The clr element indicates the acceptable Cell Loss Ratio (CLR) of 
      CBR, rt-VBR, and nrt-VBR connections."
::= { atmIfVccTm 454 }

atmIfVccTmTqpEntry OBJECT-TYPE
   SYNTAX     AtmIfVccTmTqpEntry
   ACCESS     not-accessible
   STATUS     mandatory
   DESCRIPTION
     "An entry in the atmIfVccTmTqpTable."
   INDEX {
      atmIfIndex,
      atmIfVccIndex,
      atmIfVccTmIndex,
      atmIfVccTmTqpIndex }
::= { atmIfVccTmTqpTable 1 }

AtmIfVccTmTqpEntry ::= SEQUENCE {
   atmIfVccTmTqpIndex
      INTEGER,
   atmIfVccTmTqpValue
      Unsigned32 }

atmIfVccTmTqpIndex OBJECT-TYPE
   SYNTAX     INTEGER  {
                 cdv(0),
                 ctd(1),
                 clr(2) }
   ACCESS     not-accessible
   STATUS     mandatory
   DESCRIPTION
     "This variable represents the atmIfVccTmTqpTable
      specific index for the atmIfVccTmTqpTable."
::= { atmIfVccTmTqpEntry 1 }

atmIfVccTmTqpValue OBJECT-TYPE
   SYNTAX     Unsigned32 (0..2147483647)
   ACCESS     read-only
   STATUS     mandatory
   DESCRIPTION
     "This variable represents an individual value for the
      atmIfVccTmTqpTable."
::= { atmIfVccTmTqpEntry 2 }

atmIfVccTmRqpTable OBJECT-TYPE
   SYNTAX     SEQUENCE OF AtmIfVccTmRqpEntry
   ACCESS     not-accessible
   STATUS     mandatory
   DESCRIPTION
     "This attribute is a vector of three elements that indicate the quality 
      of service parameters for the backward direction for this 
      connection. This attribute is used for SPVC and SVC connections 
      on a PNNI interface.
      
      The cdv element indicates the acceptable peak-to-peak Cell Delay 
      Variation (CDV) of real-time connections (CBR and rt-VBR). 
      
      The ctd element indicates the acceptable maximum Cell Transfer 
      Delay (maxCtd) of real-time connections (CBR and rt-VBR). 
      
      The clr element indicates the acceptable Cell Loss Ratio (CLR) of 
      CBR, rt-VBR, and nrt-VBR connections."
::= { atmIfVccTm 455 }

atmIfVccTmRqpEntry OBJECT-TYPE
   SYNTAX     AtmIfVccTmRqpEntry
   ACCESS     not-accessible
   STATUS     mandatory
   DESCRIPTION
     "An entry in the atmIfVccTmRqpTable."
   INDEX {
      atmIfIndex,
      atmIfVccIndex,
      atmIfVccTmIndex,
      atmIfVccTmRqpIndex }
::= { atmIfVccTmRqpTable 1 }

AtmIfVccTmRqpEntry ::= SEQUENCE {
   atmIfVccTmRqpIndex
      INTEGER,
   atmIfVccTmRqpValue
      Unsigned32 }

atmIfVccTmRqpIndex OBJECT-TYPE
   SYNTAX     INTEGER  {
                 cdv(0),
                 ctd(1),
                 clr(2) }
   ACCESS     not-accessible
   STATUS     mandatory
   DESCRIPTION
     "This variable represents the atmIfVccTmRqpTable
      specific index for the atmIfVccTmRqpTable."
::= { atmIfVccTmRqpEntry 1 }

atmIfVccTmRqpValue OBJECT-TYPE
   SYNTAX     Unsigned32 (0..2147483647)
   ACCESS     read-only
   STATUS     mandatory
   DESCRIPTION
     "This variable represents an individual value for the
      atmIfVccTmRqpTable."
::= { atmIfVccTmRqpEntry 2 }


-- AtmIf/n Vpc/vpi Tm AvailableBitRate, 
-- AtmIf/n Vcc/vpi.vci Tm AvailableBitRate,
-- AtmIf/n Vpt/vpi Tm AvailableBitRate,
-- AtmIf/n Vpt/vpi Vcc/vci Tm AvailableBitRate
-- This component contains ABR-related operational attributes of a 
-- connection. It is dynamically created for connections where the 
-- atmServiceCategory is availableBitRate, and where 
-- abrConnectionType is sourceDest or virtualSourceDest.

atmIfVccTmAbr OBJECT IDENTIFIER ::= { atmIfVccTm 2 }



atmIfVccTmAbrRowStatusTable OBJECT-TYPE
   SYNTAX     SEQUENCE OF AtmIfVccTmAbrRowStatusEntry
   ACCESS     not-accessible
   STATUS     mandatory
   DESCRIPTION
     "This entry controls the addition and deletion of 
      atmIfVccTmAbr components."
::= { atmIfVccTmAbr 1 }

atmIfVccTmAbrRowStatusEntry OBJECT-TYPE
   SYNTAX     AtmIfVccTmAbrRowStatusEntry
   ACCESS     not-accessible
   STATUS     mandatory
   DESCRIPTION
     "A single entry in the table represents a single 
      atmIfVccTmAbr component."
   INDEX {
      atmIfIndex,
      atmIfVccIndex,
      atmIfVccTmIndex,
      atmIfVccTmAbrIndex }
::= { atmIfVccTmAbrRowStatusTable 1 }

AtmIfVccTmAbrRowStatusEntry ::= SEQUENCE {
   atmIfVccTmAbrRowStatus
      RowStatus,
   atmIfVccTmAbrComponentName
      DisplayString,
   atmIfVccTmAbrStorageType
      StorageType,
   atmIfVccTmAbrIndex
      NonReplicated }

atmIfVccTmAbrRowStatus OBJECT-TYPE
   SYNTAX     RowStatus 
   ACCESS     read-only
   STATUS     mandatory
   DESCRIPTION
     "This variable is used as the basis for SNMP naming of
      atmIfVccTmAbr components.
      These components cannot be added nor deleted."
::= { atmIfVccTmAbrRowStatusEntry 1 }

atmIfVccTmAbrComponentName OBJECT-TYPE
   SYNTAX     DisplayString 
   ACCESS     read-only
   STATUS     mandatory
   DESCRIPTION
     "This variable provides the component's string name for
      use with the ASCII Console Interface"
::= { atmIfVccTmAbrRowStatusEntry 2 }

atmIfVccTmAbrStorageType OBJECT-TYPE
   SYNTAX     StorageType 
   ACCESS     read-only
   STATUS     mandatory
   DESCRIPTION
     "This variable represents the storage type value for the
      atmIfVccTmAbr tables."
::= { atmIfVccTmAbrRowStatusEntry 4 }

atmIfVccTmAbrIndex OBJECT-TYPE
   SYNTAX     NonReplicated 
   ACCESS     not-accessible
   STATUS     mandatory
   DESCRIPTION
     "This variable represents the index for the atmIfVccTmAbr tables."
::= { atmIfVccTmAbrRowStatusEntry 10 }

atmIfVccTmAbrOperTable OBJECT-TYPE
   SYNTAX     SEQUENCE OF AtmIfVccTmAbrOperEntry
   ACCESS     not-accessible
   STATUS     mandatory
   DESCRIPTION
     "This group contains operational attributes for connections using 
      ABR service category."
::= { atmIfVccTmAbr 110 }

atmIfVccTmAbrOperEntry OBJECT-TYPE
   SYNTAX     AtmIfVccTmAbrOperEntry
   ACCESS     not-accessible
   STATUS     mandatory
   DESCRIPTION
     "An entry in the atmIfVccTmAbrOperTable."
   INDEX {
      atmIfIndex,
      atmIfVccIndex,
      atmIfVccTmIndex,
      atmIfVccTmAbrIndex }
::= { atmIfVccTmAbrOperTable 1 }

AtmIfVccTmAbrOperEntry ::= SEQUENCE {
   atmIfVccTmAbrInitialCellRate
      Unsigned32,
   atmIfVccTmAbrTransientBufferExposure
      Unsigned32,
   atmIfVccTmAbrFixedRoundTripTime
      Unsigned32,
   atmIfVccTmAbrRateDecreaseFactor
      Unsigned32,
   atmIfVccTmAbrRateIncreaseFactor
      Unsigned32,
   atmIfVccTmAbrMaxCellPerRmCell
      Unsigned32,
   atmIfVccTmAbrMaxTimeBetweenRmCell
      Unsigned32,
   atmIfVccTmAbrCutoffDecreaseFactor
      Unsigned32,
   atmIfVccTmAbrAcrDecreaseTimeFactor
      Unsigned32,
   atmIfVccTmAbrForwardRmCellLimit
      Unsigned32,
   atmIfVccTmAbrTxRateChangeInfo
      INTEGER,
   atmIfVccTmAbrAcrRateChangeInfo
      INTEGER,
   atmIfVccTmAbrTxFwdRmCells
      Unsigned32,
   atmIfVccTmAbrRxEfci
      INTEGER,
   atmIfVccTmAbrBrmRateChangeInfo
      OCTET STRING,
   atmIfVccTmAbrBrmExplicitRate
      Unsigned32 }

atmIfVccTmAbrInitialCellRate OBJECT-TYPE
   SYNTAX     Unsigned32 (0..16777215)
   ACCESS     read-only
   STATUS     mandatory
   DESCRIPTION
     "This attribute is applicable and is displayed only for connections for 
      which the operational Tm abrConnectionType is displayed as 
      sourceDest or virtualSourceDest. 
      
      This attribute indicates the Initial Cell Rate (ICR) parameter for this 
      connection. ICR is the rate at which a source should send initially 
      and after an idle period.
      
      For nailed-up connections, this attribute is determined by the 
      provisioned value of the initialCellRate attribute. For signalled 
      connections, it is indicated in the ABR Setup Parameters 
      Information Element.
      
      The ICR for a connection is a value between the MCR and the PCR. 
      Furthermore, ICR has an upper bound determined by the 
      transientBufferExposure divided by fixedRoundTripTime."
::= { atmIfVccTmAbrOperEntry 10 }

atmIfVccTmAbrTransientBufferExposure OBJECT-TYPE
   SYNTAX     Unsigned32 (0..16777215)
   ACCESS     read-only
   STATUS     mandatory
   DESCRIPTION
     "This attribute is applicable and is displayed only for connections for 
      which the operational Tm abrConnectionType is displayed as 
      sourceDest or virtualSourceDest. 
      
      This attribute indicates the Transient Buffer Exposure (TBE) for 
      this connection. TBE is the negotiated number of cells that the 
      network would like to limit the resource to send during start-up 
      periods, before the first Resource Management (RM) cell returns.
      
      For nailed-up connections, this attribute is determined by the 
      provisioned value of the transientBufferExposure attribute. For 
      signalled connections, it is indicated in the ABR Setup Parameters 
      Information Element."
::= { atmIfVccTmAbrOperEntry 11 }

atmIfVccTmAbrFixedRoundTripTime OBJECT-TYPE
   SYNTAX     Unsigned32 (0..16700000)
   ACCESS     read-only
   STATUS     mandatory
   DESCRIPTION
     "This attribute is applicable and is displayed only for connections for 
      which the operational Tm abrConnectionType is displayed as 
      sourceDest or virtualSourceDest. 
      
      This attribute indicates the Fixed Round-Trip Time (FRTT) 
      parameter for this connection. FRTT is the sum of the fixed and 
      propagation delays from the source to a destination and back.
      
      For nailed-up connections, this attribute is determined by the 
      provisioned value of the fixedRoundTripTime attribute. For 
      signalled connections, it is indicated in the ABR Setup Parameters 
      Information Element."
::= { atmIfVccTmAbrOperEntry 12 }

atmIfVccTmAbrRateDecreaseFactor OBJECT-TYPE
   SYNTAX     Unsigned32 (0..15)
   ACCESS     read-only
   STATUS     mandatory
   DESCRIPTION
     "This attribute is applicable and is displayed only for connections for 
      which the operational Tm abrConnectionType is displayed as 
      sourceDest or virtualSourceDest. 
      
      This attribute indicates the Rate Decrease Factor (RDF) for this 
      connection. The RDF value is computed by using the operational 
      value of this attribute, n, as 2 to the inverse power n. For example, if 
      the value of this attribute is 8, RDF is 2E-8 = 1/256.
      
      RDF controls the amount by which the cell transmission rate may 
      decrease upon receipt of a backward Resource Management (RM) 
      cell. For example, if a backward RM cell is received with the 
      Congestion Indication (CI) field set to 1, the Allowed Cell Rate 
      (ACR) value would be reduced by the amount (RDF*ACR). The 
      ACR is not allowed to fall below the Minimum Cell Rate (MCR), in 
      which case the ACR is set to MCR.
      
      For nailed-up connections, this attribute is determined by the 
      provisioned value of the rateDecreaseFactor attribute. For signalled 
      connections, it is indicated in the ABR Setup Parameters 
      Information Element."
::= { atmIfVccTmAbrOperEntry 13 }

atmIfVccTmAbrRateIncreaseFactor OBJECT-TYPE
   SYNTAX     Unsigned32 (0..15)
   ACCESS     read-only
   STATUS     mandatory
   DESCRIPTION
     "This attribute is applicable and is displayed only for connections for 
      which the operational Tm abrConnectionType is displayed as 
      sourceDest or virtualSourceDest. 
      
      This attribute indicates the Rate Increase Factor (RIF) for this 
      connection. The RIF value is computed by using the operational 
      value of this attribute, n, as 2 to the inverse power n. For example, if 
      the value of this attribute is 6, RIF is 2E-6 = 1/64.
      
      RIF controls the amount by which the cell transmission rate may 
      increase upon receipt of a backward Resource Management (RM) 
      cell. For example, if a backward RM cell is received with the 
      Congestion Indication (CI) and the No Increase (NI) fields both set 
      to 0, the Allowed Cell Rate (ACR) value would be increased by the 
      amount (RIF*ACR). The ACR is not allowed to exceed the Peak 
      Cell Rate (PCR), in which case the ACR is set to PCR.
      
      For nailed-up connections, this attribute is determined by the 
      provisioned value of the rateIncreaseFactor attribute. For signalled 
      connections, it is indicated in the ABR Setup Parameters 
      Information Element."
::= { atmIfVccTmAbrOperEntry 14 }

atmIfVccTmAbrMaxCellPerRmCell OBJECT-TYPE
   SYNTAX     Unsigned32 (2 | 4 | 8 | 16 | 32 | 64 | 128 | 256)
   ACCESS     read-only
   STATUS     mandatory
   DESCRIPTION
     "This attribute is applicable and is displayed only for connections for 
      which the operational Tm abrConnectionType is displayed as 
      sourceDest or virtualSourceDest. 
      
      This attribute indicates the maximum number of cells an ABR 
      source may transmit for each forward Resource Management (RM) 
      cell. The count of the cells transmitted includes data cells, OAM 
      cells, backward RM cells, and the forward RM cell.
      
      For nailed-up connections, this attribute is determined by the 
      provisioned value of the maxCellsPerRmCell attribute. For 
      signalled connections, it is indicated in the ABR Additional 
      Parameters Information Element."
::= { atmIfVccTmAbrOperEntry 15 }

atmIfVccTmAbrMaxTimeBetweenRmCell OBJECT-TYPE
   SYNTAX     Unsigned32 (781 | 1563 | 3125 | 6250 | 12500 | 25000 | 50000 | 100000)
   ACCESS     read-only
   STATUS     mandatory
   DESCRIPTION
     "This attribute is applicable and is displayed only for connections for 
      which the operational Tm abrConnectionType is displayed as 
      sourceDest or virtualSourceDest. 
      
      This attribute indicates the TRM parameter for this connection.
      
      TRM provides an upper bound on the time interval between forward 
      Resource Management (RM) cells for an ABR source. Since the last 
      forward RM cell was sent, if at least TRM time has elapsed since 
      and at least 2 other cells have been sent, the next cell to be 
      transmitted would be a forward RM cell.
      
      For nailed-up connections, this attribute is determined by the 
      provisioned value of the maxTimeBetweenRmCell attribute. For 
      signalled connections, it is indicated in the ABR Additional 
      Parameters Information Element."
::= { atmIfVccTmAbrOperEntry 16 }

atmIfVccTmAbrCutoffDecreaseFactor OBJECT-TYPE
   SYNTAX     Unsigned32 (0 | 1 | 2 | 4 | 8 | 16 | 32 | 64)
   ACCESS     read-only
   STATUS     mandatory
   DESCRIPTION
     "This attribute is applicable and is displayed only for connections for 
      which the operational Tm abrConnectionType is displayed as 
      sourceDest or virtualSourceDest. 
      
      This attribute indicates the Cutoff Decrease Factor (CDF) parameter 
      for this connection. When the value of this attribute is non-zero, 
      CDF is computed as the inverse of the value. For example, if the 
      value is 32, the value of CDF is 1/32. When the value of this 
      attribute is 0, CDF is also zero.
      
      CDF controls the decrease in the Allowed Cell Rate (ACR) 
      associated with the forwardRmCellLimit attribute, the limit of the 
      number of forward Resource Management (RM) cells which may 
      be sent in the absence of received backward RM cells. When this 
      limit is crossed, the ACR value would be decreased by the amount 
      (CDF*ACR). The ACR is not allowed to fall below the Minimum 
      Cell Rate (MCR), in which case the ACR is set to MCR.
      
      For nailed-up connections, this attribute is determined by the 
      provisioned value of the cutoffDecreaseFactor attribute. For 
      signalled connections, it is indicated in the ABR Additional 
      Parameters Information Element."
::= { atmIfVccTmAbrOperEntry 17 }

atmIfVccTmAbrAcrDecreaseTimeFactor OBJECT-TYPE
   SYNTAX     Unsigned32 (0..1023)
   ACCESS     read-only
   STATUS     mandatory
   DESCRIPTION
     "This attribute is applicable and is displayed only for connections for 
      which the operational Tm abrConnectionType is displayed as 
      sourceDest or virtualSourceDest. 
      
      This attribute indicates the Allowed Cell Rate Decrease Time Factor 
      (ADTF) parameter for this connection.
      
      ADTF is the time interval permitted between sending forward 
      Resource Management (RM) cells before the Allowed Cell Rate 
      (ACR) is decreased to initialCellRate. In other words, if the source 
      does not transit a forward RM cell for the period specified by adtf, it 
      reduces its ACR to the value of its initialCellRate.
      
      For nailed-up connections, this attribute is determined by the 
      provisioned value of the acrDecreaseTimeFactor attribute. For 
      signalled connections, it is indicated in the ABR Additional 
      Parameters Information Element."
::= { atmIfVccTmAbrOperEntry 18 }

atmIfVccTmAbrForwardRmCellLimit OBJECT-TYPE
   SYNTAX     Unsigned32 (1 | 3 | 7 | 15 | 31 | 63 | 127 | 255 | 511 | 1023 | 2047 | 4095)
   ACCESS     read-only
   STATUS     mandatory
   DESCRIPTION
     "This attribute is applicable and is displayed only for connections for 
      which the operational Tm abrConnectionType is displayed as 
      sourceDest or virtualSourceDest. 
      
      This attribute indicates the CRM parameter for this connection.
      
      CRM is the limit of the number of forward Resource Management 
      (RM) cells which may be sent in the absence of received backward 
      RM cells. When this limit is crossed, the Allowed Cell Rate (ACR) 
      value would be decreased by the amount (CDF*ACR), where CDF 
      is determined by the cutoffDecreaseFactor. The ACR is not allowed 
      to fall below the Minimum Cell Rate (MCR), in which case the 
      ACR is set to MCR.
      
      The value of CRM is obtained as transientBufferExposure divided 
      by maxCellsPerRmCell."
::= { atmIfVccTmAbrOperEntry 19 }

atmIfVccTmAbrTxRateChangeInfo OBJECT-TYPE
   SYNTAX     INTEGER  {
                 congestionIndicated(0),
                 noIncreaseIndicated(1),
                 explicitRateIndicated(2) }
   ACCESS     read-only
   STATUS     obsolete
   DESCRIPTION
     "THIS ATTRIBUTE IS HISTORICAL:This attribute indicates the 
      rate change information put into the last forward Resource 
      Management (RM) cell turned around as a backward-RM cell. For 
      connections configured as an ABR Source or Destination, the 
      turned around backward-RM cell is sent over the interface. For 
      connections configured as an ABR Virtual Source or Virtual 
      Destination, the turned around backward-RM cell is sent over the 
      backplane."
::= { atmIfVccTmAbrOperEntry 20 }

atmIfVccTmAbrAcrRateChangeInfo OBJECT-TYPE
   SYNTAX     INTEGER  {
                 noChange(0),
                 decreasedByRdf(1),
                 increasedByRif(2),
                 setToExplicitRate(3),
                 notApplicable(15) }
   ACCESS     read-only
   STATUS     mandatory
   DESCRIPTION
     "This attribute is applicable and is displayed only for connections for 
      which the operational Tm abrConnectionType is displayed as 
      sourceDest or virtualSourceDest. 
      
      This attribute indicates the type of change in the Allowed Cell Rate 
      (ACR) as a result of the information in the last backward Resource 
      Management (B-RM) cell received from the interface.
      
      This attribute value is only applicable when the Vcc Tm or Vpc Tm 
      abrConnectionType attribute is sourceDest or VirtualSourceDest. 
      In all other cases, this attribute value is notApplicable.
      
      A value of noChange indicates that the rate did not change as a 
      result of the last backward RM cell received.
      
      A value of decreasedByRdf or increasedByRif indicates that the 
      ACR was increased or decreased by the corresponding factor. This 
      change is as a result of the CI or NI bit setting in the last backward 
      RM cell, or an ADTF timeout.
      
      A value of setToExplicitRate indicates that the ACR was set to the 
      ER value in the last backward RM cell."
::= { atmIfVccTmAbrOperEntry 21 }

atmIfVccTmAbrTxFwdRmCells OBJECT-TYPE
   SYNTAX     Unsigned32 (0..4095)
   ACCESS     read-only
   STATUS     mandatory
   DESCRIPTION
     "This attribute is applicable and is displayed only for connections for 
      which the operational Tm abrConnectionType is displayed as 
      sourceDest or virtualSourceDest. 
      
      This attribute counts the number of forward Resource Management 
      (RM) cells sent over the interface since the last backward RM-cell 
      was received from the interface. If the value of this attribute is 
      greater than or equal to the value of forwardRmCellLimit, the 
      Allowed Cell Rate (ACR) value would be decreased by the amount 
      (CDF*ACR), where CDF is determined by the 
      cutoffDecreaseFactor.
      
      This counter is reset to zero each time a backward-RM cell is 
      received.
      
      This counter does not wrap to zero if it reaches its maximum value 
      of 4095 in order to indicate that no backward RM cell has been 
      received."
::= { atmIfVccTmAbrOperEntry 22 }

atmIfVccTmAbrRxEfci OBJECT-TYPE
   SYNTAX     INTEGER  {
                 notIndicated(0),
                 indicated(1) }
   ACCESS     read-only
   STATUS     mandatory
   DESCRIPTION
     "This attribute is applicable and is displayed only for connections for 
      which the operational Tm abrConnectionType is displayed as 
      sourceDest or virtualSourceDest. 
      
      This attribute indicates the value of the Explicit Forward 
      Congestion Indication (EFCI) bit of the last data cell received from 
      the interface.
      
      When a forward Resource Management (RM) cell is turned around 
      as a backward-RM cell, the Congestion Indication (CI) field of the 
      backward-RM cell is set to 1, if the value of this attribute is 
      indicated.
      
      This attribute is set to notIndicated each time a backward-RM cell 
      is transmitted."
::= { atmIfVccTmAbrOperEntry 23 }

atmIfVccTmAbrBrmRateChangeInfo OBJECT-TYPE
   SYNTAX     OCTET STRING (SIZE (1))
   ACCESS     read-only
   STATUS     mandatory
   DESCRIPTION
     "This attribute is applicable and is displayed only for connections for 
      which the operational Tm abrConnectionType is displayed as 
      sourceDest, virtualSourceDest or explicitRate. 
      
      This attribute indicates the values of key fields which affect the rate 
      change. These fields are from the most recent Backward Resource 
      Management (B-RM) cell on this connection. These fields may have 
      been set by a connection point at some switch prior to the B-RM 
      cell arriving at this connection point. 
      
      A value of ci indicates that the Congestion Indication (CI) field is 
      set in the B-RM cell. A value of ni indicates that the No Increase 
      (NI) field is set in the B-RM cell. A value of er indicates that a rate 
      decrease is indicated by the Explicit Rate in the B-RM cell having a 
      value lower than the Current Cell Rate (CCR) field in the B-RM 
      cell. The actual explicit rate from the B-RM cell is shown in the 
      brmEr attribute of this component.

      Description of bits:
      ci(0)
      ni(1)
      er(2)"
::= { atmIfVccTmAbrOperEntry 24 }

atmIfVccTmAbrBrmExplicitRate OBJECT-TYPE
   SYNTAX     Unsigned32 (0..16777215)
   ACCESS     read-only
   STATUS     mandatory
   DESCRIPTION
     "This attribute is applicable and is displayed only for connections for 
      which the operational Tm abrConnectionType is displayed as 
      sourceDest, virtualSourceDest or explicitRate. 
      
      This attribute indicates the value of the Explicit Rate field from the 
      most recent Backward Resource Management (B-RM) cell on this 
      connection. This is the rate from the B-RM cell which may be 
      different from the explicit rate (ER) offered at this connection point. 
      Specifically, this attribute may indicate the ER which has been set in 
      the B-RM cell by some connection point before the B-RM cell 
      arrived at this connection point."
::= { atmIfVccTmAbrOperEntry 25 }


-- AtmIf/n NailedUpAccounting
-- This component represents the ATM accounting options for all 
-- nailed up connections (PVCs) on this ATM interface. The 
-- component must be provisioned in order to perform PVC ATM 
-- accounting on this ATM interface.

atmIfNAcct OBJECT IDENTIFIER ::= { atmIf 8 }



atmIfNAcctRowStatusTable OBJECT-TYPE
   SYNTAX     SEQUENCE OF AtmIfNAcctRowStatusEntry
   ACCESS     not-accessible
   STATUS     mandatory
   DESCRIPTION
     "This entry controls the addition and deletion of 
      atmIfNAcct components."
::= { atmIfNAcct 1 }

atmIfNAcctRowStatusEntry OBJECT-TYPE
   SYNTAX     AtmIfNAcctRowStatusEntry
   ACCESS     not-accessible
   STATUS     mandatory
   DESCRIPTION
     "A single entry in the table represents a single 
      atmIfNAcct component."
   INDEX {
      atmIfIndex,
      atmIfNAcctIndex }
::= { atmIfNAcctRowStatusTable 1 }

AtmIfNAcctRowStatusEntry ::= SEQUENCE {
   atmIfNAcctRowStatus
      RowStatus,
   atmIfNAcctComponentName
      DisplayString,
   atmIfNAcctStorageType
      StorageType,
   atmIfNAcctIndex
      NonReplicated }

atmIfNAcctRowStatus OBJECT-TYPE
   SYNTAX     RowStatus 
   ACCESS     read-write
   STATUS     mandatory
   DESCRIPTION
     "This variable is used as the basis for SNMP naming of
      atmIfNAcct components.
      These components can be added and deleted."
::= { atmIfNAcctRowStatusEntry 1 }

atmIfNAcctComponentName OBJECT-TYPE
   SYNTAX     DisplayString 
   ACCESS     read-only
   STATUS     mandatory
   DESCRIPTION
     "This variable provides the component's string name for
      use with the ASCII Console Interface"
::= { atmIfNAcctRowStatusEntry 2 }

atmIfNAcctStorageType OBJECT-TYPE
   SYNTAX     StorageType 
   ACCESS     read-only
   STATUS     mandatory
   DESCRIPTION
     "This variable represents the storage type value for the
      atmIfNAcct tables."
::= { atmIfNAcctRowStatusEntry 4 }

atmIfNAcctIndex OBJECT-TYPE
   SYNTAX     NonReplicated 
   ACCESS     not-accessible
   STATUS     mandatory
   DESCRIPTION
     "This variable represents the index for the atmIfNAcct tables."
::= { atmIfNAcctRowStatusEntry 10 }

atmIfNAcctProvTable OBJECT-TYPE
   SYNTAX     SEQUENCE OF AtmIfNAcctProvEntry
   ACCESS     not-accessible
   STATUS     mandatory
   DESCRIPTION
     "This group contains the provisionable attributes for PVC 
      accounting."
::= { atmIfNAcct 10 }

atmIfNAcctProvEntry OBJECT-TYPE
   SYNTAX     AtmIfNAcctProvEntry
   ACCESS     not-accessible
   STATUS     mandatory
   DESCRIPTION
     "An entry in the atmIfNAcctProvTable."
   INDEX {
      atmIfIndex,
      atmIfNAcctIndex }
::= { atmIfNAcctProvTable 1 }

AtmIfNAcctProvEntry ::= SEQUENCE {
   atmIfNAcctAccountCollection
      OCTET STRING,
   atmIfNAcctAccountConnectionType
      INTEGER,
   atmIfNAcctAccountClass
      Unsigned32,
   atmIfNAcctServiceExchange
      Unsigned32 }

atmIfNAcctAccountCollection OBJECT-TYPE
   SYNTAX     OCTET STRING (SIZE (1))
   ACCESS     read-write
   STATUS     mandatory
   DESCRIPTION
     "This attribute specifies the reason(s) for which accounting data is 
      collected: billing, test, study, audit or force. 
      
      If the set of reasons is not empty then accounting records will be 
      generated by this interface in the following situations:
      - on a TODA (time of day accounting) changeover if TODA is 
      enabled;
      - every 12 hours (per connection) if TODA is disabled;
      - when the PVC is deleted (a call record is generated with final cell 
      counts).
      
      If none of the reasons is present, then accounting will be suppressed 
      for all PVCs on this interface. Accounting can be suppressed on 
      individual PVCs by specifying a null correlationTag attribute in the 
      AtmIf NAcct component.
      
      The reason for collection is recorded in the accounting record, in 
      the attribute callingCollectReason or calledCollectReason, as 
      appropriate.

      Description of bits:
      bill(0)
      test(1)
      study(2)
      audit(3)
      force(4)"
::= { atmIfNAcctProvEntry 1 }

atmIfNAcctAccountConnectionType OBJECT-TYPE
   SYNTAX     INTEGER  {
                 origTerm(0),
                 intermediate(1) }
   ACCESS     read-write
   STATUS     mandatory
   DESCRIPTION
     "This attribute specifies whether accounting records generated for 
      the PVCs on this interface should be marked as originating, 
      terminating or intermediate. This attribute, in combination with the 
      direction of the call, determines the value of attribute 
      connPointType of the accounting record. It may be used by 
      downstream accounting processing to correlate the records.
      
      If the value is origTerm then the value of attribute connPointType 
      in the accounting records generated for incoming calls will be 
      originating and records generated for outgoing calls will be 
      terminating.
      
      If the value is intermediate then the value of attribute 
      connPointType in the accounting records generated for all calls will 
      be intermediate."
   DEFVAL     { origTerm }
::= { atmIfNAcctProvEntry 2 }

atmIfNAcctAccountClass OBJECT-TYPE
   SYNTAX     Unsigned32 (0..255)
   ACCESS     read-write
   STATUS     mandatory
   DESCRIPTION
     "This attribute specifies the accounting class associated with the 
      PVCs on this interface. Its meaning is determined by the network 
      operator.
      
      Its value is recorded in the accounting records generated by this 
      interface, in the attributes, callingServiceType and 
      calledServiceType."
   DEFVAL     { 0 }
::= { atmIfNAcctProvEntry 3 }

atmIfNAcctServiceExchange OBJECT-TYPE
   SYNTAX     Unsigned32 (0..255)
   ACCESS     read-write
   STATUS     mandatory
   DESCRIPTION
     "This attribute specifies the data service exchange associated with 
      this interface. Its meaning is determined by the network operator.
      
      Its value is recorded in the accounting records generated by this 
      interface, in the attributes, callingDse and calledDse."
   DEFVAL     { 0 }
::= { atmIfNAcctProvEntry 4 }


-- AtmIf/n VirtualPathTerminator/vpi
-- This component represents a virtual path terminator (VPT). The 
-- instance value defines the VPI value for this connectionfor 
-- example, Vpt/120 defines a terminator with a VPI of 120.

atmIfVpt OBJECT IDENTIFIER ::= { atmIf 9 }



atmIfVptRowStatusTable OBJECT-TYPE
   SYNTAX     SEQUENCE OF AtmIfVptRowStatusEntry
   ACCESS     not-accessible
   STATUS     mandatory
   DESCRIPTION
     "This entry controls the addition and deletion of 
      atmIfVpt components."
::= { atmIfVpt 1 }

atmIfVptRowStatusEntry OBJECT-TYPE
   SYNTAX     AtmIfVptRowStatusEntry
   ACCESS     not-accessible
   STATUS     mandatory
   DESCRIPTION
     "A single entry in the table represents a single 
      atmIfVpt component."
   INDEX {
      atmIfIndex,
      atmIfVptIndex }
::= { atmIfVptRowStatusTable 1 }

AtmIfVptRowStatusEntry ::= SEQUENCE {
   atmIfVptRowStatus
      RowStatus,
   atmIfVptComponentName
      DisplayString,
   atmIfVptStorageType
      StorageType,
   atmIfVptIndex
      Integer32 }

atmIfVptRowStatus OBJECT-TYPE
   SYNTAX     RowStatus 
   ACCESS     read-write
   STATUS     mandatory
   DESCRIPTION
     "This variable is used as the basis for SNMP naming of
      atmIfVpt components.
      These components can be added and deleted."
::= { atmIfVptRowStatusEntry 1 }

atmIfVptComponentName OBJECT-TYPE
   SYNTAX     DisplayString 
   ACCESS     read-only
   STATUS     mandatory
   DESCRIPTION
     "This variable provides the component's string name for
      use with the ASCII Console Interface"
::= { atmIfVptRowStatusEntry 2 }

atmIfVptStorageType OBJECT-TYPE
   SYNTAX     StorageType 
   ACCESS     read-only
   STATUS     mandatory
   DESCRIPTION
     "This variable represents the storage type value for the
      atmIfVpt tables."
::= { atmIfVptRowStatusEntry 4 }

atmIfVptIndex OBJECT-TYPE
   SYNTAX     Integer32 (0..4095)
   ACCESS     not-accessible
   STATUS     mandatory
   DESCRIPTION
     "This variable represents the index for the atmIfVpt tables."
::= { atmIfVptRowStatusEntry 10 }

atmIfVptStateTable OBJECT-TYPE
   SYNTAX     SEQUENCE OF AtmIfVptStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { atmIfVpt 100 }

atmIfVptStateEntry OBJECT-TYPE
   SYNTAX     AtmIfVptStateEntry
   ACCESS     not-accessible
   STATUS     mandatory
   DESCRIPTION
     "An entry in the atmIfVptStateTable."
   INDEX {
      atmIfIndex,
      atmIfVptIndex }
::= { atmIfVptStateTable 1 }

AtmIfVptStateEntry ::= SEQUENCE {
   atmIfVptAdminState
      INTEGER,
   atmIfVptOperationalState
      INTEGER,
   atmIfVptUsageState
      INTEGER }

atmIfVptAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { atmIfVptStateEntry 1 }

atmIfVptOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { atmIfVptStateEntry 2 }

atmIfVptUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { atmIfVptStateEntry 3 }

atmIfVptOperTable OBJECT-TYPE
   SYNTAX     SEQUENCE OF AtmIfVptOperEntry
   ACCESS     not-accessible
   STATUS     mandatory
   DESCRIPTION
     "This group contains operational information for a Vcc, Vpc, or Vpt 
      component."
::= { atmIfVpt 110 }

atmIfVptOperEntry OBJECT-TYPE
   SYNTAX     AtmIfVptOperEntry
   ACCESS     not-accessible
   STATUS     mandatory
   DESCRIPTION
     "An entry in the atmIfVptOperTable."
   INDEX {
      atmIfIndex,
      atmIfVptIndex }
::= { atmIfVptOperTable 1 }

AtmIfVptOperEntry ::= SEQUENCE {
   atmIfVptConnectionPointType
      INTEGER }

atmIfVptConnectionPointType OBJECT-TYPE
   SYNTAX     INTEGER  {
                 connectionEndPoint(0),
                 segmentEndPoint(1),
                 connectingPoint(2),
                 unknown(3) }
   ACCESS     read-only
   STATUS     mandatory
   DESCRIPTION
     "This attribute reflects the role of the connection component at this 
      interface.
      
      A value of connectionEndPoint indicates that user cells, end-to-end 
      OAM cells, and segment OAM cells are processed by the 
      connection component.
      
      A value of segmentEndPoint indicates that user cells and end-to-
      end OAM cells are relayed by the connection component, while 
      segment OAM cells are processed by the connection component.
      
      A value of connectingPoint indicates that user cells, end-to-end 
      OAM cells, and segment OAM cells are relayed by the connection 
      component.
      
      A value of unknown indicates that the connection component is 
      inactive."
::= { atmIfVptOperEntry 10 }

atmIfVptStatusTable OBJECT-TYPE
   SYNTAX     SEQUENCE OF AtmIfVptStatusEntry
   ACCESS     not-accessible
   STATUS     mandatory
   DESCRIPTION
     "This group contains operational status information for a Vcc, Vpc, 
      or Vpt component."
::= { atmIfVpt 120 }

atmIfVptStatusEntry OBJECT-TYPE
   SYNTAX     AtmIfVptStatusEntry
   ACCESS     not-accessible
   STATUS     mandatory
   DESCRIPTION
     "An entry in the atmIfVptStatusTable."
   INDEX {
      atmIfIndex,
      atmIfVptIndex }
::= { atmIfVptStatusTable 1 }

AtmIfVptStatusEntry ::= SEQUENCE {
   atmIfVptOperStatus
      INTEGER,
   atmIfVptLocalFailureCause
      INTEGER,
   atmIfVptTroubled
      INTEGER,
   atmIfVptSegLinkSideLoopbackState
      INTEGER,
   atmIfVptSegSwitchSideLoopbackState
      INTEGER,
   atmIfVptEndToEndLoopbackState
      INTEGER,
   atmIfVptRxOamCellCongestionState
      INTEGER,
   atmIfVptAisState
      INTEGER,
   atmIfVptRdiState
      INTEGER }

atmIfVptOperStatus OBJECT-TYPE
   SYNTAX     INTEGER  {
                 unknown(0),
                 end2endUp(1),
                 end2endDown(2),
                 localUpEnd2endUnknown(3),
                 localDown(4) }
   ACCESS     read-only
   STATUS     mandatory
   DESCRIPTION
     "This attribute indicates the present operational status of the Vcc, 
      Vpc, or Vpt component. Its value is dependent upon the current state 
      of the segLinkSideLoopbackState and endToEndLoopbackState 
      attributes.
      
      The value is end2endUp when the endToEndLoopbackState is good 
      and the segLinkSideLoopbackState is either good or unknown.
      
      The value is end2endDown when the endToEndLoopbackState is 
      bad and the segLinkSideLoopbackState is either good or unknown.
      
      The value is localUpEnd2endUnknown when the 
      endToEndLoopbackState is unknown and the 
      segLinkSideLoopbackState is good.
      
      The value is localDown when segLinkSideLoopbackState is bad.
      
      The value is localUpEnd2endUnknown when the 
      endToEndLoopbackState is notApplicable and the 
      segLinkSideLoopbackState is good.
      
      The value is unknown when the endToEndLoopbackState is either 
      unknown or notApplicable and the segLinkSideLoopbackState is 
      unknown."
::= { atmIfVptStatusEntry 20 }

atmIfVptLocalFailureCause OBJECT-TYPE
   SYNTAX     INTEGER  {
                 noFailure(0),
                 localBwLoss(1),
                 portDown(2),
                 notAdmitted(3),
                 appNotRegistered(4),
                 disabledByApp(5),
                 bwReduced(6),
                 vpDown(7) }
   ACCESS     read-only
   STATUS     mandatory
   DESCRIPTION
     "This attribute indicates the failure cause of the Vcc, Vpc, or Vpt 
      component. noFailure indicates that there is currently no 
      bandwidth related failure for this connection. 
      
      portDown indicates that the interface corresponding to the parent 
      AtmIf is down. 
      
      localBwLoss indicates that the Ima corresponding to this AtmIf has 
      lost some, but not all bandwidth, and as a result, this connection has 
      been released.
      
      notAdmitted indicates that this connection has failed to be admitted 
      by the Connection Admission Control (CAC) algorithm.
      
      appNotRegistered indicates that there is no application registered to 
      use this connection. This may be the case, for example when there 
      is a Vcc Test application, but the test has not been started. Check the 
      status of the application to determine why it is not functional.
      
      disabledByApp indicates that the application using this connection 
      has requested that the connection be disabled. An example is a 
      connection used by a trunk application where the trunk has timed 
      out on an attempt to stage. Check the application to determine why 
      it is not fully functional.
      
      bwReduced indicates that this connection is operating in a reduced 
      bandwidth state. It is a bandwidth elastic connection which 
      currently has been allocated less than the requested (equivalent) 
      bandwidth.
      
      vpDown indicates that this connection has been notified of a fault 
      detected at the associated VP-layer. vpDown is applicable for Vpt 
      Vccs only."
::= { atmIfVptStatusEntry 25 }

atmIfVptTroubled OBJECT-TYPE
   SYNTAX     INTEGER  {
                 no(0),
                 yes(1) }
   ACCESS     read-only
   STATUS     mandatory
   DESCRIPTION
     "This attribute indicates whether or not the connection is in a 
      troubled state. Connections become troubled because of OAM 
      failures; when one of the attributes segLinkSideLoopbackState, 
      segSwitchSideLoopbackState, endToEndLoopbackState, aisState 
      (when receiving AIS cells only) or rdiState go bad, this attribute is 
      set to yes; otherwise it is set to no."
   DEFVAL     { no }
::= { atmIfVptStatusEntry 28 }

atmIfVptSegLinkSideLoopbackState OBJECT-TYPE
   SYNTAX     INTEGER  {
                 good(0),
                 bad(1),
                 unknown(2),
                 notApplicable(3) }
   ACCESS     read-only
   STATUS     mandatory
   DESCRIPTION
     "This attribute contains the current state of the link-side segment 
      loopback for this connection. Link-side segment loopback cells are 
      transmitted (inserted) by a connection component in the direction of 
      the link (port). The value of this attribute is dependent upon the 
      current setting of the segLinkSideLoopback provisionable attribute, 
      the connection point type as specified by the connectionPointType 
      attribute, and the current loopback state (if applicable).
      
      The value is notApplicable when the connectionPointType is a 
      connectingPoint. 
      
      The value is notApplicable when the distributionType is 
      pointToMultipoint.
      
      The value is good when the segLinkSideLoopback is on, the 
      connectionPointType is a segmentEndPoint or a 
      connectionEndPoint, and the segment link side loopback is 
      working.
      
      The value is bad when the segLinkSideLoopback is on, the 
      connectionPointType is a segmentEndPoint or a 
      connectionEndPoint, and the link side segment loopback is not 
      working.
      
      The value is unknown when the segLinkSideLoopback is off.
      
      The value is unknown when the segLinkSideLoopback is on, the 
      connectionPointType is a segmentEndPoint and the segment switch 
      side loopback has not yet been determined.
      
      The state of this attribute determines, in part, the value of the 
      operStatus attribute."
::= { atmIfVptStatusEntry 30 }

atmIfVptSegSwitchSideLoopbackState OBJECT-TYPE
   SYNTAX     INTEGER  {
                 good(0),
                 bad(1),
                 unknown(2),
                 notApplicable(3) }
   ACCESS     read-only
   STATUS     mandatory
   DESCRIPTION
     "This attribute contains the current state of the switch-side segment 
      loopback for this connection. Switch-side segment loopback cells 
      are transmitted (inserted) by a connection component in the 
      direction of the bus. The value of this attribute is dependent upon 
      the current setting of the segSwitchSideLoopback provisionable 
      attribute, the connection point type as specified by the 
      connectionPointType attribute, and the current loopback state (if 
      applicable).
      
      The value is only applicable when the connectionPointType is a 
      segmentEndPoint. 
      
      The value is notApplicable when the connectionPointType is a 
      connectingPoint or connectionEndPoint. 
      
      The value is notApplicable when the distributionType is 
      pointToMultipoint.
      
      The value is good when the segSwitchSideLoopback is on, the 
      connectionPointType is a segmentEndPoint and the segment switch 
      side loopback is working.
      
      The value is bad when the segSwitchSideLoopback is on, the 
      connectionPointType is a segmentEndPoint and the switch side 
      segment loopback is not working.
      
      The value is unknown when the segSwitchSideLoopback is off.
      
      The value is unknown when the segSwitchSideLoopback is on, the 
      connectionPointType is a segmentEndPoint and the segment switch 
      side loopback has not been determined."
::= { atmIfVptStatusEntry 40 }

atmIfVptEndToEndLoopbackState OBJECT-TYPE
   SYNTAX     INTEGER  {
                 good(0),
                 bad(1),
                 unknown(2),
                 notApplicable(3) }
   ACCESS     read-only
   STATUS     mandatory
   DESCRIPTION
     "This attribute contains the current state of the end-to-end loopback 
      for this connection. Its value is dependent upon the current setting 
      of the endToEndLoopback provisionable attribute and the 
      connection point type as specified by the connectionPointType 
      attribute.
      
      The value is only applicable when the connectionPointType is a 
      connectionEndPoint. 
      
      The value is notApplicable when the connectionPointType is a 
      connectingPoint or segmentEndPoint. 
      
      The value is notApplicable when the distributionType is a 
      pointToMultipoint.
      
      The value is good when the endToEndLoopback is on, the 
      connectionPointType is a connectionEndPoint and the end-to-end 
      loopback is working.
      
      The value is bad when the endToEndLoopback is on, the 
      connectionPointType is a connectionEndPoint and the end-to-end 
      loopback is not working.
      
      The value is unknown when the endToEndLoopback is off.
      
      The value is unknown when the endToEndLoopback is on, the 
      connectionPointType is a connectionEndPoint and the end-to-end 
      loopback status has not been determined.
      
      The state of this attribute determines, in part, the value of the 
      operStatus attribute."
::= { atmIfVptStatusEntry 50 }

atmIfVptRxOamCellCongestionState OBJECT-TYPE
   SYNTAX     INTEGER  {
                 good(0),
                 bad(1),
                 unknown(2),
                 notApplicable(3) }
   ACCESS     read-only
   STATUS     mandatory
   DESCRIPTION
     "This attribute contains the current state of the receive side OAM cell 
      congestion for this connection. Its value reflects whether the rate of 
      received OAM cells for this connection is below a specified 
      threshold. The connection maintains a count of the number of OAM 
      cells which are terminated per second. Once that count exceeds the 
      specified threshold, extraction of all OAM cells for this connection 
      is disabled for a period of one minute. This is a congestion 
      management mechanism to prevent the processor from being 
      overloaded with handling OAM cells for a particular connection. 
      This mechanism ensures that tasks, such as trunks obtain enough 
      processor cycles to remain in service, and are not adversely affected 
      by excessive rate of OAM cells on a particular connection.
      
      The value is good when the rate of received OAM cells is less than 
      the allowed threshold.
      
      The value is bad when the arrival rate has exceeded the allowed 
      threshold. It remains bad for one minute, before returning to good 
      again. During this timeout, extraction of all OAM cells is disabled 
      for this connection. As a result, other loopback failure conditions 
      may occur.
      
      The value is unknown when the application has not yet begun to 
      use this connection. An example is the Test component before a test 
      has been started.
      
      Each type of OAM cell is counted separately. The threshold for AIS 
      cells is three cells per second. If more than three AIS cells are 
      received within a one second interval, this attribute is set to bad. 
      The threshold for RDI cells and each loopback type is also three, 
      but the threshold for trace cells is 250 per second.
      
      The state of this attribute has no direct effect on the value of the 
      operStatus attribute or on the number of troubled connections."
::= { atmIfVptStatusEntry 55 }

atmIfVptAisState OBJECT-TYPE
   SYNTAX     INTEGER  {
                 good(0),
                 bad(1),
                 unknown(2),
                 notApplicable(3) }
   ACCESS     read-only
   STATUS     mandatory
   DESCRIPTION
     "This attribute contains the current state of the Alarm Indication 
      Signal for this connection.
      
      A value of good indicates that the connection's application is active 
      and no alarm has occurred.
      
      A value of bad indicates that the connection's application is active 
      and an alarm has occurred.
      
      A value of unknown indicates that the connection's application is 
      inactive.
      
      A value of notApplicable occurs when the connectionPointType is 
      either a segmentEndPoint or a connectingPoint."
::= { atmIfVptStatusEntry 60 }

atmIfVptRdiState OBJECT-TYPE
   SYNTAX     INTEGER  {
                 good(0),
                 bad(1),
                 unknown(2),
                 notApplicable(3) }
   ACCESS     read-only
   STATUS     mandatory
   DESCRIPTION
     "This attribute indicates the current state of the Remote Defect 
      Indication for this connection.
      
      A value of good indicates that the connection's application is active 
      and no alarm has occurred.
      
      A value of bad indicates that the connection's application is active 
      and an alarm has occurred.
      
      A value of unknown indicates that the connection's application is 
      inactive.
      
      A value of notApplicable occurs when the connectionPointType is 
      either a segmentEndPoint or a connectingPoint."
::= { atmIfVptStatusEntry 70 }

atmIfVptTrafficTable OBJECT-TYPE
   SYNTAX     SEQUENCE OF AtmIfVptTrafficEntry
   ACCESS     not-accessible
   STATUS     mandatory
   DESCRIPTION
     "This group is HISTORICAL. Please refer to the group AtmTmOper;
      
      This attribute group contains attributes for the Vcc and Vpc 
      components to reflect operational traffic attributes."
::= { atmIfVpt 130 }

atmIfVptTrafficEntry OBJECT-TYPE
   SYNTAX     AtmIfVptTrafficEntry
   ACCESS     not-accessible
   STATUS     mandatory
   DESCRIPTION
     "An entry in the atmIfVptTrafficTable."
   INDEX {
      atmIfIndex,
      atmIfVptIndex }
::= { atmIfVptTrafficTable 1 }

AtmIfVptTrafficEntry ::= SEQUENCE {
   atmIfVptTxTrafficDescType
      INTEGER,
   atmIfVptTxQosClass
      INTEGER,
   atmIfVptFwdQosClass
      INTEGER,
   atmIfVptTxQueueLength
      INTEGER,
   atmIfVptTxQueueCongestionState
      INTEGER,
   atmIfVptHoldingPriority
      INTEGER,
   atmIfVptRxTrafficDescType
      INTEGER,
   atmIfVptRxQosClass
      INTEGER,
   atmIfVptBwdQosClass
      INTEGER,
   atmIfVptAtmServiceCategory
      INTEGER,
   atmIfVptTrafficShaping
      INTEGER,
   atmIfVptBearerClassBbc
      INTEGER,
   atmIfVptTransferCapabilityBbc
      INTEGER,
   atmIfVptClippingBbc
      INTEGER,
   atmIfVptUnshapedTransmitQueueing
      INTEGER,
   atmIfVptBestEffort
      INTEGER,
   atmIfVptUsageParameterControl
      INTEGER,
   atmIfVptTxFrameDiscard
      OCTET STRING,
   atmIfVptRxFrameDiscard
      OCTET STRING,
   atmIfVptBandwidthElastic
      INTEGER,
   atmIfVptBandwidthReduction
      INTEGER }

atmIfVptTxTrafficDescType OBJECT-TYPE
   SYNTAX     INTEGER  {
                 n1(1),
                 n2(2),
                 n3(3),
                 n4(4),
                 n5(5),
                 n6(6),
                 n7(7),
                 n8(8) }
   ACCESS     read-only
   STATUS     obsolete
   DESCRIPTION
     "This attribute is HISTORICAL. Please refer to the attribute of the 
      same name in the group AtmTmOper.
      
      This attribute indicates the type of traffic management which is 
      applied to the transmit direction of this connection as defined in the 
      ATM Forum. The txTrafficDescType determines the number and 
      meaning of the parameters in the txTrafficDescParm attribute."
::= { atmIfVptTrafficEntry 10 }

atmIfVptTxQosClass OBJECT-TYPE
   SYNTAX     INTEGER  {
                 unspecified(0),
                 constantBitRate(1),
                 variableBitRate(2),
                 connectionOriented(3),
                 connectionless(4) }
   ACCESS     read-only
   STATUS     obsolete
   DESCRIPTION
     "This attribute indicates the quality of service for the transmit 
      direction for this connection.
      
      The constantBitRate class refers to traffic offered on services such 
      as a constant bit rate video service. This traffic is highest priority.
      
      The variableBitRate class refers to traffic offered on services such 
      as packetized audio and video.
      
      The connectionOriented class refers to connection-oriented traffic 
      such as Frame Relay or X.25 traffic. 
      
      The connectionless traffic refers to traffic offered through 
      connectionless trunks such as certain LAN protocols.
      
      The unspecified class supports a 'best effort' type of service, where 
      there is a minimum guarantee of bandwidth. This traffic is lowest 
      priority.
      
      This attribute is obsolete, replaced by the UNI 4.0 attribute 
      atmServiceCategory."
::= { atmIfVptTrafficEntry 30 }

atmIfVptFwdQosClass OBJECT-TYPE
   SYNTAX     INTEGER  {
                 n0(0),
                 n1(1),
                 n2(2),
                 n3(3),
                 n4(4),
                 notApplicable(14) }
   ACCESS     read-only
   STATUS     obsolete
   DESCRIPTION
     "This attribute is HISTORICAL. Please refer to the attribute of the 
      same name in the group AtmTmOper.
      
      This attribute indicates the quality of service for the calling to called 
      direction for this connection. This is only applicable to Soft PVC 
      and SVC connections. 
      
      Class 1 supports a QOS that meets Service Class A performance 
      requirements (Circuit emulation, constant bit rate video).
      
      Class 2 supports a QOS that meets Service Class B performance 
      requirements (Variable bit rate audio and video).
      
      Class 3 supports a QOS that meets Service Class C performance 
      requirements (Connection-Oriented Data Transfer).
      
      Class 4 supports a QOS that meets Service Class D performance 
      requirements (Connectionless Data Transfer).
      
      Class 0 is the unspecified QOS class; no objective is specified for 
      the performance parameters.
      
      A value of notApplicable is displayed in the case of nailed-up PVCs 
      for which this attribute has no significance."
::= { atmIfVptTrafficEntry 31 }

atmIfVptTxQueueLength OBJECT-TYPE
   SYNTAX     INTEGER (0..30720)
   ACCESS     read-only
   STATUS     obsolete
   DESCRIPTION
     "This attribute is HISTORICAL. Please refer to the attribute of the 
      same name in the group AtmTmOper.
      
      This attribute indicates the current length of the transmit queue for 
      this connection. If this connection has traffic shaping disabled, then 
      this attribute displays the common queue length. If traffic shaping is 
      enabled, then this attribute displays the per-VC queue length."
::= { atmIfVptTrafficEntry 32 }

atmIfVptTxQueueCongestionState OBJECT-TYPE
   SYNTAX     INTEGER (0..3)
   ACCESS     read-only
   STATUS     obsolete
   DESCRIPTION
     "This attribute is HISTORICAL. Please refer to the attribute of the 
      same name in the group AtmTmOper.
      
      This attribute indicates the congestion state of the transmit queue 
      for this connection. If the connection has traffic shaping disabled, 
      then this attribute displays the common queue congestion state. If 
      traffic shaping is enabled, then this attribute displays the per-VC 
      queue congestion state.
      
      The congestion state of a queue is indicated by a numeric value 
      ranging from 0 to 3. When a queue is in a congested state x, only 
      traffic with discard priority (DP) 0 to x are enqueued. Traffic with 
      DP > x is discarded. 
      
      Therefore, if the congestion state is 3, there is no congestion and all 
      traffic is enqueued. Likewise, when the congestion state is 0, there 
      is maximum congestion and only traffic with DP=0 is enqueued on 
      that queue."
::= { atmIfVptTrafficEntry 33 }

atmIfVptHoldingPriority OBJECT-TYPE
   SYNTAX     INTEGER  {
                 n0(0),
                 n1(1),
                 n2(2),
                 n3(3),
                 n4(4),
                 notApplicable(6) }
   ACCESS     read-only
   STATUS     obsolete
   DESCRIPTION
     "This attribute is HISTORICAL. Please refer to the attribute of the 
      same name in the group AtmTmOper.
      
      This attribute indicates the actual holding priority in effect for this 
      connection. In a situation where the link bandwidth fluctuates, such 
      as over an IMA link, holding priority is used to determine which 
      connections are held and which are released. Holding priority 4 
      connections are the first to be released. Holding priority 0 
      connections are the last to be released. Some applications, for 
      example Vcc Test, may override the provisioned holding priority. 
      
      A value of notApplicable is displayed when this is an elastic 
      connection. Holding priority does not apply to bandwidth elastic 
      connections.
      
      Holding priority has no effect for ubr atmServiceCategory or 
      txTrafficDescriptorType 1 or 2 connections."
::= { atmIfVptTrafficEntry 35 }

atmIfVptRxTrafficDescType OBJECT-TYPE
   SYNTAX     INTEGER  {
                 n1(1),
                 n2(2),
                 n3(3),
                 n4(4),
                 n5(5),
                 n6(6),
                 n7(7),
                 n8(8) }
   ACCESS     read-only
   STATUS     obsolete
   DESCRIPTION
     "This attribute is HISTORICAL. Please refer to the attribute of the 
      same name in the group AtmTmOper.
      
      This attribute indicates the type of traffic management which is 
      applied to the receive direction of this connection as defined in the 
      ATM Forum. The rxTrafficDescType determines the number and 
      meaning of the parameters in the rxTrafficDescParm attribute."
::= { atmIfVptTrafficEntry 40 }

atmIfVptRxQosClass OBJECT-TYPE
   SYNTAX     INTEGER  {
                 unspecified(0),
                 constantBitRate(1),
                 variableBitRate(2),
                 connectionOriented(3),
                 connectionless(4) }
   ACCESS     read-only
   STATUS     obsolete
   DESCRIPTION
     "This attribute reflects the value of the provisioned attribute in the 
      Vcd or Vpd. Refer to that attribute for more detailed explanation. 
      
      This attribute is obsolete replaced by the UNI 4.0 attribute 
      atmServiceCategory."
::= { atmIfVptTrafficEntry 60 }

atmIfVptBwdQosClass OBJECT-TYPE
   SYNTAX     INTEGER  {
                 n0(0),
                 n1(1),
                 n2(2),
                 n3(3),
                 n4(4),
                 notApplicable(14) }
   ACCESS     read-only
   STATUS     obsolete
   DESCRIPTION
     "This attribute is HISTORICAL. Please refer to the attribute of the 
      same name in the group AtmTmOper.
      
      This attribute indicates the quality of service for the called to calling 
      direction for this connection. This is only applicable to Soft PVC 
      and SVC connections. 
      
      Class 1 supports a QOS that meets Service Class A performance 
      requirements (Circuit emulation, constant bit rate video).
      
      Class 2 supports a QOS that meets Service Class B performance 
      requirements (Variable bit rate audio and video).
      
      Class 3 supports a QOS that meets Service Class C performance 
      requirements (Connection-Oriented Data Transfer).
      
      Class 4 supports a QOS that meets Service Class D performance 
      requirements (Connectionless Data Transfer).
      
      Class 0 is the unspecified QOS class; no objective is specified for 
      the performance parameters.
      
      A value of notApplicable is displayed in the case of nailed-up PVCs 
      for which this attribute has no significance."
::= { atmIfVptTrafficEntry 61 }

atmIfVptAtmServiceCategory OBJECT-TYPE
   SYNTAX     INTEGER  {
                 unspecifiedBitRate(0),
                 constantBitRate(1),
                 rtVariableBitRate(2),
                 nrtVariableBitRate(3) }
   ACCESS     read-only
   STATUS     obsolete
   DESCRIPTION
     "This attribute is HISTORICAL. Please refer to the attribute of the 
      same name in the group AtmTmOper.
      
      This attribute indicates the ATM service category used for traffic in 
      both directions of the connection. 
      
      The constantBitRate service category is intended for real time 
      applications, that is, those requiring tightly constrained delay and 
      delay variation, as would be appropriate for voice and video 
      applications. The consistent availability of a fixed quantity of 
      bandwidth is considered appropriate for CBR service. Cells which 
      are delayed beyond the value specified by Cell Transfer Delay are 
      assumed to have significantly reduced value of the application.
      
      The rtVariableBitRate service category is intended for real time 
      applications; that is those requiring tightly constrained delay and 
      delay variation, as would be appropriate for voice and video 
      applications. Sources are expected to transmit at a rate which varies 
      with time. Equivalently, the source can be described as 'bursty'. 
      Cells which are delayed beyond the value specified by Cell Transfer 
      Delay are assumed to be of significantly reduced value to the 
      application. Real time VBR service may support statistical 
      multiplexing of real time sources.
      
      The nrtVariableBitRate service category is intended for non-real 
      time applications which have bursty traffic characteristics and which 
      can be characterized in terms of a PCR, SCR, and MBS. For those 
      cells which are transferred within the traffic contract, the application 
      expects a low cell loss ratio. For all connections, it expects a bound 
      on the mean cell transfer delay. Non-real time VBR service may 
      support statistical multiplexing of connections.
      
      The unspecifiedBitRate service is intended for non-real time 
      applications, that is those not requiring tightly constrained delay 
      and delay variation. UBR sources are expected to be bursty. UBR 
      service supports a high degree of statistical multiplexing among 
      sources. UBR service does not specify traffic related service 
      guarantees. No numerical commitments are made with respect to 
      the cell loss ratio experienced by a UBR connection, or as to the 
      cell transfer delay experienced by cells on the connection."
::= { atmIfVptTrafficEntry 62 }

atmIfVptTrafficShaping OBJECT-TYPE
   SYNTAX     INTEGER  {
                 enabled(0),
                 disabled(1),
                 notApplicable(4) }
   ACCESS     read-only
   STATUS     obsolete
   DESCRIPTION
     "This attribute is HISTORICAL. Please refer to the attribute of the 
      same name in the group AtmTmOper.
      
      This attribute indicates the traffic shaping state of the connection.
      
      A value of notApplicable indicates that traffic shaping is not 
      applicable or not supported for this connection. This is the case 
      when the atmServiceCategory is constantBitRate, or when the 
      txTrafficDescType is 1 or 2. In these cases, the value of 
      notApplicable is set regardless of whether traffic shaping is enabled 
      or disabled in the provisioning data.
      
      A value of disabled indicates that traffic shaping is applicable and 
      supported for the type of connection but has been turned off in the 
      provisioning data.
      
      A value of enabled indicates that traffic shaping is applicable and 
      supported for the type of connection and has been turned on in the 
      provisioning data. This is the only case that indicates that traffic 
      shaping is performed on the connection. In this case, the actual 
      shaping rate is reflected in the txTrafficDescParm attribute, 
      parameter number 4."
::= { atmIfVptTrafficEntry 70 }

atmIfVptBearerClassBbc OBJECT-TYPE
   SYNTAX     INTEGER  {
                 a(1),
                 c(3),
                 x(16),
                 vp(24),
                 notApplicable(30) }
   ACCESS     read-only
   STATUS     obsolete
   DESCRIPTION
     "This attribute is HISTORICAL. Please refer to the attribute of the 
      same name in the group AtmTmOper.
      
      This attribute indicates the bearer capability for this connection.
      
      Class a service is a connection-oriented, constant bit rate ATM 
      transport service. Class a service has end to end timing 
      requirements and may require stringent cell loss, cell delay and cell 
      delay variation performance.When a is displayed, the user is 
      requesting more than an ATM only service. The network may look 
      at the AAL to provide interworking based upon its contents. 
      
      Class c service is a connection-oriented, variable bit rate ATM 
      transport service. Class c service has no end-to-end timing 
      requirements.When c is displayed, the user is requesting more than 
      an ATM only service. The network interworking function may look 
      at the AAL and provide service based on it.
      
      Class x service is a connection-oriented ATM transport service 
      where the AAL, trafficType (cbr or vbr) and timing requirements 
      are user defined (that is, transparent to the network). When the 
      value of this attribute is x, the user is requesting an ATM only 
      service from the network. In this case, the network shall not process 
      any higher layer protocol.
      
      Class vp service is used to indicate a transparent VP service when 
      the user is requesting an ATM only service from the network. In this 
      case, the network does not process any higher layer protocol. This 
      service differs from class x service in that with the class vp service 
      both the VCI field (except for VCI values 0, 3, 4, and 6 through 15) 
      and Payload Type field are transported transparently by the network. 
      This attribute value is only applicable to SPVP and SVP 
      connections.
      
      A value of notApplicable is displayed in the case of nailed-up PVCs 
      for which this attribute has no significance."
::= { atmIfVptTrafficEntry 71 }

atmIfVptTransferCapabilityBbc OBJECT-TYPE
   SYNTAX     INTEGER  {
                 n0(0),
                 n1(1),
                 n2(2),
                 n5(5),
                 n8(8),
                 n9(9),
                 n10(10),
                 notApplicable(30) }
   ACCESS     read-only
   STATUS     obsolete
   DESCRIPTION
     "This attribute is HISTORICAL. Please refer to the attribute of the 
      same name in the group AtmTmOper.
      
      This attribute indicates the transfer capability for this connection. 
      Uni 3.0/3.1 traffic type and end-to-end timing parameters are 
      mapped into this parameter as follows:
      <transferCapability: TrafficType, Timing>
      0: NoIndication, NoIndication
      1: NoIndication, yes
      2: NoIndication, no
      5: CBR, yes
      8: VBR, NoIndication
      9: VBR, yes
      10: VBR, no
      
      A value of notApplicable is displayed in the case of nailed-up PVCs 
      for which this attribute has no significance, or in the case that the 
      transfer capability in the call request was set to NoIndication.
      
      The CBR traffic type refers to traffic offered on services such as a 
      constant bit rate video service or a circuit emulation.
      
      The VBR traffic type refers to traffic offered on services such as 
      packetized audio and video, or data.
      
      The value NoIndication for traffic type is used if the user has not set 
      the traffic type; similarly for end-to-end timing.
      
      The value yes for end-to-end timing indicates that end-to-end 
      timing is required for the connection.
      
      The value no for end-to-end timing indicates that end-to-end timing 
      is not required for the connection."
::= { atmIfVptTrafficEntry 72 }

atmIfVptClippingBbc OBJECT-TYPE
   SYNTAX     INTEGER  {
                 no(0),
                 yes(1),
                 notApplicable(14) }
   ACCESS     read-only
   STATUS     obsolete
   DESCRIPTION
     "This attribute is HISTORICAL. Please refer to the attribute of the 
      same name in the group AtmTmOper.
      
      This attribute indicates the value of the clipping susceptibility 
      parameter in the BBC Information Element.
      
      Clipping is an impairment in which the first fraction of a second of 
      information to be transferred is lost. It occurs after a call is 
      answered and before an associated connection is switched through.
      
      A value of notApplicable is displayed in the case of nailed-up PVCs 
      for which this attribute has no significance."
::= { atmIfVptTrafficEntry 74 }

atmIfVptUnshapedTransmitQueueing OBJECT-TYPE
   SYNTAX     INTEGER  {
                 perVc(0),
                 common(1),
                 notApplicable(4) }
   ACCESS     read-only
   STATUS     obsolete
   DESCRIPTION
     "This attribute is HISTORICAL. Please refer to the attribute of the 
      same name in the group AtmTmOper.
      
      This attribute indicates the unshaped transmit queuing state of the 
      connection.
      
      A value of common indicates that transmit traffic is being enqueued 
      onto common transmit queues. 
      
      A value of perVc indicates that transmit traffic is being enqueued 
      onto a per-VC queue for this connection. This is the case when 
      trafficShaping is disabled, but per-VC queueing has been 
      configured for this connection. 
      
      A value of notApplicable indicates that transmit traffic is being 
      shaped for this connection. Transmit traffic for a shaped connection 
      is enqueued onto a per-VC queue, but this attribute is only 
      applicable for unshaped connections."
::= { atmIfVptTrafficEntry 75 }

atmIfVptBestEffort OBJECT-TYPE
   SYNTAX     INTEGER  {
                 indicated(0),
                 notIndicated(1),
                 notApplicable(14) }
   ACCESS     read-only
   STATUS     obsolete
   DESCRIPTION
     "This attribute is HISTORICAL. Please refer to the attribute of the 
      same name in the group AtmTmOper.
      
      This attribute indicates value of best effort parameter in the ATM 
      Traffic Descriptor Information Element.
      
      The value indicated implies that the quality of service for this 
      connection is not guaranteed.
      
      The value notIndicated implies that the quality of service for this 
      connection is guaranteed.
      
      A value of notApplicable is displayed in the case of nailed-up PVCs 
      for which this attribute has no significance."
::= { atmIfVptTrafficEntry 76 }

atmIfVptUsageParameterControl OBJECT-TYPE
   SYNTAX     INTEGER  {
                 enabled(0),
                 disabled(1),
                 notApplicable(3) }
   ACCESS     read-only
   STATUS     obsolete
   DESCRIPTION
     "This attribute is HISTORICAL. Please refer to the attribute of the 
      same name in the group AtmTmOper.
      
      This attribute indicates the UPC state of the connection.
      
      A value of notApplicable indicates that UPC is not applicable or not 
      supported for the connection. This is the case when the connection's 
      rxTrafficDescType is 1 or 2. A value of notApplicable is set 
      regardless of whether UPC is disabled or enabled in provisioning 
      data.
      
      A value of disabled indicates that UPC is applicable and supported 
      for the type of connection but has been turned off in the 
      provisioning data.
      
      A value of enabled indicates that UPC is applicable and supported 
      for the type of connection and has been turned on in the 
      provisioning data. This is the only case that indicates that UPC is 
      enforced on the connection. In this case the traffic descriptor 
      parameters used for UPC enforcement are reflected in the 
      rxTrafficDescParms of the connection."
::= { atmIfVptTrafficEntry 80 }

atmIfVptTxFrameDiscard OBJECT-TYPE
   SYNTAX     OCTET STRING (SIZE (1))
   ACCESS     read-only
   STATUS     obsolete
   DESCRIPTION
     "This attribute is HISTORICAL. Please refer to the attribute of the 
      same name in the group AtmTmOper.
      
      This attribute indicates the set of current frame discard functions in 
      effect in the transmit data direction at this connection point.
      
      A value of ppd indicates that the Partial Packet Discard (PPD) 
      function is in effect. PPD may be applied at an interim connecting 
      point for a connection which is transporting frame traffic (AAL5 at 
      the endpoint). PPD is controlled by provisioning for PVCs and 
      SPVCs, and by call setup parameters in the AAL and Traffic 
      Descriptor Information Elements.
      
      A value of epd indicates that the Early Packet Discard (EPD) 
      function is in effect at this connection endpoint. PPD and EPD are 
      enabled by default at a connection endpoint which is performing 
      AAL5 segmentation and assembly.
      
      Frame discard functions are not applicable for Virtual Path 
      Connections (VPCs).

      Description of bits:
      ppd(0)
      epd(1)"
::= { atmIfVptTrafficEntry 85 }

atmIfVptRxFrameDiscard OBJECT-TYPE
   SYNTAX     OCTET STRING (SIZE (1))
   ACCESS     read-only
   STATUS     obsolete
   DESCRIPTION
     "This attribute is HISTORICAL. Please refer to the attribute of the 
      same name in the group AtmTmOper.
      
      This attribute indicates the set of current frame discard functions in 
      effect in the receive data direction at this connection point.
      
      A value of ppd indicates that the Partial Packet Discard (PPD) 
      function is in effect. PPD may be applied at an interim connecting 
      point for a connection which is transporting frame traffic (AAL5 at 
      the endpoint). PPD is controlled by provisioning for PVCs and 
      SPVCs, and by call setup parameters in the AAL and Traffic 
      Descriptor Information Elements.
      
      A value of epd indicates that the Early Packet Discard (EPD) 
      function is in effect at this connection endpoint. PPD and EPD are 
      enabled by default at a connection endpoint which is performing 
      AAL5 segmentation and assembly.
      
      Frame discard functions are not applicable for Virtual Path 
      Connections (VPCs).

      Description of bits:
      ppd(0)
      epd(1)"
::= { atmIfVptTrafficEntry 86 }

atmIfVptBandwidthElastic OBJECT-TYPE
   SYNTAX     INTEGER  {
                 no(0),
                 yes(1) }
   ACCESS     read-only
   STATUS     obsolete
   DESCRIPTION
     "This attribute is HISTORICAL. Please refer to the attribute of the 
      same name in the group AtmTmOper.
      
      This attribute is only of importance for connections which are 
      carried on a link with a variable bandwidth. For example, the 
      bandwidth may be reduced in the event that one or more physical 
      links in the IMA group fail, such that the originally requested 
      bandwidth cannot be maintained. This attribute shows whether the 
      application (for example, Trunk) running on this connection can 
      continue to operate if the bandwidth is reduced. If the bandwidth is 
      reduced, the amount by which it is reduced is displayed in the 
      bandwidthReduction attribute. 
      
      A value of yes, indicates that this connection is elastic, and the 
      bandwidth may be reduced but the connection is not released. 
      
      A value of no indicates that the bandwidth for this connection is not 
      reduced in the event of link bandwidth reduction. However, this 
      connection may be released based on its holdingPriority.
      
      Bandwidth elasticity has no effect for ubr atmServiceCategory or 
      txTrafficDescriptorType 1 or 2 connections."
::= { atmIfVptTrafficEntry 90 }

atmIfVptBandwidthReduction OBJECT-TYPE
   SYNTAX     INTEGER (0..2147483647)
   ACCESS     read-only
   STATUS     obsolete
   DESCRIPTION
     "This attribute is HISTORICAL. Please refer to the attribute of the 
      same name in the group AtmTmOper.
      
      This attribute shows the amount by which the bandwidth has been 
      reduced for this connection. This value is non-zero only for 
      connections which have bandwidthElastic displayed as yes, and 
      which are also operating in a reduced bandwidth mode. This is 
      typically be the case for selected connections running over an IMA 
      link. This attribute takes a value from 0 (no reduction) up to the 
      ECR. All connections which are running at their full allocated 
      bandwidth, bwReduction have the value 0. Connections which have 
      been reduced in allocated bandwidth have a positive number for this 
      attribute. The bwReduction may be subtracted from the ECR (which 
      is displayed as txTrafficDescParm 5) to determine the actual 
      bandwidth allocated to this connection."
::= { atmIfVptTrafficEntry 100 }

atmIfVptStatsTable OBJECT-TYPE
   SYNTAX     SEQUENCE OF AtmIfVptStatsEntry
   ACCESS     not-accessible
   STATUS     mandatory
   DESCRIPTION
     "This group contains traffic statistics for a Vcc, Vpc, or Vpt 
      component."
::= { atmIfVpt 140 }

atmIfVptStatsEntry OBJECT-TYPE
   SYNTAX     AtmIfVptStatsEntry
   ACCESS     not-accessible
   STATUS     mandatory
   DESCRIPTION
     "An entry in the atmIfVptStatsTable."
   INDEX {
      atmIfIndex,
      atmIfVptIndex }
::= { atmIfVptStatsTable 1 }

AtmIfVptStatsEntry ::= SEQUENCE {
   atmIfVptStatsTxCell
      PassportCounter64,
   atmIfVptStatsTxCellClp
      PassportCounter64,
   atmIfVptTxDiscard
      PassportCounter64,
   atmIfVptTxDiscardClp
      PassportCounter64,
   atmIfVptStatsTxCellDiscard
      PassportCounter64,
   atmIfVptStatsTxCellDiscardClp
      PassportCounter64,
   atmIfVptStatsTxFrameDiscard
      PassportCounter64,
   atmIfVptStatsTxFrameDiscardClp
      PassportCounter64,
   atmIfVptTxUtilization
      Gauge32,
   atmIfVptStatsRxCell
      PassportCounter64,
   atmIfVptStatsRxCellClp
      PassportCounter64,
   atmIfVptRxDiscard
      PassportCounter64,
   atmIfVptRxDiscardClp
      PassportCounter64,
   atmIfVptStatsRxCellDiscard
      PassportCounter64,
   atmIfVptStatsRxCellDiscardClp
      PassportCounter64,
   atmIfVptStatsRxFrameDiscard
      PassportCounter64,
   atmIfVptStatsRxFrameDiscardClp
      PassportCounter64,
   atmIfVptRxUtilization
      Gauge32,
   atmIfVptStatsRxUpcViolationOnEnforcer1
      PassportCounter64,
   atmIfVptStatsRxUpcViolationOnEnforcer2
      PassportCounter64,
   atmIfVptStatsRxAal5FrameError
      PassportCounter64,
   atmIfVptStatsRxAal5FrameAbort
      PassportCounter64 }

atmIfVptStatsTxCell OBJECT-TYPE
   SYNTAX     PassportCounter64 
   ACCESS     read-only
   STATUS     mandatory
   DESCRIPTION
     "This attribute counts the number of cells that have been transmitted 
      from the interface on this connection. The counter wraps to zero if it 
      exceeds its maximum value of (2**64)-1."
::= { atmIfVptStatsEntry 10 }

atmIfVptStatsTxCellClp OBJECT-TYPE
   SYNTAX     PassportCounter64 
   ACCESS     read-only
   STATUS     mandatory
   DESCRIPTION
     "This attribute counts the number of cells that have been transmitted 
      from the interface on this connection with the CLP=1. The counter 
      wraps to zero if it exceeds its maximum value of (2**64)-1."
::= { atmIfVptStatsEntry 20 }

atmIfVptTxDiscard OBJECT-TYPE
   SYNTAX     PassportCounter64 
   ACCESS     read-only
   STATUS     obsolete
   DESCRIPTION
     "This attribute is replaced by new attributes txCellDiscard and 
      txFrameDiscard.
      
      This attribute counts the number of cells or frames received from 
      the bus on this connection that have been discarded.
      
      If the connection segments frames into cells, the counter indicates 
      the number of frames discarded. Connections which segment 
      frames into cells have a connectionPointType of 
      connectionEndPoint.
      
      If the connection relays cells without adaptation, the counter 
      indicates the number of cells discarded. Connections which relay 
      cells without adaptation have a connectionPointType of 
      segmentEndPoint or connectingPoint.
      
      AAL1 connections are an exception to this rule; although they have 
      a connectionPointType of connectionEndPoint, they do not do 
      adaptation at this point. Thus, in the AAL1 case, this attribute 
      counts discarded cells.
      
      Discards are done due to congestion or when the connection's 
      interface is disabled.
      
      The counter wraps to zero if it exceeds its maximum value of 
      (2**64)-1."
::= { atmIfVptStatsEntry 30 }

atmIfVptTxDiscardClp OBJECT-TYPE
   SYNTAX     PassportCounter64 
   ACCESS     read-only
   STATUS     obsolete
   DESCRIPTION
     "This attribute is replaced by new attributes txCellDiscardClp and 
      txFrameDiscardClp.
      
      This attribute counts the number of cells or frames received from 
      the bus on this connection with CLP=1 that have been discarded.
      
      If the connection segments frames into cells, the counter indicates 
      the number of frames discarded. Connections which segment 
      frames into cells have a connectionPointType of 
      connectionEndPoint.
      
      If the connection relays cells without adaptation, the counter 
      indicates the number of cells discarded. Connections which relay 
      cells without adaptation have a connectionPointType of 
      segmentEndPoint or connectingPoint.
      
      AAL1 connections are an exception to this rule; although they have 
      a connectionPointType of connectionEndPoint, they do not do 
      adaptation at this point. Thus, in the AAL1 case, this attribute 
      counts discarded cells.
      
      Discards are done due to congestion or when the connection's 
      interface is disabled.
      
      The counter wraps to zero if it exceeds its maximum value of 
      (2**64)-1."
::= { atmIfVptStatsEntry 40 }

atmIfVptStatsTxCellDiscard OBJECT-TYPE
   SYNTAX     PassportCounter64 
   ACCESS     read-only
   STATUS     mandatory
   DESCRIPTION
     "This attribute counts the number of cells received from the bus on 
      this connection that have been discarded.
      
      Discarded cells are not counted in the txCell attribute.
      
      Cells are discarded due to transmit congestion, Partial Packet 
      Discard (PPD), Early Packet Discard (EPD), and Weighted Random 
      Early Detection (W-RED) mechanisms, or when the connection's 
      interface is disabled.
      
      For CQC-based ATM cards, this attribute is applicable only to 
      connections that relay cells without adaptation. Such connections 
      usually have a connectionPointType of segmentEndPoint or 
      connectingPoint. AAL1 connections are an exception to this rule; 
      although they have a connectionPointType of connectionEndPoint, 
      they do not do adaptation at this point. For Vpts, this attribute 
      provides an aggregated total of all txCellDiscard values for all such 
      connections associated with the Vpt.
      
      For Vccs on CQC-based ATM cards, if the connection segments 
      frames into cells, this attribute is not applicable and is not 
      displayed.
      
      The counter wraps to zero if it exceeds its maximum value of 
      (2**64)-1."
::= { atmIfVptStatsEntry 42 }

atmIfVptStatsTxCellDiscardClp OBJECT-TYPE
   SYNTAX     PassportCounter64 
   ACCESS     read-only
   STATUS     mandatory
   DESCRIPTION
     "This attribute counts the number of cells received from the bus on 
      this connection with CLP=1 that have been discarded.
      
      This count is included in the txCellDiscard attribute. Discarded 
      cells are not counted in the txCellClp attribute.
      
      Cells are discarded due to transmit congestion, Partial Packet 
      Discard (PPD), Early Packet Discard (EPD), and Weighted Random 
      Early Detection (W-RED) mechanisms, or when the connection's 
      interface is disabled.
      
      For CQC-based ATM cards, this attribute is applicable only to 
      connections that relay cells without adaptation. Such connections 
      have a connectionPointType of segmentEndPoint or 
      connectingPoint. AAL1 connections are an exception to this rule; 
      although they have a connectionPointType of connectionEndPoint, 
      they do not do adaptation at this point. For Vpts, this attribute 
      provides an aggregated total of all txCellDiscardClp values for all 
      such connections associated with the Vpt.
      
      For Vccs on CQC-based ATM cards, if the connection segments 
      frames into cells, this attribute is not applicable and is not 
      displayed.
      
      The counter wraps to zero if it exceeds its maximum value of 
      (2**64)-1."
::= { atmIfVptStatsEntry 43 }

atmIfVptStatsTxFrameDiscard OBJECT-TYPE
   SYNTAX     PassportCounter64 
   ACCESS     read-only
   STATUS     mandatory
   DESCRIPTION
     "This attribute counts the number of frames received from the bus on 
      this connection that have been discarded.
      
      Frames are discarded due to congestion, Partial Packet Discard 
      (PPD), Early Packet Discard (EPD), and Weighted Random Early 
      Detection (W-RED) mechanisms, or when the connection interface 
      is disabled.
      
      This count is independent of the txCell or txCellDiscard attribute.
      
      For CQC-based ATM cards, this attribute is applicable only to 
      connections that segment frames into cells. Such connections have a 
      connectionPointType of connectionEndPoint. AAL1 connections 
      are an exception to this rule; although they have a 
      connectionPointType of connectionEndPoint, they do not do 
      adaptation at this point. For Vpts, this attribute provides an 
      aggregated total of all txFrameDiscard values for all such 
      connections associated with the Vpt.
      
      For CQC-based ATM cards, for Vpcs, and Vccs that relay cells 
      without adaptation, this attribute is not applicable and is not 
      displayed.
      
      Discards due to EPD, PPD, and W-RED for a standard Vpt Vcc are 
      not included in this attribute. These discards are counted in the 
      Vcc's parent Vpt txFrameDiscard attribute.
      
      The counter wraps to zero if it exceeds its maximum value of 
      (2**64)-1."
::= { atmIfVptStatsEntry 46 }

atmIfVptStatsTxFrameDiscardClp OBJECT-TYPE
   SYNTAX     PassportCounter64 
   ACCESS     read-only
   STATUS     mandatory
   DESCRIPTION
     "This attribute counts the number of discarded frames on this 
      connection that were received from the bus and composed of one or 
      more CLP=1 cells.
      
      Frames are discarded due to congestion, Partial Packet Discard 
      (PPD), Early Packet Discard (EPD), and Weighted Random Early 
      Detection (W-RED) mechanisms, or when the connection interface 
      is disabled.
      
      This count is included in the txFrameDiscard attribute.
      
      For CQC-based ATM cards, this attribute is applicable only to 
      connections that segment frames into cells. Such connections have a 
      connectionPointType of connectionEndPoint. AAL1 connections 
      are an exception to this rule; although they have a 
      connectionPointType of connectionEndPoint, they do not do 
      adaptation at this point. For Vpts, this attribute provides an 
      aggregated total of all txFrameDiscardClp values for all such 
      connections associated with the Vpt.
      
      For CQC-based ATM cards, for Vpcs, and Vccs that relay cells 
      without adaptation, this attribute is not applicable and is not 
      displayed.
      
      Discards due to EPD, PPD, and W-RED for a standard Vpt Vcc are 
      not included in this attribute. These discards are counted in the 
      Vcc's parent Vpt txFrameDiscardClp attribute.
      
      The counter wraps to zero if it exceeds its maximum value of 
      (2**64)-1."
::= { atmIfVptStatsEntry 47 }

atmIfVptTxUtilization OBJECT-TYPE
   SYNTAX     Gauge32 (0..200 | 255)
   ACCESS     read-only
   STATUS     mandatory
   DESCRIPTION
     "This attribute indicates the current transmit utilization during the 
      most recent minute, expressed as a percentage of the total 
      bandwidth which can be carried by this connection. This attribute is 
      only applicable for Vpts and not for Vpcs or Vccs.
      
      When the Vpt is shaped, the value of this attribute is calculated 
      using its actual shaping rate (ASR) and should not exceed 100.
      
      When the Vpt is unshaped, the value of this attribute is calculated 
      using its peak cell rate (PCR) and should not exceed 200. If the 
      PCR is 0, the value 255 is used."
::= { atmIfVptStatsEntry 48 }

atmIfVptStatsRxCell OBJECT-TYPE
   SYNTAX     PassportCounter64 
   ACCESS     read-only
   STATUS     mandatory
   DESCRIPTION
     "This attribute counts cells that have been received from the interface 
      on this connection. The counter wraps to zero if it exceeds its 
      maximum value of (2**64)-1."
::= { atmIfVptStatsEntry 50 }

atmIfVptStatsRxCellClp OBJECT-TYPE
   SYNTAX     PassportCounter64 
   ACCESS     read-only
   STATUS     mandatory
   DESCRIPTION
     "This attribute counts cells that have been received from the interface 
      on this connection with the CLP=1. The counter wraps to zero if it 
      exceeds its maximum value of (2**64)-1."
::= { atmIfVptStatsEntry 60 }

atmIfVptRxDiscard OBJECT-TYPE
   SYNTAX     PassportCounter64 
   ACCESS     read-only
   STATUS     obsolete
   DESCRIPTION
     "This attribute is replaced by new attributes rxCellDiscard and 
      rxFrameDiscard.
      
      This attribute counts the number of cells or frames received from 
      the interface on this connection that have been discarded.
      
      If the connection segments frames into cells, the counter indicates 
      the number of frames discarded. Connections which segment 
      frames into cells have a connectionPointType of 
      connectionEndPoint.
      
      If the connection relays cells without adaptation, the counter 
      indicates the number of cells discarded. Connections which relay 
      cells without adaptation have a connectionPointType of 
      segmentEndPoint or connectingPoint.
      
      AAL1 connections are an exception to this rule; although they have 
      a connectionPointType of connectionEndPoint, they do not do 
      adaptation at this point. Thus, in the AAL1 case, this attribute 
      counts discarded cells.
      
      Discards are done due to congestion, non-conformance with UPC or 
      AAL reassembly problems.
      
      The counter wraps to zero if it exceeds its maximum value of 
      (2**64)-1."
::= { atmIfVptStatsEntry 70 }

atmIfVptRxDiscardClp OBJECT-TYPE
   SYNTAX     PassportCounter64 
   ACCESS     read-only
   STATUS     obsolete
   DESCRIPTION
     "This attribute is replaced by new attributes rxCellDiscardClp and 
      rxFrameDiscardClp.
      
      This attribute counts the number of cells or frames received from 
      the interface on this connection with CLP=1 that have been 
      discarded.
      
      If the connection segments frames into cells, the counter indicates 
      the number of frames discarded. Connections which segment 
      frames into cells have a connectionPointType of 
      connectionEndPoint.
      
      If the connection relays cells without adaptation, the counter 
      indicates the number of cells discarded. Connections which relay 
      cells without adaptation have a connectionPointType of 
      segmentEndPoint or connectingPoint.
      
      AAL1 connections are an exception to this rule; although they have 
      a connectionPointType of connectionEndPoint, they do not do 
      adaptation at this point. Thus, in the AAL1 case, this attribute 
      counts discarded cells.
      
      Discards are done due to congestion, non-conformance with UPC or 
      AAL reassembly problems.
      
      The counter wraps to zero if it exceeds its maximum value of 
      (2**64)-1."
::= { atmIfVptStatsEntry 80 }

atmIfVptStatsRxCellDiscard OBJECT-TYPE
   SYNTAX     PassportCounter64 
   ACCESS     read-only
   STATUS     mandatory
   DESCRIPTION
     "This attribute counts the number of cells received from the interface 
      on this connection that have been discarded. This count is included 
      in the rxCell attribute.
      
      This count includes cells discarded due to non-conformance with 
      UPC, cells which are part of a frame which has been discarded due 
      to an AAL5 frame reassembly error, cells which are discarded due 
      to congestion, or cells which are received while the next hop 
      connection to which the traffic is directed across the backplane is 
      down. The next hop connection is the Vcc or Vpc identified by the 
      nextHop attribute of the Nrp or Rp component. 
      
      For CQC-based ATM cards, this attribute is applicable only to 
      connections that relay cells without adaptation. Such connections 
      have a connectionPointType of connectionEndPoint or 
      connectingPoint. AAL1 connections are an exception to this rule; 
      although they have a connectionPointType of connectionEndPoint, 
      they do not do adaptation at this point. For Vpts, this attribute 
      provides an aggregated total of all rxCellDiscard values for all such 
      connections associated with the Vpt.
      
      For CQC-based ATM cards, for Vpcs, and Vccs that relay cells 
      without adaptation, this attribute is not applicable and is not 
      displayed.
      
      Discards due to non-conformance with UPC at the VP layer, for a 
      standard Vpt Vcc, are not included in this attribute. These discards 
      are counted in the Vcc's parent Vpt rxCellDiscard attribute.
      
      The counter wraps to zero if it exceeds its maximum value of 
      (2**64)-1."
::= { atmIfVptStatsEntry 82 }

atmIfVptStatsRxCellDiscardClp OBJECT-TYPE
   SYNTAX     PassportCounter64 
   ACCESS     read-only
   STATUS     mandatory
   DESCRIPTION
     "This attribute counts the number of cells received from the interface 
      on this connection with CLP=1 that have been discarded. This count 
      is included in the rxCell and rxCellDiscard attributes.
      
      This count includes cells discarded due to non-conformance with 
      UPC, cells which are part of a frame which has been discarded due 
      to an AAL5 frame reassembly error, cells which are discarded due 
      to congestion, or cells which are received while the next hop 
      connection to which the traffic is directed across the backplane is 
      down. The next hop connection is the Vcc or Vpc identified by the 
      nextHop attribute of the Nrp or Rp component. 
      
      For CQC-based ATM cards, this attribute is applicable only to 
      connections that relay cells without adaptation. Such connections 
      have a connectionPointType of connectionEndPoint or 
      connectingPoint. AAL1 connections are an exception to this rule; 
      although they have a connectionPointType of connectionEndPoint, 
      they do not do adaptation at this point. For Vpts, this attribute 
      provides an aggregated total of all rxCellDiscardClp values for all 
      such connections associated with the Vpt.
      
      For CQC-based ATM cards, for Vpcs, and Vccs that relay cells 
      without adaptation, this attribute is not applicable and is not 
      displayed.
      
      Discards due to non-conformance with UPC at the VP layer, for a 
      standard Vpt Vcc, are not included in this attribute. These discards 
      are counted in the Vcc's parent Vpt rxCellDiscardClp attribute.
      
      The counter wraps to zero if it exceeds its maximum value of 
      (2**64)-1."
::= { atmIfVptStatsEntry 83 }

atmIfVptStatsRxFrameDiscard OBJECT-TYPE
   SYNTAX     PassportCounter64 
   ACCESS     read-only
   STATUS     mandatory
   DESCRIPTION
     "This attribute counts the number of frames received from the 
      interface on this connection that have been discarded. This count is 
      independent of the rxCellDiscard attribute.
      
      This count includes frames discarded due to an AAL5 frame 
      reassembly error, frames discarded due to early packet discard 
      (EPD), and frames discarded due to processor (CPU) congestion. 
      This attribute is applicable only for connections that reassemble 
      incoming cells into frames. Connections which reassemble cells 
      into frames have a connectionPointType of connectionEndPoint. 
      AAL1 connections are an exception to this rule; even though they 
      have a connectionPointType of connectionEndPoint, they do not 
      do adaptation at this point. For Vpts, this attribute provides an 
      aggregated total of all rxFrameDiscard values for all applicable 
      connections associated with the Vpt.
      
      For Vpcs, and for Vccs that relay cells without adaptation, this 
      attribute is not applicable and is not displayed.
      
      The counter wraps to zero if it exceeds its maximum value of 
      (2**64)-1."
::= { atmIfVptStatsEntry 86 }

atmIfVptStatsRxFrameDiscardClp OBJECT-TYPE
   SYNTAX     PassportCounter64 
   ACCESS     read-only
   STATUS     mandatory
   DESCRIPTION
     "This attribute counts the number of discarded frames on this 
      connection that were received from the interface and composed of 
      one or more CLP1 cells. This count is included in the 
      rxFrameDiscard attribute. It is independent of the rxCellDiscard 
      attribute.
      
      This count includes frames discarded due to an AAL5 frame 
      reassembly error, frames discarded due to early packet discard 
      (EPD), and frames discarded due to processor (CPU) congestion. 
      This attribute is applicable only for connections that reassemble 
      incoming cells into frames. Connections which reassemble cells 
      into frames have a connectionPointType of connectionEndPoint. 
      AAL1 connections are an exception to this rule; even though they 
      have a connectionPointType of connectionEndPoint, they do not 
      do adaptation at this point. For Vpts, this attribute provides an 
      aggregated total of all rxFrameDiscardClp values for all applicable 
      connections associated with the Vpt.
      
      For Vpcs, and for Vccs that relay cells without adaptation, this 
      attribute is not applicable and is not displayed.
      
      The counter wraps to zero if it exceeds its maximum value of 
      (2**64)-1."
::= { atmIfVptStatsEntry 88 }

atmIfVptRxUtilization OBJECT-TYPE
   SYNTAX     Gauge32 (0..200 | 255)
   ACCESS     read-only
   STATUS     mandatory
   DESCRIPTION
     "This attribute indicates the current receive utilization during the 
      most recent minute, expressed as a percentage of the total 
      bandwidth which can be carried by this connection. This attribute is 
      only applicable for Vpts and not for Vpcs or Vccs.
      
      When the Vpt is shaped, the value of this attribute is calculated 
      using its actual shaping rate (ASR) and should not exceed 100.
      
      When the Vpt is unshaped, the value of this attribute is calculated 
      using its peak cell rate (PCR) and should not exceed 200. If the 
      PCR is 0, the value 255 is used."
::= { atmIfVptStatsEntry 89 }

atmIfVptStatsRxUpcViolationOnEnforcer1 OBJECT-TYPE
   SYNTAX     PassportCounter64 
   ACCESS     read-only
   STATUS     mandatory
   DESCRIPTION
     "This attribute counts the number of UPC violations observed by the 
      Generic Cell Rate Algorithm (GCRA) Enforcer 1. This attribute is 
      only applicable if UPC is enforced or monitored. This attribute is 
      not applicable for standard Vpt Vccs. This attribute is not applicable 
      and is not displayed on CQC-based ATM cards.
      
      When the value of rxTrafficDescType for this connection is 3, 4, 5, 
      6, 7 or 8, Enforcer 1 enforces conformance of traffic received from 
      the interface to PCR CLP0+1.
      
      When the value of rxTrafficDescType for this connection is 9, 
      Enforcer 1 performs the Dynamic Generic Cell Rate Algorithm 
      (DGCRA) used for the Available Bit Rate (ABR) service category.
      
      If UPC is enforced all non-conforming cells are discarded by this 
      enforcer. These discarded cells are included in rxCellDiscard. 
      
      For basic Vpts, this attribute provides an aggregated total of all 
      rxUpcViolationOnEnforcer1 values for the Vccs associated with the 
      Vpt.
      
      The counter wraps to zero if it exceeds its maximum value of 
      (2**64)-1."
::= { atmIfVptStatsEntry 90 }

atmIfVptStatsRxUpcViolationOnEnforcer2 OBJECT-TYPE
   SYNTAX     PassportCounter64 
   ACCESS     read-only
   STATUS     mandatory
   DESCRIPTION
     "This attribute counts the number of UPC violations observed by the 
      Generic Cell Rate Algorithm (GCRA) Enforcer 2. This attribute is 
      only applicable if UPC is enforced or monitored. This attribute is 
      not applicable for standard Vpt Vccs. This attribute is not applicable 
      and is not displayed on CQC-based ATM cards.
      
      Enforcer2 is applicable only if the rxTrafficDescType for this 
      connection is 4, 5, 6, 7 or 8.
      
      When the value of rxTrafficDescType 4 or 5, Enforcer 2 enforces 
      conformance of traffic received from the interface to PCR CLP0.
      
      When the value of rxTrafficDescType 6, Enforcer 2 enforces 
      conformance of traffic received from the interface to SCR CLP0+1.
      
      When the value of rxTrafficDescType 7 or 8, Enforcer 2 enforces 
      conformance of traffic received from the interface to SCR CLP0.
      
      If UPC is enforced, enforcer 2 discards non-conforming cells for 
      rxTrafficDescType values of 4, 6 and 7. It tags non-conforming cells 
      for rxTrafficDescType values of 5 and 8. Discarded cells are 
      counted in the rxCellDiscard attribute. 
      
      For basic Vpts, this attribute provides an aggregated total of all 
      rxUpcViolationOnEnforcer2 values for the Vccs associated with the 
      Vpt.
      
      The counter wraps to zero if it exceeds its maximum value of 
      (2**64)-1."
::= { atmIfVptStatsEntry 92 }

atmIfVptStatsRxAal5FrameError OBJECT-TYPE
   SYNTAX     PassportCounter64 
   ACCESS     read-only
   STATUS     mandatory
   DESCRIPTION
     "This attribute counts the number of frames received from the 
      interface on this connection that have AAL5 length errors or AAL5 
      CRC errors. 
      
      This attribute is not applicable and is not displayed on CQC-based 
      ATM cards.
      
      AAL5 length or CRC errors typically occur because of cell discards 
      due to congestion, UPC, or due to corruption of data between the 
      AAL5 segmentation and reassembly end points.
      
      This attribute is applicable only to connections that reassemble 
      incoming cells into frames. Such connections have a 
      connectionPointType of connectionEndPoint. AAL1 connections 
      are an exception to this rule; although they have a 
      connectionPointType of connectionEndPoint, they do not do 
      adaptation at this point. For Vpts, this attribute provides an 
      aggregated total of all rxAal5FrameError values for all applicable 
      connections associated with the Vpt.
      
      For Vpcs, and for Vccs that relay cells without adaptation, this 
      attribute is not applicable and is not displayed.
      
      The counter wraps to zero if it exceeds its maximum value of 
      (2**64)-1."
::= { atmIfVptStatsEntry 100 }

atmIfVptStatsRxAal5FrameAbort OBJECT-TYPE
   SYNTAX     PassportCounter64 
   ACCESS     read-only
   STATUS     mandatory
   DESCRIPTION
     "This attribute counts the number of frames received from the 
      interface on this connection that have the AAL5 length field set to 
      zero. 
      
      This attribute is not applicable and is not displayed for CQC-based 
      ATM cards.
      
      An AAL5 length of zero is an indication by the far end 
      segmentation point to this reassembly point that the frame is to be 
      discarded without reassembly. This mechanism is typically used by 
      a segmentation point if it detects an error in a frame after some of 
      the cells belonging to that frame have already been transmitted.
      
      This attribute is applicable only to connections that reassemble 
      incoming cells into frames. Such connections have a 
      connectionPointType of connectionEndPoint. AAL1 connections 
      are an exception to this rule; although they have a 
      connectionPointType of connectionEndPoint, they do not do 
      adaptation at this point. For Vpts, this attribute provides an 
      aggregated total of all rxAal5FrameAbort values for all applicable 
      connections associated with the Vpt.
      
      For Vpcs, and for Vccs that relay cells without adaptation, this 
      attribute is not applicable and is not displayed.
      
      The counter wraps to zero if it exceeds its maximum value of 
      (2**64)-1."
::= { atmIfVptStatsEntry 102 }

atmIfVptTxTdpTable OBJECT-TYPE
   SYNTAX     SEQUENCE OF AtmIfVptTxTdpEntry
   ACCESS     not-accessible
   STATUS     obsolete
   DESCRIPTION
     "This attribute is HISTORICAL. Please refer to the attribute of the 
      same name in the group AtmTmOper.
      
      This attribute is a vector of five transmit traffic parameters. The first 
      three elements reflect the settings of the first three elements of the 
      txTrafficDescParm attribute in the AtmTrafficProv group. 
      
      When txTrafficDescType is 1 or 2, parameters 1 through 5 are 
      unused.
      
      In this description, PCR is the greater of either the PCR or the 
      requested shaping rate (parameter 1 or parameter 5) specified in the 
      Traffic group under the Vcd or Vpd.
      
      When txTrafficDescType is 3, parameter 1 represents the PCR for 
      CLP equal to 0 or 1 traffic; parameters 2 and 3 are unused.
      
      When txTrafficDescType is 4, parameter 1 represents the PCR for 
      CLP equal to 0 and 1 traffic; parameter 2 represents the PCR for 
      CLP equal to 0 traffic with cell discard.
      
      When txTrafficDescType is 5, parameter 1 represents the PCR for 
      CLP equal to 0 and 1 traffic; parameter 2 represents the PCR for 
      CLP equal to 0 traffic with cell tagging.
      
      When txTrafficDescType is 6, parameter 1 represents the PCR for 
      CLP equal to 0 and 1 traffic; parameter 2 represents the SCR for 
      CLP equal to 0 and 1 traffic; parameter 3 represents the MBS for 
      CLP equal to 0 and 1 traffic.
      
      When txTrafficDescType is 7, parameter 1 represents the PCR for 
      CLP equal to 0 and 1 traffic; parameter 2 represents the SCR for 
      CLP equal to 0 traffic with cell discard; parameter 3 represents the 
      MBS for CLP equal to 0 traffic.
      
      When txTrafficDescType is 8, parameter 1 represents the PCR for 
      CLP equal to 0 and 1 traffic; parameter 2 represents the SCR for 
      CLP equal to 0 traffic with cell tagging; parameter 3 represents the 
      MBS for CLP equal to 0 traffic
      
      When txTrafficDescType is 3, 4, 5, 6, 7 or 8, parameter 4 reflects 
      the actual shaping rate in cell/s for this connection. This rate is one 
      of the set of available shaping rates for this type of ATM-FP, based 
      on the number of interfaces doing shaping (attribute 
      perVcQueueInterfaces), the provisioned cell rate, the 
      shapingScalingFactor attribute of the AtmResourceControl 
      component, and whether traffic shaping is enabled. A rate of zero 
      (0) indicates that shaping is not performed. 
      
      When txTrafficDescType is 3, 4, 5, 6, 7 or 8, parameter 5 reflects 
      the equivalent cell rate in cell/s for this connection as determined by 
      the Connection Admission Control (CAC) algorithm. The 
      equivalent cell rate is useful in determining the admission 
      characteristics of this connection."
::= { atmIfVpt 294 }

atmIfVptTxTdpEntry OBJECT-TYPE
   SYNTAX     AtmIfVptTxTdpEntry
   ACCESS     not-accessible
   STATUS     obsolete
   DESCRIPTION
     "An entry in the atmIfVptTxTdpTable."
   INDEX {
      atmIfIndex,
      atmIfVptIndex,
      atmIfVptTxTdpIndex }
::= { atmIfVptTxTdpTable 1 }

AtmIfVptTxTdpEntry ::= SEQUENCE {
   atmIfVptTxTdpIndex
      Integer32,
   atmIfVptTxTdpValue
      Unsigned32 }

atmIfVptTxTdpIndex OBJECT-TYPE
   SYNTAX     Integer32 (1..5)
   ACCESS     not-accessible
   STATUS     obsolete
   DESCRIPTION
     "This variable represents the atmIfVptTxTdpTable
      specific index for the atmIfVptTxTdpTable."
::= { atmIfVptTxTdpEntry 1 }

atmIfVptTxTdpValue OBJECT-TYPE
   SYNTAX     Unsigned32 (0..2147483647)
   ACCESS     read-only
   STATUS     obsolete
   DESCRIPTION
     "This variable represents an individual value for the
      atmIfVptTxTdpTable."
::= { atmIfVptTxTdpEntry 2 }

atmIfVptRxTdpTable OBJECT-TYPE
   SYNTAX     SEQUENCE OF AtmIfVptRxTdpEntry
   ACCESS     not-accessible
   STATUS     obsolete
   DESCRIPTION
     "This attribute is HISTORICAL. Please refer to the attribute of the 
      same name in the group AtmTmOper.
      
      This attribute is a vector of four traffic parameters whose meanings 
      are defined by the rxTrafficDescType attribute. The values of peak 
      cell rate (PCR), sustained cell rate (SCR) are expressed in cells/s. 
      Maximum burst size (MBS) is expressed in cells. Cell Delay 
      Variation Tolerance (CDVT) is expressed in microseconds.
      
      When rxTrafficDescType is 1 or 2, none of the parameters are used.
      
      When rxTrafficDescType is 3, parameter 1 represents the PCR for 
      CLP equal to 0 and 1 traffic; parameter 4 represents the CDVT.
      
      When rxTrafficDescType is 4, parameter 1 represents the PCR for 
      CLP equal to 0 and 1 traffic; parameter 2 represents the PCR for 
      CLP equal to 0 traffic with cell discard; parameter 4 represents the 
      CDVT.
      
      When rxTrafficDescType is 5, parameter 1 represents the PCR for 
      CLP equal to 0 and 1 traffic; parameter 2 represents the PCR for 
      CLP equal to 0 traffic with cell tagging; parameter 4 represents the 
      CDVT.
      
      When rxTrafficDescType is a 6, parameter 1 represents the PCR for 
      CLP equal to 0 and 1 traffic; parameter 2 represents the SCR for 
      CLP equal to 0 and 1 traffic; parameter 3 represents the MBS for 
      CLP equal to 0 and 1 traffic; parameter 4 represents the CDVT. 
      
      When rxTrafficDescType is 7, parameter 1 represents the PCR for 
      CLP equal to 0 and 1 traffic; parameter 2 represents the SCR for 
      CLP equal to 0 traffic with cell discard; parameter 3 represents the 
      MBS for CLP equal to 0 traffic; parameter 4 represents the CDVT.
      
      When rxTrafficDescType is 8, parameter 1 represents the PCR for 
      CLP equal to 0 and 1 traffic; parameter 2 represents the SCR for 
      CLP equal to 0 traffic with cell tagging; parameter 3 represents the 
      MBS for CLP equal to 0 traffic; parameter 4 represents the CDVT. 
      
      If Upc is disabled for this connection, the values of PCR, SCR, 
      MBS and CDVT is a combination of provisioned parameters. If Upc 
      is enabled, the values of PCR, SCR, MBS, and CDVT is exactly the 
      values used by the usage parameter control hardware in policing the 
      arriving traffic. These may vary slightly from the provisioned values 
      due to granularity of the hardware. In the case where the PCR is 
      equal to the SCR, the effective MBS is zero."
::= { atmIfVpt 295 }

atmIfVptRxTdpEntry OBJECT-TYPE
   SYNTAX     AtmIfVptRxTdpEntry
   ACCESS     not-accessible
   STATUS     obsolete
   DESCRIPTION
     "An entry in the atmIfVptRxTdpTable."
   INDEX {
      atmIfIndex,
      atmIfVptIndex,
      atmIfVptRxTdpIndex }
::= { atmIfVptRxTdpTable 1 }

AtmIfVptRxTdpEntry ::= SEQUENCE {
   atmIfVptRxTdpIndex
      Integer32,
   atmIfVptRxTdpValue
      Unsigned32 }

atmIfVptRxTdpIndex OBJECT-TYPE
   SYNTAX     Integer32 (1..4)
   ACCESS     not-accessible
   STATUS     obsolete
   DESCRIPTION
     "This variable represents the atmIfVptRxTdpTable
      specific index for the atmIfVptRxTdpTable."
::= { atmIfVptRxTdpEntry 1 }

atmIfVptRxTdpValue OBJECT-TYPE
   SYNTAX     Unsigned32 (0..2147483647)
   ACCESS     read-only
   STATUS     obsolete
   DESCRIPTION
     "This variable represents an individual value for the
      atmIfVptRxTdpTable."
::= { atmIfVptRxTdpEntry 2 }

atmIfVptTxQThreshTable OBJECT-TYPE
   SYNTAX     SEQUENCE OF AtmIfVptTxQThreshEntry
   ACCESS     not-accessible
   STATUS     obsolete
   DESCRIPTION
     "This attribute is HISTORICAL. Please refer to the attribute of the 
      same name in the group AtmTmOper.
      
      This attribute indicates the queue limit and the discard thresholds 
      for the transmit queue of this connection. 
      
      The first element indicates the queue limit. Depending upon the 
      atmServiceCategory of the connection, the provisioned value of the 
      transmit queue limit is derived from the txQueueLimit attribute 
      under one of the subcomponents of the AtmIf CA component. If the 
      connection has traffic shaping disabled, then this attribute relates to 
      the common queue. If traffic shaping is enabled, then this attribute 
      relates to the per-VC queue.
      
      The second element is the threshold that marks the transition from 
      congestion state 1 to congestion state 0. This is the threshold at 
      which traffic with discard priority (DP) = 1 is discarded. This 
      threshold is set approximately at 90 percent of the first parameter, 
      the operational queue limit.
      
      The third element is the threshold that marks the transition from 
      congestion state 2 to congestion state 1. This is the threshold at 
      which traffic with DP = 2 is discarded. This threshold is set 
      approximately at 75 percent of the first parameter, the operational 
      queue limit.
      
      The fourth element is the threshold that marks the transition from 
      congestion state 3 to congestion state 2. This is the threshold at 
      which traffic with DP = 3 is discarded. This threshold is set 
      approximately at 35 percent of the first parameter, the operational 
      queue limit."
::= { atmIfVpt 352 }

atmIfVptTxQThreshEntry OBJECT-TYPE
   SYNTAX     AtmIfVptTxQThreshEntry
   ACCESS     not-accessible
   STATUS     obsolete
   DESCRIPTION
     "An entry in the atmIfVptTxQThreshTable."
   INDEX {
      atmIfIndex,
      atmIfVptIndex,
      atmIfVptTxQThreshIndex }
::= { atmIfVptTxQThreshTable 1 }

AtmIfVptTxQThreshEntry ::= SEQUENCE {
   atmIfVptTxQThreshIndex
      Integer32,
   atmIfVptTxQThreshValue
      Unsigned32 }

atmIfVptTxQThreshIndex OBJECT-TYPE
   SYNTAX     Integer32 (0..3)
   ACCESS     not-accessible
   STATUS     obsolete
   DESCRIPTION
     "This variable represents the atmIfVptTxQThreshTable
      specific index for the atmIfVptTxQThreshTable."
::= { atmIfVptTxQThreshEntry 1 }

atmIfVptTxQThreshValue OBJECT-TYPE
   SYNTAX     Unsigned32 (0..30720)
   ACCESS     read-only
   STATUS     obsolete
   DESCRIPTION
     "This variable represents an individual value for the
      atmIfVptTxQThreshTable."
::= { atmIfVptTxQThreshEntry 2 }

atmIfVptFqpTable OBJECT-TYPE
   SYNTAX     SEQUENCE OF AtmIfVptFqpEntry
   ACCESS     not-accessible
   STATUS     obsolete
   DESCRIPTION
     "This attribute is HISTORICAL. Please refer to the attribute of the 
      same name in the group AtmTmOper.
      
      This attribute is a vector of three elements that indicate the quality 
      of service parameters for the forward direction for this connection. 
      This attribute is used for SPVC and SVC connections on a PNNI 
      interface.
      
      The cdv element indicates the acceptable peak-to-peak Cell Delay 
      Variation (CDV) of real-time connections (CBR, and rt-VBR). 
      
      The ctd element indicates the acceptable maximum Cell Transfer 
      Delay (maxCtd) of real-time connections (CBR, and rt-VBR). 
      
      The clr element indicates the acceptable Cell Loss Ratio (CLR) of 
      CBR, rt-VBR, and nrt-VBR connections."
::= { atmIfVpt 357 }

atmIfVptFqpEntry OBJECT-TYPE
   SYNTAX     AtmIfVptFqpEntry
   ACCESS     not-accessible
   STATUS     obsolete
   DESCRIPTION
     "An entry in the atmIfVptFqpTable."
   INDEX {
      atmIfIndex,
      atmIfVptIndex,
      atmIfVptFqpIndex }
::= { atmIfVptFqpTable 1 }

AtmIfVptFqpEntry ::= SEQUENCE {
   atmIfVptFqpIndex
      INTEGER,
   atmIfVptFqpValue
      Unsigned32 }

atmIfVptFqpIndex OBJECT-TYPE
   SYNTAX     INTEGER  {
                 cdv(0),
                 ctd(1),
                 clr(2) }
   ACCESS     not-accessible
   STATUS     obsolete
   DESCRIPTION
     "This variable represents the atmIfVptFqpTable
      specific index for the atmIfVptFqpTable."
::= { atmIfVptFqpEntry 1 }

atmIfVptFqpValue OBJECT-TYPE
   SYNTAX     Unsigned32 (0..2147483647)
   ACCESS     read-only
   STATUS     obsolete
   DESCRIPTION
     "This variable represents an individual value for the
      atmIfVptFqpTable."
::= { atmIfVptFqpEntry 2 }

atmIfVptBqpTable OBJECT-TYPE
   SYNTAX     SEQUENCE OF AtmIfVptBqpEntry
   ACCESS     not-accessible
   STATUS     obsolete
   DESCRIPTION
     "This attribute is HISTORICAL. Please refer to the attribute of the 
      same name in the group AtmTmOper.
      
      This attribute is a vector of three elements that indicate the quality 
      of service parameters for the backward direction for this 
      connection. This attribute is used for SPVC and SVC connections 
      on a PNNI interface.
      
      The cdv element indicates the acceptable peak-to-peak Cell Delay 
      Variation (CDV) of real-time connections (CBR, and rt-VBR). 
      
      The ctd element indicates the acceptable maximum Cell Transfer 
      Delay (maxCtd) of real-time connections (CBR, and rt-VBR). 
      
      The clr element indicates the acceptable Cell Loss Ratio (CLR) of 
      CBR, rt-VBR, and nrt-VBR connections."
::= { atmIfVpt 358 }

atmIfVptBqpEntry OBJECT-TYPE
   SYNTAX     AtmIfVptBqpEntry
   ACCESS     not-accessible
   STATUS     obsolete
   DESCRIPTION
     "An entry in the atmIfVptBqpTable."
   INDEX {
      atmIfIndex,
      atmIfVptIndex,
      atmIfVptBqpIndex }
::= { atmIfVptBqpTable 1 }

AtmIfVptBqpEntry ::= SEQUENCE {
   atmIfVptBqpIndex
      INTEGER,
   atmIfVptBqpValue
      Unsigned32 }

atmIfVptBqpIndex OBJECT-TYPE
   SYNTAX     INTEGER  {
                 cdv(0),
                 ctd(1),
                 clr(2) }
   ACCESS     not-accessible
   STATUS     obsolete
   DESCRIPTION
     "This variable represents the atmIfVptBqpTable
      specific index for the atmIfVptBqpTable."
::= { atmIfVptBqpEntry 1 }

atmIfVptBqpValue OBJECT-TYPE
   SYNTAX     Unsigned32 (0..2147483647)
   ACCESS     read-only
   STATUS     obsolete
   DESCRIPTION
     "This variable represents an individual value for the
      atmIfVptBqpTable."
::= { atmIfVptBqpEntry 2 }


-- AtmIf/n Vpt/vpi Vpd
-- The VptVpd component contains provisioning information about its 
-- parent Vpt component.

atmIfVptVpd OBJECT IDENTIFIER ::= { atmIfVpt 2 }



atmIfVptVpdRowStatusTable OBJECT-TYPE
   SYNTAX     SEQUENCE OF AtmIfVptVpdRowStatusEntry
   ACCESS     not-accessible
   STATUS     mandatory
   DESCRIPTION
     "This entry controls the addition and deletion of 
      atmIfVptVpd components."
::= { atmIfVptVpd 1 }

atmIfVptVpdRowStatusEntry OBJECT-TYPE
   SYNTAX     AtmIfVptVpdRowStatusEntry
   ACCESS     not-accessible
   STATUS     mandatory
   DESCRIPTION
     "A single entry in the table represents a single 
      atmIfVptVpd component."
   INDEX {
      atmIfIndex,
      atmIfVptIndex,
      atmIfVptVpdIndex }
::= { atmIfVptVpdRowStatusTable 1 }

AtmIfVptVpdRowStatusEntry ::= SEQUENCE {
   atmIfVptVpdRowStatus
      RowStatus,
   atmIfVptVpdComponentName
      DisplayString,
   atmIfVptVpdStorageType
      StorageType,
   atmIfVptVpdIndex
      NonReplicated }

atmIfVptVpdRowStatus OBJECT-TYPE
   SYNTAX     RowStatus 
   ACCESS     read-only
   STATUS     mandatory
   DESCRIPTION
     "This variable is used as the basis for SNMP naming of
      atmIfVptVpd components.
      These components cannot be added nor deleted."
::= { atmIfVptVpdRowStatusEntry 1 }

atmIfVptVpdComponentName OBJECT-TYPE
   SYNTAX     DisplayString 
   ACCESS     read-only
   STATUS     mandatory
   DESCRIPTION
     "This variable provides the component's string name for
      use with the ASCII Console Interface"
::= { atmIfVptVpdRowStatusEntry 2 }

atmIfVptVpdStorageType OBJECT-TYPE
   SYNTAX     StorageType 
   ACCESS     read-only
   STATUS     mandatory
   DESCRIPTION
     "This variable represents the storage type value for the
      atmIfVptVpd tables."
::= { atmIfVptVpdRowStatusEntry 4 }

atmIfVptVpdIndex OBJECT-TYPE
   SYNTAX     NonReplicated 
   ACCESS     not-accessible
   STATUS     mandatory
   DESCRIPTION
     "This variable represents the index for the atmIfVptVpd tables."
::= { atmIfVptVpdRowStatusEntry 10 }

atmIfVptVpdLbkTable OBJECT-TYPE
   SYNTAX     SEQUENCE OF AtmIfVptVpdLbkEntry
   ACCESS     not-accessible
   STATUS     mandatory
   DESCRIPTION
     "This group contains the provisionable loopback attributes for a Vcc, 
      Vpc, or Vpt component.
      
      Note that certain loopback requests may not be possible on a given 
      connection. In such cases, the corresponding operational loopback 
      attribute in the Status group of the Vcc, Vpc, or Vpt component is 
      set to notApplicable and the requested loopback is not performed.
      
      If loopbacks are provisioned to be on, and for any reason the 
      segment or end-to-end OAM loopback cells are not relayed, the 
      connection component becomes troubled, and user cell traffic may 
      be discarded. If loopbacks are provisioned to be on, all of the nodes 
      in the segment, and external networks which are in the end-to-end 
      connection must relay the OAM loopback cells."
::= { atmIfVptVpd 100 }

atmIfVptVpdLbkEntry OBJECT-TYPE
   SYNTAX     AtmIfVptVpdLbkEntry
   ACCESS     not-accessible
   STATUS     mandatory
   DESCRIPTION
     "An entry in the atmIfVptVpdLbkTable."
   INDEX {
      atmIfIndex,
      atmIfVptIndex,
      atmIfVptVpdIndex }
::= { atmIfVptVpdLbkTable 1 }

AtmIfVptVpdLbkEntry ::= SEQUENCE {
   atmIfVptVpdSegLinkSideLoopback
      INTEGER,
   atmIfVptVpdSegSwitchSideLoopback
      INTEGER,
   atmIfVptVpdEndToEndLoopback
      INTEGER,
   atmIfVptVpdLoopbackMonitoring
      INTEGER }

atmIfVptVpdSegLinkSideLoopback OBJECT-TYPE
   SYNTAX     INTEGER  {
                 on(0),
                 off(1),
                 sameAsInterface(2) }
   ACCESS     read-write
   STATUS     mandatory
   DESCRIPTION
     "This attribute specifies whether link-side segment loopback 
      insertion should be performed on this connection. 
      
      When sameAsInterface is selected, the link-side segment loopback 
      insertion for the connection is based on the segLinkSideLoopback 
      attribute of the connection's parent AtmIf componentif the ATM 
      interface has link-side segment loopback insertion turned on, then 
      link-side segment loopback insertion is also on for the connection. 
      
      When on or off is selected, link-side segment loopback insertion is 
      turned on or off respectively for the connection regardless of the 
      provisioning of the parent AtmIf component.
      
      Note that link-side segment loopback insertion is not possible if the 
      connectionPointType attribute of the Vcc or Vpc component is 
      connectingPoint. Link-side segment loopback insertion is also not 
      possible if the distributionType of the Vcc is pointToMultipoint. In 
      such cases, the associated segLinkSideLoopbackState attribute 
      indicates notApplicable and link-side segment loopback insertion is 
      not performed. Link-side segment loopback insertion is always 
      possible on a Vpt."
   DEFVAL     { sameAsInterface }
::= { atmIfVptVpdLbkEntry 10 }

atmIfVptVpdSegSwitchSideLoopback OBJECT-TYPE
   SYNTAX     INTEGER  {
                 on(0),
                 off(1),
                 sameAsInterface(2) }
   ACCESS     read-write
   STATUS     mandatory
   DESCRIPTION
     "This attribute specifies whether switch-side segment loopback 
      insertion should be performed on this connection.
      
      When sameAsInterface is selected, the switch-side segment 
      loopback for the connection is based on the segSwitchSideLoopback 
      attribute of the connection's parent AtmIf componentif the ATM 
      interface has switch-side segment loopback insertion turned on, 
      then switch-side segment loopback insertion is also on for the 
      connection. 
      
      When on or off is selected, switch-side segment loopback insertion 
      is turned on or off respectively for the connection regardless of the 
      provisioning of the parent AtmIf component.
      
      Note that switch-side segment loopback insertion is not possible if 
      the connectionPointType attribute of the Vcc or Vpc component is 
      connectingPoint or connectionEndPoint. Switch-side segment 
      loopback insertion is also not possible if the distributionType of the 
      Vcc is pointToMultipoint In such cases, the associated 
      segSwitchSideLoopbackState attribute indicates notApplicable and 
      switch-side segment loopback insertion is not performed. Switch-
      side segment loopback is never possible on a Vpt."
   DEFVAL     { sameAsInterface }
::= { atmIfVptVpdLbkEntry 20 }

atmIfVptVpdEndToEndLoopback OBJECT-TYPE
   SYNTAX     INTEGER  {
                 on(0),
                 off(1),
                 sameAsInterface(2) }
   ACCESS     read-write
   STATUS     mandatory
   DESCRIPTION
     "This attribute specifies whether end-to-end loopback insertion 
      should be performed on this connection.
      
      When sameAsInterface is selected, the end-to-end loopback for the 
      connection is based on the endToEndLoopback attribute of the 
      connection's parent AtmIf componentif the ATM interface has 
      end-to-end loopback insertion turned on, then end-to-end loopback 
      insertion is also on for the connection. 
      
      When on or off is selected, end-to-end loopback insertion is turned 
      on or off respectively for the connection regardless of the 
      provisioning of the parent AtmIf component.
      
      Note that end-to-end loopback insertion is not possible if the 
      connectionPointType attribute of the Vcc or Vpc component is 
      connectingPoint or segmentEndPoint. End-to-end loopback 
      insertion is also not possible if the distributionType of the Vcc is 
      pointToMultipoint. In such cases, the associated 
      endToEndLoopbackState attribute indicates notApplicable and end-
      to-end loopback insertion is not performed. End-to-end loopback 
      insertion is always possible on a Vpt."
   DEFVAL     { sameAsInterface }
::= { atmIfVptVpdLbkEntry 30 }

atmIfVptVpdLoopbackMonitoring OBJECT-TYPE
   SYNTAX     INTEGER  {
                 on(0),
                 off(1),
                 sameAsInterface(2) }
   ACCESS     read-write
   STATUS     mandatory
   DESCRIPTION
     "This attribute specifies whether or not a connection monitors the 
      OAM stream for loopback cells. Currently this attributed is only 
      applied to Passport-specific trace cells and only affects 
      connectingPoints.
      
      When sameAsInterface is selected, the trace visibility for the 
      connection is based on the traceVisible attribute of the connection's 
      parent AtmIf componentif the ATM interface is trace visible, then 
      the connection is also trace visible. 
      
      When on or off is selected, the connection is nor isn't visible to 
      trace cells respectively for the connection regardless of the 
      provisioning of the parent AtmIf component.
      
      Note that trace visibility only affects connections whose 
      connectionPointType attribute of the Vcc or Vpc component is 
      connectingPoint. Trace visibility is also not possible if the 
      distributionType of the Vcc is pointToMultipoint."
   DEFVAL     { sameAsInterface }
::= { atmIfVptVpdLbkEntry 1000 }

atmIfVptVpdTrafficTable OBJECT-TYPE
   SYNTAX     SEQUENCE OF AtmIfVptVpdTrafficEntry
   ACCESS     not-accessible
   STATUS     mandatory
   DESCRIPTION
     "This group contains traffic related provisionable attributes for the 
      Vcc and Vpc components. The attributes' operational values are 
      reflected in the Traffic group for these components. Changing any 
      of the attributes in this group causes a service interruption on the 
      Vcc or Vpc component."
::= { atmIfVptVpd 110 }

atmIfVptVpdTrafficEntry OBJECT-TYPE
   SYNTAX     AtmIfVptVpdTrafficEntry
   ACCESS     not-accessible
   STATUS     mandatory
   DESCRIPTION
     "An entry in the atmIfVptVpdTrafficTable."
   INDEX {
      atmIfIndex,
      atmIfVptIndex,
      atmIfVptVpdIndex }
::= { atmIfVptVpdTrafficTable 1 }

AtmIfVptVpdTrafficEntry ::= SEQUENCE {
   atmIfVptVpdTxTrafficDescType
      INTEGER,
   atmIfVptVpdTxQosClass
      INTEGER,
   atmIfVptVpdFwdQosClass
      INTEGER,
   atmIfVptVpdHoldingPriority
      INTEGER,
   atmIfVptVpdRxTrafficDescType
      INTEGER,
   atmIfVptVpdRxQosClass
      INTEGER,
   atmIfVptVpdBwdQosClass
      INTEGER,
   atmIfVptVpdAtmServiceCategory
      INTEGER,
   atmIfVptVpdTrafficShaping
      INTEGER,
   atmIfVptVpdUnshapedTransmitQueueing
      INTEGER,
   atmIfVptVpdUsageParameterControl
      INTEGER,
   atmIfVptVpdBearerClassBbc
      INTEGER,
   atmIfVptVpdTransferCapabilityBbc
      INTEGER,
   atmIfVptVpdClippingBbc
      INTEGER,
   atmIfVptVpdBestEffort
      INTEGER,
   atmIfVptVpdFwdFrameDiscard
      INTEGER,
   atmIfVptVpdBwdFrameDiscard
      INTEGER }

atmIfVptVpdTxTrafficDescType OBJECT-TYPE
   SYNTAX     INTEGER  {
                 n1(1),
                 n2(2),
                 n3(3),
                 n4(4),
                 n5(5),
                 n6(6),
                 n7(7),
                 n8(8),
                 n9(9) }
   ACCESS     read-write
   STATUS     obsolete
   DESCRIPTION
     "This attribute is migrated to the AtmTmProv group.
      
      This attribute specifies the type of traffic management which is 
      applied to the transmit direction of this connection as defined in the 
      ATM Forum. The txTrafficDescType determines the number and 
      meaning of the parameters in the txTrafficDescParm attribute."
   DEFVAL     { n1 }
::= { atmIfVptVpdTrafficEntry 10 }

atmIfVptVpdTxQosClass OBJECT-TYPE
   SYNTAX     INTEGER  {
                 unspecified(0),
                 constantBitRate(1),
                 variableBitRate(2),
                 connectionOriented(3),
                 connectionless(4) }
   ACCESS     read-write
   STATUS     obsolete
   DESCRIPTION
     "This attribute specifies the quality of service for the transmit 
      direction for this connection.
      
      The constantBitRate class refers to traffic offered on services such 
      as a constant bit rate video service. This traffic is highest priority.
      
      The variableBitRate class refers to traffic offered on services such 
      as packetized audio and video.
      
      The connectionOriented class refers to connection-oriented traffic 
      such as Frame Relay or X.25 traffic. 
      
      The connectionless traffic refers to traffic offered through 
      connectionless trunks such as certain LAN protocols.
      
      The unspecified class supports a 'best effort' type of service, where 
      there is a minimum guarantee of bandwidth. This traffic is lowest 
      priority.
      
      This attribute is obsolete. The value is migrated into 
      atmServiceCategory. The atmServiceCategory applies in both 
      transmit and receive directions.
      
      unspecified maps to unspecifiedBitRate;
      constantBitRate maps to constantBitRate;
      variableBitRate maps to variableBitRateRt;
      connectionOriented maps to variableBitRateNrt
      connectionless maps to variableBitRateNrt"
   DEFVAL     { connectionOriented }
::= { atmIfVptVpdTrafficEntry 20 }

atmIfVptVpdFwdQosClass OBJECT-TYPE
   SYNTAX     INTEGER  {
                 n0(0),
                 n1(1),
                 n2(2),
                 n3(3),
                 n4(4) }
   ACCESS     read-write
   STATUS     obsolete
   DESCRIPTION
     "This attribute is migrated to the AtmTmProv group.
      
      This attribute specifies the quality of service for the forward 
      direction for this connection. This attribute is only used for SPVC 
      connections.
      
      Class 1 supports a QOS that meets Service Class A performance 
      requirements (Circuit emulation, constant bit rate video).
      
      Class 2 supports a QOS that meets Service Class B performance 
      requirements (Variable bit rate audio and video).
      
      Class 3 supports a QOS that meets Service Class C performance 
      requirements (Connection-Oriented Data Transfer).
      
      Class 4 supports a QOS that meets Service Class D performance 
      requirements (Connectionless Data Transfer).
      
      Class 0 is the unspecified bit rate QOS class; no objective is 
      specified for the performance parameters."
   DEFVAL     { n0 }
::= { atmIfVptVpdTrafficEntry 21 }

atmIfVptVpdHoldingPriority OBJECT-TYPE
   SYNTAX     INTEGER  {
                 n0(0),
                 n1(1),
                 n2(2),
                 n3(3),
                 n4(4) }
   ACCESS     read-write
   STATUS     obsolete
   DESCRIPTION
     "This attribute is migrated to the AtmTmProv group.
      
      This attribute specifies the holding priority of this connection. In a 
      situation where the link bandwidth fluctuates, such as over an IMA 
      link, holding priority is used to determine which connections are 
      held and which are released. Holding priority 4 connections are the 
      first to be released. Holding priority 0 connections are the last to be 
      released. This value provisioned in the Vcd or Vpd may be 
      overridden by certain applications, for example Vcc Test, which run 
      over this connection. The default holding priority for a provisioned 
      connection is higher then default holding priorities for dynamic 
      (SVC) connections."
   DEFVAL     { n2 }
::= { atmIfVptVpdTrafficEntry 25 }

atmIfVptVpdRxTrafficDescType OBJECT-TYPE
   SYNTAX     INTEGER  {
                 n1(1),
                 n2(2),
                 n3(3),
                 n4(4),
                 n5(5),
                 n6(6),
                 n7(7),
                 n8(8),
                 sameAsTx(15) }
   ACCESS     read-write
   STATUS     obsolete
   DESCRIPTION
     "This attribute is migrated to the AtmTmProv group.
      
      This attribute specifies the type of traffic management which is 
      applied to the receive direction of this connection as defined in the 
      ATM Forum. The rxTrafficDescType determines the number and 
      meaning of the parameters in the rxTrafficDescParm attribute
      
      When sameAsTx is selected, the rxTrafficDescType as well as the 
      rxTrafficDescParm are taken from the transmit values."
   DEFVAL     { sameAsTx }
::= { atmIfVptVpdTrafficEntry 30 }

atmIfVptVpdRxQosClass OBJECT-TYPE
   SYNTAX     INTEGER  {
                 unspecified(0),
                 constantBitRate(1),
                 variableBitRate(2),
                 connectionOriented(3),
                 connectionless(4),
                 sameAsTx(15) }
   ACCESS     read-write
   STATUS     obsolete
   DESCRIPTION
     "This attribute specifies the quality of service for the receive 
      direction for this connection.
      
      The constantBitRate class refers to traffic offered on services such 
      as a constant bit rate video service. 
      
      The variableBitRate class refers to traffic offered on services such 
      as packetized audio and video. 
      
      The connectionOriented class refers to connection-oriented traffic.
      
      The connectionless traffic refers to traffic offered through 
      connectionless trunks. 
      
      The unspecified class supports a 'best effort' type of service, where 
      there is a minimum guarantee of bandwidth. 
      
      The sameAsTx selection sets the receive quality of service to be the 
      same as the transmit quality of service.
      
      This attribute is obsolete. The value of txQosClass is migrated into 
      atmServiceCategory. The value of this attribute is ignored. 
      AtmServiceCategory applies in both transmit and receive directions."
   DEFVAL     { sameAsTx }
::= { atmIfVptVpdTrafficEntry 40 }

atmIfVptVpdBwdQosClass OBJECT-TYPE
   SYNTAX     INTEGER  {
                 n0(0),
                 n1(1),
                 n2(2),
                 n3(3),
                 n4(4),
                 sameAsFwd(15) }
   ACCESS     read-write
   STATUS     obsolete
   DESCRIPTION
     "This attribute is migrated to the AtmTmProv group.
      
      This attribute specifies the quality of service for the backward 
      direction for this connection. This attribute is only used for SPVC 
      connections.
      
      Class 1 supports a QOS that meets Service Class A performance 
      requirements (Circuit emulation, constant bit rate video).
      
      Class 2 supports a QOS that meets Service Class B performance 
      requirements (Variable bit rate audio and video).
      
      Class 3 supports a QOS that meets Service Class C performance 
      requirements (Connection-Oriented Data Transfer).
      
      Class 4 supports a QOS that meets Service Class D performance 
      requirements (Connectionless Data Transfer).
      
      Class 0 is the unspecified bit rate QOS class; no objective is 
      specified for the performance parameters.
      
      The sameAsFwd selection sets the backward quality of service to 
      be the same as the forward quality of service."
   DEFVAL     { sameAsFwd }
::= { atmIfVptVpdTrafficEntry 41 }

atmIfVptVpdAtmServiceCategory OBJECT-TYPE
   SYNTAX     INTEGER  {
                 unspecifiedBitRate(0),
                 constantBitRate(1),
                 rtVariableBitRate(2),
                 nrtVariableBitRate(3),
                 derivedFromBBC(15) }
   ACCESS     read-write
   STATUS     obsolete
   DESCRIPTION
     "This attribute is migrated to the AtmTmProv group.
      
      This attribute specifies the ATM service category for both directions 
      of the connection. 
      
      The value derivedFromBBC may only be used if the SrcPvc 
      component is provisioned under this Vcc.Otherwise a specific ATM 
      service category must be specified. 
      
      If this attribute is set to derivedFromBBC, the Broadband Bearer 
      Capability (BBC) and bestEffort attributes are used to determine the 
      atmServiceCategory of this connection. 
      
      If this attribute is set to other than derivedFromBBC, the value of 
      this attribute is used to override the provisioned BBC Information 
      Element parameters. In those cases, the BBC attributes are not used. 
      
      The constantBitRate service category is intended for real time 
      applications, that is those requiring tightly constrained delay and 
      delay variation, as would be appropriate for voice and video 
      applications. The consistent availability of a fixed quantity of 
      bandwidth is considered appropriate for CBR service. Cells which 
      are delayed beyond the value specified by Cell Transfer Delay are 
      assumed to be of significantly reduce value to the application.
      
      The rtVariableBitRate service category is intended for real time 
      applications, that is those requiring tightly constrained delay and 
      delay variation, as would be appropriate for voice and video 
      applications. Sources are expected to transmit at a rate which varies 
      with time. Equivalently, the source can be described as 'bursty'. 
      Cells which are delayed beyond the value specified by CTD are 
      assumed to be of significantly reduced value to the application. Real 
      time VBR service may support statistical multiplexing of real time 
      sources.
      
      The nrtVariableBitRate service category is intended for non-real 
      time applications which have bursty traffic characteristics and which 
      can be characterized in terms of a PCR, SCR, and MBS. For those 
      cells which are transferred within the traffic contract, the application 
      expects a low cell loss ratio. For all connections, it expects a bound 
      on the mean cell transfer delay. Non-real time VBR service may 
      support statistical multiplexing of connections.
      
      The unspecifiedBitRate service is intended for non-real time 
      applications; that is, those not requiring tightly constrained delay 
      and delay variation. UBR sources are expected to be bursty. UBR 
      service supports a high degree of statistical multiplexing among 
      sources. UBR service does not specify traffic related service 
      guarantees. No numerical commitments are made with respect to 
      the cell loss ratio experienced by a UBR connection, or as to the 
      cell transfer delay experienced by cells on the connection."
   DEFVAL     { unspecifiedBitRate }
::= { atmIfVptVpdTrafficEntry 42 }

atmIfVptVpdTrafficShaping OBJECT-TYPE
   SYNTAX     INTEGER  {
                 disabled(1),
                 sameAsInterface(2) }
   ACCESS     read-write
   STATUS     obsolete
   DESCRIPTION
     "This attribute is migrated to the AtmTmProv group.
      
      This attribute specifies whether this connection uses traffic shaping 
      when transmitting traffic to the ATM interface.
      
      When sameAsInterface is selected, traffic shaping for the 
      connection is based on the trafficShaping attribute of the 
      connection's parent AtmIf componentif the ATM interface has 
      traffic shaping enabled, then traffic shaping is enabled for the 
      connection. Note that enabling traffic shaping may have no effect 
      under certain cases. These cases are listed in the description of the 
      trafficShaping operational attribute, which is under the Vcc and Vpc 
      components.
      
      When disabled is selected, traffic shaping for this connection is 
      disabled regardless of the provisioning of the parent AtmIf 
      component."
   DEFVAL     { sameAsInterface }
::= { atmIfVptVpdTrafficEntry 50 }

atmIfVptVpdUnshapedTransmitQueueing OBJECT-TYPE
   SYNTAX     INTEGER  {
                 common(1),
                 sameAsInterface(3) }
   ACCESS     read-write
   STATUS     obsolete
   DESCRIPTION
     "This attribute is migrated to the AtmTmProv group.
      
      This attribute only applies when this connection is unshaped. This 
      attribute defines the transmit queueing method for this connection if 
      it is unshaped. Refer to the unshapedTransmitQueueing attribute 
      under the AtmIf for more details on the meaning of this attribute. 
      
      When this attribute is set to sameAsInterface, the value from the 
      AtmIf is used. 
      
      When this attribute is set to common, transmit traffic on this 
      unshaped connection is destined for the common queue."
   DEFVAL     { sameAsInterface }
::= { atmIfVptVpdTrafficEntry 60 }

atmIfVptVpdUsageParameterControl OBJECT-TYPE
   SYNTAX     INTEGER  {
                 disabled(1),
                 sameAsInterface(2) }
   ACCESS     read-write
   STATUS     obsolete
   DESCRIPTION
     "This attribute is migrated to the AtmTmProv group.
      
      This attribute specifies whether this connection enforces usage 
      parameter control when receiving traffic from the ATM interface.
      
      When sameAsInterface is selected, UPC for the connection is 
      based on the usageParameterControl attribute of the connection's 
      parent AtmIf componentif the ATM interface has UPC enabled, 
      then UPC is enabled for the connection. Note that enabling UPC 
      may have no effect under certain cases. These cases are listed in the 
      description of the usageParameterControl operational attribute, 
      which is under the Vcc and Vpc components.
      
      When disabled is selected, UPC for this connection is disabled 
      regardless of the provisioning of the parent AtmIf component."
   DEFVAL     { sameAsInterface }
::= { atmIfVptVpdTrafficEntry 70 }

atmIfVptVpdBearerClassBbc OBJECT-TYPE
   SYNTAX     INTEGER  {
                 a(1),
                 c(3),
                 x(16),
                 vp(24),
                 derivedFromServiceCategory(31) }
   ACCESS     read-write
   STATUS     obsolete
   DESCRIPTION
     "This attribute is migrated to the AtmTmProv group.
      
      This attribute specifies the bearer capability. This attribute is only 
      used for SPVC and SPVP connections. It is one of the Broadband 
      Bearer Capability (BBC) attributes. The purpose of the BBC 
      information element is to indicate a requested broadband 
      connection-oriented bearer service to be provided by the network.
      
      The value derivedFromServiceCategory specifies that the actual 
      value which is used for this connection is derived from the value of 
      the atmServiceCategory. Either, this attribute must be set to 
      derivedFromServiceCategory, or the atmServiceCategory attribute 
      must be set to derivedFromBBC, but not both.
      
      Class a service is a connection-oriented, constant bit rate ATM 
      transport service. Class a service has end to end timing 
      requirements and may require stringent cell loss, cell delay and cell 
      delay variation performance.When a is set, the user is requesting 
      more than an ATM only service. The network may look at the AAL 
      to provide interworking based upon its contents. 
      
      Class c service is a connection-oriented, variable bit rate ATM 
      transport service. Class c service has no end-to-end timing 
      requirements. When c is set, the user is requesting more than an 
      ATM only service. The network interworking function may look at 
      the AAL and provide service based on it.
      
      Class x service is a connection-oriented ATM transport service 
      where the AAL, trafficType (vbr or cbr) and timing requirements 
      are user defined (that is, transparent to the network).When x is set 
      the user is requesting an ATM only service from the network.
      
      Class vp service is used to specify a transparent VP service. When 
      the value of this attribute is vp, the user is requesting an ATM only 
      service from the network. In this case, the network shall not process 
      any higher layer protocol. This service differs from class x service 
      in that with the class vp service both the VCI field (except or VCI 
      values 0, 3, 4, and 6 through 15) and Payload Type field are 
      transported transparently by the network. This attribute value is 
      only applicable to SPVP connections."
   DEFVAL     { derivedFromServiceCategory }
::= { atmIfVptVpdTrafficEntry 71 }

atmIfVptVpdTransferCapabilityBbc OBJECT-TYPE
   SYNTAX     INTEGER  {
                 n0(0),
                 n1(1),
                 n2(2),
                 n5(5),
                 n8(8),
                 n9(9),
                 n10(10),
                 notApplicable(30),
                 derivedFromServiceCategory(31) }
   ACCESS     read-write
   STATUS     obsolete
   DESCRIPTION
     "This attribute is migrated to the AtmTmProv group.
      
      This attribute specifies the transfer capability for this connection. 
      Uni 3.0/3.1 traffic type and end-to-end timing parameters are 
      mapped into this parameter as follows:
      <transferCapability: TrafficType, Timing>
      0: NoIndication, NoIndication
      1: NoIndication, yes
      2: NoIndication, no
      5: CBR, yes
      8: VBR, NoIndication
      9: VBR, yes
      10: VBR, no
      
      NotApplicable specifies that the user does not want to specify the 
      transfer capability.
      
      The CBR traffic type refers to traffic offered on services such as a 
      constant bit rate video service or a circuit emulation.
      
      The VBR traffic type refers to traffic offered on services such as 
      packetized audio and video, or data.
      
      The value no indication for traffic type is used if the user has not set 
      the traffic type; similarly for end-to-end timing.
      
      The value yes for end-to-end timing indicates that end-to-end 
      timing is required.
      
      The value no for end-to-end timing indicates that end-to-end timing 
      is not required.
      
      The value derivedFromServiceCategory specifies that the actual 
      value which is used for this connection is derived from the value of 
      the atmServiceCategory. Either, this attribute must be set to 
      derivedFromServiceCategory, or the atmServiceCategory attribute 
      must be set to derivedFromBBC, but not both."
   DEFVAL     { derivedFromServiceCategory }
::= { atmIfVptVpdTrafficEntry 72 }

atmIfVptVpdClippingBbc OBJECT-TYPE
   SYNTAX     INTEGER  {
                 no(0),
                 yes(1) }
   ACCESS     read-write
   STATUS     obsolete
   DESCRIPTION
     "This attribute is migrated to the AtmTmProv group.
      
      This attribute specifies the value for the clipping susceptibility 
      parameter in the BBC Information Element. This attribute is only 
      used for SPVC connections. It is one of the Broadband Bearer 
      Capability attributes.
      
      Clipping is an impairment in which the first fraction of a second of 
      information to be transferred is lost. It occurs after a call is 
      answered and before an associated connection is switched through."
   DEFVAL     { no }
::= { atmIfVptVpdTrafficEntry 74 }

atmIfVptVpdBestEffort OBJECT-TYPE
   SYNTAX     INTEGER  {
                 indicated(0),
                 notIndicated(1),
                 derivedFromServiceCategory(15) }
   ACCESS     read-write
   STATUS     obsolete
   DESCRIPTION
     "This attribute is migrated to the AtmTmProv group.
      
      This attribute specifies the value of the best effort parameter in the 
      ATM Traffic Descriptor Information Element. This attribute is only 
      used for Soft PVC connections. It is one of the Broadband Bearer 
      Capability attributes.
      
      The value indicated implies that the quality of service for this 
      connection is not guaranteed.
      
      The value notIndicated implies that the quality of service for this 
      connection is guaranteed.
      
      The value derivedFromServiceCategory specifies that the actual 
      value which is used for this connection is derived from the value of 
      the atmServiceCategory. Either, this attribute must be set to 
      derivedFromServiceCategory, or the atmServiceCategory attribute 
      must be set to derivedFromBBC, but not both."
   DEFVAL     { derivedFromServiceCategory }
::= { atmIfVptVpdTrafficEntry 75 }

atmIfVptVpdFwdFrameDiscard OBJECT-TYPE
   SYNTAX     INTEGER  {
                 notIndicated(0),
                 indicated(1) }
   ACCESS     read-write
   STATUS     obsolete
   DESCRIPTION
     "This attribute specifies the activation of frame discard functionality 
      in the forward data direction, at relay points, for this connection. It 
      applies to each hop of the connection. Frame discard functions 
      should not be requested if this connection is not transferring frame 
      (AAL5) traffic. Setting the value to indicated for any other traffic 
      type results in all traffic being discarded.
      
      If this connection point is a permanent (provisioned) VCC mid-
      point, this attribute specifies whether the Partial Packet 
      Discard (PPD) function is to be enabled or disabled in the transmit 
      direction at this connecting point. The PPD function allows the 
      connecting point to discard the remainder of a cell-forwarded AAL5 
      frame if one cell of this frame has been discarded. The PPD 
      function increases the 'goodput' of the link, since cells which are 
      only going to be discarded by the AAL5 reassembly are not 
      transmitted.
      
      At a permanent VCC connecting point which is not a connection 
      endpoint, when this attribute is set to indicated, the PPD function is 
      applied to transmit traffic at this connecting point. It should not be 
      indicated for connections whose end points are not performing 
      AAL5 segmentation and reassembly. When this attribute is set to 
      notIndicated, the PPD feature is not applied to transmit traffic at 
      this connecting point.
      
      At a SPVC origin on a PNNI interface, a value of indicated 
      specifies that frame discard is requested in the forward direction. 
      The frame discard function for SPVCs consists of PPD at the SPVC 
      origin and at all intermediate connecting points. When this attribute 
      is set to notIndicated, forward frame discard is not requested in the 
      SPVC call setup. Thus PPD is not enabled at the SPVC origin nor at 
      any intermediate connecting point.
      
      At all points along a VPC, this setting is ignored.
      
      At a permanent VCC connection endpoint, this value is ignored. If 
      AAL5 segmentation and reassembly has been requested, PPD and 
      Early Packet Discard (EPD) are automatically enabled.
      
      This attribute has been migrated to txFrameDiscard."
   DEFVAL     { notIndicated }
::= { atmIfVptVpdTrafficEntry 76 }

atmIfVptVpdBwdFrameDiscard OBJECT-TYPE
   SYNTAX     INTEGER  {
                 notIndicated(0),
                 indicated(1) }
   ACCESS     read-write
   STATUS     obsolete
   DESCRIPTION
     "This attribute specifies the activation of frame discard functionality 
      in the backward data direction, at relay points, for this connection. 
      It applies to each hop of the connection. Frame discard functions 
      should not be requested if this connection is not transferring frame 
      (AAL5) traffic. Setting the value to indicated for any other traffic 
      type results in all traffic being discarded.
      
      If this connection point is a permanent (provisioned) VCC mid-
      point, this attribute specifies whether the Partial Packet Discard 
      (PPD) function is to be enabled or disabled in the receive direction 
      at this connecting point. The PPD function allows the connecting 
      point to discard the remainder of a cell-forwarded AAL5 frame if 
      one cell of this frame has been discarded. The PPD function 
      increases the 'goodput' of the link, since cells which are only going 
      to be discarded by the AAL5 reassembly are not received.
      
      At a permanent VCC connecting point which is not a connection 
      endpoint, when this attribute is set to indicated, the PPD function is 
      applied to receive traffic at this connecting point. It should not be 
      indicated for connections whose end points are not performing 
      AAL5 segmentation and reassembly. When this attribute is set to 
      notIndicated, the PPD feature is not applied to receive traffic at this 
      connecting point.
      
      At a SPVC origin on a PNNI interface, a value of indicated 
      specifies that frame discard is requested in the backward direction. 
      The frame discard function for SPVCs consists of PPD at the SPVC 
      origin and at all intermediate connecting points. When this attribute 
      is set to notIndicated, backwards frame discard is not requested in 
      the SPVC call setup. Thus PPD is not enabled at the SPVC origin 
      nor at any intermediate connecting point.
      
      At all points along a VPC, this setting is ignored.
      
      At a permanent VCC connection endpoint, this value is ignored. If 
      AAL5 segmentation and reassembly has been requested, PPD and 
      Early Packet Discard (EPD) are automatically enabled.
      
      This attribute has been migrated to rxFrameDiscard."
   DEFVAL     { notIndicated }
::= { atmIfVptVpdTrafficEntry 77 }

atmIfVptVpdAcctTable OBJECT-TYPE
   SYNTAX     SEQUENCE OF AtmIfVptVpdAcctEntry
   ACCESS     not-accessible
   STATUS     mandatory
   DESCRIPTION
     "This group contains the provisionable ATM accounting attributes 
      for a Vcc, Vpc, or Vpt component."
::= { atmIfVptVpd 111 }

atmIfVptVpdAcctEntry OBJECT-TYPE
   SYNTAX     AtmIfVptVpdAcctEntry
   ACCESS     not-accessible
   STATUS     mandatory
   DESCRIPTION
     "An entry in the atmIfVptVpdAcctTable."
   INDEX {
      atmIfIndex,
      atmIfVptIndex,
      atmIfVptVpdIndex }
::= { atmIfVptVpdAcctTable 1 }

AtmIfVptVpdAcctEntry ::= SEQUENCE {
   atmIfVptVpdCorrelationTag
      AsciiString }

atmIfVptVpdCorrelationTag OBJECT-TYPE
   SYNTAX     AsciiString (SIZE (0..32))
   ACCESS     read-write
   STATUS     mandatory
   DESCRIPTION
     "This attribute specifies a unique indentifier for each end of a PVC. It 
      that may be used by downstream processing systems to correlate 
      accounting records issued at different nodes in the network. The 
      attribute can be up to 32 bytes long. If it is less than 32 bytes, it is 
      zero filled on the right to create a 32 byte value. The resulting value 
      is recorded in the attribute callConnId for this PVC's ATM 
      accounting records.
      If the attribute is a null string then this PVC does not have any 
      accounting records generated for it."
   DEFVAL     { ''H }  -- ""
::= { atmIfVptVpdAcctEntry 10 }

atmIfVptVpdProvTable OBJECT-TYPE
   SYNTAX     SEQUENCE OF AtmIfVptVpdProvEntry
   ACCESS     not-accessible
   STATUS     mandatory
   DESCRIPTION
     "This group contains the provisionable ATM Virtual Path Descriptor 
      attributes for a Vpt component."
::= { atmIfVptVpd 112 }

atmIfVptVpdProvEntry OBJECT-TYPE
   SYNTAX     AtmIfVptVpdProvEntry
   ACCESS     not-accessible
   STATUS     mandatory
   DESCRIPTION
     "An entry in the atmIfVptVpdProvTable."
   INDEX {
      atmIfIndex,
      atmIfVptIndex,
      atmIfVptVpdIndex }
::= { atmIfVptVpdProvTable 1 }

AtmIfVptVpdProvEntry ::= SEQUENCE {
   atmIfVptVpdVptType
      INTEGER }

atmIfVptVpdVptType OBJECT-TYPE
   SYNTAX     INTEGER  {
                 basic(0),
                 standard(1),
                 virtualLink(2) }
   ACCESS     read-write
   STATUS     mandatory
   DESCRIPTION
     "This attribute specifies the type of the Vpt.
      
      On CQC-based ATM FPs all Vpts must be basic. Vpts on ATM IP 
      FPs may be of any type.
      
      A value of basic configures one level of traffic management (TM) 
      for the VPT, at the VC level. VCs within the VP are treated like 
      independent VCC connections, and thus, are scheduled the same as 
      other VCs under the AtmIf, with no scheduling done for the VP 
      itself.
      
      A value of standard configures two levels of TM for the VPT, one 
      level for VP TM and one level for VC level TM. VCs within the VP 
      use weighted fair queueing (standard VPT VCC scheduling) to 
      schedule VCs within the VPT, with VCs differentiated as either 
      real-time (CBR, rt-VBR) or non-real-time (nrt-VBR, UBR) 
      connections. The VP itself has a full range of emission scheduling 
      and service category differentiation available between itself and the 
      other connections under the AtmIf."
   DEFVAL     { basic }
::= { atmIfVptVpdProvEntry 10 }

atmIfVptVpdTxTdpTable OBJECT-TYPE
   SYNTAX     SEQUENCE OF AtmIfVptVpdTxTdpEntry
   ACCESS     not-accessible
   STATUS     obsolete
   DESCRIPTION
     "This attribute is migrated to the AtmTmProv group.
      
      This attribute is a vector of five traffic parameters whose meanings 
      are defined by the txTrafficDescType attribute. The values of peak 
      cell rate (PCR), sustained cell rate (SCR) and requested shaping rate 
      are expressed in cell/s. Maximum burst size (MBS) is expressed in 
      cells. CDVT is expressed in microseconds. The values of PCR, 
      SCR, MBS and CDVT are used for connection admission control 
      (CAC). The value of CDVT is only used for connections where the 
      atmServiceCategory is constantBitRate. For all other values of 
      atmServiceCategory, CDVT is ignored. The values of PCR, SCR 
      and requested shaping rate are used to determine the actual shaping 
      rate where traffic shaping is enabled.
      
      When txTrafficDescType is 1 or 2, all of the parameters must be set 
      to zero.
      
      When txTrafficDescType is 3, parameter 1 represents the PCR for 
      CLP equal to 0 and 1 traffic; parameter 4 represents the CDVT; and 
      parameter 5 represents the requested shaping rate. A non-zero value 
      in parameter 5 overrides any value in parameter 1. This result is 
      used as the PCR. Parameter 1 must be non-zero. Parameters 2 and 3 
      must be zero.
      
      When txTrafficDescType is 4, parameter 1 represents the PCR for 
      CLP equal to 0 and 1 traffic with cell discard; parameter 2 
      represents the PCR for CLP equal to 0 traffic; parameter 4 
      represents the CDVT; and parameter 5 represents the requested 
      shaping rate. A non-zero value in parameter 5 overrides any value in 
      parameter 1. This result is used as the PCR. Parameter 1 must be 
      greater than or equal to parameter 2. Parameters 1 and 2 must be 
      non-zero. Parameter 3 must be zero.
      
      When txTrafficDescType is 5, parameter 1 represents the PCR for 
      CLP equal to 0 and 1 traffic with cell tagging; parameter 2 
      represents the PCR for CLP equal to 0 traffic; parameter 4 
      represents the CDVT; and parameter 5 represents the requested 
      shaping rate. A non-zero value in parameter 5 overrides any value in 
      parameter 1. This result is used as the PCR. Parameter 1 must be 
      greater than or equal to parameter 2. Parameters 1 and 2 must be 
      non-zero. Parameter 3 must be zero.
      
      When txTrafficDescType is 6, parameter 1 represents the PCR for 
      CLP equal to 0 and 1 traffic; parameter 2 represents the SCR for 
      CLP equal to 0 and 1 traffic; parameter 3 represents the MBS for 
      CLP equal to 0 and 1 traffic; parameter 4 represents the CDVT; and 
      parameter 5 represents the requested shaping rate. A non-zero value 
      in parameter 5 overrides any value in parameter 1. This result is 
      used as the PCR. Parameters 1, 2 and 3 must be non-zero. 
      Parameter 1 must be greater than or equal to parameter 2. Parameter 
      5, must either be zero (unused) or greater than or equal to parameter 
      2.
      
      When txTrafficDescType is 7, parameter 1 represents the PCR for 
      CLP equal to 0 and 1 traffic; parameter 2 represents the SCR for 
      CLP equal to 0 with cell discard; parameter 3 represents the MBS 
      for CLP equal to 0 traffic; parameter 4 represents the CDVT; and 
      parameter 5 represents the requested shaping rate. A non-zero value 
      in parameter 5 overrides any value in parameter 1. This result is 
      used as the PCR. Parameters 1, 2 and 3 must be non-zero. 
      Parameter 1 must be greater than or equal to parameter 2. Parameter 
      5, must either be zero (unused) or greater than or equal to parameter 
      2.
      
      When txTrafficDescType is 8, parameter 1 represents the PCR for 
      CLP equal to 0 and 1 traffic; parameter 2 represents the SCR for 
      CLP equal to 0 traffic with cell tagging; parameter 3 represents the 
      MBS for CLP equal to 0 traffic; parameter 4 represents the CDVT; 
      and parameter 5 represents the requested shaping rate. A non-zero 
      value in parameter 5 overrides any value in parameter 1. This result 
      is used as the PCR. Parameters 1, 2 and 3 must be non-zero. 
      Parameter 1 must be greater than or equal to parameter 2. Parameter 
      5, must either be zero (unused) or greater than or equal to parameter 
      2.
      
      Whenever it is valid for PCR to be specified, parameter 5 may also 
      be used to specify a requested shaping rate. A non-zero value in 
      parameter 5 overrides the value in parameter 1 and is used as the 
      peak cell rate in calculations of CAC and shaping rate.
      
      For txTrafficDescType 3, 4 and 5, the transmit traffic is shaped at 
      the next rate less than the PCR. 
      
      For txTrafficDescType 6, 7 and 8, the transmit traffic is shaped at 
      the highest available rate which is between PCR and SCR. 
      However, if there is no available shaping rate between PCR and 
      SCR, traffic is shaped at the next rate above the PCR."
::= { atmIfVptVpd 297 }

atmIfVptVpdTxTdpEntry OBJECT-TYPE
   SYNTAX     AtmIfVptVpdTxTdpEntry
   ACCESS     not-accessible
   STATUS     obsolete
   DESCRIPTION
     "An entry in the atmIfVptVpdTxTdpTable."
   INDEX {
      atmIfIndex,
      atmIfVptIndex,
      atmIfVptVpdIndex,
      atmIfVptVpdTxTdpIndex }
::= { atmIfVptVpdTxTdpTable 1 }

AtmIfVptVpdTxTdpEntry ::= SEQUENCE {
   atmIfVptVpdTxTdpIndex
      Integer32,
   atmIfVptVpdTxTdpValue
      Unsigned32 }

atmIfVptVpdTxTdpIndex OBJECT-TYPE
   SYNTAX     Integer32 (1..5)
   ACCESS     not-accessible
   STATUS     obsolete
   DESCRIPTION
     "This variable represents the atmIfVptVpdTxTdpTable
      specific index for the atmIfVptVpdTxTdpTable."
::= { atmIfVptVpdTxTdpEntry 1 }

atmIfVptVpdTxTdpValue OBJECT-TYPE
   SYNTAX     Unsigned32 (0..2147483647)
   ACCESS     read-write
   STATUS     obsolete
   DESCRIPTION
     "This variable represents an individual value for the
      atmIfVptVpdTxTdpTable."
::= { atmIfVptVpdTxTdpEntry 2 }

atmIfVptVpdRxTdpTable OBJECT-TYPE
   SYNTAX     SEQUENCE OF AtmIfVptVpdRxTdpEntry
   ACCESS     not-accessible
   STATUS     obsolete
   DESCRIPTION
     "This attribute is migrated to the AtmTmProv group.
      
      This attribute is a vector of four traffic parameters whose meanings 
      are defined by the rxTrafficDescType attribute. The values of peak 
      cell rate (PCR) and sustained cell rate (SCR) are expressed in 
      cell/s. Maximum burst size (MBS) is expressed in cells. The value 
      of CDVT is expressed in microseconds. The values of PCR, SCR, 
      MBS and CDVT are used for usage parameter control (UPC).
      
      When rxTrafficDescType is 1 or 2, all of the parameters must be set 
      to zero (unused).
      
      When rxTrafficDescType is 3, parameter 1 represents the PCR for 
      CLP equal to 0 and 1 traffic. Parameter 1 must be non-zero. 
      Parameters 2 and 3 must be set to zero (unused).
      
      When rxTrafficDescType is 4, parameter 1 represents the PCR for 
      CLP equal to 0 and 1 traffic; parameter 2 represents the PCR for 
      CLP equal to 0 traffic with cell discard. Parameters 1 and 2 must be 
      non-zero. Parameter 3 must be set to zero (unused). Parameter 1 
      must be greater than or equal to parameter 2.
      
      When rxTrafficDescType is 5, parameter 1 represents the PCR for 
      CLP equal to 0 and 1 traffic; parameter 2 represents the PCR for 
      CLP equal to 0 traffic with cell tagging. Parameters 1 and 2 must be 
      non-zero. Parameter 3 must be set to zero (unused). Parameter 1 
      must be greater than or equal to parameter 2.
      
      When rxTrafficDescType is a 6, parameter 1 represents the PCR for 
      CLP equal to 0 and 1 traffic; parameter 2 represents the SCR for 
      CLP equal to 0 and 1 traffic; parameter 3 represents the MBS for 
      CLP equal to 0 and 1 traffic. Parameters 1, 2 and 3 must be non-
      zero. Parameter 1 must be greater than or equal to Parameter 2. 
      
      When rxTrafficDescType is 7, parameter 1 represents the PCR for 
      CLP equal to 0 and 1 traffic; parameter 2 represents the SCR for 
      CLP equal to 0 traffic with cell discard; parameter 3 represents the 
      MBS for CLP equal to 0 traffic. Parameters 1, 2 and 3 must be non-
      zero. Parameter 1 must be greater than or equal to parameter 2. 
      
      When rxTrafficDescType is 8, parameter 1 represents the PCR for 
      CLP equal to 0 and 1 traffic; parameter 2 represents the SCR for 
      CLP equal to 0 traffic with cell tagging; parameter 3 represents the 
      MBS for CLP equal to 0 traffic. Parameter 1, 2 and 3 must be non-
      zero. Parameter 1 must be greater than or equal to parameter 2.
      
      When rxTrafficDescType is any value from 3 through 8, parameter 
      4 represents the CDVT. If this value is zero, the CDVT is taken 
      from the ConnectionAdministrator defaults for the particular 
      atmServiceCategory of this connection.
      
      When rxTrafficDescriptorType is 3 through 8, there are certain 
      extreme combinations of rxTrafficDescParm which are outside the 
      capabilities of the UPC hardware. The check prov command detects 
      such cases and generates an error message. If this happens, adjust 
      the parameters until they fall within the supported limits. 
      
      To calculate the limits, use the following formulae:
      I1 = 1 000 000 000 / PCR
      L1 = CDVT * 1000
      I2 = 1 000 000 000 / SCR
      L2 = CDVT + (MBS - 1) * (I2 - I1)
      I1 and I2 must be less than or equal to 335 523 840. I1 + L1 must 
      be less than or equal to 1 342 156 800. I2 + L2 must be less than or 
      equal to 1 342 156 800. Note that I2 and L2 only apply when the 
      rxTrafficDescriptorType is 6 through 8.
      
      If the values of I1, L1, I2 or L2 are closer to the limits described 
      above, a further restriction applies. Specifically, if either:
      I1 > 41 940 480 or
      I2 > 41 940 480 or
      I1 + L1 > 167 769 600 or
      I2 + L2 > 167 769 600
      then both I1 and I2 must be greater than 20 480. 
      
      Parameter 5 of the rxTrafficDescParm is always unused. 
      
      If the rxTrafficDescType is sameAsTx, the values in this attribute 
      are taken from the txTrafficDescParm."
::= { atmIfVptVpd 298 }

atmIfVptVpdRxTdpEntry OBJECT-TYPE
   SYNTAX     AtmIfVptVpdRxTdpEntry
   ACCESS     not-accessible
   STATUS     obsolete
   DESCRIPTION
     "An entry in the atmIfVptVpdRxTdpTable."
   INDEX {
      atmIfIndex,
      atmIfVptIndex,
      atmIfVptVpdIndex,
      atmIfVptVpdRxTdpIndex }
::= { atmIfVptVpdRxTdpTable 1 }

AtmIfVptVpdRxTdpEntry ::= SEQUENCE {
   atmIfVptVpdRxTdpIndex
      Integer32,
   atmIfVptVpdRxTdpValue
      Unsigned32 }

atmIfVptVpdRxTdpIndex OBJECT-TYPE
   SYNTAX     Integer32 (1..5)
   ACCESS     not-accessible
   STATUS     obsolete
   DESCRIPTION
     "This variable represents the atmIfVptVpdRxTdpTable
      specific index for the atmIfVptVpdRxTdpTable."
::= { atmIfVptVpdRxTdpEntry 1 }

atmIfVptVpdRxTdpValue OBJECT-TYPE
   SYNTAX     Unsigned32 (0..2147483647)
   ACCESS     read-write
   STATUS     obsolete
   DESCRIPTION
     "This variable represents an individual value for the
      atmIfVptVpdRxTdpTable."
::= { atmIfVptVpdRxTdpEntry 2 }

atmIfVptVpdFqpTable OBJECT-TYPE
   SYNTAX     SEQUENCE OF AtmIfVptVpdFqpEntry
   ACCESS     not-accessible
   STATUS     obsolete
   DESCRIPTION
     "This attribute is migrated to the AtmTmProv group.
      
      This attribute is a vector of three elements that specify the quality of 
      service parameters for the forward direction for this connection. 
      This attribute is used for SPVC connections.
      
      The cdv element specifies the acceptable peak-to-peak Cell Delay 
      Variation (CDV) of real-time connections (CBR, and rt-VBR). It is 
      signalled through the extended QoS information element.
      
      The ctd specifies the acceptable maximum Cell Transfer Delay 
      (maxCtd) of real-time connections (CBR, and rt-VBR). 
      It is signalled through the end to end transit delay information 
      element.
      
      The clr specifies the acceptable Cell Loss Ratio (CLR) of CBR, rt-
      VBR, and nrt-VBR connections. It is signalled through the extended 
      QoS information element."
::= { atmIfVptVpd 359 }

atmIfVptVpdFqpEntry OBJECT-TYPE
   SYNTAX     AtmIfVptVpdFqpEntry
   ACCESS     not-accessible
   STATUS     obsolete
   DESCRIPTION
     "An entry in the atmIfVptVpdFqpTable."
   INDEX {
      atmIfIndex,
      atmIfVptIndex,
      atmIfVptVpdIndex,
      atmIfVptVpdFqpIndex }
::= { atmIfVptVpdFqpTable 1 }

AtmIfVptVpdFqpEntry ::= SEQUENCE {
   atmIfVptVpdFqpIndex
      INTEGER,
   atmIfVptVpdFqpValue
      Unsigned32 }

atmIfVptVpdFqpIndex OBJECT-TYPE
   SYNTAX     INTEGER  {
                 cdv(0),
                 ctd(1),
                 clr(2) }
   ACCESS     not-accessible
   STATUS     obsolete
   DESCRIPTION
     "This variable represents the atmIfVptVpdFqpTable
      specific index for the atmIfVptVpdFqpTable."
::= { atmIfVptVpdFqpEntry 1 }

atmIfVptVpdFqpValue OBJECT-TYPE
   SYNTAX     Unsigned32 (0..2147483647)
   ACCESS     read-write
   STATUS     obsolete
   DESCRIPTION
     "This variable represents an individual value for the
      atmIfVptVpdFqpTable."
::= { atmIfVptVpdFqpEntry 2 }

atmIfVptVpdBqpTable OBJECT-TYPE
   SYNTAX     SEQUENCE OF AtmIfVptVpdBqpEntry
   ACCESS     not-accessible
   STATUS     obsolete
   DESCRIPTION
     "This attribute is migrated to the AtmTmProv group.
      
      This attribute is a vector of three elements that specify the quality of 
      service parameters for the backward direction for this connection. 
      This attribute is used for SPVC connections.
      
      The cdv element specifies the acceptable peak-to-peak Cell Delay 
      Variation (CDV) of real-time connections (CBR, and rt-VBR). 
      
      It is signalled through the extended QoS information element.
      
      The ctd specifies the acceptable maximum Cell Transfer Delay 
      (maxCtd) of real-time connections (CBR, and rt-VBR). It is 
      signalled through the end to end transit delay information element.
      
      The clr specifies the acceptable Cell Loss Ratio (CLR) of CBR, rt-
      VBR, and nrt-VBR connections. It is signalled through the extended 
      QoS information element."
::= { atmIfVptVpd 360 }

atmIfVptVpdBqpEntry OBJECT-TYPE
   SYNTAX     AtmIfVptVpdBqpEntry
   ACCESS     not-accessible
   STATUS     obsolete
   DESCRIPTION
     "An entry in the atmIfVptVpdBqpTable."
   INDEX {
      atmIfIndex,
      atmIfVptIndex,
      atmIfVptVpdIndex,
      atmIfVptVpdBqpIndex }
::= { atmIfVptVpdBqpTable 1 }

AtmIfVptVpdBqpEntry ::= SEQUENCE {
   atmIfVptVpdBqpIndex
      INTEGER,
   atmIfVptVpdBqpValue
      Unsigned32 }

atmIfVptVpdBqpIndex OBJECT-TYPE
   SYNTAX     INTEGER  {
                 cdv(0),
                 ctd(1),
                 clr(2) }
   ACCESS     not-accessible
   STATUS     obsolete
   DESCRIPTION
     "This variable represents the atmIfVptVpdBqpTable
      specific index for the atmIfVptVpdBqpTable."
::= { atmIfVptVpdBqpEntry 1 }

atmIfVptVpdBqpValue OBJECT-TYPE
   SYNTAX     Unsigned32 (0..2147483647)
   ACCESS     read-write
   STATUS     obsolete
   DESCRIPTION
     "This variable represents an individual value for the
      atmIfVptVpdBqpTable."
::= { atmIfVptVpdBqpEntry 2 }


-- AtmIf/n Vcc/vpi.vci Vcd TrafficManagement, 
-- AtmIf/n Vpc/vci Vpd TrafficManagement,
-- AtmIf/n Vpt/vpi Vpd TrafficManagement,
-- AtmIf/n Vpt/vpi Vcc/vci Vcd TrafficManagement
-- This component contains provisioned traffic management attributes 
-- of a connection. It is added automatically when a Vcc, Vpc, or Vpt is 
-- added in provisioning mode. It is a mandatory subcomponent of the 
-- Vcd or Vpd component.

atmIfVptVpdTm OBJECT IDENTIFIER ::= { atmIfVptVpd 2 }



atmIfVptVpdTmRowStatusTable OBJECT-TYPE
   SYNTAX     SEQUENCE OF AtmIfVptVpdTmRowStatusEntry
   ACCESS     not-accessible
   STATUS     mandatory
   DESCRIPTION
     "This entry controls the addition and deletion of 
      atmIfVptVpdTm components."
::= { atmIfVptVpdTm 1 }

atmIfVptVpdTmRowStatusEntry OBJECT-TYPE
   SYNTAX     AtmIfVptVpdTmRowStatusEntry
   ACCESS     not-accessible
   STATUS     mandatory
   DESCRIPTION
     "A single entry in the table represents a single 
      atmIfVptVpdTm component."
   INDEX {
      atmIfIndex,
      atmIfVptIndex,
      atmIfVptVpdIndex,
      atmIfVptVpdTmIndex }
::= { atmIfVptVpdTmRowStatusTable 1 }

AtmIfVptVpdTmRowStatusEntry ::= SEQUENCE {
   atmIfVptVpdTmRowStatus
      RowStatus,
   atmIfVptVpdTmComponentName
      DisplayString,
   atmIfVptVpdTmStorageType
      StorageType,
   atmIfVptVpdTmIndex
      NonReplicated }

atmIfVptVpdTmRowStatus OBJECT-TYPE
   SYNTAX     RowStatus 
   ACCESS     read-only
   STATUS     mandatory
   DESCRIPTION
     "This variable is used as the basis for SNMP naming of
      atmIfVptVpdTm components.
      These components cannot be added nor deleted."
::= { atmIfVptVpdTmRowStatusEntry 1 }

atmIfVptVpdTmComponentName OBJECT-TYPE
   SYNTAX     DisplayString 
   ACCESS     read-only
   STATUS     mandatory
   DESCRIPTION
     "This variable provides the component's string name for
      use with the ASCII Console Interface"
::= { atmIfVptVpdTmRowStatusEntry 2 }

atmIfVptVpdTmStorageType OBJECT-TYPE
   SYNTAX     StorageType 
   ACCESS     read-only
   STATUS     mandatory
   DESCRIPTION
     "This variable represents the storage type value for the
      atmIfVptVpdTm tables."
::= { atmIfVptVpdTmRowStatusEntry 4 }

atmIfVptVpdTmIndex OBJECT-TYPE
   SYNTAX     NonReplicated 
   ACCESS     not-accessible
   STATUS     mandatory
   DESCRIPTION
     "This variable represents the index for the atmIfVptVpdTm tables."
::= { atmIfVptVpdTmRowStatusEntry 10 }

atmIfVptVpdTmProvTable OBJECT-TYPE
   SYNTAX     SEQUENCE OF AtmIfVptVpdTmProvEntry
   ACCESS     not-accessible
   STATUS     mandatory
   DESCRIPTION
     "This group contains traffic related provisionable attributes for the 
      Vcc, Vpc, and Vpt components. Changing any of the attributes in 
      this group causes a service interruption on the Vcc, Vpc, or Vpt 
      component."
::= { atmIfVptVpdTm 100 }

atmIfVptVpdTmProvEntry OBJECT-TYPE
   SYNTAX     AtmIfVptVpdTmProvEntry
   ACCESS     not-accessible
   STATUS     mandatory
   DESCRIPTION
     "An entry in the atmIfVptVpdTmProvTable."
   INDEX {
      atmIfIndex,
      atmIfVptIndex,
      atmIfVptVpdIndex,
      atmIfVptVpdTmIndex }
::= { atmIfVptVpdTmProvTable 1 }

AtmIfVptVpdTmProvEntry ::= SEQUENCE {
   atmIfVptVpdTmTxTrafficDescType
      INTEGER,
   atmIfVptVpdTmFwdQosClass
      INTEGER,
   atmIfVptVpdTmTxQueueLimit
      Unsigned32,
   atmIfVptVpdTmHoldingPriority
      INTEGER,
   atmIfVptVpdTmRxTrafficDescType
      INTEGER,
   atmIfVptVpdTmBwdQosClass
      INTEGER,
   atmIfVptVpdTmAtmServiceCategory
      INTEGER,
   atmIfVptVpdTmTrafficShaping
      INTEGER,
   atmIfVptVpdTmUnshapedTransmitQueueing
      INTEGER,
   atmIfVptVpdTmWeight
      Unsigned32,
   atmIfVptVpdTmForceTagging
      INTEGER,
   atmIfVptVpdTmUsageParameterControl
      INTEGER,
   atmIfVptVpdTmBearerClassBbc
      INTEGER,
   atmIfVptVpdTmTransferCapabilityBbc
      INTEGER,
   atmIfVptVpdTmTxWredThreshold
      Unsigned32,
   atmIfVptVpdTmClippingBbc
      INTEGER,
   atmIfVptVpdTmBestEffort
      INTEGER,
   atmIfVptVpdTmTxPacketWiseDiscard
      INTEGER,
   atmIfVptVpdTmTxWredMode
      INTEGER,
   atmIfVptVpdTmRxPacketWiseDiscard
      INTEGER,
   atmIfVptVpdTmAbrConnectionType
      INTEGER }

atmIfVptVpdTmTxTrafficDescType OBJECT-TYPE
   SYNTAX     INTEGER  {
                 n1(1),
                 n2(2),
                 n3(3),
                 n4(4),
                 n5(5),
                 n6(6),
                 n7(7),
                 n8(8),
                 n9(9) }
   ACCESS     read-write
   STATUS     mandatory
   DESCRIPTION
     "This attribute specifies the type of traffic management which is 
      applied to the transmit direction of this connection as defined in the 
      ATM Forum. The txTrafficDescType determines the number and 
      meaning of the parameters in the txTrafficDescParm attribute.
      
      This attribute can have a value of 9 if and only if the 
      atmServiceCategory is availableBitRate."
   DEFVAL     { n1 }
::= { atmIfVptVpdTmProvEntry 10 }

atmIfVptVpdTmFwdQosClass OBJECT-TYPE
   SYNTAX     INTEGER  {
                 n0(0),
                 n1(1),
                 n2(2),
                 n3(3),
                 n4(4) }
   ACCESS     read-write
   STATUS     mandatory
   DESCRIPTION
     "This attribute specifies the quality of service for the forward 
      direction for this connection. This attribute is only used for SPVC 
      connections.
      
      Class 1 supports a QOS that meets Service Class A performance 
      requirements (circuit emulation, constant bit rate video).
      
      Class 2 supports a QOS that meets Service Class B performance 
      requirements (variable bit rate audio and video).
      
      Class 3 supports a QOS that meets Service Class C performance 
      requirements (Connection-Oriented Data Transfer).
      
      Class 4 supports a QOS that meets Service Class D performance 
      requirements (Connectionless Data Transfer).
      
      Class 0 is the unspecified bit rate QOS class; no objective is 
      specified for the performance parameters."
   DEFVAL     { n0 }
::= { atmIfVptVpdTmProvEntry 21 }

atmIfVptVpdTmTxQueueLimit OBJECT-TYPE
   SYNTAX     Unsigned32 (0 | 5..63488)
   ACCESS     read-write
   STATUS     mandatory
   DESCRIPTION
     "This attribute specifies an override to the default transmit queue 
      limit for this connection. A value other than sameAsCa may be 
      specified only for ATM IP cards. This attribute is not applicable for 
      basic Vpts.
      
      A value of sameAsCa means to use the default common or per-VC 
      transmit queue limit as defined by the CA service category for this 
      connection. 
      
      A value from 5 to 63,488 indicates that a specific transmit queue 
      limit is requested which differs from the default which is defined 
      under the CA component for this service category. A specific value 
      is ignored for connections where common queuing is specified for 
      the service category.
      
      The actual transmit queue limit for a connection is visible in the Vcc 
      Tm, Vpc Tm, or Vpt Tm txQueueThresholds attribute.

      VALUES (

      0 = sameAsCa

      )"
   DEFVAL     { 0 }
::= { atmIfVptVpdTmProvEntry 22 }

atmIfVptVpdTmHoldingPriority OBJECT-TYPE
   SYNTAX     INTEGER  {
                 n0(0),
                 n1(1),
                 n2(2),
                 n3(3),
                 n4(4) }
   ACCESS     read-write
   STATUS     mandatory
   DESCRIPTION
     "This attribute specifies the holding priority of this connection. In a 
      situation where the link bandwidth fluctuates, such as over an IMA 
      link, holding priority is used to determine which connections are 
      held and which are released. Holding priority 4 connections are the 
      first to be released. Holding priority 0 connections are the last to be 
      released. This value provisioned in the Vcd or Vpd may be 
      overridden by certain applications, for example Vcc Test, which run 
      over this connection. The default holding priority for a provisioned 
      connection is higher then default holding priorities for dynamic 
      (SVC) connections. 
      
      This attribute is not applicable for Vpt Vccs."
   DEFVAL     { n2 }
::= { atmIfVptVpdTmProvEntry 25 }

atmIfVptVpdTmRxTrafficDescType OBJECT-TYPE
   SYNTAX     INTEGER  {
                 n1(1),
                 n2(2),
                 n3(3),
                 n4(4),
                 n5(5),
                 n6(6),
                 n7(7),
                 n8(8),
                 n9(9),
                 sameAsTx(15) }
   ACCESS     read-write
   STATUS     mandatory
   DESCRIPTION
     "This attribute specifies the type of traffic management which is 
      applied to the receive direction of this connection as defined in the 
      ATM Forum. The rxTrafficDescType determines the number and 
      meaning of the parameters in the rxTrafficDescParm attribute.
      
      When this attribute is set to sameAsTx, the rxTrafficDescType as 
      well as the rxTrafficDescParm are taken from the 
      txTrafficDescType and txTrafficDescParm values."
   DEFVAL     { sameAsTx }
::= { atmIfVptVpdTmProvEntry 30 }

atmIfVptVpdTmBwdQosClass OBJECT-TYPE
   SYNTAX     INTEGER  {
                 n0(0),
                 n1(1),
                 n2(2),
                 n3(3),
                 n4(4),
                 sameAsFwd(15) }
   ACCESS     read-write
   STATUS     mandatory
   DESCRIPTION
     "This attribute specifies the quality of service for the backward 
      direction for this connection. This attribute is only used for SPVC 
      connections.
      
      Class 1 supports a QOS that meets Service Class A performance 
      requirements (Circuit emulation, constant bit rate video).
      
      Class 2 supports a QOS that meets Service Class B performance 
      requirements (Variable bit rate audio and video).
      
      Class 3 supports a QOS that meets Service Class C performance 
      requirements (Connection-Oriented Data Transfer).
      
      Class 4 supports a QOS that meets Service Class D performance 
      requirements (Connectionless Data Transfer).
      
      Class 0 is the unspecified bit rate QOS class; no objective is 
      specified for the performance parameters.
      
      The sameAsFwd selection sets the backward quality of service to 
      be the same as the forward quality of service."
   DEFVAL     { sameAsFwd }
::= { atmIfVptVpdTmProvEntry 41 }

atmIfVptVpdTmAtmServiceCategory OBJECT-TYPE
   SYNTAX     INTEGER  {
                 unspecifiedBitRate(0),
                 constantBitRate(1),
                 rtVariableBitRate(2),
                 nrtVariableBitRate(3),
                 availableBitRate(4),
                 derivedFromBBC(15) }
   ACCESS     read-write
   STATUS     mandatory
   DESCRIPTION
     "This attribute specifies the ATM service category for both directions 
      of the connection. 
      
      The value derivedFromBBC may only be used if the SrcPvc 
      component is provisioned under this Vcc. Otherwise a specific 
      ATM service category must be specified. 
      
      If this attribute is set to derivedFromBBC, the Broadband Bearer 
      Capability (BBC) and bestEffort attributes are used to determine the 
      atmServiceCategory of this connection. 
      
      If this attribute is set to other than derivedFromBBC, the value of 
      this attribute is used to override the provisioned BBC Information 
      Element parameters. In those cases, the BBC attributes are not used. 
      
      The constantBitRate service category is intended for real time 
      applications, that is those requiring tightly constrained delay and 
      delay variation, as would be appropriate for voice and video 
      applications. The consistent availability of a fixed quantity of 
      bandwidth is considered appropriate for CBR service. Cells which 
      are delayed beyond the value specified by Cell Transfer Delay are 
      assumed to be of significantly reduced value to the application.
      
      The rtVariableBitRate service category is intended for real time 
      applications, that is those requiring tightly constrained delay and 
      delay variation, as would be appropriate for voice and video 
      applications. Sources are expected to transmit at a rate which varies 
      with time. Equivalently, the source can be described as 'bursty'. 
      Cells which are delayed beyond the value specified by CTD are 
      assumed to be of significantly reduced value to the application. Real 
      time VBR service may support statistical multiplexing of real time 
      sources.
      
      The nrtVariableBitRate service category is intended for non-real 
      time applications which have bursty traffic characteristics and which 
      can be characterized in terms of a PCR, SCR, and MBS. For those 
      cells which are transferred within the traffic contract, the application 
      expects a low cell loss ratio. For all connections, it expects a bound 
      on the mean cell transfer delay. Non-real time VBR service may 
      support statistical multiplexing of connections. 
      
      The availableBitRate service is an ATM layer service category for 
      which the limiting ATM layer transfer characteristics provided by 
      the network may change subsequent to connection establishment. 
      ABR service has a flow control mechanism which supports several 
      types of feedback to control the source rate in response to changing 
      ATM layer transfer characteristics. ABR service is not intended to 
      support real-time applications. 
      
      The unspecifiedBitRate service is intended for non-real time 
      applications; that is, those not requiring tightly constrained delay 
      and delay variation. UBR sources are expected to be bursty. UBR 
      service supports a high degree of statistical multiplexing among 
      sources. UBR service does not specify traffic related service 
      guarantees. No numerical commitments are made with respect to 
      the cell loss ratio experienced by a UBR connection, or as to the 
      cell transfer delay experienced by cells on the connection."
   DEFVAL     { unspecifiedBitRate }
::= { atmIfVptVpdTmProvEntry 42 }

atmIfVptVpdTmTrafficShaping OBJECT-TYPE
   SYNTAX     INTEGER  {
                 disabled(1),
                 sameAsCa(2) }
   ACCESS     read-write
   STATUS     mandatory
   DESCRIPTION
     "This attribute specifies whether this connection uses traffic shaping 
      when transmitting traffic to the ATM interface.
      
      This attribute is ignored if the atmServiceCategory is 
      availableBitRate.
      
      When sameAsCa is selected, traffic shaping for the connection is 
      based on the trafficShaping attribute of the connection's service 
      category component under the CA. If the service category has 
      trafficShaping set to enabled or inverseUpc, then traffic shaping is 
      enabled for the connection. Note that enabling traffic shaping may 
      have no effect under certain cases. These cases are listed in the 
      description of the trafficShaping operational attribute, which is 
      under the Vcc Tm, Vpc Tm, or Vpt Tm components.
      
      When disabled is selected, traffic shaping for this connection is 
      disabled regardless of the provisioning of the connection's service 
      category component."
   DEFVAL     { sameAsCa }
::= { atmIfVptVpdTmProvEntry 50 }

atmIfVptVpdTmUnshapedTransmitQueueing OBJECT-TYPE
   SYNTAX     INTEGER  {
                 common(1),
                 sameAsCa(3) }
   ACCESS     read-write
   STATUS     mandatory
   DESCRIPTION
     "This attribute only applies when this connection is unshaped. This 
      attribute specifies the transmit queueing method for this connection 
      if it is unshaped. The two possible methods are per-VC queuing and 
      common queuing. 
      
      On ATM IP FPs, this attribute must be set to sameAsCa. 
      
      This attribute is ignored in the following situations:
      - if the connection has trafficShaping enabled or inverseUpc, or 
      - if the atmServiceCategory is availableBitRate, or
      - if the atmServiceCategory is constantBitRate and this is a CQC-
      based ATM FP.
      - for basic Vpts and standard Vpt Vccs
      
      When this attribute is set to sameAsCa, the transmit queueing 
      method for the connection is based on the 
      unshapedTransmitQueueing attribute of the connection's service 
      category component under the CA. 
      
      When this attribute is set to common, transmit traffic on this 
      unshaped connection is destined for the common queue."
   DEFVAL     { sameAsCa }
::= { atmIfVptVpdTmProvEntry 60 }

atmIfVptVpdTmWeight OBJECT-TYPE
   SYNTAX     Unsigned32 (0 | 1..4095 | 65535)
   ACCESS     read-write
   STATUS     mandatory
   DESCRIPTION
     "This attribute specifies an override for the weight of this unshaped 
      connection. This attribute is ignored for shaped connections, for 
      ABR connections, for connections on a CQC-based ATM FP, and 
      basic Vpts. 
      
      When the value is set to sameAsCa, the weight is determined by the 
      fairnessWeight attribute under the CA service category component 
      for all but standard Vpt Vccs. For standard Vpt Vccs, the weight is 
      determined by the Vcc's service category, when the value is set to 
      sameAsCa.
      
      When this attribute is set to a value from 1 to 4095, that value is 
      used for the fairness weight of this connection relative to other 
      connections. For all but standard Vpt Vccs, fairness weight 
      determines the proportion of transmit cell opportunities which are 
      allocated to this connection, compared to other connections in the 
      same service category. For standard Vpt Vccs, fairness weight 
      determines the proportion of transmit cell opportunities which are 
      allocated to this connection, compared to other connections 
      associated with the Vpt.
      
      When the value is set to upToQueueLimit, the fairness weight is 
      limited only by the txQueueLimit.

      VALUES (

      0 = upToQueueLimit

      65535 = sameAsCa

      )"
   DEFVAL     { 65535 }
::= { atmIfVptVpdTmProvEntry 61 }

atmIfVptVpdTmForceTagging OBJECT-TYPE
   SYNTAX     INTEGER  {
                 enabled(0),
                 disabled(1),
                 sameAsCa(2) }
   ACCESS     read-write
   STATUS     mandatory
   DESCRIPTION
     "This attribute specifies whether force tagging is enforced for this 
      connection for cells in the transmit direction. 
      
      On CQC-based ATM cards, and for Vpts, this attribute is not 
      applicable and is ignored. 
      
      When the value is set to sameAsCa, the force tagging functionality 
      is determined by the forceTagging attribute under the CA service 
      category component. 
      
      When the value is set to enabled, force tagging is enabled for cells 
      in the transmit direction on this connection. When this option is 
      selected, the CLP bit is set to 1 for all cells in the transmit direction. 
      Cells which are tagged are counted in the txCellClp attribute. 
      
      When the value is set to disabled, force tagging is disabled for cells 
      in the transmit direction on this connection. When this option is 
      selected, the CLP bit is unchanged for cells in the transmit 
      direction."
   DEFVAL     { sameAsCa }
::= { atmIfVptVpdTmProvEntry 62 }

atmIfVptVpdTmUsageParameterControl OBJECT-TYPE
   SYNTAX     INTEGER  {
                 enforced(0),
                 disabled(1),
                 sameAsCa(2),
                 monitored(4) }
   ACCESS     read-write
   STATUS     mandatory
   DESCRIPTION
     "This attribute specifies whether this connection enforces usage 
      parameter control when receiving traffic from the ATM interface.
      
      When sameAsCa is selected, UPC for the connection is based on 
      the usageParameterControl attribute of the service category 
      component under the AtmIf CA. If the service category has UPC 
      enforced or monitored, then UPC is set to that value for the 
      connection. 
      
      When disabled is selected, UPC for this connection is disabled 
      regardless of the provisioning of the service category. 
      
      When enforced is selected, UPC for this connection is enforced 
      regardless of the provisioning of the service category. 
      
      ATM IP cards provide the ability to monitor UPC violations without 
      tagging or discarding. When monitored is selected, UPC is actively 
      checking conformance for the connection and counting the 
      violations, but is not discarding or tagging cells which do not 
      conform to the connection traffic contract. 
      
      If this is a connection of serviceCategory abr on an ATM IP card, 
      and the abrConnectionType is sourceDest, virtualSourceDest or 
      explicitRate, selecting enforced enables dynamic generic cell rate 
      algorithm (DGCRA) to discard violating cells. Selecting monitored 
      enables DGCRA to count violating cells. 
      
      Note that setting UPC to enforced or monitored may have no effect 
      under certain cases. These cases are listed in the description of the 
      usageParameterControl operational attribute, which is under the 
      Vcc, Vpc, and Vpt components."
   DEFVAL     { sameAsCa }
::= { atmIfVptVpdTmProvEntry 70 }

atmIfVptVpdTmBearerClassBbc OBJECT-TYPE
   SYNTAX     INTEGER  {
                 a(1),
                 c(3),
                 x(16),
                 vp(24),
                 derivedFromServiceCategory(31) }
   ACCESS     read-write
   STATUS     mandatory
   DESCRIPTION
     "This attribute specifies the bearer capability. This attribute is only 
      used for SPVC and SPVP connections. It is one of the Broadband 
      Bearer Capability (BBC) attributes. The purpose of the BBC 
      information element is to indicate a requested broadband 
      connection-oriented bearer service to be provided by the network.
      
      The value derivedFromServiceCategory specifies that the actual 
      value which is used for this connection is derived from the value of 
      the atmServiceCategory. Either, this attribute must be set to 
      derivedFromServiceCategory, or the atmServiceCategory attribute 
      must be set to derivedFromBBC, but not both.
      
      Class a service is a connection-oriented, constant bit rate ATM 
      transport service. Class a service has end to end timing 
      requirements and may require stringent cell loss, cell delay and cell 
      delay variation performance.When a is set, the user is requesting 
      more than an ATM only service. The network may look at the AAL 
      to provide interworking based upon its contents. 
      
      Class c service is a connection-oriented, variable bit rate ATM 
      transport service. Class c service has no end-to-end timing 
      requirements. When c is set, the user is requesting more than an 
      ATM only service. The network interworking function may look at 
      the AAL and provide service based on it.
      
      Class x service is a connection-oriented ATM transport service 
      where the AAL, trafficType (vbr or cbr) and timing requirements 
      are user defined (that is, transparent to the network).When x is set 
      the user is requesting an ATM only service from the network. In this 
      case, the network shall not process any higher layer protocol.
      
      Class vp service is used to specify a transparent VP service. When 
      the value of this attribute is vp, the user is requesting an ATM only 
      service from the network. In this case, the network shall not process 
      any higher layer protocol. This service differs from class x service 
      in that with the class vp service both the VCI field (except or VCI 
      values 0, 3, 4, and 6 through 15) and Payload Type field are 
      transported transparently by the network. This attribute value is 
      only applicable to SPVP connections."
   DEFVAL     { derivedFromServiceCategory }
::= { atmIfVptVpdTmProvEntry 71 }

atmIfVptVpdTmTransferCapabilityBbc OBJECT-TYPE
   SYNTAX     INTEGER  {
                 n0(0),
                 n1(1),
                 n2(2),
                 n5(5),
                 n8(8),
                 n9(9),
                 n10(10),
                 notApplicable(30),
                 derivedFromServiceCategory(31) }
   ACCESS     read-write
   STATUS     mandatory
   DESCRIPTION
     "This attribute specifies the transfer capability for this connection. 
      Uni 3.0/3.1 traffic type and end-to-end timing parameters are 
      mapped into this parameter as follows:
      <transferCapability: TrafficType, Timing>
      0: NoIndication, NoIndication
      1: NoIndication, yes
      2: NoIndication, no
      5: CBR, yes
      8: VBR, NoIndication
      9: VBR, yes
      10: VBR, no
      
      notApplicable specifies that the user does not want to specify the 
      transfer capability.
      
      The CBR traffic type refers to traffic offered on services such as a 
      constant bit rate video service or a circuit emulation.
      The VBR traffic type refers to traffic offered on services such as 
      packetized audio and video, or data.
      
      The value no indication for traffic type is used if the user has not set 
      the traffic type; similarly for end-to-end timing.
      
      The value yes for end-to-end timing indicates that end-to-end 
      timing is required.
      
      The value no for end-to-end timing indicates that end-to-end timing 
      is not required.
      
      The value derivedFromServiceCategory specifies that the actual 
      value which is used for this connection is derived from the value of 
      the atmServiceCategory. Either, this attribute must be set to 
      derivedFromServiceCategory, or the atmServiceCategory attribute 
      must be set to derivedFromBBC, but not both."
   DEFVAL     { derivedFromServiceCategory }
::= { atmIfVptVpdTmProvEntry 72 }

atmIfVptVpdTmTxWredThreshold OBJECT-TYPE
   SYNTAX     Unsigned32 (25 | 50 | 75)
   ACCESS     read-write
   STATUS     mandatory
   DESCRIPTION
     "This attribute determines at what percentage of the queue being at 
      the EPD threshold, WRED starts. When the value is set to 25%, 
      WRED starts as soon as the queue is 25% of the way to the EPD 
      threshold. When the value is set to 50%, WRED starts later, after 
      the queue is 50% of the way to the EPD threshold. When the value 
      is set to 75%, WRED starts only when the queue is 75% of the way 
      to the EPD threshold. The EPD threshold is 85% of the transmit 
      queue length.
      
      This attribue is ignored if txWredMode or txPacketWiseDiscard is 
      disabled. It is always ignored on CQC-based ATM FP."
   DEFVAL     { 25 }
::= { atmIfVptVpdTmProvEntry 73 }

atmIfVptVpdTmClippingBbc OBJECT-TYPE
   SYNTAX     INTEGER  {
                 no(0),
                 yes(1) }
   ACCESS     read-write
   STATUS     mandatory
   DESCRIPTION
     "This attribute specifies the value for the clipping susceptibility 
      parameter in the BBC Information Element. This attribute is only 
      used for SPVC connections. It is one of the Broadband Bearer 
      Capability attributes.
      
      Clipping is an impairment in which the first fraction of a second of 
      information to be transferred is lost. It occurs after a call is 
      answered and before an associated connection is switched through."
   DEFVAL     { no }
::= { atmIfVptVpdTmProvEntry 74 }

atmIfVptVpdTmBestEffort OBJECT-TYPE
   SYNTAX     INTEGER  {
                 indicated(0),
                 notIndicated(1),
                 derivedFromServiceCategory(15) }
   ACCESS     read-write
   STATUS     mandatory
   DESCRIPTION
     "This attribute specifies the value of the best effort parameter in the 
      ATM Traffic Descriptor Information Element. This attribute is only 
      used for Soft PVC connections. It is one of the Broadband Bearer 
      Capability attributes.
      
      The value indicated implies that the quality of service for this 
      connection is not guaranteed.
      
      The value notIndicated implies that the quality of service for this 
      connection is guaranteed.
      
      The value derivedFromServiceCategory specifies that the actual 
      value which is used for this connection is derived from the value of 
      the atmServiceCategory. Either, this attribute must be set to 
      derivedFromServiceCategory, or the atmServiceCategory attribute 
      must be set to derivedFromBBC, but not both."
   DEFVAL     { derivedFromServiceCategory }
::= { atmIfVptVpdTmProvEntry 75 }

atmIfVptVpdTmTxPacketWiseDiscard OBJECT-TYPE
   SYNTAX     INTEGER  {
                 disabled(0),
                 enabled(1) }
   ACCESS     read-write
   STATUS     mandatory
   DESCRIPTION
     "This attribute specifies whether packet-wise discard functions are to 
      be enabled or disabled in the transmit data direction for this 
      connection. Packet-wise discard functions should only be requested 
      if this connection is transferring AAL5 frame traffic. This attribute 
      is not applicable for Vpts.
      
      Packet-wise functions increase the 'goodput' of the link. The 
      transmit packet-wise functions are Early Packet Discard (EPD) and 
      Partial Packet Discard (PPD). 
      
      EPD allows the connection to discard an entire frame once the 
      transmit queue has reached the EPD threshold. EPD increases the 
      'goodput' of a link, since discarding an entire frame means that 
      some queue capacity is guarded for some other frame which is 
      already partially transmitted. All cells of the frame are discarded 
      from the Beginning of Message (BOM) cell up to and including the 
      End of Message (EOM) cell. 
      
      PPD allows the connection to discard the remainder of a cell-
      forwarded AAL5 frame if one cell of this frame has been discarded. 
      All cells are discarded up to but not including the EOM cell. The 
      PPD function increases the 'goodput' of the link, since cells which 
      are only going to be discarded at the AAL5 reassembly point are 
      not transmitted.
      
      On CQC-based ATM cards, the packet-wise discard functions are 
      PPD and EPD. PPD is available at VCC cell-transfer points. PPD is 
      not applicable at frame-cell conversion points, and is not applicable 
      for Vpcs. PPD is configured by this attribute. Packet-wise discard 
      should only be enabled for connections carrying AAL5 
      segmentation traffic. Setting the value to enabled for any other 
      traffic type may result in all traffic being discarded. On CQC-based 
      ATM FPs, EPD is automatically enabled at frame-to-cell conversion 
      points, independent of the setting of this attribute. 
      
      On ATM IP cards, packet-wise discard functions include EPD and 
      PPD. PPD and EPD apply to individual VCCs and VCCs within 
      VPCs at all connection points, including tandem VPC connections. 
      Both PPD and EPD are controlled by this attribute. This attribute 
      may safely be set to enabled for any connection (Vcc or Vpc) on 
      ATM IP FPs since they have the ability to automatically detect 
      AAL5-segmented traffic on a connection, and only enable packet-
      wise discards if AAL5-segmented traffic is detected.
      
      When this attribute is set to enabled, packet-wise discard functions 
      are applied to transmit traffic at this connection point. When this 
      attribute is set to disabled, packet-wise discard functions are not 
      applied to transmit traffic at this connection point.
      
      At a SPVC origin on a PNNI interface, a value of enabled specifies 
      that frame discard is requested in the backward direction. When this 
      attribute is set to disabled, backward frame discard is not requested 
      in the SPVC call setup. 
      
      The transmit packet-wise discard functions that are active are 
      visible in the Vcc/Vpc Tm txPacketWiseDiscard operational 
      attribute."
   DEFVAL     { disabled }
::= { atmIfVptVpdTmProvEntry 76 }

atmIfVptVpdTmTxWredMode OBJECT-TYPE
   SYNTAX     INTEGER  {
                 disabled(0),
                 enabled(1),
                 perFlow(2) }
   ACCESS     read-write
   STATUS     mandatory
   DESCRIPTION
     "This attribute specifies the activation of weighted random early 
      detection (WRED) functionality. WRED is only available on ATM 
      IP FPs. On CQC-based ATM FPs, this attribute is ignored. If 
      txPacketWiseDiscard is set to disabled this attribute is ignored. This 
      attribute is not applicable for Vpts or Vpt Vccs.
      
      WRED is applied in the transmit direction for this connection. 
      WRED function should be enabled only for connections which are 
      transferring TCP/IP traffic. WRED acts to prevent synchronization 
      of multiple TCP/IP sources by randomly discarding a small 
      percentage of frames when transmit queue congestion reaches the 
      designated level. W-RED may also be used to differentiate service 
      on VCC's by preferentially discarding one VCC before another. 
      Discards start at 0% of cells, when the queue is part-way to the 
      Early Packet Discard (EPD) threshold, and rise to 100% of cells 
      discarded at the EPD threshold. WRED discards all the cells in a 
      frame. 
      
      If this attribute is set to enabled, WRED is enabled for all 
      applications linked to the given Vcc. If it is set to perFlow, each 
      TCP application has individual control over whether to enable or 
      disable WRED
      
      If txPacketWiseDiscard is set to disabled, or if this attribute is set to 
      disabled, WRED functionality is disabled. 
      
      If WRED is active, it is visible in the Vcc/Vpc Tm 
      txPacketWiseDiscard operational attribute."
   DEFVAL     { disabled }
::= { atmIfVptVpdTmProvEntry 77 }

atmIfVptVpdTmRxPacketWiseDiscard OBJECT-TYPE
   SYNTAX     INTEGER  {
                 disabled(0),
                 enabled(1) }
   ACCESS     read-write
   STATUS     mandatory
   DESCRIPTION
     "This attribute specifies whether packet-wise discard functions are to 
      be enabled or disabled in the receive data direction for this 
      connection. Packet-wise discard functions should only be requested 
      if this connection is transferring AAL5 frame traffic. This attribute 
      is not applicable for Vpts.
      
      Packet-wise functions increase the 'goodput' of the link. The 
      receive packet-wise function is Partial Packet Discard (PPD). 
      
      PPD allows the connection to discard the remainder of a cell-
      forwarded AAL5 frame if one cell of this frame has been discarded, 
      for example due to UPC. All cells are discarded up to but not 
      including the EOM cell. The PPD function increases the 'goodput' 
      of the link, since cells which are only going to be discarded at the 
      AAL5 reassembly point are not transmitted.
      
      PPD is available at all VCC connection points where UPC may be 
      activated. PPD is not applicable for Vpcs. 
      
      On CQC-based ATM FPs, packet-wise discards should only be 
      enabled for connections carrying AAL5 segmentation traffic. 
      Setting the value to enabled for any other traffic type may result in 
      traffic being discarded. 
      
      On ATM IP cards, this attribute may safely be set to enabled for any 
      connection (Vcc or Vpc) since they have the ability to automatically 
      detect AAL5-segmented traffic on a connection, and only enables 
      packet-wise discards if AAL5-segmented traffic is detected.
      
      When this attribute is set to enabled, packet-wise discard functions 
      are applied to receive traffic at this connection point. When this 
      attribute is set to disabled, packet-wise discard functions are not 
      applied to receive traffic at this connection point.
      
      At a SPVC origin on a PNNI interface, a value of enabled specifies 
      that frame discard is requested in the forward direction. When this 
      attribute is set to disabled, forward frame discard is not requested in 
      the SPVC call setup. 
      
      The receive packet-wise discard functions that are active are visible 
      in the Vcc/Vpc Tm rxPacketWiseDiscard operational attribute."
   DEFVAL     { disabled }
::= { atmIfVptVpdTmProvEntry 78 }

atmIfVptVpdTmAbrConnectionType OBJECT-TYPE
   SYNTAX     INTEGER  {
                 abrSwitch(0),
                 virtualSourceDest(3),
                 sourceDest(4),
                 nonAbrInterworking(5),
                 sameAsCa(14) }
   ACCESS     read-write
   STATUS     mandatory
   DESCRIPTION
     "This attribute specifies the type of ABR behavior which is to be 
      enforced at this connection. This attribute is only applicable if the 
      atmServiceCategory attribute is availableBitRate. If the 
      atmServicecategory attribute is not availableBitRate, this attribute 
      value is ignored.
      
      The actual ABR functionality which is in effect is visible in the 
      Vcc/Vpc/Vpt Tm abrConnectionType operational attribute.
      
      For CQC-based ATM cards, the only allowable values are 
      sameAsCa, nonAbrInterworking or abrSwitch. If abrSwitch is 
      selected, the CQC implements EFCI marking behavior.
      
      sameAsCa is used to request the default behavior as specified in the 
      CA Abr component for this Vcc. Otherwise, this attribute overrides 
      the default behavior. 
      
      virtualSourceDest is used to request that this connection point 
      function as a virtual source/virtual destination. VS/VD functionality 
      is only supported on ATM IP FPs.
      
      sourceDest requires that this connection point function as a S/D for 
      RM cells. S/D mode is automatically invoked at this connection 
      point either if this is a connection end point, or if the next hop 
      connection point is configured as nonAbrInterworking.
      
      nonAbrInterworking is used to request that this connection point 
      function as an interworking between ABR and non-ABR service 
      categories. This means that there are no RM cells on the link side of 
      this connection, and that the next hop connection point is 
      performing as an ABR sourceDest.
      
      abrSwitch is used to request ABR switch behavior for this 
      connection point. The ABR switch behavior is first, to confirm to 
      virtualSourceDest or nonAbrInterworking setting on the next hop, 
      and otherwise to implement ABR ER switch behavior. For CQC-
      based FPs, ABR switch behavior is implemented as EFCI marking."
   DEFVAL     { sameAsCa }
::= { atmIfVptVpdTmProvEntry 90 }

atmIfVptVpdTmTxTdpTable OBJECT-TYPE
   SYNTAX     SEQUENCE OF AtmIfVptVpdTmTxTdpEntry
   ACCESS     not-accessible
   STATUS     mandatory
   DESCRIPTION
     "This attribute is a vector of five traffic parameters whose meanings 
      are defined by the txTrafficDescType attribute. 
      
      The values of peak cell rate (PCR), sustained cell rate (SCR), 
      Minimum Cell Rate (MCR) and requested shaping rate are 
      expressed in cell/s. Maximum burst size (MBS) is expressed in 
      cells. CDVT is expressed in microseconds. The values of PCR, 
      SCR, MCR, MBS and CDVT are used for connection admission 
      control (CAC). The value of CDVT is only used for connections 
      where the atmServiceCategory is constantBitRate. For all other 
      values of atmServiceCategory, CDVT is ignored. The values of 
      PCR, SCR, MCR and requested shaping rate are used to determine 
      the actual shaping rate where traffic shaping is enabled.
      
      When txTrafficDescType is 1 or 2, all of the parameters must be set 
      to zero.
      
      When txTrafficDescType is 3, parameter 1 represents the PCR for 
      CLP equal to 0 and 1 traffic; parameter 4 represents the CDVT; and 
      parameter 5 represents the requested shaping rate. A non-zero value 
      in parameter 5 overrides any value in parameter 1. This result is 
      used as the PCR. Parameter 1 must be non-zero. Parameters 2 and 3 
      must be zero.
      
      When txTrafficDescType is 4, parameter 1 represents the PCR for 
      CLP equal to 0 and 1 traffic with cell discard; parameter 2 
      represents the PCR for CLP equal to 0 traffic; parameter 4 
      represents the CDVT; and parameter 5 represents the requested 
      shaping rate. A non-zero value in parameter 5 overrides any value in 
      parameter 1. This result is used as the PCR. Parameter 1 must be 
      greater than or equal to parameter 2. Parameters 1 and 2 must be 
      non-zero. Parameter 3 must be zero.
      
      When txTrafficDescType is 5, parameter 1 represents the PCR for 
      CLP equal to 0 and 1 traffic with cell tagging; parameter 2 
      represents the PCR for CLP equal to 0 traffic; parameter 4 
      represents the CDVT; and parameter 5 represents the requested 
      shaping rate. A non-zero value in parameter 5 overrides any value in 
      parameter 1. This result is used as the PCR. Parameter 1 must be 
      greater than or equal to parameter 2. Parameters 1 and 2 must be 
      non-zero. Parameter 3 must be zero.
      
      When txTrafficDescType is 6, parameter 1 represents the PCR for 
      CLP equal to 0 and 1 traffic; parameter 2 represents the SCR for 
      CLP equal to 0 and 1 traffic; parameter 3 represents the MBS for 
      CLP equal to 0 and 1 traffic; parameter 4 represents the CDVT; and 
      parameter 5 represents the requested shaping rate. A non-zero value 
      in parameter 5 overrides any value in parameter 1. This result is 
      used as the PCR. Parameters 1, 2 and 3 must be non-zero. 
      Parameter 1 must be greater than or equal to parameter 2. Parameter 
      5, must either be zero (unused) or greater than or equal to parameter 
      2.
      
      When txTrafficDescType is 7, parameter 1 represents the PCR for 
      CLP equal to 0 and 1 traffic; parameter 2 represents the SCR for 
      CLP equal to 0 with cell discard; parameter 3 represents the MBS 
      for CLP equal to 0 traffic; parameter 4 represents the CDVT; and 
      parameter 5 represents the requested shaping rate. A non-zero value 
      in parameter 5 overrides any value in parameter 1. This result is 
      used as the PCR. Parameters 1, 2 and 3 must be non-zero. 
      Parameter 1 must be greater than or equal to parameter 2. Parameter 
      5, must either be zero (unused) or greater than or equal to parameter 
      2.
      
      When txTrafficDescType is 8, parameter 1 represents the PCR for 
      CLP equal to 0 and 1 traffic; parameter 2 represents the SCR for 
      CLP equal to 0 traffic with cell tagging; parameter 3 represents the 
      MBS for CLP equal to 0 traffic; parameter 4 represents the CDVT; 
      and parameter 5 represents the requested shaping rate. A non-zero 
      value in parameter 5 overrides any value in parameter 1. This result 
      is used as the PCR. Parameters 1, 2 and 3 must be non-zero. 
      Parameter 1 must be greater than or equal to parameter 2. Parameter 
      5, must either be zero (unused) or greater than or equal to parameter 
      2.
      
      When txTrafficDescType is 9, parameter 1 represents the PCR; 
      parameter 2 represents the CDVT; parameter 3 represents the MCR; 
      parameter 4 and parameter 5 represent are not used and must be 
      zero. Parameter 1 must be non-zero and must be greater than or 
      equal to parameter 3. Parameter 3 may be optionally zero.
      
      Whenever it is valid for PCR to be specified, parameter 5 may also 
      be used to specify a requested shaping rate. A non-zero value in 
      parameter 5 overrides the value in parameter 1 and is used as the 
      peak cell rate in calculations of CAC and shaping rate. When the 
      atmServiceCategory is availableBitRate (ABR), the shaping rate is 
      dynamically chosen, based on the ABR flow control mechanism, as 
      a value between the MCR and the PCR or the requested shaping 
      rate if applicable.
      
      For txTrafficDescType 3, 4 and 5, the transmit traffic is shaped at 
      the next available shaping rate less than the PCR. 
      
      For txTrafficDescType 6, 7 and 8 if linear traffic shaping is selected, 
      the transmit traffic is shaped at the highest available rate which is 
      between PCR and SCR. However, if there is no available shaping 
      rate between PCR and SCR, traffic is shaped at the next rate above 
      the PCR. 
      
      For txTrafficDescType 6, 7 and 8 if inverse-UPC traffic shaping is 
      selected, the transmit traffic is shaped at a variable rate which 
      conforms to the PCR, SCR and MBS of the connection traffic 
      descriptor. Inverse-UPC traffic shaping is available only on ATM IP 
      cards."
::= { atmIfVptVpdTm 456 }

atmIfVptVpdTmTxTdpEntry OBJECT-TYPE
   SYNTAX     AtmIfVptVpdTmTxTdpEntry
   ACCESS     not-accessible
   STATUS     mandatory
   DESCRIPTION
     "An entry in the atmIfVptVpdTmTxTdpTable."
   INDEX {
      atmIfIndex,
      atmIfVptIndex,
      atmIfVptVpdIndex,
      atmIfVptVpdTmIndex,
      atmIfVptVpdTmTxTdpIndex }
::= { atmIfVptVpdTmTxTdpTable 1 }

AtmIfVptVpdTmTxTdpEntry ::= SEQUENCE {
   atmIfVptVpdTmTxTdpIndex
      Integer32,
   atmIfVptVpdTmTxTdpValue
      Unsigned32 }

atmIfVptVpdTmTxTdpIndex OBJECT-TYPE
   SYNTAX     Integer32 (1..5)
   ACCESS     not-accessible
   STATUS     mandatory
   DESCRIPTION
     "This variable represents the atmIfVptVpdTmTxTdpTable
      specific index for the atmIfVptVpdTmTxTdpTable."
::= { atmIfVptVpdTmTxTdpEntry 1 }

atmIfVptVpdTmTxTdpValue OBJECT-TYPE
   SYNTAX     Unsigned32 (0..2147483647)
   ACCESS     read-write
   STATUS     mandatory
   DESCRIPTION
     "This variable represents an individual value for the
      atmIfVptVpdTmTxTdpTable."
::= { atmIfVptVpdTmTxTdpEntry 2 }

atmIfVptVpdTmRxTdpTable OBJECT-TYPE
   SYNTAX     SEQUENCE OF AtmIfVptVpdTmRxTdpEntry
   ACCESS     not-accessible
   STATUS     mandatory
   DESCRIPTION
     "This attribute is a vector of four traffic parameters whose meanings 
      are defined by the rxTrafficDescType attribute. The values of peak 
      cell rate (PCR), sustained cell rate (SCR) and Minimum Cell Rate 
      (MCR) are expressed in cell/s. Maximum burst size (MBS) is 
      expressed in cells. The value of CDVT is expressed in 
      microseconds. The values of PCR, SCR, MCR, MBS and CDVT 
      are used for usage parameter control (UPC).
      
      When rxTrafficDescType is 1 or 2, all of the parameters must be set 
      to zero (unused).
      
      When rxTrafficDescType is 3, parameter 1 represents the PCR for 
      CLP equal to 0 and 1 traffic. Parameter 1 must be non-zero. 
      Parameters 2 and 3 must be set to zero (unused).
      
      When rxTrafficDescType is 4, parameter 1 represents the PCR 
      for CLP equal to 0 and 1 traffic; parameter 2 represents the PCR for 
      CLP equal to 0 traffic with cell discard. Parameters 1 and 2 must be 
      non-zero. Parameter 3 must be set to zero (unused). Parameter 1 
      must be greater than or equal to parameter 2.
      
      When rxTrafficDescType is 5, parameter 1 represents the PCR for 
      CLP equal to 0 and 1 traffic; parameter 2 represents the PCR for 
      CLP equal to 0 traffic with cell tagging. Parameters 1 and 2 must be 
      non-zero. Parameter 3 must be set to zero (unused). Parameter 1 
      must be greater than or equal to parameter 2.
      
      When rxTrafficDescType is a 6, parameter 1 represents the PCR for 
      CLP equal to 0 and 1 traffic; parameter 2 represents the SCR for 
      CLP equal to 0 and 1 traffic; parameter 3 represents the MBS for 
      CLP equal to 0 and 1 traffic. Parameters 1, 2 and 3 must be non-
      zero. Parameter 1 must be greater than or equal to Parameter 2. 
      
      When rxTrafficDescType is 7, parameter 1 represents the PCR for 
      CLP equal to 0 and 1 traffic; parameter 2 represents the SCR for 
      CLP equal to 0 traffic with cell discard; parameter 3 represents the 
      MBS for CLP equal to 0 traffic. Parameters 1, 2 and 3 must be non-
      zero. Parameter 1 must be greater than or equal to parameter 2. 
      
      When rxTrafficDescType is 8, parameter 1 represents the PCR for 
      CLP equal to 0 and 1 traffic; parameter 2 represents the SCR for 
      CLP equal to 0 traffic with cell tagging; parameter 3 represents the 
      MBS for CLP equal to 0 traffic. Parameter 1, 2 and 3 must be non-
      zero. Parameter 1 must be greater than or equal to parameter 2.
      
      When rxTrafficDescType is 9, parameter 1 represents the PCR; 
      parameter 2 represents the CDVT; parameter 3 represents the MCR. 
      Parameter 4 is not used and must be zero. Parameter 1,must be non-
      zero and must be greater than or equal to parameter 3. Parameter 3 
      may optionally be zero.
      
      When rxTrafficDescType is any value from 3 through 8, parameter 
      4 represents the CDVT. 
      
      If the value of CDVT either in parameter 2 or in parameter 4 is zero, 
      the CDVT is taken from the CA defaults for the particular 
      atmServiceCategory of this connection.
      
      On a CQC-based ATM card, when rxTrafficDescriptorType is 3 
      through 8, there are certain extreme combinations of 
      rxTrafficDescParm which are outside the capabilities of the UPC 
      hardware. The check prov command detects such cases and 
      generates an error message. If this happens, adjust the parameters 
      until they fall within the supported limits. 
      
      To calculate the limits, use the following formulae:
      I1 = 1 000 000 000 / PCR
      L1 = CDVT * 1000
      I2 = 1,000,000,000 / SCR
      L2 = CDVT + (MBS - 1) * (I2 - I1)
      I1 and I2 must be less than or equal to 335,523,840. I1 + L1 must 
      be less than or equal to 1,342,156,800. I2 + L2 must be less than or 
      equal to 1,342,156,800. Note that I2 and L2 only apply when the 
      rxTrafficDescriptorType is 6 through 8.
      
      If the values of I1, L1, I2 or L2 are closer to the limits described 
      above, a further restriction applies. Specifically, if either:
      I1 > 41,940,480 or
      I2 > 41,940,480 or
      I1 + L1 > 167,769,600 or
      I2 + L2 > 167,769,600
      then both I1 and I2 must be greater than 20,480. 
      
      Parameter 5 of the rxTrafficDescParm is always unused. 
      
      If the rxTrafficDescType is sameAsTx, the values provisioned in 
      this attribute are ignored. The traffic parameters for the receive 
      direction are taken from the txTrafficDescParm."
::= { atmIfVptVpdTm 457 }

atmIfVptVpdTmRxTdpEntry OBJECT-TYPE
   SYNTAX     AtmIfVptVpdTmRxTdpEntry
   ACCESS     not-accessible
   STATUS     mandatory
   DESCRIPTION
     "An entry in the atmIfVptVpdTmRxTdpTable."
   INDEX {
      atmIfIndex,
      atmIfVptIndex,
      atmIfVptVpdIndex,
      atmIfVptVpdTmIndex,
      atmIfVptVpdTmRxTdpIndex }
::= { atmIfVptVpdTmRxTdpTable 1 }

AtmIfVptVpdTmRxTdpEntry ::= SEQUENCE {
   atmIfVptVpdTmRxTdpIndex
      Integer32,
   atmIfVptVpdTmRxTdpValue
      Unsigned32 }

atmIfVptVpdTmRxTdpIndex OBJECT-TYPE
   SYNTAX     Integer32 (1..5)
   ACCESS     not-accessible
   STATUS     mandatory
   DESCRIPTION
     "This variable represents the atmIfVptVpdTmRxTdpTable
      specific index for the atmIfVptVpdTmRxTdpTable."
::= { atmIfVptVpdTmRxTdpEntry 1 }

atmIfVptVpdTmRxTdpValue OBJECT-TYPE
   SYNTAX     Unsigned32 (0..2147483647)
   ACCESS     read-write
   STATUS     mandatory
   DESCRIPTION
     "This variable represents an individual value for the
      atmIfVptVpdTmRxTdpTable."
::= { atmIfVptVpdTmRxTdpEntry 2 }

atmIfVptVpdTmFqpTable OBJECT-TYPE
   SYNTAX     SEQUENCE OF AtmIfVptVpdTmFqpEntry
   ACCESS     not-accessible
   STATUS     mandatory
   DESCRIPTION
     "This attribute is a vector of three elements that specify the quality of 
      service parameters for the forward direction for this connection. 
      This attribute is used for SPVC connections.
      
      The cdv element specifies the acceptable peak-to-peak Cell Delay 
      Variation (CDV) of real-time connections (CBR and rt-VBR). It is 
      signalled through the extended QoS information element.
      
      The ctd specifies the acceptable maximum Cell Transfer Delay 
      (maxCtd) of real-time connections (CBR and rt-VBR). 
      It is signalled through the end to end transit delay information 
      element.
      
      The clr specifies the acceptable Cell Loss Ratio (CLR) of CBR, rt-
      VBR, and nrt-VBR connections. It is signalled through the extended 
      QoS information element."
::= { atmIfVptVpdTm 458 }

atmIfVptVpdTmFqpEntry OBJECT-TYPE
   SYNTAX     AtmIfVptVpdTmFqpEntry
   ACCESS     not-accessible
   STATUS     mandatory
   DESCRIPTION
     "An entry in the atmIfVptVpdTmFqpTable."
   INDEX {
      atmIfIndex,
      atmIfVptIndex,
      atmIfVptVpdIndex,
      atmIfVptVpdTmIndex,
      atmIfVptVpdTmFqpIndex }
::= { atmIfVptVpdTmFqpTable 1 }

AtmIfVptVpdTmFqpEntry ::= SEQUENCE {
   atmIfVptVpdTmFqpIndex
      INTEGER,
   atmIfVptVpdTmFqpValue
      Unsigned32 }

atmIfVptVpdTmFqpIndex OBJECT-TYPE
   SYNTAX     INTEGER  {
                 cdv(0),
                 ctd(1),
                 clr(2) }
   ACCESS     not-accessible
   STATUS     mandatory
   DESCRIPTION
     "This variable represents the atmIfVptVpdTmFqpTable
      specific index for the atmIfVptVpdTmFqpTable."
::= { atmIfVptVpdTmFqpEntry 1 }

atmIfVptVpdTmFqpValue OBJECT-TYPE
   SYNTAX     Unsigned32 (0..16777215)
   ACCESS     read-write
   STATUS     mandatory
   DESCRIPTION
     "This variable represents an individual value for the
      atmIfVptVpdTmFqpTable."
::= { atmIfVptVpdTmFqpEntry 2 }

atmIfVptVpdTmBqpTable OBJECT-TYPE
   SYNTAX     SEQUENCE OF AtmIfVptVpdTmBqpEntry
   ACCESS     not-accessible
   STATUS     mandatory
   DESCRIPTION
     "This attribute is a vector of two elements that specify the quality of 
      service parameters for the backward direction for this connection. 
      This attribute is used for SPVC connections.
      
      The cdv element specifies the acceptable peak-to-peak Cell Delay 
      Variation (CDV) of real-time connections (CBR and rt-VBR). It is 
      signalled through the extended QoS information element.
      
      The clr specifies the acceptable Cell Loss Ratio (CLR) of CBR, rt-
      VBR, and nrt-VBR connections. It is signalled through the extended 
      QoS information element."
::= { atmIfVptVpdTm 459 }

atmIfVptVpdTmBqpEntry OBJECT-TYPE
   SYNTAX     AtmIfVptVpdTmBqpEntry
   ACCESS     not-accessible
   STATUS     mandatory
   DESCRIPTION
     "An entry in the atmIfVptVpdTmBqpTable."
   INDEX {
      atmIfIndex,
      atmIfVptIndex,
      atmIfVptVpdIndex,
      atmIfVptVpdTmIndex,
      atmIfVptVpdTmBqpIndex }
::= { atmIfVptVpdTmBqpTable 1 }

AtmIfVptVpdTmBqpEntry ::= SEQUENCE {
   atmIfVptVpdTmBqpIndex
      INTEGER,
   atmIfVptVpdTmBqpValue
      Unsigned32 }

atmIfVptVpdTmBqpIndex OBJECT-TYPE
   SYNTAX     INTEGER  {
                 cdv(0),
                 clr(2) }
   ACCESS     not-accessible
   STATUS     mandatory
   DESCRIPTION
     "This variable represents the atmIfVptVpdTmBqpTable
      specific index for the atmIfVptVpdTmBqpTable."
::= { atmIfVptVpdTmBqpEntry 1 }

atmIfVptVpdTmBqpValue OBJECT-TYPE
   SYNTAX     Unsigned32 (0..16777215)
   ACCESS     read-write
   STATUS     mandatory
   DESCRIPTION
     "This variable represents an individual value for the
      atmIfVptVpdTmBqpTable."
::= { atmIfVptVpdTmBqpEntry 2 }


-- AtmIf/n Vcc/vpi.vci Vcd Tm AvailableBitRate, 
-- AtmIf/n Vpc/vci Vpd Tm AvailableBitRate,
-- AtmIf/n Vpt/vpi Vpd Tm AvailableBitRate,
-- AtmIf/n Vpt/vpi Vcc/vci Vcd Tm AvailableBitRate
-- This component contains provisioned ABR-related attributes of a 
-- connection. It is an optional subcomponent of the Vcd Tm and Vpd 
-- Tm component. It is used to override DGCRA-related defaults in 
-- the CA Abr component. It contains the specific configuration for the 
-- ABR connection at this connection point. If this is the source of an 
-- SPVC connection, this component also contains the ABR 
-- parameters required for the SPVC call request.

atmIfVptVpdTmAbr OBJECT IDENTIFIER ::= { atmIfVptVpdTm 2 }



atmIfVptVpdTmAbrRowStatusTable OBJECT-TYPE
   SYNTAX     SEQUENCE OF AtmIfVptVpdTmAbrRowStatusEntry
   ACCESS     not-accessible
   STATUS     mandatory
   DESCRIPTION
     "This entry controls the addition and deletion of 
      atmIfVptVpdTmAbr components."
::= { atmIfVptVpdTmAbr 1 }

atmIfVptVpdTmAbrRowStatusEntry OBJECT-TYPE
   SYNTAX     AtmIfVptVpdTmAbrRowStatusEntry
   ACCESS     not-accessible
   STATUS     mandatory
   DESCRIPTION
     "A single entry in the table represents a single 
      atmIfVptVpdTmAbr component."
   INDEX {
      atmIfIndex,
      atmIfVptIndex,
      atmIfVptVpdIndex,
      atmIfVptVpdTmIndex,
      atmIfVptVpdTmAbrIndex }
::= { atmIfVptVpdTmAbrRowStatusTable 1 }

AtmIfVptVpdTmAbrRowStatusEntry ::= SEQUENCE {
   atmIfVptVpdTmAbrRowStatus
      RowStatus,
   atmIfVptVpdTmAbrComponentName
      DisplayString,
   atmIfVptVpdTmAbrStorageType
      StorageType,
   atmIfVptVpdTmAbrIndex
      NonReplicated }

atmIfVptVpdTmAbrRowStatus OBJECT-TYPE
   SYNTAX     RowStatus 
   ACCESS     read-write
   STATUS     mandatory
   DESCRIPTION
     "This variable is used as the basis for SNMP naming of
      atmIfVptVpdTmAbr components.
      These components can be added and deleted."
::= { atmIfVptVpdTmAbrRowStatusEntry 1 }

atmIfVptVpdTmAbrComponentName OBJECT-TYPE
   SYNTAX     DisplayString 
   ACCESS     read-only
   STATUS     mandatory
   DESCRIPTION
     "This variable provides the component's string name for
      use with the ASCII Console Interface"
::= { atmIfVptVpdTmAbrRowStatusEntry 2 }

atmIfVptVpdTmAbrStorageType OBJECT-TYPE
   SYNTAX     StorageType 
   ACCESS     read-only
   STATUS     mandatory
   DESCRIPTION
     "This variable represents the storage type value for the
      atmIfVptVpdTmAbr tables."
::= { atmIfVptVpdTmAbrRowStatusEntry 4 }

atmIfVptVpdTmAbrIndex OBJECT-TYPE
   SYNTAX     NonReplicated 
   ACCESS     not-accessible
   STATUS     mandatory
   DESCRIPTION
     "This variable represents the index for the atmIfVptVpdTmAbr tables."
::= { atmIfVptVpdTmAbrRowStatusEntry 10 }

atmIfVptVpdTmAbrProvTable OBJECT-TYPE
   SYNTAX     SEQUENCE OF AtmIfVptVpdTmAbrProvEntry
   ACCESS     not-accessible
   STATUS     mandatory
   DESCRIPTION
     "This group contains provisioned attributes for the ABR ATM 
      connections configured on an ATM interface."
::= { atmIfVptVpdTmAbr 110 }

atmIfVptVpdTmAbrProvEntry OBJECT-TYPE
   SYNTAX     AtmIfVptVpdTmAbrProvEntry
   ACCESS     not-accessible
   STATUS     mandatory
   DESCRIPTION
     "An entry in the atmIfVptVpdTmAbrProvTable."
   INDEX {
      atmIfIndex,
      atmIfVptIndex,
      atmIfVptVpdIndex,
      atmIfVptVpdTmIndex,
      atmIfVptVpdTmAbrIndex }
::= { atmIfVptVpdTmAbrProvTable 1 }

AtmIfVptVpdTmAbrProvEntry ::= SEQUENCE {
   atmIfVptVpdTmAbrInitialCellRate
      Unsigned32,
   atmIfVptVpdTmAbrTransientBufferExposure
      Unsigned32,
   atmIfVptVpdTmAbrFixedRoundTripTime
      Unsigned32,
   atmIfVptVpdTmAbrRateDecreaseFactor
      Unsigned32,
   atmIfVptVpdTmAbrRateIncreaseFactor
      Unsigned32,
   atmIfVptVpdTmAbrMaxCellPerRmCell
      Unsigned32,
   atmIfVptVpdTmAbrMaxTimeBetweenRmCells
      Unsigned32,
   atmIfVptVpdTmAbrCutoffDecreaseFactor
      Unsigned32,
   atmIfVptVpdTmAbrAcrDecreaseTimeFactor
      Unsigned32,
   atmIfVptVpdTmAbrDgcraMaximumDelay
      Unsigned32,
   atmIfVptVpdTmAbrDgcraMinimumDelay
      Unsigned32,
   atmIfVptVpdTmAbrFarEndAcrDecreaseTimeFactor
      Unsigned32,
   atmIfVptVpdTmAbrFarEndInitialCellRate
      Unsigned32 }

atmIfVptVpdTmAbrInitialCellRate OBJECT-TYPE
   SYNTAX     Unsigned32 (0..16777215 | 16777216 | 16777217 | 16777218)
   ACCESS     read-write
   STATUS     mandatory
   DESCRIPTION
     "This attribute specifies the Initial Cell Rate (ICR) parameter for this 
      connection. ICR is the rate at which a source should send initially 
      and after an idle period.
      
      When this attribute is set to sameAsCa, the initial cell rate is 
      determined by the AtmIf CA Abr/0 icr attribute. When the value of 
      this attribute is set to useMcr, ICR is set to the same value as the 
      Minimum Cell Rate (MCR) for the connection.
      
      When the value of this attribute is set to usePcr, ICR is set to the 
      same value as the Peak Cell Rate (PCR) for the connection.
      
      If this attribute is specified less than the MCR of the connection, 
      then the MCR is used as the ICR. If this attribute is specified more 
      than PCR of the connection, then PCR is used as the ICR.
      
      This attribute is ignored under all conditions where the operational 
      attribute abrConnectionType indicates erSwitch or efciSwitch.

      VALUES (

      16777216 = sameAsCa

      16777217 = useMcr

      16777218 = usePcr

      )"
   DEFVAL     { 16777216 }
::= { atmIfVptVpdTmAbrProvEntry 10 }

atmIfVptVpdTmAbrTransientBufferExposure OBJECT-TYPE
   SYNTAX     Unsigned32 (0..16777215)
   ACCESS     read-write
   STATUS     mandatory
   DESCRIPTION
     "This attribute specifies the Transient Buffer Exposure (TBE) for this 
      connection. TBE is the negotiated number of cells that the network 
      would like to limit the source to send during start-up periods, before 
      the first Resource Management (RM) cell returns.
      
      TBE divided by fixedRoundTripTime determines an upper bound 
      for the operational value of initialCellRate, the rate at which a 
      source should send initially and after an idle period.
      
      TBE divided by maxCellsPerRmCell specifies the operational value 
      of forwardRmCellLimit, the limit of the number of forward 
      Resource Management (RM) cells which may be sent in the 
      absence of received backward RM cells.
      
      This attribute is ignored under all conditions where the operational 
      attribute abrConnectionType is set to erSwitch."
   DEFVAL     { 16777215 }
::= { atmIfVptVpdTmAbrProvEntry 11 }

atmIfVptVpdTmAbrFixedRoundTripTime OBJECT-TYPE
   SYNTAX     Unsigned32 (0..16700000)
   ACCESS     read-write
   STATUS     mandatory
   DESCRIPTION
     "This attribute specifies the Fixed Round-Trip Time (FRTT) 
      parameter for this connection. FRTT is the sum of the fixed and 
      propagation delays from the source to a destination and back.
      
      The value of transientBufferExposure divided by the value of FRTT 
      (in seconds) determines an upper bound for the operational value of 
      initialCellRate, the rate at which a source should send initially and 
      after an idle period.
      
      This attribute is ignored under all conditions where the operational 
      attribute abrConnectionType indicates erSwitch or efciSwitch."
   DEFVAL     { 5000000 }
::= { atmIfVptVpdTmAbrProvEntry 12 }

atmIfVptVpdTmAbrRateDecreaseFactor OBJECT-TYPE
   SYNTAX     Unsigned32 (0..15 | 16777216)
   ACCESS     read-write
   STATUS     mandatory
   DESCRIPTION
     "This attribute specifies the Rate Decrease Factor (RDF) for this 
      connection. The RDF value is computed by using the provisioned 
      value of this attribute, n, as 2 to the inverse power n. For example, if 
      the value of this attribute is 8, RDF is 2E-8 = 1/256.
      
      RDF controls the amount by which the cell transmission rate may 
      decrease upon receipt of a backward Resource Management (RM) 
      cell. For example, if a backward RM cell is received with the 
      Congestion Indication (CI) field set to 1, the Allowed Cell Rate 
      (ACR) value would be reduced by the amount (RDF*ACR). The 
      ACR is not allowed to fall below the Minimum Cell Rate (MCR), in 
      which case the ACR is set to MCR.
      
      This attribute is ignored under all conditions where the operational 
      attribute abrConnectionType has the value erSwitch.

      VALUES (

      16777216 = sameAsCa

      )"
   DEFVAL     { 16777216 }
::= { atmIfVptVpdTmAbrProvEntry 13 }

atmIfVptVpdTmAbrRateIncreaseFactor OBJECT-TYPE
   SYNTAX     Unsigned32 (0..15 | 16777216)
   ACCESS     read-write
   STATUS     mandatory
   DESCRIPTION
     "This attribute specifies the Rate Increase Factor (RIF) for this 
      connection. The RIF value is computed by using the provisioned 
      value of this attribute, n, as 2 to the inverse power n. For example, if 
      the value of this attribute is 6, RIF is 2E-6 = 1/64.
      
      RIF controls the amount by which the cell transmission rate may 
      increase upon receipt of a backward Resource Management (RM) 
      cell. For example, if a backward RM cell is received with the 
      Congestion Indication (CI) and the No Increase (NI) fields both set 
      to 0, the Allowed Cell Rate (ACR) value would be increased by the 
      amount (RIF*ACR). The ACR is not allowed to exceed the Peak 
      Cell Rate (PCR), in which case the ACR is set to PCR.
      
      This attribute is ignored under all conditions where the operational 
      attribute abrConnectionType has the value erSwitch.

      VALUES (

      16777216 = sameAsCa

      )"
   DEFVAL     { 16777216 }
::= { atmIfVptVpdTmAbrProvEntry 14 }

atmIfVptVpdTmAbrMaxCellPerRmCell OBJECT-TYPE
   SYNTAX     Unsigned32 (2 | 4 | 8 | 16 | 32 | 64 | 128 | 256 | 16777216)
   ACCESS     read-write
   STATUS     mandatory
   DESCRIPTION
     "This attribute specifies the maximum number of cells an ABR 
      source may transmit for each forward Resource Management (RM) 
      cell. The count of the cells transmitted includes data cells, OAM 
      cells, backward RM cells, and the forward RM cell.
      
      A value of 2 is not recommended although it is permitted according 
      to the ATM Forum standard. When this attribute is set to a value of 
      2, it is possible that only one forward and one backward RM cell 
      are repeatedly transmitted, and all data traffic is queued up 
      indefinitely.
      
      This attribute is ignored under all conditions where the operational 
      attribute abrConnectionType has the value erSwitch.

      VALUES (

      16777216 = sameAsCa

      )"
   DEFVAL     { 16777216 }
::= { atmIfVptVpdTmAbrProvEntry 15 }

atmIfVptVpdTmAbrMaxTimeBetweenRmCells OBJECT-TYPE
   SYNTAX     Unsigned32 (781 | 1563 | 3125 | 6250 | 12500 | 25000 | 50000 | 100000 | 16777216)
   ACCESS     read-write
   STATUS     mandatory
   DESCRIPTION
     "This attribute specifies the TRM parameter for this connection.
      
      TRM provides an lower bound on the time interval between forward 
      Resource Management (RM) cells for an ABR source. Since the last 
      forward RM cell was sent, if at least TRM time has elapsed since 
      and at least two other cells have been sent, then the next cell to be 
      transmitted would be a forward RM cell.
      
      This attribute is ignored under all conditions where the operational 
      attribute abrConnectionType has the value erSwitch.
      
      The provisioned value of 781 is signalled as TRM = 0, in the ABR 
      Additional Parameters Information Element. 
      1563 is signalled as TRM = 1. 
      3125 is signalled as TRM = 2. 
      6250 is signalled as TRM = 3. 
      12500 is signalled as TRM = 4 
      25000 is signalled as TRM = 5. 
      50000 is signalled as TRM = 6. 
      100000 is signalled as TRM = 7.

      VALUES (

      16777216 = sameAsCa

      )"
   DEFVAL     { 16777216 }
::= { atmIfVptVpdTmAbrProvEntry 16 }

atmIfVptVpdTmAbrCutoffDecreaseFactor OBJECT-TYPE
   SYNTAX     Unsigned32 (0 | 1 | 2 | 4 | 8 | 16 | 32 | 64 | 16777216)
   ACCESS     read-write
   STATUS     mandatory
   DESCRIPTION
     "This attribute specifies the Cutoff Decrease Factor (CDF) parameter 
      for this connection. When the value of this attribute is non-zero, 
      CDF is computed as the inverse of the value. For example, if the 
      value is 32, the value of CDF is 1/32. When the value of this 
      attribute is 0, CDF is also zero.
      
      CDF controls the decrease in the Allowed Cell Rate (ACR) 
      associated with the CRM parameter, the limit of the number of 
      forward Resource Management (RM) cells which may be sent in 
      the absence of received backward RM cells. When this limit is 
      crossed, the ACR value would be decreased by the amount 
      (CDF*ACR). The ACR is not allowed to fall below the Minimum 
      Cell Rate (MCR), in which case the ACR is set to MCR.
      
      The value of CRM is indicated by the forwardRmCellLimit 
      attribute.
      
      This attribute is ignored under all conditions where the operational 
      attribute abrConnectionType indicates erSwitch or efciSwitch.

      VALUES (

      16777216 = sameAsCa

      )"
   DEFVAL     { 16777216 }
::= { atmIfVptVpdTmAbrProvEntry 17 }

atmIfVptVpdTmAbrAcrDecreaseTimeFactor OBJECT-TYPE
   SYNTAX     Unsigned32 (0..1023 | 16777216)
   ACCESS     read-write
   STATUS     mandatory
   DESCRIPTION
     "This attribute specifies the Allowed Cell Rate Decrease Time Factor 
      (ADTF) parameter for this connection.
      
      ADTF is the maximum time interval permitted between sending 
      forward Resource Management (RM) cells before the Allowed Cell 
      Rate (ACR) is decreased to initialCellRate. In other words, if the 
      source does not transit a forward RM cell for the period specified by 
      adtf, it reduces its ACR to the value of its initialCellRate.
      
      This attribute is ignored under all conditions where the operational 
      attribute abrConnectionType indicates erSwitch or efciSwitch.

      VALUES (

      16777216 = sameAsCa

      )"
   DEFVAL     { 16777216 }
::= { atmIfVptVpdTmAbrProvEntry 18 }

atmIfVptVpdTmAbrDgcraMaximumDelay OBJECT-TYPE
   SYNTAX     Unsigned32 (1..16700000 | 16777216)
   ACCESS     read-write
   STATUS     mandatory
   DESCRIPTION
     "This attribute specifies an upper bound on the delay after which the 
      rate change induced by a backward Resource Management (RM) 
      cell departing from this connection point (in the backward 
      direction) is expected to be observed at this connection point (in the 
      forward direction).
      
      This upper bound may be approximated as the sum of the round trip 
      fixed and propagation delays and the maximum queuing delays 
      between the ABR source and this interface.
      
      The value of this attribute is used in policing an ABR connection 
      using the Dynamic General Cell Rate Algorithm (DGCRA). A 
      larger value for this attribute implies a more lenient policer. When 
      there is a reduction in the Allowed Cell Rate (ACR), the policer 
      waits for a correspondingly longer period of time before it enforces 
      at the new cell rate.
      
      The value of this attribute must not be less than the 
      dgcraMinimumDelay attribute.

      VALUES (

      16777216 = sameAsCa

      )"
   DEFVAL     { 16777216 }
::= { atmIfVptVpdTmAbrProvEntry 19 }

atmIfVptVpdTmAbrDgcraMinimumDelay OBJECT-TYPE
   SYNTAX     Unsigned32 (1..16700000 | 16777216)
   ACCESS     read-write
   STATUS     mandatory
   DESCRIPTION
     "This attribute specifies a lower bound on the delay after which the 
      rate change induced by a backward Resource Management (RM) 
      cell departing from this connection point (in the backward 
      direction) is expected to be observed at this connection point (in the 
      forward connection).
      
      This lower bound may be approximated as the sum of the round trip 
      fixed and propagation delays between the ABR source and this 
      interface.
      
      The value of this attribute is used in policing an ABR connection 
      using the Dynamic General Cell Rate Algorithm (DGCRA). A 
      smaller value for this attribute implies a more lenient policer. When 
      there is a increase in the Allowed Cell Rate (ACR), the policer waits 
      for a correspondingly shorter period of time before it enforces at the 
      new cell rate.

      VALUES (

      16777216 = sameAsCa

      )"
   DEFVAL     { 16777216 }
::= { atmIfVptVpdTmAbrProvEntry 20 }

atmIfVptVpdTmAbrFarEndAcrDecreaseTimeFactor OBJECT-TYPE
   SYNTAX     Unsigned32 (0..1023 | 1024)
   ACCESS     read-write
   STATUS     mandatory
   DESCRIPTION
     "This attribute specifies the Allowed Cell Rate Decrease Time Factor 
      (ADTF) of the far end ABR source. The value specified should be 
      the same as the ADTF parameter at the far end of this ABR 
      connection. 
      
      The value of this attribute is used in policing an ABR connection 
      using the Dynamic Generic Cell Rate Algorithm (DGCRA). A 
      larger value for this attribute implies a more lenient policer. When 
      the delay between two consecutive forward Resource Management 
      (RM) cells received at this interface corresponds to a value greater 
      than the value of this attribute, the policer begins to limit enforce 
      the incoming traffic at the initial cell rate (ICR) of the far end, as 
      specified by the farEndInitialCellRate attribute.

      VALUES (

      1024 = sameAsLocal

      )"
   DEFVAL     { 1024 }
::= { atmIfVptVpdTmAbrProvEntry 21 }

atmIfVptVpdTmAbrFarEndInitialCellRate OBJECT-TYPE
   SYNTAX     Unsigned32 (0..16777215 | 16777219)
   ACCESS     read-write
   STATUS     mandatory
   DESCRIPTION
     "This attribute specifies the Initial Cell Rate (ICR) of the far end 
      ABR source. The value specified should be the same as the ICR 
      parameter at the far end of this ABR connection. 
      
      The value of this attribute is used in policing an ABR connection 
      using the Dynamic Generic Cell Rate Algorithm (DGCRA). A 
      larger value for this attribute implies a more lenient policer. When 
      the delay between two consecutive forward Resource Management 
      (RM) cells received at this interface corresponds to a value greater 
      than the farEndAcrDecreaseTimeFactor attribute, the policer begins 
      to enforce the incoming traffic at the value of this attribute.
      
      If this attribute is specified less than the MCR of the connection, 
      then the MCR is used as the feIcr. If this attribute is more than the 
      PCR of the connection, then PCR is used as the feIcr.

      VALUES (

      16777219 = sameAsLocal

      )"
   DEFVAL     { 16777219 }
::= { atmIfVptVpdTmAbrProvEntry 22 }


-- AtmIf/n Vpt/n ConnectionAdministrator 
-- This component controls connection admission, and reports 
-- statistics about the ATM connections which have been admitted on 
-- this Virtual Path Terminator (VPT).
-- 
-- If the VPT does not have the optional CA component, all 
-- connections associated with the given VPT attempt their admission 
-- through the AtmIf CA.
-- 
-- The provisionable attributes of this ConnectionAdministrator 
-- override those of the AtmIf CA, for all connections associated with 
-- this Vpt. Any attributes of the AtmIf CA that cannot be overridden in 
-- the Vpt CA affect all connections, including Vpt Vccs.

atmIfVptCA OBJECT IDENTIFIER ::= { atmIfVpt 5 }



atmIfVptCARowStatusTable OBJECT-TYPE
   SYNTAX     SEQUENCE OF AtmIfVptCARowStatusEntry
   ACCESS     not-accessible
   STATUS     mandatory
   DESCRIPTION
     "This entry controls the addition and deletion of 
      atmIfVptCA components."
::= { atmIfVptCA 1 }

atmIfVptCARowStatusEntry OBJECT-TYPE
   SYNTAX     AtmIfVptCARowStatusEntry
   ACCESS     not-accessible
   STATUS     mandatory
   DESCRIPTION
     "A single entry in the table represents a single 
      atmIfVptCA component."
   INDEX {
      atmIfIndex,
      atmIfVptIndex,
      atmIfVptCAIndex }
::= { atmIfVptCARowStatusTable 1 }

AtmIfVptCARowStatusEntry ::= SEQUENCE {
   atmIfVptCARowStatus
      RowStatus,
   atmIfVptCAComponentName
      DisplayString,
   atmIfVptCAStorageType
      StorageType,
   atmIfVptCAIndex
      NonReplicated }

atmIfVptCARowStatus OBJECT-TYPE
   SYNTAX     RowStatus 
   ACCESS     read-write
   STATUS     mandatory
   DESCRIPTION
     "This variable is used as the basis for SNMP naming of
      atmIfVptCA components.
      These components can be added and deleted."
::= { atmIfVptCARowStatusEntry 1 }

atmIfVptCAComponentName OBJECT-TYPE
   SYNTAX     DisplayString 
   ACCESS     read-only
   STATUS     mandatory
   DESCRIPTION
     "This variable provides the component's string name for
      use with the ASCII Console Interface"
::= { atmIfVptCARowStatusEntry 2 }

atmIfVptCAStorageType OBJECT-TYPE
   SYNTAX     StorageType 
   ACCESS     read-only
   STATUS     mandatory
   DESCRIPTION
     "This variable represents the storage type value for the
      atmIfVptCA tables."
::= { atmIfVptCARowStatusEntry 4 }

atmIfVptCAIndex OBJECT-TYPE
   SYNTAX     NonReplicated 
   ACCESS     not-accessible
   STATUS     mandatory
   DESCRIPTION
     "This variable represents the index for the atmIfVptCA tables."
::= { atmIfVptCARowStatusEntry 10 }

atmIfVptCAProvTable OBJECT-TYPE
   SYNTAX     SEQUENCE OF AtmIfVptCAProvEntry
   ACCESS     not-accessible
   STATUS     mandatory
   DESCRIPTION
     "This group contains provisioned attributes which control 
      Connection Admission Control (CAC) attributes for the ATM 
      connections associated with a Virtual Path Terminator. Note that the 
      names of some of the attributes follow the conventions of UNI 4.0 
      for forward compatibility reasons. This does not imply conformance 
      in general with the UNI 4.0 specification. 
      
      The provisioned attributes of this ConnectionAdministrator will 
      override those of the AtmIf CA, for all connections associated with 
      this Vpt. Any attributes of the AtmIf CA that cannot be overridden in 
      the Vpt CA affect all connections, including Vpt Vccs."
::= { atmIfVptCA 100 }

atmIfVptCAProvEntry OBJECT-TYPE
   SYNTAX     AtmIfVptCAProvEntry
   ACCESS     not-accessible
   STATUS     mandatory
   DESCRIPTION
     "An entry in the atmIfVptCAProvTable."
   INDEX {
      atmIfIndex,
      atmIfVptIndex,
      atmIfVptCAIndex }
::= { atmIfVptCAProvTable 1 }

AtmIfVptCAProvEntry ::= SEQUENCE {
   atmIfVptCAMaxVccs
      Unsigned32,
   atmIfVptCAPermittedAtmServiceCategories
      OCTET STRING }

atmIfVptCAMaxVccs OBJECT-TYPE
   SYNTAX     Unsigned32 (0..16384)
   ACCESS     read-write
   STATUS     mandatory
   DESCRIPTION
     "This attribute specifies the maximum number of Vccs that can be 
      associated with this Vpt. The value must not exceed the maxVccs 
      attribute of the Atmif CA."
   DEFVAL     { 255 }
::= { atmIfVptCAProvEntry 6 }

atmIfVptCAPermittedAtmServiceCategories OBJECT-TYPE
   SYNTAX     OCTET STRING (SIZE (1))
   ACCESS     read-write
   STATUS     mandatory
   DESCRIPTION
     "This attribute specifies which ATM service categories are permitted 
      on this Vpt for SVCs. The value of this attribute does not affect 
      control Vccs, such as signalling and ILMI channels. If the value is 
      empty, no SVCs are permitted to use this Vpt.

      Description of bits:
      unspecifiedBitRate(0)
      constantBitRate(1)
      rtVariableBitRate(2)
      nrtVariableBitRate(3)"
   DEFVAL     { 'f0'H }
::= { atmIfVptCAProvEntry 25 }

atmIfVptCAOperTable OBJECT-TYPE
   SYNTAX     SEQUENCE OF AtmIfVptCAOperEntry
   ACCESS     not-accessible
   STATUS     mandatory
   DESCRIPTION
     "This group contains operational attributes giving statistics about the 
      ATM connections associated with a Virtual Path Terminator (VPT)."
::= { atmIfVptCA 110 }

atmIfVptCAOperEntry OBJECT-TYPE
   SYNTAX     AtmIfVptCAOperEntry
   ACCESS     not-accessible
   STATUS     mandatory
   DESCRIPTION
     "An entry in the atmIfVptCAOperTable."
   INDEX {
      atmIfIndex,
      atmIfVptIndex,
      atmIfVptCAIndex }
::= { atmIfVptCAOperTable 1 }

AtmIfVptCAOperEntry ::= SEQUENCE {
   atmIfVptCAPermanentVccs
      Unsigned32,
   atmIfVptCASwitchedVccs
      Gauge32,
   atmIfVptCATroubledVccs
      Unsigned32,
   atmIfVptCAConnectionPoolUsage
      Gauge32 }

atmIfVptCAPermanentVccs OBJECT-TYPE
   SYNTAX     Unsigned32 (0..16384)
   ACCESS     read-only
   STATUS     mandatory
   DESCRIPTION
     "This attribute indicates the number of permanent Vccs that are 
      currently associated with this Vpt."
::= { atmIfVptCAOperEntry 20 }

atmIfVptCASwitchedVccs OBJECT-TYPE
   SYNTAX     Gauge32 (0..16384)
   ACCESS     read-only
   STATUS     mandatory
   DESCRIPTION
     "This attribute indicates the number of switched Vccs that are 
      currently associated with this Vpt."
::= { atmIfVptCAOperEntry 30 }

atmIfVptCATroubledVccs OBJECT-TYPE
   SYNTAX     Unsigned32 (0..16384)
   ACCESS     read-only
   STATUS     mandatory
   DESCRIPTION
     "This attribute indicates the number of troubled Vccs associated with 
      this Vpt. A Vcc is 'troubled' if its operational troubled attribute has 
      the value yes."
::= { atmIfVptCAOperEntry 70 }

atmIfVptCAConnectionPoolUsage OBJECT-TYPE
   SYNTAX     Gauge32 (0..10752)
   ACCESS     read-only
   STATUS     mandatory
   DESCRIPTION
     "This attribute indicates the number of allocated VCCs associated 
      with this VPT.
      
      Each of these VCCs uses a connection out of the pool defined by 
      the Arc totalConnectionPoolAvailable attribute."
::= { atmIfVptCAOperEntry 81 }

atmIfVptCAPoolAvailBwTable OBJECT-TYPE
   SYNTAX     SEQUENCE OF AtmIfVptCAPoolAvailBwEntry
   ACCESS     not-accessible
   STATUS     mandatory
   DESCRIPTION
     "This attribute indicates the total available bandwidth in the 
      corresponding bandwidthPool. A non-zero number indicates that 
      there is still bandwidth available in the pool which has not been 
      allocated."
::= { atmIfVptCA 460 }

atmIfVptCAPoolAvailBwEntry OBJECT-TYPE
   SYNTAX     AtmIfVptCAPoolAvailBwEntry
   ACCESS     not-accessible
   STATUS     mandatory
   DESCRIPTION
     "An entry in the atmIfVptCAPoolAvailBwTable."
   INDEX {
      atmIfIndex,
      atmIfVptIndex,
      atmIfVptCAIndex,
      atmIfVptCAPoolAvailBwIndex }
::= { atmIfVptCAPoolAvailBwTable 1 }

AtmIfVptCAPoolAvailBwEntry ::= SEQUENCE {
   atmIfVptCAPoolAvailBwIndex
      Integer32,
   atmIfVptCAPoolAvailBwValue
      INTEGER }

atmIfVptCAPoolAvailBwIndex OBJECT-TYPE
   SYNTAX     Integer32 (1..5)
   ACCESS     not-accessible
   STATUS     mandatory
   DESCRIPTION
     "This variable represents the atmIfVptCAPoolAvailBwTable
      specific index for the atmIfVptCAPoolAvailBwTable."
::= { atmIfVptCAPoolAvailBwEntry 1 }

atmIfVptCAPoolAvailBwValue OBJECT-TYPE
   SYNTAX     INTEGER (0..2147483647)
   ACCESS     read-only
   STATUS     mandatory
   DESCRIPTION
     "This variable represents an individual value for the
      atmIfVptCAPoolAvailBwTable."
::= { atmIfVptCAPoolAvailBwEntry 2 }

atmIfVptCABwPoolTable OBJECT-TYPE
   SYNTAX     SEQUENCE OF AtmIfVptCABwPoolEntry
   ACCESS     not-accessible
   STATUS     mandatory
   DESCRIPTION
     "Total bandwidth capacity is partitioned into five bandwidth pools. 
      This attribute specifies the percentage of Vpt bandwidth that is 
      allowed for each pool. The percentage for each pool ranges from 
      0% to 12,800%. This allows for both under and over subscription of 
      the VPT bandwidth. Under subscription occurs when the sum of the 
      percentages assigned to the five pools is less than 100%. Over 
      subscription occurs when the sum of the percentages for the five 
      pools exceeds 100%."
::= { atmIfVptCA 461 }

atmIfVptCABwPoolEntry OBJECT-TYPE
   SYNTAX     AtmIfVptCABwPoolEntry
   ACCESS     not-accessible
   STATUS     mandatory
   DESCRIPTION
     "An entry in the atmIfVptCABwPoolTable."
   INDEX {
      atmIfIndex,
      atmIfVptIndex,
      atmIfVptCAIndex,
      atmIfVptCABwPoolIndex }
::= { atmIfVptCABwPoolTable 1 }

AtmIfVptCABwPoolEntry ::= SEQUENCE {
   atmIfVptCABwPoolIndex
      Integer32,
   atmIfVptCABwPoolValue
      Unsigned32 }

atmIfVptCABwPoolIndex OBJECT-TYPE
   SYNTAX     Integer32 (1..5)
   ACCESS     not-accessible
   STATUS     mandatory
   DESCRIPTION
     "This variable represents the atmIfVptCABwPoolTable
      specific index for the atmIfVptCABwPoolTable."
::= { atmIfVptCABwPoolEntry 1 }

atmIfVptCABwPoolValue OBJECT-TYPE
   SYNTAX     Unsigned32 (0..12800)
   ACCESS     read-write
   STATUS     mandatory
   DESCRIPTION
     "This variable represents an individual value for the
      atmIfVptCABwPoolTable."
::= { atmIfVptCABwPoolEntry 2 }

atmIfVptCAPoolProvBwTable OBJECT-TYPE
   SYNTAX     SEQUENCE OF AtmIfVptCAPoolProvBwEntry
   ACCESS     not-accessible
   STATUS     mandatory
   DESCRIPTION
     "This attribute indicates the total provisioned bandwidth from the 
      corresponding bandwidthPool. Its value is the sum of the equivalent 
      cell rates (ECR) of the provisioned connections."
::= { atmIfVptCA 462 }

atmIfVptCAPoolProvBwEntry OBJECT-TYPE
   SYNTAX     AtmIfVptCAPoolProvBwEntry
   ACCESS     not-accessible
   STATUS     mandatory
   DESCRIPTION
     "An entry in the atmIfVptCAPoolProvBwTable."
   INDEX {
      atmIfIndex,
      atmIfVptIndex,
      atmIfVptCAIndex,
      atmIfVptCAPoolProvBwIndex }
::= { atmIfVptCAPoolProvBwTable 1 }

AtmIfVptCAPoolProvBwEntry ::= SEQUENCE {
   atmIfVptCAPoolProvBwIndex
      Integer32,
   atmIfVptCAPoolProvBwValue
      Gauge32 }

atmIfVptCAPoolProvBwIndex OBJECT-TYPE
   SYNTAX     Integer32 (1..5)
   ACCESS     not-accessible
   STATUS     mandatory
   DESCRIPTION
     "This variable represents the atmIfVptCAPoolProvBwTable
      specific index for the atmIfVptCAPoolProvBwTable."
::= { atmIfVptCAPoolProvBwEntry 1 }

atmIfVptCAPoolProvBwValue OBJECT-TYPE
   SYNTAX     Gauge32 (0..2147483647)
   ACCESS     read-only
   STATUS     mandatory
   DESCRIPTION
     "This variable represents an individual value for the
      atmIfVptCAPoolProvBwTable."
::= { atmIfVptCAPoolProvBwEntry 2 }

atmIfVptCAPoolRequBwTable OBJECT-TYPE
   SYNTAX     SEQUENCE OF AtmIfVptCAPoolRequBwEntry
   ACCESS     not-accessible
   STATUS     mandatory
   DESCRIPTION
     "This attribute indicates the total requested bandwidth from the 
      corresponding bandwidthPool. Its value is the sum of the equivalent 
      cell rates (ECR) for connections which are admitted and 
      connections which are requesting admission, but have not yet been 
      admitted."
::= { atmIfVptCA 463 }

atmIfVptCAPoolRequBwEntry OBJECT-TYPE
   SYNTAX     AtmIfVptCAPoolRequBwEntry
   ACCESS     not-accessible
   STATUS     mandatory
   DESCRIPTION
     "An entry in the atmIfVptCAPoolRequBwTable."
   INDEX {
      atmIfIndex,
      atmIfVptIndex,
      atmIfVptCAIndex,
      atmIfVptCAPoolRequBwIndex }
::= { atmIfVptCAPoolRequBwTable 1 }

AtmIfVptCAPoolRequBwEntry ::= SEQUENCE {
   atmIfVptCAPoolRequBwIndex
      Integer32,
   atmIfVptCAPoolRequBwValue
      Gauge32 }

atmIfVptCAPoolRequBwIndex OBJECT-TYPE
   SYNTAX     Integer32 (1..5)
   ACCESS     not-accessible
   STATUS     mandatory
   DESCRIPTION
     "This variable represents the atmIfVptCAPoolRequBwTable
      specific index for the atmIfVptCAPoolRequBwTable."
::= { atmIfVptCAPoolRequBwEntry 1 }

atmIfVptCAPoolRequBwValue OBJECT-TYPE
   SYNTAX     Gauge32 (0..2147483647)
   ACCESS     read-only
   STATUS     mandatory
   DESCRIPTION
     "This variable represents an individual value for the
      atmIfVptCAPoolRequBwTable."
::= { atmIfVptCAPoolRequBwEntry 2 }

atmIfVptCAPoolAdmitBwTable OBJECT-TYPE
   SYNTAX     SEQUENCE OF AtmIfVptCAPoolAdmitBwEntry
   ACCESS     not-accessible
   STATUS     mandatory
   DESCRIPTION
     "This attribute indicates the total admitted bandwidth in the 
      corresponding bandwidthPool. Its value is the sum of the equivalent 
      cell rates (ECR) of the admitted connections."
::= { atmIfVptCA 464 }

atmIfVptCAPoolAdmitBwEntry OBJECT-TYPE
   SYNTAX     AtmIfVptCAPoolAdmitBwEntry
   ACCESS     not-accessible
   STATUS     mandatory
   DESCRIPTION
     "An entry in the atmIfVptCAPoolAdmitBwTable."
   INDEX {
      atmIfIndex,
      atmIfVptIndex,
      atmIfVptCAIndex,
      atmIfVptCAPoolAdmitBwIndex }
::= { atmIfVptCAPoolAdmitBwTable 1 }

AtmIfVptCAPoolAdmitBwEntry ::= SEQUENCE {
   atmIfVptCAPoolAdmitBwIndex
      Integer32,
   atmIfVptCAPoolAdmitBwValue
      Gauge32 }

atmIfVptCAPoolAdmitBwIndex OBJECT-TYPE
   SYNTAX     Integer32 (1..5)
   ACCESS     not-accessible
   STATUS     mandatory
   DESCRIPTION
     "This variable represents the atmIfVptCAPoolAdmitBwTable
      specific index for the atmIfVptCAPoolAdmitBwTable."
::= { atmIfVptCAPoolAdmitBwEntry 1 }

atmIfVptCAPoolAdmitBwValue OBJECT-TYPE
   SYNTAX     Gauge32 (0..2147483647)
   ACCESS     read-only
   STATUS     mandatory
   DESCRIPTION
     "This variable represents an individual value for the
      atmIfVptCAPoolAdmitBwTable."
::= { atmIfVptCAPoolAdmitBwEntry 2 }

atmIfVptCAPoolAdmConnsTable OBJECT-TYPE
   SYNTAX     SEQUENCE OF AtmIfVptCAPoolAdmConnsEntry
   ACCESS     not-accessible
   STATUS     mandatory
   DESCRIPTION
     "This attribute indicates the total number of connections which are 
      currently admitted in the corresponding bandwidthPool."
::= { atmIfVptCA 465 }

atmIfVptCAPoolAdmConnsEntry OBJECT-TYPE
   SYNTAX     AtmIfVptCAPoolAdmConnsEntry
   ACCESS     not-accessible
   STATUS     mandatory
   DESCRIPTION
     "An entry in the atmIfVptCAPoolAdmConnsTable."
   INDEX {
      atmIfIndex,
      atmIfVptIndex,
      atmIfVptCAIndex,
      atmIfVptCAPoolAdmConnsIndex }
::= { atmIfVptCAPoolAdmConnsTable 1 }

AtmIfVptCAPoolAdmConnsEntry ::= SEQUENCE {
   atmIfVptCAPoolAdmConnsIndex
      Integer32,
   atmIfVptCAPoolAdmConnsValue
      Gauge32 }

atmIfVptCAPoolAdmConnsIndex OBJECT-TYPE
   SYNTAX     Integer32 (1..5)
   ACCESS     not-accessible
   STATUS     mandatory
   DESCRIPTION
     "This variable represents the atmIfVptCAPoolAdmConnsTable
      specific index for the atmIfVptCAPoolAdmConnsTable."
::= { atmIfVptCAPoolAdmConnsEntry 1 }

atmIfVptCAPoolAdmConnsValue OBJECT-TYPE
   SYNTAX     Gauge32 (0..16384)
   ACCESS     read-only
   STATUS     mandatory
   DESCRIPTION
     "This variable represents an individual value for the
      atmIfVptCAPoolAdmConnsTable."
::= { atmIfVptCAPoolAdmConnsEntry 2 }

atmIfVptCAPoolWaitAdmConnsTable OBJECT-TYPE
   SYNTAX     SEQUENCE OF AtmIfVptCAPoolWaitAdmConnsEntry
   ACCESS     not-accessible
   STATUS     mandatory
   DESCRIPTION
     "This attribute indicates the total number of connections which have 
      currently requested admission in the corresponding bandwidthPool 
      but are not yet admitted."
::= { atmIfVptCA 466 }

atmIfVptCAPoolWaitAdmConnsEntry OBJECT-TYPE
   SYNTAX     AtmIfVptCAPoolWaitAdmConnsEntry
   ACCESS     not-accessible
   STATUS     mandatory
   DESCRIPTION
     "An entry in the atmIfVptCAPoolWaitAdmConnsTable."
   INDEX {
      atmIfIndex,
      atmIfVptIndex,
      atmIfVptCAIndex,
      atmIfVptCAPoolWaitAdmConnsIndex }
::= { atmIfVptCAPoolWaitAdmConnsTable 1 }

AtmIfVptCAPoolWaitAdmConnsEntry ::= SEQUENCE {
   atmIfVptCAPoolWaitAdmConnsIndex
      Integer32,
   atmIfVptCAPoolWaitAdmConnsValue
      Gauge32 }

atmIfVptCAPoolWaitAdmConnsIndex OBJECT-TYPE
   SYNTAX     Integer32 (1..5)
   ACCESS     not-accessible
   STATUS     mandatory
   DESCRIPTION
     "This variable represents the atmIfVptCAPoolWaitAdmConnsTable
      specific index for the atmIfVptCAPoolWaitAdmConnsTable."
::= { atmIfVptCAPoolWaitAdmConnsEntry 1 }

atmIfVptCAPoolWaitAdmConnsValue OBJECT-TYPE
   SYNTAX     Gauge32 (0..16384)
   ACCESS     read-only
   STATUS     mandatory
   DESCRIPTION
     "This variable represents an individual value for the
      atmIfVptCAPoolWaitAdmConnsTable."
::= { atmIfVptCAPoolWaitAdmConnsEntry 2 }


-- AtmIf/n Vpt/n CA ConstantBitRate/n 
-- This component controls default characteristics of the constant bit 
-- rate (CBR) service category, for Vccs administered by this CA. Any 
-- attributes of the AtmIf CA Cbr that cannot be overridden in the Vpt 
-- CA Cbr affect all connections, including Vpt Vccs.

atmIfVptCACbr OBJECT IDENTIFIER ::= { atmIfVptCA 2 }



atmIfVptCACbrRowStatusTable OBJECT-TYPE
   SYNTAX     SEQUENCE OF AtmIfVptCACbrRowStatusEntry
   ACCESS     not-accessible
   STATUS     mandatory
   DESCRIPTION
     "This entry controls the addition and deletion of 
      atmIfVptCACbr components."
::= { atmIfVptCACbr 1 }

atmIfVptCACbrRowStatusEntry OBJECT-TYPE
   SYNTAX     AtmIfVptCACbrRowStatusEntry
   ACCESS     not-accessible
   STATUS     mandatory
   DESCRIPTION
     "A single entry in the table represents a single 
      atmIfVptCACbr component."
   INDEX {
      atmIfIndex,
      atmIfVptIndex,
      atmIfVptCAIndex,
      atmIfVptCACbrIndex }
::= { atmIfVptCACbrRowStatusTable 1 }

AtmIfVptCACbrRowStatusEntry ::= SEQUENCE {
   atmIfVptCACbrRowStatus
      RowStatus,
   atmIfVptCACbrComponentName
      DisplayString,
   atmIfVptCACbrStorageType
      StorageType,
   atmIfVptCACbrIndex
      Integer32 }

atmIfVptCACbrRowStatus OBJECT-TYPE
   SYNTAX     RowStatus 
   ACCESS     read-write
   STATUS     mandatory
   DESCRIPTION
     "This variable is used as the basis for SNMP naming of
      atmIfVptCACbr components.
      These components can be added."
::= { atmIfVptCACbrRowStatusEntry 1 }

atmIfVptCACbrComponentName OBJECT-TYPE
   SYNTAX     DisplayString 
   ACCESS     read-only
   STATUS     mandatory
   DESCRIPTION
     "This variable provides the component's string name for
      use with the ASCII Console Interface"
::= { atmIfVptCACbrRowStatusEntry 2 }

atmIfVptCACbrStorageType OBJECT-TYPE
   SYNTAX     StorageType 
   ACCESS     read-only
   STATUS     mandatory
   DESCRIPTION
     "This variable represents the storage type value for the
      atmIfVptCACbr tables."
::= { atmIfVptCACbrRowStatusEntry 4 }

atmIfVptCACbrIndex OBJECT-TYPE
   SYNTAX     Integer32 (0)
   ACCESS     not-accessible
   STATUS     mandatory
   DESCRIPTION
     "This variable represents the index for the atmIfVptCACbr tables."
::= { atmIfVptCACbrRowStatusEntry 10 }

atmIfVptCACbrProvTable OBJECT-TYPE
   SYNTAX     SEQUENCE OF AtmIfVptCACbrProvEntry
   ACCESS     not-accessible
   STATUS     mandatory
   DESCRIPTION
     "This group contains provisioned attributes which control 
      Connection Admission Control (CAC) and Usage Parameter 
      Control (UPC) attributes for the CBR ATM connections managed 
      by this Vpt. Any attributes of the AtmIf CA Cbr that cannot be 
      overridden in the Vpt CA Cbr affect all connections, including Vpt 
      Vccs."
::= { atmIfVptCACbr 100 }

atmIfVptCACbrProvEntry OBJECT-TYPE
   SYNTAX     AtmIfVptCACbrProvEntry
   ACCESS     not-accessible
   STATUS     mandatory
   DESCRIPTION
     "An entry in the atmIfVptCACbrProvTable."
   INDEX {
      atmIfIndex,
      atmIfVptIndex,
      atmIfVptCAIndex,
      atmIfVptCACbrIndex }
::= { atmIfVptCACbrProvTable 1 }

AtmIfVptCACbrProvEntry ::= SEQUENCE {
   atmIfVptCACbrPool
      INTEGER,
   atmIfVptCACbrCdvt
      Unsigned32,
   atmIfVptCACbrCdv
      Unsigned32,
   atmIfVptCACbrMaxCtd
      Unsigned32,
   atmIfVptCACbrCellLossRatio
      Unsigned32 }

atmIfVptCACbrPool OBJECT-TYPE
   SYNTAX     INTEGER  {
                 pool1(1),
                 pool2(2),
                 pool3(3),
                 pool4(4),
                 pool5(5) }
   ACCESS     read-write
   STATUS     mandatory
   DESCRIPTION
     "This attribute specifies the bandwidth pool which is to be used to 
      support the constant bit rate (CBR) service category. The percentage 
      of Vpt bandwidth capacity reserved for the given bandwidth pool is 
      the maximum bandwidth that can be allocated to CBR traffic. The 
      percentage allocated to each bandwidth pool can be provisioned 
      through the bandwidthPool attribute under the CA."
   DEFVAL     { pool1 }
::= { atmIfVptCACbrProvEntry 10 }

atmIfVptCACbrCdvt OBJECT-TYPE
   SYNTAX     Unsigned32 (1..10000)
   ACCESS     read-write
   STATUS     mandatory
   DESCRIPTION
     "This attribute specifies the default cell delay variation tolerance 
      (CDVT) for connections of the CBR service category. An override 
      to this default may be specified for a provisioned connection under 
      the Vcd Tm or Vpd Tm component.
      
      This attribute is used by the CAC function to compute the 
      equivalent cell rate (ECR) required by a given CBR connection. The 
      larger the value of CDVT, the larger is its ECR. 
      
      If Usage Parameter Control (UPC) is enabled for a connection, 
      CDVT is used by the UPC function on the ingress to decide whether 
      a cell is conforming or non-conforming based on the connection's 
      traffic descriptor type. The larger the CDVT value, the more tolerant 
      is the UPC of bandwidth usage beyond the traffic contract."
   DEFVAL     { 250 }
::= { atmIfVptCACbrProvEntry 20 }

atmIfVptCACbrCdv OBJECT-TYPE
   SYNTAX     Unsigned32 (0..2147483647)
   ACCESS     read-write
   STATUS     mandatory
   DESCRIPTION
     "This attribute specifies the peak-to-peak cell delay variation (CDV) 
      which is contributed to connections associated with this Vpt for 
      CBR traffic. 
      
      The CDV is a measure of the delay jitter introduced mostly by 
      traffic buffering and cell scheduling. 
      
      The value of this attribute is used by PNNI in the Resource 
      Availability Information Group (RAIG) topology updates and route 
      selection. It is also used by CAC at connection set-up time to 
      determine whether this Vpt can meet the ATM connection's CDV 
      requirement. If so, the value of this attribute is added to the 
      cumulative CDV field of the extended QoS information element."
   DEFVAL     { 250 }
::= { atmIfVptCACbrProvEntry 30 }

atmIfVptCACbrMaxCtd OBJECT-TYPE
   SYNTAX     Unsigned32 (0..2147483647)
   ACCESS     read-write
   STATUS     mandatory
   DESCRIPTION
     "This attribute specifies the maximum cell transfer delay (MaxCTD) 
      which is applied to all connections associated with this Vpt for CBR 
      traffic.
      
      MaxCTD is the sum of the fixed delay and the CDV. The 
      components of the fixed delay include propagation delay through 
      the physical media, delays induced by the transmission system, and 
      fixed components of switch processing delay. 
      
      This attribute is used by PNNI in the Resource Availability 
      Information Group (RAIG) topology updates and route selection. It 
      is also used by CAC at connection set-up time to determine whether 
      this Vpt can meet the ATM connection's MaxCTD requirement."
   DEFVAL     { 1000 }
::= { atmIfVptCACbrProvEntry 40 }

atmIfVptCACbrCellLossRatio OBJECT-TYPE
   SYNTAX     Unsigned32 (0..15)
   ACCESS     read-write
   STATUS     mandatory
   DESCRIPTION
     "This attribute specifies the tolerable cell loss ratio (CLR) for CBR 
      traffic. The number is the negative logarithm (base 10) of the CLR. 
      For example, if the target CLR = 1E-10 then Cbr cellLossRatio = 
      10. This number must be the same as the RtVbr cellLossRatio since 
      CBR and rt-VBR traffic have the same discard priority. The Cbr 
      cellLossRatio is used by the Connection Admission Control (CAC) 
      algorithm to compute the required (equivalent) cell rate for CBR 
      connections. 
      
      There is a trade-off between the service category CLR and the 
      achievable Vpt bandwidth utilization. To guarantee an excellent 
      service category, the CLR should be as small as possible (e.g., 1E-
      10). However, a smaller CLR results in a larger equivalent cell rate 
      for a given connection and hence a lower Vpt bandwidth utilization.
      
      Setting this attribute to 0 means that a CLR of 1 can be tolerated. In 
      this case, no bandwidth is reserved for CBR connections, and CAC 
      is effectively turned off. All CBR connections are admitted."
   DEFVAL     { 10 }
::= { atmIfVptCACbrProvEntry 50 }


-- AtmIf/n Vpt/n CA RealTimeVariableBitRate/n 
-- This component controls default characteristics of the real-time 
-- variable bit rate (rt-VBR) service category, for Vccs administered by 
-- this CA. Any attributes of the AtmIf CA RtVbr that cannot be 
-- overridden in the Vpt CA RtVbr affect all connections, including Vpt 
-- Vccs.

atmIfVptCARtVbr OBJECT IDENTIFIER ::= { atmIfVptCA 3 }



atmIfVptCARtVbrRowStatusTable OBJECT-TYPE
   SYNTAX     SEQUENCE OF AtmIfVptCARtVbrRowStatusEntry
   ACCESS     not-accessible
   STATUS     mandatory
   DESCRIPTION
     "This entry controls the addition and deletion of 
      atmIfVptCARtVbr components."
::= { atmIfVptCARtVbr 1 }

atmIfVptCARtVbrRowStatusEntry OBJECT-TYPE
   SYNTAX     AtmIfVptCARtVbrRowStatusEntry
   ACCESS     not-accessible
   STATUS     mandatory
   DESCRIPTION
     "A single entry in the table represents a single 
      atmIfVptCARtVbr component."
   INDEX {
      atmIfIndex,
      atmIfVptIndex,
      atmIfVptCAIndex,
      atmIfVptCARtVbrIndex }
::= { atmIfVptCARtVbrRowStatusTable 1 }

AtmIfVptCARtVbrRowStatusEntry ::= SEQUENCE {
   atmIfVptCARtVbrRowStatus
      RowStatus,
   atmIfVptCARtVbrComponentName
      DisplayString,
   atmIfVptCARtVbrStorageType
      StorageType,
   atmIfVptCARtVbrIndex
      Integer32 }

atmIfVptCARtVbrRowStatus OBJECT-TYPE
   SYNTAX     RowStatus 
   ACCESS     read-write
   STATUS     mandatory
   DESCRIPTION
     "This variable is used as the basis for SNMP naming of
      atmIfVptCARtVbr components.
      These components can be added."
::= { atmIfVptCARtVbrRowStatusEntry 1 }

atmIfVptCARtVbrComponentName OBJECT-TYPE
   SYNTAX     DisplayString 
   ACCESS     read-only
   STATUS     mandatory
   DESCRIPTION
     "This variable provides the component's string name for
      use with the ASCII Console Interface"
::= { atmIfVptCARtVbrRowStatusEntry 2 }

atmIfVptCARtVbrStorageType OBJECT-TYPE
   SYNTAX     StorageType 
   ACCESS     read-only
   STATUS     mandatory
   DESCRIPTION
     "This variable represents the storage type value for the
      atmIfVptCARtVbr tables."
::= { atmIfVptCARtVbrRowStatusEntry 4 }

atmIfVptCARtVbrIndex OBJECT-TYPE
   SYNTAX     Integer32 (0)
   ACCESS     not-accessible
   STATUS     mandatory
   DESCRIPTION
     "This variable represents the index for the atmIfVptCARtVbr tables."
::= { atmIfVptCARtVbrRowStatusEntry 10 }

atmIfVptCARtVbrProvTable OBJECT-TYPE
   SYNTAX     SEQUENCE OF AtmIfVptCARtVbrProvEntry
   ACCESS     not-accessible
   STATUS     mandatory
   DESCRIPTION
     "This group contains provisioned attributes which control 
      Connection Admission Control (CAC) and UPC attributes for the rt-
      VBR ATM connections associated with this Vpt. Any attributes of 
      the AtmIf CA RtVbr that cannot be overridden in the Vpt CA RtVbr 
      affect all connections, including Vpt Vccs."
::= { atmIfVptCARtVbr 100 }

atmIfVptCARtVbrProvEntry OBJECT-TYPE
   SYNTAX     AtmIfVptCARtVbrProvEntry
   ACCESS     not-accessible
   STATUS     mandatory
   DESCRIPTION
     "An entry in the atmIfVptCARtVbrProvTable."
   INDEX {
      atmIfIndex,
      atmIfVptIndex,
      atmIfVptCAIndex,
      atmIfVptCARtVbrIndex }
::= { atmIfVptCARtVbrProvTable 1 }

AtmIfVptCARtVbrProvEntry ::= SEQUENCE {
   atmIfVptCARtVbrPool
      INTEGER,
   atmIfVptCARtVbrCdv
      Unsigned32,
   atmIfVptCARtVbrMaxCtd
      Unsigned32,
   atmIfVptCARtVbrCellLossRatio
      Unsigned32 }

atmIfVptCARtVbrPool OBJECT-TYPE
   SYNTAX     INTEGER  {
                 pool1(1),
                 pool2(2),
                 pool3(3),
                 pool4(4),
                 pool5(5) }
   ACCESS     read-write
   STATUS     mandatory
   DESCRIPTION
     "This attribute specifies the bandwidth pool which is to be used to 
      support the real-time variable bit rate (rt-VBR) service category. 
      The percentage of Vpt capacity reserved for the given bandwidth 
      pool is the maximum bandwidth that can be allocated to rt-VBR 
      traffic. The percentage allocated to each bandwidth pool can be 
      provisioned through the bandwidthPool attribute under the Vpt CA."
   DEFVAL     { pool1 }
::= { atmIfVptCARtVbrProvEntry 10 }

atmIfVptCARtVbrCdv OBJECT-TYPE
   SYNTAX     Unsigned32 (0..2147483647)
   ACCESS     read-write
   STATUS     mandatory
   DESCRIPTION
     "This attribute specifies the peak-to-peak cell delay variation (CDV) 
      which is contributed to all rt-VBR connections associated with this 
      Vpt. 
      
      The CDV is a measure of the delay jitter introduced mostly by 
      traffic buffering and cell scheduling.
      
      The value of this attribute is used by PNNI in the Resource 
      Availability Information Group (RAIG) topology updates and route 
      selection. It is also used by CAC at connection set-up time to 
      determine whether this Vpt can meet the CDV requirement for that 
      connection. If so, the value of this attribute is added to the 
      cumulative CDV field of the extended QoS information element."
   DEFVAL     { 1268 }
::= { atmIfVptCARtVbrProvEntry 30 }

atmIfVptCARtVbrMaxCtd OBJECT-TYPE
   SYNTAX     Unsigned32 (0..2147483647)
   ACCESS     read-write
   STATUS     mandatory
   DESCRIPTION
     "This attribute specifies the maximum cell transfer delay (MaxCTD) 
      which is applied to all rt-VBR connections associated with this Vpt.
      
      MaxCTD is the sum of the fixed delay and the CDV. The 
      components of the fixed delay include propagation delay through 
      the physical media, delays induced by the transmission system, and 
      fixed components of switch processing delay.
      
      This attribute is used by PNNI in the Resource Availability 
      Information Group (RAIG) topology updates and route selection. It 
      is also used by CAC at connection set-up time to determine whether 
      this Vpt can meet the ATM connection's MaxCTD requirement."
   DEFVAL     { 2000 }
::= { atmIfVptCARtVbrProvEntry 40 }

atmIfVptCARtVbrCellLossRatio OBJECT-TYPE
   SYNTAX     Unsigned32 (0..15)
   ACCESS     read-write
   STATUS     mandatory
   DESCRIPTION
     "This attribute specifies the tolerable cell loss ratio (CLR) for rt-
      VBR traffic. The number is the negative logarithm (base 10) of the 
      CLR. For example, if the target CLR = 1E-10 then RtVbr 
      cellLossRatio = 10. This number must be the same as the Cbr 
      cellLossRatio since CBR and rt-VBR traffic have the same discard 
      priority. The RtVbr cellLossRatio is used by the Connection 
      Admission Control (CAC) algorithm to compute the required 
      (equivalent) cell rate for rt-VBR connections. This number must be 
      less than or equal to the NrtVbr cellLossRatio, since rt-VBR traffic 
      has a higher discard priority.
      
      There is a trade-off between the service category CLR and the 
      achievable Vpt bandwidth utilization. To guarantee an excellent 
      service category, the CLR should be as small as possible (e.g., 1E-
      10). However, a smaller CLR results in a larger equivalent cell rate 
      for a given connection and hence a lower Vpt bandwidth utilization. 
      
      Setting this attribute to 0 means that a CLR of 1 can be tolerated. In 
      this case, no bandwidth is reserved for rt-VBR connections and 
      CAC is effectively turned off. All rt-VBR connections are admitted."
   DEFVAL     { 10 }
::= { atmIfVptCARtVbrProvEntry 50 }


-- AtmIf/n Vpt/n CA NonRealTimeVariableBitRate/n 
-- This component controls default characteristics of the non-real-time 
-- variable bit rate (nrt-VBR) service category, for Vccs administered 
-- by this CA. Any attributes of the AtmIf CA NrtVbr that cannot be 
-- overridden in the Vpt CA NrtVbr affect all connections, including 
-- Vpt Vccs.

atmIfVptCANrtVbr OBJECT IDENTIFIER ::= { atmIfVptCA 4 }



atmIfVptCANrtVbrRowStatusTable OBJECT-TYPE
   SYNTAX     SEQUENCE OF AtmIfVptCANrtVbrRowStatusEntry
   ACCESS     not-accessible
   STATUS     mandatory
   DESCRIPTION
     "This entry controls the addition and deletion of 
      atmIfVptCANrtVbr components."
::= { atmIfVptCANrtVbr 1 }

atmIfVptCANrtVbrRowStatusEntry OBJECT-TYPE
   SYNTAX     AtmIfVptCANrtVbrRowStatusEntry
   ACCESS     not-accessible
   STATUS     mandatory
   DESCRIPTION
     "A single entry in the table represents a single 
      atmIfVptCANrtVbr component."
   INDEX {
      atmIfIndex,
      atmIfVptIndex,
      atmIfVptCAIndex,
      atmIfVptCANrtVbrIndex }
::= { atmIfVptCANrtVbrRowStatusTable 1 }

AtmIfVptCANrtVbrRowStatusEntry ::= SEQUENCE {
   atmIfVptCANrtVbrRowStatus
      RowStatus,
   atmIfVptCANrtVbrComponentName
      DisplayString,
   atmIfVptCANrtVbrStorageType
      StorageType,
   atmIfVptCANrtVbrIndex
      Integer32 }

atmIfVptCANrtVbrRowStatus OBJECT-TYPE
   SYNTAX     RowStatus 
   ACCESS     read-write
   STATUS     mandatory
   DESCRIPTION
     "This variable is used as the basis for SNMP naming of
      atmIfVptCANrtVbr components.
      These components can be added."
::= { atmIfVptCANrtVbrRowStatusEntry 1 }

atmIfVptCANrtVbrComponentName OBJECT-TYPE
   SYNTAX     DisplayString 
   ACCESS     read-only
   STATUS     mandatory
   DESCRIPTION
     "This variable provides the component's string name for
      use with the ASCII Console Interface"
::= { atmIfVptCANrtVbrRowStatusEntry 2 }

atmIfVptCANrtVbrStorageType OBJECT-TYPE
   SYNTAX     StorageType 
   ACCESS     read-only
   STATUS     mandatory
   DESCRIPTION
     "This variable represents the storage type value for the
      atmIfVptCANrtVbr tables."
::= { atmIfVptCANrtVbrRowStatusEntry 4 }

atmIfVptCANrtVbrIndex OBJECT-TYPE
   SYNTAX     Integer32 (0)
   ACCESS     not-accessible
   STATUS     mandatory
   DESCRIPTION
     "This variable represents the index for the atmIfVptCANrtVbr tables."
::= { atmIfVptCANrtVbrRowStatusEntry 10 }

atmIfVptCANrtVbrProvTable OBJECT-TYPE
   SYNTAX     SEQUENCE OF AtmIfVptCANrtVbrProvEntry
   ACCESS     not-accessible
   STATUS     mandatory
   DESCRIPTION
     "This group contains provisioned attributes which control 
      Connection Admission Control (CAC) and UPC attributes for the 
      nrt-VBR ATM connections associated with this Vpt. Any attributes 
      of the AtmIf CA NrtVbr that cannot be overridden in the Vpt CA 
      NrtVbr affect all connections, including Vpt Vccs."
::= { atmIfVptCANrtVbr 100 }

atmIfVptCANrtVbrProvEntry OBJECT-TYPE
   SYNTAX     AtmIfVptCANrtVbrProvEntry
   ACCESS     not-accessible
   STATUS     mandatory
   DESCRIPTION
     "An entry in the atmIfVptCANrtVbrProvTable."
   INDEX {
      atmIfIndex,
      atmIfVptIndex,
      atmIfVptCAIndex,
      atmIfVptCANrtVbrIndex }
::= { atmIfVptCANrtVbrProvTable 1 }

AtmIfVptCANrtVbrProvEntry ::= SEQUENCE {
   atmIfVptCANrtVbrPool
      INTEGER,
   atmIfVptCANrtVbrCellLossRatio
      Unsigned32 }

atmIfVptCANrtVbrPool OBJECT-TYPE
   SYNTAX     INTEGER  {
                 pool1(1),
                 pool2(2),
                 pool3(3),
                 pool4(4),
                 pool5(5) }
   ACCESS     read-write
   STATUS     mandatory
   DESCRIPTION
     "This attribute specifies the bandwidth pool which is to be used to 
      support the non-real time variable bit rate (nrt-VBR) service 
      category. The percentage of Vpt bandwidth capacity reserved for the 
      given bandwidth pool is the maximum bandwidth that can be 
      allocated to nrt-VBR traffic. The percentage allocated to each 
      bandwidth pool can be provisioned through the bandwidthPool 
      attribute under the CA."
   DEFVAL     { pool1 }
::= { atmIfVptCANrtVbrProvEntry 1 }

atmIfVptCANrtVbrCellLossRatio OBJECT-TYPE
   SYNTAX     Unsigned32 (0..15)
   ACCESS     read-write
   STATUS     mandatory
   DESCRIPTION
     "This attribute specifies the tolerable cell loss ratio (CLR) for nrt-
      VBR traffic. The number is the negative logarithm (base 10) of the 
      CLR. In other words if the target CLR = 1E-10 then NrtVbr 
      cellLossRatio = 10. This number must be greater than or equal to 
      RtVbr cellLossRatio since rt-VBR traffic has a higher discard 
      priority. The NrtVbr cellLossRatio is used by the Connection 
      Admission Control (CAC) algorithm to compute the required 
      (equivalent) cell rate for nrt-VBR connections. 
      
      There is a trade-off between the service category CLR and the 
      achievable Vpt bandwidth utilization. To guarantee an excellent 
      service category, the CLR should be as small as possible (e.g., 1E-
      10). However, a smaller CLR results in a larger equivalent cell rate 
      for a given connection and hence a lower Vpt bandwidth utilization. 
      
      Setting this attribute to 0 means that a CLR of 1 can be tolerated. In 
      this case, no bandwidth is reserved for nrt-VBR connections, and 
      CAC is effectively turned off. All nrt-VBR connections are 
      admitted."
   DEFVAL     { 7 }
::= { atmIfVptCANrtVbrProvEntry 3 }


-- AtmIf/n Vpt/n CA AvailableBitRate/n 
-- This component controls default characteristics of the available bit 
-- rate (ABR) service category, for Vccs administered by this CA. Any 
-- attributes of the AtmIf CA Abr that cannot be overridden in the Vpt 
-- CA Abr affect all connections, including Vpt Vccs.

atmIfVptCAAbr OBJECT IDENTIFIER ::= { atmIfVptCA 5 }



atmIfVptCAAbrRowStatusTable OBJECT-TYPE
   SYNTAX     SEQUENCE OF AtmIfVptCAAbrRowStatusEntry
   ACCESS     not-accessible
   STATUS     mandatory
   DESCRIPTION
     "This entry controls the addition and deletion of 
      atmIfVptCAAbr components."
::= { atmIfVptCAAbr 1 }

atmIfVptCAAbrRowStatusEntry OBJECT-TYPE
   SYNTAX     AtmIfVptCAAbrRowStatusEntry
   ACCESS     not-accessible
   STATUS     mandatory
   DESCRIPTION
     "A single entry in the table represents a single 
      atmIfVptCAAbr component."
   INDEX {
      atmIfIndex,
      atmIfVptIndex,
      atmIfVptCAIndex,
      atmIfVptCAAbrIndex }
::= { atmIfVptCAAbrRowStatusTable 1 }

AtmIfVptCAAbrRowStatusEntry ::= SEQUENCE {
   atmIfVptCAAbrRowStatus
      RowStatus,
   atmIfVptCAAbrComponentName
      DisplayString,
   atmIfVptCAAbrStorageType
      StorageType,
   atmIfVptCAAbrIndex
      Integer32 }

atmIfVptCAAbrRowStatus OBJECT-TYPE
   SYNTAX     RowStatus 
   ACCESS     read-write
   STATUS     mandatory
   DESCRIPTION
     "This variable is used as the basis for SNMP naming of
      atmIfVptCAAbr components.
      These components can be added."
::= { atmIfVptCAAbrRowStatusEntry 1 }

atmIfVptCAAbrComponentName OBJECT-TYPE
   SYNTAX     DisplayString 
   ACCESS     read-only
   STATUS     mandatory
   DESCRIPTION
     "This variable provides the component's string name for
      use with the ASCII Console Interface"
::= { atmIfVptCAAbrRowStatusEntry 2 }

atmIfVptCAAbrStorageType OBJECT-TYPE
   SYNTAX     StorageType 
   ACCESS     read-only
   STATUS     mandatory
   DESCRIPTION
     "This variable represents the storage type value for the
      atmIfVptCAAbr tables."
::= { atmIfVptCAAbrRowStatusEntry 4 }

atmIfVptCAAbrIndex OBJECT-TYPE
   SYNTAX     Integer32 (0)
   ACCESS     not-accessible
   STATUS     mandatory
   DESCRIPTION
     "This variable represents the index for the atmIfVptCAAbr tables."
::= { atmIfVptCAAbrRowStatusEntry 10 }

atmIfVptCAAbrProvTable OBJECT-TYPE
   SYNTAX     SEQUENCE OF AtmIfVptCAAbrProvEntry
   ACCESS     not-accessible
   STATUS     mandatory
   DESCRIPTION
     "This group contains provisioned attributes which control 
      Connection Admission Control (CAC) attributes for ABR 
      connections associated with this Vpt. Any attributes of the AtmIf CA 
      Abr that cannot be overridden in the Vpt CA Abr affect all 
      connections, including Vpt Vccs."
::= { atmIfVptCAAbr 100 }

atmIfVptCAAbrProvEntry OBJECT-TYPE
   SYNTAX     AtmIfVptCAAbrProvEntry
   ACCESS     not-accessible
   STATUS     mandatory
   DESCRIPTION
     "An entry in the atmIfVptCAAbrProvTable."
   INDEX {
      atmIfIndex,
      atmIfVptIndex,
      atmIfVptCAIndex,
      atmIfVptCAAbrIndex }
::= { atmIfVptCAAbrProvTable 1 }

AtmIfVptCAAbrProvEntry ::= SEQUENCE {
   atmIfVptCAAbrPool
      INTEGER }

atmIfVptCAAbrPool OBJECT-TYPE
   SYNTAX     INTEGER  {
                 pool1(1),
                 pool2(2),
                 pool3(3),
                 pool4(4),
                 pool5(5) }
   ACCESS     read-write
   STATUS     mandatory
   DESCRIPTION
     "This attribute specifies the bandwidth pool which is to be used to 
      support the available bit rate (ABR) service category. The 
      percentage of Vpt bandwidth capacity reserved for the given 
      bandwidth pool is the maximum bandwidth that can be allocated to 
      ABR traffic. The percentage allocated to each bandwidth pool can 
      be provisioned through the bandwidthPool attribute under the CA."
   DEFVAL     { pool1 }
::= { atmIfVptCAAbrProvEntry 10 }


-- AtmIf/n Vpt/n CA UnspecifiedBitRate/n 
-- This component controls default characteristics of the unspecified 
-- bit rate (UBR) service category, for Vccs administered by this CA. 
-- Any attributes of the AtmIf CA Ubr that cannot be overridden in the 
-- Vpt CA Ubr affect all connections, including Vpt Vccs.

atmIfVptCAUbr OBJECT IDENTIFIER ::= { atmIfVptCA 6 }



atmIfVptCAUbrRowStatusTable OBJECT-TYPE
   SYNTAX     SEQUENCE OF AtmIfVptCAUbrRowStatusEntry
   ACCESS     not-accessible
   STATUS     mandatory
   DESCRIPTION
     "This entry controls the addition and deletion of 
      atmIfVptCAUbr components."
::= { atmIfVptCAUbr 1 }

atmIfVptCAUbrRowStatusEntry OBJECT-TYPE
   SYNTAX     AtmIfVptCAUbrRowStatusEntry
   ACCESS     not-accessible
   STATUS     mandatory
   DESCRIPTION
     "A single entry in the table represents a single 
      atmIfVptCAUbr component."
   INDEX {
      atmIfIndex,
      atmIfVptIndex,
      atmIfVptCAIndex,
      atmIfVptCAUbrIndex }
::= { atmIfVptCAUbrRowStatusTable 1 }

AtmIfVptCAUbrRowStatusEntry ::= SEQUENCE {
   atmIfVptCAUbrRowStatus
      RowStatus,
   atmIfVptCAUbrComponentName
      DisplayString,
   atmIfVptCAUbrStorageType
      StorageType,
   atmIfVptCAUbrIndex
      Integer32 }

atmIfVptCAUbrRowStatus OBJECT-TYPE
   SYNTAX     RowStatus 
   ACCESS     read-write
   STATUS     mandatory
   DESCRIPTION
     "This variable is used as the basis for SNMP naming of
      atmIfVptCAUbr components.
      These components can be added."
::= { atmIfVptCAUbrRowStatusEntry 1 }

atmIfVptCAUbrComponentName OBJECT-TYPE
   SYNTAX     DisplayString 
   ACCESS     read-only
   STATUS     mandatory
   DESCRIPTION
     "This variable provides the component's string name for
      use with the ASCII Console Interface"
::= { atmIfVptCAUbrRowStatusEntry 2 }

atmIfVptCAUbrStorageType OBJECT-TYPE
   SYNTAX     StorageType 
   ACCESS     read-only
   STATUS     mandatory
   DESCRIPTION
     "This variable represents the storage type value for the
      atmIfVptCAUbr tables."
::= { atmIfVptCAUbrRowStatusEntry 4 }

atmIfVptCAUbrIndex OBJECT-TYPE
   SYNTAX     Integer32 (0)
   ACCESS     not-accessible
   STATUS     mandatory
   DESCRIPTION
     "This variable represents the index for the atmIfVptCAUbr tables."
::= { atmIfVptCAUbrRowStatusEntry 10 }

atmIfVptCAUbrProvTable OBJECT-TYPE
   SYNTAX     SEQUENCE OF AtmIfVptCAUbrProvEntry
   ACCESS     not-accessible
   STATUS     mandatory
   DESCRIPTION
     "This group contains provisioned attributes which control 
      Connection Admission Control (CAC) attributes for UBR 
      connections associated with this Vpt. Any attributes of the AtmIf CA 
      Ubr that cannot be overridden in the Vpt CA Ubr affect all 
      connections, including Vpt Vccs."
::= { atmIfVptCAUbr 100 }

atmIfVptCAUbrProvEntry OBJECT-TYPE
   SYNTAX     AtmIfVptCAUbrProvEntry
   ACCESS     not-accessible
   STATUS     mandatory
   DESCRIPTION
     "An entry in the atmIfVptCAUbrProvTable."
   INDEX {
      atmIfIndex,
      atmIfVptIndex,
      atmIfVptCAIndex,
      atmIfVptCAUbrIndex }
::= { atmIfVptCAUbrProvTable 1 }

AtmIfVptCAUbrProvEntry ::= SEQUENCE {
   atmIfVptCAUbrMaxVccs
      Unsigned32,
   atmIfVptCAUbrPool
      INTEGER,
   atmIfVptCAUbrMinimumCellRate
      Unsigned32 }

atmIfVptCAUbrMaxVccs OBJECT-TYPE
   SYNTAX     Unsigned32 (0..16384 | 16385)
   ACCESS     read-write
   STATUS     mandatory
   DESCRIPTION
     "This attribute specifies the maximum number of UBR Vccs that can 
      be configured associated with this Vpt. The value must not exceed 
      the maxVccs attribute of the parent Vpt CA component.
      
      If this attribute is set to sameAsCa, the maximum number of UBR 
      Vccs is the same as specified by the maxVccs attribute of the Vpt 
      CA.
      
      Changes to this attribute are not critical to the Vpt. If the value is 
      changed to a number smaller than the current number of active 
      VCCs, no new VCCs can be admitted until the number of active 
      VCCs drops below the value of this attribute. The current number of 
      active VCCs is indicated by the sum of the permanentVccs and 
      switchedVccs operational attribute under the Vpt CA component.

      VALUES (

      16385 = sameAsCa

      )"
   DEFVAL     { 16385 }
::= { atmIfVptCAUbrProvEntry 6 }

atmIfVptCAUbrPool OBJECT-TYPE
   SYNTAX     INTEGER  {
                 pool1(1),
                 pool2(2),
                 pool3(3),
                 pool4(4),
                 pool5(5) }
   ACCESS     read-write
   STATUS     mandatory
   DESCRIPTION
     "This attribute specifies the bandwidth pool which is to be used to 
      support the unspecified bit rate (UBR) service category. The 
      percentage of Vpt bandwidth capacity reserved for the given 
      bandwidth pool is the maximum bandwidth that can be allocated to 
      UBR traffic. The percentage allocated to each bandwidth pool can 
      be provisioned through the bandwidthPool attribute under the CA."
   DEFVAL     { pool1 }
::= { atmIfVptCAUbrProvEntry 10 }

atmIfVptCAUbrMinimumCellRate OBJECT-TYPE
   SYNTAX     Unsigned32 (0..2147483647)
   ACCESS     read-write
   STATUS     mandatory
   DESCRIPTION
     "This attribute specifies the default minimum cell rate (MCR) which 
      is allocated from the UBR pool bandwidth for each UBR 
      connection which is admitted. UBR connections normally are 
      serviced on a best effort basis, but this attribute allows allocation of 
      a default minimum bandwidth for each connection."
   DEFVAL     { 0 }
::= { atmIfVptCAUbrProvEntry 11 }

atmIfVptCAUbrOperTable OBJECT-TYPE
   SYNTAX     SEQUENCE OF AtmIfVptCAUbrOperEntry
   ACCESS     not-accessible
   STATUS     mandatory
   DESCRIPTION
     "This group contains operational attributes which show operational 
      attributes for UBR connections associated with this Vpt."
::= { atmIfVptCAUbr 110 }

atmIfVptCAUbrOperEntry OBJECT-TYPE
   SYNTAX     AtmIfVptCAUbrOperEntry
   ACCESS     not-accessible
   STATUS     mandatory
   DESCRIPTION
     "An entry in the atmIfVptCAUbrOperTable."
   INDEX {
      atmIfIndex,
      atmIfVptIndex,
      atmIfVptCAIndex,
      atmIfVptCAUbrIndex }
::= { atmIfVptCAUbrOperTable 1 }

AtmIfVptCAUbrOperEntry ::= SEQUENCE {
   atmIfVptCAUbrVccUsage
      Unsigned32 }

atmIfVptCAUbrVccUsage OBJECT-TYPE
   SYNTAX     Unsigned32 (0..16384)
   ACCESS     read-only
   STATUS     mandatory
   DESCRIPTION
     "This attribute indicates the number of active UBR Vccs under this 
      Vpt. It includes switched and permanent connections."
::= { atmIfVptCAUbrOperEntry 12 }


-- AtmIf/n Vpc/vpi TrafficManagement, 
-- AtmIf/n Vcc/vpi.vci TrafficManagement,
-- AtmIf/n Vpt/vpi TrafficManagement,
-- AtmIf/n Vpt/vpi Vcc/vci TrafficManagement
-- The Tm subcomponent contains the operational traffic management 
-- attributes of a connection. It is created dynamically for each 
-- activated Vcc, Vpc, or Vpt component.

atmIfVptTm OBJECT IDENTIFIER ::= { atmIfVpt 9 }



atmIfVptTmRowStatusTable OBJECT-TYPE
   SYNTAX     SEQUENCE OF AtmIfVptTmRowStatusEntry
   ACCESS     not-accessible
   STATUS     mandatory
   DESCRIPTION
     "This entry controls the addition and deletion of 
      atmIfVptTm components."
::= { atmIfVptTm 1 }

atmIfVptTmRowStatusEntry OBJECT-TYPE
   SYNTAX     AtmIfVptTmRowStatusEntry
   ACCESS     not-accessible
   STATUS     mandatory
   DESCRIPTION
     "A single entry in the table represents a single 
      atmIfVptTm component."
   INDEX {
      atmIfIndex,
      atmIfVptIndex,
      atmIfVptTmIndex }
::= { atmIfVptTmRowStatusTable 1 }

AtmIfVptTmRowStatusEntry ::= SEQUENCE {
   atmIfVptTmRowStatus
      RowStatus,
   atmIfVptTmComponentName
      DisplayString,
   atmIfVptTmStorageType
      StorageType,
   atmIfVptTmIndex
      NonReplicated }

atmIfVptTmRowStatus OBJECT-TYPE
   SYNTAX     RowStatus 
   ACCESS     read-only
   STATUS     mandatory
   DESCRIPTION
     "This variable is used as the basis for SNMP naming of
      atmIfVptTm components.
      These components cannot be added nor deleted."
::= { atmIfVptTmRowStatusEntry 1 }

atmIfVptTmComponentName OBJECT-TYPE
   SYNTAX     DisplayString 
   ACCESS     read-only
   STATUS     mandatory
   DESCRIPTION
     "This variable provides the component's string name for
      use with the ASCII Console Interface"
::= { atmIfVptTmRowStatusEntry 2 }

atmIfVptTmStorageType OBJECT-TYPE
   SYNTAX     StorageType 
   ACCESS     read-only
   STATUS     mandatory
   DESCRIPTION
     "This variable represents the storage type value for the
      atmIfVptTm tables."
::= { atmIfVptTmRowStatusEntry 4 }

atmIfVptTmIndex OBJECT-TYPE
   SYNTAX     NonReplicated 
   ACCESS     not-accessible
   STATUS     mandatory
   DESCRIPTION
     "This variable represents the index for the atmIfVptTm tables."
::= { atmIfVptTmRowStatusEntry 10 }

atmIfVptTmOperTable OBJECT-TYPE
   SYNTAX     SEQUENCE OF AtmIfVptTmOperEntry
   ACCESS     not-accessible
   STATUS     mandatory
   DESCRIPTION
     "This group contains attributes for the Tm component to reflect 
      operational traffic attributes."
::= { atmIfVptTm 100 }

atmIfVptTmOperEntry OBJECT-TYPE
   SYNTAX     AtmIfVptTmOperEntry
   ACCESS     not-accessible
   STATUS     mandatory
   DESCRIPTION
     "An entry in the atmIfVptTmOperTable."
   INDEX {
      atmIfIndex,
      atmIfVptIndex,
      atmIfVptTmIndex }
::= { atmIfVptTmOperTable 1 }

AtmIfVptTmOperEntry ::= SEQUENCE {
   atmIfVptTmTxTrafficDescType
      INTEGER,
   atmIfVptTmTxQosClass
      INTEGER,
   atmIfVptTmTxQueueLength
      Unsigned32,
   atmIfVptTmTxQueueCongestionState
      Unsigned32,
   atmIfVptTmHoldingPriority
      INTEGER,
   atmIfVptTmRxTrafficDescType
      INTEGER,
   atmIfVptTmRxQosClass
      INTEGER,
   atmIfVptTmAtmServiceCategory
      INTEGER,
   atmIfVptTmTrafficShaping
      INTEGER,
   atmIfVptTmBearerClassBbc
      INTEGER,
   atmIfVptTmTransferCapabilityBbc
      INTEGER,
   atmIfVptTmClippingBbc
      INTEGER,
   atmIfVptTmUnshapedTransmitQueueing
      INTEGER,
   atmIfVptTmBestEffort
      INTEGER,
   atmIfVptTmForceTagging
      INTEGER,
   atmIfVptTmWeight
      Unsigned32,
   atmIfVptTmUsageParameterControl
      INTEGER,
   atmIfVptTmTxPacketWiseDiscard
      OCTET STRING,
   atmIfVptTmRxPacketWiseDiscard
      OCTET STRING,
   atmIfVptTmBandwidthElastic
      INTEGER,
   atmIfVptTmBandwidthReduction
      Unsigned32,
   atmIfVptTmAbrConnectionType
      INTEGER }

atmIfVptTmTxTrafficDescType OBJECT-TYPE
   SYNTAX     INTEGER  {
                 n1(1),
                 n2(2),
                 n3(3),
                 n4(4),
                 n5(5),
                 n6(6),
                 n7(7),
                 n8(8),
                 n9(9) }
   ACCESS     read-only
   STATUS     mandatory
   DESCRIPTION
     "T his attribute indicates the type of traffic management which is 
      applied to the transmit direction of this connection as defined in the 
      ATM Forum. The txTrafficDescType determines the number and 
      meaning of the parameters in the txTrafficDescParm attribute."
::= { atmIfVptTmOperEntry 10 }

atmIfVptTmTxQosClass OBJECT-TYPE
   SYNTAX     INTEGER  {
                 n0(0),
                 n1(1),
                 n2(2),
                 n3(3),
                 n4(4),
                 notApplicable(14) }
   ACCESS     read-only
   STATUS     mandatory
   DESCRIPTION
     "This attribute indicates the quality of service for the calling to called 
      direction for this connection. This is only applicable to Soft PVC 
      and SVC connections. 
      
      Class 1 supports a QOS that meets Service Class A performance 
      requirements (Circuit emulation, constant bit rate video).
      
      Class 2 supports a QOS that meets Service Class B performance 
      requirements (Variable bit rate audio and video).
      
      Class 3 supports a QOS that meets Service Class C performance 
      requirements (Connection-Oriented Data Transfer).
      
      Class 4 supports a QOS that meets Service Class D performance 
      requirements (Connectionless Data Transfer).
      
      Class 0 is the unspecified QOS class; no objective is specified for 
      the performance parameters.
      
      A value of notApplicable is displayed in the case of nailed-up PVCs 
      for which this attribute has no significance."
::= { atmIfVptTmOperEntry 31 }

atmIfVptTmTxQueueLength OBJECT-TYPE
   SYNTAX     Unsigned32 (0..30720)
   ACCESS     read-only
   STATUS     mandatory
   DESCRIPTION
     "This attribute indicates the current number of cells in the transmit 
      queue for this connection. 
      
      If this connection has unshapedTransmitQueueing attribute 
      displayed as common, this attribute displays the length of the 
      common queue which is used for this atm service category. 
      
      If this connection has unshapedTransmitQueueing attribute 
      displayed as fifo, this attribute indicates the number of cells for this 
      connection which are enqueued in a first-in-first-out queuing 
      method for this atm service category. This will only occur for 
      connections on ATM IP cards with atmServiceCategory of nrtVbr 
      or ubr. 
      
      If this connection has unshapedTransmitQueueing attribute 
      displayed as perVc or as notApplicable, this attribute displays the 
      length of the per-VC queue.
      
      This attribute does not apply to basic Vpts."
::= { atmIfVptTmOperEntry 32 }

atmIfVptTmTxQueueCongestionState OBJECT-TYPE
   SYNTAX     Unsigned32 (0..3)
   ACCESS     read-only
   STATUS     mandatory
   DESCRIPTION
     "This attribute indicates the congestion state of the transmit queue 
      for this connection. 
      
      If this connection has unshapedTransmitQueueing attribute 
      displayed as common, this attribute displays the congestion state of 
      the common queue. If this connection has 
      unshapedTransmitQueueing attribute displayed as perVc or as 
      notApplicable, this attribute displays the congestion state of the per-
      VC queue.
      
      The congestion state of a queue is indicated by a numeric value 
      ranging from 0 to 3. When a queue is in a congested state x, only 
      traffic with discard priority (DP) 0 to x are enqueued. Traffic with 
      DP > x is discarded. 
      
      For example, if the congestion state is 3, there is no congestion and 
      all traffic is enqueued. Likewise, when the congestion state is 0, 
      there is maximum congestion and only traffic with DP=0 is 
      enqueued on that queue.
      
      This attribute does not apply to basic Vpts."
::= { atmIfVptTmOperEntry 33 }

atmIfVptTmHoldingPriority OBJECT-TYPE
   SYNTAX     INTEGER  {
                 n0(0),
                 n1(1),
                 n2(2),
                 n3(3),
                 n4(4),
                 notApplicable(6) }
   ACCESS     read-only
   STATUS     mandatory
   DESCRIPTION
     "This attribute indicates the actual holding priority in effect for this 
      connection. In a situation where the link bandwidth fluctuates, such 
      as over an IMA link, holding priority is used to determine which 
      connections are held and which are released. Holding priority 4 
      connections are the first to be released. Holding priority 0 
      connections are the last to be released. Some applications, for 
      example Vcc Test, may override the provisioned holding priority. 
      
      A value of notApplicable is displayed when this is an elastic 
      connection. Holding priority does not apply to bandwidth elastic 
      connections.
      
      Holding priority has no effect if the equivalent cell rate (ECR) for a 
      connection is zero.
      
      This attribute does not apply to Vpt Vccs."
::= { atmIfVptTmOperEntry 35 }

atmIfVptTmRxTrafficDescType OBJECT-TYPE
   SYNTAX     INTEGER  {
                 n1(1),
                 n2(2),
                 n3(3),
                 n4(4),
                 n5(5),
                 n6(6),
                 n7(7),
                 n8(8),
                 n9(9) }
   ACCESS     read-only
   STATUS     mandatory
   DESCRIPTION
     "This attribute indicates the type of traffic management which is 
      applied to the receive direction of this connection as defined in the 
      ATM Forum. The rxTrafficDescType determines the number and 
      meaning of the parameters in the rxTrafficDescParm attribute."
::= { atmIfVptTmOperEntry 40 }

atmIfVptTmRxQosClass OBJECT-TYPE
   SYNTAX     INTEGER  {
                 n0(0),
                 n1(1),
                 n2(2),
                 n3(3),
                 n4(4),
                 notApplicable(14) }
   ACCESS     read-only
   STATUS     mandatory
   DESCRIPTION
     "This attribute indicates the quality of service for the called to calling 
      direction for this connection. This is only applicable to Soft PVC 
      and SVC connections. 
      
      Class 1 supports a QOS that meets Service Class A performance 
      requirements (circuit emulation, constant bit rate video).
      
      Class 2 supports a QOS that meets Service Class B performance 
      requirements (variable bit rate audio and video).
      
      Class 3 supports a QOS that meets Service Class C performance 
      requirements (Connection-Oriented Data Transfer).
      
      Class 4 supports a QOS that meets Service Class D performance 
      requirements (Connectionless Data Transfer).
      
      Class 0 is the unspecified QOS class; no objective is specified for 
      the performance parameters.
      
      A value of notApplicable is displayed in the case of nailed-up PVCs 
      for which this attribute has no significance."
::= { atmIfVptTmOperEntry 61 }

atmIfVptTmAtmServiceCategory OBJECT-TYPE
   SYNTAX     INTEGER  {
                 unspecifiedBitRate(0),
                 constantBitRate(1),
                 rtVariableBitRate(2),
                 nrtVariableBitRate(3),
                 availableBitRate(4) }
   ACCESS     read-only
   STATUS     mandatory
   DESCRIPTION
     "This attribute indicates the ATM service category used for traffic in 
      both directions of the connection. This attribute does not apply to 
      Virtual Link VPTs and will always be displayed as 
      constantBitRate.
      
      The constantBitRate service category is intended for real time 
      applications, that is, those requiring tightly constrained delay and 
      delay variation, as would be appropriate for voice and video 
      applications. The consistent availability of a fixed quantity of 
      bandwidth is considered appropriate for CBR service. Cells which 
      are delayed beyond the value specified by Cell Transfer Delay are 
      assumed to have significantly reduced value for the application.
      
      The rtVariableBitRate service category is intended for real time 
      applications; that is those requiring tightly constrained delay and 
      delay variation, as would be appropriate for voice and video 
      applications. Sources are expected to transmit at a rate which varies 
      with time. Equivalently, the source can be described as 'bursty'. 
      Cells which are delayed beyond the value specified by Cell Transfer 
      Delay are assumed to be of significantly reduced value to the 
      application. Real time VBR service may support statistical 
      multiplexing of real time sources.
      
      The nrtVariableBitRate service category is intended for non-real 
      time applications which have bursty traffic characteristics and which 
      can be characterized in terms of a PCR, SCR, and MBS. For those 
      cells which are transferred within the traffic contract, the application 
      expects a low cell loss ratio. For all connections, it expects a bound 
      on the mean cell transfer delay. Non-real time VBR service may 
      support statistical multiplexing of connections.
      
      The availableBitRate service is an ATM layer service category for 
      which the limiting ATM layer transfer characteristics provided by 
      the network may change subsequent to connection establishment. 
      ABR service has a flow control mechanism which supports several 
      types of feedback to control the source rate in response to changing 
      ATM layer transfer characteristics. ABR service is not intended to 
      support real-time applications.
      
      The unspecifiedBitRate service is intended for non-real time 
      applications, that is those not requiring tightly constrained delay 
      and delay variation. UBR sources are expected to be bursty. UBR 
      service supports a high degree of statistical multiplexing among 
      sources. UBR service does not specify traffic related service 
      guarantees. No numerical commitments are made with respect to 
      the cell loss ratio experienced by a UBR connection, or as to the 
      cell transfer delay experienced by cells on the connection."
::= { atmIfVptTmOperEntry 62 }

atmIfVptTmTrafficShaping OBJECT-TYPE
   SYNTAX     INTEGER  {
                 disabled(1),
                 notApplicable(4),
                 linear(5),
                 inverseUpc(6),
                 dynamic(7) }
   ACCESS     read-only
   STATUS     mandatory
   DESCRIPTION
     "This attribute indicates the traffic shaping state of the connection.
      
      A value of notApplicable indicates that traffic shaping is not 
      applicable or not supported for this connection. This is the case:
      - when the txTrafficDescType is 1 or 2.
      - for standard Vpt Vccs and basic Vpts.
      - for CQC-based ATM cards, when the atmServiceCategory is 
      constantBitRate.
      
      In these cases, the value of notApplicable is set regardless of 
      whether traffic shaping is enabled or disabled in the provisioning 
      data.
      
      A value of disabled indicates that traffic shaping is applicable and 
      supported for the type of connection but has been turned off in the 
      provisioning data.
      
      A value of linear or inverseUpc indicates that traffic shaping is 
      applicable and supported for the type of connection and has been 
      turned on in the provisioning data. This is the only case that 
      indicates that traffic shaping is performed on the connection. In this 
      case, the actual shaping rate is reflected in the txTrafficDescParm 
      attribute, parameter number 4. A value of linear indicates that 
      traffic is being shaped at the constant rate indicated in 
      txTrafficDescParm 4.
      
      A value of inverseUpc is possible only on ATM IP cards. This value 
      indicates that the shaper strictly conforms to the requirements of a 
      dual leaky bucket UPC enforcer. This value is indicated if traffic 
      shaping is enabled, and the txTrafficDescType for this connection is 
      6, 7 or 8.
      
      Traffic shaping for connections with atmServiceCategory as 
      availableBitRate (txTrafficDescType 9) depends upon the 
      abrConnectionType attribute. If abrConnectionType is sourceDest 
      or virtualSourceDest, the value of this attribute is dynamic. If 
      abrConnectionType is erSwitch or efciSwitch, this attribute is 
      notApplicable."
::= { atmIfVptTmOperEntry 70 }

atmIfVptTmBearerClassBbc OBJECT-TYPE
   SYNTAX     INTEGER  {
                 a(1),
                 c(3),
                 x(16),
                 vp(24),
                 notApplicable(30) }
   ACCESS     read-only
   STATUS     mandatory
   DESCRIPTION
     "This attribute indicates the bearer capability for this connection.
      
      Class a service is a connection-oriented, constant bit rate ATM 
      transport service. Class a service has end to end timing 
      requirements and may require stringent cell loss, cell delay and cell 
      delay variation performance.When a is displayed, the user is 
      requesting more than an ATM only service. The network may look 
      at the AAL to provide interworking based upon its contents. 
      
      Class c service is a connection-oriented, variable bit rate ATM 
      transport service. Class c service has no end-to-end timing 
      requirements.When c is displayed, the user is requesting more than 
      an ATM only service. The network interworking function may look 
      at the AAL and provide service based on it.
      
      Class x service is a connection-oriented ATM transport service 
      where the AAL, trafficType (cbr or vbr), and timing requirements 
      are user defined (that is, transparent to the network). When the 
      value of this attribute is x, the user is requesting an ATM only 
      service from the network. In this case, the network shall not process 
      any higher layer protocol.
      
      Class vp service is used to indicate a transparent VP service when 
      the user is requesting an ATM only service from the network. In this 
      case, the network does not process any higher layer protocol. This 
      service differs from class x service in that with the class vp service 
      both the VCI field (except for VCI values 0, 3, 4, and 6 through 15) 
      and Payload Type field are transported transparently by the network. 
      This attribute value is only applicable to SPVP and SVP 
      connections.
      
      A value of notApplicable is displayed in the case of nailed-up PVCs 
      for which this attribute has no significance."
::= { atmIfVptTmOperEntry 71 }

atmIfVptTmTransferCapabilityBbc OBJECT-TYPE
   SYNTAX     INTEGER  {
                 n0(0),
                 n1(1),
                 n2(2),
                 n5(5),
                 n8(8),
                 n9(9),
                 n10(10),
                 notApplicable(30) }
   ACCESS     read-only
   STATUS     mandatory
   DESCRIPTION
     "This attribute indicates the transfer capability for this connection. 
      Uni 3.0/3.1 traffic type and end-to-end timing parameters are 
      mapped into this parameter as follows:
      <transferCapability: TrafficType, Timing>
      0: NoIndication, NoIndication
      1: NoIndication, yes
      2: NoIndication, no
      5: CBR, yes
      8: VBR, NoIndication
      9: VBR, yes
      10: VBR, no
      
      A value of notApplicable is displayed in the case of nailed-up PVCs 
      for which this attribute has no significance, or in the case that the 
      transfer capability in the call request was set to NoIndication.
      
      The CBR traffic type refers to traffic offered on services such as a 
      constant bit rate video service or a circuit emulation.
      
      The VBR traffic type refers to traffic offered on services such as 
      packetized audio and video, or data.
      
      The value NoIndication for traffic type is used if the user has not set 
      the traffic type; similarly for end-to-end timing.
      
      The value yes for end-to-end timing indicates that end-to-end 
      timing is required for the connection.
      
      The value no for end-to-end timing indicates that end-to-end timing 
      is not required for the connection."
::= { atmIfVptTmOperEntry 72 }

atmIfVptTmClippingBbc OBJECT-TYPE
   SYNTAX     INTEGER  {
                 no(0),
                 yes(1),
                 notApplicable(14) }
   ACCESS     read-only
   STATUS     mandatory
   DESCRIPTION
     "This attribute indicates the value of the clipping susceptibility 
      parameter in the broadband bearer capability (BBC) Information 
      Element.
      
      Clipping is an impairment in which the first fraction of a second of 
      information to be transferred is lost. It occurs after a call is 
      answered and before an associated connection is switched through.
      
      A value of notApplicable is displayed in the case of nailed-up PVCs 
      for which this attribute has no significance."
::= { atmIfVptTmOperEntry 74 }

atmIfVptTmUnshapedTransmitQueueing OBJECT-TYPE
   SYNTAX     INTEGER  {
                 perVc(0),
                 common(1),
                 notApplicable(4),
                 fifo(5) }
   ACCESS     read-only
   STATUS     mandatory
   DESCRIPTION
     "This attribute indicates the unshaped transmit queuing state of the 
      connection.
      
      A value of common indicates that transmit traffic is being enqueued 
      onto the common transmit queue for this service category. 
      The txQueueLength attribute indicates the current length of the 
      common transmit queue.
      
      A value of fifo indicates that transmit traffic is being queued in a 
      first-in-first-out basis for this service category. This is similar to 
      common queueing, but the txQueueLength attribute indicates the 
      number of cells in this connection queue. A value of fifo will only 
      be indicated for connections on ATM IP cards with 
      atmServiceCategory of nrtVbr or ubr. 
      A value of perVc indicates that transmit traffic is being enqueued 
      onto a per-VC queue for this connection.
      
      A value of notApplicable indicates that transmit traffic is being 
      shaped for this connection, or that unshaped transmit queuing is not 
      applicable for this type of connection. Transmit traffic for a shaped 
      connection is enqueued onto a per-VC queue, but this attribute is 
      only applicable for unshaped connections. Unshaped transmit 
      queuing is not applicable for basic Vpts."
::= { atmIfVptTmOperEntry 75 }

atmIfVptTmBestEffort OBJECT-TYPE
   SYNTAX     INTEGER  {
                 indicated(0),
                 notIndicated(1),
                 notApplicable(14) }
   ACCESS     read-only
   STATUS     mandatory
   DESCRIPTION
     "This attribute indicates value of best effort parameter in the ATM 
      Traffic Descriptor Information Element.
      
      The value indicated implies that the quality of service for this 
      connection is not guaranteed.
      
      The value notIndicated implies that the quality of service for this 
      connection is guaranteed.
      
      A value of notApplicable is displayed in the case of nailed-up PVCs 
      for which this attribute has no significance."
::= { atmIfVptTmOperEntry 76 }

atmIfVptTmForceTagging OBJECT-TYPE
   SYNTAX     INTEGER  {
                 enabled(0),
                 disabled(1) }
   ACCESS     read-only
   STATUS     mandatory
   DESCRIPTION
     "This attribute indicates the state of force tagging option for this 
      connection. Force tagging refers to setting the CLP bit for all cells 
      on a connection. 
      
      For CQC-based ATM cards, this attribute is not applicable and is 
      not displayed.
      
      A value of enabled indicates that the CLP bit is being set to 1 for all 
      cells in the transmit direction on this connection. 
      
      A value of disabled indicates that the CLP bit is unchanged for cells 
      in the transmit direction on this connection. disabled is always 
      displayed for Vpts since forced tagging is applied on a per Vpt Vcc 
      basis."
::= { atmIfVptTmOperEntry 78 }

atmIfVptTmWeight OBJECT-TYPE
   SYNTAX     Unsigned32 (0 | 1..4095 | 65534)
   ACCESS     read-only
   STATUS     mandatory
   DESCRIPTION
     "This attribute indicates the relative weight of this unshaped 
      connection. Connections with a larger weight get a larger proportion 
      of the link bandwidth, or in the case of standard Vpt Vccs, the Vpt 
      bandwidth. 
      
      For all but standard Vpt Vccs, the default connection weight is 
      determined by the weight policy for a service category and the 
      traffic descriptor for a connection. For standard Vpt Vccs, the 
      default connection weight is determined by the Vcc's service 
      category.
      
      For CQC-based ATM cards, this attribute is not applicable and is 
      not displayed.
      
      A value from 1 to 4095 indicates an actual weight. The value 
      upToQueueLimit indicates that the weight of a connection is up to 
      the transmit queue limit for this connection. upToQueueLimit is 
      used with common (first-in-first-out) queueing. 
      
      This attribute is displayed as notApplicable if:
      - this connection has trafficShaping displayed as linear or 
      inverseUpc.
      - this is a basic Vpt.

      VALUES (

      0 = upToQueueLimit

      65534 = notApplicable

      )"
::= { atmIfVptTmOperEntry 79 }

atmIfVptTmUsageParameterControl OBJECT-TYPE
   SYNTAX     INTEGER  {
                 enforced(0),
                 disabled(1),
                 notApplicable(3),
                 monitored(4),
                 abrMonitored(5),
                 abrEnforced(6) }
   ACCESS     read-only
   STATUS     mandatory
   DESCRIPTION
     "This attribute indicates the UPC state of the connection.
      
      A value of notApplicable indicates that UPC is not applicable or not 
      supported for the connection. This is the case:
      - when the connection's rxTrafficDescType is 1 or 2. 
      - for standard Vpt Vccs and basic Vpts.
      
      A value of notApplicable is set regardless of whether UPC is 
      disabled or enabled in provisioning data.
      
      A value of disabled indicates that UPC is applicable and supported 
      for the type of connection but has been turned off in the 
      provisioning data.
      
      A value of enforced indicates that UPC is actively checking 
      conformance for the connection and is discarding or tagging cells 
      which do not conform to the connection traffic contract. The traffic 
      descriptor parameters used for UPC conformance are reflected in 
      the rxTrafficDescParms of the connection. On ATM IP cards, the 
      counts of UPC violations are visible in the Vcc, Vpc, or Vpt 
      rxUpcViolationsOnEnforcer1 or rxUpcViolationsOnEnforcer2 
      attributes. 
      
      ATM IP cards provide the ability to monitor UPC violations without 
      tagging or discarding. A value of monitored indicates that UPC is 
      actively checking conformance for the connection and counting the 
      violations, but is not discarding or tagging cells which do not 
      conform to the connection traffic contract. The traffic descriptor 
      parameters used for UPC conformance are reflected in the 
      rxTrafficDescParms of the connection. The counts of UPC 
      violations are visible in the Vcc, Vpc, or Vpt 
      rxUpcViolationsOnEnforcer1 or rxUpcViolationsOnEnforcer2 
      attributes. The value of monitored appears only on ATM IP cards. 
      
      If the atmServiceCategory for this connection indicates 
      availableBitRate, a value of abrEnforced indicates that Dynamic 
      Generic Cell Rate Algorithm (DGCRA) is active for the connection 
      and that violating cells are discarded. The cell rate which is in effect 
      at any particular instant is indicated in rxTrafficDescParm 4 of the 
      connection. 
      
      If the atmServiceCategory for this connection indicates 
      availableBitRate, a value of abrMonitored indicates that Dynamic 
      Generic Cell Rate Algorithm (DGCRA) is active for the connection 
      but that violating cells are counted only. The cell rate which is in 
      effect at any particular instant is indicated in rxTrafficDescParm 4 
      of the connection."
::= { atmIfVptTmOperEntry 80 }

atmIfVptTmTxPacketWiseDiscard OBJECT-TYPE
   SYNTAX     OCTET STRING (SIZE (1))
   ACCESS     read-only
   STATUS     mandatory
   DESCRIPTION
     "This attribute indicates the current set of packet-wise discard 
      functions in effect in the transmit data direction at this connection 
      point.
      
      A value of ppd indicates that the Partial Packet Discard (PPD) 
      function is in effect. PPD may be applied at an intermediate 
      connecting point for a connection which is transporting frame traffic 
      (AAL5 at the endpoint). PPD is controlled by provisioning for 
      PVCs and SPVCs, and by call setup parameters in the AAL and 
      Traffic Descriptor Information Elements.
      
      A value of epd indicates that the Early Packet Discard (EPD) 
      function is in effect at this connection endpoint. On CQC-based 
      ATM cards, PPD and EPD are enabled by default at a connection 
      endpoint which is performing AAL5 segmentation and assembly.
      
      A value of wred indicates that Weighted Random Early Detection is 
      in effect at this connection point. W-RED can be enabled by 
      provisioning for PVCs and SPVCs.
      
      On ATM IP cards, all packet-wise discard functions also apply to 
      provisioned virtual path connections (VPCs). On CQC-based ATM 
      cards, packet-wise functions are not applicable for VPCs.
      
      This attribute is not applicable for Vpts.

      Description of bits:
      ppd(0)
      epd(1)
      wred(2)"
::= { atmIfVptTmOperEntry 85 }

atmIfVptTmRxPacketWiseDiscard OBJECT-TYPE
   SYNTAX     OCTET STRING (SIZE (1))
   ACCESS     read-only
   STATUS     mandatory
   DESCRIPTION
     "This attribute indicates the current set of packet-wise discard 
      functions in effect in the receive data direction at this connection 
      point.
      
      A value of ppd indicates that the Partial Packet Discard (PPD) 
      function is in effect. PPD may be applied at an intermediate 
      connecting point for a connection which is transporting frame traffic 
      (AAL5 at the endpoint). PPD is controlled by provisioning for 
      PVCs and SPVCs, and by call setup parameters in the AAL and 
      Traffic Descriptor Information Elements.
      
      A value of epd indicates that the Early Packet Discard (EPD) 
      function is in effect at this connection endpoint. PPD and EPD are 
      enabled by default at a connection endpoint which is performing 
      AAL5 segmentation and assembly.
      
      On ATM IP cards, all packet-wise discard functions also apply to 
      provisioned virtual path connections (VPCs). On CQC-based ATM 
      cards, packet-wise functions are not applicable for VPCs.
      
      This attribute is not applicable for Vpts.

      Description of bits:
      ppd(0)
      epd(1)"
::= { atmIfVptTmOperEntry 86 }

atmIfVptTmBandwidthElastic OBJECT-TYPE
   SYNTAX     INTEGER  {
                 no(0),
                 yes(1) }
   ACCESS     read-only
   STATUS     mandatory
   DESCRIPTION
     "This attribute is only of importance for connections which are 
      carried on a link with a variable bandwidth. For example, the 
      bandwidth may be reduced in the event that one or more physical 
      links in the IMA group fail, such that the originally requested 
      bandwidth cannot be maintained. This attribute shows whether the 
      application (for example, Trunk) running on this connection can 
      continue to operate if the bandwidth is reduced. If the bandwidth is 
      reduced, the amount by which it is reduced is displayed in the 
      bandwidthReduction attribute. 
      
      A value of yes, indicates that this connection is elastic, and the 
      bandwidth may be reduced but the connection is not released. 
      
      A value of no indicates that the bandwidth for this connection is not 
      reduced in the event of link bandwidth reduction. However, this 
      connection may be released based on its holdingPriority.
      
      Bandwidth elasticity has no effect for connections which have an 
      equivalent cell rate (ECR) of zero. 
      
      This attribute is not applicable for Vpts and Vpt Vccs."
::= { atmIfVptTmOperEntry 90 }

atmIfVptTmBandwidthReduction OBJECT-TYPE
   SYNTAX     Unsigned32 (0..2147483647)
   ACCESS     read-only
   STATUS     mandatory
   DESCRIPTION
     "This attribute shows the amount by which the bandwidth has been 
      reduced for this connection. This value is non-zero only for 
      connections which have bandwidthElastic displayed as yes, and 
      which are also operating in a reduced bandwidth mode. This is 
      typically the case for selected connections running over an IMA 
      link. This attribute takes a value from 0 (no reduction) up to the 
      ECR. For all connections which are running at their full allocated 
      bandwidth, bwReduction has the value 0. Connections which have 
      been reduced in allocated bandwidth have a positive number for this 
      attribute. The bwReduction may be subtracted from the ECR (which 
      is displayed as txTrafficDescParm 5) to determine the actual 
      bandwidth allocated to this connection."
::= { atmIfVptTmOperEntry 100 }

atmIfVptTmAbrConnectionType OBJECT-TYPE
   SYNTAX     INTEGER  {
                 erSwitch(1),
                 efciSwitch(2),
                 virtualSourceDest(3),
                 sourceDest(4),
                 nonAbrInterworking(5),
                 notApplicable(15) }
   ACCESS     read-only
   STATUS     mandatory
   DESCRIPTION
     "This attribute indicates the type of ABR behavior which is in effect 
      at this connection. This attribute is only applicable if the 
      atmServiceCategory attribute is availableBitRate. If the 
      atmServiceCategory attribute is not availableBitRate, or if the 
      connection is not active, this attribute value is displayed as 
      notApplicable.
      
      For CQC-based ATM cards, the only possible values are 
      notApplicable, efciSwitch or nonAbrInterworking. In EFCI 
      marking mode, the Explicit Forward Congestion Indication (EFCI) 
      field in the data cell headers is used to indicate transmit queue 
      congestion. 
      
      For ATM IP cards, if the connectionPointType is displayed as 
      connectionEndPoint, this attribute has the value sourceDest. In this 
      mode, the ABR Source and Destination behavior is in effect at this 
      connection. This attribute is also sourceDest in the case where the 
      next hop connection is specified as nonAbrInterworking. The next 
      hop connection is the Vcc or Vpc identified by the nextHop attribute 
      of the Nrp or Rp component. 
      
      If the connectionPointType is not connectionEndPoint, the value of 
      this attribute depends upon the abrConnectionType provisioning 
      and the card type to which the traffic is forwarded on the backplane. 
      The default abrConnectionType is provisioned at the CA Abr 
      abrConnectionType attribute, and may be overridden for a 
      provisioned connection in the Vcd Tm abrConnectionType or Vpd 
      Tm abrConnectionType attribute. If the CA Abr abrConnectionType 
      attribute is virtualSourceDest at either one of the two connection 
      points, and if both the connection points are defined on ATM IP 
      cards, virtual source and destination behavior is applied to the 
      connection. In this instance, the attribute displays the value 
      virtualSourceDest.
      
      This attribute has the value erSwitch if ABR explicit rate 
      functionality is in effect at this connection. In this mode, the switch 
      may modify the Explicit Rate (ER) field of backward Resource 
      Management (RM) cells to indicate the status of congestion at this 
      connection point.
      
      This attribute has the value nonAbrInterworking in the case where 
      this connection point is functioning as an SPVC origin for an ABR 
      connection where the link side of this connection is configured as a 
      non-ABR ATM service category. This means that there are no RM 
      cells on the link side of this connection, and that the next hop 
      connection point is performing as an ABR sourceDest."
::= { atmIfVptTmOperEntry 110 }

atmIfVptTmTxTdpTable OBJECT-TYPE
   SYNTAX     SEQUENCE OF AtmIfVptTmTxTdpEntry
   ACCESS     not-accessible
   STATUS     mandatory
   DESCRIPTION
     "This attribute is a vector of five transmit traffic parameters whose 
      mapping is defined by the txTrafficDescType attribute. 
      
      The values of peak cell rate (PCR), sustained cell rate (SCR), 
      Minimum Cell Rate (MCR), actual cell rate (ACR), explicit rate 
      (ER), equivalent cell rate (ECR), and actual shaping rate are 
      expressed in cell/s. Maximum burst size (MBS) is expressed in 
      cells. CDVT is expressed in microseconds. 
      
      When txTrafficDescType is 1 or 2, parameters 1 through 5 are 
      unused.
      
      In this description, PCR is the greater of either the PCR or the 
      requested shaping rate (parameter 1 or parameter 5) specified in the 
      txTrafficDescParm attribute under the Vcd Tm or Vpd Tm 
      component.
      
      When txTrafficDescType is 3, parameter 1 represents the PCR for 
      CLP equal to 0 or 1 traffic; parameters 2 and 3 are unused.
      
      When txTrafficDescType is 4, parameter 1 represents the PCR for 
      CLP equal to 0 and 1 traffic; parameter 2 represents the PCR for 
      CLP equal to 0 traffic with cell discard.
      
      When txTrafficDescType is 5, parameter 1 represents the PCR for 
      CLP equal to 0 and 1 traffic; parameter 2 represents the PCR for 
      CLP equal to 0 traffic with cell tagging.
      
      When txTrafficDescType is 6, parameter 1 represents the PCR for 
      CLP equal to 0 and 1 traffic; parameter 2 represents the SCR for 
      CLP equal to 0 and 1 traffic; parameter 3 represents the MBS for 
      CLP equal to 0 and 1 traffic.
      
      When txTrafficDescType is 7, parameter 1 represents the PCR for 
      CLP equal to 0 and 1 traffic; parameter 2 represents the SCR for 
      CLP equal to 0 traffic with cell discard; parameter 3 represents the 
      MBS for CLP equal to 0 traffic.
      
      When txTrafficDescType is 8, parameter 1 represents the PCR for 
      CLP equal to 0 and 1 traffic; parameter 2 represents the SCR for 
      CLP equal to 0 traffic with cell tagging; parameter 3 represents the 
      MBS for CLP equal to 0 traffic.
      
      When txTrafficDescType is 3, 4, 5, 6, 7, or 8, parameter 4 reflects 
      the actual shaping rate in cell/s for this connection. For CQC-based 
      ATM cards, the set of available shaping rates is based on the 
      number of interfaces doing shaping (attribute 
      perVcQueueInterfaces), and the shapingScalingFactor attribute of 
      the Arc Cqc Override component. A rate of zero (0) indicates that 
      shaping is not performed, or that the interface is down. 
      
      When txTrafficDescType is 9, parameter 1 represents the PCR; 
      parameter 2 represents the Cell Delay Variation Toleration (CDVT); 
      parameter 3 represents the Minimum Cell Rate (MCR); the meaning 
      of parameter 4 depends upon the value of the abrConnectionType 
      attribute. if abrConnectionType is sourceDest or 
      virtualSourceDest, parameter 4 represents the Allowed Cell Rate 
      (ACR); If abrConnectionType is erSwitch, parameter 4 represents 
      the Explicit Rate (ER); and if abrConnectionType is efciSwitch, 
      parameter 4 reflects the actual shaping rate in cell/s for this 
      connection.
      
      When txTrafficDescType is 3, 4, 5, 6, 7, 8, or 9, parameter 5 reflects 
      the equivalent cell rate in cell/s for this connection as determined by 
      the Connection Admission Control (CAC) algorithm. The 
      equivalent cell rate is useful in determining the admission 
      characteristics of this connection."
::= { atmIfVptTm 451 }

atmIfVptTmTxTdpEntry OBJECT-TYPE
   SYNTAX     AtmIfVptTmTxTdpEntry
   ACCESS     not-accessible
   STATUS     mandatory
   DESCRIPTION
     "An entry in the atmIfVptTmTxTdpTable."
   INDEX {
      atmIfIndex,
      atmIfVptIndex,
      atmIfVptTmIndex,
      atmIfVptTmTxTdpIndex }
::= { atmIfVptTmTxTdpTable 1 }

AtmIfVptTmTxTdpEntry ::= SEQUENCE {
   atmIfVptTmTxTdpIndex
      Integer32,
   atmIfVptTmTxTdpValue
      Unsigned32 }

atmIfVptTmTxTdpIndex OBJECT-TYPE
   SYNTAX     Integer32 (1..5)
   ACCESS     not-accessible
   STATUS     mandatory
   DESCRIPTION
     "This variable represents the atmIfVptTmTxTdpTable
      specific index for the atmIfVptTmTxTdpTable."
::= { atmIfVptTmTxTdpEntry 1 }

atmIfVptTmTxTdpValue OBJECT-TYPE
   SYNTAX     Unsigned32 (0..2147483647)
   ACCESS     read-only
   STATUS     mandatory
   DESCRIPTION
     "This variable represents an individual value for the
      atmIfVptTmTxTdpTable."
::= { atmIfVptTmTxTdpEntry 2 }

atmIfVptTmTxQThreshTable OBJECT-TYPE
   SYNTAX     SEQUENCE OF AtmIfVptTmTxQThreshEntry
   ACCESS     not-accessible
   STATUS     mandatory
   DESCRIPTION
     "This attribute indicates the queue limit and the discard thresholds 
      for the transmit queue of this connection. 
      
      If this connection has unshapedTransmitQueueing attribute 
      displayed as common, this attribute displays the thresholds of the 
      common queue. If this connection has unshapedTransmitQueueing 
      attribute displayed as perVc or as notApplicable, this attribute 
      displays the thresholds of the per-VC queue.
      
      The first element indicates the queue limit. 
      
      The second element is the threshold that marks the transition from 
      congestion state 1 to congestion state 0. This is the threshold at 
      which traffic with discard priority (DP) = 1 is discarded. This 
      threshold is set at approximately 90 percent of the first parameter, 
      the operational queue limit.
      
      The third element is the threshold that marks the transition from 
      congestion state 2 to congestion state 1. This is the threshold at 
      which traffic with DP = 2 is discarded. This threshold is set at 
      approximately 75 percent of the first parameter, the operational 
      queue limit.
      
      The fourth element is the threshold that marks the transition from 
      congestion state 3 to congestion state 2. This is the threshold at 
      which traffic with DP = 3 is discarded. This threshold is set at 
      approximately 35 percent of the first parameter, the operational 
      queue limit.
      
      This attribute does not apply to basic Vpts."
::= { atmIfVptTm 452 }

atmIfVptTmTxQThreshEntry OBJECT-TYPE
   SYNTAX     AtmIfVptTmTxQThreshEntry
   ACCESS     not-accessible
   STATUS     mandatory
   DESCRIPTION
     "An entry in the atmIfVptTmTxQThreshTable."
   INDEX {
      atmIfIndex,
      atmIfVptIndex,
      atmIfVptTmIndex,
      atmIfVptTmTxQThreshIndex }
::= { atmIfVptTmTxQThreshTable 1 }

AtmIfVptTmTxQThreshEntry ::= SEQUENCE {
   atmIfVptTmTxQThreshIndex
      Integer32,
   atmIfVptTmTxQThreshValue
      Unsigned32 }

atmIfVptTmTxQThreshIndex OBJECT-TYPE
   SYNTAX     Integer32 (0..3)
   ACCESS     not-accessible
   STATUS     mandatory
   DESCRIPTION
     "This variable represents the atmIfVptTmTxQThreshTable
      specific index for the atmIfVptTmTxQThreshTable."
::= { atmIfVptTmTxQThreshEntry 1 }

atmIfVptTmTxQThreshValue OBJECT-TYPE
   SYNTAX     Unsigned32 (0..30720)
   ACCESS     read-only
   STATUS     mandatory
   DESCRIPTION
     "This variable represents an individual value for the
      atmIfVptTmTxQThreshTable."
::= { atmIfVptTmTxQThreshEntry 2 }

atmIfVptTmRxTdpTable OBJECT-TYPE
   SYNTAX     SEQUENCE OF AtmIfVptTmRxTdpEntry
   ACCESS     not-accessible
   STATUS     mandatory
   DESCRIPTION
     "This attribute is a vector of four traffic parameters whose meanings 
      are defined by the rxTrafficDescType attribute. The values of peak 
      cell rate (PCR), sustained cell rate (SCR), minimum cell rate 
      (MCR) are expressed in cell/s. Maximum burst size (MBS) is 
      expressed in cells. Cell delay variation tolerance (CDVT) is 
      expressed in microseconds.
      
      When rxTrafficDescType is 1 or 2, none of the parameters are used.
      
      When rxTrafficDescType is 3, parameter 1 represents the PCR for 
      CLP equal to 0 and 1 traffic; parameter 4 represents the CDVT.
      
      When rxTrafficDescType is 4, parameter 1 represents the PCR for 
      CLP equal to 0 and 1 traffic; parameter 2 represents the PCR for 
      CLP equal to 0 traffic with cell discard; parameter 4 represents the 
      CDVT.
      
      When rxTrafficDescType is 5, parameter 1 represents the PCR for 
      CLP equal to 0 and 1 traffic; parameter 2 represents the PCR for 
      CLP equal to 0 traffic with cell tagging; parameter 4 represents the 
      CDVT.
      
      When rxTrafficDescType is 6, parameter 1 represents the PCR for 
      CLP equal to 0 and 1 traffic; parameter 2 represents the SCR for 
      CLP equal to 0 and 1 traffic; parameter 3 represents the MBS for 
      CLP equal to 0 and 1 traffic; parameter 4 represents the CDVT. 
      
      When rxTrafficDescType is 7, parameter 1 represents the PCR for 
      CLP equal to 0 and 1 traffic; parameter 2 represents the SCR for 
      CLP equal to 0 traffic with cell discard; parameter 3 represents the 
      MBS for CLP equal to 0 traffic; parameter 4 represents the CDVT.
      
      When rxTrafficDescType is 8, parameter 1 represents the PCR for 
      CLP equal to 0 and 1 traffic; parameter 2 represents the SCR for 
      CLP equal to 0 traffic with cell tagging; parameter 3 represents the 
      MBS for CLP equal to 0 traffic; parameter 4 represents the CDVT. 
      
      When rxTrafficDescType is 9, parameter 1 represents the PCR; 
      parameter 2 represents CDVT; parameter 3 represents the MCR; 
      parameter 4 indicates the instantaneous rate at which dynamic 
      generic cell rate algorithm (DGCRA) is in effect. 
      
      If upc is disabled for this connection, the values of PCR, SCR, 
      MBS and CDVT are the provisioned parameters.
      
      If upc is enabled, the values of PCR, SCR, MBS, and CDVT are 
      exactly the values used by the usage parameter control hardware in 
      policing the arriving traffic. These may vary slightly from the 
      provisioned values due to granularity of the hardware. In the case 
      where the PCR is equal to the SCR, the effective MBS is zero."
::= { atmIfVptTm 453 }

atmIfVptTmRxTdpEntry OBJECT-TYPE
   SYNTAX     AtmIfVptTmRxTdpEntry
   ACCESS     not-accessible
   STATUS     mandatory
   DESCRIPTION
     "An entry in the atmIfVptTmRxTdpTable."
   INDEX {
      atmIfIndex,
      atmIfVptIndex,
      atmIfVptTmIndex,
      atmIfVptTmRxTdpIndex }
::= { atmIfVptTmRxTdpTable 1 }

AtmIfVptTmRxTdpEntry ::= SEQUENCE {
   atmIfVptTmRxTdpIndex
      Integer32,
   atmIfVptTmRxTdpValue
      Unsigned32 }

atmIfVptTmRxTdpIndex OBJECT-TYPE
   SYNTAX     Integer32 (1..4)
   ACCESS     not-accessible
   STATUS     mandatory
   DESCRIPTION
     "This variable represents the atmIfVptTmRxTdpTable
      specific index for the atmIfVptTmRxTdpTable."
::= { atmIfVptTmRxTdpEntry 1 }

atmIfVptTmRxTdpValue OBJECT-TYPE
   SYNTAX     Unsigned32 (0..2147483647)
   ACCESS     read-only
   STATUS     mandatory
   DESCRIPTION
     "This variable represents an individual value for the
      atmIfVptTmRxTdpTable."
::= { atmIfVptTmRxTdpEntry 2 }

atmIfVptTmTqpTable OBJECT-TYPE
   SYNTAX     SEQUENCE OF AtmIfVptTmTqpEntry
   ACCESS     not-accessible
   STATUS     mandatory
   DESCRIPTION
     "This attribute is a vector of three elements that indicate the quality 
      of service parameters for the forward direction for this connection. 
      This attribute is used for SPVC and SVC connections on a PNNI 
      interface.
      
      The cdv element indicates the acceptable peak-to-peak Cell Delay 
      Variation (CDV) of real-time connections (CBR and rt-VBR). 
      
      The ctd element indicates the acceptable maximum Cell Transfer 
      Delay (maxCtd) of real-time connections (CBR and rt-VBR). 
      
      The clr element indicates the acceptable Cell Loss Ratio (CLR) of 
      CBR, rt-VBR, and nrt-VBR connections."
::= { atmIfVptTm 454 }

atmIfVptTmTqpEntry OBJECT-TYPE
   SYNTAX     AtmIfVptTmTqpEntry
   ACCESS     not-accessible
   STATUS     mandatory
   DESCRIPTION
     "An entry in the atmIfVptTmTqpTable."
   INDEX {
      atmIfIndex,
      atmIfVptIndex,
      atmIfVptTmIndex,
      atmIfVptTmTqpIndex }
::= { atmIfVptTmTqpTable 1 }

AtmIfVptTmTqpEntry ::= SEQUENCE {
   atmIfVptTmTqpIndex
      INTEGER,
   atmIfVptTmTqpValue
      Unsigned32 }

atmIfVptTmTqpIndex OBJECT-TYPE
   SYNTAX     INTEGER  {
                 cdv(0),
                 ctd(1),
                 clr(2) }
   ACCESS     not-accessible
   STATUS     mandatory
   DESCRIPTION
     "This variable represents the atmIfVptTmTqpTable
      specific index for the atmIfVptTmTqpTable."
::= { atmIfVptTmTqpEntry 1 }

atmIfVptTmTqpValue OBJECT-TYPE
   SYNTAX     Unsigned32 (0..2147483647)
   ACCESS     read-only
   STATUS     mandatory
   DESCRIPTION
     "This variable represents an individual value for the
      atmIfVptTmTqpTable."
::= { atmIfVptTmTqpEntry 2 }

atmIfVptTmRqpTable OBJECT-TYPE
   SYNTAX     SEQUENCE OF AtmIfVptTmRqpEntry
   ACCESS     not-accessible
   STATUS     mandatory
   DESCRIPTION
     "This attribute is a vector of three elements that indicate the quality 
      of service parameters for the backward direction for this 
      connection. This attribute is used for SPVC and SVC connections 
      on a PNNI interface.
      
      The cdv element indicates the acceptable peak-to-peak Cell Delay 
      Variation (CDV) of real-time connections (CBR and rt-VBR). 
      
      The ctd element indicates the acceptable maximum Cell Transfer 
      Delay (maxCtd) of real-time connections (CBR and rt-VBR). 
      
      The clr element indicates the acceptable Cell Loss Ratio (CLR) of 
      CBR, rt-VBR, and nrt-VBR connections."
::= { atmIfVptTm 455 }

atmIfVptTmRqpEntry OBJECT-TYPE
   SYNTAX     AtmIfVptTmRqpEntry
   ACCESS     not-accessible
   STATUS     mandatory
   DESCRIPTION
     "An entry in the atmIfVptTmRqpTable."
   INDEX {
      atmIfIndex,
      atmIfVptIndex,
      atmIfVptTmIndex,
      atmIfVptTmRqpIndex }
::= { atmIfVptTmRqpTable 1 }

AtmIfVptTmRqpEntry ::= SEQUENCE {
   atmIfVptTmRqpIndex
      INTEGER,
   atmIfVptTmRqpValue
      Unsigned32 }

atmIfVptTmRqpIndex OBJECT-TYPE
   SYNTAX     INTEGER  {
                 cdv(0),
                 ctd(1),
                 clr(2) }
   ACCESS     not-accessible
   STATUS     mandatory
   DESCRIPTION
     "This variable represents the atmIfVptTmRqpTable
      specific index for the atmIfVptTmRqpTable."
::= { atmIfVptTmRqpEntry 1 }

atmIfVptTmRqpValue OBJECT-TYPE
   SYNTAX     Unsigned32 (0..2147483647)
   ACCESS     read-only
   STATUS     mandatory
   DESCRIPTION
     "This variable represents an individual value for the
      atmIfVptTmRqpTable."
::= { atmIfVptTmRqpEntry 2 }


-- AtmIf/n Vpc/vpi Tm AvailableBitRate, 
-- AtmIf/n Vcc/vpi.vci Tm AvailableBitRate,
-- AtmIf/n Vpt/vpi Tm AvailableBitRate,
-- AtmIf/n Vpt/vpi Vcc/vci Tm AvailableBitRate
-- This component contains ABR-related operational attributes of a 
-- connection. It is dynamically created for connections where the 
-- atmServiceCategory is availableBitRate, and where 
-- abrConnectionType is sourceDest or virtualSourceDest.

atmIfVptTmAbr OBJECT IDENTIFIER ::= { atmIfVptTm 2 }



atmIfVptTmAbrRowStatusTable OBJECT-TYPE
   SYNTAX     SEQUENCE OF AtmIfVptTmAbrRowStatusEntry
   ACCESS     not-accessible
   STATUS     mandatory
   DESCRIPTION
     "This entry controls the addition and deletion of 
      atmIfVptTmAbr components."
::= { atmIfVptTmAbr 1 }

atmIfVptTmAbrRowStatusEntry OBJECT-TYPE
   SYNTAX     AtmIfVptTmAbrRowStatusEntry
   ACCESS     not-accessible
   STATUS     mandatory
   DESCRIPTION
     "A single entry in the table represents a single 
      atmIfVptTmAbr component."
   INDEX {
      atmIfIndex,
      atmIfVptIndex,
      atmIfVptTmIndex,
      atmIfVptTmAbrIndex }
::= { atmIfVptTmAbrRowStatusTable 1 }

AtmIfVptTmAbrRowStatusEntry ::= SEQUENCE {
   atmIfVptTmAbrRowStatus
      RowStatus,
   atmIfVptTmAbrComponentName
      DisplayString,
   atmIfVptTmAbrStorageType
      StorageType,
   atmIfVptTmAbrIndex
      NonReplicated }

atmIfVptTmAbrRowStatus OBJECT-TYPE
   SYNTAX     RowStatus 
   ACCESS     read-only
   STATUS     mandatory
   DESCRIPTION
     "This variable is used as the basis for SNMP naming of
      atmIfVptTmAbr components.
      These components cannot be added nor deleted."
::= { atmIfVptTmAbrRowStatusEntry 1 }

atmIfVptTmAbrComponentName OBJECT-TYPE
   SYNTAX     DisplayString 
   ACCESS     read-only
   STATUS     mandatory
   DESCRIPTION
     "This variable provides the component's string name for
      use with the ASCII Console Interface"
::= { atmIfVptTmAbrRowStatusEntry 2 }

atmIfVptTmAbrStorageType OBJECT-TYPE
   SYNTAX     StorageType 
   ACCESS     read-only
   STATUS     mandatory
   DESCRIPTION
     "This variable represents the storage type value for the
      atmIfVptTmAbr tables."
::= { atmIfVptTmAbrRowStatusEntry 4 }

atmIfVptTmAbrIndex OBJECT-TYPE
   SYNTAX     NonReplicated 
   ACCESS     not-accessible
   STATUS     mandatory
   DESCRIPTION
     "This variable represents the index for the atmIfVptTmAbr tables."
::= { atmIfVptTmAbrRowStatusEntry 10 }

atmIfVptTmAbrOperTable OBJECT-TYPE
   SYNTAX     SEQUENCE OF AtmIfVptTmAbrOperEntry
   ACCESS     not-accessible
   STATUS     mandatory
   DESCRIPTION
     "This group contains operational attributes for connections using 
      ABR service category."
::= { atmIfVptTmAbr 110 }

atmIfVptTmAbrOperEntry OBJECT-TYPE
   SYNTAX     AtmIfVptTmAbrOperEntry
   ACCESS     not-accessible
   STATUS     mandatory
   DESCRIPTION
     "An entry in the atmIfVptTmAbrOperTable."
   INDEX {
      atmIfIndex,
      atmIfVptIndex,
      atmIfVptTmIndex,
      atmIfVptTmAbrIndex }
::= { atmIfVptTmAbrOperTable 1 }

AtmIfVptTmAbrOperEntry ::= SEQUENCE {
   atmIfVptTmAbrInitialCellRate
      Unsigned32,
   atmIfVptTmAbrTransientBufferExposure
      Unsigned32,
   atmIfVptTmAbrFixedRoundTripTime
      Unsigned32,
   atmIfVptTmAbrRateDecreaseFactor
      Unsigned32,
   atmIfVptTmAbrRateIncreaseFactor
      Unsigned32,
   atmIfVptTmAbrMaxCellPerRmCell
      Unsigned32,
   atmIfVptTmAbrMaxTimeBetweenRmCell
      Unsigned32,
   atmIfVptTmAbrCutoffDecreaseFactor
      Unsigned32,
   atmIfVptTmAbrAcrDecreaseTimeFactor
      Unsigned32,
   atmIfVptTmAbrForwardRmCellLimit
      Unsigned32,
   atmIfVptTmAbrTxRateChangeInfo
      INTEGER,
   atmIfVptTmAbrAcrRateChangeInfo
      INTEGER,
   atmIfVptTmAbrTxFwdRmCells
      Unsigned32,
   atmIfVptTmAbrRxEfci
      INTEGER,
   atmIfVptTmAbrBrmRateChangeInfo
      OCTET STRING,
   atmIfVptTmAbrBrmExplicitRate
      Unsigned32 }

atmIfVptTmAbrInitialCellRate OBJECT-TYPE
   SYNTAX     Unsigned32 (0..16777215)
   ACCESS     read-only
   STATUS     mandatory
   DESCRIPTION
     "This attribute is applicable and is displayed only for connections for 
      which the operational Tm abrConnectionType is displayed as 
      sourceDest or virtualSourceDest. 
      
      This attribute indicates the Initial Cell Rate (ICR) parameter for this 
      connection. ICR is the rate at which a source should send initially 
      and after an idle period.
      
      For nailed-up connections, this attribute is determined by the 
      provisioned value of the initialCellRate attribute. For signalled 
      connections, it is indicated in the ABR Setup Parameters 
      Information Element.
      
      The ICR for a connection is a value between the MCR and the PCR. 
      Furthermore, ICR has an upper bound determined by the 
      transientBufferExposure divided by fixedRoundTripTime."
::= { atmIfVptTmAbrOperEntry 10 }

atmIfVptTmAbrTransientBufferExposure OBJECT-TYPE
   SYNTAX     Unsigned32 (0..16777215)
   ACCESS     read-only
   STATUS     mandatory
   DESCRIPTION
     "This attribute is applicable and is displayed only for connections for 
      which the operational Tm abrConnectionType is displayed as 
      sourceDest or virtualSourceDest. 
      
      This attribute indicates the Transient Buffer Exposure (TBE) for 
      this connection. TBE is the negotiated number of cells that the 
      network would like to limit the resource to send during start-up 
      periods, before the first Resource Management (RM) cell returns.
      
      For nailed-up connections, this attribute is determined by the 
      provisioned value of the transientBufferExposure attribute. For 
      signalled connections, it is indicated in the ABR Setup Parameters 
      Information Element."
::= { atmIfVptTmAbrOperEntry 11 }

atmIfVptTmAbrFixedRoundTripTime OBJECT-TYPE
   SYNTAX     Unsigned32 (0..16700000)
   ACCESS     read-only
   STATUS     mandatory
   DESCRIPTION
     "This attribute is applicable and is displayed only for connections for 
      which the operational Tm abrConnectionType is displayed as 
      sourceDest or virtualSourceDest. 
      
      This attribute indicates the Fixed Round-Trip Time (FRTT) 
      parameter for this connection. FRTT is the sum of the fixed and 
      propagation delays from the source to a destination and back.
      
      For nailed-up connections, this attribute is determined by the 
      provisioned value of the fixedRoundTripTime attribute. For 
      signalled connections, it is indicated in the ABR Setup Parameters 
      Information Element."
::= { atmIfVptTmAbrOperEntry 12 }

atmIfVptTmAbrRateDecreaseFactor OBJECT-TYPE
   SYNTAX     Unsigned32 (0..15)
   ACCESS     read-only
   STATUS     mandatory
   DESCRIPTION
     "This attribute is applicable and is displayed only for connections for 
      which the operational Tm abrConnectionType is displayed as 
      sourceDest or virtualSourceDest. 
      
      This attribute indicates the Rate Decrease Factor (RDF) for this 
      connection. The RDF value is computed by using the operational 
      value of this attribute, n, as 2 to the inverse power n. For example, if 
      the value of this attribute is 8, RDF is 2E-8 = 1/256.
      
      RDF controls the amount by which the cell transmission rate may 
      decrease upon receipt of a backward Resource Management (RM) 
      cell. For example, if a backward RM cell is received with the 
      Congestion Indication (CI) field set to 1, the Allowed Cell Rate 
      (ACR) value would be reduced by the amount (RDF*ACR). The 
      ACR is not allowed to fall below the Minimum Cell Rate (MCR), in 
      which case the ACR is set to MCR.
      
      For nailed-up connections, this attribute is determined by the 
      provisioned value of the rateDecreaseFactor attribute. For signalled 
      connections, it is indicated in the ABR Setup Parameters 
      Information Element."
::= { atmIfVptTmAbrOperEntry 13 }

atmIfVptTmAbrRateIncreaseFactor OBJECT-TYPE
   SYNTAX     Unsigned32 (0..15)
   ACCESS     read-only
   STATUS     mandatory
   DESCRIPTION
     "This attribute is applicable and is displayed only for connections for 
      which the operational Tm abrConnectionType is displayed as 
      sourceDest or virtualSourceDest. 
      
      This attribute indicates the Rate Increase Factor (RIF) for this 
      connection. The RIF value is computed by using the operational 
      value of this attribute, n, as 2 to the inverse power n. For example, if 
      the value of this attribute is 6, RIF is 2E-6 = 1/64.
      
      RIF controls the amount by which the cell transmission rate may 
      increase upon receipt of a backward Resource Management (RM) 
      cell. For example, if a backward RM cell is received with the 
      Congestion Indication (CI) and the No Increase (NI) fields both set 
      to 0, the Allowed Cell Rate (ACR) value would be increased by the 
      amount (RIF*ACR). The ACR is not allowed to exceed the Peak 
      Cell Rate (PCR), in which case the ACR is set to PCR.
      
      For nailed-up connections, this attribute is determined by the 
      provisioned value of the rateIncreaseFactor attribute. For signalled 
      connections, it is indicated in the ABR Setup Parameters 
      Information Element."
::= { atmIfVptTmAbrOperEntry 14 }

atmIfVptTmAbrMaxCellPerRmCell OBJECT-TYPE
   SYNTAX     Unsigned32 (2 | 4 | 8 | 16 | 32 | 64 | 128 | 256)
   ACCESS     read-only
   STATUS     mandatory
   DESCRIPTION
     "This attribute is applicable and is displayed only for connections for 
      which the operational Tm abrConnectionType is displayed as 
      sourceDest or virtualSourceDest. 
      
      This attribute indicates the maximum number of cells an ABR 
      source may transmit for each forward Resource Management (RM) 
      cell. The count of the cells transmitted includes data cells, OAM 
      cells, backward RM cells, and the forward RM cell.
      
      For nailed-up connections, this attribute is determined by the 
      provisioned value of the maxCellsPerRmCell attribute. For 
      signalled connections, it is indicated in the ABR Additional 
      Parameters Information Element."
::= { atmIfVptTmAbrOperEntry 15 }

atmIfVptTmAbrMaxTimeBetweenRmCell OBJECT-TYPE
   SYNTAX     Unsigned32 (781 | 1563 | 3125 | 6250 | 12500 | 25000 | 50000 | 100000)
   ACCESS     read-only
   STATUS     mandatory
   DESCRIPTION
     "This attribute is applicable and is displayed only for connections for 
      which the operational Tm abrConnectionType is displayed as 
      sourceDest or virtualSourceDest. 
      
      This attribute indicates the TRM parameter for this connection.
      
      TRM provides an upper bound on the time interval between forward 
      Resource Management (RM) cells for an ABR source. Since the last 
      forward RM cell was sent, if at least TRM time has elapsed since 
      and at least 2 other cells have been sent, the next cell to be 
      transmitted would be a forward RM cell.
      
      For nailed-up connections, this attribute is determined by the 
      provisioned value of the maxTimeBetweenRmCell attribute. For 
      signalled connections, it is indicated in the ABR Additional 
      Parameters Information Element."
::= { atmIfVptTmAbrOperEntry 16 }

atmIfVptTmAbrCutoffDecreaseFactor OBJECT-TYPE
   SYNTAX     Unsigned32 (0 | 1 | 2 | 4 | 8 | 16 | 32 | 64)
   ACCESS     read-only
   STATUS     mandatory
   DESCRIPTION
     "This attribute is applicable and is displayed only for connections for 
      which the operational Tm abrConnectionType is displayed as 
      sourceDest or virtualSourceDest. 
      
      This attribute indicates the Cutoff Decrease Factor (CDF) parameter 
      for this connection. When the value of this attribute is non-zero, 
      CDF is computed as the inverse of the value. For example, if the 
      value is 32, the value of CDF is 1/32. When the value of this 
      attribute is 0, CDF is also zero.
      
      CDF controls the decrease in the Allowed Cell Rate (ACR) 
      associated with the forwardRmCellLimit attribute, the limit of the 
      number of forward Resource Management (RM) cells which may 
      be sent in the absence of received backward RM cells. When this 
      limit is crossed, the ACR value would be decreased by the amount 
      (CDF*ACR). The ACR is not allowed to fall below the Minimum 
      Cell Rate (MCR), in which case the ACR is set to MCR.
      
      For nailed-up connections, this attribute is determined by the 
      provisioned value of the cutoffDecreaseFactor attribute. For 
      signalled connections, it is indicated in the ABR Additional 
      Parameters Information Element."
::= { atmIfVptTmAbrOperEntry 17 }

atmIfVptTmAbrAcrDecreaseTimeFactor OBJECT-TYPE
   SYNTAX     Unsigned32 (0..1023)
   ACCESS     read-only
   STATUS     mandatory
   DESCRIPTION
     "This attribute is applicable and is displayed only for connections for 
      which the operational Tm abrConnectionType is displayed as 
      sourceDest or virtualSourceDest. 
      
      This attribute indicates the Allowed Cell Rate Decrease Time Factor 
      (ADTF) parameter for this connection.
      
      ADTF is the time interval permitted between sending forward 
      Resource Management (RM) cells before the Allowed Cell Rate 
      (ACR) is decreased to initialCellRate. In other words, if the source 
      does not transit a forward RM cell for the period specified by adtf, it 
      reduces its ACR to the value of its initialCellRate.
      
      For nailed-up connections, this attribute is determined by the 
      provisioned value of the acrDecreaseTimeFactor attribute. For 
      signalled connections, it is indicated in the ABR Additional 
      Parameters Information Element."
::= { atmIfVptTmAbrOperEntry 18 }

atmIfVptTmAbrForwardRmCellLimit OBJECT-TYPE
   SYNTAX     Unsigned32 (1 | 3 | 7 | 15 | 31 | 63 | 127 | 255 | 511 | 1023 | 2047 | 4095)
   ACCESS     read-only
   STATUS     mandatory
   DESCRIPTION
     "This attribute is applicable and is displayed only for connections for 
      which the operational Tm abrConnectionType is displayed as 
      sourceDest or virtualSourceDest. 
      
      This attribute indicates the CRM parameter for this connection.
      
      CRM is the limit of the number of forward Resource Management 
      (RM) cells which may be sent in the absence of received backward 
      RM cells. When this limit is crossed, the Allowed Cell Rate (ACR) 
      value would be decreased by the amount (CDF*ACR), where CDF 
      is determined by the cutoffDecreaseFactor. The ACR is not allowed 
      to fall below the Minimum Cell Rate (MCR), in which case the 
      ACR is set to MCR.
      
      The value of CRM is obtained as transientBufferExposure divided 
      by maxCellsPerRmCell."
::= { atmIfVptTmAbrOperEntry 19 }

atmIfVptTmAbrTxRateChangeInfo OBJECT-TYPE
   SYNTAX     INTEGER  {
                 congestionIndicated(0),
                 noIncreaseIndicated(1),
                 explicitRateIndicated(2) }
   ACCESS     read-only
   STATUS     obsolete
   DESCRIPTION
     "THIS ATTRIBUTE IS HISTORICAL:This attribute indicates the 
      rate change information put into the last forward Resource 
      Management (RM) cell turned around as a backward-RM cell. For 
      connections configured as an ABR Source or Destination, the 
      turned around backward-RM cell is sent over the interface. For 
      connections configured as an ABR Virtual Source or Virtual 
      Destination, the turned around backward-RM cell is sent over the 
      backplane."
::= { atmIfVptTmAbrOperEntry 20 }

atmIfVptTmAbrAcrRateChangeInfo OBJECT-TYPE
   SYNTAX     INTEGER  {
                 noChange(0),
                 decreasedByRdf(1),
                 increasedByRif(2),
                 setToExplicitRate(3),
                 notApplicable(15) }
   ACCESS     read-only
   STATUS     mandatory
   DESCRIPTION
     "This attribute is applicable and is displayed only for connections for 
      which the operational Tm abrConnectionType is displayed as 
      sourceDest or virtualSourceDest. 
      
      This attribute indicates the type of change in the Allowed Cell Rate 
      (ACR) as a result of the information in the last backward Resource 
      Management (B-RM) cell received from the interface.
      
      This attribute value is only applicable when the Vcc Tm or Vpc Tm 
      abrConnectionType attribute is sourceDest or VirtualSourceDest. 
      In all other cases, this attribute value is notApplicable.
      
      A value of noChange indicates that the rate did not change as a 
      result of the last backward RM cell received.
      
      A value of decreasedByRdf or increasedByRif indicates that the 
      ACR was increased or decreased by the corresponding factor. This 
      change is as a result of the CI or NI bit setting in the last backward 
      RM cell, or an ADTF timeout.
      
      A value of setToExplicitRate indicates that the ACR was set to the 
      ER value in the last backward RM cell."
::= { atmIfVptTmAbrOperEntry 21 }

atmIfVptTmAbrTxFwdRmCells OBJECT-TYPE
   SYNTAX     Unsigned32 (0..4095)
   ACCESS     read-only
   STATUS     mandatory
   DESCRIPTION
     "This attribute is applicable and is displayed only for connections for 
      which the operational Tm abrConnectionType is displayed as 
      sourceDest or virtualSourceDest. 
      
      This attribute counts the number of forward Resource Management 
      (RM) cells sent over the interface since the last backward RM-cell 
      was received from the interface. If the value of this attribute is 
      greater than or equal to the value of forwardRmCellLimit, the 
      Allowed Cell Rate (ACR) value would be decreased by the amount 
      (CDF*ACR), where CDF is determined by the 
      cutoffDecreaseFactor.
      
      This counter is reset to zero each time a backward-RM cell is 
      received.
      
      This counter does not wrap to zero if it reaches its maximum value 
      of 4095 in order to indicate that no backward RM cell has been 
      received."
::= { atmIfVptTmAbrOperEntry 22 }

atmIfVptTmAbrRxEfci OBJECT-TYPE
   SYNTAX     INTEGER  {
                 notIndicated(0),
                 indicated(1) }
   ACCESS     read-only
   STATUS     mandatory
   DESCRIPTION
     "This attribute is applicable and is displayed only for connections for 
      which the operational Tm abrConnectionType is displayed as 
      sourceDest or virtualSourceDest. 
      
      This attribute indicates the value of the Explicit Forward 
      Congestion Indication (EFCI) bit of the last data cell received from 
      the interface.
      
      When a forward Resource Management (RM) cell is turned around 
      as a backward-RM cell, the Congestion Indication (CI) field of the 
      backward-RM cell is set to 1, if the value of this attribute is 
      indicated.
      
      This attribute is set to notIndicated each time a backward-RM cell 
      is transmitted."
::= { atmIfVptTmAbrOperEntry 23 }

atmIfVptTmAbrBrmRateChangeInfo OBJECT-TYPE
   SYNTAX     OCTET STRING (SIZE (1))
   ACCESS     read-only
   STATUS     mandatory
   DESCRIPTION
     "This attribute is applicable and is displayed only for connections for 
      which the operational Tm abrConnectionType is displayed as 
      sourceDest, virtualSourceDest or explicitRate. 
      
      This attribute indicates the values of key fields which affect the rate 
      change. These fields are from the most recent Backward Resource 
      Management (B-RM) cell on this connection. These fields may have 
      been set by a connection point at some switch prior to the B-RM 
      cell arriving at this connection point. 
      
      A value of ci indicates that the Congestion Indication (CI) field is 
      set in the B-RM cell. A value of ni indicates that the No Increase 
      (NI) field is set in the B-RM cell. A value of er indicates that a rate 
      decrease is indicated by the Explicit Rate in the B-RM cell having a 
      value lower than the Current Cell Rate (CCR) field in the B-RM 
      cell. The actual explicit rate from the B-RM cell is shown in the 
      brmEr attribute of this component.

      Description of bits:
      ci(0)
      ni(1)
      er(2)"
::= { atmIfVptTmAbrOperEntry 24 }

atmIfVptTmAbrBrmExplicitRate OBJECT-TYPE
   SYNTAX     Unsigned32 (0..16777215)
   ACCESS     read-only
   STATUS     mandatory
   DESCRIPTION
     "This attribute is applicable and is displayed only for connections for 
      which the operational Tm abrConnectionType is displayed as 
      sourceDest, virtualSourceDest or explicitRate. 
      
      This attribute indicates the value of the Explicit Rate field from the 
      most recent Backward Resource Management (B-RM) cell on this 
      connection. This is the rate from the B-RM cell which may be 
      different from the explicit rate (ER) offered at this connection point. 
      Specifically, this attribute may indicate the ER which has been set in 
      the B-RM cell by some connection point before the B-RM cell 
      arrived at this connection point."
::= { atmIfVptTmAbrOperEntry 25 }


-- AtmIf/n Vpt/vpi VirtualChannelConnection/vci 
-- This component represents a virtual channel connection terminated 
-- by a Virtual Path Terminator (VPT).
-- 
-- For Vccs beneath Vpts, the instance value defines the VCI value for 
-- this connectionfor example, Vpt/16 Vcc/32 would define a 
-- connection with a VPI of 16, and a VCI of 32. The VPI value of the 
-- Vcc is inherited from the parent Vpt.
-- 
-- The VPI can be in the range of 0 to 4095 and the VCI can be in the 
-- range of 0 to 65535. Note that a Vcc instance of 0.0 is invalid as 
-- defined in the ATM Forum. Thus, the combination of Vpt/0 Vcc/0 is 
-- also invalid.

atmIfVptVcc OBJECT IDENTIFIER ::= { atmIfVpt 20 }



atmIfVptVccRowStatusTable OBJECT-TYPE
   SYNTAX     SEQUENCE OF AtmIfVptVccRowStatusEntry
   ACCESS     not-accessible
   STATUS     mandatory
   DESCRIPTION
     "This entry controls the addition and deletion of 
      atmIfVptVcc components."
::= { atmIfVptVcc 1 }

atmIfVptVccRowStatusEntry OBJECT-TYPE
   SYNTAX     AtmIfVptVccRowStatusEntry
   ACCESS     not-accessible
   STATUS     mandatory
   DESCRIPTION
     "A single entry in the table represents a single 
      atmIfVptVcc component."
   INDEX {
      atmIfIndex,
      atmIfVptIndex,
      atmIfVptVccIndex }
::= { atmIfVptVccRowStatusTable 1 }

AtmIfVptVccRowStatusEntry ::= SEQUENCE {
   atmIfVptVccRowStatus
      RowStatus,
   atmIfVptVccComponentName
      DisplayString,
   atmIfVptVccStorageType
      StorageType,
   atmIfVptVccIndex
      Integer32 }

atmIfVptVccRowStatus OBJECT-TYPE
   SYNTAX     RowStatus 
   ACCESS     read-write
   STATUS     mandatory
   DESCRIPTION
     "This variable is used as the basis for SNMP naming of
      atmIfVptVcc components.
      These components can be added and deleted."
::= { atmIfVptVccRowStatusEntry 1 }

atmIfVptVccComponentName OBJECT-TYPE
   SYNTAX     DisplayString 
   ACCESS     read-only
   STATUS     mandatory
   DESCRIPTION
     "This variable provides the component's string name for
      use with the ASCII Console Interface"
::= { atmIfVptVccRowStatusEntry 2 }

atmIfVptVccStorageType OBJECT-TYPE
   SYNTAX     StorageType 
   ACCESS     read-only
   STATUS     mandatory
   DESCRIPTION
     "This variable represents the storage type value for the
      atmIfVptVcc tables."
::= { atmIfVptVccRowStatusEntry 4 }

atmIfVptVccIndex OBJECT-TYPE
   SYNTAX     Integer32 (0..65535)
   ACCESS     not-accessible
   STATUS     mandatory
   DESCRIPTION
     "This variable represents the index for the atmIfVptVcc tables."
::= { atmIfVptVccRowStatusEntry 10 }

atmIfVptVccStateTable OBJECT-TYPE
   SYNTAX     SEQUENCE OF AtmIfVptVccStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { atmIfVptVcc 100 }

atmIfVptVccStateEntry OBJECT-TYPE
   SYNTAX     AtmIfVptVccStateEntry
   ACCESS     not-accessible
   STATUS     mandatory
   DESCRIPTION
     "An entry in the atmIfVptVccStateTable."
   INDEX {
      atmIfIndex,
      atmIfVptIndex,
      atmIfVptVccIndex }
::= { atmIfVptVccStateTable 1 }

AtmIfVptVccStateEntry ::= SEQUENCE {
   atmIfVptVccAdminState
      INTEGER,
   atmIfVptVccOperationalState
      INTEGER,
   atmIfVptVccUsageState
      INTEGER }

atmIfVptVccAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { atmIfVptVccStateEntry 1 }

atmIfVptVccOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { atmIfVptVccStateEntry 2 }

atmIfVptVccUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { atmIfVptVccStateEntry 3 }

atmIfVptVccOperTable OBJECT-TYPE
   SYNTAX     SEQUENCE OF AtmIfVptVccOperEntry
   ACCESS     not-accessible
   STATUS     mandatory
   DESCRIPTION
     "This group contains operational information for a Vcc, Vpc, or Vpt 
      component."
::= { atmIfVptVcc 110 }

atmIfVptVccOperEntry OBJECT-TYPE
   SYNTAX     AtmIfVptVccOperEntry
   ACCESS     not-accessible
   STATUS     mandatory
   DESCRIPTION
     "An entry in the atmIfVptVccOperTable."
   INDEX {
      atmIfIndex,
      atmIfVptIndex,
      atmIfVptVccIndex }
::= { atmIfVptVccOperTable 1 }

AtmIfVptVccOperEntry ::= SEQUENCE {
   atmIfVptVccConnectionPointType
      INTEGER }

atmIfVptVccConnectionPointType OBJECT-TYPE
   SYNTAX     INTEGER  {
                 connectionEndPoint(0),
                 segmentEndPoint(1),
                 connectingPoint(2),
                 unknown(3) }
   ACCESS     read-only
   STATUS     mandatory
   DESCRIPTION
     "This attribute reflects the role of the connection component at this 
      interface.
      
      A value of connectionEndPoint indicates that user cells, end-to-end 
      OAM cells, and segment OAM cells are processed by the 
      connection component.
      
      A value of segmentEndPoint indicates that user cells and end-to-
      end OAM cells are relayed by the connection component, while 
      segment OAM cells are processed by the connection component.
      
      A value of connectingPoint indicates that user cells, end-to-end 
      OAM cells, and segment OAM cells are relayed by the connection 
      component.
      
      A value of unknown indicates that the connection component is 
      inactive."
::= { atmIfVptVccOperEntry 10 }

atmIfVptVccConnInfoTable OBJECT-TYPE
   SYNTAX     SEQUENCE OF AtmIfVptVccConnInfoEntry
   ACCESS     not-accessible
   STATUS     mandatory
   DESCRIPTION
     "This group contains operational connection characteristics 
      information for a Vcc component."
::= { atmIfVptVcc 115 }

atmIfVptVccConnInfoEntry OBJECT-TYPE
   SYNTAX     AtmIfVptVccConnInfoEntry
   ACCESS     not-accessible
   STATUS     mandatory
   DESCRIPTION
     "An entry in the atmIfVptVccConnInfoTable."
   INDEX {
      atmIfIndex,
      atmIfVptIndex,
      atmIfVptVccIndex }
::= { atmIfVptVccConnInfoTable 1 }

AtmIfVptVccConnInfoEntry ::= SEQUENCE {
   atmIfVptVccDistributionType
      INTEGER,
   atmIfVptVccNumLeaves
      Gauge32,
   atmIfVptVccCallDirection
      INTEGER }

atmIfVptVccDistributionType OBJECT-TYPE
   SYNTAX     INTEGER  {
                 pointToPoint(0),
                 pointToMultipoint(1) }
   ACCESS     read-only
   STATUS     mandatory
   DESCRIPTION
     "This attribute indicates the way data is distributed in the connection.
      
      A value of pointToPoint indicates this connection point is part of a 
      point-to-point connection.
      
      A value of pointToMultipoint indicates this connection point is part 
      of a point-to-multipoint connection."
   DEFVAL     { pointToPoint }
::= { atmIfVptVccConnInfoEntry 11 }

atmIfVptVccNumLeaves OBJECT-TYPE
   SYNTAX     Gauge32 (0..2147483647)
   ACCESS     read-only
   STATUS     mandatory
   DESCRIPTION
     "This attribute indicates the number of destination leaves of the 
      connection. If the distributionType is pointToPoint the value of this 
      attribute is 0."
   DEFVAL     { 0 }
::= { atmIfVptVccConnInfoEntry 12 }

atmIfVptVccCallDirection OBJECT-TYPE
   SYNTAX     INTEGER  {
                 fromLink(0),
                 toLink(1),
                 notApplicable(2) }
   ACCESS     read-only
   STATUS     mandatory
   DESCRIPTION
     "This attribute indicates the direction of the call setup request for an 
      SVC.
      
      A value of fromLink means that the call setup originated from the 
      link.
      
      A value of toLink means that the call setup was directed to the link.
      
      For PVC connections, the value of this attribute is notApplicable.
      
      For SPVC connections, the value of this attribute is notApplicable 
      for Vccs with the SourcePVC and DestinationPVC subcomponents.
      
      For Signalling channels, the value of this attribute is notApplicable."
   DEFVAL     { notApplicable }
::= { atmIfVptVccConnInfoEntry 13 }

atmIfVptVccStatusTable OBJECT-TYPE
   SYNTAX     SEQUENCE OF AtmIfVptVccStatusEntry
   ACCESS     not-accessible
   STATUS     mandatory
   DESCRIPTION
     "This group contains operational status information for a Vcc, Vpc, 
      or Vpt component."
::= { atmIfVptVcc 120 }

atmIfVptVccStatusEntry OBJECT-TYPE
   SYNTAX     AtmIfVptVccStatusEntry
   ACCESS     not-accessible
   STATUS     mandatory
   DESCRIPTION
     "An entry in the atmIfVptVccStatusTable."
   INDEX {
      atmIfIndex,
      atmIfVptIndex,
      atmIfVptVccIndex }
::= { atmIfVptVccStatusTable 1 }

AtmIfVptVccStatusEntry ::= SEQUENCE {
   atmIfVptVccOperStatus
      INTEGER,
   atmIfVptVccLocalFailureCause
      INTEGER,
   atmIfVptVccTroubled
      INTEGER,
   atmIfVptVccSegLinkSideLoopbackState
      INTEGER,
   atmIfVptVccSegSwitchSideLoopbackState
      INTEGER,
   atmIfVptVccEndToEndLoopbackState
      INTEGER,
   atmIfVptVccRxOamCellCongestionState
      INTEGER,
   atmIfVptVccAisState
      INTEGER,
   atmIfVptVccRdiState
      INTEGER }

atmIfVptVccOperStatus OBJECT-TYPE
   SYNTAX     INTEGER  {
                 unknown(0),
                 end2endUp(1),
                 end2endDown(2),
                 localUpEnd2endUnknown(3),
                 localDown(4) }
   ACCESS     read-only
   STATUS     mandatory
   DESCRIPTION
     "This attribute indicates the present operational status of the Vcc, 
      Vpc, or Vpt component. Its value is dependent upon the current state 
      of the segLinkSideLoopbackState and endToEndLoopbackState 
      attributes.
      
      The value is end2endUp when the endToEndLoopbackState is good 
      and the segLinkSideLoopbackState is either good or unknown.
      
      The value is end2endDown when the endToEndLoopbackState is 
      bad and the segLinkSideLoopbackState is either good or unknown.
      
      The value is localUpEnd2endUnknown when the 
      endToEndLoopbackState is unknown and the 
      segLinkSideLoopbackState is good.
      
      The value is localDown when segLinkSideLoopbackState is bad.
      
      The value is localUpEnd2endUnknown when the 
      endToEndLoopbackState is notApplicable and the 
      segLinkSideLoopbackState is good.
      
      The value is unknown when the endToEndLoopbackState is either 
      unknown or notApplicable and the segLinkSideLoopbackState is 
      unknown."
::= { atmIfVptVccStatusEntry 20 }

atmIfVptVccLocalFailureCause OBJECT-TYPE
   SYNTAX     INTEGER  {
                 noFailure(0),
                 localBwLoss(1),
                 portDown(2),
                 notAdmitted(3),
                 appNotRegistered(4),
                 disabledByApp(5),
                 bwReduced(6),
                 vpDown(7) }
   ACCESS     read-only
   STATUS     mandatory
   DESCRIPTION
     "This attribute indicates the failure cause of the Vcc, Vpc, or Vpt 
      component. noFailure indicates that there is currently no 
      bandwidth related failure for this connection. 
      
      portDown indicates that the interface corresponding to the parent 
      AtmIf is down. 
      
      localBwLoss indicates that the Ima corresponding to this AtmIf has 
      lost some, but not all bandwidth, and as a result, this connection has 
      been released.
      
      notAdmitted indicates that this connection has failed to be admitted 
      by the Connection Admission Control (CAC) algorithm.
      
      appNotRegistered indicates that there is no application registered to 
      use this connection. This may be the case, for example when there 
      is a Vcc Test application, but the test has not been started. Check the 
      status of the application to determine why it is not functional.
      
      disabledByApp indicates that the application using this connection 
      has requested that the connection be disabled. An example is a 
      connection used by a trunk application where the trunk has timed 
      out on an attempt to stage. Check the application to determine why 
      it is not fully functional.
      
      bwReduced indicates that this connection is operating in a reduced 
      bandwidth state. It is a bandwidth elastic connection which 
      currently has been allocated less than the requested (equivalent) 
      bandwidth.
      
      vpDown indicates that this connection has been notified of a fault 
      detected at the associated VP-layer. vpDown is applicable for Vpt 
      Vccs only."
::= { atmIfVptVccStatusEntry 25 }

atmIfVptVccTroubled OBJECT-TYPE
   SYNTAX     INTEGER  {
                 no(0),
                 yes(1) }
   ACCESS     read-only
   STATUS     mandatory
   DESCRIPTION
     "This attribute indicates whether or not the connection is in a 
      troubled state. Connections become troubled because of OAM 
      failures; when one of the attributes segLinkSideLoopbackState, 
      segSwitchSideLoopbackState, endToEndLoopbackState, aisState 
      (when receiving AIS cells only) or rdiState go bad, this attribute is 
      set to yes; otherwise it is set to no."
   DEFVAL     { no }
::= { atmIfVptVccStatusEntry 28 }

atmIfVptVccSegLinkSideLoopbackState OBJECT-TYPE
   SYNTAX     INTEGER  {
                 good(0),
                 bad(1),
                 unknown(2),
                 notApplicable(3) }
   ACCESS     read-only
   STATUS     mandatory
   DESCRIPTION
     "This attribute contains the current state of the link-side segment 
      loopback for this connection. Link-side segment loopback cells are 
      transmitted (inserted) by a connection component in the direction of 
      the link (port). The value of this attribute is dependent upon the 
      current setting of the segLinkSideLoopback provisionable attribute, 
      the connection point type as specified by the connectionPointType 
      attribute, and the current loopback state (if applicable).
      
      The value is notApplicable when the connectionPointType is a 
      connectingPoint. 
      
      The value is notApplicable when the distributionType is 
      pointToMultipoint.
      
      The value is good when the segLinkSideLoopback is on, the 
      connectionPointType is a segmentEndPoint or a 
      connectionEndPoint, and the segment link side loopback is 
      working.
      
      The value is bad when the segLinkSideLoopback is on, the 
      connectionPointType is a segmentEndPoint or a 
      connectionEndPoint, and the link side segment loopback is not 
      working.
      
      The value is unknown when the segLinkSideLoopback is off.
      
      The value is unknown when the segLinkSideLoopback is on, the 
      connectionPointType is a segmentEndPoint and the segment switch 
      side loopback has not yet been determined.
      
      The state of this attribute determines, in part, the value of the 
      operStatus attribute."
::= { atmIfVptVccStatusEntry 30 }

atmIfVptVccSegSwitchSideLoopbackState OBJECT-TYPE
   SYNTAX     INTEGER  {
                 good(0),
                 bad(1),
                 unknown(2),
                 notApplicable(3) }
   ACCESS     read-only
   STATUS     mandatory
   DESCRIPTION
     "This attribute contains the current state of the switch-side segment 
      loopback for this connection. Switch-side segment loopback cells 
      are transmitted (inserted) by a connection component in the 
      direction of the bus. The value of this attribute is dependent upon 
      the current setting of the segSwitchSideLoopback provisionable 
      attribute, the connection point type as specified by the 
      connectionPointType attribute, and the current loopback state (if 
      applicable).
      
      The value is only applicable when the connectionPointType is a 
      segmentEndPoint. 
      
      The value is notApplicable when the connectionPointType is a 
      connectingPoint or connectionEndPoint. 
      
      The value is notApplicable when the distributionType is 
      pointToMultipoint.
      
      The value is good when the segSwitchSideLoopback is on, the 
      connectionPointType is a segmentEndPoint and the segment switch 
      side loopback is working.
      
      The value is bad when the segSwitchSideLoopback is on, the 
      connectionPointType is a segmentEndPoint and the switch side 
      segment loopback is not working.
      
      The value is unknown when the segSwitchSideLoopback is off.
      
      The value is unknown when the segSwitchSideLoopback is on, the 
      connectionPointType is a segmentEndPoint and the segment switch 
      side loopback has not been determined."
::= { atmIfVptVccStatusEntry 40 }

atmIfVptVccEndToEndLoopbackState OBJECT-TYPE
   SYNTAX     INTEGER  {
                 good(0),
                 bad(1),
                 unknown(2),
                 notApplicable(3) }
   ACCESS     read-only
   STATUS     mandatory
   DESCRIPTION
     "This attribute contains the current state of the end-to-end loopback 
      for this connection. Its value is dependent upon the current setting 
      of the endToEndLoopback provisionable attribute and the 
      connection point type as specified by the connectionPointType 
      attribute.
      
      The value is only applicable when the connectionPointType is a 
      connectionEndPoint. 
      
      The value is notApplicable when the connectionPointType is a 
      connectingPoint or segmentEndPoint. 
      
      The value is notApplicable when the distributionType is a 
      pointToMultipoint.
      
      The value is good when the endToEndLoopback is on, the 
      connectionPointType is a connectionEndPoint and the end-to-end 
      loopback is working.
      
      The value is bad when the endToEndLoopback is on, the 
      connectionPointType is a connectionEndPoint and the end-to-end 
      loopback is not working.
      
      The value is unknown when the endToEndLoopback is off.
      
      The value is unknown when the endToEndLoopback is on, the 
      connectionPointType is a connectionEndPoint and the end-to-end 
      loopback status has not been determined.
      
      The state of this attribute determines, in part, the value of the 
      operStatus attribute."
::= { atmIfVptVccStatusEntry 50 }

atmIfVptVccRxOamCellCongestionState OBJECT-TYPE
   SYNTAX     INTEGER  {
                 good(0),
                 bad(1),
                 unknown(2),
                 notApplicable(3) }
   ACCESS     read-only
   STATUS     mandatory
   DESCRIPTION
     "This attribute contains the current state of the receive side OAM cell 
      congestion for this connection. Its value reflects whether the rate of 
      received OAM cells for this connection is below a specified 
      threshold. The connection maintains a count of the number of OAM 
      cells which are terminated per second. Once that count exceeds the 
      specified threshold, extraction of all OAM cells for this connection 
      is disabled for a period of one minute. This is a congestion 
      management mechanism to prevent the processor from being 
      overloaded with handling OAM cells for a particular connection. 
      This mechanism ensures that tasks, such as trunks obtain enough 
      processor cycles to remain in service, and are not adversely affected 
      by excessive rate of OAM cells on a particular connection.
      
      The value is good when the rate of received OAM cells is less than 
      the allowed threshold.
      
      The value is bad when the arrival rate has exceeded the allowed 
      threshold. It remains bad for one minute, before returning to good 
      again. During this timeout, extraction of all OAM cells is disabled 
      for this connection. As a result, other loopback failure conditions 
      may occur.
      
      The value is unknown when the application has not yet begun to 
      use this connection. An example is the Test component before a test 
      has been started.
      
      Each type of OAM cell is counted separately. The threshold for AIS 
      cells is three cells per second. If more than three AIS cells are 
      received within a one second interval, this attribute is set to bad. 
      The threshold for RDI cells and each loopback type is also three, 
      but the threshold for trace cells is 250 per second.
      
      The state of this attribute has no direct effect on the value of the 
      operStatus attribute or on the number of troubled connections."
::= { atmIfVptVccStatusEntry 55 }

atmIfVptVccAisState OBJECT-TYPE
   SYNTAX     INTEGER  {
                 good(0),
                 bad(1),
                 unknown(2),
                 notApplicable(3) }
   ACCESS     read-only
   STATUS     mandatory
   DESCRIPTION
     "This attribute contains the current state of the Alarm Indication 
      Signal for this connection.
      
      A value of good indicates that the connection's application is active 
      and no alarm has occurred.
      
      A value of bad indicates that the connection's application is active 
      and an alarm has occurred.
      
      A value of unknown indicates that the connection's application is 
      inactive.
      
      A value of notApplicable occurs when the connectionPointType is 
      either a segmentEndPoint or a connectingPoint."
::= { atmIfVptVccStatusEntry 60 }

atmIfVptVccRdiState OBJECT-TYPE
   SYNTAX     INTEGER  {
                 good(0),
                 bad(1),
                 unknown(2),
                 notApplicable(3) }
   ACCESS     read-only
   STATUS     mandatory
   DESCRIPTION
     "This attribute indicates the current state of the Remote Defect 
      Indication for this connection.
      
      A value of good indicates that the connection's application is active 
      and no alarm has occurred.
      
      A value of bad indicates that the connection's application is active 
      and an alarm has occurred.
      
      A value of unknown indicates that the connection's application is 
      inactive.
      
      A value of notApplicable occurs when the connectionPointType is 
      either a segmentEndPoint or a connectingPoint."
::= { atmIfVptVccStatusEntry 70 }

atmIfVptVccTrafficTable OBJECT-TYPE
   SYNTAX     SEQUENCE OF AtmIfVptVccTrafficEntry
   ACCESS     not-accessible
   STATUS     mandatory
   DESCRIPTION
     "This group is HISTORICAL. Please refer to the group AtmTmOper;
      
      This attribute group contains attributes for the Vcc and Vpc 
      components to reflect operational traffic attributes."
::= { atmIfVptVcc 130 }

atmIfVptVccTrafficEntry OBJECT-TYPE
   SYNTAX     AtmIfVptVccTrafficEntry
   ACCESS     not-accessible
   STATUS     mandatory
   DESCRIPTION
     "An entry in the atmIfVptVccTrafficTable."
   INDEX {
      atmIfIndex,
      atmIfVptIndex,
      atmIfVptVccIndex }
::= { atmIfVptVccTrafficTable 1 }

AtmIfVptVccTrafficEntry ::= SEQUENCE {
   atmIfVptVccTxTrafficDescType
      INTEGER,
   atmIfVptVccTxQosClass
      INTEGER,
   atmIfVptVccFwdQosClass
      INTEGER,
   atmIfVptVccTxQueueLength
      INTEGER,
   atmIfVptVccTxQueueCongestionState
      INTEGER,
   atmIfVptVccHoldingPriority
      INTEGER,
   atmIfVptVccRxTrafficDescType
      INTEGER,
   atmIfVptVccRxQosClass
      INTEGER,
   atmIfVptVccBwdQosClass
      INTEGER,
   atmIfVptVccAtmServiceCategory
      INTEGER,
   atmIfVptVccTrafficShaping
      INTEGER,
   atmIfVptVccBearerClassBbc
      INTEGER,
   atmIfVptVccTransferCapabilityBbc
      INTEGER,
   atmIfVptVccClippingBbc
      INTEGER,
   atmIfVptVccUnshapedTransmitQueueing
      INTEGER,
   atmIfVptVccBestEffort
      INTEGER,
   atmIfVptVccUsageParameterControl
      INTEGER,
   atmIfVptVccTxFrameDiscard
      OCTET STRING,
   atmIfVptVccRxFrameDiscard
      OCTET STRING,
   atmIfVptVccBandwidthElastic
      INTEGER,
   atmIfVptVccBandwidthReduction
      INTEGER }

atmIfVptVccTxTrafficDescType OBJECT-TYPE
   SYNTAX     INTEGER  {
                 n1(1),
                 n2(2),
                 n3(3),
                 n4(4),
                 n5(5),
                 n6(6),
                 n7(7),
                 n8(8) }
   ACCESS     read-only
   STATUS     obsolete
   DESCRIPTION
     "This attribute is HISTORICAL. Please refer to the attribute of the 
      same name in the group AtmTmOper.
      
      This attribute indicates the type of traffic management which is 
      applied to the transmit direction of this connection as defined in the 
      ATM Forum. The txTrafficDescType determines the number and 
      meaning of the parameters in the txTrafficDescParm attribute."
::= { atmIfVptVccTrafficEntry 10 }

atmIfVptVccTxQosClass OBJECT-TYPE
   SYNTAX     INTEGER  {
                 unspecified(0),
                 constantBitRate(1),
                 variableBitRate(2),
                 connectionOriented(3),
                 connectionless(4) }
   ACCESS     read-only
   STATUS     obsolete
   DESCRIPTION
     "This attribute indicates the quality of service for the transmit 
      direction for this connection.
      
      The constantBitRate class refers to traffic offered on services such 
      as a constant bit rate video service. This traffic is highest priority.
      
      The variableBitRate class refers to traffic offered on services such 
      as packetized audio and video.
      
      The connectionOriented class refers to connection-oriented traffic 
      such as Frame Relay or X.25 traffic. 
      
      The connectionless traffic refers to traffic offered through 
      connectionless trunks such as certain LAN protocols.
      
      The unspecified class supports a 'best effort' type of service, where 
      there is a minimum guarantee of bandwidth. This traffic is lowest 
      priority.
      
      This attribute is obsolete, replaced by the UNI 4.0 attribute 
      atmServiceCategory."
::= { atmIfVptVccTrafficEntry 30 }

atmIfVptVccFwdQosClass OBJECT-TYPE
   SYNTAX     INTEGER  {
                 n0(0),
                 n1(1),
                 n2(2),
                 n3(3),
                 n4(4),
                 notApplicable(14) }
   ACCESS     read-only
   STATUS     obsolete
   DESCRIPTION
     "This attribute is HISTORICAL. Please refer to the attribute of the 
      same name in the group AtmTmOper.
      
      This attribute indicates the quality of service for the calling to called 
      direction for this connection. This is only applicable to Soft PVC 
      and SVC connections. 
      
      Class 1 supports a QOS that meets Service Class A performance 
      requirements (Circuit emulation, constant bit rate video).
      
      Class 2 supports a QOS that meets Service Class B performance 
      requirements (Variable bit rate audio and video).
      
      Class 3 supports a QOS that meets Service Class C performance 
      requirements (Connection-Oriented Data Transfer).
      
      Class 4 supports a QOS that meets Service Class D performance 
      requirements (Connectionless Data Transfer).
      
      Class 0 is the unspecified QOS class; no objective is specified for 
      the performance parameters.
      
      A value of notApplicable is displayed in the case of nailed-up PVCs 
      for which this attribute has no significance."
::= { atmIfVptVccTrafficEntry 31 }

atmIfVptVccTxQueueLength OBJECT-TYPE
   SYNTAX     INTEGER (0..30720)
   ACCESS     read-only
   STATUS     obsolete
   DESCRIPTION
     "This attribute is HISTORICAL. Please refer to the attribute of the 
      same name in the group AtmTmOper.
      
      This attribute indicates the current length of the transmit queue for 
      this connection. If this connection has traffic shaping disabled, then 
      this attribute displays the common queue length. If traffic shaping is 
      enabled, then this attribute displays the per-VC queue length."
::= { atmIfVptVccTrafficEntry 32 }

atmIfVptVccTxQueueCongestionState OBJECT-TYPE
   SYNTAX     INTEGER (0..3)
   ACCESS     read-only
   STATUS     obsolete
   DESCRIPTION
     "This attribute is HISTORICAL. Please refer to the attribute of the 
      same name in the group AtmTmOper.
      
      This attribute indicates the congestion state of the transmit queue 
      for this connection. If the connection has traffic shaping disabled, 
      then this attribute displays the common queue congestion state. If 
      traffic shaping is enabled, then this attribute displays the per-VC 
      queue congestion state.
      
      The congestion state of a queue is indicated by a numeric value 
      ranging from 0 to 3. When a queue is in a congested state x, only 
      traffic with discard priority (DP) 0 to x are enqueued. Traffic with 
      DP > x is discarded. 
      
      Therefore, if the congestion state is 3, there is no congestion and all 
      traffic is enqueued. Likewise, when the congestion state is 0, there 
      is maximum congestion and only traffic with DP=0 is enqueued on 
      that queue."
::= { atmIfVptVccTrafficEntry 33 }

atmIfVptVccHoldingPriority OBJECT-TYPE
   SYNTAX     INTEGER  {
                 n0(0),
                 n1(1),
                 n2(2),
                 n3(3),
                 n4(4),
                 notApplicable(6) }
   ACCESS     read-only
   STATUS     obsolete
   DESCRIPTION
     "This attribute is HISTORICAL. Please refer to the attribute of the 
      same name in the group AtmTmOper.
      
      This attribute indicates the actual holding priority in effect for this 
      connection. In a situation where the link bandwidth fluctuates, such 
      as over an IMA link, holding priority is used to determine which 
      connections are held and which are released. Holding priority 4 
      connections are the first to be released. Holding priority 0 
      connections are the last to be released. Some applications, for 
      example Vcc Test, may override the provisioned holding priority. 
      
      A value of notApplicable is displayed when this is an elastic 
      connection. Holding priority does not apply to bandwidth elastic 
      connections.
      
      Holding priority has no effect for ubr atmServiceCategory or 
      txTrafficDescriptorType 1 or 2 connections."
::= { atmIfVptVccTrafficEntry 35 }

atmIfVptVccRxTrafficDescType OBJECT-TYPE
   SYNTAX     INTEGER  {
                 n1(1),
                 n2(2),
                 n3(3),
                 n4(4),
                 n5(5),
                 n6(6),
                 n7(7),
                 n8(8) }
   ACCESS     read-only
   STATUS     obsolete
   DESCRIPTION
     "This attribute is HISTORICAL. Please refer to the attribute of the 
      same name in the group AtmTmOper.
      
      This attribute indicates the type of traffic management which is 
      applied to the receive direction of this connection as defined in the 
      ATM Forum. The rxTrafficDescType determines the number and 
      meaning of the parameters in the rxTrafficDescParm attribute."
::= { atmIfVptVccTrafficEntry 40 }

atmIfVptVccRxQosClass OBJECT-TYPE
   SYNTAX     INTEGER  {
                 unspecified(0),
                 constantBitRate(1),
                 variableBitRate(2),
                 connectionOriented(3),
                 connectionless(4) }
   ACCESS     read-only
   STATUS     obsolete
   DESCRIPTION
     "This attribute reflects the value of the provisioned attribute in the 
      Vcd or Vpd. Refer to that attribute for more detailed explanation. 
      
      This attribute is obsolete replaced by the UNI 4.0 attribute 
      atmServiceCategory."
::= { atmIfVptVccTrafficEntry 60 }

atmIfVptVccBwdQosClass OBJECT-TYPE
   SYNTAX     INTEGER  {
                 n0(0),
                 n1(1),
                 n2(2),
                 n3(3),
                 n4(4),
                 notApplicable(14) }
   ACCESS     read-only
   STATUS     obsolete
   DESCRIPTION
     "This attribute is HISTORICAL. Please refer to the attribute of the 
      same name in the group AtmTmOper.
      
      This attribute indicates the quality of service for the called to calling 
      direction for this connection. This is only applicable to Soft PVC 
      and SVC connections. 
      
      Class 1 supports a QOS that meets Service Class A performance 
      requirements (Circuit emulation, constant bit rate video).
      
      Class 2 supports a QOS that meets Service Class B performance 
      requirements (Variable bit rate audio and video).
      
      Class 3 supports a QOS that meets Service Class C performance 
      requirements (Connection-Oriented Data Transfer).
      
      Class 4 supports a QOS that meets Service Class D performance 
      requirements (Connectionless Data Transfer).
      
      Class 0 is the unspecified QOS class; no objective is specified for 
      the performance parameters.
      
      A value of notApplicable is displayed in the case of nailed-up PVCs 
      for which this attribute has no significance."
::= { atmIfVptVccTrafficEntry 61 }

atmIfVptVccAtmServiceCategory OBJECT-TYPE
   SYNTAX     INTEGER  {
                 unspecifiedBitRate(0),
                 constantBitRate(1),
                 rtVariableBitRate(2),
                 nrtVariableBitRate(3) }
   ACCESS     read-only
   STATUS     obsolete
   DESCRIPTION
     "This attribute is HISTORICAL. Please refer to the attribute of the 
      same name in the group AtmTmOper.
      
      This attribute indicates the ATM service category used for traffic in 
      both directions of the connection. 
      
      The constantBitRate service category is intended for real time 
      applications, that is, those requiring tightly constrained delay and 
      delay variation, as would be appropriate for voice and video 
      applications. The consistent availability of a fixed quantity of 
      bandwidth is considered appropriate for CBR service. Cells which 
      are delayed beyond the value specified by Cell Transfer Delay are 
      assumed to have significantly reduced value of the application.
      
      The rtVariableBitRate service category is intended for real time 
      applications; that is those requiring tightly constrained delay and 
      delay variation, as would be appropriate for voice and video 
      applications. Sources are expected to transmit at a rate which varies 
      with time. Equivalently, the source can be described as 'bursty'. 
      Cells which are delayed beyond the value specified by Cell Transfer 
      Delay are assumed to be of significantly reduced value to the 
      application. Real time VBR service may support statistical 
      multiplexing of real time sources.
      
      The nrtVariableBitRate service category is intended for non-real 
      time applications which have bursty traffic characteristics and which 
      can be characterized in terms of a PCR, SCR, and MBS. For those 
      cells which are transferred within the traffic contract, the application 
      expects a low cell loss ratio. For all connections, it expects a bound 
      on the mean cell transfer delay. Non-real time VBR service may 
      support statistical multiplexing of connections.
      
      The unspecifiedBitRate service is intended for non-real time 
      applications, that is those not requiring tightly constrained delay 
      and delay variation. UBR sources are expected to be bursty. UBR 
      service supports a high degree of statistical multiplexing among 
      sources. UBR service does not specify traffic related service 
      guarantees. No numerical commitments are made with respect to 
      the cell loss ratio experienced by a UBR connection, or as to the 
      cell transfer delay experienced by cells on the connection."
::= { atmIfVptVccTrafficEntry 62 }

atmIfVptVccTrafficShaping OBJECT-TYPE
   SYNTAX     INTEGER  {
                 enabled(0),
                 disabled(1),
                 notApplicable(4) }
   ACCESS     read-only
   STATUS     obsolete
   DESCRIPTION
     "This attribute is HISTORICAL. Please refer to the attribute of the 
      same name in the group AtmTmOper.
      
      This attribute indicates the traffic shaping state of the connection.
      
      A value of notApplicable indicates that traffic shaping is not 
      applicable or not supported for this connection. This is the case 
      when the atmServiceCategory is constantBitRate, or when the 
      txTrafficDescType is 1 or 2. In these cases, the value of 
      notApplicable is set regardless of whether traffic shaping is enabled 
      or disabled in the provisioning data.
      
      A value of disabled indicates that traffic shaping is applicable and 
      supported for the type of connection but has been turned off in the 
      provisioning data.
      
      A value of enabled indicates that traffic shaping is applicable and 
      supported for the type of connection and has been turned on in the 
      provisioning data. This is the only case that indicates that traffic 
      shaping is performed on the connection. In this case, the actual 
      shaping rate is reflected in the txTrafficDescParm attribute, 
      parameter number 4."
::= { atmIfVptVccTrafficEntry 70 }

atmIfVptVccBearerClassBbc OBJECT-TYPE
   SYNTAX     INTEGER  {
                 a(1),
                 c(3),
                 x(16),
                 vp(24),
                 notApplicable(30) }
   ACCESS     read-only
   STATUS     obsolete
   DESCRIPTION
     "This attribute is HISTORICAL. Please refer to the attribute of the 
      same name in the group AtmTmOper.
      
      This attribute indicates the bearer capability for this connection.
      
      Class a service is a connection-oriented, constant bit rate ATM 
      transport service. Class a service has end to end timing 
      requirements and may require stringent cell loss, cell delay and cell 
      delay variation performance.When a is displayed, the user is 
      requesting more than an ATM only service. The network may look 
      at the AAL to provide interworking based upon its contents. 
      
      Class c service is a connection-oriented, variable bit rate ATM 
      transport service. Class c service has no end-to-end timing 
      requirements.When c is displayed, the user is requesting more than 
      an ATM only service. The network interworking function may look 
      at the AAL and provide service based on it.
      
      Class x service is a connection-oriented ATM transport service 
      where the AAL, trafficType (cbr or vbr) and timing requirements 
      are user defined (that is, transparent to the network). When the 
      value of this attribute is x, the user is requesting an ATM only 
      service from the network. In this case, the network shall not process 
      any higher layer protocol.
      
      Class vp service is used to indicate a transparent VP service when 
      the user is requesting an ATM only service from the network. In this 
      case, the network does not process any higher layer protocol. This 
      service differs from class x service in that with the class vp service 
      both the VCI field (except for VCI values 0, 3, 4, and 6 through 15) 
      and Payload Type field are transported transparently by the network. 
      This attribute value is only applicable to SPVP and SVP 
      connections.
      
      A value of notApplicable is displayed in the case of nailed-up PVCs 
      for which this attribute has no significance."
::= { atmIfVptVccTrafficEntry 71 }

atmIfVptVccTransferCapabilityBbc OBJECT-TYPE
   SYNTAX     INTEGER  {
                 n0(0),
                 n1(1),
                 n2(2),
                 n5(5),
                 n8(8),
                 n9(9),
                 n10(10),
                 notApplicable(30) }
   ACCESS     read-only
   STATUS     obsolete
   DESCRIPTION
     "This attribute is HISTORICAL. Please refer to the attribute of the 
      same name in the group AtmTmOper.
      
      This attribute indicates the transfer capability for this connection. 
      Uni 3.0/3.1 traffic type and end-to-end timing parameters are 
      mapped into this parameter as follows:
      <transferCapability: TrafficType, Timing>
      0: NoIndication, NoIndication
      1: NoIndication, yes
      2: NoIndication, no
      5: CBR, yes
      8: VBR, NoIndication
      9: VBR, yes
      10: VBR, no
      
      A value of notApplicable is displayed in the case of nailed-up PVCs 
      for which this attribute has no significance, or in the case that the 
      transfer capability in the call request was set to NoIndication.
      
      The CBR traffic type refers to traffic offered on services such as a 
      constant bit rate video service or a circuit emulation.
      
      The VBR traffic type refers to traffic offered on services such as 
      packetized audio and video, or data.
      
      The value NoIndication for traffic type is used if the user has not set 
      the traffic type; similarly for end-to-end timing.
      
      The value yes for end-to-end timing indicates that end-to-end 
      timing is required for the connection.
      
      The value no for end-to-end timing indicates that end-to-end timing 
      is not required for the connection."
::= { atmIfVptVccTrafficEntry 72 }

atmIfVptVccClippingBbc OBJECT-TYPE
   SYNTAX     INTEGER  {
                 no(0),
                 yes(1),
                 notApplicable(14) }
   ACCESS     read-only
   STATUS     obsolete
   DESCRIPTION
     "This attribute is HISTORICAL. Please refer to the attribute of the 
      same name in the group AtmTmOper.
      
      This attribute indicates the value of the clipping susceptibility 
      parameter in the BBC Information Element.
      
      Clipping is an impairment in which the first fraction of a second of 
      information to be transferred is lost. It occurs after a call is 
      answered and before an associated connection is switched through.
      
      A value of notApplicable is displayed in the case of nailed-up PVCs 
      for which this attribute has no significance."
::= { atmIfVptVccTrafficEntry 74 }

atmIfVptVccUnshapedTransmitQueueing OBJECT-TYPE
   SYNTAX     INTEGER  {
                 perVc(0),
                 common(1),
                 notApplicable(4) }
   ACCESS     read-only
   STATUS     obsolete
   DESCRIPTION
     "This attribute is HISTORICAL. Please refer to the attribute of the 
      same name in the group AtmTmOper.
      
      This attribute indicates the unshaped transmit queuing state of the 
      connection.
      
      A value of common indicates that transmit traffic is being enqueued 
      onto common transmit queues. 
      
      A value of perVc indicates that transmit traffic is being enqueued 
      onto a per-VC queue for this connection. This is the case when 
      trafficShaping is disabled, but per-VC queueing has been 
      configured for this connection. 
      
      A value of notApplicable indicates that transmit traffic is being 
      shaped for this connection. Transmit traffic for a shaped connection 
      is enqueued onto a per-VC queue, but this attribute is only 
      applicable for unshaped connections."
::= { atmIfVptVccTrafficEntry 75 }

atmIfVptVccBestEffort OBJECT-TYPE
   SYNTAX     INTEGER  {
                 indicated(0),
                 notIndicated(1),
                 notApplicable(14) }
   ACCESS     read-only
   STATUS     obsolete
   DESCRIPTION
     "This attribute is HISTORICAL. Please refer to the attribute of the 
      same name in the group AtmTmOper.
      
      This attribute indicates value of best effort parameter in the ATM 
      Traffic Descriptor Information Element.
      
      The value indicated implies that the quality of service for this 
      connection is not guaranteed.
      
      The value notIndicated implies that the quality of service for this 
      connection is guaranteed.
      
      A value of notApplicable is displayed in the case of nailed-up PVCs 
      for which this attribute has no significance."
::= { atmIfVptVccTrafficEntry 76 }

atmIfVptVccUsageParameterControl OBJECT-TYPE
   SYNTAX     INTEGER  {
                 enabled(0),
                 disabled(1),
                 notApplicable(3) }
   ACCESS     read-only
   STATUS     obsolete
   DESCRIPTION
     "This attribute is HISTORICAL. Please refer to the attribute of the 
      same name in the group AtmTmOper.
      
      This attribute indicates the UPC state of the connection.
      
      A value of notApplicable indicates that UPC is not applicable or not 
      supported for the connection. This is the case when the connection's 
      rxTrafficDescType is 1 or 2. A value of notApplicable is set 
      regardless of whether UPC is disabled or enabled in provisioning 
      data.
      
      A value of disabled indicates that UPC is applicable and supported 
      for the type of connection but has been turned off in the 
      provisioning data.
      
      A value of enabled indicates that UPC is applicable and supported 
      for the type of connection and has been turned on in the 
      provisioning data. This is the only case that indicates that UPC is 
      enforced on the connection. In this case the traffic descriptor 
      parameters used for UPC enforcement are reflected in the 
      rxTrafficDescParms of the connection."
::= { atmIfVptVccTrafficEntry 80 }

atmIfVptVccTxFrameDiscard OBJECT-TYPE
   SYNTAX     OCTET STRING (SIZE (1))
   ACCESS     read-only
   STATUS     obsolete
   DESCRIPTION
     "This attribute is HISTORICAL. Please refer to the attribute of the 
      same name in the group AtmTmOper.
      
      This attribute indicates the set of current frame discard functions in 
      effect in the transmit data direction at this connection point.
      
      A value of ppd indicates that the Partial Packet Discard (PPD) 
      function is in effect. PPD may be applied at an interim connecting 
      point for a connection which is transporting frame traffic (AAL5 at 
      the endpoint). PPD is controlled by provisioning for PVCs and 
      SPVCs, and by call setup parameters in the AAL and Traffic 
      Descriptor Information Elements.
      
      A value of epd indicates that the Early Packet Discard (EPD) 
      function is in effect at this connection endpoint. PPD and EPD are 
      enabled by default at a connection endpoint which is performing 
      AAL5 segmentation and assembly.
      
      Frame discard functions are not applicable for Virtual Path 
      Connections (VPCs).

      Description of bits:
      ppd(0)
      epd(1)"
::= { atmIfVptVccTrafficEntry 85 }

atmIfVptVccRxFrameDiscard OBJECT-TYPE
   SYNTAX     OCTET STRING (SIZE (1))
   ACCESS     read-only
   STATUS     obsolete
   DESCRIPTION
     "This attribute is HISTORICAL. Please refer to the attribute of the 
      same name in the group AtmTmOper.
      
      This attribute indicates the set of current frame discard functions in 
      effect in the receive data direction at this connection point.
      
      A value of ppd indicates that the Partial Packet Discard (PPD) 
      function is in effect. PPD may be applied at an interim connecting 
      point for a connection which is transporting frame traffic (AAL5 at 
      the endpoint). PPD is controlled by provisioning for PVCs and 
      SPVCs, and by call setup parameters in the AAL and Traffic 
      Descriptor Information Elements.
      
      A value of epd indicates that the Early Packet Discard (EPD) 
      function is in effect at this connection endpoint. PPD and EPD are 
      enabled by default at a connection endpoint which is performing 
      AAL5 segmentation and assembly.
      
      Frame discard functions are not applicable for Virtual Path 
      Connections (VPCs).

      Description of bits:
      ppd(0)
      epd(1)"
::= { atmIfVptVccTrafficEntry 86 }

atmIfVptVccBandwidthElastic OBJECT-TYPE
   SYNTAX     INTEGER  {
                 no(0),
                 yes(1) }
   ACCESS     read-only
   STATUS     obsolete
   DESCRIPTION
     "This attribute is HISTORICAL. Please refer to the attribute of the 
      same name in the group AtmTmOper.
      
      This attribute is only of importance for connections which are 
      carried on a link with a variable bandwidth. For example, the 
      bandwidth may be reduced in the event that one or more physical 
      links in the IMA group fail, such that the originally requested 
      bandwidth cannot be maintained. This attribute shows whether the 
      application (for example, Trunk) running on this connection can 
      continue to operate if the bandwidth is reduced. If the bandwidth is 
      reduced, the amount by which it is reduced is displayed in the 
      bandwidthReduction attribute. 
      
      A value of yes, indicates that this connection is elastic, and the 
      bandwidth may be reduced but the connection is not released. 
      
      A value of no indicates that the bandwidth for this connection is not 
      reduced in the event of link bandwidth reduction. However, this 
      connection may be released based on its holdingPriority.
      
      Bandwidth elasticity has no effect for ubr atmServiceCategory or 
      txTrafficDescriptorType 1 or 2 connections."
::= { atmIfVptVccTrafficEntry 90 }

atmIfVptVccBandwidthReduction OBJECT-TYPE
   SYNTAX     INTEGER (0..2147483647)
   ACCESS     read-only
   STATUS     obsolete
   DESCRIPTION
     "This attribute is HISTORICAL. Please refer to the attribute of the 
      same name in the group AtmTmOper.
      
      This attribute shows the amount by which the bandwidth has been 
      reduced for this connection. This value is non-zero only for 
      connections which have bandwidthElastic displayed as yes, and 
      which are also operating in a reduced bandwidth mode. This is 
      typically be the case for selected connections running over an IMA 
      link. This attribute takes a value from 0 (no reduction) up to the 
      ECR. All connections which are running at their full allocated 
      bandwidth, bwReduction have the value 0. Connections which have 
      been reduced in allocated bandwidth have a positive number for this 
      attribute. The bwReduction may be subtracted from the ECR (which 
      is displayed as txTrafficDescParm 5) to determine the actual 
      bandwidth allocated to this connection."
::= { atmIfVptVccTrafficEntry 100 }

atmIfVptVccStatsTable OBJECT-TYPE
   SYNTAX     SEQUENCE OF AtmIfVptVccStatsEntry
   ACCESS     not-accessible
   STATUS     mandatory
   DESCRIPTION
     "This group contains traffic statistics for a Vcc, Vpc, or Vpt 
      component."
::= { atmIfVptVcc 140 }

atmIfVptVccStatsEntry OBJECT-TYPE
   SYNTAX     AtmIfVptVccStatsEntry
   ACCESS     not-accessible
   STATUS     mandatory
   DESCRIPTION
     "An entry in the atmIfVptVccStatsTable."
   INDEX {
      atmIfIndex,
      atmIfVptIndex,
      atmIfVptVccIndex }
::= { atmIfVptVccStatsTable 1 }

AtmIfVptVccStatsEntry ::= SEQUENCE {
   atmIfVptVccStatsTxCell
      PassportCounter64,
   atmIfVptVccStatsTxCellClp
      PassportCounter64,
   atmIfVptVccTxDiscard
      PassportCounter64,
   atmIfVptVccTxDiscardClp
      PassportCounter64,
   atmIfVptVccStatsTxCellDiscard
      PassportCounter64,
   atmIfVptVccStatsTxCellDiscardClp
      PassportCounter64,
   atmIfVptVccStatsTxFrameDiscard
      PassportCounter64,
   atmIfVptVccStatsTxFrameDiscardClp
      PassportCounter64,
   atmIfVptVccTxUtilization
      Gauge32,
   atmIfVptVccStatsRxCell
      PassportCounter64,
   atmIfVptVccStatsRxCellClp
      PassportCounter64,
   atmIfVptVccRxDiscard
      PassportCounter64,
   atmIfVptVccRxDiscardClp
      PassportCounter64,
   atmIfVptVccStatsRxCellDiscard
      PassportCounter64,
   atmIfVptVccStatsRxCellDiscardClp
      PassportCounter64,
   atmIfVptVccStatsRxFrameDiscard
      PassportCounter64,
   atmIfVptVccStatsRxFrameDiscardClp
      PassportCounter64,
   atmIfVptVccRxUtilization
      Gauge32,
   atmIfVptVccStatsRxUpcViolationOnEnforcer1
      PassportCounter64,
   atmIfVptVccStatsRxUpcViolationOnEnforcer2
      PassportCounter64,
   atmIfVptVccStatsRxAal5FrameError
      PassportCounter64,
   atmIfVptVccStatsRxAal5FrameAbort
      PassportCounter64 }

atmIfVptVccStatsTxCell OBJECT-TYPE
   SYNTAX     PassportCounter64 
   ACCESS     read-only
   STATUS     mandatory
   DESCRIPTION
     "This attribute counts the number of cells that have been transmitted 
      from the interface on this connection. The counter wraps to zero if it 
      exceeds its maximum value of (2**64)-1."
::= { atmIfVptVccStatsEntry 10 }

atmIfVptVccStatsTxCellClp OBJECT-TYPE
   SYNTAX     PassportCounter64 
   ACCESS     read-only
   STATUS     mandatory
   DESCRIPTION
     "This attribute counts the number of cells that have been transmitted 
      from the interface on this connection with the CLP=1. The counter 
      wraps to zero if it exceeds its maximum value of (2**64)-1."
::= { atmIfVptVccStatsEntry 20 }

atmIfVptVccTxDiscard OBJECT-TYPE
   SYNTAX     PassportCounter64 
   ACCESS     read-only
   STATUS     obsolete
   DESCRIPTION
     "This attribute is replaced by new attributes txCellDiscard and 
      txFrameDiscard.
      
      This attribute counts the number of cells or frames received from 
      the bus on this connection that have been discarded.
      
      If the connection segments frames into cells, the counter indicates 
      the number of frames discarded. Connections which segment 
      frames into cells have a connectionPointType of 
      connectionEndPoint.
      
      If the connection relays cells without adaptation, the counter 
      indicates the number of cells discarded. Connections which relay 
      cells without adaptation have a connectionPointType of 
      segmentEndPoint or connectingPoint.
      
      AAL1 connections are an exception to this rule; although they have 
      a connectionPointType of connectionEndPoint, they do not do 
      adaptation at this point. Thus, in the AAL1 case, this attribute 
      counts discarded cells.
      
      Discards are done due to congestion or when the connection's 
      interface is disabled.
      
      The counter wraps to zero if it exceeds its maximum value of 
      (2**64)-1."
::= { atmIfVptVccStatsEntry 30 }

atmIfVptVccTxDiscardClp OBJECT-TYPE
   SYNTAX     PassportCounter64 
   ACCESS     read-only
   STATUS     obsolete
   DESCRIPTION
     "This attribute is replaced by new attributes txCellDiscardClp and 
      txFrameDiscardClp.
      
      This attribute counts the number of cells or frames received from 
      the bus on this connection with CLP=1 that have been discarded.
      
      If the connection segments frames into cells, the counter indicates 
      the number of frames discarded. Connections which segment 
      frames into cells have a connectionPointType of 
      connectionEndPoint.
      
      If the connection relays cells without adaptation, the counter 
      indicates the number of cells discarded. Connections which relay 
      cells without adaptation have a connectionPointType of 
      segmentEndPoint or connectingPoint.
      
      AAL1 connections are an exception to this rule; although they have 
      a connectionPointType of connectionEndPoint, they do not do 
      adaptation at this point. Thus, in the AAL1 case, this attribute 
      counts discarded cells.
      
      Discards are done due to congestion or when the connection's 
      interface is disabled.
      
      The counter wraps to zero if it exceeds its maximum value of 
      (2**64)-1."
::= { atmIfVptVccStatsEntry 40 }

atmIfVptVccStatsTxCellDiscard OBJECT-TYPE
   SYNTAX     PassportCounter64 
   ACCESS     read-only
   STATUS     mandatory
   DESCRIPTION
     "This attribute counts the number of cells received from the bus on 
      this connection that have been discarded.
      
      Discarded cells are not counted in the txCell attribute.
      
      Cells are discarded due to transmit congestion, Partial Packet 
      Discard (PPD), Early Packet Discard (EPD), and Weighted Random 
      Early Detection (W-RED) mechanisms, or when the connection's 
      interface is disabled.
      
      For CQC-based ATM cards, this attribute is applicable only to 
      connections that relay cells without adaptation. Such connections 
      usually have a connectionPointType of segmentEndPoint or 
      connectingPoint. AAL1 connections are an exception to this rule; 
      although they have a connectionPointType of connectionEndPoint, 
      they do not do adaptation at this point. For Vpts, this attribute 
      provides an aggregated total of all txCellDiscard values for all such 
      connections associated with the Vpt.
      
      For Vccs on CQC-based ATM cards, if the connection segments 
      frames into cells, this attribute is not applicable and is not 
      displayed.
      
      The counter wraps to zero if it exceeds its maximum value of 
      (2**64)-1."
::= { atmIfVptVccStatsEntry 42 }

atmIfVptVccStatsTxCellDiscardClp OBJECT-TYPE
   SYNTAX     PassportCounter64 
   ACCESS     read-only
   STATUS     mandatory
   DESCRIPTION
     "This attribute counts the number of cells received from the bus on 
      this connection with CLP=1 that have been discarded.
      
      This count is included in the txCellDiscard attribute. Discarded 
      cells are not counted in the txCellClp attribute.
      
      Cells are discarded due to transmit congestion, Partial Packet 
      Discard (PPD), Early Packet Discard (EPD), and Weighted Random 
      Early Detection (W-RED) mechanisms, or when the connection's 
      interface is disabled.
      
      For CQC-based ATM cards, this attribute is applicable only to 
      connections that relay cells without adaptation. Such connections 
      have a connectionPointType of segmentEndPoint or 
      connectingPoint. AAL1 connections are an exception to this rule; 
      although they have a connectionPointType of connectionEndPoint, 
      they do not do adaptation at this point. For Vpts, this attribute 
      provides an aggregated total of all txCellDiscardClp values for all 
      such connections associated with the Vpt.
      
      For Vccs on CQC-based ATM cards, if the connection segments 
      frames into cells, this attribute is not applicable and is not 
      displayed.
      
      The counter wraps to zero if it exceeds its maximum value of 
      (2**64)-1."
::= { atmIfVptVccStatsEntry 43 }

atmIfVptVccStatsTxFrameDiscard OBJECT-TYPE
   SYNTAX     PassportCounter64 
   ACCESS     read-only
   STATUS     mandatory
   DESCRIPTION
     "This attribute counts the number of frames received from the bus on 
      this connection that have been discarded.
      
      Frames are discarded due to congestion, Partial Packet Discard 
      (PPD), Early Packet Discard (EPD), and Weighted Random Early 
      Detection (W-RED) mechanisms, or when the connection interface 
      is disabled.
      
      This count is independent of the txCell or txCellDiscard attribute.
      
      For CQC-based ATM cards, this attribute is applicable only to 
      connections that segment frames into cells. Such connections have a 
      connectionPointType of connectionEndPoint. AAL1 connections 
      are an exception to this rule; although they have a 
      connectionPointType of connectionEndPoint, they do not do 
      adaptation at this point. For Vpts, this attribute provides an 
      aggregated total of all txFrameDiscard values for all such 
      connections associated with the Vpt.
      
      For CQC-based ATM cards, for Vpcs, and Vccs that relay cells 
      without adaptation, this attribute is not applicable and is not 
      displayed.
      
      Discards due to EPD, PPD, and W-RED for a standard Vpt Vcc are 
      not included in this attribute. These discards are counted in the 
      Vcc's parent Vpt txFrameDiscard attribute.
      
      The counter wraps to zero if it exceeds its maximum value of 
      (2**64)-1."
::= { atmIfVptVccStatsEntry 46 }

atmIfVptVccStatsTxFrameDiscardClp OBJECT-TYPE
   SYNTAX     PassportCounter64 
   ACCESS     read-only
   STATUS     mandatory
   DESCRIPTION
     "This attribute counts the number of discarded frames on this 
      connection that were received from the bus and composed of one or 
      more CLP=1 cells.
      
      Frames are discarded due to congestion, Partial Packet Discard 
      (PPD), Early Packet Discard (EPD), and Weighted Random Early 
      Detection (W-RED) mechanisms, or when the connection interface 
      is disabled.
      
      This count is included in the txFrameDiscard attribute.
      
      For CQC-based ATM cards, this attribute is applicable only to 
      connections that segment frames into cells. Such connections have a 
      connectionPointType of connectionEndPoint. AAL1 connections 
      are an exception to this rule; although they have a 
      connectionPointType of connectionEndPoint, they do not do 
      adaptation at this point. For Vpts, this attribute provides an 
      aggregated total of all txFrameDiscardClp values for all such 
      connections associated with the Vpt.
      
      For CQC-based ATM cards, for Vpcs, and Vccs that relay cells 
      without adaptation, this attribute is not applicable and is not 
      displayed.
      
      Discards due to EPD, PPD, and W-RED for a standard Vpt Vcc are 
      not included in this attribute. These discards are counted in the 
      Vcc's parent Vpt txFrameDiscardClp attribute.
      
      The counter wraps to zero if it exceeds its maximum value of 
      (2**64)-1."
::= { atmIfVptVccStatsEntry 47 }

atmIfVptVccTxUtilization OBJECT-TYPE
   SYNTAX     Gauge32 (0..200 | 255)
   ACCESS     read-only
   STATUS     mandatory
   DESCRIPTION
     "This attribute indicates the current transmit utilization during the 
      most recent minute, expressed as a percentage of the total 
      bandwidth which can be carried by this connection. This attribute is 
      only applicable for Vpts and not for Vpcs or Vccs.
      
      When the Vpt is shaped, the value of this attribute is calculated 
      using its actual shaping rate (ASR) and should not exceed 100.
      
      When the Vpt is unshaped, the value of this attribute is calculated 
      using its peak cell rate (PCR) and should not exceed 200. If the 
      PCR is 0, the value 255 is used."
::= { atmIfVptVccStatsEntry 48 }

atmIfVptVccStatsRxCell OBJECT-TYPE
   SYNTAX     PassportCounter64 
   ACCESS     read-only
   STATUS     mandatory
   DESCRIPTION
     "This attribute counts cells that have been received from the interface 
      on this connection. The counter wraps to zero if it exceeds its 
      maximum value of (2**64)-1."
::= { atmIfVptVccStatsEntry 50 }

atmIfVptVccStatsRxCellClp OBJECT-TYPE
   SYNTAX     PassportCounter64 
   ACCESS     read-only
   STATUS     mandatory
   DESCRIPTION
     "This attribute counts cells that have been received from the interface 
      on this connection with the CLP=1. The counter wraps to zero if it 
      exceeds its maximum value of (2**64)-1."
::= { atmIfVptVccStatsEntry 60 }

atmIfVptVccRxDiscard OBJECT-TYPE
   SYNTAX     PassportCounter64 
   ACCESS     read-only
   STATUS     obsolete
   DESCRIPTION
     "This attribute is replaced by new attributes rxCellDiscard and 
      rxFrameDiscard.
      
      This attribute counts the number of cells or frames received from 
      the interface on this connection that have been discarded.
      
      If the connection segments frames into cells, the counter indicates 
      the number of frames discarded. Connections which segment 
      frames into cells have a connectionPointType of 
      connectionEndPoint.
      
      If the connection relays cells without adaptation, the counter 
      indicates the number of cells discarded. Connections which relay 
      cells without adaptation have a connectionPointType of 
      segmentEndPoint or connectingPoint.
      
      AAL1 connections are an exception to this rule; although they have 
      a connectionPointType of connectionEndPoint, they do not do 
      adaptation at this point. Thus, in the AAL1 case, this attribute 
      counts discarded cells.
      
      Discards are done due to congestion, non-conformance with UPC or 
      AAL reassembly problems.
      
      The counter wraps to zero if it exceeds its maximum value of 
      (2**64)-1."
::= { atmIfVptVccStatsEntry 70 }

atmIfVptVccRxDiscardClp OBJECT-TYPE
   SYNTAX     PassportCounter64 
   ACCESS     read-only
   STATUS     obsolete
   DESCRIPTION
     "This attribute is replaced by new attributes rxCellDiscardClp and 
      rxFrameDiscardClp.
      
      This attribute counts the number of cells or frames received from 
      the interface on this connection with CLP=1 that have been 
      discarded.
      
      If the connection segments frames into cells, the counter indicates 
      the number of frames discarded. Connections which segment 
      frames into cells have a connectionPointType of 
      connectionEndPoint.
      
      If the connection relays cells without adaptation, the counter 
      indicates the number of cells discarded. Connections which relay 
      cells without adaptation have a connectionPointType of 
      segmentEndPoint or connectingPoint.
      
      AAL1 connections are an exception to this rule; although they have 
      a connectionPointType of connectionEndPoint, they do not do 
      adaptation at this point. Thus, in the AAL1 case, this attribute 
      counts discarded cells.
      
      Discards are done due to congestion, non-conformance with UPC or 
      AAL reassembly problems.
      
      The counter wraps to zero if it exceeds its maximum value of 
      (2**64)-1."
::= { atmIfVptVccStatsEntry 80 }

atmIfVptVccStatsRxCellDiscard OBJECT-TYPE
   SYNTAX     PassportCounter64 
   ACCESS     read-only
   STATUS     mandatory
   DESCRIPTION
     "This attribute counts the number of cells received from the interface 
      on this connection that have been discarded. This count is included 
      in the rxCell attribute.
      
      This count includes cells discarded due to non-conformance with 
      UPC, cells which are part of a frame which has been discarded due 
      to an AAL5 frame reassembly error, cells which are discarded due 
      to congestion, or cells which are received while the next hop 
      connection to which the traffic is directed across the backplane is 
      down. The next hop connection is the Vcc or Vpc identified by the 
      nextHop attribute of the Nrp or Rp component. 
      
      For CQC-based ATM cards, this attribute is applicable only to 
      connections that relay cells without adaptation. Such connections 
      have a connectionPointType of connectionEndPoint or 
      connectingPoint. AAL1 connections are an exception to this rule; 
      although they have a connectionPointType of connectionEndPoint, 
      they do not do adaptation at this point. For Vpts, this attribute 
      provides an aggregated total of all rxCellDiscard values for all such 
      connections associated with the Vpt.
      
      For CQC-based ATM cards, for Vpcs, and Vccs that relay cells 
      without adaptation, this attribute is not applicable and is not 
      displayed.
      
      Discards due to non-conformance with UPC at the VP layer, for a 
      standard Vpt Vcc, are not included in this attribute. These discards 
      are counted in the Vcc's parent Vpt rxCellDiscard attribute.
      
      The counter wraps to zero if it exceeds its maximum value of 
      (2**64)-1."
::= { atmIfVptVccStatsEntry 82 }

atmIfVptVccStatsRxCellDiscardClp OBJECT-TYPE
   SYNTAX     PassportCounter64 
   ACCESS     read-only
   STATUS     mandatory
   DESCRIPTION
     "This attribute counts the number of cells received from the interface 
      on this connection with CLP=1 that have been discarded. This count 
      is included in the rxCell and rxCellDiscard attributes.
      
      This count includes cells discarded due to non-conformance with 
      UPC, cells which are part of a frame which has been discarded due 
      to an AAL5 frame reassembly error, cells which are discarded due 
      to congestion, or cells which are received while the next hop 
      connection to which the traffic is directed across the backplane is 
      down. The next hop connection is the Vcc or Vpc identified by the 
      nextHop attribute of the Nrp or Rp component. 
      
      For CQC-based ATM cards, this attribute is applicable only to 
      connections that relay cells without adaptation. Such connections 
      have a connectionPointType of connectionEndPoint or 
      connectingPoint. AAL1 connections are an exception to this rule; 
      although they have a connectionPointType of connectionEndPoint, 
      they do not do adaptation at this point. For Vpts, this attribute 
      provides an aggregated total of all rxCellDiscardClp values for all 
      such connections associated with the Vpt.
      
      For CQC-based ATM cards, for Vpcs, and Vccs that relay cells 
      without adaptation, this attribute is not applicable and is not 
      displayed.
      
      Discards due to non-conformance with UPC at the VP layer, for a 
      standard Vpt Vcc, are not included in this attribute. These discards 
      are counted in the Vcc's parent Vpt rxCellDiscardClp attribute.
      
      The counter wraps to zero if it exceeds its maximum value of 
      (2**64)-1."
::= { atmIfVptVccStatsEntry 83 }

atmIfVptVccStatsRxFrameDiscard OBJECT-TYPE
   SYNTAX     PassportCounter64 
   ACCESS     read-only
   STATUS     mandatory
   DESCRIPTION
     "This attribute counts the number of frames received from the 
      interface on this connection that have been discarded. This count is 
      independent of the rxCellDiscard attribute.
      
      This count includes frames discarded due to an AAL5 frame 
      reassembly error, frames discarded due to early packet discard 
      (EPD), and frames discarded due to processor (CPU) congestion. 
      This attribute is applicable only for connections that reassemble 
      incoming cells into frames. Connections which reassemble cells 
      into frames have a connectionPointType of connectionEndPoint. 
      AAL1 connections are an exception to this rule; even though they 
      have a connectionPointType of connectionEndPoint, they do not 
      do adaptation at this point. For Vpts, this attribute provides an 
      aggregated total of all rxFrameDiscard values for all applicable 
      connections associated with the Vpt.
      
      For Vpcs, and for Vccs that relay cells without adaptation, this 
      attribute is not applicable and is not displayed.
      
      The counter wraps to zero if it exceeds its maximum value of 
      (2**64)-1."
::= { atmIfVptVccStatsEntry 86 }

atmIfVptVccStatsRxFrameDiscardClp OBJECT-TYPE
   SYNTAX     PassportCounter64 
   ACCESS     read-only
   STATUS     mandatory
   DESCRIPTION
     "This attribute counts the number of discarded frames on this 
      connection that were received from the interface and composed of 
      one or more CLP1 cells. This count is included in the 
      rxFrameDiscard attribute. It is independent of the rxCellDiscard 
      attribute.
      
      This count includes frames discarded due to an AAL5 frame 
      reassembly error, frames discarded due to early packet discard 
      (EPD), and frames discarded due to processor (CPU) congestion. 
      This attribute is applicable only for connections that reassemble 
      incoming cells into frames. Connections which reassemble cells 
      into frames have a connectionPointType of connectionEndPoint. 
      AAL1 connections are an exception to this rule; even though they 
      have a connectionPointType of connectionEndPoint, they do not 
      do adaptation at this point. For Vpts, this attribute provides an 
      aggregated total of all rxFrameDiscardClp values for all applicable 
      connections associated with the Vpt.
      
      For Vpcs, and for Vccs that relay cells without adaptation, this 
      attribute is not applicable and is not displayed.
      
      The counter wraps to zero if it exceeds its maximum value of 
      (2**64)-1."
::= { atmIfVptVccStatsEntry 88 }

atmIfVptVccRxUtilization OBJECT-TYPE
   SYNTAX     Gauge32 (0..200 | 255)
   ACCESS     read-only
   STATUS     mandatory
   DESCRIPTION
     "This attribute indicates the current receive utilization during the 
      most recent minute, expressed as a percentage of the total 
      bandwidth which can be carried by this connection. This attribute is 
      only applicable for Vpts and not for Vpcs or Vccs.
      
      When the Vpt is shaped, the value of this attribute is calculated 
      using its actual shaping rate (ASR) and should not exceed 100.
      
      When the Vpt is unshaped, the value of this attribute is calculated 
      using its peak cell rate (PCR) and should not exceed 200. If the 
      PCR is 0, the value 255 is used."
::= { atmIfVptVccStatsEntry 89 }

atmIfVptVccStatsRxUpcViolationOnEnforcer1 OBJECT-TYPE
   SYNTAX     PassportCounter64 
   ACCESS     read-only
   STATUS     mandatory
   DESCRIPTION
     "This attribute counts the number of UPC violations observed by the 
      Generic Cell Rate Algorithm (GCRA) Enforcer 1. This attribute is 
      only applicable if UPC is enforced or monitored. This attribute is 
      not applicable for standard Vpt Vccs. This attribute is not applicable 
      and is not displayed on CQC-based ATM cards.
      
      When the value of rxTrafficDescType for this connection is 3, 4, 5, 
      6, 7 or 8, Enforcer 1 enforces conformance of traffic received from 
      the interface to PCR CLP0+1.
      
      When the value of rxTrafficDescType for this connection is 9, 
      Enforcer 1 performs the Dynamic Generic Cell Rate Algorithm 
      (DGCRA) used for the Available Bit Rate (ABR) service category.
      
      If UPC is enforced all non-conforming cells are discarded by this 
      enforcer. These discarded cells are included in rxCellDiscard. 
      
      For basic Vpts, this attribute provides an aggregated total of all 
      rxUpcViolationOnEnforcer1 values for the Vccs associated with the 
      Vpt.
      
      The counter wraps to zero if it exceeds its maximum value of 
      (2**64)-1."
::= { atmIfVptVccStatsEntry 90 }

atmIfVptVccStatsRxUpcViolationOnEnforcer2 OBJECT-TYPE
   SYNTAX     PassportCounter64 
   ACCESS     read-only
   STATUS     mandatory
   DESCRIPTION
     "This attribute counts the number of UPC violations observed by the 
      Generic Cell Rate Algorithm (GCRA) Enforcer 2. This attribute is 
      only applicable if UPC is enforced or monitored. This attribute is 
      not applicable for standard Vpt Vccs. This attribute is not applicable 
      and is not displayed on CQC-based ATM cards.
      
      Enforcer2 is applicable only if the rxTrafficDescType for this 
      connection is 4, 5, 6, 7 or 8.
      
      When the value of rxTrafficDescType 4 or 5, Enforcer 2 enforces 
      conformance of traffic received from the interface to PCR CLP0.
      
      When the value of rxTrafficDescType 6, Enforcer 2 enforces 
      conformance of traffic received from the interface to SCR CLP0+1.
      
      When the value of rxTrafficDescType 7 or 8, Enforcer 2 enforces 
      conformance of traffic received from the interface to SCR CLP0.
      
      If UPC is enforced, enforcer 2 discards non-conforming cells for 
      rxTrafficDescType values of 4, 6 and 7. It tags non-conforming cells 
      for rxTrafficDescType values of 5 and 8. Discarded cells are 
      counted in the rxCellDiscard attribute. 
      
      For basic Vpts, this attribute provides an aggregated total of all 
      rxUpcViolationOnEnforcer2 values for the Vccs associated with the 
      Vpt.
      
      The counter wraps to zero if it exceeds its maximum value of 
      (2**64)-1."
::= { atmIfVptVccStatsEntry 92 }

atmIfVptVccStatsRxAal5FrameError OBJECT-TYPE
   SYNTAX     PassportCounter64 
   ACCESS     read-only
   STATUS     mandatory
   DESCRIPTION
     "This attribute counts the number of frames received from the 
      interface on this connection that have AAL5 length errors or AAL5 
      CRC errors. 
      
      This attribute is not applicable and is not displayed on CQC-based 
      ATM cards.
      
      AAL5 length or CRC errors typically occur because of cell discards 
      due to congestion, UPC, or due to corruption of data between the 
      AAL5 segmentation and reassembly end points.
      
      This attribute is applicable only to connections that reassemble 
      incoming cells into frames. Such connections have a 
      connectionPointType of connectionEndPoint. AAL1 connections 
      are an exception to this rule; although they have a 
      connectionPointType of connectionEndPoint, they do not do 
      adaptation at this point. For Vpts, this attribute provides an 
      aggregated total of all rxAal5FrameError values for all applicable 
      connections associated with the Vpt.
      
      For Vpcs, and for Vccs that relay cells without adaptation, this 
      attribute is not applicable and is not displayed.
      
      The counter wraps to zero if it exceeds its maximum value of 
      (2**64)-1."
::= { atmIfVptVccStatsEntry 100 }

atmIfVptVccStatsRxAal5FrameAbort OBJECT-TYPE
   SYNTAX     PassportCounter64 
   ACCESS     read-only
   STATUS     mandatory
   DESCRIPTION
     "This attribute counts the number of frames received from the 
      interface on this connection that have the AAL5 length field set to 
      zero. 
      
      This attribute is not applicable and is not displayed for CQC-based 
      ATM cards.
      
      An AAL5 length of zero is an indication by the far end 
      segmentation point to this reassembly point that the frame is to be 
      discarded without reassembly. This mechanism is typically used by 
      a segmentation point if it detects an error in a frame after some of 
      the cells belonging to that frame have already been transmitted.
      
      This attribute is applicable only to connections that reassemble 
      incoming cells into frames. Such connections have a 
      connectionPointType of connectionEndPoint. AAL1 connections 
      are an exception to this rule; although they have a 
      connectionPointType of connectionEndPoint, they do not do 
      adaptation at this point. For Vpts, this attribute provides an 
      aggregated total of all rxAal5FrameAbort values for all applicable 
      connections associated with the Vpt.
      
      For Vpcs, and for Vccs that relay cells without adaptation, this 
      attribute is not applicable and is not displayed.
      
      The counter wraps to zero if it exceeds its maximum value of 
      (2**64)-1."
::= { atmIfVptVccStatsEntry 102 }

atmIfVptVccTxTdpTable OBJECT-TYPE
   SYNTAX     SEQUENCE OF AtmIfVptVccTxTdpEntry
   ACCESS     not-accessible
   STATUS     obsolete
   DESCRIPTION
     "This attribute is HISTORICAL. Please refer to the attribute of the 
      same name in the group AtmTmOper.
      
      This attribute is a vector of five transmit traffic parameters. The first 
      three elements reflect the settings of the first three elements of the 
      txTrafficDescParm attribute in the AtmTrafficProv group. 
      
      When txTrafficDescType is 1 or 2, parameters 1 through 5 are 
      unused.
      
      In this description, PCR is the greater of either the PCR or the 
      requested shaping rate (parameter 1 or parameter 5) specified in the 
      Traffic group under the Vcd or Vpd.
      
      When txTrafficDescType is 3, parameter 1 represents the PCR for 
      CLP equal to 0 or 1 traffic; parameters 2 and 3 are unused.
      
      When txTrafficDescType is 4, parameter 1 represents the PCR for 
      CLP equal to 0 and 1 traffic; parameter 2 represents the PCR for 
      CLP equal to 0 traffic with cell discard.
      
      When txTrafficDescType is 5, parameter 1 represents the PCR for 
      CLP equal to 0 and 1 traffic; parameter 2 represents the PCR for 
      CLP equal to 0 traffic with cell tagging.
      
      When txTrafficDescType is 6, parameter 1 represents the PCR for 
      CLP equal to 0 and 1 traffic; parameter 2 represents the SCR for 
      CLP equal to 0 and 1 traffic; parameter 3 represents the MBS for 
      CLP equal to 0 and 1 traffic.
      
      When txTrafficDescType is 7, parameter 1 represents the PCR for 
      CLP equal to 0 and 1 traffic; parameter 2 represents the SCR for 
      CLP equal to 0 traffic with cell discard; parameter 3 represents the 
      MBS for CLP equal to 0 traffic.
      
      When txTrafficDescType is 8, parameter 1 represents the PCR for 
      CLP equal to 0 and 1 traffic; parameter 2 represents the SCR for 
      CLP equal to 0 traffic with cell tagging; parameter 3 represents the 
      MBS for CLP equal to 0 traffic
      
      When txTrafficDescType is 3, 4, 5, 6, 7 or 8, parameter 4 reflects 
      the actual shaping rate in cell/s for this connection. This rate is one 
      of the set of available shaping rates for this type of ATM-FP, based 
      on the number of interfaces doing shaping (attribute 
      perVcQueueInterfaces), the provisioned cell rate, the 
      shapingScalingFactor attribute of the AtmResourceControl 
      component, and whether traffic shaping is enabled. A rate of zero 
      (0) indicates that shaping is not performed. 
      
      When txTrafficDescType is 3, 4, 5, 6, 7 or 8, parameter 5 reflects 
      the equivalent cell rate in cell/s for this connection as determined by 
      the Connection Admission Control (CAC) algorithm. The 
      equivalent cell rate is useful in determining the admission 
      characteristics of this connection."
::= { atmIfVptVcc 294 }

atmIfVptVccTxTdpEntry OBJECT-TYPE
   SYNTAX     AtmIfVptVccTxTdpEntry
   ACCESS     not-accessible
   STATUS     obsolete
   DESCRIPTION
     "An entry in the atmIfVptVccTxTdpTable."
   INDEX {
      atmIfIndex,
      atmIfVptIndex,
      atmIfVptVccIndex,
      atmIfVptVccTxTdpIndex }
::= { atmIfVptVccTxTdpTable 1 }

AtmIfVptVccTxTdpEntry ::= SEQUENCE {
   atmIfVptVccTxTdpIndex
      Integer32,
   atmIfVptVccTxTdpValue
      Unsigned32 }

atmIfVptVccTxTdpIndex OBJECT-TYPE
   SYNTAX     Integer32 (1..5)
   ACCESS     not-accessible
   STATUS     obsolete
   DESCRIPTION
     "This variable represents the atmIfVptVccTxTdpTable
      specific index for the atmIfVptVccTxTdpTable."
::= { atmIfVptVccTxTdpEntry 1 }

atmIfVptVccTxTdpValue OBJECT-TYPE
   SYNTAX     Unsigned32 (0..2147483647)
   ACCESS     read-only
   STATUS     obsolete
   DESCRIPTION
     "This variable represents an individual value for the
      atmIfVptVccTxTdpTable."
::= { atmIfVptVccTxTdpEntry 2 }

atmIfVptVccRxTdpTable OBJECT-TYPE
   SYNTAX     SEQUENCE OF AtmIfVptVccRxTdpEntry
   ACCESS     not-accessible
   STATUS     obsolete
   DESCRIPTION
     "This attribute is HISTORICAL. Please refer to the attribute of the 
      same name in the group AtmTmOper.
      
      This attribute is a vector of four traffic parameters whose meanings 
      are defined by the rxTrafficDescType attribute. The values of peak 
      cell rate (PCR), sustained cell rate (SCR) are expressed in cells/s. 
      Maximum burst size (MBS) is expressed in cells. Cell Delay 
      Variation Tolerance (CDVT) is expressed in microseconds.
      
      When rxTrafficDescType is 1 or 2, none of the parameters are used.
      
      When rxTrafficDescType is 3, parameter 1 represents the PCR for 
      CLP equal to 0 and 1 traffic; parameter 4 represents the CDVT.
      
      When rxTrafficDescType is 4, parameter 1 represents the PCR for 
      CLP equal to 0 and 1 traffic; parameter 2 represents the PCR for 
      CLP equal to 0 traffic with cell discard; parameter 4 represents the 
      CDVT.
      
      When rxTrafficDescType is 5, parameter 1 represents the PCR for 
      CLP equal to 0 and 1 traffic; parameter 2 represents the PCR for 
      CLP equal to 0 traffic with cell tagging; parameter 4 represents the 
      CDVT.
      
      When rxTrafficDescType is a 6, parameter 1 represents the PCR for 
      CLP equal to 0 and 1 traffic; parameter 2 represents the SCR for 
      CLP equal to 0 and 1 traffic; parameter 3 represents the MBS for 
      CLP equal to 0 and 1 traffic; parameter 4 represents the CDVT. 
      
      When rxTrafficDescType is 7, parameter 1 represents the PCR for 
      CLP equal to 0 and 1 traffic; parameter 2 represents the SCR for 
      CLP equal to 0 traffic with cell discard; parameter 3 represents the 
      MBS for CLP equal to 0 traffic; parameter 4 represents the CDVT.
      
      When rxTrafficDescType is 8, parameter 1 represents the PCR for 
      CLP equal to 0 and 1 traffic; parameter 2 represents the SCR for 
      CLP equal to 0 traffic with cell tagging; parameter 3 represents the 
      MBS for CLP equal to 0 traffic; parameter 4 represents the CDVT. 
      
      If Upc is disabled for this connection, the values of PCR, SCR, 
      MBS and CDVT is a combination of provisioned parameters. If Upc 
      is enabled, the values of PCR, SCR, MBS, and CDVT is exactly the 
      values used by the usage parameter control hardware in policing the 
      arriving traffic. These may vary slightly from the provisioned values 
      due to granularity of the hardware. In the case where the PCR is 
      equal to the SCR, the effective MBS is zero."
::= { atmIfVptVcc 295 }

atmIfVptVccRxTdpEntry OBJECT-TYPE
   SYNTAX     AtmIfVptVccRxTdpEntry
   ACCESS     not-accessible
   STATUS     obsolete
   DESCRIPTION
     "An entry in the atmIfVptVccRxTdpTable."
   INDEX {
      atmIfIndex,
      atmIfVptIndex,
      atmIfVptVccIndex,
      atmIfVptVccRxTdpIndex }
::= { atmIfVptVccRxTdpTable 1 }

AtmIfVptVccRxTdpEntry ::= SEQUENCE {
   atmIfVptVccRxTdpIndex
      Integer32,
   atmIfVptVccRxTdpValue
      Unsigned32 }

atmIfVptVccRxTdpIndex OBJECT-TYPE
   SYNTAX     Integer32 (1..4)
   ACCESS     not-accessible
   STATUS     obsolete
   DESCRIPTION
     "This variable represents the atmIfVptVccRxTdpTable
      specific index for the atmIfVptVccRxTdpTable."
::= { atmIfVptVccRxTdpEntry 1 }

atmIfVptVccRxTdpValue OBJECT-TYPE
   SYNTAX     Unsigned32 (0..2147483647)
   ACCESS     read-only
   STATUS     obsolete
   DESCRIPTION
     "This variable represents an individual value for the
      atmIfVptVccRxTdpTable."
::= { atmIfVptVccRxTdpEntry 2 }

atmIfVptVccTxQThreshTable OBJECT-TYPE
   SYNTAX     SEQUENCE OF AtmIfVptVccTxQThreshEntry
   ACCESS     not-accessible
   STATUS     obsolete
   DESCRIPTION
     "This attribute is HISTORICAL. Please refer to the attribute of the 
      same name in the group AtmTmOper.
      
      This attribute indicates the queue limit and the discard thresholds 
      for the transmit queue of this connection. 
      
      The first element indicates the queue limit. Depending upon the 
      atmServiceCategory of the connection, the provisioned value of the 
      transmit queue limit is derived from the txQueueLimit attribute 
      under one of the subcomponents of the AtmIf CA component. If the 
      connection has traffic shaping disabled, then this attribute relates to 
      the common queue. If traffic shaping is enabled, then this attribute 
      relates to the per-VC queue.
      
      The second element is the threshold that marks the transition from 
      congestion state 1 to congestion state 0. This is the threshold at 
      which traffic with discard priority (DP) = 1 is discarded. This 
      threshold is set approximately at 90 percent of the first parameter, 
      the operational queue limit.
      
      The third element is the threshold that marks the transition from 
      congestion state 2 to congestion state 1. This is the threshold at 
      which traffic with DP = 2 is discarded. This threshold is set 
      approximately at 75 percent of the first parameter, the operational 
      queue limit.
      
      The fourth element is the threshold that marks the transition from 
      congestion state 3 to congestion state 2. This is the threshold at 
      which traffic with DP = 3 is discarded. This threshold is set 
      approximately at 35 percent of the first parameter, the operational 
      queue limit."
::= { atmIfVptVcc 352 }

atmIfVptVccTxQThreshEntry OBJECT-TYPE
   SYNTAX     AtmIfVptVccTxQThreshEntry
   ACCESS     not-accessible
   STATUS     obsolete
   DESCRIPTION
     "An entry in the atmIfVptVccTxQThreshTable."
   INDEX {
      atmIfIndex,
      atmIfVptIndex,
      atmIfVptVccIndex,
      atmIfVptVccTxQThreshIndex }
::= { atmIfVptVccTxQThreshTable 1 }

AtmIfVptVccTxQThreshEntry ::= SEQUENCE {
   atmIfVptVccTxQThreshIndex
      Integer32,
   atmIfVptVccTxQThreshValue
      Unsigned32 }

atmIfVptVccTxQThreshIndex OBJECT-TYPE
   SYNTAX     Integer32 (0..3)
   ACCESS     not-accessible
   STATUS     obsolete
   DESCRIPTION
     "This variable represents the atmIfVptVccTxQThreshTable
      specific index for the atmIfVptVccTxQThreshTable."
::= { atmIfVptVccTxQThreshEntry 1 }

atmIfVptVccTxQThreshValue OBJECT-TYPE
   SYNTAX     Unsigned32 (0..30720)
   ACCESS     read-only
   STATUS     obsolete
   DESCRIPTION
     "This variable represents an individual value for the
      atmIfVptVccTxQThreshTable."
::= { atmIfVptVccTxQThreshEntry 2 }

atmIfVptVccFqpTable OBJECT-TYPE
   SYNTAX     SEQUENCE OF AtmIfVptVccFqpEntry
   ACCESS     not-accessible
   STATUS     obsolete
   DESCRIPTION
     "This attribute is HISTORICAL. Please refer to the attribute of the 
      same name in the group AtmTmOper.
      
      This attribute is a vector of three elements that indicate the quality 
      of service parameters for the forward direction for this connection. 
      This attribute is used for SPVC and SVC connections on a PNNI 
      interface.
      
      The cdv element indicates the acceptable peak-to-peak Cell Delay 
      Variation (CDV) of real-time connections (CBR, and rt-VBR). 
      
      The ctd element indicates the acceptable maximum Cell Transfer 
      Delay (maxCtd) of real-time connections (CBR, and rt-VBR). 
      
      The clr element indicates the acceptable Cell Loss Ratio (CLR) of 
      CBR, rt-VBR, and nrt-VBR connections."
::= { atmIfVptVcc 357 }

atmIfVptVccFqpEntry OBJECT-TYPE
   SYNTAX     AtmIfVptVccFqpEntry
   ACCESS     not-accessible
   STATUS     obsolete
   DESCRIPTION
     "An entry in the atmIfVptVccFqpTable."
   INDEX {
      atmIfIndex,
      atmIfVptIndex,
      atmIfVptVccIndex,
      atmIfVptVccFqpIndex }
::= { atmIfVptVccFqpTable 1 }

AtmIfVptVccFqpEntry ::= SEQUENCE {
   atmIfVptVccFqpIndex
      INTEGER,
   atmIfVptVccFqpValue
      Unsigned32 }

atmIfVptVccFqpIndex OBJECT-TYPE
   SYNTAX     INTEGER  {
                 cdv(0),
                 ctd(1),
                 clr(2) }
   ACCESS     not-accessible
   STATUS     obsolete
   DESCRIPTION
     "This variable represents the atmIfVptVccFqpTable
      specific index for the atmIfVptVccFqpTable."
::= { atmIfVptVccFqpEntry 1 }

atmIfVptVccFqpValue OBJECT-TYPE
   SYNTAX     Unsigned32 (0..2147483647)
   ACCESS     read-only
   STATUS     obsolete
   DESCRIPTION
     "This variable represents an individual value for the
      atmIfVptVccFqpTable."
::= { atmIfVptVccFqpEntry 2 }

atmIfVptVccBqpTable OBJECT-TYPE
   SYNTAX     SEQUENCE OF AtmIfVptVccBqpEntry
   ACCESS     not-accessible
   STATUS     obsolete
   DESCRIPTION
     "This attribute is HISTORICAL. Please refer to the attribute of the 
      same name in the group AtmTmOper.
      
      This attribute is a vector of three elements that indicate the quality 
      of service parameters for the backward direction for this 
      connection. This attribute is used for SPVC and SVC connections 
      on a PNNI interface.
      
      The cdv element indicates the acceptable peak-to-peak Cell Delay 
      Variation (CDV) of real-time connections (CBR, and rt-VBR). 
      
      The ctd element indicates the acceptable maximum Cell Transfer 
      Delay (maxCtd) of real-time connections (CBR, and rt-VBR). 
      
      The clr element indicates the acceptable Cell Loss Ratio (CLR) of 
      CBR, rt-VBR, and nrt-VBR connections."
::= { atmIfVptVcc 358 }

atmIfVptVccBqpEntry OBJECT-TYPE
   SYNTAX     AtmIfVptVccBqpEntry
   ACCESS     not-accessible
   STATUS     obsolete
   DESCRIPTION
     "An entry in the atmIfVptVccBqpTable."
   INDEX {
      atmIfIndex,
      atmIfVptIndex,
      atmIfVptVccIndex,
      atmIfVptVccBqpIndex }
::= { atmIfVptVccBqpTable 1 }

AtmIfVptVccBqpEntry ::= SEQUENCE {
   atmIfVptVccBqpIndex
      INTEGER,
   atmIfVptVccBqpValue
      Unsigned32 }

atmIfVptVccBqpIndex OBJECT-TYPE
   SYNTAX     INTEGER  {
                 cdv(0),
                 ctd(1),
                 clr(2) }
   ACCESS     not-accessible
   STATUS     obsolete
   DESCRIPTION
     "This variable represents the atmIfVptVccBqpTable
      specific index for the atmIfVptVccBqpTable."
::= { atmIfVptVccBqpEntry 1 }

atmIfVptVccBqpValue OBJECT-TYPE
   SYNTAX     Unsigned32 (0..2147483647)
   ACCESS     read-only
   STATUS     obsolete
   DESCRIPTION
     "This variable represents an individual value for the
      atmIfVptVccBqpTable."
::= { atmIfVptVccBqpEntry 2 }


-- AtmIf/n Vcc/vpi.vci VirtualChannelDescriptor,
-- AtmIf/n Vpt/vpi Vcc/vci VirtualChannelDescriptor
-- The Vcd component contains provisioning information about its 
-- parent Vcc component.

atmIfVptVccVcd OBJECT IDENTIFIER ::= { atmIfVptVcc 2 }



atmIfVptVccVcdRowStatusTable OBJECT-TYPE
   SYNTAX     SEQUENCE OF AtmIfVptVccVcdRowStatusEntry
   ACCESS     not-accessible
   STATUS     mandatory
   DESCRIPTION
     "This entry controls the addition and deletion of 
      atmIfVptVccVcd components."
::= { atmIfVptVccVcd 1 }

atmIfVptVccVcdRowStatusEntry OBJECT-TYPE
   SYNTAX     AtmIfVptVccVcdRowStatusEntry
   ACCESS     not-accessible
   STATUS     mandatory
   DESCRIPTION
     "A single entry in the table represents a single 
      atmIfVptVccVcd component."
   INDEX {
      atmIfIndex,
      atmIfVptIndex,
      atmIfVptVccIndex,
      atmIfVptVccVcdIndex }
::= { atmIfVptVccVcdRowStatusTable 1 }

AtmIfVptVccVcdRowStatusEntry ::= SEQUENCE {
   atmIfVptVccVcdRowStatus
      RowStatus,
   atmIfVptVccVcdComponentName
      DisplayString,
   atmIfVptVccVcdStorageType
      StorageType,
   atmIfVptVccVcdIndex
      NonReplicated }

atmIfVptVccVcdRowStatus OBJECT-TYPE
   SYNTAX     RowStatus 
   ACCESS     read-only
   STATUS     mandatory
   DESCRIPTION
     "This variable is used as the basis for SNMP naming of
      atmIfVptVccVcd components.
      These components cannot be added nor deleted."
::= { atmIfVptVccVcdRowStatusEntry 1 }

atmIfVptVccVcdComponentName OBJECT-TYPE
   SYNTAX     DisplayString 
   ACCESS     read-only
   STATUS     mandatory
   DESCRIPTION
     "This variable provides the component's string name for
      use with the ASCII Console Interface"
::= { atmIfVptVccVcdRowStatusEntry 2 }

atmIfVptVccVcdStorageType OBJECT-TYPE
   SYNTAX     StorageType 
   ACCESS     read-only
   STATUS     mandatory
   DESCRIPTION
     "This variable represents the storage type value for the
      atmIfVptVccVcd tables."
::= { atmIfVptVccVcdRowStatusEntry 4 }

atmIfVptVccVcdIndex OBJECT-TYPE
   SYNTAX     NonReplicated 
   ACCESS     not-accessible
   STATUS     mandatory
   DESCRIPTION
     "This variable represents the index for the atmIfVptVccVcd tables."
::= { atmIfVptVccVcdRowStatusEntry 10 }

atmIfVptVccVcdLbkTable OBJECT-TYPE
   SYNTAX     SEQUENCE OF AtmIfVptVccVcdLbkEntry
   ACCESS     not-accessible
   STATUS     mandatory
   DESCRIPTION
     "This group contains the provisionable loopback attributes for a Vcc, 
      Vpc, or Vpt component.
      
      Note that certain loopback requests may not be possible on a given 
      connection. In such cases, the corresponding operational loopback 
      attribute in the Status group of the Vcc, Vpc, or Vpt component is 
      set to notApplicable and the requested loopback is not performed.
      
      If loopbacks are provisioned to be on, and for any reason the 
      segment or end-to-end OAM loopback cells are not relayed, the 
      connection component becomes troubled, and user cell traffic may 
      be discarded. If loopbacks are provisioned to be on, all of the nodes 
      in the segment, and external networks which are in the end-to-end 
      connection must relay the OAM loopback cells."
::= { atmIfVptVccVcd 100 }

atmIfVptVccVcdLbkEntry OBJECT-TYPE
   SYNTAX     AtmIfVptVccVcdLbkEntry
   ACCESS     not-accessible
   STATUS     mandatory
   DESCRIPTION
     "An entry in the atmIfVptVccVcdLbkTable."
   INDEX {
      atmIfIndex,
      atmIfVptIndex,
      atmIfVptVccIndex,
      atmIfVptVccVcdIndex }
::= { atmIfVptVccVcdLbkTable 1 }

AtmIfVptVccVcdLbkEntry ::= SEQUENCE {
   atmIfVptVccVcdSegLinkSideLoopback
      INTEGER,
   atmIfVptVccVcdSegSwitchSideLoopback
      INTEGER,
   atmIfVptVccVcdEndToEndLoopback
      INTEGER,
   atmIfVptVccVcdLoopbackMonitoring
      INTEGER }

atmIfVptVccVcdSegLinkSideLoopback OBJECT-TYPE
   SYNTAX     INTEGER  {
                 on(0),
                 off(1),
                 sameAsInterface(2) }
   ACCESS     read-write
   STATUS     mandatory
   DESCRIPTION
     "This attribute specifies whether link-side segment loopback 
      insertion should be performed on this connection. 
      
      When sameAsInterface is selected, the link-side segment loopback 
      insertion for the connection is based on the segLinkSideLoopback 
      attribute of the connection's parent AtmIf componentif the ATM 
      interface has link-side segment loopback insertion turned on, then 
      link-side segment loopback insertion is also on for the connection. 
      
      When on or off is selected, link-side segment loopback insertion is 
      turned on or off respectively for the connection regardless of the 
      provisioning of the parent AtmIf component.
      
      Note that link-side segment loopback insertion is not possible if the 
      connectionPointType attribute of the Vcc or Vpc component is 
      connectingPoint. Link-side segment loopback insertion is also not 
      possible if the distributionType of the Vcc is pointToMultipoint. In 
      such cases, the associated segLinkSideLoopbackState attribute 
      indicates notApplicable and link-side segment loopback insertion is 
      not performed. Link-side segment loopback insertion is always 
      possible on a Vpt."
   DEFVAL     { sameAsInterface }
::= { atmIfVptVccVcdLbkEntry 10 }

atmIfVptVccVcdSegSwitchSideLoopback OBJECT-TYPE
   SYNTAX     INTEGER  {
                 on(0),
                 off(1),
                 sameAsInterface(2) }
   ACCESS     read-write
   STATUS     mandatory
   DESCRIPTION
     "This attribute specifies whether switch-side segment loopback 
      insertion should be performed on this connection.
      
      When sameAsInterface is selected, the switch-side segment 
      loopback for the connection is based on the segSwitchSideLoopback 
      attribute of the connection's parent AtmIf componentif the ATM 
      interface has switch-side segment loopback insertion turned on, 
      then switch-side segment loopback insertion is also on for the 
      connection. 
      
      When on or off is selected, switch-side segment loopback insertion 
      is turned on or off respectively for the connection regardless of the 
      provisioning of the parent AtmIf component.
      
      Note that switch-side segment loopback insertion is not possible if 
      the connectionPointType attribute of the Vcc or Vpc component is 
      connectingPoint or connectionEndPoint. Switch-side segment 
      loopback insertion is also not possible if the distributionType of the 
      Vcc is pointToMultipoint In such cases, the associated 
      segSwitchSideLoopbackState attribute indicates notApplicable and 
      switch-side segment loopback insertion is not performed. Switch-
      side segment loopback is never possible on a Vpt."
   DEFVAL     { sameAsInterface }
::= { atmIfVptVccVcdLbkEntry 20 }

atmIfVptVccVcdEndToEndLoopback OBJECT-TYPE
   SYNTAX     INTEGER  {
                 on(0),
                 off(1),
                 sameAsInterface(2) }
   ACCESS     read-write
   STATUS     mandatory
   DESCRIPTION
     "This attribute specifies whether end-to-end loopback insertion 
      should be performed on this connection.
      
      When sameAsInterface is selected, the end-to-end loopback for the 
      connection is based on the endToEndLoopback attribute of the 
      connection's parent AtmIf componentif the ATM interface has 
      end-to-end loopback insertion turned on, then end-to-end loopback 
      insertion is also on for the connection. 
      
      When on or off is selected, end-to-end loopback insertion is turned 
      on or off respectively for the connection regardless of the 
      provisioning of the parent AtmIf component.
      
      Note that end-to-end loopback insertion is not possible if the 
      connectionPointType attribute of the Vcc or Vpc component is 
      connectingPoint or segmentEndPoint. End-to-end loopback 
      insertion is also not possible if the distributionType of the Vcc is 
      pointToMultipoint. In such cases, the associated 
      endToEndLoopbackState attribute indicates notApplicable and end-
      to-end loopback insertion is not performed. End-to-end loopback 
      insertion is always possible on a Vpt."
   DEFVAL     { sameAsInterface }
::= { atmIfVptVccVcdLbkEntry 30 }

atmIfVptVccVcdLoopbackMonitoring OBJECT-TYPE
   SYNTAX     INTEGER  {
                 on(0),
                 off(1),
                 sameAsInterface(2) }
   ACCESS     read-write
   STATUS     mandatory
   DESCRIPTION
     "This attribute specifies whether or not a connection monitors the 
      OAM stream for loopback cells. Currently this attributed is only 
      applied to Passport-specific trace cells and only affects 
      connectingPoints.
      
      When sameAsInterface is selected, the trace visibility for the 
      connection is based on the traceVisible attribute of the connection's 
      parent AtmIf componentif the ATM interface is trace visible, then 
      the connection is also trace visible. 
      
      When on or off is selected, the connection is nor isn't visible to 
      trace cells respectively for the connection regardless of the 
      provisioning of the parent AtmIf component.
      
      Note that trace visibility only affects connections whose 
      connectionPointType attribute of the Vcc or Vpc component is 
      connectingPoint. Trace visibility is also not possible if the 
      distributionType of the Vcc is pointToMultipoint."
   DEFVAL     { sameAsInterface }
::= { atmIfVptVccVcdLbkEntry 1000 }

atmIfVptVccVcdTrafficTable OBJECT-TYPE
   SYNTAX     SEQUENCE OF AtmIfVptVccVcdTrafficEntry
   ACCESS     not-accessible
   STATUS     mandatory
   DESCRIPTION
     "This group contains traffic related provisionable attributes for the 
      Vcc and Vpc components. The attributes' operational values are 
      reflected in the Traffic group for these components. Changing any 
      of the attributes in this group causes a service interruption on the 
      Vcc or Vpc component."
::= { atmIfVptVccVcd 110 }

atmIfVptVccVcdTrafficEntry OBJECT-TYPE
   SYNTAX     AtmIfVptVccVcdTrafficEntry
   ACCESS     not-accessible
   STATUS     mandatory
   DESCRIPTION
     "An entry in the atmIfVptVccVcdTrafficTable."
   INDEX {
      atmIfIndex,
      atmIfVptIndex,
      atmIfVptVccIndex,
      atmIfVptVccVcdIndex }
::= { atmIfVptVccVcdTrafficTable 1 }

AtmIfVptVccVcdTrafficEntry ::= SEQUENCE {
   atmIfVptVccVcdTxTrafficDescType
      INTEGER,
   atmIfVptVccVcdTxQosClass
      INTEGER,
   atmIfVptVccVcdFwdQosClass
      INTEGER,
   atmIfVptVccVcdHoldingPriority
      INTEGER,
   atmIfVptVccVcdRxTrafficDescType
      INTEGER,
   atmIfVptVccVcdRxQosClass
      INTEGER,
   atmIfVptVccVcdBwdQosClass
      INTEGER,
   atmIfVptVccVcdAtmServiceCategory
      INTEGER,
   atmIfVptVccVcdTrafficShaping
      INTEGER,
   atmIfVptVccVcdUnshapedTransmitQueueing
      INTEGER,
   atmIfVptVccVcdUsageParameterControl
      INTEGER,
   atmIfVptVccVcdBearerClassBbc
      INTEGER,
   atmIfVptVccVcdTransferCapabilityBbc
      INTEGER,
   atmIfVptVccVcdClippingBbc
      INTEGER,
   atmIfVptVccVcdBestEffort
      INTEGER,
   atmIfVptVccVcdFwdFrameDiscard
      INTEGER,
   atmIfVptVccVcdBwdFrameDiscard
      INTEGER }

atmIfVptVccVcdTxTrafficDescType OBJECT-TYPE
   SYNTAX     INTEGER  {
                 n1(1),
                 n2(2),
                 n3(3),
                 n4(4),
                 n5(5),
                 n6(6),
                 n7(7),
                 n8(8),
                 n9(9) }
   ACCESS     read-write
   STATUS     obsolete
   DESCRIPTION
     "This attribute is migrated to the AtmTmProv group.
      
      This attribute specifies the type of traffic management which is 
      applied to the transmit direction of this connection as defined in the 
      ATM Forum. The txTrafficDescType determines the number and 
      meaning of the parameters in the txTrafficDescParm attribute."
   DEFVAL     { n1 }
::= { atmIfVptVccVcdTrafficEntry 10 }

atmIfVptVccVcdTxQosClass OBJECT-TYPE
   SYNTAX     INTEGER  {
                 unspecified(0),
                 constantBitRate(1),
                 variableBitRate(2),
                 connectionOriented(3),
                 connectionless(4) }
   ACCESS     read-write
   STATUS     obsolete
   DESCRIPTION
     "This attribute specifies the quality of service for the transmit 
      direction for this connection.
      
      The constantBitRate class refers to traffic offered on services such 
      as a constant bit rate video service. This traffic is highest priority.
      
      The variableBitRate class refers to traffic offered on services such 
      as packetized audio and video.
      
      The connectionOriented class refers to connection-oriented traffic 
      such as Frame Relay or X.25 traffic. 
      
      The connectionless traffic refers to traffic offered through 
      connectionless trunks such as certain LAN protocols.
      
      The unspecified class supports a 'best effort' type of service, where 
      there is a minimum guarantee of bandwidth. This traffic is lowest 
      priority.
      
      This attribute is obsolete. The value is migrated into 
      atmServiceCategory. The atmServiceCategory applies in both 
      transmit and receive directions.
      
      unspecified maps to unspecifiedBitRate;
      constantBitRate maps to constantBitRate;
      variableBitRate maps to variableBitRateRt;
      connectionOriented maps to variableBitRateNrt
      connectionless maps to variableBitRateNrt"
   DEFVAL     { connectionOriented }
::= { atmIfVptVccVcdTrafficEntry 20 }

atmIfVptVccVcdFwdQosClass OBJECT-TYPE
   SYNTAX     INTEGER  {
                 n0(0),
                 n1(1),
                 n2(2),
                 n3(3),
                 n4(4) }
   ACCESS     read-write
   STATUS     obsolete
   DESCRIPTION
     "This attribute is migrated to the AtmTmProv group.
      
      This attribute specifies the quality of service for the forward 
      direction for this connection. This attribute is only used for SPVC 
      connections.
      
      Class 1 supports a QOS that meets Service Class A performance 
      requirements (Circuit emulation, constant bit rate video).
      
      Class 2 supports a QOS that meets Service Class B performance 
      requirements (Variable bit rate audio and video).
      
      Class 3 supports a QOS that meets Service Class C performance 
      requirements (Connection-Oriented Data Transfer).
      
      Class 4 supports a QOS that meets Service Class D performance 
      requirements (Connectionless Data Transfer).
      
      Class 0 is the unspecified bit rate QOS class; no objective is 
      specified for the performance parameters."
   DEFVAL     { n0 }
::= { atmIfVptVccVcdTrafficEntry 21 }

atmIfVptVccVcdHoldingPriority OBJECT-TYPE
   SYNTAX     INTEGER  {
                 n0(0),
                 n1(1),
                 n2(2),
                 n3(3),
                 n4(4) }
   ACCESS     read-write
   STATUS     obsolete
   DESCRIPTION
     "This attribute is migrated to the AtmTmProv group.
      
      This attribute specifies the holding priority of this connection. In a 
      situation where the link bandwidth fluctuates, such as over an IMA 
      link, holding priority is used to determine which connections are 
      held and which are released. Holding priority 4 connections are the 
      first to be released. Holding priority 0 connections are the last to be 
      released. This value provisioned in the Vcd or Vpd may be 
      overridden by certain applications, for example Vcc Test, which run 
      over this connection. The default holding priority for a provisioned 
      connection is higher then default holding priorities for dynamic 
      (SVC) connections."
   DEFVAL     { n2 }
::= { atmIfVptVccVcdTrafficEntry 25 }

atmIfVptVccVcdRxTrafficDescType OBJECT-TYPE
   SYNTAX     INTEGER  {
                 n1(1),
                 n2(2),
                 n3(3),
                 n4(4),
                 n5(5),
                 n6(6),
                 n7(7),
                 n8(8),
                 sameAsTx(15) }
   ACCESS     read-write
   STATUS     obsolete
   DESCRIPTION
     "This attribute is migrated to the AtmTmProv group.
      
      This attribute specifies the type of traffic management which is 
      applied to the receive direction of this connection as defined in the 
      ATM Forum. The rxTrafficDescType determines the number and 
      meaning of the parameters in the rxTrafficDescParm attribute
      
      When sameAsTx is selected, the rxTrafficDescType as well as the 
      rxTrafficDescParm are taken from the transmit values."
   DEFVAL     { sameAsTx }
::= { atmIfVptVccVcdTrafficEntry 30 }

atmIfVptVccVcdRxQosClass OBJECT-TYPE
   SYNTAX     INTEGER  {
                 unspecified(0),
                 constantBitRate(1),
                 variableBitRate(2),
                 connectionOriented(3),
                 connectionless(4),
                 sameAsTx(15) }
   ACCESS     read-write
   STATUS     obsolete
   DESCRIPTION
     "This attribute specifies the quality of service for the receive 
      direction for this connection.
      
      The constantBitRate class refers to traffic offered on services such 
      as a constant bit rate video service. 
      
      The variableBitRate class refers to traffic offered on services such 
      as packetized audio and video. 
      
      The connectionOriented class refers to connection-oriented traffic.
      
      The connectionless traffic refers to traffic offered through 
      connectionless trunks. 
      
      The unspecified class supports a 'best effort' type of service, where 
      there is a minimum guarantee of bandwidth. 
      
      The sameAsTx selection sets the receive quality of service to be the 
      same as the transmit quality of service.
      
      This attribute is obsolete. The value of txQosClass is migrated into 
      atmServiceCategory. The value of this attribute is ignored. 
      AtmServiceCategory applies in both transmit and receive directions."
   DEFVAL     { sameAsTx }
::= { atmIfVptVccVcdTrafficEntry 40 }

atmIfVptVccVcdBwdQosClass OBJECT-TYPE
   SYNTAX     INTEGER  {
                 n0(0),
                 n1(1),
                 n2(2),
                 n3(3),
                 n4(4),
                 sameAsFwd(15) }
   ACCESS     read-write
   STATUS     obsolete
   DESCRIPTION
     "This attribute is migrated to the AtmTmProv group.
      
      This attribute specifies the quality of service for the backward 
      direction for this connection. This attribute is only used for SPVC 
      connections.
      
      Class 1 supports a QOS that meets Service Class A performance 
      requirements (Circuit emulation, constant bit rate video).
      
      Class 2 supports a QOS that meets Service Class B performance 
      requirements (Variable bit rate audio and video).
      
      Class 3 supports a QOS that meets Service Class C performance 
      requirements (Connection-Oriented Data Transfer).
      
      Class 4 supports a QOS that meets Service Class D performance 
      requirements (Connectionless Data Transfer).
      
      Class 0 is the unspecified bit rate QOS class; no objective is 
      specified for the performance parameters.
      
      The sameAsFwd selection sets the backward quality of service to 
      be the same as the forward quality of service."
   DEFVAL     { sameAsFwd }
::= { atmIfVptVccVcdTrafficEntry 41 }

atmIfVptVccVcdAtmServiceCategory OBJECT-TYPE
   SYNTAX     INTEGER  {
                 unspecifiedBitRate(0),
                 constantBitRate(1),
                 rtVariableBitRate(2),
                 nrtVariableBitRate(3),
                 derivedFromBBC(15) }
   ACCESS     read-write
   STATUS     obsolete
   DESCRIPTION
     "This attribute is migrated to the AtmTmProv group.
      
      This attribute specifies the ATM service category for both directions 
      of the connection. 
      
      The value derivedFromBBC may only be used if the SrcPvc 
      component is provisioned under this Vcc.Otherwise a specific ATM 
      service category must be specified. 
      
      If this attribute is set to derivedFromBBC, the Broadband Bearer 
      Capability (BBC) and bestEffort attributes are used to determine the 
      atmServiceCategory of this connection. 
      
      If this attribute is set to other than derivedFromBBC, the value of 
      this attribute is used to override the provisioned BBC Information 
      Element parameters. In those cases, the BBC attributes are not used. 
      
      The constantBitRate service category is intended for real time 
      applications, that is those requiring tightly constrained delay and 
      delay variation, as would be appropriate for voice and video 
      applications. The consistent availability of a fixed quantity of 
      bandwidth is considered appropriate for CBR service. Cells which 
      are delayed beyond the value specified by Cell Transfer Delay are 
      assumed to be of significantly reduce value to the application.
      
      The rtVariableBitRate service category is intended for real time 
      applications, that is those requiring tightly constrained delay and 
      delay variation, as would be appropriate for voice and video 
      applications. Sources are expected to transmit at a rate which varies 
      with time. Equivalently, the source can be described as 'bursty'. 
      Cells which are delayed beyond the value specified by CTD are 
      assumed to be of significantly reduced value to the application. Real 
      time VBR service may support statistical multiplexing of real time 
      sources.
      
      The nrtVariableBitRate service category is intended for non-real 
      time applications which have bursty traffic characteristics and which 
      can be characterized in terms of a PCR, SCR, and MBS. For those 
      cells which are transferred within the traffic contract, the application 
      expects a low cell loss ratio. For all connections, it expects a bound 
      on the mean cell transfer delay. Non-real time VBR service may 
      support statistical multiplexing of connections.
      
      The unspecifiedBitRate service is intended for non-real time 
      applications; that is, those not requiring tightly constrained delay 
      and delay variation. UBR sources are expected to be bursty. UBR 
      service supports a high degree of statistical multiplexing among 
      sources. UBR service does not specify traffic related service 
      guarantees. No numerical commitments are made with respect to 
      the cell loss ratio experienced by a UBR connection, or as to the 
      cell transfer delay experienced by cells on the connection."
   DEFVAL     { unspecifiedBitRate }
::= { atmIfVptVccVcdTrafficEntry 42 }

atmIfVptVccVcdTrafficShaping OBJECT-TYPE
   SYNTAX     INTEGER  {
                 disabled(1),
                 sameAsInterface(2) }
   ACCESS     read-write
   STATUS     obsolete
   DESCRIPTION
     "This attribute is migrated to the AtmTmProv group.
      
      This attribute specifies whether this connection uses traffic shaping 
      when transmitting traffic to the ATM interface.
      
      When sameAsInterface is selected, traffic shaping for the 
      connection is based on the trafficShaping attribute of the 
      connection's parent AtmIf componentif the ATM interface has 
      traffic shaping enabled, then traffic shaping is enabled for the 
      connection. Note that enabling traffic shaping may have no effect 
      under certain cases. These cases are listed in the description of the 
      trafficShaping operational attribute, which is under the Vcc and Vpc 
      components.
      
      When disabled is selected, traffic shaping for this connection is 
      disabled regardless of the provisioning of the parent AtmIf 
      component."
   DEFVAL     { sameAsInterface }
::= { atmIfVptVccVcdTrafficEntry 50 }

atmIfVptVccVcdUnshapedTransmitQueueing OBJECT-TYPE
   SYNTAX     INTEGER  {
                 common(1),
                 sameAsInterface(3) }
   ACCESS     read-write
   STATUS     obsolete
   DESCRIPTION
     "This attribute is migrated to the AtmTmProv group.
      
      This attribute only applies when this connection is unshaped. This 
      attribute defines the transmit queueing method for this connection if 
      it is unshaped. Refer to the unshapedTransmitQueueing attribute 
      under the AtmIf for more details on the meaning of this attribute. 
      
      When this attribute is set to sameAsInterface, the value from the 
      AtmIf is used. 
      
      When this attribute is set to common, transmit traffic on this 
      unshaped connection is destined for the common queue."
   DEFVAL     { sameAsInterface }
::= { atmIfVptVccVcdTrafficEntry 60 }

atmIfVptVccVcdUsageParameterControl OBJECT-TYPE
   SYNTAX     INTEGER  {
                 disabled(1),
                 sameAsInterface(2) }
   ACCESS     read-write
   STATUS     obsolete
   DESCRIPTION
     "This attribute is migrated to the AtmTmProv group.
      
      This attribute specifies whether this connection enforces usage 
      parameter control when receiving traffic from the ATM interface.
      
      When sameAsInterface is selected, UPC for the connection is 
      based on the usageParameterControl attribute of the connection's 
      parent AtmIf componentif the ATM interface has UPC enabled, 
      then UPC is enabled for the connection. Note that enabling UPC 
      may have no effect under certain cases. These cases are listed in the 
      description of the usageParameterControl operational attribute, 
      which is under the Vcc and Vpc components.
      
      When disabled is selected, UPC for this connection is disabled 
      regardless of the provisioning of the parent AtmIf component."
   DEFVAL     { sameAsInterface }
::= { atmIfVptVccVcdTrafficEntry 70 }

atmIfVptVccVcdBearerClassBbc OBJECT-TYPE
   SYNTAX     INTEGER  {
                 a(1),
                 c(3),
                 x(16),
                 vp(24),
                 derivedFromServiceCategory(31) }
   ACCESS     read-write
   STATUS     obsolete
   DESCRIPTION
     "This attribute is migrated to the AtmTmProv group.
      
      This attribute specifies the bearer capability. This attribute is only 
      used for SPVC and SPVP connections. It is one of the Broadband 
      Bearer Capability (BBC) attributes. The purpose of the BBC 
      information element is to indicate a requested broadband 
      connection-oriented bearer service to be provided by the network.
      
      The value derivedFromServiceCategory specifies that the actual 
      value which is used for this connection is derived from the value of 
      the atmServiceCategory. Either, this attribute must be set to 
      derivedFromServiceCategory, or the atmServiceCategory attribute 
      must be set to derivedFromBBC, but not both.
      
      Class a service is a connection-oriented, constant bit rate ATM 
      transport service. Class a service has end to end timing 
      requirements and may require stringent cell loss, cell delay and cell 
      delay variation performance.When a is set, the user is requesting 
      more than an ATM only service. The network may look at the AAL 
      to provide interworking based upon its contents. 
      
      Class c service is a connection-oriented, variable bit rate ATM 
      transport service. Class c service has no end-to-end timing 
      requirements. When c is set, the user is requesting more than an 
      ATM only service. The network interworking function may look at 
      the AAL and provide service based on it.
      
      Class x service is a connection-oriented ATM transport service 
      where the AAL, trafficType (vbr or cbr) and timing requirements 
      are user defined (that is, transparent to the network).When x is set 
      the user is requesting an ATM only service from the network.
      
      Class vp service is used to specify a transparent VP service. When 
      the value of this attribute is vp, the user is requesting an ATM only 
      service from the network. In this case, the network shall not process 
      any higher layer protocol. This service differs from class x service 
      in that with the class vp service both the VCI field (except or VCI 
      values 0, 3, 4, and 6 through 15) and Payload Type field are 
      transported transparently by the network. This attribute value is 
      only applicable to SPVP connections."
   DEFVAL     { derivedFromServiceCategory }
::= { atmIfVptVccVcdTrafficEntry 71 }

atmIfVptVccVcdTransferCapabilityBbc OBJECT-TYPE
   SYNTAX     INTEGER  {
                 n0(0),
                 n1(1),
                 n2(2),
                 n5(5),
                 n8(8),
                 n9(9),
                 n10(10),
                 notApplicable(30),
                 derivedFromServiceCategory(31) }
   ACCESS     read-write
   STATUS     obsolete
   DESCRIPTION
     "This attribute is migrated to the AtmTmProv group.
      
      This attribute specifies the transfer capability for this connection. 
      Uni 3.0/3.1 traffic type and end-to-end timing parameters are 
      mapped into this parameter as follows:
      <transferCapability: TrafficType, Timing>
      0: NoIndication, NoIndication
      1: NoIndication, yes
      2: NoIndication, no
      5: CBR, yes
      8: VBR, NoIndication
      9: VBR, yes
      10: VBR, no
      
      NotApplicable specifies that the user does not want to specify the 
      transfer capability.
      
      The CBR traffic type refers to traffic offered on services such as a 
      constant bit rate video service or a circuit emulation.
      
      The VBR traffic type refers to traffic offered on services such as 
      packetized audio and video, or data.
      
      The value no indication for traffic type is used if the user has not set 
      the traffic type; similarly for end-to-end timing.
      
      The value yes for end-to-end timing indicates that end-to-end 
      timing is required.
      
      The value no for end-to-end timing indicates that end-to-end timing 
      is not required.
      
      The value derivedFromServiceCategory specifies that the actual 
      value which is used for this connection is derived from the value of 
      the atmServiceCategory. Either, this attribute must be set to 
      derivedFromServiceCategory, or the atmServiceCategory attribute 
      must be set to derivedFromBBC, but not both."
   DEFVAL     { derivedFromServiceCategory }
::= { atmIfVptVccVcdTrafficEntry 72 }

atmIfVptVccVcdClippingBbc OBJECT-TYPE
   SYNTAX     INTEGER  {
                 no(0),
                 yes(1) }
   ACCESS     read-write
   STATUS     obsolete
   DESCRIPTION
     "This attribute is migrated to the AtmTmProv group.
      
      This attribute specifies the value for the clipping susceptibility 
      parameter in the BBC Information Element. This attribute is only 
      used for SPVC connections. It is one of the Broadband Bearer 
      Capability attributes.
      
      Clipping is an impairment in which the first fraction of a second of 
      information to be transferred is lost. It occurs after a call is 
      answered and before an associated connection is switched through."
   DEFVAL     { no }
::= { atmIfVptVccVcdTrafficEntry 74 }

atmIfVptVccVcdBestEffort OBJECT-TYPE
   SYNTAX     INTEGER  {
                 indicated(0),
                 notIndicated(1),
                 derivedFromServiceCategory(15) }
   ACCESS     read-write
   STATUS     obsolete
   DESCRIPTION
     "This attribute is migrated to the AtmTmProv group.
      
      This attribute specifies the value of the best effort parameter in the 
      ATM Traffic Descriptor Information Element. This attribute is only 
      used for Soft PVC connections. It is one of the Broadband Bearer 
      Capability attributes.
      
      The value indicated implies that the quality of service for this 
      connection is not guaranteed.
      
      The value notIndicated implies that the quality of service for this 
      connection is guaranteed.
      
      The value derivedFromServiceCategory specifies that the actual 
      value which is used for this connection is derived from the value of 
      the atmServiceCategory. Either, this attribute must be set to 
      derivedFromServiceCategory, or the atmServiceCategory attribute 
      must be set to derivedFromBBC, but not both."
   DEFVAL     { derivedFromServiceCategory }
::= { atmIfVptVccVcdTrafficEntry 75 }

atmIfVptVccVcdFwdFrameDiscard OBJECT-TYPE
   SYNTAX     INTEGER  {
                 notIndicated(0),
                 indicated(1) }
   ACCESS     read-write
   STATUS     obsolete
   DESCRIPTION
     "This attribute specifies the activation of frame discard functionality 
      in the forward data direction, at relay points, for this connection. It 
      applies to each hop of the connection. Frame discard functions 
      should not be requested if this connection is not transferring frame 
      (AAL5) traffic. Setting the value to indicated for any other traffic 
      type results in all traffic being discarded.
      
      If this connection point is a permanent (provisioned) VCC mid-
      point, this attribute specifies whether the Partial Packet 
      Discard (PPD) function is to be enabled or disabled in the transmit 
      direction at this connecting point. The PPD function allows the 
      connecting point to discard the remainder of a cell-forwarded AAL5 
      frame if one cell of this frame has been discarded. The PPD 
      function increases the 'goodput' of the link, since cells which are 
      only going to be discarded by the AAL5 reassembly are not 
      transmitted.
      
      At a permanent VCC connecting point which is not a connection 
      endpoint, when this attribute is set to indicated, the PPD function is 
      applied to transmit traffic at this connecting point. It should not be 
      indicated for connections whose end points are not performing 
      AAL5 segmentation and reassembly. When this attribute is set to 
      notIndicated, the PPD feature is not applied to transmit traffic at 
      this connecting point.
      
      At a SPVC origin on a PNNI interface, a value of indicated 
      specifies that frame discard is requested in the forward direction. 
      The frame discard function for SPVCs consists of PPD at the SPVC 
      origin and at all intermediate connecting points. When this attribute 
      is set to notIndicated, forward frame discard is not requested in the 
      SPVC call setup. Thus PPD is not enabled at the SPVC origin nor at 
      any intermediate connecting point.
      
      At all points along a VPC, this setting is ignored.
      
      At a permanent VCC connection endpoint, this value is ignored. If 
      AAL5 segmentation and reassembly has been requested, PPD and 
      Early Packet Discard (EPD) are automatically enabled.
      
      This attribute has been migrated to txFrameDiscard."
   DEFVAL     { notIndicated }
::= { atmIfVptVccVcdTrafficEntry 76 }

atmIfVptVccVcdBwdFrameDiscard OBJECT-TYPE
   SYNTAX     INTEGER  {
                 notIndicated(0),
                 indicated(1) }
   ACCESS     read-write
   STATUS     obsolete
   DESCRIPTION
     "This attribute specifies the activation of frame discard functionality 
      in the backward data direction, at relay points, for this connection. 
      It applies to each hop of the connection. Frame discard functions 
      should not be requested if this connection is not transferring frame 
      (AAL5) traffic. Setting the value to indicated for any other traffic 
      type results in all traffic being discarded.
      
      If this connection point is a permanent (provisioned) VCC mid-
      point, this attribute specifies whether the Partial Packet Discard 
      (PPD) function is to be enabled or disabled in the receive direction 
      at this connecting point. The PPD function allows the connecting 
      point to discard the remainder of a cell-forwarded AAL5 frame if 
      one cell of this frame has been discarded. The PPD function 
      increases the 'goodput' of the link, since cells which are only going 
      to be discarded by the AAL5 reassembly are not received.
      
      At a permanent VCC connecting point which is not a connection 
      endpoint, when this attribute is set to indicated, the PPD function is 
      applied to receive traffic at this connecting point. It should not be 
      indicated for connections whose end points are not performing 
      AAL5 segmentation and reassembly. When this attribute is set to 
      notIndicated, the PPD feature is not applied to receive traffic at this 
      connecting point.
      
      At a SPVC origin on a PNNI interface, a value of indicated 
      specifies that frame discard is requested in the backward direction. 
      The frame discard function for SPVCs consists of PPD at the SPVC 
      origin and at all intermediate connecting points. When this attribute 
      is set to notIndicated, backwards frame discard is not requested in 
      the SPVC call setup. Thus PPD is not enabled at the SPVC origin 
      nor at any intermediate connecting point.
      
      At all points along a VPC, this setting is ignored.
      
      At a permanent VCC connection endpoint, this value is ignored. If 
      AAL5 segmentation and reassembly has been requested, PPD and 
      Early Packet Discard (EPD) are automatically enabled.
      
      This attribute has been migrated to rxFrameDiscard."
   DEFVAL     { notIndicated }
::= { atmIfVptVccVcdTrafficEntry 77 }

atmIfVptVccVcdAcctTable OBJECT-TYPE
   SYNTAX     SEQUENCE OF AtmIfVptVccVcdAcctEntry
   ACCESS     not-accessible
   STATUS     mandatory
   DESCRIPTION
     "This group contains the provisionable ATM accounting attributes 
      for a Vcc, Vpc, or Vpt component."
::= { atmIfVptVccVcd 111 }

atmIfVptVccVcdAcctEntry OBJECT-TYPE
   SYNTAX     AtmIfVptVccVcdAcctEntry
   ACCESS     not-accessible
   STATUS     mandatory
   DESCRIPTION
     "An entry in the atmIfVptVccVcdAcctTable."
   INDEX {
      atmIfIndex,
      atmIfVptIndex,
      atmIfVptVccIndex,
      atmIfVptVccVcdIndex }
::= { atmIfVptVccVcdAcctTable 1 }

AtmIfVptVccVcdAcctEntry ::= SEQUENCE {
   atmIfVptVccVcdCorrelationTag
      AsciiString }

atmIfVptVccVcdCorrelationTag OBJECT-TYPE
   SYNTAX     AsciiString (SIZE (0..32))
   ACCESS     read-write
   STATUS     mandatory
   DESCRIPTION
     "This attribute specifies a unique indentifier for each end of a PVC. It 
      that may be used by downstream processing systems to correlate 
      accounting records issued at different nodes in the network. The 
      attribute can be up to 32 bytes long. If it is less than 32 bytes, it is 
      zero filled on the right to create a 32 byte value. The resulting value 
      is recorded in the attribute callConnId for this PVC's ATM 
      accounting records.
      If the attribute is a null string then this PVC does not have any 
      accounting records generated for it."
   DEFVAL     { ''H }  -- ""
::= { atmIfVptVccVcdAcctEntry 10 }

atmIfVptVccVcdTxTdpTable OBJECT-TYPE
   SYNTAX     SEQUENCE OF AtmIfVptVccVcdTxTdpEntry
   ACCESS     not-accessible
   STATUS     obsolete
   DESCRIPTION
     "This attribute is migrated to the AtmTmProv group.
      
      This attribute is a vector of five traffic parameters whose meanings 
      are defined by the txTrafficDescType attribute. The values of peak 
      cell rate (PCR), sustained cell rate (SCR) and requested shaping rate 
      are expressed in cell/s. Maximum burst size (MBS) is expressed in 
      cells. CDVT is expressed in microseconds. The values of PCR, 
      SCR, MBS and CDVT are used for connection admission control 
      (CAC). The value of CDVT is only used for connections where the 
      atmServiceCategory is constantBitRate. For all other values of 
      atmServiceCategory, CDVT is ignored. The values of PCR, SCR 
      and requested shaping rate are used to determine the actual shaping 
      rate where traffic shaping is enabled.
      
      When txTrafficDescType is 1 or 2, all of the parameters must be set 
      to zero.
      
      When txTrafficDescType is 3, parameter 1 represents the PCR for 
      CLP equal to 0 and 1 traffic; parameter 4 represents the CDVT; and 
      parameter 5 represents the requested shaping rate. A non-zero value 
      in parameter 5 overrides any value in parameter 1. This result is 
      used as the PCR. Parameter 1 must be non-zero. Parameters 2 and 3 
      must be zero.
      
      When txTrafficDescType is 4, parameter 1 represents the PCR for 
      CLP equal to 0 and 1 traffic with cell discard; parameter 2 
      represents the PCR for CLP equal to 0 traffic; parameter 4 
      represents the CDVT; and parameter 5 represents the requested 
      shaping rate. A non-zero value in parameter 5 overrides any value in 
      parameter 1. This result is used as the PCR. Parameter 1 must be 
      greater than or equal to parameter 2. Parameters 1 and 2 must be 
      non-zero. Parameter 3 must be zero.
      
      When txTrafficDescType is 5, parameter 1 represents the PCR for 
      CLP equal to 0 and 1 traffic with cell tagging; parameter 2 
      represents the PCR for CLP equal to 0 traffic; parameter 4 
      represents the CDVT; and parameter 5 represents the requested 
      shaping rate. A non-zero value in parameter 5 overrides any value in 
      parameter 1. This result is used as the PCR. Parameter 1 must be 
      greater than or equal to parameter 2. Parameters 1 and 2 must be 
      non-zero. Parameter 3 must be zero.
      
      When txTrafficDescType is 6, parameter 1 represents the PCR for 
      CLP equal to 0 and 1 traffic; parameter 2 represents the SCR for 
      CLP equal to 0 and 1 traffic; parameter 3 represents the MBS for 
      CLP equal to 0 and 1 traffic; parameter 4 represents the CDVT; and 
      parameter 5 represents the requested shaping rate. A non-zero value 
      in parameter 5 overrides any value in parameter 1. This result is 
      used as the PCR. Parameters 1, 2 and 3 must be non-zero. 
      Parameter 1 must be greater than or equal to parameter 2. Parameter 
      5, must either be zero (unused) or greater than or equal to parameter 
      2.
      
      When txTrafficDescType is 7, parameter 1 represents the PCR for 
      CLP equal to 0 and 1 traffic; parameter 2 represents the SCR for 
      CLP equal to 0 with cell discard; parameter 3 represents the MBS 
      for CLP equal to 0 traffic; parameter 4 represents the CDVT; and 
      parameter 5 represents the requested shaping rate. A non-zero value 
      in parameter 5 overrides any value in parameter 1. This result is 
      used as the PCR. Parameters 1, 2 and 3 must be non-zero. 
      Parameter 1 must be greater than or equal to parameter 2. Parameter 
      5, must either be zero (unused) or greater than or equal to parameter 
      2.
      
      When txTrafficDescType is 8, parameter 1 represents the PCR for 
      CLP equal to 0 and 1 traffic; parameter 2 represents the SCR for 
      CLP equal to 0 traffic with cell tagging; parameter 3 represents the 
      MBS for CLP equal to 0 traffic; parameter 4 represents the CDVT; 
      and parameter 5 represents the requested shaping rate. A non-zero 
      value in parameter 5 overrides any value in parameter 1. This result 
      is used as the PCR. Parameters 1, 2 and 3 must be non-zero. 
      Parameter 1 must be greater than or equal to parameter 2. Parameter 
      5, must either be zero (unused) or greater than or equal to parameter 
      2.
      
      Whenever it is valid for PCR to be specified, parameter 5 may also 
      be used to specify a requested shaping rate. A non-zero value in 
      parameter 5 overrides the value in parameter 1 and is used as the 
      peak cell rate in calculations of CAC and shaping rate.
      
      For txTrafficDescType 3, 4 and 5, the transmit traffic is shaped at 
      the next rate less than the PCR. 
      
      For txTrafficDescType 6, 7 and 8, the transmit traffic is shaped at 
      the highest available rate which is between PCR and SCR. 
      However, if there is no available shaping rate between PCR and 
      SCR, traffic is shaped at the next rate above the PCR."
::= { atmIfVptVccVcd 297 }

atmIfVptVccVcdTxTdpEntry OBJECT-TYPE
   SYNTAX     AtmIfVptVccVcdTxTdpEntry
   ACCESS     not-accessible
   STATUS     obsolete
   DESCRIPTION
     "An entry in the atmIfVptVccVcdTxTdpTable."
   INDEX {
      atmIfIndex,
      atmIfVptIndex,
      atmIfVptVccIndex,
      atmIfVptVccVcdIndex,
      atmIfVptVccVcdTxTdpIndex }
::= { atmIfVptVccVcdTxTdpTable 1 }

AtmIfVptVccVcdTxTdpEntry ::= SEQUENCE {
   atmIfVptVccVcdTxTdpIndex
      Integer32,
   atmIfVptVccVcdTxTdpValue
      Unsigned32 }

atmIfVptVccVcdTxTdpIndex OBJECT-TYPE
   SYNTAX     Integer32 (1..5)
   ACCESS     not-accessible
   STATUS     obsolete
   DESCRIPTION
     "This variable represents the atmIfVptVccVcdTxTdpTable
      specific index for the atmIfVptVccVcdTxTdpTable."
::= { atmIfVptVccVcdTxTdpEntry 1 }

atmIfVptVccVcdTxTdpValue OBJECT-TYPE
   SYNTAX     Unsigned32 (0..2147483647)
   ACCESS     read-write
   STATUS     obsolete
   DESCRIPTION
     "This variable represents an individual value for the
      atmIfVptVccVcdTxTdpTable."
::= { atmIfVptVccVcdTxTdpEntry 2 }

atmIfVptVccVcdRxTdpTable OBJECT-TYPE
   SYNTAX     SEQUENCE OF AtmIfVptVccVcdRxTdpEntry
   ACCESS     not-accessible
   STATUS     obsolete
   DESCRIPTION
     "This attribute is migrated to the AtmTmProv group.
      
      This attribute is a vector of four traffic parameters whose meanings 
      are defined by the rxTrafficDescType attribute. The values of peak 
      cell rate (PCR) and sustained cell rate (SCR) are expressed in 
      cell/s. Maximum burst size (MBS) is expressed in cells. The value 
      of CDVT is expressed in microseconds. The values of PCR, SCR, 
      MBS and CDVT are used for usage parameter control (UPC).
      
      When rxTrafficDescType is 1 or 2, all of the parameters must be set 
      to zero (unused).
      
      When rxTrafficDescType is 3, parameter 1 represents the PCR for 
      CLP equal to 0 and 1 traffic. Parameter 1 must be non-zero. 
      Parameters 2 and 3 must be set to zero (unused).
      
      When rxTrafficDescType is 4, parameter 1 represents the PCR for 
      CLP equal to 0 and 1 traffic; parameter 2 represents the PCR for 
      CLP equal to 0 traffic with cell discard. Parameters 1 and 2 must be 
      non-zero. Parameter 3 must be set to zero (unused). Parameter 1 
      must be greater than or equal to parameter 2.
      
      When rxTrafficDescType is 5, parameter 1 represents the PCR for 
      CLP equal to 0 and 1 traffic; parameter 2 represents the PCR for 
      CLP equal to 0 traffic with cell tagging. Parameters 1 and 2 must be 
      non-zero. Parameter 3 must be set to zero (unused). Parameter 1 
      must be greater than or equal to parameter 2.
      
      When rxTrafficDescType is a 6, parameter 1 represents the PCR for 
      CLP equal to 0 and 1 traffic; parameter 2 represents the SCR for 
      CLP equal to 0 and 1 traffic; parameter 3 represents the MBS for 
      CLP equal to 0 and 1 traffic. Parameters 1, 2 and 3 must be non-
      zero. Parameter 1 must be greater than or equal to Parameter 2. 
      
      When rxTrafficDescType is 7, parameter 1 represents the PCR for 
      CLP equal to 0 and 1 traffic; parameter 2 represents the SCR for 
      CLP equal to 0 traffic with cell discard; parameter 3 represents the 
      MBS for CLP equal to 0 traffic. Parameters 1, 2 and 3 must be non-
      zero. Parameter 1 must be greater than or equal to parameter 2. 
      
      When rxTrafficDescType is 8, parameter 1 represents the PCR for 
      CLP equal to 0 and 1 traffic; parameter 2 represents the SCR for 
      CLP equal to 0 traffic with cell tagging; parameter 3 represents the 
      MBS for CLP equal to 0 traffic. Parameter 1, 2 and 3 must be non-
      zero. Parameter 1 must be greater than or equal to parameter 2.
      
      When rxTrafficDescType is any value from 3 through 8, parameter 
      4 represents the CDVT. If this value is zero, the CDVT is taken 
      from the ConnectionAdministrator defaults for the particular 
      atmServiceCategory of this connection.
      
      When rxTrafficDescriptorType is 3 through 8, there are certain 
      extreme combinations of rxTrafficDescParm which are outside the 
      capabilities of the UPC hardware. The check prov command detects 
      such cases and generates an error message. If this happens, adjust 
      the parameters until they fall within the supported limits. 
      
      To calculate the limits, use the following formulae:
      I1 = 1 000 000 000 / PCR
      L1 = CDVT * 1000
      I2 = 1 000 000 000 / SCR
      L2 = CDVT + (MBS - 1) * (I2 - I1)
      I1 and I2 must be less than or equal to 335 523 840. I1 + L1 must 
      be less than or equal to 1 342 156 800. I2 + L2 must be less than or 
      equal to 1 342 156 800. Note that I2 and L2 only apply when the 
      rxTrafficDescriptorType is 6 through 8.
      
      If the values of I1, L1, I2 or L2 are closer to the limits described 
      above, a further restriction applies. Specifically, if either:
      I1 > 41 940 480 or
      I2 > 41 940 480 or
      I1 + L1 > 167 769 600 or
      I2 + L2 > 167 769 600
      then both I1 and I2 must be greater than 20 480. 
      
      Parameter 5 of the rxTrafficDescParm is always unused. 
      
      If the rxTrafficDescType is sameAsTx, the values in this attribute 
      are taken from the txTrafficDescParm."
::= { atmIfVptVccVcd 298 }

atmIfVptVccVcdRxTdpEntry OBJECT-TYPE
   SYNTAX     AtmIfVptVccVcdRxTdpEntry
   ACCESS     not-accessible
   STATUS     obsolete
   DESCRIPTION
     "An entry in the atmIfVptVccVcdRxTdpTable."
   INDEX {
      atmIfIndex,
      atmIfVptIndex,
      atmIfVptVccIndex,
      atmIfVptVccVcdIndex,
      atmIfVptVccVcdRxTdpIndex }
::= { atmIfVptVccVcdRxTdpTable 1 }

AtmIfVptVccVcdRxTdpEntry ::= SEQUENCE {
   atmIfVptVccVcdRxTdpIndex
      Integer32,
   atmIfVptVccVcdRxTdpValue
      Unsigned32 }

atmIfVptVccVcdRxTdpIndex OBJECT-TYPE
   SYNTAX     Integer32 (1..5)
   ACCESS     not-accessible
   STATUS     obsolete
   DESCRIPTION
     "This variable represents the atmIfVptVccVcdRxTdpTable
      specific index for the atmIfVptVccVcdRxTdpTable."
::= { atmIfVptVccVcdRxTdpEntry 1 }

atmIfVptVccVcdRxTdpValue OBJECT-TYPE
   SYNTAX     Unsigned32 (0..2147483647)
   ACCESS     read-write
   STATUS     obsolete
   DESCRIPTION
     "This variable represents an individual value for the
      atmIfVptVccVcdRxTdpTable."
::= { atmIfVptVccVcdRxTdpEntry 2 }

atmIfVptVccVcdFqpTable OBJECT-TYPE
   SYNTAX     SEQUENCE OF AtmIfVptVccVcdFqpEntry
   ACCESS     not-accessible
   STATUS     obsolete
   DESCRIPTION
     "This attribute is migrated to the AtmTmProv group.
      
      This attribute is a vector of three elements that specify the quality of 
      service parameters for the forward direction for this connection. 
      This attribute is used for SPVC connections.
      
      The cdv element specifies the acceptable peak-to-peak Cell Delay 
      Variation (CDV) of real-time connections (CBR, and rt-VBR). It is 
      signalled through the extended QoS information element.
      
      The ctd specifies the acceptable maximum Cell Transfer Delay 
      (maxCtd) of real-time connections (CBR, and rt-VBR). 
      It is signalled through the end to end transit delay information 
      element.
      
      The clr specifies the acceptable Cell Loss Ratio (CLR) of CBR, rt-
      VBR, and nrt-VBR connections. It is signalled through the extended 
      QoS information element."
::= { atmIfVptVccVcd 359 }

atmIfVptVccVcdFqpEntry OBJECT-TYPE
   SYNTAX     AtmIfVptVccVcdFqpEntry
   ACCESS     not-accessible
   STATUS     obsolete
   DESCRIPTION
     "An entry in the atmIfVptVccVcdFqpTable."
   INDEX {
      atmIfIndex,
      atmIfVptIndex,
      atmIfVptVccIndex,
      atmIfVptVccVcdIndex,
      atmIfVptVccVcdFqpIndex }
::= { atmIfVptVccVcdFqpTable 1 }

AtmIfVptVccVcdFqpEntry ::= SEQUENCE {
   atmIfVptVccVcdFqpIndex
      INTEGER,
   atmIfVptVccVcdFqpValue
      Unsigned32 }

atmIfVptVccVcdFqpIndex OBJECT-TYPE
   SYNTAX     INTEGER  {
                 cdv(0),
                 ctd(1),
                 clr(2) }
   ACCESS     not-accessible
   STATUS     obsolete
   DESCRIPTION
     "This variable represents the atmIfVptVccVcdFqpTable
      specific index for the atmIfVptVccVcdFqpTable."
::= { atmIfVptVccVcdFqpEntry 1 }

atmIfVptVccVcdFqpValue OBJECT-TYPE
   SYNTAX     Unsigned32 (0..2147483647)
   ACCESS     read-write
   STATUS     obsolete
   DESCRIPTION
     "This variable represents an individual value for the
      atmIfVptVccVcdFqpTable."
::= { atmIfVptVccVcdFqpEntry 2 }

atmIfVptVccVcdBqpTable OBJECT-TYPE
   SYNTAX     SEQUENCE OF AtmIfVptVccVcdBqpEntry
   ACCESS     not-accessible
   STATUS     obsolete
   DESCRIPTION
     "This attribute is migrated to the AtmTmProv group.
      
      This attribute is a vector of three elements that specify the quality of 
      service parameters for the backward direction for this connection. 
      This attribute is used for SPVC connections.
      
      The cdv element specifies the acceptable peak-to-peak Cell Delay 
      Variation (CDV) of real-time connections (CBR, and rt-VBR). 
      
      It is signalled through the extended QoS information element.
      
      The ctd specifies the acceptable maximum Cell Transfer Delay 
      (maxCtd) of real-time connections (CBR, and rt-VBR). It is 
      signalled through the end to end transit delay information element.
      
      The clr specifies the acceptable Cell Loss Ratio (CLR) of CBR, rt-
      VBR, and nrt-VBR connections. It is signalled through the extended 
      QoS information element."
::= { atmIfVptVccVcd 360 }

atmIfVptVccVcdBqpEntry OBJECT-TYPE
   SYNTAX     AtmIfVptVccVcdBqpEntry
   ACCESS     not-accessible
   STATUS     obsolete
   DESCRIPTION
     "An entry in the atmIfVptVccVcdBqpTable."
   INDEX {
      atmIfIndex,
      atmIfVptIndex,
      atmIfVptVccIndex,
      atmIfVptVccVcdIndex,
      atmIfVptVccVcdBqpIndex }
::= { atmIfVptVccVcdBqpTable 1 }

AtmIfVptVccVcdBqpEntry ::= SEQUENCE {
   atmIfVptVccVcdBqpIndex
      INTEGER,
   atmIfVptVccVcdBqpValue
      Unsigned32 }

atmIfVptVccVcdBqpIndex OBJECT-TYPE
   SYNTAX     INTEGER  {
                 cdv(0),
                 ctd(1),
                 clr(2) }
   ACCESS     not-accessible
   STATUS     obsolete
   DESCRIPTION
     "This variable represents the atmIfVptVccVcdBqpTable
      specific index for the atmIfVptVccVcdBqpTable."
::= { atmIfVptVccVcdBqpEntry 1 }

atmIfVptVccVcdBqpValue OBJECT-TYPE
   SYNTAX     Unsigned32 (0..2147483647)
   ACCESS     read-write
   STATUS     obsolete
   DESCRIPTION
     "This variable represents an individual value for the
      atmIfVptVccVcdBqpTable."
::= { atmIfVptVccVcdBqpEntry 2 }


-- AtmIf/n Vcc/vpi.vci Vcd TrafficManagement, 
-- AtmIf/n Vpc/vci Vpd TrafficManagement,
-- AtmIf/n Vpt/vpi Vpd TrafficManagement,
-- AtmIf/n Vpt/vpi Vcc/vci Vcd TrafficManagement
-- This component contains provisioned traffic management attributes 
-- of a connection. It is added automatically when a Vcc, Vpc, or Vpt is 
-- added in provisioning mode. It is a mandatory subcomponent of the 
-- Vcd or Vpd component.

atmIfVptVccVcdTm OBJECT IDENTIFIER ::= { atmIfVptVccVcd 2 }



atmIfVptVccVcdTmRowStatusTable OBJECT-TYPE
   SYNTAX     SEQUENCE OF AtmIfVptVccVcdTmRowStatusEntry
   ACCESS     not-accessible
   STATUS     mandatory
   DESCRIPTION
     "This entry controls the addition and deletion of 
      atmIfVptVccVcdTm components."
::= { atmIfVptVccVcdTm 1 }

atmIfVptVccVcdTmRowStatusEntry OBJECT-TYPE
   SYNTAX     AtmIfVptVccVcdTmRowStatusEntry
   ACCESS     not-accessible
   STATUS     mandatory
   DESCRIPTION
     "A single entry in the table represents a single 
      atmIfVptVccVcdTm component."
   INDEX {
      atmIfIndex,
      atmIfVptIndex,
      atmIfVptVccIndex,
      atmIfVptVccVcdIndex,
      atmIfVptVccVcdTmIndex }
::= { atmIfVptVccVcdTmRowStatusTable 1 }

AtmIfVptVccVcdTmRowStatusEntry ::= SEQUENCE {
   atmIfVptVccVcdTmRowStatus
      RowStatus,
   atmIfVptVccVcdTmComponentName
      DisplayString,
   atmIfVptVccVcdTmStorageType
      StorageType,
   atmIfVptVccVcdTmIndex
      NonReplicated }

atmIfVptVccVcdTmRowStatus OBJECT-TYPE
   SYNTAX     RowStatus 
   ACCESS     read-only
   STATUS     mandatory
   DESCRIPTION
     "This variable is used as the basis for SNMP naming of
      atmIfVptVccVcdTm components.
      These components cannot be added nor deleted."
::= { atmIfVptVccVcdTmRowStatusEntry 1 }

atmIfVptVccVcdTmComponentName OBJECT-TYPE
   SYNTAX     DisplayString 
   ACCESS     read-only
   STATUS     mandatory
   DESCRIPTION
     "This variable provides the component's string name for
      use with the ASCII Console Interface"
::= { atmIfVptVccVcdTmRowStatusEntry 2 }

atmIfVptVccVcdTmStorageType OBJECT-TYPE
   SYNTAX     StorageType 
   ACCESS     read-only
   STATUS     mandatory
   DESCRIPTION
     "This variable represents the storage type value for the
      atmIfVptVccVcdTm tables."
::= { atmIfVptVccVcdTmRowStatusEntry 4 }

atmIfVptVccVcdTmIndex OBJECT-TYPE
   SYNTAX     NonReplicated 
   ACCESS     not-accessible
   STATUS     mandatory
   DESCRIPTION
     "This variable represents the index for the atmIfVptVccVcdTm tables."
::= { atmIfVptVccVcdTmRowStatusEntry 10 }

atmIfVptVccVcdTmProvTable OBJECT-TYPE
   SYNTAX     SEQUENCE OF AtmIfVptVccVcdTmProvEntry
   ACCESS     not-accessible
   STATUS     mandatory
   DESCRIPTION
     "This group contains traffic related provisionable attributes for the 
      Vcc, Vpc, and Vpt components. Changing any of the attributes in 
      this group causes a service interruption on the Vcc, Vpc, or Vpt 
      component."
::= { atmIfVptVccVcdTm 100 }

atmIfVptVccVcdTmProvEntry OBJECT-TYPE
   SYNTAX     AtmIfVptVccVcdTmProvEntry
   ACCESS     not-accessible
   STATUS     mandatory
   DESCRIPTION
     "An entry in the atmIfVptVccVcdTmProvTable."
   INDEX {
      atmIfIndex,
      atmIfVptIndex,
      atmIfVptVccIndex,
      atmIfVptVccVcdIndex,
      atmIfVptVccVcdTmIndex }
::= { atmIfVptVccVcdTmProvTable 1 }

AtmIfVptVccVcdTmProvEntry ::= SEQUENCE {
   atmIfVptVccVcdTmTxTrafficDescType
      INTEGER,
   atmIfVptVccVcdTmFwdQosClass
      INTEGER,
   atmIfVptVccVcdTmTxQueueLimit
      Unsigned32,
   atmIfVptVccVcdTmHoldingPriority
      INTEGER,
   atmIfVptVccVcdTmRxTrafficDescType
      INTEGER,
   atmIfVptVccVcdTmBwdQosClass
      INTEGER,
   atmIfVptVccVcdTmAtmServiceCategory
      INTEGER,
   atmIfVptVccVcdTmTrafficShaping
      INTEGER,
   atmIfVptVccVcdTmUnshapedTransmitQueueing
      INTEGER,
   atmIfVptVccVcdTmWeight
      Unsigned32,
   atmIfVptVccVcdTmForceTagging
      INTEGER,
   atmIfVptVccVcdTmUsageParameterControl
      INTEGER,
   atmIfVptVccVcdTmBearerClassBbc
      INTEGER,
   atmIfVptVccVcdTmTransferCapabilityBbc
      INTEGER,
   atmIfVptVccVcdTmTxWredThreshold
      Unsigned32,
   atmIfVptVccVcdTmClippingBbc
      INTEGER,
   atmIfVptVccVcdTmBestEffort
      INTEGER,
   atmIfVptVccVcdTmTxPacketWiseDiscard
      INTEGER,
   atmIfVptVccVcdTmTxWredMode
      INTEGER,
   atmIfVptVccVcdTmRxPacketWiseDiscard
      INTEGER,
   atmIfVptVccVcdTmAbrConnectionType
      INTEGER }

atmIfVptVccVcdTmTxTrafficDescType OBJECT-TYPE
   SYNTAX     INTEGER  {
                 n1(1),
                 n2(2),
                 n3(3),
                 n4(4),
                 n5(5),
                 n6(6),
                 n7(7),
                 n8(8),
                 n9(9) }
   ACCESS     read-write
   STATUS     mandatory
   DESCRIPTION
     "This attribute specifies the type of traffic management which is 
      applied to the transmit direction of this connection as defined in the 
      ATM Forum. The txTrafficDescType determines the number and 
      meaning of the parameters in the txTrafficDescParm attribute.
      
      This attribute can have a value of 9 if and only if the 
      atmServiceCategory is availableBitRate."
   DEFVAL     { n1 }
::= { atmIfVptVccVcdTmProvEntry 10 }

atmIfVptVccVcdTmFwdQosClass OBJECT-TYPE
   SYNTAX     INTEGER  {
                 n0(0),
                 n1(1),
                 n2(2),
                 n3(3),
                 n4(4) }
   ACCESS     read-write
   STATUS     mandatory
   DESCRIPTION
     "This attribute specifies the quality of service for the forward 
      direction for this connection. This attribute is only used for SPVC 
      connections.
      
      Class 1 supports a QOS that meets Service Class A performance 
      requirements (circuit emulation, constant bit rate video).
      
      Class 2 supports a QOS that meets Service Class B performance 
      requirements (variable bit rate audio and video).
      
      Class 3 supports a QOS that meets Service Class C performance 
      requirements (Connection-Oriented Data Transfer).
      
      Class 4 supports a QOS that meets Service Class D performance 
      requirements (Connectionless Data Transfer).
      
      Class 0 is the unspecified bit rate QOS class; no objective is 
      specified for the performance parameters."
   DEFVAL     { n0 }
::= { atmIfVptVccVcdTmProvEntry 21 }

atmIfVptVccVcdTmTxQueueLimit OBJECT-TYPE
   SYNTAX     Unsigned32 (0 | 5..63488)
   ACCESS     read-write
   STATUS     mandatory
   DESCRIPTION
     "This attribute specifies an override to the default transmit queue 
      limit for this connection. A value other than sameAsCa may be 
      specified only for ATM IP cards. This attribute is not applicable for 
      basic Vpts.
      
      A value of sameAsCa means to use the default common or per-VC 
      transmit queue limit as defined by the CA service category for this 
      connection. 
      
      A value from 5 to 63,488 indicates that a specific transmit queue 
      limit is requested which differs from the default which is defined 
      under the CA component for this service category. A specific value 
      is ignored for connections where common queuing is specified for 
      the service category.
      
      The actual transmit queue limit for a connection is visible in the Vcc 
      Tm, Vpc Tm, or Vpt Tm txQueueThresholds attribute.

      VALUES (

      0 = sameAsCa

      )"
   DEFVAL     { 0 }
::= { atmIfVptVccVcdTmProvEntry 22 }

atmIfVptVccVcdTmHoldingPriority OBJECT-TYPE
   SYNTAX     INTEGER  {
                 n0(0),
                 n1(1),
                 n2(2),
                 n3(3),
                 n4(4) }
   ACCESS     read-write
   STATUS     mandatory
   DESCRIPTION
     "This attribute specifies the holding priority of this connection. In a 
      situation where the link bandwidth fluctuates, such as over an IMA 
      link, holding priority is used to determine which connections are 
      held and which are released. Holding priority 4 connections are the 
      first to be released. Holding priority 0 connections are the last to be 
      released. This value provisioned in the Vcd or Vpd may be 
      overridden by certain applications, for example Vcc Test, which run 
      over this connection. The default holding priority for a provisioned 
      connection is higher then default holding priorities for dynamic 
      (SVC) connections. 
      
      This attribute is not applicable for Vpt Vccs."
   DEFVAL     { n2 }
::= { atmIfVptVccVcdTmProvEntry 25 }

atmIfVptVccVcdTmRxTrafficDescType OBJECT-TYPE
   SYNTAX     INTEGER  {
                 n1(1),
                 n2(2),
                 n3(3),
                 n4(4),
                 n5(5),
                 n6(6),
                 n7(7),
                 n8(8),
                 n9(9),
                 sameAsTx(15) }
   ACCESS     read-write
   STATUS     mandatory
   DESCRIPTION
     "This attribute specifies the type of traffic management which is 
      applied to the receive direction of this connection as defined in the 
      ATM Forum. The rxTrafficDescType determines the number and 
      meaning of the parameters in the rxTrafficDescParm attribute.
      
      When this attribute is set to sameAsTx, the rxTrafficDescType as 
      well as the rxTrafficDescParm are taken from the 
      txTrafficDescType and txTrafficDescParm values."
   DEFVAL     { sameAsTx }
::= { atmIfVptVccVcdTmProvEntry 30 }

atmIfVptVccVcdTmBwdQosClass OBJECT-TYPE
   SYNTAX     INTEGER  {
                 n0(0),
                 n1(1),
                 n2(2),
                 n3(3),
                 n4(4),
                 sameAsFwd(15) }
   ACCESS     read-write
   STATUS     mandatory
   DESCRIPTION
     "This attribute specifies the quality of service for the backward 
      direction for this connection. This attribute is only used for SPVC 
      connections.
      
      Class 1 supports a QOS that meets Service Class A performance 
      requirements (Circuit emulation, constant bit rate video).
      
      Class 2 supports a QOS that meets Service Class B performance 
      requirements (Variable bit rate audio and video).
      
      Class 3 supports a QOS that meets Service Class C performance 
      requirements (Connection-Oriented Data Transfer).
      
      Class 4 supports a QOS that meets Service Class D performance 
      requirements (Connectionless Data Transfer).
      
      Class 0 is the unspecified bit rate QOS class; no objective is 
      specified for the performance parameters.
      
      The sameAsFwd selection sets the backward quality of service to 
      be the same as the forward quality of service."
   DEFVAL     { sameAsFwd }
::= { atmIfVptVccVcdTmProvEntry 41 }

atmIfVptVccVcdTmAtmServiceCategory OBJECT-TYPE
   SYNTAX     INTEGER  {
                 unspecifiedBitRate(0),
                 constantBitRate(1),
                 rtVariableBitRate(2),
                 nrtVariableBitRate(3),
                 availableBitRate(4),
                 derivedFromBBC(15) }
   ACCESS     read-write
   STATUS     mandatory
   DESCRIPTION
     "This attribute specifies the ATM service category for both directions 
      of the connection. 
      
      The value derivedFromBBC may only be used if the SrcPvc 
      component is provisioned under this Vcc. Otherwise a specific 
      ATM service category must be specified. 
      
      If this attribute is set to derivedFromBBC, the Broadband Bearer 
      Capability (BBC) and bestEffort attributes are used to determine the 
      atmServiceCategory of this connection. 
      
      If this attribute is set to other than derivedFromBBC, the value of 
      this attribute is used to override the provisioned BBC Information 
      Element parameters. In those cases, the BBC attributes are not used. 
      
      The constantBitRate service category is intended for real time 
      applications, that is those requiring tightly constrained delay and 
      delay variation, as would be appropriate for voice and video 
      applications. The consistent availability of a fixed quantity of 
      bandwidth is considered appropriate for CBR service. Cells which 
      are delayed beyond the value specified by Cell Transfer Delay are 
      assumed to be of significantly reduced value to the application.
      
      The rtVariableBitRate service category is intended for real time 
      applications, that is those requiring tightly constrained delay and 
      delay variation, as would be appropriate for voice and video 
      applications. Sources are expected to transmit at a rate which varies 
      with time. Equivalently, the source can be described as 'bursty'. 
      Cells which are delayed beyond the value specified by CTD are 
      assumed to be of significantly reduced value to the application. Real 
      time VBR service may support statistical multiplexing of real time 
      sources.
      
      The nrtVariableBitRate service category is intended for non-real 
      time applications which have bursty traffic characteristics and which 
      can be characterized in terms of a PCR, SCR, and MBS. For those 
      cells which are transferred within the traffic contract, the application 
      expects a low cell loss ratio. For all connections, it expects a bound 
      on the mean cell transfer delay. Non-real time VBR service may 
      support statistical multiplexing of connections. 
      
      The availableBitRate service is an ATM layer service category for 
      which the limiting ATM layer transfer characteristics provided by 
      the network may change subsequent to connection establishment. 
      ABR service has a flow control mechanism which supports several 
      types of feedback to control the source rate in response to changing 
      ATM layer transfer characteristics. ABR service is not intended to 
      support real-time applications. 
      
      The unspecifiedBitRate service is intended for non-real time 
      applications; that is, those not requiring tightly constrained delay 
      and delay variation. UBR sources are expected to be bursty. UBR 
      service supports a high degree of statistical multiplexing among 
      sources. UBR service does not specify traffic related service 
      guarantees. No numerical commitments are made with respect to 
      the cell loss ratio experienced by a UBR connection, or as to the 
      cell transfer delay experienced by cells on the connection."
   DEFVAL     { unspecifiedBitRate }
::= { atmIfVptVccVcdTmProvEntry 42 }

atmIfVptVccVcdTmTrafficShaping OBJECT-TYPE
   SYNTAX     INTEGER  {
                 disabled(1),
                 sameAsCa(2) }
   ACCESS     read-write
   STATUS     mandatory
   DESCRIPTION
     "This attribute specifies whether this connection uses traffic shaping 
      when transmitting traffic to the ATM interface.
      
      This attribute is ignored if the atmServiceCategory is 
      availableBitRate.
      
      When sameAsCa is selected, traffic shaping for the connection is 
      based on the trafficShaping attribute of the connection's service 
      category component under the CA. If the service category has 
      trafficShaping set to enabled or inverseUpc, then traffic shaping is 
      enabled for the connection. Note that enabling traffic shaping may 
      have no effect under certain cases. These cases are listed in the 
      description of the trafficShaping operational attribute, which is 
      under the Vcc Tm, Vpc Tm, or Vpt Tm components.
      
      When disabled is selected, traffic shaping for this connection is 
      disabled regardless of the provisioning of the connection's service 
      category component."
   DEFVAL     { sameAsCa }
::= { atmIfVptVccVcdTmProvEntry 50 }

atmIfVptVccVcdTmUnshapedTransmitQueueing OBJECT-TYPE
   SYNTAX     INTEGER  {
                 common(1),
                 sameAsCa(3) }
   ACCESS     read-write
   STATUS     mandatory
   DESCRIPTION
     "This attribute only applies when this connection is unshaped. This 
      attribute specifies the transmit queueing method for this connection 
      if it is unshaped. The two possible methods are per-VC queuing and 
      common queuing. 
      
      On ATM IP FPs, this attribute must be set to sameAsCa. 
      
      This attribute is ignored in the following situations:
      - if the connection has trafficShaping enabled or inverseUpc, or 
      - if the atmServiceCategory is availableBitRate, or
      - if the atmServiceCategory is constantBitRate and this is a CQC-
      based ATM FP.
      - for basic Vpts and standard Vpt Vccs
      
      When this attribute is set to sameAsCa, the transmit queueing 
      method for the connection is based on the 
      unshapedTransmitQueueing attribute of the connection's service 
      category component under the CA. 
      
      When this attribute is set to common, transmit traffic on this 
      unshaped connection is destined for the common queue."
   DEFVAL     { sameAsCa }
::= { atmIfVptVccVcdTmProvEntry 60 }

atmIfVptVccVcdTmWeight OBJECT-TYPE
   SYNTAX     Unsigned32 (0 | 1..4095 | 65535)
   ACCESS     read-write
   STATUS     mandatory
   DESCRIPTION
     "This attribute specifies an override for the weight of this unshaped 
      connection. This attribute is ignored for shaped connections, for 
      ABR connections, for connections on a CQC-based ATM FP, and 
      basic Vpts. 
      
      When the value is set to sameAsCa, the weight is determined by the 
      fairnessWeight attribute under the CA service category component 
      for all but standard Vpt Vccs. For standard Vpt Vccs, the weight is 
      determined by the Vcc's service category, when the value is set to 
      sameAsCa.
      
      When this attribute is set to a value from 1 to 4095, that value is 
      used for the fairness weight of this connection relative to other 
      connections. For all but standard Vpt Vccs, fairness weight 
      determines the proportion of transmit cell opportunities which are 
      allocated to this connection, compared to other connections in the 
      same service category. For standard Vpt Vccs, fairness weight 
      determines the proportion of transmit cell opportunities which are 
      allocated to this connection, compared to other connections 
      associated with the Vpt.
      
      When the value is set to upToQueueLimit, the fairness weight is 
      limited only by the txQueueLimit.

      VALUES (

      0 = upToQueueLimit

      65535 = sameAsCa

      )"
   DEFVAL     { 65535 }
::= { atmIfVptVccVcdTmProvEntry 61 }

atmIfVptVccVcdTmForceTagging OBJECT-TYPE
   SYNTAX     INTEGER  {
                 enabled(0),
                 disabled(1),
                 sameAsCa(2) }
   ACCESS     read-write
   STATUS     mandatory
   DESCRIPTION
     "This attribute specifies whether force tagging is enforced for this 
      connection for cells in the transmit direction. 
      
      On CQC-based ATM cards, and for Vpts, this attribute is not 
      applicable and is ignored. 
      
      When the value is set to sameAsCa, the force tagging functionality 
      is determined by the forceTagging attribute under the CA service 
      category component. 
      
      When the value is set to enabled, force tagging is enabled for cells 
      in the transmit direction on this connection. When this option is 
      selected, the CLP bit is set to 1 for all cells in the transmit direction. 
      Cells which are tagged are counted in the txCellClp attribute. 
      
      When the value is set to disabled, force tagging is disabled for cells 
      in the transmit direction on this connection. When this option is 
      selected, the CLP bit is unchanged for cells in the transmit 
      direction."
   DEFVAL     { sameAsCa }
::= { atmIfVptVccVcdTmProvEntry 62 }

atmIfVptVccVcdTmUsageParameterControl OBJECT-TYPE
   SYNTAX     INTEGER  {
                 enforced(0),
                 disabled(1),
                 sameAsCa(2),
                 monitored(4) }
   ACCESS     read-write
   STATUS     mandatory
   DESCRIPTION
     "This attribute specifies whether this connection enforces usage 
      parameter control when receiving traffic from the ATM interface.
      
      When sameAsCa is selected, UPC for the connection is based on 
      the usageParameterControl attribute of the service category 
      component under the AtmIf CA. If the service category has UPC 
      enforced or monitored, then UPC is set to that value for the 
      connection. 
      
      When disabled is selected, UPC for this connection is disabled 
      regardless of the provisioning of the service category. 
      
      When enforced is selected, UPC for this connection is enforced 
      regardless of the provisioning of the service category. 
      
      ATM IP cards provide the ability to monitor UPC violations without 
      tagging or discarding. When monitored is selected, UPC is actively 
      checking conformance for the connection and counting the 
      violations, but is not discarding or tagging cells which do not 
      conform to the connection traffic contract. 
      
      If this is a connection of serviceCategory abr on an ATM IP card, 
      and the abrConnectionType is sourceDest, virtualSourceDest or 
      explicitRate, selecting enforced enables dynamic generic cell rate 
      algorithm (DGCRA) to discard violating cells. Selecting monitored 
      enables DGCRA to count violating cells. 
      
      Note that setting UPC to enforced or monitored may have no effect 
      under certain cases. These cases are listed in the description of the 
      usageParameterControl operational attribute, which is under the 
      Vcc, Vpc, and Vpt components."
   DEFVAL     { sameAsCa }
::= { atmIfVptVccVcdTmProvEntry 70 }

atmIfVptVccVcdTmBearerClassBbc OBJECT-TYPE
   SYNTAX     INTEGER  {
                 a(1),
                 c(3),
                 x(16),
                 vp(24),
                 derivedFromServiceCategory(31) }
   ACCESS     read-write
   STATUS     mandatory
   DESCRIPTION
     "This attribute specifies the bearer capability. This attribute is only 
      used for SPVC and SPVP connections. It is one of the Broadband 
      Bearer Capability (BBC) attributes. The purpose of the BBC 
      information element is to indicate a requested broadband 
      connection-oriented bearer service to be provided by the network.
      
      The value derivedFromServiceCategory specifies that the actual 
      value which is used for this connection is derived from the value of 
      the atmServiceCategory. Either, this attribute must be set to 
      derivedFromServiceCategory, or the atmServiceCategory attribute 
      must be set to derivedFromBBC, but not both.
      
      Class a service is a connection-oriented, constant bit rate ATM 
      transport service. Class a service has end to end timing 
      requirements and may require stringent cell loss, cell delay and cell 
      delay variation performance.When a is set, the user is requesting 
      more than an ATM only service. The network may look at the AAL 
      to provide interworking based upon its contents. 
      
      Class c service is a connection-oriented, variable bit rate ATM 
      transport service. Class c service has no end-to-end timing 
      requirements. When c is set, the user is requesting more than an 
      ATM only service. The network interworking function may look at 
      the AAL and provide service based on it.
      
      Class x service is a connection-oriented ATM transport service 
      where the AAL, trafficType (vbr or cbr) and timing requirements 
      are user defined (that is, transparent to the network).When x is set 
      the user is requesting an ATM only service from the network. In this 
      case, the network shall not process any higher layer protocol.
      
      Class vp service is used to specify a transparent VP service. When 
      the value of this attribute is vp, the user is requesting an ATM only 
      service from the network. In this case, the network shall not process 
      any higher layer protocol. This service differs from class x service 
      in that with the class vp service both the VCI field (except or VCI 
      values 0, 3, 4, and 6 through 15) and Payload Type field are 
      transported transparently by the network. This attribute value is 
      only applicable to SPVP connections."
   DEFVAL     { derivedFromServiceCategory }
::= { atmIfVptVccVcdTmProvEntry 71 }

atmIfVptVccVcdTmTransferCapabilityBbc OBJECT-TYPE
   SYNTAX     INTEGER  {
                 n0(0),
                 n1(1),
                 n2(2),
                 n5(5),
                 n8(8),
                 n9(9),
                 n10(10),
                 notApplicable(30),
                 derivedFromServiceCategory(31) }
   ACCESS     read-write
   STATUS     mandatory
   DESCRIPTION
     "This attribute specifies the transfer capability for this connection. 
      Uni 3.0/3.1 traffic type and end-to-end timing parameters are 
      mapped into this parameter as follows:
      <transferCapability: TrafficType, Timing>
      0: NoIndication, NoIndication
      1: NoIndication, yes
      2: NoIndication, no
      5: CBR, yes
      8: VBR, NoIndication
      9: VBR, yes
      10: VBR, no
      
      notApplicable specifies that the user does not want to specify the 
      transfer capability.
      
      The CBR traffic type refers to traffic offered on services such as a 
      constant bit rate video service or a circuit emulation.
      The VBR traffic type refers to traffic offered on services such as 
      packetized audio and video, or data.
      
      The value no indication for traffic type is used if the user has not set 
      the traffic type; similarly for end-to-end timing.
      
      The value yes for end-to-end timing indicates that end-to-end 
      timing is required.
      
      The value no for end-to-end timing indicates that end-to-end timing 
      is not required.
      
      The value derivedFromServiceCategory specifies that the actual 
      value which is used for this connection is derived from the value of 
      the atmServiceCategory. Either, this attribute must be set to 
      derivedFromServiceCategory, or the atmServiceCategory attribute 
      must be set to derivedFromBBC, but not both."
   DEFVAL     { derivedFromServiceCategory }
::= { atmIfVptVccVcdTmProvEntry 72 }

atmIfVptVccVcdTmTxWredThreshold OBJECT-TYPE
   SYNTAX     Unsigned32 (25 | 50 | 75)
   ACCESS     read-write
   STATUS     mandatory
   DESCRIPTION
     "This attribute determines at what percentage of the queue being at 
      the EPD threshold, WRED starts. When the value is set to 25%, 
      WRED starts as soon as the queue is 25% of the way to the EPD 
      threshold. When the value is set to 50%, WRED starts later, after 
      the queue is 50% of the way to the EPD threshold. When the value 
      is set to 75%, WRED starts only when the queue is 75% of the way 
      to the EPD threshold. The EPD threshold is 85% of the transmit 
      queue length.
      
      This attribue is ignored if txWredMode or txPacketWiseDiscard is 
      disabled. It is always ignored on CQC-based ATM FP."
   DEFVAL     { 25 }
::= { atmIfVptVccVcdTmProvEntry 73 }

atmIfVptVccVcdTmClippingBbc OBJECT-TYPE
   SYNTAX     INTEGER  {
                 no(0),
                 yes(1) }
   ACCESS     read-write
   STATUS     mandatory
   DESCRIPTION
     "This attribute specifies the value for the clipping susceptibility 
      parameter in the BBC Information Element. This attribute is only 
      used for SPVC connections. It is one of the Broadband Bearer 
      Capability attributes.
      
      Clipping is an impairment in which the first fraction of a second of 
      information to be transferred is lost. It occurs after a call is 
      answered and before an associated connection is switched through."
   DEFVAL     { no }
::= { atmIfVptVccVcdTmProvEntry 74 }

atmIfVptVccVcdTmBestEffort OBJECT-TYPE
   SYNTAX     INTEGER  {
                 indicated(0),
                 notIndicated(1),
                 derivedFromServiceCategory(15) }
   ACCESS     read-write
   STATUS     mandatory
   DESCRIPTION
     "This attribute specifies the value of the best effort parameter in the 
      ATM Traffic Descriptor Information Element. This attribute is only 
      used for Soft PVC connections. It is one of the Broadband Bearer 
      Capability attributes.
      
      The value indicated implies that the quality of service for this 
      connection is not guaranteed.
      
      The value notIndicated implies that the quality of service for this 
      connection is guaranteed.
      
      The value derivedFromServiceCategory specifies that the actual 
      value which is used for this connection is derived from the value of 
      the atmServiceCategory. Either, this attribute must be set to 
      derivedFromServiceCategory, or the atmServiceCategory attribute 
      must be set to derivedFromBBC, but not both."
   DEFVAL     { derivedFromServiceCategory }
::= { atmIfVptVccVcdTmProvEntry 75 }

atmIfVptVccVcdTmTxPacketWiseDiscard OBJECT-TYPE
   SYNTAX     INTEGER  {
                 disabled(0),
                 enabled(1) }
   ACCESS     read-write
   STATUS     mandatory
   DESCRIPTION
     "This attribute specifies whether packet-wise discard functions are to 
      be enabled or disabled in the transmit data direction for this 
      connection. Packet-wise discard functions should only be requested 
      if this connection is transferring AAL5 frame traffic. This attribute 
      is not applicable for Vpts.
      
      Packet-wise functions increase the 'goodput' of the link. The 
      transmit packet-wise functions are Early Packet Discard (EPD) and 
      Partial Packet Discard (PPD). 
      
      EPD allows the connection to discard an entire frame once the 
      transmit queue has reached the EPD threshold. EPD increases the 
      'goodput' of a link, since discarding an entire frame means that 
      some queue capacity is guarded for some other frame which is 
      already partially transmitted. All cells of the frame are discarded 
      from the Beginning of Message (BOM) cell up to and including the 
      End of Message (EOM) cell. 
      
      PPD allows the connection to discard the remainder of a cell-
      forwarded AAL5 frame if one cell of this frame has been discarded. 
      All cells are discarded up to but not including the EOM cell. The 
      PPD function increases the 'goodput' of the link, since cells which 
      are only going to be discarded at the AAL5 reassembly point are 
      not transmitted.
      
      On CQC-based ATM cards, the packet-wise discard functions are 
      PPD and EPD. PPD is available at VCC cell-transfer points. PPD is 
      not applicable at frame-cell conversion points, and is not applicable 
      for Vpcs. PPD is configured by this attribute. Packet-wise discard 
      should only be enabled for connections carrying AAL5 
      segmentation traffic. Setting the value to enabled for any other 
      traffic type may result in all traffic being discarded. On CQC-based 
      ATM FPs, EPD is automatically enabled at frame-to-cell conversion 
      points, independent of the setting of this attribute. 
      
      On ATM IP cards, packet-wise discard functions include EPD and 
      PPD. PPD and EPD apply to individual VCCs and VCCs within 
      VPCs at all connection points, including tandem VPC connections. 
      Both PPD and EPD are controlled by this attribute. This attribute 
      may safely be set to enabled for any connection (Vcc or Vpc) on 
      ATM IP FPs since they have the ability to automatically detect 
      AAL5-segmented traffic on a connection, and only enable packet-
      wise discards if AAL5-segmented traffic is detected.
      
      When this attribute is set to enabled, packet-wise discard functions 
      are applied to transmit traffic at this connection point. When this 
      attribute is set to disabled, packet-wise discard functions are not 
      applied to transmit traffic at this connection point.
      
      At a SPVC origin on a PNNI interface, a value of enabled specifies 
      that frame discard is requested in the backward direction. When this 
      attribute is set to disabled, backward frame discard is not requested 
      in the SPVC call setup. 
      
      The transmit packet-wise discard functions that are active are 
      visible in the Vcc/Vpc Tm txPacketWiseDiscard operational 
      attribute."
   DEFVAL     { disabled }
::= { atmIfVptVccVcdTmProvEntry 76 }

atmIfVptVccVcdTmTxWredMode OBJECT-TYPE
   SYNTAX     INTEGER  {
                 disabled(0),
                 enabled(1),
                 perFlow(2) }
   ACCESS     read-write
   STATUS     mandatory
   DESCRIPTION
     "This attribute specifies the activation of weighted random early 
      detection (WRED) functionality. WRED is only available on ATM 
      IP FPs. On CQC-based ATM FPs, this attribute is ignored. If 
      txPacketWiseDiscard is set to disabled this attribute is ignored. This 
      attribute is not applicable for Vpts or Vpt Vccs.
      
      WRED is applied in the transmit direction for this connection. 
      WRED function should be enabled only for connections which are 
      transferring TCP/IP traffic. WRED acts to prevent synchronization 
      of multiple TCP/IP sources by randomly discarding a small 
      percentage of frames when transmit queue congestion reaches the 
      designated level. W-RED may also be used to differentiate service 
      on VCC's by preferentially discarding one VCC before another. 
      Discards start at 0% of cells, when the queue is part-way to the 
      Early Packet Discard (EPD) threshold, and rise to 100% of cells 
      discarded at the EPD threshold. WRED discards all the cells in a 
      frame. 
      
      If this attribute is set to enabled, WRED is enabled for all 
      applications linked to the given Vcc. If it is set to perFlow, each 
      TCP application has individual control over whether to enable or 
      disable WRED
      
      If txPacketWiseDiscard is set to disabled, or if this attribute is set to 
      disabled, WRED functionality is disabled. 
      
      If WRED is active, it is visible in the Vcc/Vpc Tm 
      txPacketWiseDiscard operational attribute."
   DEFVAL     { disabled }
::= { atmIfVptVccVcdTmProvEntry 77 }

atmIfVptVccVcdTmRxPacketWiseDiscard OBJECT-TYPE
   SYNTAX     INTEGER  {
                 disabled(0),
                 enabled(1) }
   ACCESS     read-write
   STATUS     mandatory
   DESCRIPTION
     "This attribute specifies whether packet-wise discard functions are to 
      be enabled or disabled in the receive data direction for this 
      connection. Packet-wise discard functions should only be requested 
      if this connection is transferring AAL5 frame traffic. This attribute 
      is not applicable for Vpts.
      
      Packet-wise functions increase the 'goodput' of the link. The 
      receive packet-wise function is Partial Packet Discard (PPD). 
      
      PPD allows the connection to discard the remainder of a cell-
      forwarded AAL5 frame if one cell of this frame has been discarded, 
      for example due to UPC. All cells are discarded up to but not 
      including the EOM cell. The PPD function increases the 'goodput' 
      of the link, since cells which are only going to be discarded at the 
      AAL5 reassembly point are not transmitted.
      
      PPD is available at all VCC connection points where UPC may be 
      activated. PPD is not applicable for Vpcs. 
      
      On CQC-based ATM FPs, packet-wise discards should only be 
      enabled for connections carrying AAL5 segmentation traffic. 
      Setting the value to enabled for any other traffic type may result in 
      traffic being discarded. 
      
      On ATM IP cards, this attribute may safely be set to enabled for any 
      connection (Vcc or Vpc) since they have the ability to automatically 
      detect AAL5-segmented traffic on a connection, and only enables 
      packet-wise discards if AAL5-segmented traffic is detected.
      
      When this attribute is set to enabled, packet-wise discard functions 
      are applied to receive traffic at this connection point. When this 
      attribute is set to disabled, packet-wise discard functions are not 
      applied to receive traffic at this connection point.
      
      At a SPVC origin on a PNNI interface, a value of enabled specifies 
      that frame discard is requested in the forward direction. When this 
      attribute is set to disabled, forward frame discard is not requested in 
      the SPVC call setup. 
      
      The receive packet-wise discard functions that are active are visible 
      in the Vcc/Vpc Tm rxPacketWiseDiscard operational attribute."
   DEFVAL     { disabled }
::= { atmIfVptVccVcdTmProvEntry 78 }

atmIfVptVccVcdTmAbrConnectionType OBJECT-TYPE
   SYNTAX     INTEGER  {
                 abrSwitch(0),
                 virtualSourceDest(3),
                 sourceDest(4),
                 nonAbrInterworking(5),
                 sameAsCa(14) }
   ACCESS     read-write
   STATUS     mandatory
   DESCRIPTION
     "This attribute specifies the type of ABR behavior which is to be 
      enforced at this connection. This attribute is only applicable if the 
      atmServiceCategory attribute is availableBitRate. If the 
      atmServicecategory attribute is not availableBitRate, this attribute 
      value is ignored.
      
      The actual ABR functionality which is in effect is visible in the 
      Vcc/Vpc/Vpt Tm abrConnectionType operational attribute.
      
      For CQC-based ATM cards, the only allowable values are 
      sameAsCa, nonAbrInterworking or abrSwitch. If abrSwitch is 
      selected, the CQC implements EFCI marking behavior.
      
      sameAsCa is used to request the default behavior as specified in the 
      CA Abr component for this Vcc. Otherwise, this attribute overrides 
      the default behavior. 
      
      virtualSourceDest is used to request that this connection point 
      function as a virtual source/virtual destination. VS/VD functionality 
      is only supported on ATM IP FPs.
      
      sourceDest requires that this connection point function as a S/D for 
      RM cells. S/D mode is automatically invoked at this connection 
      point either if this is a connection end point, or if the next hop 
      connection point is configured as nonAbrInterworking.
      
      nonAbrInterworking is used to request that this connection point 
      function as an interworking between ABR and non-ABR service 
      categories. This means that there are no RM cells on the link side of 
      this connection, and that the next hop connection point is 
      performing as an ABR sourceDest.
      
      abrSwitch is used to request ABR switch behavior for this 
      connection point. The ABR switch behavior is first, to confirm to 
      virtualSourceDest or nonAbrInterworking setting on the next hop, 
      and otherwise to implement ABR ER switch behavior. For CQC-
      based FPs, ABR switch behavior is implemented as EFCI marking."
   DEFVAL     { sameAsCa }
::= { atmIfVptVccVcdTmProvEntry 90 }

atmIfVptVccVcdTmTxTdpTable OBJECT-TYPE
   SYNTAX     SEQUENCE OF AtmIfVptVccVcdTmTxTdpEntry
   ACCESS     not-accessible
   STATUS     mandatory
   DESCRIPTION
     "This attribute is a vector of five traffic parameters whose meanings 
      are defined by the txTrafficDescType attribute. 
      
      The values of peak cell rate (PCR), sustained cell rate (SCR), 
      Minimum Cell Rate (MCR) and requested shaping rate are 
      expressed in cell/s. Maximum burst size (MBS) is expressed in 
      cells. CDVT is expressed in microseconds. The values of PCR, 
      SCR, MCR, MBS and CDVT are used for connection admission 
      control (CAC). The value of CDVT is only used for connections 
      where the atmServiceCategory is constantBitRate. For all other 
      values of atmServiceCategory, CDVT is ignored. The values of 
      PCR, SCR, MCR and requested shaping rate are used to determine 
      the actual shaping rate where traffic shaping is enabled.
      
      When txTrafficDescType is 1 or 2, all of the parameters must be set 
      to zero.
      
      When txTrafficDescType is 3, parameter 1 represents the PCR for 
      CLP equal to 0 and 1 traffic; parameter 4 represents the CDVT; and 
      parameter 5 represents the requested shaping rate. A non-zero value 
      in parameter 5 overrides any value in parameter 1. This result is 
      used as the PCR. Parameter 1 must be non-zero. Parameters 2 and 3 
      must be zero.
      
      When txTrafficDescType is 4, parameter 1 represents the PCR for 
      CLP equal to 0 and 1 traffic with cell discard; parameter 2 
      represents the PCR for CLP equal to 0 traffic; parameter 4 
      represents the CDVT; and parameter 5 represents the requested 
      shaping rate. A non-zero value in parameter 5 overrides any value in 
      parameter 1. This result is used as the PCR. Parameter 1 must be 
      greater than or equal to parameter 2. Parameters 1 and 2 must be 
      non-zero. Parameter 3 must be zero.
      
      When txTrafficDescType is 5, parameter 1 represents the PCR for 
      CLP equal to 0 and 1 traffic with cell tagging; parameter 2 
      represents the PCR for CLP equal to 0 traffic; parameter 4 
      represents the CDVT; and parameter 5 represents the requested 
      shaping rate. A non-zero value in parameter 5 overrides any value in 
      parameter 1. This result is used as the PCR. Parameter 1 must be 
      greater than or equal to parameter 2. Parameters 1 and 2 must be 
      non-zero. Parameter 3 must be zero.
      
      When txTrafficDescType is 6, parameter 1 represents the PCR for 
      CLP equal to 0 and 1 traffic; parameter 2 represents the SCR for 
      CLP equal to 0 and 1 traffic; parameter 3 represents the MBS for 
      CLP equal to 0 and 1 traffic; parameter 4 represents the CDVT; and 
      parameter 5 represents the requested shaping rate. A non-zero value 
      in parameter 5 overrides any value in parameter 1. This result is 
      used as the PCR. Parameters 1, 2 and 3 must be non-zero. 
      Parameter 1 must be greater than or equal to parameter 2. Parameter 
      5, must either be zero (unused) or greater than or equal to parameter 
      2.
      
      When txTrafficDescType is 7, parameter 1 represents the PCR for 
      CLP equal to 0 and 1 traffic; parameter 2 represents the SCR for 
      CLP equal to 0 with cell discard; parameter 3 represents the MBS 
      for CLP equal to 0 traffic; parameter 4 represents the CDVT; and 
      parameter 5 represents the requested shaping rate. A non-zero value 
      in parameter 5 overrides any value in parameter 1. This result is 
      used as the PCR. Parameters 1, 2 and 3 must be non-zero. 
      Parameter 1 must be greater than or equal to parameter 2. Parameter 
      5, must either be zero (unused) or greater than or equal to parameter 
      2.
      
      When txTrafficDescType is 8, parameter 1 represents the PCR for 
      CLP equal to 0 and 1 traffic; parameter 2 represents the SCR for 
      CLP equal to 0 traffic with cell tagging; parameter 3 represents the 
      MBS for CLP equal to 0 traffic; parameter 4 represents the CDVT; 
      and parameter 5 represents the requested shaping rate. A non-zero 
      value in parameter 5 overrides any value in parameter 1. This result 
      is used as the PCR. Parameters 1, 2 and 3 must be non-zero. 
      Parameter 1 must be greater than or equal to parameter 2. Parameter 
      5, must either be zero (unused) or greater than or equal to parameter 
      2.
      
      When txTrafficDescType is 9, parameter 1 represents the PCR; 
      parameter 2 represents the CDVT; parameter 3 represents the MCR; 
      parameter 4 and parameter 5 represent are not used and must be 
      zero. Parameter 1 must be non-zero and must be greater than or 
      equal to parameter 3. Parameter 3 may be optionally zero.
      
      Whenever it is valid for PCR to be specified, parameter 5 may also 
      be used to specify a requested shaping rate. A non-zero value in 
      parameter 5 overrides the value in parameter 1 and is used as the 
      peak cell rate in calculations of CAC and shaping rate. When the 
      atmServiceCategory is availableBitRate (ABR), the shaping rate is 
      dynamically chosen, based on the ABR flow control mechanism, as 
      a value between the MCR and the PCR or the requested shaping 
      rate if applicable.
      
      For txTrafficDescType 3, 4 and 5, the transmit traffic is shaped at 
      the next available shaping rate less than the PCR. 
      
      For txTrafficDescType 6, 7 and 8 if linear traffic shaping is selected, 
      the transmit traffic is shaped at the highest available rate which is 
      between PCR and SCR. However, if there is no available shaping 
      rate between PCR and SCR, traffic is shaped at the next rate above 
      the PCR. 
      
      For txTrafficDescType 6, 7 and 8 if inverse-UPC traffic shaping is 
      selected, the transmit traffic is shaped at a variable rate which 
      conforms to the PCR, SCR and MBS of the connection traffic 
      descriptor. Inverse-UPC traffic shaping is available only on ATM IP 
      cards."
::= { atmIfVptVccVcdTm 456 }

atmIfVptVccVcdTmTxTdpEntry OBJECT-TYPE
   SYNTAX     AtmIfVptVccVcdTmTxTdpEntry
   ACCESS     not-accessible
   STATUS     mandatory
   DESCRIPTION
     "An entry in the atmIfVptVccVcdTmTxTdpTable."
   INDEX {
      atmIfIndex,
      atmIfVptIndex,
      atmIfVptVccIndex,
      atmIfVptVccVcdIndex,
      atmIfVptVccVcdTmIndex,
      atmIfVptVccVcdTmTxTdpIndex }
::= { atmIfVptVccVcdTmTxTdpTable 1 }

AtmIfVptVccVcdTmTxTdpEntry ::= SEQUENCE {
   atmIfVptVccVcdTmTxTdpIndex
      Integer32,
   atmIfVptVccVcdTmTxTdpValue
      Unsigned32 }

atmIfVptVccVcdTmTxTdpIndex OBJECT-TYPE
   SYNTAX     Integer32 (1..5)
   ACCESS     not-accessible
   STATUS     mandatory
   DESCRIPTION
     "This variable represents the atmIfVptVccVcdTmTxTdpTable
      specific index for the atmIfVptVccVcdTmTxTdpTable."
::= { atmIfVptVccVcdTmTxTdpEntry 1 }

atmIfVptVccVcdTmTxTdpValue OBJECT-TYPE
   SYNTAX     Unsigned32 (0..2147483647)
   ACCESS     read-write
   STATUS     mandatory
   DESCRIPTION
     "This variable represents an individual value for the
      atmIfVptVccVcdTmTxTdpTable."
::= { atmIfVptVccVcdTmTxTdpEntry 2 }

atmIfVptVccVcdTmRxTdpTable OBJECT-TYPE
   SYNTAX     SEQUENCE OF AtmIfVptVccVcdTmRxTdpEntry
   ACCESS     not-accessible
   STATUS     mandatory
   DESCRIPTION
     "This attribute is a vector of four traffic parameters whose meanings 
      are defined by the rxTrafficDescType attribute. The values of peak 
      cell rate (PCR), sustained cell rate (SCR) and Minimum Cell Rate 
      (MCR) are expressed in cell/s. Maximum burst size (MBS) is 
      expressed in cells. The value of CDVT is expressed in 
      microseconds. The values of PCR, SCR, MCR, MBS and CDVT 
      are used for usage parameter control (UPC).
      
      When rxTrafficDescType is 1 or 2, all of the parameters must be set 
      to zero (unused).
      
      When rxTrafficDescType is 3, parameter 1 represents the PCR for 
      CLP equal to 0 and 1 traffic. Parameter 1 must be non-zero. 
      Parameters 2 and 3 must be set to zero (unused).
      
      When rxTrafficDescType is 4, parameter 1 represents the PCR 
      for CLP equal to 0 and 1 traffic; parameter 2 represents the PCR for 
      CLP equal to 0 traffic with cell discard. Parameters 1 and 2 must be 
      non-zero. Parameter 3 must be set to zero (unused). Parameter 1 
      must be greater than or equal to parameter 2.
      
      When rxTrafficDescType is 5, parameter 1 represents the PCR for 
      CLP equal to 0 and 1 traffic; parameter 2 represents the PCR for 
      CLP equal to 0 traffic with cell tagging. Parameters 1 and 2 must be 
      non-zero. Parameter 3 must be set to zero (unused). Parameter 1 
      must be greater than or equal to parameter 2.
      
      When rxTrafficDescType is a 6, parameter 1 represents the PCR for 
      CLP equal to 0 and 1 traffic; parameter 2 represents the SCR for 
      CLP equal to 0 and 1 traffic; parameter 3 represents the MBS for 
      CLP equal to 0 and 1 traffic. Parameters 1, 2 and 3 must be non-
      zero. Parameter 1 must be greater than or equal to Parameter 2. 
      
      When rxTrafficDescType is 7, parameter 1 represents the PCR for 
      CLP equal to 0 and 1 traffic; parameter 2 represents the SCR for 
      CLP equal to 0 traffic with cell discard; parameter 3 represents the 
      MBS for CLP equal to 0 traffic. Parameters 1, 2 and 3 must be non-
      zero. Parameter 1 must be greater than or equal to parameter 2. 
      
      When rxTrafficDescType is 8, parameter 1 represents the PCR for 
      CLP equal to 0 and 1 traffic; parameter 2 represents the SCR for 
      CLP equal to 0 traffic with cell tagging; parameter 3 represents the 
      MBS for CLP equal to 0 traffic. Parameter 1, 2 and 3 must be non-
      zero. Parameter 1 must be greater than or equal to parameter 2.
      
      When rxTrafficDescType is 9, parameter 1 represents the PCR; 
      parameter 2 represents the CDVT; parameter 3 represents the MCR. 
      Parameter 4 is not used and must be zero. Parameter 1,must be non-
      zero and must be greater than or equal to parameter 3. Parameter 3 
      may optionally be zero.
      
      When rxTrafficDescType is any value from 3 through 8, parameter 
      4 represents the CDVT. 
      
      If the value of CDVT either in parameter 2 or in parameter 4 is zero, 
      the CDVT is taken from the CA defaults for the particular 
      atmServiceCategory of this connection.
      
      On a CQC-based ATM card, when rxTrafficDescriptorType is 3 
      through 8, there are certain extreme combinations of 
      rxTrafficDescParm which are outside the capabilities of the UPC 
      hardware. The check prov command detects such cases and 
      generates an error message. If this happens, adjust the parameters 
      until they fall within the supported limits. 
      
      To calculate the limits, use the following formulae:
      I1 = 1 000 000 000 / PCR
      L1 = CDVT * 1000
      I2 = 1,000,000,000 / SCR
      L2 = CDVT + (MBS - 1) * (I2 - I1)
      I1 and I2 must be less than or equal to 335,523,840. I1 + L1 must 
      be less than or equal to 1,342,156,800. I2 + L2 must be less than or 
      equal to 1,342,156,800. Note that I2 and L2 only apply when the 
      rxTrafficDescriptorType is 6 through 8.
      
      If the values of I1, L1, I2 or L2 are closer to the limits described 
      above, a further restriction applies. Specifically, if either:
      I1 > 41,940,480 or
      I2 > 41,940,480 or
      I1 + L1 > 167,769,600 or
      I2 + L2 > 167,769,600
      then both I1 and I2 must be greater than 20,480. 
      
      Parameter 5 of the rxTrafficDescParm is always unused. 
      
      If the rxTrafficDescType is sameAsTx, the values provisioned in 
      this attribute are ignored. The traffic parameters for the receive 
      direction are taken from the txTrafficDescParm."
::= { atmIfVptVccVcdTm 457 }

atmIfVptVccVcdTmRxTdpEntry OBJECT-TYPE
   SYNTAX     AtmIfVptVccVcdTmRxTdpEntry
   ACCESS     not-accessible
   STATUS     mandatory
   DESCRIPTION
     "An entry in the atmIfVptVccVcdTmRxTdpTable."
   INDEX {
      atmIfIndex,
      atmIfVptIndex,
      atmIfVptVccIndex,
      atmIfVptVccVcdIndex,
      atmIfVptVccVcdTmIndex,
      atmIfVptVccVcdTmRxTdpIndex }
::= { atmIfVptVccVcdTmRxTdpTable 1 }

AtmIfVptVccVcdTmRxTdpEntry ::= SEQUENCE {
   atmIfVptVccVcdTmRxTdpIndex
      Integer32,
   atmIfVptVccVcdTmRxTdpValue
      Unsigned32 }

atmIfVptVccVcdTmRxTdpIndex OBJECT-TYPE
   SYNTAX     Integer32 (1..5)
   ACCESS     not-accessible
   STATUS     mandatory
   DESCRIPTION
     "This variable represents the atmIfVptVccVcdTmRxTdpTable
      specific index for the atmIfVptVccVcdTmRxTdpTable."
::= { atmIfVptVccVcdTmRxTdpEntry 1 }

atmIfVptVccVcdTmRxTdpValue OBJECT-TYPE
   SYNTAX     Unsigned32 (0..2147483647)
   ACCESS     read-write
   STATUS     mandatory
   DESCRIPTION
     "This variable represents an individual value for the
      atmIfVptVccVcdTmRxTdpTable."
::= { atmIfVptVccVcdTmRxTdpEntry 2 }

atmIfVptVccVcdTmFqpTable OBJECT-TYPE
   SYNTAX     SEQUENCE OF AtmIfVptVccVcdTmFqpEntry
   ACCESS     not-accessible
   STATUS     mandatory
   DESCRIPTION
     "This attribute is a vector of three elements that specify the quality of 
      service parameters for the forward direction for this connection. 
      This attribute is used for SPVC connections.
      
      The cdv element specifies the acceptable peak-to-peak Cell Delay 
      Variation (CDV) of real-time connections (CBR and rt-VBR). It is 
      signalled through the extended QoS information element.
      
      The ctd specifies the acceptable maximum Cell Transfer Delay 
      (maxCtd) of real-time connections (CBR and rt-VBR). 
      It is signalled through the end to end transit delay information 
      element.
      
      The clr specifies the acceptable Cell Loss Ratio (CLR) of CBR, rt-
      VBR, and nrt-VBR connections. It is signalled through the extended 
      QoS information element."
::= { atmIfVptVccVcdTm 458 }

atmIfVptVccVcdTmFqpEntry OBJECT-TYPE
   SYNTAX     AtmIfVptVccVcdTmFqpEntry
   ACCESS     not-accessible
   STATUS     mandatory
   DESCRIPTION
     "An entry in the atmIfVptVccVcdTmFqpTable."
   INDEX {
      atmIfIndex,
      atmIfVptIndex,
      atmIfVptVccIndex,
      atmIfVptVccVcdIndex,
      atmIfVptVccVcdTmIndex,
      atmIfVptVccVcdTmFqpIndex }
::= { atmIfVptVccVcdTmFqpTable 1 }

AtmIfVptVccVcdTmFqpEntry ::= SEQUENCE {
   atmIfVptVccVcdTmFqpIndex
      INTEGER,
   atmIfVptVccVcdTmFqpValue
      Unsigned32 }

atmIfVptVccVcdTmFqpIndex OBJECT-TYPE
   SYNTAX     INTEGER  {
                 cdv(0),
                 ctd(1),
                 clr(2) }
   ACCESS     not-accessible
   STATUS     mandatory
   DESCRIPTION
     "This variable represents the atmIfVptVccVcdTmFqpTable
      specific index for the atmIfVptVccVcdTmFqpTable."
::= { atmIfVptVccVcdTmFqpEntry 1 }

atmIfVptVccVcdTmFqpValue OBJECT-TYPE
   SYNTAX     Unsigned32 (0..16777215)
   ACCESS     read-write
   STATUS     mandatory
   DESCRIPTION
     "This variable represents an individual value for the
      atmIfVptVccVcdTmFqpTable."
::= { atmIfVptVccVcdTmFqpEntry 2 }

atmIfVptVccVcdTmBqpTable OBJECT-TYPE
   SYNTAX     SEQUENCE OF AtmIfVptVccVcdTmBqpEntry
   ACCESS     not-accessible
   STATUS     mandatory
   DESCRIPTION
     "This attribute is a vector of two elements that specify the quality of 
      service parameters for the backward direction for this connection. 
      This attribute is used for SPVC connections.
      
      The cdv element specifies the acceptable peak-to-peak Cell Delay 
      Variation (CDV) of real-time connections (CBR and rt-VBR). It is 
      signalled through the extended QoS information element.
      
      The clr specifies the acceptable Cell Loss Ratio (CLR) of CBR, rt-
      VBR, and nrt-VBR connections. It is signalled through the extended 
      QoS information element."
::= { atmIfVptVccVcdTm 459 }

atmIfVptVccVcdTmBqpEntry OBJECT-TYPE
   SYNTAX     AtmIfVptVccVcdTmBqpEntry
   ACCESS     not-accessible
   STATUS     mandatory
   DESCRIPTION
     "An entry in the atmIfVptVccVcdTmBqpTable."
   INDEX {
      atmIfIndex,
      atmIfVptIndex,
      atmIfVptVccIndex,
      atmIfVptVccVcdIndex,
      atmIfVptVccVcdTmIndex,
      atmIfVptVccVcdTmBqpIndex }
::= { atmIfVptVccVcdTmBqpTable 1 }

AtmIfVptVccVcdTmBqpEntry ::= SEQUENCE {
   atmIfVptVccVcdTmBqpIndex
      INTEGER,
   atmIfVptVccVcdTmBqpValue
      Unsigned32 }

atmIfVptVccVcdTmBqpIndex OBJECT-TYPE
   SYNTAX     INTEGER  {
                 cdv(0),
                 clr(2) }
   ACCESS     not-accessible
   STATUS     mandatory
   DESCRIPTION
     "This variable represents the atmIfVptVccVcdTmBqpTable
      specific index for the atmIfVptVccVcdTmBqpTable."
::= { atmIfVptVccVcdTmBqpEntry 1 }

atmIfVptVccVcdTmBqpValue OBJECT-TYPE
   SYNTAX     Unsigned32 (0..16777215)
   ACCESS     read-write
   STATUS     mandatory
   DESCRIPTION
     "This variable represents an individual value for the
      atmIfVptVccVcdTmBqpTable."
::= { atmIfVptVccVcdTmBqpEntry 2 }


-- AtmIf/n Vcc/vpi.vci Vcd Tm AvailableBitRate, 
-- AtmIf/n Vpc/vci Vpd Tm AvailableBitRate,
-- AtmIf/n Vpt/vpi Vpd Tm AvailableBitRate,
-- AtmIf/n Vpt/vpi Vcc/vci Vcd Tm AvailableBitRate
-- This component contains provisioned ABR-related attributes of a 
-- connection. It is an optional subcomponent of the Vcd Tm and Vpd 
-- Tm component. It is used to override DGCRA-related defaults in 
-- the CA Abr component. It contains the specific configuration for the 
-- ABR connection at this connection point. If this is the source of an 
-- SPVC connection, this component also contains the ABR 
-- parameters required for the SPVC call request.

atmIfVptVccVcdTmAbr OBJECT IDENTIFIER ::= { atmIfVptVccVcdTm 2 }



atmIfVptVccVcdTmAbrRowStatusTable OBJECT-TYPE
   SYNTAX     SEQUENCE OF AtmIfVptVccVcdTmAbrRowStatusEntry
   ACCESS     not-accessible
   STATUS     mandatory
   DESCRIPTION
     "This entry controls the addition and deletion of 
      atmIfVptVccVcdTmAbr components."
::= { atmIfVptVccVcdTmAbr 1 }

atmIfVptVccVcdTmAbrRowStatusEntry OBJECT-TYPE
   SYNTAX     AtmIfVptVccVcdTmAbrRowStatusEntry
   ACCESS     not-accessible
   STATUS     mandatory
   DESCRIPTION
     "A single entry in the table represents a single 
      atmIfVptVccVcdTmAbr component."
   INDEX {
      atmIfIndex,
      atmIfVptIndex,
      atmIfVptVccIndex,
      atmIfVptVccVcdIndex,
      atmIfVptVccVcdTmIndex,
      atmIfVptVccVcdTmAbrIndex }
::= { atmIfVptVccVcdTmAbrRowStatusTable 1 }

AtmIfVptVccVcdTmAbrRowStatusEntry ::= SEQUENCE {
   atmIfVptVccVcdTmAbrRowStatus
      RowStatus,
   atmIfVptVccVcdTmAbrComponentName
      DisplayString,
   atmIfVptVccVcdTmAbrStorageType
      StorageType,
   atmIfVptVccVcdTmAbrIndex
      NonReplicated }

atmIfVptVccVcdTmAbrRowStatus OBJECT-TYPE
   SYNTAX     RowStatus 
   ACCESS     read-write
   STATUS     mandatory
   DESCRIPTION
     "This variable is used as the basis for SNMP naming of
      atmIfVptVccVcdTmAbr components.
      These components can be added and deleted."
::= { atmIfVptVccVcdTmAbrRowStatusEntry 1 }

atmIfVptVccVcdTmAbrComponentName OBJECT-TYPE
   SYNTAX     DisplayString 
   ACCESS     read-only
   STATUS     mandatory
   DESCRIPTION
     "This variable provides the component's string name for
      use with the ASCII Console Interface"
::= { atmIfVptVccVcdTmAbrRowStatusEntry 2 }

atmIfVptVccVcdTmAbrStorageType OBJECT-TYPE
   SYNTAX     StorageType 
   ACCESS     read-only
   STATUS     mandatory
   DESCRIPTION
     "This variable represents the storage type value for the
      atmIfVptVccVcdTmAbr tables."
::= { atmIfVptVccVcdTmAbrRowStatusEntry 4 }

atmIfVptVccVcdTmAbrIndex OBJECT-TYPE
   SYNTAX     NonReplicated 
   ACCESS     not-accessible
   STATUS     mandatory
   DESCRIPTION
     "This variable represents the index for the atmIfVptVccVcdTmAbr tables."
::= { atmIfVptVccVcdTmAbrRowStatusEntry 10 }

atmIfVptVccVcdTmAbrProvTable OBJECT-TYPE
   SYNTAX     SEQUENCE OF AtmIfVptVccVcdTmAbrProvEntry
   ACCESS     not-accessible
   STATUS     mandatory
   DESCRIPTION
     "This group contains provisioned attributes for the ABR ATM 
      connections configured on an ATM interface."
::= { atmIfVptVccVcdTmAbr 110 }

atmIfVptVccVcdTmAbrProvEntry OBJECT-TYPE
   SYNTAX     AtmIfVptVccVcdTmAbrProvEntry
   ACCESS     not-accessible
   STATUS     mandatory
   DESCRIPTION
     "An entry in the atmIfVptVccVcdTmAbrProvTable."
   INDEX {
      atmIfIndex,
      atmIfVptIndex,
      atmIfVptVccIndex,
      atmIfVptVccVcdIndex,
      atmIfVptVccVcdTmIndex,
      atmIfVptVccVcdTmAbrIndex }
::= { atmIfVptVccVcdTmAbrProvTable 1 }

AtmIfVptVccVcdTmAbrProvEntry ::= SEQUENCE {
   atmIfVptVccVcdTmAbrInitialCellRate
      Unsigned32,
   atmIfVptVccVcdTmAbrTransientBufferExposure
      Unsigned32,
   atmIfVptVccVcdTmAbrFixedRoundTripTime
      Unsigned32,
   atmIfVptVccVcdTmAbrRateDecreaseFactor
      Unsigned32,
   atmIfVptVccVcdTmAbrRateIncreaseFactor
      Unsigned32,
   atmIfVptVccVcdTmAbrMaxCellPerRmCell
      Unsigned32,
   atmIfVptVccVcdTmAbrMaxTimeBetweenRmCells
      Unsigned32,
   atmIfVptVccVcdTmAbrCutoffDecreaseFactor
      Unsigned32,
   atmIfVptVccVcdTmAbrAcrDecreaseTimeFactor
      Unsigned32,
   atmIfVptVccVcdTmAbrDgcraMaximumDelay
      Unsigned32,
   atmIfVptVccVcdTmAbrDgcraMinimumDelay
      Unsigned32,
   atmIfVptVccVcdTmAbrFarEndAcrDecreaseTimeFactor
      Unsigned32,
   atmIfVptVccVcdTmAbrFarEndInitialCellRate
      Unsigned32 }

atmIfVptVccVcdTmAbrInitialCellRate OBJECT-TYPE
   SYNTAX     Unsigned32 (0..16777215 | 16777216 | 16777217 | 16777218)
   ACCESS     read-write
   STATUS     mandatory
   DESCRIPTION
     "This attribute specifies the Initial Cell Rate (ICR) parameter for this 
      connection. ICR is the rate at which a source should send initially 
      and after an idle period.
      
      When this attribute is set to sameAsCa, the initial cell rate is 
      determined by the AtmIf CA Abr/0 icr attribute. When the value of 
      this attribute is set to useMcr, ICR is set to the same value as the 
      Minimum Cell Rate (MCR) for the connection.
      
      When the value of this attribute is set to usePcr, ICR is set to the 
      same value as the Peak Cell Rate (PCR) for the connection.
      
      If this attribute is specified less than the MCR of the connection, 
      then the MCR is used as the ICR. If this attribute is specified more 
      than PCR of the connection, then PCR is used as the ICR.
      
      This attribute is ignored under all conditions where the operational 
      attribute abrConnectionType indicates erSwitch or efciSwitch.

      VALUES (

      16777216 = sameAsCa

      16777217 = useMcr

      16777218 = usePcr

      )"
   DEFVAL     { 16777216 }
::= { atmIfVptVccVcdTmAbrProvEntry 10 }

atmIfVptVccVcdTmAbrTransientBufferExposure OBJECT-TYPE
   SYNTAX     Unsigned32 (0..16777215)
   ACCESS     read-write
   STATUS     mandatory
   DESCRIPTION
     "This attribute specifies the Transient Buffer Exposure (TBE) for this 
      connection. TBE is the negotiated number of cells that the network 
      would like to limit the source to send during start-up periods, before 
      the first Resource Management (RM) cell returns.
      
      TBE divided by fixedRoundTripTime determines an upper bound 
      for the operational value of initialCellRate, the rate at which a 
      source should send initially and after an idle period.
      
      TBE divided by maxCellsPerRmCell specifies the operational value 
      of forwardRmCellLimit, the limit of the number of forward 
      Resource Management (RM) cells which may be sent in the 
      absence of received backward RM cells.
      
      This attribute is ignored under all conditions where the operational 
      attribute abrConnectionType is set to erSwitch."
   DEFVAL     { 16777215 }
::= { atmIfVptVccVcdTmAbrProvEntry 11 }

atmIfVptVccVcdTmAbrFixedRoundTripTime OBJECT-TYPE
   SYNTAX     Unsigned32 (0..16700000)
   ACCESS     read-write
   STATUS     mandatory
   DESCRIPTION
     "This attribute specifies the Fixed Round-Trip Time (FRTT) 
      parameter for this connection. FRTT is the sum of the fixed and 
      propagation delays from the source to a destination and back.
      
      The value of transientBufferExposure divided by the value of FRTT 
      (in seconds) determines an upper bound for the operational value of 
      initialCellRate, the rate at which a source should send initially and 
      after an idle period.
      
      This attribute is ignored under all conditions where the operational 
      attribute abrConnectionType indicates erSwitch or efciSwitch."
   DEFVAL     { 5000000 }
::= { atmIfVptVccVcdTmAbrProvEntry 12 }

atmIfVptVccVcdTmAbrRateDecreaseFactor OBJECT-TYPE
   SYNTAX     Unsigned32 (0..15 | 16777216)
   ACCESS     read-write
   STATUS     mandatory
   DESCRIPTION
     "This attribute specifies the Rate Decrease Factor (RDF) for this 
      connection. The RDF value is computed by using the provisioned 
      value of this attribute, n, as 2 to the inverse power n. For example, if 
      the value of this attribute is 8, RDF is 2E-8 = 1/256.
      
      RDF controls the amount by which the cell transmission rate may 
      decrease upon receipt of a backward Resource Management (RM) 
      cell. For example, if a backward RM cell is received with the 
      Congestion Indication (CI) field set to 1, the Allowed Cell Rate 
      (ACR) value would be reduced by the amount (RDF*ACR). The 
      ACR is not allowed to fall below the Minimum Cell Rate (MCR), in 
      which case the ACR is set to MCR.
      
      This attribute is ignored under all conditions where the operational 
      attribute abrConnectionType has the value erSwitch.

      VALUES (

      16777216 = sameAsCa

      )"
   DEFVAL     { 16777216 }
::= { atmIfVptVccVcdTmAbrProvEntry 13 }

atmIfVptVccVcdTmAbrRateIncreaseFactor OBJECT-TYPE
   SYNTAX     Unsigned32 (0..15 | 16777216)
   ACCESS     read-write
   STATUS     mandatory
   DESCRIPTION
     "This attribute specifies the Rate Increase Factor (RIF) for this 
      connection. The RIF value is computed by using the provisioned 
      value of this attribute, n, as 2 to the inverse power n. For example, if 
      the value of this attribute is 6, RIF is 2E-6 = 1/64.
      
      RIF controls the amount by which the cell transmission rate may 
      increase upon receipt of a backward Resource Management (RM) 
      cell. For example, if a backward RM cell is received with the 
      Congestion Indication (CI) and the No Increase (NI) fields both set 
      to 0, the Allowed Cell Rate (ACR) value would be increased by the 
      amount (RIF*ACR). The ACR is not allowed to exceed the Peak 
      Cell Rate (PCR), in which case the ACR is set to PCR.
      
      This attribute is ignored under all conditions where the operational 
      attribute abrConnectionType has the value erSwitch.

      VALUES (

      16777216 = sameAsCa

      )"
   DEFVAL     { 16777216 }
::= { atmIfVptVccVcdTmAbrProvEntry 14 }

atmIfVptVccVcdTmAbrMaxCellPerRmCell OBJECT-TYPE
   SYNTAX     Unsigned32 (2 | 4 | 8 | 16 | 32 | 64 | 128 | 256 | 16777216)
   ACCESS     read-write
   STATUS     mandatory
   DESCRIPTION
     "This attribute specifies the maximum number of cells an ABR 
      source may transmit for each forward Resource Management (RM) 
      cell. The count of the cells transmitted includes data cells, OAM 
      cells, backward RM cells, and the forward RM cell.
      
      A value of 2 is not recommended although it is permitted according 
      to the ATM Forum standard. When this attribute is set to a value of 
      2, it is possible that only one forward and one backward RM cell 
      are repeatedly transmitted, and all data traffic is queued up 
      indefinitely.
      
      This attribute is ignored under all conditions where the operational 
      attribute abrConnectionType has the value erSwitch.

      VALUES (

      16777216 = sameAsCa

      )"
   DEFVAL     { 16777216 }
::= { atmIfVptVccVcdTmAbrProvEntry 15 }

atmIfVptVccVcdTmAbrMaxTimeBetweenRmCells OBJECT-TYPE
   SYNTAX     Unsigned32 (781 | 1563 | 3125 | 6250 | 12500 | 25000 | 50000 | 100000 | 16777216)
   ACCESS     read-write
   STATUS     mandatory
   DESCRIPTION
     "This attribute specifies the TRM parameter for this connection.
      
      TRM provides an lower bound on the time interval between forward 
      Resource Management (RM) cells for an ABR source. Since the last 
      forward RM cell was sent, if at least TRM time has elapsed since 
      and at least two other cells have been sent, then the next cell to be 
      transmitted would be a forward RM cell.
      
      This attribute is ignored under all conditions where the operational 
      attribute abrConnectionType has the value erSwitch.
      
      The provisioned value of 781 is signalled as TRM = 0, in the ABR 
      Additional Parameters Information Element. 
      1563 is signalled as TRM = 1. 
      3125 is signalled as TRM = 2. 
      6250 is signalled as TRM = 3. 
      12500 is signalled as TRM = 4 
      25000 is signalled as TRM = 5. 
      50000 is signalled as TRM = 6. 
      100000 is signalled as TRM = 7.

      VALUES (

      16777216 = sameAsCa

      )"
   DEFVAL     { 16777216 }
::= { atmIfVptVccVcdTmAbrProvEntry 16 }

atmIfVptVccVcdTmAbrCutoffDecreaseFactor OBJECT-TYPE
   SYNTAX     Unsigned32 (0 | 1 | 2 | 4 | 8 | 16 | 32 | 64 | 16777216)
   ACCESS     read-write
   STATUS     mandatory
   DESCRIPTION
     "This attribute specifies the Cutoff Decrease Factor (CDF) parameter 
      for this connection. When the value of this attribute is non-zero, 
      CDF is computed as the inverse of the value. For example, if the 
      value is 32, the value of CDF is 1/32. When the value of this 
      attribute is 0, CDF is also zero.
      
      CDF controls the decrease in the Allowed Cell Rate (ACR) 
      associated with the CRM parameter, the limit of the number of 
      forward Resource Management (RM) cells which may be sent in 
      the absence of received backward RM cells. When this limit is 
      crossed, the ACR value would be decreased by the amount 
      (CDF*ACR). The ACR is not allowed to fall below the Minimum 
      Cell Rate (MCR), in which case the ACR is set to MCR.
      
      The value of CRM is indicated by the forwardRmCellLimit 
      attribute.
      
      This attribute is ignored under all conditions where the operational 
      attribute abrConnectionType indicates erSwitch or efciSwitch.

      VALUES (

      16777216 = sameAsCa

      )"
   DEFVAL     { 16777216 }
::= { atmIfVptVccVcdTmAbrProvEntry 17 }

atmIfVptVccVcdTmAbrAcrDecreaseTimeFactor OBJECT-TYPE
   SYNTAX     Unsigned32 (0..1023 | 16777216)
   ACCESS     read-write
   STATUS     mandatory
   DESCRIPTION
     "This attribute specifies the Allowed Cell Rate Decrease Time Factor 
      (ADTF) parameter for this connection.
      
      ADTF is the maximum time interval permitted between sending 
      forward Resource Management (RM) cells before the Allowed Cell 
      Rate (ACR) is decreased to initialCellRate. In other words, if the 
      source does not transit a forward RM cell for the period specified by 
      adtf, it reduces its ACR to the value of its initialCellRate.
      
      This attribute is ignored under all conditions where the operational 
      attribute abrConnectionType indicates erSwitch or efciSwitch.

      VALUES (

      16777216 = sameAsCa

      )"
   DEFVAL     { 16777216 }
::= { atmIfVptVccVcdTmAbrProvEntry 18 }

atmIfVptVccVcdTmAbrDgcraMaximumDelay OBJECT-TYPE
   SYNTAX     Unsigned32 (1..16700000 | 16777216)
   ACCESS     read-write
   STATUS     mandatory
   DESCRIPTION
     "This attribute specifies an upper bound on the delay after which the 
      rate change induced by a backward Resource Management (RM) 
      cell departing from this connection point (in the backward 
      direction) is expected to be observed at this connection point (in the 
      forward direction).
      
      This upper bound may be approximated as the sum of the round trip 
      fixed and propagation delays and the maximum queuing delays 
      between the ABR source and this interface.
      
      The value of this attribute is used in policing an ABR connection 
      using the Dynamic General Cell Rate Algorithm (DGCRA). A 
      larger value for this attribute implies a more lenient policer. When 
      there is a reduction in the Allowed Cell Rate (ACR), the policer 
      waits for a correspondingly longer period of time before it enforces 
      at the new cell rate.
      
      The value of this attribute must not be less than the 
      dgcraMinimumDelay attribute.

      VALUES (

      16777216 = sameAsCa

      )"
   DEFVAL     { 16777216 }
::= { atmIfVptVccVcdTmAbrProvEntry 19 }

atmIfVptVccVcdTmAbrDgcraMinimumDelay OBJECT-TYPE
   SYNTAX     Unsigned32 (1..16700000 | 16777216)
   ACCESS     read-write
   STATUS     mandatory
   DESCRIPTION
     "This attribute specifies a lower bound on the delay after which the 
      rate change induced by a backward Resource Management (RM) 
      cell departing from this connection point (in the backward 
      direction) is expected to be observed at this connection point (in the 
      forward connection).
      
      This lower bound may be approximated as the sum of the round trip 
      fixed and propagation delays between the ABR source and this 
      interface.
      
      The value of this attribute is used in policing an ABR connection 
      using the Dynamic General Cell Rate Algorithm (DGCRA). A 
      smaller value for this attribute implies a more lenient policer. When 
      there is a increase in the Allowed Cell Rate (ACR), the policer waits 
      for a correspondingly shorter period of time before it enforces at the 
      new cell rate.

      VALUES (

      16777216 = sameAsCa

      )"
   DEFVAL     { 16777216 }
::= { atmIfVptVccVcdTmAbrProvEntry 20 }

atmIfVptVccVcdTmAbrFarEndAcrDecreaseTimeFactor OBJECT-TYPE
   SYNTAX     Unsigned32 (0..1023 | 1024)
   ACCESS     read-write
   STATUS     mandatory
   DESCRIPTION
     "This attribute specifies the Allowed Cell Rate Decrease Time Factor 
      (ADTF) of the far end ABR source. The value specified should be 
      the same as the ADTF parameter at the far end of this ABR 
      connection. 
      
      The value of this attribute is used in policing an ABR connection 
      using the Dynamic Generic Cell Rate Algorithm (DGCRA). A 
      larger value for this attribute implies a more lenient policer. When 
      the delay between two consecutive forward Resource Management 
      (RM) cells received at this interface corresponds to a value greater 
      than the value of this attribute, the policer begins to limit enforce 
      the incoming traffic at the initial cell rate (ICR) of the far end, as 
      specified by the farEndInitialCellRate attribute.

      VALUES (

      1024 = sameAsLocal

      )"
   DEFVAL     { 1024 }
::= { atmIfVptVccVcdTmAbrProvEntry 21 }

atmIfVptVccVcdTmAbrFarEndInitialCellRate OBJECT-TYPE
   SYNTAX     Unsigned32 (0..16777215 | 16777219)
   ACCESS     read-write
   STATUS     mandatory
   DESCRIPTION
     "This attribute specifies the Initial Cell Rate (ICR) of the far end 
      ABR source. The value specified should be the same as the ICR 
      parameter at the far end of this ABR connection. 
      
      The value of this attribute is used in policing an ABR connection 
      using the Dynamic Generic Cell Rate Algorithm (DGCRA). A 
      larger value for this attribute implies a more lenient policer. When 
      the delay between two consecutive forward Resource Management 
      (RM) cells received at this interface corresponds to a value greater 
      than the farEndAcrDecreaseTimeFactor attribute, the policer begins 
      to enforce the incoming traffic at the value of this attribute.
      
      If this attribute is specified less than the MCR of the connection, 
      then the MCR is used as the feIcr. If this attribute is more than the 
      PCR of the connection, then PCR is used as the feIcr.

      VALUES (

      16777219 = sameAsLocal

      )"
   DEFVAL     { 16777219 }
::= { atmIfVptVccVcdTmAbrProvEntry 22 }


-- AtmIf/n Vcc/vpi.vci Loop
-- The Loop component configures an ATM connection so that cells 
-- received from the ATM interface are retransmitted back to the 
-- interface through that connection. The Loop component requires 
-- exclusive use of its parent Vcc or Vpc and cannot co-exist with other 
-- ATM service components (such as Nep, Nrp, and Test).

atmIfVptVccLoop OBJECT IDENTIFIER ::= { atmIfVptVcc 3 }



atmIfVptVccLoopRowStatusTable OBJECT-TYPE
   SYNTAX     SEQUENCE OF AtmIfVptVccLoopRowStatusEntry
   ACCESS     not-accessible
   STATUS     mandatory
   DESCRIPTION
     "This entry controls the addition and deletion of 
      atmIfVptVccLoop components."
::= { atmIfVptVccLoop 1 }

atmIfVptVccLoopRowStatusEntry OBJECT-TYPE
   SYNTAX     AtmIfVptVccLoopRowStatusEntry
   ACCESS     not-accessible
   STATUS     mandatory
   DESCRIPTION
     "A single entry in the table represents a single 
      atmIfVptVccLoop component."
   INDEX {
      atmIfIndex,
      atmIfVptIndex,
      atmIfVptVccIndex,
      atmIfVptVccLoopIndex }
::= { atmIfVptVccLoopRowStatusTable 1 }

AtmIfVptVccLoopRowStatusEntry ::= SEQUENCE {
   atmIfVptVccLoopRowStatus
      RowStatus,
   atmIfVptVccLoopComponentName
      DisplayString,
   atmIfVptVccLoopStorageType
      StorageType,
   atmIfVptVccLoopIndex
      NonReplicated }

atmIfVptVccLoopRowStatus OBJECT-TYPE
   SYNTAX     RowStatus 
   ACCESS     read-write
   STATUS     mandatory
   DESCRIPTION
     "This variable is used as the basis for SNMP naming of
      atmIfVptVccLoop components.
      These components can be added and deleted."
::= { atmIfVptVccLoopRowStatusEntry 1 }

atmIfVptVccLoopComponentName OBJECT-TYPE
   SYNTAX     DisplayString 
   ACCESS     read-only
   STATUS     mandatory
   DESCRIPTION
     "This variable provides the component's string name for
      use with the ASCII Console Interface"
::= { atmIfVptVccLoopRowStatusEntry 2 }

atmIfVptVccLoopStorageType OBJECT-TYPE
   SYNTAX     StorageType 
   ACCESS     read-only
   STATUS     mandatory
   DESCRIPTION
     "This variable represents the storage type value for the
      atmIfVptVccLoop tables."
::= { atmIfVptVccLoopRowStatusEntry 4 }

atmIfVptVccLoopIndex OBJECT-TYPE
   SYNTAX     NonReplicated 
   ACCESS     not-accessible
   STATUS     mandatory
   DESCRIPTION
     "This variable represents the index for the atmIfVptVccLoop tables."
::= { atmIfVptVccLoopRowStatusEntry 10 }


-- AtmIf/n Vcc/vpi.vci Nep
-- The NailedUpEndPoint component is used to link a VCC to an 
-- application that sends and receives frames using the connection. 
-- The Nep component requires exclusive use of its parent Vcc and 
-- cannot co-exist with other ATM service components (such as Nrp, 
-- Test, and Loop).

atmIfVptVccNep OBJECT IDENTIFIER ::= { atmIfVptVcc 5 }



atmIfVptVccNepRowStatusTable OBJECT-TYPE
   SYNTAX     SEQUENCE OF AtmIfVptVccNepRowStatusEntry
   ACCESS     not-accessible
   STATUS     mandatory
   DESCRIPTION
     "This entry controls the addition and deletion of 
      atmIfVptVccNep components."
::= { atmIfVptVccNep 1 }

atmIfVptVccNepRowStatusEntry OBJECT-TYPE
   SYNTAX     AtmIfVptVccNepRowStatusEntry
   ACCESS     not-accessible
   STATUS     mandatory
   DESCRIPTION
     "A single entry in the table represents a single 
      atmIfVptVccNep component."
   INDEX {
      atmIfIndex,
      atmIfVptIndex,
      atmIfVptVccIndex,
      atmIfVptVccNepIndex }
::= { atmIfVptVccNepRowStatusTable 1 }

AtmIfVptVccNepRowStatusEntry ::= SEQUENCE {
   atmIfVptVccNepRowStatus
      RowStatus,
   atmIfVptVccNepComponentName
      DisplayString,
   atmIfVptVccNepStorageType
      StorageType,
   atmIfVptVccNepIndex
      NonReplicated }

atmIfVptVccNepRowStatus OBJECT-TYPE
   SYNTAX     RowStatus 
   ACCESS     read-write
   STATUS     mandatory
   DESCRIPTION
     "This variable is used as the basis for SNMP naming of
      atmIfVptVccNep components.
      These components can be added and deleted."
::= { atmIfVptVccNepRowStatusEntry 1 }

atmIfVptVccNepComponentName OBJECT-TYPE
   SYNTAX     DisplayString 
   ACCESS     read-only
   STATUS     mandatory
   DESCRIPTION
     "This variable provides the component's string name for
      use with the ASCII Console Interface"
::= { atmIfVptVccNepRowStatusEntry 2 }

atmIfVptVccNepStorageType OBJECT-TYPE
   SYNTAX     StorageType 
   ACCESS     read-only
   STATUS     mandatory
   DESCRIPTION
     "This variable represents the storage type value for the
      atmIfVptVccNep tables."
::= { atmIfVptVccNepRowStatusEntry 4 }

atmIfVptVccNepIndex OBJECT-TYPE
   SYNTAX     NonReplicated 
   ACCESS     not-accessible
   STATUS     mandatory
   DESCRIPTION
     "This variable represents the index for the atmIfVptVccNep tables."
::= { atmIfVptVccNepRowStatusEntry 10 }

atmIfVptVccNepProvTable OBJECT-TYPE
   SYNTAX     SEQUENCE OF AtmIfVptVccNepProvEntry
   ACCESS     not-accessible
   STATUS     mandatory
   DESCRIPTION
     "This group contains provisionable attributes for the Nep component."
::= { atmIfVptVccNep 100 }

atmIfVptVccNepProvEntry OBJECT-TYPE
   SYNTAX     AtmIfVptVccNepProvEntry
   ACCESS     not-accessible
   STATUS     mandatory
   DESCRIPTION
     "An entry in the atmIfVptVccNepProvTable."
   INDEX {
      atmIfIndex,
      atmIfVptIndex,
      atmIfVptVccIndex,
      atmIfVptVccNepIndex }
::= { atmIfVptVccNepProvTable 1 }

AtmIfVptVccNepProvEntry ::= SEQUENCE {
   atmIfVptVccNepApplicationName
      Link }

atmIfVptVccNepApplicationName OBJECT-TYPE
   SYNTAX     Link 
   ACCESS     read-only
   STATUS     mandatory
   DESCRIPTION
     "This attribute specifies the application that sends and receives 
      frames using the VCC. This attribute is set, for example, by 
      provisioning the Trunk AtmAccess AtmConnection attribute. If it is 
      properly configured, this attribute will show a value such as
      'Trk/22 AtmAccess'."
::= { atmIfVptVccNepProvEntry 10 }


-- AtmIf/n Vcc/vpi.vci Test
-- The Test component allows test traffic to be sent over an ATM 
-- connection. It is used to verify the integrity of hardware carrying 
-- ATM traffic, and provides test capabilities similar to those provided 
-- by non-ATM port and line tests. The Test component requires 
-- exclusive use of its parent Vcc and cannot co-exist with other ATM 
-- service components (such as Nep, Nrp, and Loop).
-- 
-- An ATM connection test circulates traffic through a VCC having a 
-- Test component at one end and the other end configured to loop 
-- back ATM cells. The Test component generates test frames, 
-- transforms them into ATM cells using AAL5 segmentation, and 
-- transmits them through the VCC; the returned cells are received by 
-- the Test component, reassembled back into frames, and the frames 
-- are consumed.
-- 
-- The test frames generated by the test are grouped into two 
-- independent streams.
-- 1) The loading frame stream circulates a set of "loading frames" 
-- through the connection as rapidly as possible. The intent of this 
-- stream is to verify the operation of the connection under a 
-- controlled load.
-- 2) The verification stream transmits a series of "verification frames" 
-- through the connection; as each frame is returned, the Test 
-- component verifies its contents and the next verification frame in 
-- the series is transmitted. The intent of this stream is to verify that 
-- frames are not being corrupted.
-- The test can be configured to send frames from either or both 
-- streams. The size and content of the test frames can also be 
-- controlled.

atmIfVptVccTest OBJECT IDENTIFIER ::= { atmIfVptVcc 6 }



atmIfVptVccTestRowStatusTable OBJECT-TYPE
   SYNTAX     SEQUENCE OF AtmIfVptVccTestRowStatusEntry
   ACCESS     not-accessible
   STATUS     mandatory
   DESCRIPTION
     "This entry controls the addition and deletion of 
      atmIfVptVccTest components."
::= { atmIfVptVccTest 1 }

atmIfVptVccTestRowStatusEntry OBJECT-TYPE
   SYNTAX     AtmIfVptVccTestRowStatusEntry
   ACCESS     not-accessible
   STATUS     mandatory
   DESCRIPTION
     "A single entry in the table represents a single 
      atmIfVptVccTest component."
   INDEX {
      atmIfIndex,
      atmIfVptIndex,
      atmIfVptVccIndex,
      atmIfVptVccTestIndex }
::= { atmIfVptVccTestRowStatusTable 1 }

AtmIfVptVccTestRowStatusEntry ::= SEQUENCE {
   atmIfVptVccTestRowStatus
      RowStatus,
   atmIfVptVccTestComponentName
      DisplayString,
   atmIfVptVccTestStorageType
      StorageType,
   atmIfVptVccTestIndex
      NonReplicated }

atmIfVptVccTestRowStatus OBJECT-TYPE
   SYNTAX     RowStatus 
   ACCESS     read-write
   STATUS     mandatory
   DESCRIPTION
     "This variable is used as the basis for SNMP naming of
      atmIfVptVccTest components.
      These components can be added and deleted."
::= { atmIfVptVccTestRowStatusEntry 1 }

atmIfVptVccTestComponentName OBJECT-TYPE
   SYNTAX     DisplayString 
   ACCESS     read-only
   STATUS     mandatory
   DESCRIPTION
     "This variable provides the component's string name for
      use with the ASCII Console Interface"
::= { atmIfVptVccTestRowStatusEntry 2 }

atmIfVptVccTestStorageType OBJECT-TYPE
   SYNTAX     StorageType 
   ACCESS     read-only
   STATUS     mandatory
   DESCRIPTION
     "This variable represents the storage type value for the
      atmIfVptVccTest tables."
::= { atmIfVptVccTestRowStatusEntry 4 }

atmIfVptVccTestIndex OBJECT-TYPE
   SYNTAX     NonReplicated 
   ACCESS     not-accessible
   STATUS     mandatory
   DESCRIPTION
     "This variable represents the index for the atmIfVptVccTest tables."
::= { atmIfVptVccTestRowStatusEntry 10 }

atmIfVptVccTestStateTable OBJECT-TYPE
   SYNTAX     SEQUENCE OF AtmIfVptVccTestStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { atmIfVptVccTest 100 }

atmIfVptVccTestStateEntry OBJECT-TYPE
   SYNTAX     AtmIfVptVccTestStateEntry
   ACCESS     not-accessible
   STATUS     mandatory
   DESCRIPTION
     "An entry in the atmIfVptVccTestStateTable."
   INDEX {
      atmIfIndex,
      atmIfVptIndex,
      atmIfVptVccIndex,
      atmIfVptVccTestIndex }
::= { atmIfVptVccTestStateTable 1 }

AtmIfVptVccTestStateEntry ::= SEQUENCE {
   atmIfVptVccTestAdminState
      INTEGER,
   atmIfVptVccTestOperationalState
      INTEGER,
   atmIfVptVccTestUsageState
      INTEGER }

atmIfVptVccTestAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { atmIfVptVccTestStateEntry 1 }

atmIfVptVccTestOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { atmIfVptVccTestStateEntry 2 }

atmIfVptVccTestUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { atmIfVptVccTestStateEntry 3 }

atmIfVptVccTestSetupTable OBJECT-TYPE
   SYNTAX     SEQUENCE OF AtmIfVptVccTestSetupEntry
   ACCESS     not-accessible
   STATUS     mandatory
   DESCRIPTION
     "This group contains attributes that govern the operation of an ATM 
      connection test. These attributes cannot be changed while the test is 
      running."
::= { atmIfVptVccTest 110 }

atmIfVptVccTestSetupEntry OBJECT-TYPE
   SYNTAX     AtmIfVptVccTestSetupEntry
   ACCESS     not-accessible
   STATUS     mandatory
   DESCRIPTION
     "An entry in the atmIfVptVccTestSetupTable."
   INDEX {
      atmIfIndex,
      atmIfVptIndex,
      atmIfVptVccIndex,
      atmIfVptVccTestIndex }
::= { atmIfVptVccTestSetupTable 1 }

AtmIfVptVccTestSetupEntry ::= SEQUENCE {
   atmIfVptVccTestFrmTypes
      OCTET STRING,
   atmIfVptVccTestFrmSize
      Unsigned32,
   atmIfVptVccTestFrmPatternType
      INTEGER,
   atmIfVptVccTestCustomizedPattern
      Hex,
   atmIfVptVccTestDuration
      Unsigned32,
   atmIfVptVccTestBandwidthElastic
      INTEGER,
   atmIfVptVccTestOverrideHoldingPriority
      INTEGER }

atmIfVptVccTestFrmTypes OBJECT-TYPE
   SYNTAX     OCTET STRING (SIZE (1))
   ACCESS     read-write
   STATUS     mandatory
   DESCRIPTION
     "This attribute specifies the types of the test frames to be transmitted 
      during the ATM connection test. It must contain at least one of the 
      following:
      loading: A set of 'loading frames' is circulated over the link as 
      rapidly as possible. This frame type should be selected when the 
      test is intended to verify the operation of the connection under a 
      specified load. These frames are not checked for bit errors.
      verification: A single 'verification frame' is transmitted over the 
      link; when the frame is returned, its contents are verified and the 
      next verification frame in the series is transmitted. This frame type 
      should be selected when the test is intended to verify that frames are 
      not being corrupted as they pass over the connection.

      Description of bits:
      loading(0)
      verification(1)"
   DEFVAL     { 'c0'H }
::= { atmIfVptVccTestSetupEntry 10 }

atmIfVptVccTestFrmSize OBJECT-TYPE
   SYNTAX     Unsigned32 (4..4096)
   ACCESS     read-write
   STATUS     mandatory
   DESCRIPTION
     "This attribute defines the size of the test frames used in an ATM 
      connection test."
   DEFVAL     { 1024 }
::= { atmIfVptVccTestSetupEntry 20 }

atmIfVptVccTestFrmPatternType OBJECT-TYPE
   SYNTAX     INTEGER  {
                 ccitt32kBitPattern(0),
                 ccitt8MBitPattern(1),
                 customizedPattern(2) }
   ACCESS     read-write
   STATUS     mandatory
   DESCRIPTION
     "This attribute specifies the bit sequence used to fill the frames used 
      in the ATM connection test. It must contain one of the following 
      values:
      ccitt32kBitPattern: a pseudo-random sequence of 32 Kbit is used
      ccitt8MBitPattern: a pseudo-random sequence of 8Mbit is used
      customizedPattern: the pattern defined in the customizedPattern 
      attribute is used"
   DEFVAL     { ccitt32kBitPattern }
::= { atmIfVptVccTestSetupEntry 30 }

atmIfVptVccTestCustomizedPattern OBJECT-TYPE
   SYNTAX     Hex (0..4294967295)
   ACCESS     read-write
   STATUS     mandatory
   DESCRIPTION
     "This attribute specifies a 32 bit sequence to be used to fill frames 
      when the framePatternType attribute is set to customizedPattern. 
      The default value gives a pattern of alternating 0 and 1 bits."
   DEFVAL     { 1431655765 }
::= { atmIfVptVccTestSetupEntry 40 }

atmIfVptVccTestDuration OBJECT-TYPE
   SYNTAX     Unsigned32 (1..30240)
   ACCESS     read-write
   STATUS     mandatory
   DESCRIPTION
     "This attribute specifies the maximum number of minutes that the 
      ATM connection test is allowed to run. The maximum allowed 
      value permits the test to be run for up to 21 days."
   DEFVAL     { 1 }
::= { atmIfVptVccTestSetupEntry 50 }

atmIfVptVccTestBandwidthElastic OBJECT-TYPE
   SYNTAX     INTEGER  {
                 no(0),
                 yes(1) }
   ACCESS     read-write
   STATUS     mandatory
   DESCRIPTION
     "This attribute specifies whether the connection (VCC) should be 
      configured with elastic bandwidth or not. Elastic bandwidth is of 
      importance in conjuction with IMA links, where some links fail and 
      the resulting bandwidth is less than the requested bandwidth for all 
      connections. In that case, some connections may be reduced in 
      bandwidth based on the setting of the bwElastic attribute.
      
      If this attribute is set to yes, the Test application signals to the 
      connection that the bandwidth for this connection is elastic, and 
      may be reduced in the case of IMA link failures. If the bandwidth is 
      reduced, the rate of test cells which can be handled by the 
      connection will also be reduced. 
      
      If this attribute is set to no, the Test application signals to the 
      connection that the bandwidth for this connection must be 
      maintained at the requested level. If the connection cannot maintain 
      the full bandwidth, the connection may be released (cleared) based 
      on the holding priority of the connection."
   DEFVAL     { no }
::= { atmIfVptVccTestSetupEntry 60 }

atmIfVptVccTestOverrideHoldingPriority OBJECT-TYPE
   SYNTAX     INTEGER  {
                 n0(0),
                 n1(1),
                 n2(2),
                 n3(3),
                 n4(4),
                 noOverride(6) }
   ACCESS     read-write
   STATUS     mandatory
   DESCRIPTION
     "This attribute specifies the override holding priority which should 
      be signalled to the VCC connection at the start of the test. Holding 
      priority is of importance in conjuction with IMA links, where some 
      links fail and the resulting bandwidth is less than the requested 
      bandwidth for all connections. In that case, some connections may 
      be released based on the connection's holding priority.
      
      Zero (0) is thie highest holding priority, and four (4) is the lowest 
      priority. A setting of zero to four overrides whatever holding 
      priority that has been configured at the connection (VCC). A setting 
      of noOverride means that the connection should use its internally 
      configured holding priority."
   DEFVAL     { noOverride }
::= { atmIfVptVccTestSetupEntry 70 }

atmIfVptVccTestResultsTable OBJECT-TYPE
   SYNTAX     SEQUENCE OF AtmIfVptVccTestResultsEntry
   ACCESS     not-accessible
   STATUS     mandatory
   DESCRIPTION
     "This group contains attributes that show the result of an ATM 
      connection test; if no test is running, the attribute group contains the 
      results of the most recently completed test. The attributes of the 
      Results group are reset to their inital values whenever a test is 
      started or any attribute of the Setup group is set."
::= { atmIfVptVccTest 120 }

atmIfVptVccTestResultsEntry OBJECT-TYPE
   SYNTAX     AtmIfVptVccTestResultsEntry
   ACCESS     not-accessible
   STATUS     mandatory
   DESCRIPTION
     "An entry in the atmIfVptVccTestResultsTable."
   INDEX {
      atmIfIndex,
      atmIfVptIndex,
      atmIfVptVccIndex,
      atmIfVptVccTestIndex }
::= { atmIfVptVccTestResultsTable 1 }

AtmIfVptVccTestResultsEntry ::= SEQUENCE {
   atmIfVptVccTestElapsedTime
      Unsigned32,
   atmIfVptVccTestTimeRemaining
      Unsigned32,
   atmIfVptVccTestCauseOfTermination
      INTEGER,
   atmIfVptVccTestBytesTx
      PassportCounter64,
   atmIfVptVccTestBytesRx
      PassportCounter64,
   atmIfVptVccTestLoadingFrmTx
      PassportCounter64,
   atmIfVptVccTestLoadingFrmRx
      PassportCounter64,
   atmIfVptVccTestLoadingFrmLost
      PassportCounter64,
   atmIfVptVccTestVerificationFrmTx
      PassportCounter64,
   atmIfVptVccTestVerificationFrmRx
      PassportCounter64,
   atmIfVptVccTestVerificationFrmBad
      PassportCounter64,
   atmIfVptVccTestUnrecognizableFrmRx
      PassportCounter64 }

atmIfVptVccTestElapsedTime OBJECT-TYPE
   SYNTAX     Unsigned32 (0..30240)
   ACCESS     read-only
   STATUS     mandatory
   DESCRIPTION
     "This attribute displays the number of minutes that the test has been 
      running."
   DEFVAL     { 0 }
::= { atmIfVptVccTestResultsEntry 10 }

atmIfVptVccTestTimeRemaining OBJECT-TYPE
   SYNTAX     Unsigned32 (0..30240)
   ACCESS     read-only
   STATUS     mandatory
   DESCRIPTION
     "This attribute displays the number of minutes that the test will 
      continue to run before stopping automatically."
   DEFVAL     { 0 }
::= { atmIfVptVccTestResultsEntry 20 }

atmIfVptVccTestCauseOfTermination OBJECT-TYPE
   SYNTAX     INTEGER  {
                 testTimeExpired(0),
                 stoppedByOperator(1),
                 neverStarted(2),
                 testRunning(3) }
   ACCESS     read-only
   STATUS     mandatory
   DESCRIPTION
     "This attribute displays the reason the test ended. It contains one fo 
      the following values.
      testTimeExpired: the test ran for the specified duration
      stoppedByOperator: a STOP command was issued
      neverStarted: the test has not been started
      testRunning: the test is currently running"
   DEFVAL     { neverStarted }
::= { atmIfVptVccTestResultsEntry 30 }

atmIfVptVccTestBytesTx OBJECT-TYPE
   SYNTAX     PassportCounter64 
   ACCESS     read-only
   STATUS     mandatory
   DESCRIPTION
     "This attribute displays the number of bytes sent during the test. The 
      counter wraps to zero if it exceeds its maximum value of (2**64)-1."
::= { atmIfVptVccTestResultsEntry 40 }

atmIfVptVccTestBytesRx OBJECT-TYPE
   SYNTAX     PassportCounter64 
   ACCESS     read-only
   STATUS     mandatory
   DESCRIPTION
     "This attribute displays the number of bytes received during the test. 
      The counter wraps to zero if it exceeds its maximum value of 
      (2**64)-1."
::= { atmIfVptVccTestResultsEntry 50 }

atmIfVptVccTestLoadingFrmTx OBJECT-TYPE
   SYNTAX     PassportCounter64 
   ACCESS     read-only
   STATUS     mandatory
   DESCRIPTION
     "This attribute displays the number of loading frames sent during the 
      test. The counter wraps to zero if it exceeds its maximum value of 
      (2**64)-1."
::= { atmIfVptVccTestResultsEntry 60 }

atmIfVptVccTestLoadingFrmRx OBJECT-TYPE
   SYNTAX     PassportCounter64 
   ACCESS     read-only
   STATUS     mandatory
   DESCRIPTION
     "This attribute displays the number of loading frames received 
      during the test. The counter wraps to zero if it exceeds its maximum 
      value of (2**64)-1."
::= { atmIfVptVccTestResultsEntry 70 }

atmIfVptVccTestLoadingFrmLost OBJECT-TYPE
   SYNTAX     PassportCounter64 
   ACCESS     read-only
   STATUS     mandatory
   DESCRIPTION
     "This attribute displays the number of loading frames that were lost 
      during the test. The counter wraps to zero if it exceeds its maximum 
      value of (2**64)-1."
::= { atmIfVptVccTestResultsEntry 80 }

atmIfVptVccTestVerificationFrmTx OBJECT-TYPE
   SYNTAX     PassportCounter64 
   ACCESS     read-only
   STATUS     mandatory
   DESCRIPTION
     "This attribute displays the number of verification frames sent during 
      the test. The counter wraps to zero if it exceeds its maximum value 
      of (2**64)-1."
::= { atmIfVptVccTestResultsEntry 90 }

atmIfVptVccTestVerificationFrmRx OBJECT-TYPE
   SYNTAX     PassportCounter64 
   ACCESS     read-only
   STATUS     mandatory
   DESCRIPTION
     "This attribute displays the number of verification frames received 
      during the test (including errored verification frames). The counter 
      wraps to zero if it exceeds its maximum value of (2**64)-1.
      
      Note that the number of verification frames lost during the test can 
      be computed by the expression verificationFrmTx - 
      verificationFrmRx."
::= { atmIfVptVccTestResultsEntry 100 }

atmIfVptVccTestVerificationFrmBad OBJECT-TYPE
   SYNTAX     PassportCounter64 
   ACCESS     read-only
   STATUS     mandatory
   DESCRIPTION
     "This attribute displays the number of errored verification frames 
      received during the test. A verification frame is considered to be 
      errored if it contains a recognizable verification frame header, but 
      does not match the transmitted frame bit for bit. (Thus, a 
      verification frame that returns after the succeeding verification 
      frame has been transmitted is considered to be errored.) The counter 
      wraps to zero if it exceeds its maximum value of (2**64)-1.
      
      Note that the number of correct verification frames received during 
      the test can be computed by the expression verificationFrmRx - 
      verificationFrmBad."
::= { atmIfVptVccTestResultsEntry 110 }

atmIfVptVccTestUnrecognizableFrmRx OBJECT-TYPE
   SYNTAX     PassportCounter64 
   ACCESS     read-only
   STATUS     mandatory
   DESCRIPTION
     "This attribute displays the number of frames received during the test 
      which do not contain a valid loading frame header or verification 
      frame header. The counter wraps to zero if it exceeds its maximum 
      value of (2**64)-1."
::= { atmIfVptVccTestResultsEntry 120 }


-- AtmIf/n Vpc/vpi TrafficManagement, 
-- AtmIf/n Vcc/vpi.vci TrafficManagement,
-- AtmIf/n Vpt/vpi TrafficManagement,
-- AtmIf/n Vpt/vpi Vcc/vci TrafficManagement
-- The Tm subcomponent contains the operational traffic management 
-- attributes of a connection. It is created dynamically for each 
-- activated Vcc, Vpc, or Vpt component.

atmIfVptVccTm OBJECT IDENTIFIER ::= { atmIfVptVcc 7 }



atmIfVptVccTmRowStatusTable OBJECT-TYPE
   SYNTAX     SEQUENCE OF AtmIfVptVccTmRowStatusEntry
   ACCESS     not-accessible
   STATUS     mandatory
   DESCRIPTION
     "This entry controls the addition and deletion of 
      atmIfVptVccTm components."
::= { atmIfVptVccTm 1 }

atmIfVptVccTmRowStatusEntry OBJECT-TYPE
   SYNTAX     AtmIfVptVccTmRowStatusEntry
   ACCESS     not-accessible
   STATUS     mandatory
   DESCRIPTION
     "A single entry in the table represents a single 
      atmIfVptVccTm component."
   INDEX {
      atmIfIndex,
      atmIfVptIndex,
      atmIfVptVccIndex,
      atmIfVptVccTmIndex }
::= { atmIfVptVccTmRowStatusTable 1 }

AtmIfVptVccTmRowStatusEntry ::= SEQUENCE {
   atmIfVptVccTmRowStatus
      RowStatus,
   atmIfVptVccTmComponentName
      DisplayString,
   atmIfVptVccTmStorageType
      StorageType,
   atmIfVptVccTmIndex
      NonReplicated }

atmIfVptVccTmRowStatus OBJECT-TYPE
   SYNTAX     RowStatus 
   ACCESS     read-only
   STATUS     mandatory
   DESCRIPTION
     "This variable is used as the basis for SNMP naming of
      atmIfVptVccTm components.
      These components cannot be added nor deleted."
::= { atmIfVptVccTmRowStatusEntry 1 }

atmIfVptVccTmComponentName OBJECT-TYPE
   SYNTAX     DisplayString 
   ACCESS     read-only
   STATUS     mandatory
   DESCRIPTION
     "This variable provides the component's string name for
      use with the ASCII Console Interface"
::= { atmIfVptVccTmRowStatusEntry 2 }

atmIfVptVccTmStorageType OBJECT-TYPE
   SYNTAX     StorageType 
   ACCESS     read-only
   STATUS     mandatory
   DESCRIPTION
     "This variable represents the storage type value for the
      atmIfVptVccTm tables."
::= { atmIfVptVccTmRowStatusEntry 4 }

atmIfVptVccTmIndex OBJECT-TYPE
   SYNTAX     NonReplicated 
   ACCESS     not-accessible
   STATUS     mandatory
   DESCRIPTION
     "This variable represents the index for the atmIfVptVccTm tables."
::= { atmIfVptVccTmRowStatusEntry 10 }

atmIfVptVccTmOperTable OBJECT-TYPE
   SYNTAX     SEQUENCE OF AtmIfVptVccTmOperEntry
   ACCESS     not-accessible
   STATUS     mandatory
   DESCRIPTION
     "This group contains attributes for the Tm component to reflect 
      operational traffic attributes."
::= { atmIfVptVccTm 100 }

atmIfVptVccTmOperEntry OBJECT-TYPE
   SYNTAX     AtmIfVptVccTmOperEntry
   ACCESS     not-accessible
   STATUS     mandatory
   DESCRIPTION
     "An entry in the atmIfVptVccTmOperTable."
   INDEX {
      atmIfIndex,
      atmIfVptIndex,
      atmIfVptVccIndex,
      atmIfVptVccTmIndex }
::= { atmIfVptVccTmOperTable 1 }

AtmIfVptVccTmOperEntry ::= SEQUENCE {
   atmIfVptVccTmTxTrafficDescType
      INTEGER,
   atmIfVptVccTmTxQosClass
      INTEGER,
   atmIfVptVccTmTxQueueLength
      Unsigned32,
   atmIfVptVccTmTxQueueCongestionState
      Unsigned32,
   atmIfVptVccTmHoldingPriority
      INTEGER,
   atmIfVptVccTmRxTrafficDescType
      INTEGER,
   atmIfVptVccTmRxQosClass
      INTEGER,
   atmIfVptVccTmAtmServiceCategory
      INTEGER,
   atmIfVptVccTmTrafficShaping
      INTEGER,
   atmIfVptVccTmBearerClassBbc
      INTEGER,
   atmIfVptVccTmTransferCapabilityBbc
      INTEGER,
   atmIfVptVccTmClippingBbc
      INTEGER,
   atmIfVptVccTmUnshapedTransmitQueueing
      INTEGER,
   atmIfVptVccTmBestEffort
      INTEGER,
   atmIfVptVccTmForceTagging
      INTEGER,
   atmIfVptVccTmWeight
      Unsigned32,
   atmIfVptVccTmUsageParameterControl
      INTEGER,
   atmIfVptVccTmTxPacketWiseDiscard
      OCTET STRING,
   atmIfVptVccTmRxPacketWiseDiscard
      OCTET STRING,
   atmIfVptVccTmBandwidthElastic
      INTEGER,
   atmIfVptVccTmBandwidthReduction
      Unsigned32,
   atmIfVptVccTmAbrConnectionType
      INTEGER }

atmIfVptVccTmTxTrafficDescType OBJECT-TYPE
   SYNTAX     INTEGER  {
                 n1(1),
                 n2(2),
                 n3(3),
                 n4(4),
                 n5(5),
                 n6(6),
                 n7(7),
                 n8(8),
                 n9(9) }
   ACCESS     read-only
   STATUS     mandatory
   DESCRIPTION
     "T his attribute indicates the type of traffic management which is 
      applied to the transmit direction of this connection as defined in the 
      ATM Forum. The txTrafficDescType determines the number and 
      meaning of the parameters in the txTrafficDescParm attribute."
::= { atmIfVptVccTmOperEntry 10 }

atmIfVptVccTmTxQosClass OBJECT-TYPE
   SYNTAX     INTEGER  {
                 n0(0),
                 n1(1),
                 n2(2),
                 n3(3),
                 n4(4),
                 notApplicable(14) }
   ACCESS     read-only
   STATUS     mandatory
   DESCRIPTION
     "This attribute indicates the quality of service for the calling to called 
      direction for this connection. This is only applicable to Soft PVC 
      and SVC connections. 
      
      Class 1 supports a QOS that meets Service Class A performance 
      requirements (Circuit emulation, constant bit rate video).
      
      Class 2 supports a QOS that meets Service Class B performance 
      requirements (Variable bit rate audio and video).
      
      Class 3 supports a QOS that meets Service Class C performance 
      requirements (Connection-Oriented Data Transfer).
      
      Class 4 supports a QOS that meets Service Class D performance 
      requirements (Connectionless Data Transfer).
      
      Class 0 is the unspecified QOS class; no objective is specified for 
      the performance parameters.
      
      A value of notApplicable is displayed in the case of nailed-up PVCs 
      for which this attribute has no significance."
::= { atmIfVptVccTmOperEntry 31 }

atmIfVptVccTmTxQueueLength OBJECT-TYPE
   SYNTAX     Unsigned32 (0..30720)
   ACCESS     read-only
   STATUS     mandatory
   DESCRIPTION
     "This attribute indicates the current number of cells in the transmit 
      queue for this connection. 
      
      If this connection has unshapedTransmitQueueing attribute 
      displayed as common, this attribute displays the length of the 
      common queue which is used for this atm service category. 
      
      If this connection has unshapedTransmitQueueing attribute 
      displayed as fifo, this attribute indicates the number of cells for this 
      connection which are enqueued in a first-in-first-out queuing 
      method for this atm service category. This will only occur for 
      connections on ATM IP cards with atmServiceCategory of nrtVbr 
      or ubr. 
      
      If this connection has unshapedTransmitQueueing attribute 
      displayed as perVc or as notApplicable, this attribute displays the 
      length of the per-VC queue.
      
      This attribute does not apply to basic Vpts."
::= { atmIfVptVccTmOperEntry 32 }

atmIfVptVccTmTxQueueCongestionState OBJECT-TYPE
   SYNTAX     Unsigned32 (0..3)
   ACCESS     read-only
   STATUS     mandatory
   DESCRIPTION
     "This attribute indicates the congestion state of the transmit queue 
      for this connection. 
      
      If this connection has unshapedTransmitQueueing attribute 
      displayed as common, this attribute displays the congestion state of 
      the common queue. If this connection has 
      unshapedTransmitQueueing attribute displayed as perVc or as 
      notApplicable, this attribute displays the congestion state of the per-
      VC queue.
      
      The congestion state of a queue is indicated by a numeric value 
      ranging from 0 to 3. When a queue is in a congested state x, only 
      traffic with discard priority (DP) 0 to x are enqueued. Traffic with 
      DP > x is discarded. 
      
      For example, if the congestion state is 3, there is no congestion and 
      all traffic is enqueued. Likewise, when the congestion state is 0, 
      there is maximum congestion and only traffic with DP=0 is 
      enqueued on that queue.
      
      This attribute does not apply to basic Vpts."
::= { atmIfVptVccTmOperEntry 33 }

atmIfVptVccTmHoldingPriority OBJECT-TYPE
   SYNTAX     INTEGER  {
                 n0(0),
                 n1(1),
                 n2(2),
                 n3(3),
                 n4(4),
                 notApplicable(6) }
   ACCESS     read-only
   STATUS     mandatory
   DESCRIPTION
     "This attribute indicates the actual holding priority in effect for this 
      connection. In a situation where the link bandwidth fluctuates, such 
      as over an IMA link, holding priority is used to determine which 
      connections are held and which are released. Holding priority 4 
      connections are the first to be released. Holding priority 0 
      connections are the last to be released. Some applications, for 
      example Vcc Test, may override the provisioned holding priority. 
      
      A value of notApplicable is displayed when this is an elastic 
      connection. Holding priority does not apply to bandwidth elastic 
      connections.
      
      Holding priority has no effect if the equivalent cell rate (ECR) for a 
      connection is zero.
      
      This attribute does not apply to Vpt Vccs."
::= { atmIfVptVccTmOperEntry 35 }

atmIfVptVccTmRxTrafficDescType OBJECT-TYPE
   SYNTAX     INTEGER  {
                 n1(1),
                 n2(2),
                 n3(3),
                 n4(4),
                 n5(5),
                 n6(6),
                 n7(7),
                 n8(8),
                 n9(9) }
   ACCESS     read-only
   STATUS     mandatory
   DESCRIPTION
     "This attribute indicates the type of traffic management which is 
      applied to the receive direction of this connection as defined in the 
      ATM Forum. The rxTrafficDescType determines the number and 
      meaning of the parameters in the rxTrafficDescParm attribute."
::= { atmIfVptVccTmOperEntry 40 }

atmIfVptVccTmRxQosClass OBJECT-TYPE
   SYNTAX     INTEGER  {
                 n0(0),
                 n1(1),
                 n2(2),
                 n3(3),
                 n4(4),
                 notApplicable(14) }
   ACCESS     read-only
   STATUS     mandatory
   DESCRIPTION
     "This attribute indicates the quality of service for the called to calling 
      direction for this connection. This is only applicable to Soft PVC 
      and SVC connections. 
      
      Class 1 supports a QOS that meets Service Class A performance 
      requirements (circuit emulation, constant bit rate video).
      
      Class 2 supports a QOS that meets Service Class B performance 
      requirements (variable bit rate audio and video).
      
      Class 3 supports a QOS that meets Service Class C performance 
      requirements (Connection-Oriented Data Transfer).
      
      Class 4 supports a QOS that meets Service Class D performance 
      requirements (Connectionless Data Transfer).
      
      Class 0 is the unspecified QOS class; no objective is specified for 
      the performance parameters.
      
      A value of notApplicable is displayed in the case of nailed-up PVCs 
      for which this attribute has no significance."
::= { atmIfVptVccTmOperEntry 61 }

atmIfVptVccTmAtmServiceCategory OBJECT-TYPE
   SYNTAX     INTEGER  {
                 unspecifiedBitRate(0),
                 constantBitRate(1),
                 rtVariableBitRate(2),
                 nrtVariableBitRate(3),
                 availableBitRate(4) }
   ACCESS     read-only
   STATUS     mandatory
   DESCRIPTION
     "This attribute indicates the ATM service category used for traffic in 
      both directions of the connection. This attribute does not apply to 
      Virtual Link VPTs and will always be displayed as 
      constantBitRate.
      
      The constantBitRate service category is intended for real time 
      applications, that is, those requiring tightly constrained delay and 
      delay variation, as would be appropriate for voice and video 
      applications. The consistent availability of a fixed quantity of 
      bandwidth is considered appropriate for CBR service. Cells which 
      are delayed beyond the value specified by Cell Transfer Delay are 
      assumed to have significantly reduced value for the application.
      
      The rtVariableBitRate service category is intended for real time 
      applications; that is those requiring tightly constrained delay and 
      delay variation, as would be appropriate for voice and video 
      applications. Sources are expected to transmit at a rate which varies 
      with time. Equivalently, the source can be described as 'bursty'. 
      Cells which are delayed beyond the value specified by Cell Transfer 
      Delay are assumed to be of significantly reduced value to the 
      application. Real time VBR service may support statistical 
      multiplexing of real time sources.
      
      The nrtVariableBitRate service category is intended for non-real 
      time applications which have bursty traffic characteristics and which 
      can be characterized in terms of a PCR, SCR, and MBS. For those 
      cells which are transferred within the traffic contract, the application 
      expects a low cell loss ratio. For all connections, it expects a bound 
      on the mean cell transfer delay. Non-real time VBR service may 
      support statistical multiplexing of connections.
      
      The availableBitRate service is an ATM layer service category for 
      which the limiting ATM layer transfer characteristics provided by 
      the network may change subsequent to connection establishment. 
      ABR service has a flow control mechanism which supports several 
      types of feedback to control the source rate in response to changing 
      ATM layer transfer characteristics. ABR service is not intended to 
      support real-time applications.
      
      The unspecifiedBitRate service is intended for non-real time 
      applications, that is those not requiring tightly constrained delay 
      and delay variation. UBR sources are expected to be bursty. UBR 
      service supports a high degree of statistical multiplexing among 
      sources. UBR service does not specify traffic related service 
      guarantees. No numerical commitments are made with respect to 
      the cell loss ratio experienced by a UBR connection, or as to the 
      cell transfer delay experienced by cells on the connection."
::= { atmIfVptVccTmOperEntry 62 }

atmIfVptVccTmTrafficShaping OBJECT-TYPE
   SYNTAX     INTEGER  {
                 disabled(1),
                 notApplicable(4),
                 linear(5),
                 inverseUpc(6),
                 dynamic(7) }
   ACCESS     read-only
   STATUS     mandatory
   DESCRIPTION
     "This attribute indicates the traffic shaping state of the connection.
      
      A value of notApplicable indicates that traffic shaping is not 
      applicable or not supported for this connection. This is the case:
      - when the txTrafficDescType is 1 or 2.
      - for standard Vpt Vccs and basic Vpts.
      - for CQC-based ATM cards, when the atmServiceCategory is 
      constantBitRate.
      
      In these cases, the value of notApplicable is set regardless of 
      whether traffic shaping is enabled or disabled in the provisioning 
      data.
      
      A value of disabled indicates that traffic shaping is applicable and 
      supported for the type of connection but has been turned off in the 
      provisioning data.
      
      A value of linear or inverseUpc indicates that traffic shaping is 
      applicable and supported for the type of connection and has been 
      turned on in the provisioning data. This is the only case that 
      indicates that traffic shaping is performed on the connection. In this 
      case, the actual shaping rate is reflected in the txTrafficDescParm 
      attribute, parameter number 4. A value of linear indicates that 
      traffic is being shaped at the constant rate indicated in 
      txTrafficDescParm 4.
      
      A value of inverseUpc is possible only on ATM IP cards. This value 
      indicates that the shaper strictly conforms to the requirements of a 
      dual leaky bucket UPC enforcer. This value is indicated if traffic 
      shaping is enabled, and the txTrafficDescType for this connection is 
      6, 7 or 8.
      
      Traffic shaping for connections with atmServiceCategory as 
      availableBitRate (txTrafficDescType 9) depends upon the 
      abrConnectionType attribute. If abrConnectionType is sourceDest 
      or virtualSourceDest, the value of this attribute is dynamic. If 
      abrConnectionType is erSwitch or efciSwitch, this attribute is 
      notApplicable."
::= { atmIfVptVccTmOperEntry 70 }

atmIfVptVccTmBearerClassBbc OBJECT-TYPE
   SYNTAX     INTEGER  {
                 a(1),
                 c(3),
                 x(16),
                 vp(24),
                 notApplicable(30) }
   ACCESS     read-only
   STATUS     mandatory
   DESCRIPTION
     "This attribute indicates the bearer capability for this connection.
      
      Class a service is a connection-oriented, constant bit rate ATM 
      transport service. Class a service has end to end timing 
      requirements and may require stringent cell loss, cell delay and cell 
      delay variation performance.When a is displayed, the user is 
      requesting more than an ATM only service. The network may look 
      at the AAL to provide interworking based upon its contents. 
      
      Class c service is a connection-oriented, variable bit rate ATM 
      transport service. Class c service has no end-to-end timing 
      requirements.When c is displayed, the user is requesting more than 
      an ATM only service. The network interworking function may look 
      at the AAL and provide service based on it.
      
      Class x service is a connection-oriented ATM transport service 
      where the AAL, trafficType (cbr or vbr), and timing requirements 
      are user defined (that is, transparent to the network). When the 
      value of this attribute is x, the user is requesting an ATM only 
      service from the network. In this case, the network shall not process 
      any higher layer protocol.
      
      Class vp service is used to indicate a transparent VP service when 
      the user is requesting an ATM only service from the network. In this 
      case, the network does not process any higher layer protocol. This 
      service differs from class x service in that with the class vp service 
      both the VCI field (except for VCI values 0, 3, 4, and 6 through 15) 
      and Payload Type field are transported transparently by the network. 
      This attribute value is only applicable to SPVP and SVP 
      connections.
      
      A value of notApplicable is displayed in the case of nailed-up PVCs 
      for which this attribute has no significance."
::= { atmIfVptVccTmOperEntry 71 }

atmIfVptVccTmTransferCapabilityBbc OBJECT-TYPE
   SYNTAX     INTEGER  {
                 n0(0),
                 n1(1),
                 n2(2),
                 n5(5),
                 n8(8),
                 n9(9),
                 n10(10),
                 notApplicable(30) }
   ACCESS     read-only
   STATUS     mandatory
   DESCRIPTION
     "This attribute indicates the transfer capability for this connection. 
      Uni 3.0/3.1 traffic type and end-to-end timing parameters are 
      mapped into this parameter as follows:
      <transferCapability: TrafficType, Timing>
      0: NoIndication, NoIndication
      1: NoIndication, yes
      2: NoIndication, no
      5: CBR, yes
      8: VBR, NoIndication
      9: VBR, yes
      10: VBR, no
      
      A value of notApplicable is displayed in the case of nailed-up PVCs 
      for which this attribute has no significance, or in the case that the 
      transfer capability in the call request was set to NoIndication.
      
      The CBR traffic type refers to traffic offered on services such as a 
      constant bit rate video service or a circuit emulation.
      
      The VBR traffic type refers to traffic offered on services such as 
      packetized audio and video, or data.
      
      The value NoIndication for traffic type is used if the user has not set 
      the traffic type; similarly for end-to-end timing.
      
      The value yes for end-to-end timing indicates that end-to-end 
      timing is required for the connection.
      
      The value no for end-to-end timing indicates that end-to-end timing 
      is not required for the connection."
::= { atmIfVptVccTmOperEntry 72 }

atmIfVptVccTmClippingBbc OBJECT-TYPE
   SYNTAX     INTEGER  {
                 no(0),
                 yes(1),
                 notApplicable(14) }
   ACCESS     read-only
   STATUS     mandatory
   DESCRIPTION
     "This attribute indicates the value of the clipping susceptibility 
      parameter in the broadband bearer capability (BBC) Information 
      Element.
      
      Clipping is an impairment in which the first fraction of a second of 
      information to be transferred is lost. It occurs after a call is 
      answered and before an associated connection is switched through.
      
      A value of notApplicable is displayed in the case of nailed-up PVCs 
      for which this attribute has no significance."
::= { atmIfVptVccTmOperEntry 74 }

atmIfVptVccTmUnshapedTransmitQueueing OBJECT-TYPE
   SYNTAX     INTEGER  {
                 perVc(0),
                 common(1),
                 notApplicable(4),
                 fifo(5) }
   ACCESS     read-only
   STATUS     mandatory
   DESCRIPTION
     "This attribute indicates the unshaped transmit queuing state of the 
      connection.
      
      A value of common indicates that transmit traffic is being enqueued 
      onto the common transmit queue for this service category. 
      The txQueueLength attribute indicates the current length of the 
      common transmit queue.
      
      A value of fifo indicates that transmit traffic is being queued in a 
      first-in-first-out basis for this service category. This is similar to 
      common queueing, but the txQueueLength attribute indicates the 
      number of cells in this connection queue. A value of fifo will only 
      be indicated for connections on ATM IP cards with 
      atmServiceCategory of nrtVbr or ubr. 
      A value of perVc indicates that transmit traffic is being enqueued 
      onto a per-VC queue for this connection.
      
      A value of notApplicable indicates that transmit traffic is being 
      shaped for this connection, or that unshaped transmit queuing is not 
      applicable for this type of connection. Transmit traffic for a shaped 
      connection is enqueued onto a per-VC queue, but this attribute is 
      only applicable for unshaped connections. Unshaped transmit 
      queuing is not applicable for basic Vpts."
::= { atmIfVptVccTmOperEntry 75 }

atmIfVptVccTmBestEffort OBJECT-TYPE
   SYNTAX     INTEGER  {
                 indicated(0),
                 notIndicated(1),
                 notApplicable(14) }
   ACCESS     read-only
   STATUS     mandatory
   DESCRIPTION
     "This attribute indicates value of best effort parameter in the ATM 
      Traffic Descriptor Information Element.
      
      The value indicated implies that the quality of service for this 
      connection is not guaranteed.
      
      The value notIndicated implies that the quality of service for this 
      connection is guaranteed.
      
      A value of notApplicable is displayed in the case of nailed-up PVCs 
      for which this attribute has no significance."
::= { atmIfVptVccTmOperEntry 76 }

atmIfVptVccTmForceTagging OBJECT-TYPE
   SYNTAX     INTEGER  {
                 enabled(0),
                 disabled(1) }
   ACCESS     read-only
   STATUS     mandatory
   DESCRIPTION
     "This attribute indicates the state of force tagging option for this 
      connection. Force tagging refers to setting the CLP bit for all cells 
      on a connection. 
      
      For CQC-based ATM cards, this attribute is not applicable and is 
      not displayed.
      
      A value of enabled indicates that the CLP bit is being set to 1 for all 
      cells in the transmit direction on this connection. 
      
      A value of disabled indicates that the CLP bit is unchanged for cells 
      in the transmit direction on this connection. disabled is always 
      displayed for Vpts since forced tagging is applied on a per Vpt Vcc 
      basis."
::= { atmIfVptVccTmOperEntry 78 }

atmIfVptVccTmWeight OBJECT-TYPE
   SYNTAX     Unsigned32 (0 | 1..4095 | 65534)
   ACCESS     read-only
   STATUS     mandatory
   DESCRIPTION
     "This attribute indicates the relative weight of this unshaped 
      connection. Connections with a larger weight get a larger proportion 
      of the link bandwidth, or in the case of standard Vpt Vccs, the Vpt 
      bandwidth. 
      
      For all but standard Vpt Vccs, the default connection weight is 
      determined by the weight policy for a service category and the 
      traffic descriptor for a connection. For standard Vpt Vccs, the 
      default connection weight is determined by the Vcc's service 
      category.
      
      For CQC-based ATM cards, this attribute is not applicable and is 
      not displayed.
      
      A value from 1 to 4095 indicates an actual weight. The value 
      upToQueueLimit indicates that the weight of a connection is up to 
      the transmit queue limit for this connection. upToQueueLimit is 
      used with common (first-in-first-out) queueing. 
      
      This attribute is displayed as notApplicable if:
      - this connection has trafficShaping displayed as linear or 
      inverseUpc.
      - this is a basic Vpt.

      VALUES (

      0 = upToQueueLimit

      65534 = notApplicable

      )"
::= { atmIfVptVccTmOperEntry 79 }

atmIfVptVccTmUsageParameterControl OBJECT-TYPE
   SYNTAX     INTEGER  {
                 enforced(0),
                 disabled(1),
                 notApplicable(3),
                 monitored(4),
                 abrMonitored(5),
                 abrEnforced(6) }
   ACCESS     read-only
   STATUS     mandatory
   DESCRIPTION
     "This attribute indicates the UPC state of the connection.
      
      A value of notApplicable indicates that UPC is not applicable or not 
      supported for the connection. This is the case:
      - when the connection's rxTrafficDescType is 1 or 2. 
      - for standard Vpt Vccs and basic Vpts.
      
      A value of notApplicable is set regardless of whether UPC is 
      disabled or enabled in provisioning data.
      
      A value of disabled indicates that UPC is applicable and supported 
      for the type of connection but has been turned off in the 
      provisioning data.
      
      A value of enforced indicates that UPC is actively checking 
      conformance for the connection and is discarding or tagging cells 
      which do not conform to the connection traffic contract. The traffic 
      descriptor parameters used for UPC conformance are reflected in 
      the rxTrafficDescParms of the connection. On ATM IP cards, the 
      counts of UPC violations are visible in the Vcc, Vpc, or Vpt 
      rxUpcViolationsOnEnforcer1 or rxUpcViolationsOnEnforcer2 
      attributes. 
      
      ATM IP cards provide the ability to monitor UPC violations without 
      tagging or discarding. A value of monitored indicates that UPC is 
      actively checking conformance for the connection and counting the 
      violations, but is not discarding or tagging cells which do not 
      conform to the connection traffic contract. The traffic descriptor 
      parameters used for UPC conformance are reflected in the 
      rxTrafficDescParms of the connection. The counts of UPC 
      violations are visible in the Vcc, Vpc, or Vpt 
      rxUpcViolationsOnEnforcer1 or rxUpcViolationsOnEnforcer2 
      attributes. The value of monitored appears only on ATM IP cards. 
      
      If the atmServiceCategory for this connection indicates 
      availableBitRate, a value of abrEnforced indicates that Dynamic 
      Generic Cell Rate Algorithm (DGCRA) is active for the connection 
      and that violating cells are discarded. The cell rate which is in effect 
      at any particular instant is indicated in rxTrafficDescParm 4 of the 
      connection. 
      
      If the atmServiceCategory for this connection indicates 
      availableBitRate, a value of abrMonitored indicates that Dynamic 
      Generic Cell Rate Algorithm (DGCRA) is active for the connection 
      but that violating cells are counted only. The cell rate which is in 
      effect at any particular instant is indicated in rxTrafficDescParm 4 
      of the connection."
::= { atmIfVptVccTmOperEntry 80 }

atmIfVptVccTmTxPacketWiseDiscard OBJECT-TYPE
   SYNTAX     OCTET STRING (SIZE (1))
   ACCESS     read-only
   STATUS     mandatory
   DESCRIPTION
     "This attribute indicates the current set of packet-wise discard 
      functions in effect in the transmit data direction at this connection 
      point.
      
      A value of ppd indicates that the Partial Packet Discard (PPD) 
      function is in effect. PPD may be applied at an intermediate 
      connecting point for a connection which is transporting frame traffic 
      (AAL5 at the endpoint). PPD is controlled by provisioning for 
      PVCs and SPVCs, and by call setup parameters in the AAL and 
      Traffic Descriptor Information Elements.
      
      A value of epd indicates that the Early Packet Discard (EPD) 
      function is in effect at this connection endpoint. On CQC-based 
      ATM cards, PPD and EPD are enabled by default at a connection 
      endpoint which is performing AAL5 segmentation and assembly.
      
      A value of wred indicates that Weighted Random Early Detection is 
      in effect at this connection point. W-RED can be enabled by 
      provisioning for PVCs and SPVCs.
      
      On ATM IP cards, all packet-wise discard functions also apply to 
      provisioned virtual path connections (VPCs). On CQC-based ATM 
      cards, packet-wise functions are not applicable for VPCs.
      
      This attribute is not applicable for Vpts.

      Description of bits:
      ppd(0)
      epd(1)
      wred(2)"
::= { atmIfVptVccTmOperEntry 85 }

atmIfVptVccTmRxPacketWiseDiscard OBJECT-TYPE
   SYNTAX     OCTET STRING (SIZE (1))
   ACCESS     read-only
   STATUS     mandatory
   DESCRIPTION
     "This attribute indicates the current set of packet-wise discard 
      functions in effect in the receive data direction at this connection 
      point.
      
      A value of ppd indicates that the Partial Packet Discard (PPD) 
      function is in effect. PPD may be applied at an intermediate 
      connecting point for a connection which is transporting frame traffic 
      (AAL5 at the endpoint). PPD is controlled by provisioning for 
      PVCs and SPVCs, and by call setup parameters in the AAL and 
      Traffic Descriptor Information Elements.
      
      A value of epd indicates that the Early Packet Discard (EPD) 
      function is in effect at this connection endpoint. PPD and EPD are 
      enabled by default at a connection endpoint which is performing 
      AAL5 segmentation and assembly.
      
      On ATM IP cards, all packet-wise discard functions also apply to 
      provisioned virtual path connections (VPCs). On CQC-based ATM 
      cards, packet-wise functions are not applicable for VPCs.
      
      This attribute is not applicable for Vpts.

      Description of bits:
      ppd(0)
      epd(1)"
::= { atmIfVptVccTmOperEntry 86 }

atmIfVptVccTmBandwidthElastic OBJECT-TYPE
   SYNTAX     INTEGER  {
                 no(0),
                 yes(1) }
   ACCESS     read-only
   STATUS     mandatory
   DESCRIPTION
     "This attribute is only of importance for connections which are 
      carried on a link with a variable bandwidth. For example, the 
      bandwidth may be reduced in the event that one or more physical 
      links in the IMA group fail, such that the originally requested 
      bandwidth cannot be maintained. This attribute shows whether the 
      application (for example, Trunk) running on this connection can 
      continue to operate if the bandwidth is reduced. If the bandwidth is 
      reduced, the amount by which it is reduced is displayed in the 
      bandwidthReduction attribute. 
      
      A value of yes, indicates that this connection is elastic, and the 
      bandwidth may be reduced but the connection is not released. 
      
      A value of no indicates that the bandwidth for this connection is not 
      reduced in the event of link bandwidth reduction. However, this 
      connection may be released based on its holdingPriority.
      
      Bandwidth elasticity has no effect for connections which have an 
      equivalent cell rate (ECR) of zero. 
      
      This attribute is not applicable for Vpts and Vpt Vccs."
::= { atmIfVptVccTmOperEntry 90 }

atmIfVptVccTmBandwidthReduction OBJECT-TYPE
   SYNTAX     Unsigned32 (0..2147483647)
   ACCESS     read-only
   STATUS     mandatory
   DESCRIPTION
     "This attribute shows the amount by which the bandwidth has been 
      reduced for this connection. This value is non-zero only for 
      connections which have bandwidthElastic displayed as yes, and 
      which are also operating in a reduced bandwidth mode. This is 
      typically the case for selected connections running over an IMA 
      link. This attribute takes a value from 0 (no reduction) up to the 
      ECR. For all connections which are running at their full allocated 
      bandwidth, bwReduction has the value 0. Connections which have 
      been reduced in allocated bandwidth have a positive number for this 
      attribute. The bwReduction may be subtracted from the ECR (which 
      is displayed as txTrafficDescParm 5) to determine the actual 
      bandwidth allocated to this connection."
::= { atmIfVptVccTmOperEntry 100 }

atmIfVptVccTmAbrConnectionType OBJECT-TYPE
   SYNTAX     INTEGER  {
                 erSwitch(1),
                 efciSwitch(2),
                 virtualSourceDest(3),
                 sourceDest(4),
                 nonAbrInterworking(5),
                 notApplicable(15) }
   ACCESS     read-only
   STATUS     mandatory
   DESCRIPTION
     "This attribute indicates the type of ABR behavior which is in effect 
      at this connection. This attribute is only applicable if the 
      atmServiceCategory attribute is availableBitRate. If the 
      atmServiceCategory attribute is not availableBitRate, or if the 
      connection is not active, this attribute value is displayed as 
      notApplicable.
      
      For CQC-based ATM cards, the only possible values are 
      notApplicable, efciSwitch or nonAbrInterworking. In EFCI 
      marking mode, the Explicit Forward Congestion Indication (EFCI) 
      field in the data cell headers is used to indicate transmit queue 
      congestion. 
      
      For ATM IP cards, if the connectionPointType is displayed as 
      connectionEndPoint, this attribute has the value sourceDest. In this 
      mode, the ABR Source and Destination behavior is in effect at this 
      connection. This attribute is also sourceDest in the case where the 
      next hop connection is specified as nonAbrInterworking. The next 
      hop connection is the Vcc or Vpc identified by the nextHop attribute 
      of the Nrp or Rp component. 
      
      If the connectionPointType is not connectionEndPoint, the value of 
      this attribute depends upon the abrConnectionType provisioning 
      and the card type to which the traffic is forwarded on the backplane. 
      The default abrConnectionType is provisioned at the CA Abr 
      abrConnectionType attribute, and may be overridden for a 
      provisioned connection in the Vcd Tm abrConnectionType or Vpd 
      Tm abrConnectionType attribute. If the CA Abr abrConnectionType 
      attribute is virtualSourceDest at either one of the two connection 
      points, and if both the connection points are defined on ATM IP 
      cards, virtual source and destination behavior is applied to the 
      connection. In this instance, the attribute displays the value 
      virtualSourceDest.
      
      This attribute has the value erSwitch if ABR explicit rate 
      functionality is in effect at this connection. In this mode, the switch 
      may modify the Explicit Rate (ER) field of backward Resource 
      Management (RM) cells to indicate the status of congestion at this 
      connection point.
      
      This attribute has the value nonAbrInterworking in the case where 
      this connection point is functioning as an SPVC origin for an ABR 
      connection where the link side of this connection is configured as a 
      non-ABR ATM service category. This means that there are no RM 
      cells on the link side of this connection, and that the next hop 
      connection point is performing as an ABR sourceDest."
::= { atmIfVptVccTmOperEntry 110 }

atmIfVptVccTmTxTdpTable OBJECT-TYPE
   SYNTAX     SEQUENCE OF AtmIfVptVccTmTxTdpEntry
   ACCESS     not-accessible
   STATUS     mandatory
   DESCRIPTION
     "This attribute is a vector of five transmit traffic parameters whose 
      mapping is defined by the txTrafficDescType attribute. 
      
      The values of peak cell rate (PCR), sustained cell rate (SCR), 
      Minimum Cell Rate (MCR), actual cell rate (ACR), explicit rate 
      (ER), equivalent cell rate (ECR), and actual shaping rate are 
      expressed in cell/s. Maximum burst size (MBS) is expressed in 
      cells. CDVT is expressed in microseconds. 
      
      When txTrafficDescType is 1 or 2, parameters 1 through 5 are 
      unused.
      
      In this description, PCR is the greater of either the PCR or the 
      requested shaping rate (parameter 1 or parameter 5) specified in the 
      txTrafficDescParm attribute under the Vcd Tm or Vpd Tm 
      component.
      
      When txTrafficDescType is 3, parameter 1 represents the PCR for 
      CLP equal to 0 or 1 traffic; parameters 2 and 3 are unused.
      
      When txTrafficDescType is 4, parameter 1 represents the PCR for 
      CLP equal to 0 and 1 traffic; parameter 2 represents the PCR for 
      CLP equal to 0 traffic with cell discard.
      
      When txTrafficDescType is 5, parameter 1 represents the PCR for 
      CLP equal to 0 and 1 traffic; parameter 2 represents the PCR for 
      CLP equal to 0 traffic with cell tagging.
      
      When txTrafficDescType is 6, parameter 1 represents the PCR for 
      CLP equal to 0 and 1 traffic; parameter 2 represents the SCR for 
      CLP equal to 0 and 1 traffic; parameter 3 represents the MBS for 
      CLP equal to 0 and 1 traffic.
      
      When txTrafficDescType is 7, parameter 1 represents the PCR for 
      CLP equal to 0 and 1 traffic; parameter 2 represents the SCR for 
      CLP equal to 0 traffic with cell discard; parameter 3 represents the 
      MBS for CLP equal to 0 traffic.
      
      When txTrafficDescType is 8, parameter 1 represents the PCR for 
      CLP equal to 0 and 1 traffic; parameter 2 represents the SCR for 
      CLP equal to 0 traffic with cell tagging; parameter 3 represents the 
      MBS for CLP equal to 0 traffic.
      
      When txTrafficDescType is 3, 4, 5, 6, 7, or 8, parameter 4 reflects 
      the actual shaping rate in cell/s for this connection. For CQC-based 
      ATM cards, the set of available shaping rates is based on the 
      number of interfaces doing shaping (attribute 
      perVcQueueInterfaces), and the shapingScalingFactor attribute of 
      the Arc Cqc Override component. A rate of zero (0) indicates that 
      shaping is not performed, or that the interface is down. 
      
      When txTrafficDescType is 9, parameter 1 represents the PCR; 
      parameter 2 represents the Cell Delay Variation Toleration (CDVT); 
      parameter 3 represents the Minimum Cell Rate (MCR); the meaning 
      of parameter 4 depends upon the value of the abrConnectionType 
      attribute. if abrConnectionType is sourceDest or 
      virtualSourceDest, parameter 4 represents the Allowed Cell Rate 
      (ACR); If abrConnectionType is erSwitch, parameter 4 represents 
      the Explicit Rate (ER); and if abrConnectionType is efciSwitch, 
      parameter 4 reflects the actual shaping rate in cell/s for this 
      connection.
      
      When txTrafficDescType is 3, 4, 5, 6, 7, 8, or 9, parameter 5 reflects 
      the equivalent cell rate in cell/s for this connection as determined by 
      the Connection Admission Control (CAC) algorithm. The 
      equivalent cell rate is useful in determining the admission 
      characteristics of this connection."
::= { atmIfVptVccTm 451 }

atmIfVptVccTmTxTdpEntry OBJECT-TYPE
   SYNTAX     AtmIfVptVccTmTxTdpEntry
   ACCESS     not-accessible
   STATUS     mandatory
   DESCRIPTION
     "An entry in the atmIfVptVccTmTxTdpTable."
   INDEX {
      atmIfIndex,
      atmIfVptIndex,
      atmIfVptVccIndex,
      atmIfVptVccTmIndex,
      atmIfVptVccTmTxTdpIndex }
::= { atmIfVptVccTmTxTdpTable 1 }

AtmIfVptVccTmTxTdpEntry ::= SEQUENCE {
   atmIfVptVccTmTxTdpIndex
      Integer32,
   atmIfVptVccTmTxTdpValue
      Unsigned32 }

atmIfVptVccTmTxTdpIndex OBJECT-TYPE
   SYNTAX     Integer32 (1..5)
   ACCESS     not-accessible
   STATUS     mandatory
   DESCRIPTION
     "This variable represents the atmIfVptVccTmTxTdpTable
      specific index for the atmIfVptVccTmTxTdpTable."
::= { atmIfVptVccTmTxTdpEntry 1 }

atmIfVptVccTmTxTdpValue OBJECT-TYPE
   SYNTAX     Unsigned32 (0..2147483647)
   ACCESS     read-only
   STATUS     mandatory
   DESCRIPTION
     "This variable represents an individual value for the
      atmIfVptVccTmTxTdpTable."
::= { atmIfVptVccTmTxTdpEntry 2 }

atmIfVptVccTmTxQThreshTable OBJECT-TYPE
   SYNTAX     SEQUENCE OF AtmIfVptVccTmTxQThreshEntry
   ACCESS     not-accessible
   STATUS     mandatory
   DESCRIPTION
     "This attribute indicates the queue limit and the discard thresholds 
      for the transmit queue of this connection. 
      
      If this connection has unshapedTransmitQueueing attribute 
      displayed as common, this attribute displays the thresholds of the 
      common queue. If this connection has unshapedTransmitQueueing 
      attribute displayed as perVc or as notApplicable, this attribute 
      displays the thresholds of the per-VC queue.
      
      The first element indicates the queue limit. 
      
      The second element is the threshold that marks the transition from 
      congestion state 1 to congestion state 0. This is the threshold at 
      which traffic with discard priority (DP) = 1 is discarded. This 
      threshold is set at approximately 90 percent of the first parameter, 
      the operational queue limit.
      
      The third element is the threshold that marks the transition from 
      congestion state 2 to congestion state 1. This is the threshold at 
      which traffic with DP = 2 is discarded. This threshold is set at 
      approximately 75 percent of the first parameter, the operational 
      queue limit.
      
      The fourth element is the threshold that marks the transition from 
      congestion state 3 to congestion state 2. This is the threshold at 
      which traffic with DP = 3 is discarded. This threshold is set at 
      approximately 35 percent of the first parameter, the operational 
      queue limit.
      
      This attribute does not apply to basic Vpts."
::= { atmIfVptVccTm 452 }

atmIfVptVccTmTxQThreshEntry OBJECT-TYPE
   SYNTAX     AtmIfVptVccTmTxQThreshEntry
   ACCESS     not-accessible
   STATUS     mandatory
   DESCRIPTION
     "An entry in the atmIfVptVccTmTxQThreshTable."
   INDEX {
      atmIfIndex,
      atmIfVptIndex,
      atmIfVptVccIndex,
      atmIfVptVccTmIndex,
      atmIfVptVccTmTxQThreshIndex }
::= { atmIfVptVccTmTxQThreshTable 1 }

AtmIfVptVccTmTxQThreshEntry ::= SEQUENCE {
   atmIfVptVccTmTxQThreshIndex
      Integer32,
   atmIfVptVccTmTxQThreshValue
      Unsigned32 }

atmIfVptVccTmTxQThreshIndex OBJECT-TYPE
   SYNTAX     Integer32 (0..3)
   ACCESS     not-accessible
   STATUS     mandatory
   DESCRIPTION
     "This variable represents the atmIfVptVccTmTxQThreshTable
      specific index for the atmIfVptVccTmTxQThreshTable."
::= { atmIfVptVccTmTxQThreshEntry 1 }

atmIfVptVccTmTxQThreshValue OBJECT-TYPE
   SYNTAX     Unsigned32 (0..30720)
   ACCESS     read-only
   STATUS     mandatory
   DESCRIPTION
     "This variable represents an individual value for the
      atmIfVptVccTmTxQThreshTable."
::= { atmIfVptVccTmTxQThreshEntry 2 }

atmIfVptVccTmRxTdpTable OBJECT-TYPE
   SYNTAX     SEQUENCE OF AtmIfVptVccTmRxTdpEntry
   ACCESS     not-accessible
   STATUS     mandatory
   DESCRIPTION
     "This attribute is a vector of four traffic parameters whose meanings 
      are defined by the rxTrafficDescType attribute. The values of peak 
      cell rate (PCR), sustained cell rate (SCR), minimum cell rate 
      (MCR) are expressed in cell/s. Maximum burst size (MBS) is 
      expressed in cells. Cell delay variation tolerance (CDVT) is 
      expressed in microseconds.
      
      When rxTrafficDescType is 1 or 2, none of the parameters are used.
      
      When rxTrafficDescType is 3, parameter 1 represents the PCR for 
      CLP equal to 0 and 1 traffic; parameter 4 represents the CDVT.
      
      When rxTrafficDescType is 4, parameter 1 represents the PCR for 
      CLP equal to 0 and 1 traffic; parameter 2 represents the PCR for 
      CLP equal to 0 traffic with cell discard; parameter 4 represents the 
      CDVT.
      
      When rxTrafficDescType is 5, parameter 1 represents the PCR for 
      CLP equal to 0 and 1 traffic; parameter 2 represents the PCR for 
      CLP equal to 0 traffic with cell tagging; parameter 4 represents the 
      CDVT.
      
      When rxTrafficDescType is 6, parameter 1 represents the PCR for 
      CLP equal to 0 and 1 traffic; parameter 2 represents the SCR for 
      CLP equal to 0 and 1 traffic; parameter 3 represents the MBS for 
      CLP equal to 0 and 1 traffic; parameter 4 represents the CDVT. 
      
      When rxTrafficDescType is 7, parameter 1 represents the PCR for 
      CLP equal to 0 and 1 traffic; parameter 2 represents the SCR for 
      CLP equal to 0 traffic with cell discard; parameter 3 represents the 
      MBS for CLP equal to 0 traffic; parameter 4 represents the CDVT.
      
      When rxTrafficDescType is 8, parameter 1 represents the PCR for 
      CLP equal to 0 and 1 traffic; parameter 2 represents the SCR for 
      CLP equal to 0 traffic with cell tagging; parameter 3 represents the 
      MBS for CLP equal to 0 traffic; parameter 4 represents the CDVT. 
      
      When rxTrafficDescType is 9, parameter 1 represents the PCR; 
      parameter 2 represents CDVT; parameter 3 represents the MCR; 
      parameter 4 indicates the instantaneous rate at which dynamic 
      generic cell rate algorithm (DGCRA) is in effect. 
      
      If upc is disabled for this connection, the values of PCR, SCR, 
      MBS and CDVT are the provisioned parameters.
      
      If upc is enabled, the values of PCR, SCR, MBS, and CDVT are 
      exactly the values used by the usage parameter control hardware in 
      policing the arriving traffic. These may vary slightly from the 
      provisioned values due to granularity of the hardware. In the case 
      where the PCR is equal to the SCR, the effective MBS is zero."
::= { atmIfVptVccTm 453 }

atmIfVptVccTmRxTdpEntry OBJECT-TYPE
   SYNTAX     AtmIfVptVccTmRxTdpEntry
   ACCESS     not-accessible
   STATUS     mandatory
   DESCRIPTION
     "An entry in the atmIfVptVccTmRxTdpTable."
   INDEX {
      atmIfIndex,
      atmIfVptIndex,
      atmIfVptVccIndex,
      atmIfVptVccTmIndex,
      atmIfVptVccTmRxTdpIndex }
::= { atmIfVptVccTmRxTdpTable 1 }

AtmIfVptVccTmRxTdpEntry ::= SEQUENCE {
   atmIfVptVccTmRxTdpIndex
      Integer32,
   atmIfVptVccTmRxTdpValue
      Unsigned32 }

atmIfVptVccTmRxTdpIndex OBJECT-TYPE
   SYNTAX     Integer32 (1..4)
   ACCESS     not-accessible
   STATUS     mandatory
   DESCRIPTION
     "This variable represents the atmIfVptVccTmRxTdpTable
      specific index for the atmIfVptVccTmRxTdpTable."
::= { atmIfVptVccTmRxTdpEntry 1 }

atmIfVptVccTmRxTdpValue OBJECT-TYPE
   SYNTAX     Unsigned32 (0..2147483647)
   ACCESS     read-only
   STATUS     mandatory
   DESCRIPTION
     "This variable represents an individual value for the
      atmIfVptVccTmRxTdpTable."
::= { atmIfVptVccTmRxTdpEntry 2 }

atmIfVptVccTmTqpTable OBJECT-TYPE
   SYNTAX     SEQUENCE OF AtmIfVptVccTmTqpEntry
   ACCESS     not-accessible
   STATUS     mandatory
   DESCRIPTION
     "This attribute is a vector of three elements that indicate the quality 
      of service parameters for the forward direction for this connection. 
      This attribute is used for SPVC and SVC connections on a PNNI 
      interface.
      
      The cdv element indicates the acceptable peak-to-peak Cell Delay 
      Variation (CDV) of real-time connections (CBR and rt-VBR). 
      
      The ctd element indicates the acceptable maximum Cell Transfer 
      Delay (maxCtd) of real-time connections (CBR and rt-VBR). 
      
      The clr element indicates the acceptable Cell Loss Ratio (CLR) of 
      CBR, rt-VBR, and nrt-VBR connections."
::= { atmIfVptVccTm 454 }

atmIfVptVccTmTqpEntry OBJECT-TYPE
   SYNTAX     AtmIfVptVccTmTqpEntry
   ACCESS     not-accessible
   STATUS     mandatory
   DESCRIPTION
     "An entry in the atmIfVptVccTmTqpTable."
   INDEX {
      atmIfIndex,
      atmIfVptIndex,
      atmIfVptVccIndex,
      atmIfVptVccTmIndex,
      atmIfVptVccTmTqpIndex }
::= { atmIfVptVccTmTqpTable 1 }

AtmIfVptVccTmTqpEntry ::= SEQUENCE {
   atmIfVptVccTmTqpIndex
      INTEGER,
   atmIfVptVccTmTqpValue
      Unsigned32 }

atmIfVptVccTmTqpIndex OBJECT-TYPE
   SYNTAX     INTEGER  {
                 cdv(0),
                 ctd(1),
                 clr(2) }
   ACCESS     not-accessible
   STATUS     mandatory
   DESCRIPTION
     "This variable represents the atmIfVptVccTmTqpTable
      specific index for the atmIfVptVccTmTqpTable."
::= { atmIfVptVccTmTqpEntry 1 }

atmIfVptVccTmTqpValue OBJECT-TYPE
   SYNTAX     Unsigned32 (0..2147483647)
   ACCESS     read-only
   STATUS     mandatory
   DESCRIPTION
     "This variable represents an individual value for the
      atmIfVptVccTmTqpTable."
::= { atmIfVptVccTmTqpEntry 2 }

atmIfVptVccTmRqpTable OBJECT-TYPE
   SYNTAX     SEQUENCE OF AtmIfVptVccTmRqpEntry
   ACCESS     not-accessible
   STATUS     mandatory
   DESCRIPTION
     "This attribute is a vector of three elements that indicate the quality 
      of service parameters for the backward direction for this 
      connection. This attribute is used for SPVC and SVC connections 
      on a PNNI interface.
      
      The cdv element indicates the acceptable peak-to-peak Cell Delay 
      Variation (CDV) of real-time connections (CBR and rt-VBR). 
      
      The ctd element indicates the acceptable maximum Cell Transfer 
      Delay (maxCtd) of real-time connections (CBR and rt-VBR). 
      
      The clr element indicates the acceptable Cell Loss Ratio (CLR) of 
      CBR, rt-VBR, and nrt-VBR connections."
::= { atmIfVptVccTm 455 }

atmIfVptVccTmRqpEntry OBJECT-TYPE
   SYNTAX     AtmIfVptVccTmRqpEntry
   ACCESS     not-accessible
   STATUS     mandatory
   DESCRIPTION
     "An entry in the atmIfVptVccTmRqpTable."
   INDEX {
      atmIfIndex,
      atmIfVptIndex,
      atmIfVptVccIndex,
      atmIfVptVccTmIndex,
      atmIfVptVccTmRqpIndex }
::= { atmIfVptVccTmRqpTable 1 }

AtmIfVptVccTmRqpEntry ::= SEQUENCE {
   atmIfVptVccTmRqpIndex
      INTEGER,
   atmIfVptVccTmRqpValue
      Unsigned32 }

atmIfVptVccTmRqpIndex OBJECT-TYPE
   SYNTAX     INTEGER  {
                 cdv(0),
                 ctd(1),
                 clr(2) }
   ACCESS     not-accessible
   STATUS     mandatory
   DESCRIPTION
     "This variable represents the atmIfVptVccTmRqpTable
      specific index for the atmIfVptVccTmRqpTable."
::= { atmIfVptVccTmRqpEntry 1 }

atmIfVptVccTmRqpValue OBJECT-TYPE
   SYNTAX     Unsigned32 (0..2147483647)
   ACCESS     read-only
   STATUS     mandatory
   DESCRIPTION
     "This variable represents an individual value for the
      atmIfVptVccTmRqpTable."
::= { atmIfVptVccTmRqpEntry 2 }


-- AtmIf/n Vpc/vpi Tm AvailableBitRate, 
-- AtmIf/n Vcc/vpi.vci Tm AvailableBitRate,
-- AtmIf/n Vpt/vpi Tm AvailableBitRate,
-- AtmIf/n Vpt/vpi Vcc/vci Tm AvailableBitRate
-- This component contains ABR-related operational attributes of a 
-- connection. It is dynamically created for connections where the 
-- atmServiceCategory is availableBitRate, and where 
-- abrConnectionType is sourceDest or virtualSourceDest.

atmIfVptVccTmAbr OBJECT IDENTIFIER ::= { atmIfVptVccTm 2 }



atmIfVptVccTmAbrRowStatusTable OBJECT-TYPE
   SYNTAX     SEQUENCE OF AtmIfVptVccTmAbrRowStatusEntry
   ACCESS     not-accessible
   STATUS     mandatory
   DESCRIPTION
     "This entry controls the addition and deletion of 
      atmIfVptVccTmAbr components."
::= { atmIfVptVccTmAbr 1 }

atmIfVptVccTmAbrRowStatusEntry OBJECT-TYPE
   SYNTAX     AtmIfVptVccTmAbrRowStatusEntry
   ACCESS     not-accessible
   STATUS     mandatory
   DESCRIPTION
     "A single entry in the table represents a single 
      atmIfVptVccTmAbr component."
   INDEX {
      atmIfIndex,
      atmIfVptIndex,
      atmIfVptVccIndex,
      atmIfVptVccTmIndex,
      atmIfVptVccTmAbrIndex }
::= { atmIfVptVccTmAbrRowStatusTable 1 }

AtmIfVptVccTmAbrRowStatusEntry ::= SEQUENCE {
   atmIfVptVccTmAbrRowStatus
      RowStatus,
   atmIfVptVccTmAbrComponentName
      DisplayString,
   atmIfVptVccTmAbrStorageType
      StorageType,
   atmIfVptVccTmAbrIndex
      NonReplicated }

atmIfVptVccTmAbrRowStatus OBJECT-TYPE
   SYNTAX     RowStatus 
   ACCESS     read-only
   STATUS     mandatory
   DESCRIPTION
     "This variable is used as the basis for SNMP naming of
      atmIfVptVccTmAbr components.
      These components cannot be added nor deleted."
::= { atmIfVptVccTmAbrRowStatusEntry 1 }

atmIfVptVccTmAbrComponentName OBJECT-TYPE
   SYNTAX     DisplayString 
   ACCESS     read-only
   STATUS     mandatory
   DESCRIPTION
     "This variable provides the component's string name for
      use with the ASCII Console Interface"
::= { atmIfVptVccTmAbrRowStatusEntry 2 }

atmIfVptVccTmAbrStorageType OBJECT-TYPE
   SYNTAX     StorageType 
   ACCESS     read-only
   STATUS     mandatory
   DESCRIPTION
     "This variable represents the storage type value for the
      atmIfVptVccTmAbr tables."
::= { atmIfVptVccTmAbrRowStatusEntry 4 }

atmIfVptVccTmAbrIndex OBJECT-TYPE
   SYNTAX     NonReplicated 
   ACCESS     not-accessible
   STATUS     mandatory
   DESCRIPTION
     "This variable represents the index for the atmIfVptVccTmAbr tables."
::= { atmIfVptVccTmAbrRowStatusEntry 10 }

atmIfVptVccTmAbrOperTable OBJECT-TYPE
   SYNTAX     SEQUENCE OF AtmIfVptVccTmAbrOperEntry
   ACCESS     not-accessible
   STATUS     mandatory
   DESCRIPTION
     "This group contains operational attributes for connections using 
      ABR service category."
::= { atmIfVptVccTmAbr 110 }

atmIfVptVccTmAbrOperEntry OBJECT-TYPE
   SYNTAX     AtmIfVptVccTmAbrOperEntry
   ACCESS     not-accessible
   STATUS     mandatory
   DESCRIPTION
     "An entry in the atmIfVptVccTmAbrOperTable."
   INDEX {
      atmIfIndex,
      atmIfVptIndex,
      atmIfVptVccIndex,
      atmIfVptVccTmIndex,
      atmIfVptVccTmAbrIndex }
::= { atmIfVptVccTmAbrOperTable 1 }

AtmIfVptVccTmAbrOperEntry ::= SEQUENCE {
   atmIfVptVccTmAbrInitialCellRate
      Unsigned32,
   atmIfVptVccTmAbrTransientBufferExposure
      Unsigned32,
   atmIfVptVccTmAbrFixedRoundTripTime
      Unsigned32,
   atmIfVptVccTmAbrRateDecreaseFactor
      Unsigned32,
   atmIfVptVccTmAbrRateIncreaseFactor
      Unsigned32,
   atmIfVptVccTmAbrMaxCellPerRmCell
      Unsigned32,
   atmIfVptVccTmAbrMaxTimeBetweenRmCell
      Unsigned32,
   atmIfVptVccTmAbrCutoffDecreaseFactor
      Unsigned32,
   atmIfVptVccTmAbrAcrDecreaseTimeFactor
      Unsigned32,
   atmIfVptVccTmAbrForwardRmCellLimit
      Unsigned32,
   atmIfVptVccTmAbrTxRateChangeInfo
      INTEGER,
   atmIfVptVccTmAbrAcrRateChangeInfo
      INTEGER,
   atmIfVptVccTmAbrTxFwdRmCells
      Unsigned32,
   atmIfVptVccTmAbrRxEfci
      INTEGER,
   atmIfVptVccTmAbrBrmRateChangeInfo
      OCTET STRING,
   atmIfVptVccTmAbrBrmExplicitRate
      Unsigned32 }

atmIfVptVccTmAbrInitialCellRate OBJECT-TYPE
   SYNTAX     Unsigned32 (0..16777215)
   ACCESS     read-only
   STATUS     mandatory
   DESCRIPTION
     "This attribute is applicable and is displayed only for connections for 
      which the operational Tm abrConnectionType is displayed as 
      sourceDest or virtualSourceDest. 
      
      This attribute indicates the Initial Cell Rate (ICR) parameter for this 
      connection. ICR is the rate at which a source should send initially 
      and after an idle period.
      
      For nailed-up connections, this attribute is determined by the 
      provisioned value of the initialCellRate attribute. For signalled 
      connections, it is indicated in the ABR Setup Parameters 
      Information Element.
      
      The ICR for a connection is a value between the MCR and the PCR. 
      Furthermore, ICR has an upper bound determined by the 
      transientBufferExposure divided by fixedRoundTripTime."
::= { atmIfVptVccTmAbrOperEntry 10 }

atmIfVptVccTmAbrTransientBufferExposure OBJECT-TYPE
   SYNTAX     Unsigned32 (0..16777215)
   ACCESS     read-only
   STATUS     mandatory
   DESCRIPTION
     "This attribute is applicable and is displayed only for connections for 
      which the operational Tm abrConnectionType is displayed as 
      sourceDest or virtualSourceDest. 
      
      This attribute indicates the Transient Buffer Exposure (TBE) for 
      this connection. TBE is the negotiated number of cells that the 
      network would like to limit the resource to send during start-up 
      periods, before the first Resource Management (RM) cell returns.
      
      For nailed-up connections, this attribute is determined by the 
      provisioned value of the transientBufferExposure attribute. For 
      signalled connections, it is indicated in the ABR Setup Parameters 
      Information Element."
::= { atmIfVptVccTmAbrOperEntry 11 }

atmIfVptVccTmAbrFixedRoundTripTime OBJECT-TYPE
   SYNTAX     Unsigned32 (0..16700000)
   ACCESS     read-only
   STATUS     mandatory
   DESCRIPTION
     "This attribute is applicable and is displayed only for connections for 
      which the operational Tm abrConnectionType is displayed as 
      sourceDest or virtualSourceDest. 
      
      This attribute indicates the Fixed Round-Trip Time (FRTT) 
      parameter for this connection. FRTT is the sum of the fixed and 
      propagation delays from the source to a destination and back.
      
      For nailed-up connections, this attribute is determined by the 
      provisioned value of the fixedRoundTripTime attribute. For 
      signalled connections, it is indicated in the ABR Setup Parameters 
      Information Element."
::= { atmIfVptVccTmAbrOperEntry 12 }

atmIfVptVccTmAbrRateDecreaseFactor OBJECT-TYPE
   SYNTAX     Unsigned32 (0..15)
   ACCESS     read-only
   STATUS     mandatory
   DESCRIPTION
     "This attribute is applicable and is displayed only for connections for 
      which the operational Tm abrConnectionType is displayed as 
      sourceDest or virtualSourceDest. 
      
      This attribute indicates the Rate Decrease Factor (RDF) for this 
      connection. The RDF value is computed by using the operational 
      value of this attribute, n, as 2 to the inverse power n. For example, if 
      the value of this attribute is 8, RDF is 2E-8 = 1/256.
      
      RDF controls the amount by which the cell transmission rate may 
      decrease upon receipt of a backward Resource Management (RM) 
      cell. For example, if a backward RM cell is received with the 
      Congestion Indication (CI) field set to 1, the Allowed Cell Rate 
      (ACR) value would be reduced by the amount (RDF*ACR). The 
      ACR is not allowed to fall below the Minimum Cell Rate (MCR), in 
      which case the ACR is set to MCR.
      
      For nailed-up connections, this attribute is determined by the 
      provisioned value of the rateDecreaseFactor attribute. For signalled 
      connections, it is indicated in the ABR Setup Parameters 
      Information Element."
::= { atmIfVptVccTmAbrOperEntry 13 }

atmIfVptVccTmAbrRateIncreaseFactor OBJECT-TYPE
   SYNTAX     Unsigned32 (0..15)
   ACCESS     read-only
   STATUS     mandatory
   DESCRIPTION
     "This attribute is applicable and is displayed only for connections for 
      which the operational Tm abrConnectionType is displayed as 
      sourceDest or virtualSourceDest. 
      
      This attribute indicates the Rate Increase Factor (RIF) for this 
      connection. The RIF value is computed by using the operational 
      value of this attribute, n, as 2 to the inverse power n. For example, if 
      the value of this attribute is 6, RIF is 2E-6 = 1/64.
      
      RIF controls the amount by which the cell transmission rate may 
      increase upon receipt of a backward Resource Management (RM) 
      cell. For example, if a backward RM cell is received with the 
      Congestion Indication (CI) and the No Increase (NI) fields both set 
      to 0, the Allowed Cell Rate (ACR) value would be increased by the 
      amount (RIF*ACR). The ACR is not allowed to exceed the Peak 
      Cell Rate (PCR), in which case the ACR is set to PCR.
      
      For nailed-up connections, this attribute is determined by the 
      provisioned value of the rateIncreaseFactor attribute. For signalled 
      connections, it is indicated in the ABR Setup Parameters 
      Information Element."
::= { atmIfVptVccTmAbrOperEntry 14 }

atmIfVptVccTmAbrMaxCellPerRmCell OBJECT-TYPE
   SYNTAX     Unsigned32 (2 | 4 | 8 | 16 | 32 | 64 | 128 | 256)
   ACCESS     read-only
   STATUS     mandatory
   DESCRIPTION
     "This attribute is applicable and is displayed only for connections for 
      which the operational Tm abrConnectionType is displayed as 
      sourceDest or virtualSourceDest. 
      
      This attribute indicates the maximum number of cells an ABR 
      source may transmit for each forward Resource Management (RM) 
      cell. The count of the cells transmitted includes data cells, OAM 
      cells, backward RM cells, and the forward RM cell.
      
      For nailed-up connections, this attribute is determined by the 
      provisioned value of the maxCellsPerRmCell attribute. For 
      signalled connections, it is indicated in the ABR Additional 
      Parameters Information Element."
::= { atmIfVptVccTmAbrOperEntry 15 }

atmIfVptVccTmAbrMaxTimeBetweenRmCell OBJECT-TYPE
   SYNTAX     Unsigned32 (781 | 1563 | 3125 | 6250 | 12500 | 25000 | 50000 | 100000)
   ACCESS     read-only
   STATUS     mandatory
   DESCRIPTION
     "This attribute is applicable and is displayed only for connections for 
      which the operational Tm abrConnectionType is displayed as 
      sourceDest or virtualSourceDest. 
      
      This attribute indicates the TRM parameter for this connection.
      
      TRM provides an upper bound on the time interval between forward 
      Resource Management (RM) cells for an ABR source. Since the last 
      forward RM cell was sent, if at least TRM time has elapsed since 
      and at least 2 other cells have been sent, the next cell to be 
      transmitted would be a forward RM cell.
      
      For nailed-up connections, this attribute is determined by the 
      provisioned value of the maxTimeBetweenRmCell attribute. For 
      signalled connections, it is indicated in the ABR Additional 
      Parameters Information Element."
::= { atmIfVptVccTmAbrOperEntry 16 }

atmIfVptVccTmAbrCutoffDecreaseFactor OBJECT-TYPE
   SYNTAX     Unsigned32 (0 | 1 | 2 | 4 | 8 | 16 | 32 | 64)
   ACCESS     read-only
   STATUS     mandatory
   DESCRIPTION
     "This attribute is applicable and is displayed only for connections for 
      which the operational Tm abrConnectionType is displayed as 
      sourceDest or virtualSourceDest. 
      
      This attribute indicates the Cutoff Decrease Factor (CDF) parameter 
      for this connection. When the value of this attribute is non-zero, 
      CDF is computed as the inverse of the value. For example, if the 
      value is 32, the value of CDF is 1/32. When the value of this 
      attribute is 0, CDF is also zero.
      
      CDF controls the decrease in the Allowed Cell Rate (ACR) 
      associated with the forwardRmCellLimit attribute, the limit of the 
      number of forward Resource Management (RM) cells which may 
      be sent in the absence of received backward RM cells. When this 
      limit is crossed, the ACR value would be decreased by the amount 
      (CDF*ACR). The ACR is not allowed to fall below the Minimum 
      Cell Rate (MCR), in which case the ACR is set to MCR.
      
      For nailed-up connections, this attribute is determined by the 
      provisioned value of the cutoffDecreaseFactor attribute. For 
      signalled connections, it is indicated in the ABR Additional 
      Parameters Information Element."
::= { atmIfVptVccTmAbrOperEntry 17 }

atmIfVptVccTmAbrAcrDecreaseTimeFactor OBJECT-TYPE
   SYNTAX     Unsigned32 (0..1023)
   ACCESS     read-only
   STATUS     mandatory
   DESCRIPTION
     "This attribute is applicable and is displayed only for connections for 
      which the operational Tm abrConnectionType is displayed as 
      sourceDest or virtualSourceDest. 
      
      This attribute indicates the Allowed Cell Rate Decrease Time Factor 
      (ADTF) parameter for this connection.
      
      ADTF is the time interval permitted between sending forward 
      Resource Management (RM) cells before the Allowed Cell Rate 
      (ACR) is decreased to initialCellRate. In other words, if the source 
      does not transit a forward RM cell for the period specified by adtf, it 
      reduces its ACR to the value of its initialCellRate.
      
      For nailed-up connections, this attribute is determined by the 
      provisioned value of the acrDecreaseTimeFactor attribute. For 
      signalled connections, it is indicated in the ABR Additional 
      Parameters Information Element."
::= { atmIfVptVccTmAbrOperEntry 18 }

atmIfVptVccTmAbrForwardRmCellLimit OBJECT-TYPE
   SYNTAX     Unsigned32 (1 | 3 | 7 | 15 | 31 | 63 | 127 | 255 | 511 | 1023 | 2047 | 4095)
   ACCESS     read-only
   STATUS     mandatory
   DESCRIPTION
     "This attribute is applicable and is displayed only for connections for 
      which the operational Tm abrConnectionType is displayed as 
      sourceDest or virtualSourceDest. 
      
      This attribute indicates the CRM parameter for this connection.
      
      CRM is the limit of the number of forward Resource Management 
      (RM) cells which may be sent in the absence of received backward 
      RM cells. When this limit is crossed, the Allowed Cell Rate (ACR) 
      value would be decreased by the amount (CDF*ACR), where CDF 
      is determined by the cutoffDecreaseFactor. The ACR is not allowed 
      to fall below the Minimum Cell Rate (MCR), in which case the 
      ACR is set to MCR.
      
      The value of CRM is obtained as transientBufferExposure divided 
      by maxCellsPerRmCell."
::= { atmIfVptVccTmAbrOperEntry 19 }

atmIfVptVccTmAbrTxRateChangeInfo OBJECT-TYPE
   SYNTAX     INTEGER  {
                 congestionIndicated(0),
                 noIncreaseIndicated(1),
                 explicitRateIndicated(2) }
   ACCESS     read-only
   STATUS     obsolete
   DESCRIPTION
     "THIS ATTRIBUTE IS HISTORICAL:This attribute indicates the 
      rate change information put into the last forward Resource 
      Management (RM) cell turned around as a backward-RM cell. For 
      connections configured as an ABR Source or Destination, the 
      turned around backward-RM cell is sent over the interface. For 
      connections configured as an ABR Virtual Source or Virtual 
      Destination, the turned around backward-RM cell is sent over the 
      backplane."
::= { atmIfVptVccTmAbrOperEntry 20 }

atmIfVptVccTmAbrAcrRateChangeInfo OBJECT-TYPE
   SYNTAX     INTEGER  {
                 noChange(0),
                 decreasedByRdf(1),
                 increasedByRif(2),
                 setToExplicitRate(3),
                 notApplicable(15) }
   ACCESS     read-only
   STATUS     mandatory
   DESCRIPTION
     "This attribute is applicable and is displayed only for connections for 
      which the operational Tm abrConnectionType is displayed as 
      sourceDest or virtualSourceDest. 
      
      This attribute indicates the type of change in the Allowed Cell Rate 
      (ACR) as a result of the information in the last backward Resource 
      Management (B-RM) cell received from the interface.
      
      This attribute value is only applicable when the Vcc Tm or Vpc Tm 
      abrConnectionType attribute is sourceDest or VirtualSourceDest. 
      In all other cases, this attribute value is notApplicable.
      
      A value of noChange indicates that the rate did not change as a 
      result of the last backward RM cell received.
      
      A value of decreasedByRdf or increasedByRif indicates that the 
      ACR was increased or decreased by the corresponding factor. This 
      change is as a result of the CI or NI bit setting in the last backward 
      RM cell, or an ADTF timeout.
      
      A value of setToExplicitRate indicates that the ACR was set to the 
      ER value in the last backward RM cell."
::= { atmIfVptVccTmAbrOperEntry 21 }

atmIfVptVccTmAbrTxFwdRmCells OBJECT-TYPE
   SYNTAX     Unsigned32 (0..4095)
   ACCESS     read-only
   STATUS     mandatory
   DESCRIPTION
     "This attribute is applicable and is displayed only for connections for 
      which the operational Tm abrConnectionType is displayed as 
      sourceDest or virtualSourceDest. 
      
      This attribute counts the number of forward Resource Management 
      (RM) cells sent over the interface since the last backward RM-cell 
      was received from the interface. If the value of this attribute is 
      greater than or equal to the value of forwardRmCellLimit, the 
      Allowed Cell Rate (ACR) value would be decreased by the amount 
      (CDF*ACR), where CDF is determined by the 
      cutoffDecreaseFactor.
      
      This counter is reset to zero each time a backward-RM cell is 
      received.
      
      This counter does not wrap to zero if it reaches its maximum value 
      of 4095 in order to indicate that no backward RM cell has been 
      received."
::= { atmIfVptVccTmAbrOperEntry 22 }

atmIfVptVccTmAbrRxEfci OBJECT-TYPE
   SYNTAX     INTEGER  {
                 notIndicated(0),
                 indicated(1) }
   ACCESS     read-only
   STATUS     mandatory
   DESCRIPTION
     "This attribute is applicable and is displayed only for connections for 
      which the operational Tm abrConnectionType is displayed as 
      sourceDest or virtualSourceDest. 
      
      This attribute indicates the value of the Explicit Forward 
      Congestion Indication (EFCI) bit of the last data cell received from 
      the interface.
      
      When a forward Resource Management (RM) cell is turned around 
      as a backward-RM cell, the Congestion Indication (CI) field of the 
      backward-RM cell is set to 1, if the value of this attribute is 
      indicated.
      
      This attribute is set to notIndicated each time a backward-RM cell 
      is transmitted."
::= { atmIfVptVccTmAbrOperEntry 23 }

atmIfVptVccTmAbrBrmRateChangeInfo OBJECT-TYPE
   SYNTAX     OCTET STRING (SIZE (1))
   ACCESS     read-only
   STATUS     mandatory
   DESCRIPTION
     "This attribute is applicable and is displayed only for connections for 
      which the operational Tm abrConnectionType is displayed as 
      sourceDest, virtualSourceDest or explicitRate. 
      
      This attribute indicates the values of key fields which affect the rate 
      change. These fields are from the most recent Backward Resource 
      Management (B-RM) cell on this connection. These fields may have 
      been set by a connection point at some switch prior to the B-RM 
      cell arriving at this connection point. 
      
      A value of ci indicates that the Congestion Indication (CI) field is 
      set in the B-RM cell. A value of ni indicates that the No Increase 
      (NI) field is set in the B-RM cell. A value of er indicates that a rate 
      decrease is indicated by the Explicit Rate in the B-RM cell having a 
      value lower than the Current Cell Rate (CCR) field in the B-RM 
      cell. The actual explicit rate from the B-RM cell is shown in the 
      brmEr attribute of this component.

      Description of bits:
      ci(0)
      ni(1)
      er(2)"
::= { atmIfVptVccTmAbrOperEntry 24 }

atmIfVptVccTmAbrBrmExplicitRate OBJECT-TYPE
   SYNTAX     Unsigned32 (0..16777215)
   ACCESS     read-only
   STATUS     mandatory
   DESCRIPTION
     "This attribute is applicable and is displayed only for connections for 
      which the operational Tm abrConnectionType is displayed as 
      sourceDest, virtualSourceDest or explicitRate. 
      
      This attribute indicates the value of the Explicit Rate field from the 
      most recent Backward Resource Management (B-RM) cell on this 
      connection. This is the rate from the B-RM cell which may be 
      different from the explicit rate (ER) offered at this connection point. 
      Specifically, this attribute may indicate the ER which has been set in 
      the B-RM cell by some connection point before the B-RM cell 
      arrived at this connection point."
::= { atmIfVptVccTmAbrOperEntry 25 }


-- AtmIf/n EmissionPriority/n 
-- This component controls the characteristics of an emission priority 
-- for an AtmIf. This component is optional on ATM IP FPs. It is not 
-- permitted on CQC-based ATM FPs.
-- 
-- On ATM IP FPs, there are eight emission priorities (EP). EP 0 is the 
-- highest priority and EP 7 is the lowest priority. Normally, link 
-- bandwidth is allocated in strict precedence of emission priority. All 
-- traffic at EP 0 is transmitted on the link first. Then, when there is an 
-- unused cell opportunity, a cell from EP 1 is transmitted. When EP 0 
-- and 1 have nothing to send, then EP 2 gets the transmit cell 
-- opportunities. Each emission priority 2 through 7 has a 
-- corresponding Ep component with instance number 2 through 7. 
-- Emission priorities 0 and 1 do not have corresponding Ep 
-- components since there is no configuration which is relevant for 
-- those EPs. 
-- 
-- Traffic is associated with an EP in the following way. Each Vcc or 
-- Vpc has an associated atmServiceCategory. Under the AtmIf 
-- component there is a service category component which provides 
-- default characteristics for that service category. For example, AtmIf/
-- n CA Cbr/0 defines the default characteristics for connections of the 
-- CBR service category. Each service category has an 
-- emissionPriority (ep) attribute, for example AtmIf/n CA Cbr/0 ep. 
-- The value provisioned in that ep attribute maps to the corresponding 
-- EP component. If AtmIf/n CA Cbr/0 ep is specified as 2, CBR is 
-- associated with AtmIf/n Ep/2. 
-- 
-- EP 0 and EP 1 are in the absolute priority range. Traffic in the 
-- absolute priority range always gets first choice for a transmit cell 
-- opportunity. EP 2 through EP 7 are in the guaranteed bandwidth 
-- range. Traffic at EP 3 through EP 7 in the guaranteed bandwidth 
-- range may achieve a priority which is different from the strict 
-- hierarchical priority, if a minimum bandwidth guarantee is 
-- provisioned for an Ep. 

atmIfEp OBJECT IDENTIFIER ::= { atmIf 10 }



atmIfEpRowStatusTable OBJECT-TYPE
   SYNTAX     SEQUENCE OF AtmIfEpRowStatusEntry
   ACCESS     not-accessible
   STATUS     mandatory
   DESCRIPTION
     "This entry controls the addition and deletion of 
      atmIfEp components."
::= { atmIfEp 1 }

atmIfEpRowStatusEntry OBJECT-TYPE
   SYNTAX     AtmIfEpRowStatusEntry
   ACCESS     not-accessible
   STATUS     mandatory
   DESCRIPTION
     "A single entry in the table represents a single 
      atmIfEp component."
   INDEX {
      atmIfIndex,
      atmIfEpIndex }
::= { atmIfEpRowStatusTable 1 }

AtmIfEpRowStatusEntry ::= SEQUENCE {
   atmIfEpRowStatus
      RowStatus,
   atmIfEpComponentName
      DisplayString,
   atmIfEpStorageType
      StorageType,
   atmIfEpIndex
      Integer32 }

atmIfEpRowStatus OBJECT-TYPE
   SYNTAX     RowStatus 
   ACCESS     read-write
   STATUS     mandatory
   DESCRIPTION
     "This variable is used as the basis for SNMP naming of
      atmIfEp components.
      These components can be added and deleted."
::= { atmIfEpRowStatusEntry 1 }

atmIfEpComponentName OBJECT-TYPE
   SYNTAX     DisplayString 
   ACCESS     read-only
   STATUS     mandatory
   DESCRIPTION
     "This variable provides the component's string name for
      use with the ASCII Console Interface"
::= { atmIfEpRowStatusEntry 2 }

atmIfEpStorageType OBJECT-TYPE
   SYNTAX     StorageType 
   ACCESS     read-only
   STATUS     mandatory
   DESCRIPTION
     "This variable represents the storage type value for the
      atmIfEp tables."
::= { atmIfEpRowStatusEntry 4 }

atmIfEpIndex OBJECT-TYPE
   SYNTAX     Integer32 (2..7)
   ACCESS     not-accessible
   STATUS     mandatory
   DESCRIPTION
     "This variable represents the index for the atmIfEp tables."
::= { atmIfEpRowStatusEntry 10 }

atmIfEpProvTable OBJECT-TYPE
   SYNTAX     SEQUENCE OF AtmIfEpProvEntry
   ACCESS     not-accessible
   STATUS     mandatory
   DESCRIPTION
     "This group contains provisioned attributes which specify the 
      behavior of an emission priority for the ATM interface."
::= { atmIfEp 100 }

atmIfEpProvEntry OBJECT-TYPE
   SYNTAX     AtmIfEpProvEntry
   ACCESS     not-accessible
   STATUS     mandatory
   DESCRIPTION
     "An entry in the atmIfEpProvTable."
   INDEX {
      atmIfIndex,
      atmIfEpIndex }
::= { atmIfEpProvTable 1 }

AtmIfEpProvEntry ::= SEQUENCE {
   atmIfEpMinimumBandwidthGuarantee
      Unsigned32 }

atmIfEpMinimumBandwidthGuarantee OBJECT-TYPE
   SYNTAX     Unsigned32 (0 | 1..49)
   ACCESS     read-write
   STATUS     mandatory
   DESCRIPTION
     "This attribute specifies the minimum bandwidth guarantee 
      associated with this EmissionPriority. A minimum bandwidth 
      guarantee is designed to prevent starvation of traffic at this EP by 
      traffic at higher EPs. Minimum bandwidth guarantees only operate 
      for EPs within the guaranteed bandwidth range 2 through 7. 
      
      The minimum bandwidth guarantee specified is a percentage of the 
      bandwidth which remains after all traffic at EP 0 and EP 1 is served. 
      For example, if EP 0 and EP 1 traffic consumes 20% of link 
      bandwidth, the minimum bandwidth guarantee applies to the 
      remaining 80% of the link bandwidth. A minimum bandwidth 
      guarantee of 2% would actually result in this EP getting 2% of 80% 
      (total 1.6%) of the link bandwidth.
      
      The sum of minimumBandwidthGuarantee values for all Eps under 
      an AtmIf must not exceed 100%.
      
      The value priority specifies that this Ep gets the bandwidth 
      guarantee which is applicable based on the hierarchy of emission 
      priorities. In this case, there is no minimum bandwidth guarantee. 
      
      A value between 1 and 49 specifies that from 1% to 49% of the 
      remaining link bandwidth is reserved for traffic at this EP. Given a 
      value n of minimumBandwidthGuarantee, then for n% of transmit 
      cell opportunities in the guaranteed bandwidth range, this EP get 
      first opportunity to send a cell. If this EP uses less than n% of the 
      link bandwidth, the extra opportunities are allocated in priority. Due 
      to scheduling and cell arrival times, traffic at this EP may not 
      necessarily achieve full utilization of its minimum bandwidth 
      guarantee. 
      
      When specifying a value for minimumBandwidthGuarantee, 
      consider the effect on cell delay variation (CDV) of traffic which 
      would normally be of higher priority. For example, if RtVbr service 
      category traffic is assigned to Ep/2 and Ubr traffic is assigned on 
      Ep/7 where Ep/7 has a minimumBandwidthGuarantee of 25%, there 
      can be a large impact on CDV of the RtVbr traffic. Traffic of the 
      Cbr or RtVbr service category which is sensitive to CDV and is of 
      known volume, can be assigned on EP 0 or EP 1 which are 
      independent of the effects of minimum bandwidth guarantee.

      VALUES (

      0 = priority

      )"
   DEFVAL     { 0 }
::= { atmIfEpProvEntry 1 }




-- 
-- Version and Compliance statements
-- 



-- Object-Group Statement:
-- A list of all current accessible leaf objects.

-- OBJECTS { atmIfVccVcdEndToEndLoopback,
--           atmIfCAConnectionPoolUsage,
--           atmIfVptTmUsageParameterControl,
--           atmIfCANrtVbrPool,
--           atmIfVpcStatsRxFrameDiscardClp,
--           atmIfVptVccVcdTmAbrDgcraMinimumDelay,
--           atmIfVpcStatsRxAal5FrameError,
--           atmIfCAAbrRateIncreaseFactor,
--           atmIfVccVcdTmBestEffort,
--           atmIfVpcTmAbrMaxTimeBetweenRmCell,
--           atmIfVccTmAbrRateDecreaseFactor,
--           atmIfVpcTmAbrStorageType,
--           atmIfVptStatsRxAal5FrameAbort,
--           atmIfVptVccNepComponentName,
--           atmIfSegSwitchSideLoopback,
--           atmIfVptVccVcdTmAbrCutoffDecreaseFactor,
--           atmIfVptCAAbrRowStatus,
--           atmIfVccVcdTmRxTrafficDescType,
--           atmIfVptVccTestBytesTx,
--           atmIfCAUbrForceTagging,
--           atmIfVccTmBestEffort,
--           atmIfVptVccTestCustomizedPattern,
--           atmIfControlStatus,
--           atmIfTxCellMemoryThresholdValue,
--           atmIfVptVccVcdTmBqpValue,
--           atmIfVptVccTmAbrAcrDecreaseTimeFactor,
--           atmIfVptVccTxUtilization,
--           atmIfCANrtVbrCdvt,
--           atmIfCAUbrStorageType,
--           atmIfVptVccTestBytesRx,
--           atmIfVptVpdTmTrafficShaping,
--           atmIfVptVccVcdTmAtmServiceCategory,
--           atmIfVpcOperStatus,
--           atmIfVptVpdSegLinkSideLoopback,
--           atmIfVpcStatsTxFrameDiscard,
--           atmIfCARtVbrPerVcQueueLimitReferenceRate,
--           atmIfVptVccStorageType,
--           atmIfCARtVbrTrafficShaping,
--           atmIfVptVpdComponentName,
--           atmIfVccVcdTmStorageType,
--           atmIfRxCellClp,
--           atmIfVptVpdTmAbrComponentName,
--           atmIfCAMaxCaVpcs,
--           atmIfVptVccTmBearerClassBbc,
--           atmIfVptCAPoolAdmConnsValue,
--           atmIfVccLoopRowStatus,
--           atmIfVpcVpdTmAbrDgcraMaximumDelay,
--           atmIfVptVpdTmStorageType,
--           atmIfVccVcdTmAbrMaxTimeBetweenRmCells,
--           atmIfAal5RxAborts,
--           atmIfVptVccTestLoadingFrmLost,
--           atmIfVptVccTestBandwidthElastic,
--           atmIfVptVccTmAbrCutoffDecreaseFactor,
--           atmIfVpcVpdTmFqpValue,
--           atmIfVpcStatsRxFrameDiscard,
--           atmIfCANrtVbrMinPerVcQueueLimit,
--           atmIfCAAbrInitialCellRate,
--           atmIfVptRxOamCellCongestionState,
--           atmIfCAPoolAdmitBwValue,
--           atmIfVptVccSegLinkSideLoopbackState,
--           atmIfVccVcdTmAbrStorageType,
--           atmIfVpcVpdTmAbrDgcraMinimumDelay,
--           atmIfVptCAMaxVccs,
--           atmIfVptVccSegSwitchSideLoopbackState,
--           atmIfVptVccVcdTmTrafficShaping,
--           atmIfConnMapOvComponentName,
--           atmIfCAPermanentVpcs,
--           atmIfVptVccTmAtmServiceCategory,
--           atmIfCAUbrComponentName,
--           atmIfCAPermittedAtmServiceCategories,
--           atmIfProceduralStatus,
--           atmIfVptVccTmAbrForwardRmCellLimit,
--           atmIfVccTmAbrConnectionType,
--           atmIfEpComponentName,
--           atmIfVptCACbrStorageType,
--           atmIfVptVccTestFrmPatternType,
--           atmIfVpcVpdTmBqpValue,
--           atmIfVccNepApplicationName,
--           atmIfVccTmTxTrafficDescType,
--           atmIfVptTmAbrCutoffDecreaseFactor,
--           atmIfVccTmBandwidthElastic,
--           atmIfVpcTmTqpValue,
--           atmIfVccVcdTmTrafficShaping,
--           atmIfVccTestLoadingFrmTx,
--           atmIfVptCARtVbrCellLossRatio,
--           atmIfCAPoolWaitAdmConnsValue,
--           atmIfCACbrEpdOffset,
--           atmIfCARtVbrOpUnshapedTransmitQueueing,
--           atmIfVpcTmAbrFixedRoundTripTime,
--           atmIfVptCAAbrStorageType,
--           atmIfCAUbrMaxVpcs,
--           atmIfCAAbrAcrDecreaseTimeFactor,
--           atmIfCANrtVbrRowStatus,
--           atmIfVccStatsRxAal5FrameError,
--           atmIfVptSegSwitchSideLoopbackState,
--           atmIfVpcTmRowStatus,
--           atmIfVccTmAbrMaxTimeBetweenRmCell,
--           atmIfVptCAPoolProvBwValue,
--           atmIfVpcTmRqpValue,
--           atmIfVccTestElapsedTime,
--           atmIfVccTmAbrStorageType,
--           atmIfNAcctComponentName,
--           atmIfVptTmAtmServiceCategory,
--           atmIfCAAbrRateDecreaseFactor,
--           atmIfVptCACbrPool,
--           atmIfCAAbrEpdOffset,
--           atmIfVptTmAbrForwardRmCellLimit,
--           atmIfVpcOperationalState,
--           atmIfVptCAAbrPool,
--           atmIfVptVccTestLoadingFrmTx,
--           atmIfVptVccVcdComponentName,
--           atmIfVptVccTmAbrTxFwdRmCells,
--           atmIfCAUbrUnshapedTransmitQueueing,
--           atmIfConnMapOvNumVccsForVpiZero,
--           atmIfVpcVpdComponentName,
--           atmIfVccNumLeaves,
--           atmIfVpcTmAbrRowStatus,
--           atmIfCAAbrMinPerVcQueueLimit,
--           atmIfVptVccTestComponentName,
--           atmIfVptCARtVbrMaxCtd,
--           atmIfCANrtVbrUsageParameterControl,
--           atmIfCACbrStorageType,
--           atmIfCANrtVbrTxQueueLimit,
--           atmIfVpcTmUsageParameterControl,
--           atmIfCANrtVbrHoldingPriority,
--           atmIfVptComponentName,
--           atmIfVpcVpdTmTrafficShaping,
--           atmIfVptVpdTmAbrTransientBufferExposure,
--           atmIfVpcTmHoldingPriority,
--           atmIfVccOperStatus,
--           atmIfVccTestOverrideHoldingPriority,
--           atmIfVpcStatsRxAal5FrameAbort,
--           atmIfVccTestFrmSize,
--           atmIfVccStatsTxFrameDiscard,
--           atmIfVptVccTmAbrBrmRateChangeInfo,
--           atmIfVptVccStatsTxCellClp,
--           atmIfVptVccNepStorageType,
--           atmIfVccVcdTmFwdQosClass,
--           atmIfVptVccUsageState,
--           atmIfVpcVpdTmAbrCutoffDecreaseFactor,
--           atmIfVptVccTestVerificationFrmTx,
--           atmIfVptTmAbrTxFwdRmCells,
--           atmIfVptVccTmTxQThreshValue,
--           atmIfVccAdminState,
--           atmIfCACbrMaxCtd,
--           atmIfCACbrForceTagging,
--           atmIfVccVcdTmAbrFixedRoundTripTime,
--           atmIfVccStatsRxFrameDiscard,
--           atmIfVptVccStatsRxCellClp,
--           atmIfVccEndToEndLoopbackState,
--           atmIfVptCAPoolWaitAdmConnsValue,
--           atmIfVptVpdTmClippingBbc,
--           atmIfTxLinkUtilization,
--           atmIfVccVcdTmTxWredThreshold,
--           atmIfVptVccStatsRxUpcViolationOnEnforcer2,
--           atmIfVccTmTxQueueCongestionState,
--           atmIfVptCACbrCdvt,
--           atmIfVpcVpdSegLinkSideLoopback,
--           atmIfVptVccLoopComponentName,
--           atmIfVptVccStatsRxUpcViolationOnEnforcer1,
--           atmIfVptVpdTmTransferCapabilityBbc,
--           atmIfCAPermanentVccs,
--           atmIfVptVccTestUsageState,
--           atmIfVptVccTmAbrBrmExplicitRate,
--           atmIfVccVcdTmBwdQosClass,
--           atmIfVccTmRxTrafficDescType,
--           atmIfVptTmAbrBrmRateChangeInfo,
--           atmIfVptStatsTxCellClp,
--           atmIfCAUbrVptUsage,
--           atmIfVptCAUbrStorageType,
--           atmIfVptVccVcdTmBestEffort,
--           atmIfVccVcdTmAbrRowStatus,
--           atmIfVptUsageState,
--           atmIfConnMapOvFirstNonZeroVpiForVccs,
--           atmIfVptCARtVbrComponentName,
--           atmIfVccVcdTmUsageParameterControl,
--           atmIfVccVcdTmTxQueueLimit,
--           atmIfVccTmTqpValue,
--           atmIfVptVpdTmAbrRowStatus,
--           atmIfVptVccTmBandwidthReduction,
--           atmIfCACbrProvClr,
--           atmIfVptStatsRxCellClp,
--           atmIfCANrtVbrForceTagging,
--           atmIfConnMapNumNonZeroVpisForVccsOper,
--           atmIfVccVcdTmHoldingPriority,
--           atmIfTxCellClp,
--           atmIfVptCARowStatus,
--           atmIfCARtVbrSvcMpHoldingPriority,
--           atmIfVptVpdTmTxPacketWiseDiscard,
--           atmIfVptStatsRxUpcViolationOnEnforcer2,
--           atmIfVccTmAbrFixedRoundTripTime,
--           atmIfCAUbrMaxVccs,
--           atmIfVpcVpdTmAbrMaxTimeBetweenRmCells,
--           atmIfVptVccStatsTxCell,
--           atmIfVptVccVcdTmAbrTransientBufferExposure,
--           atmIfVptVpdTmAbrRateIncreaseFactor,
--           atmIfVccTmRowStatus,
--           atmIfConnMapOvStorageType,
--           atmIfVccTmRqpValue,
--           atmIfVptStatsRxUpcViolationOnEnforcer1,
--           atmIfCANrtVbrEmissionPriority,
--           atmIfVptVccTmHoldingPriority,
--           atmIfVptTmAbrBrmExplicitRate,
--           atmIfCAAbrFrttPortion,
--           atmIfVptCANrtVbrComponentName,
--           atmIfVptTmAbrRateIncreaseFactor,
--           atmIfVptVpdTmTxQueueLimit,
--           atmIfVptVccTroubled,
--           atmIfEpStorageType,
--           atmIfVccOperationalState,
--           atmIfVptCAPoolRequBwValue,
--           atmIfCACbrComponentName,
--           atmIfVptVccCallDirection,
--           atmIfVpcTmAbrCutoffDecreaseFactor,
--           atmIfVptCARtVbrCdv,
--           atmIfVccTmAbrRowStatus,
--           atmIfVptTmBandwidthReduction,
--           atmIfCAUbrPool,
--           atmIfVptVccVcdTmClippingBbc,
--           atmIfVptVccTmAbrAcrRateChangeInfo,
--           atmIfCAAbrMaxCellPerRmCell,
--           atmIfCAMaxAutoSelectedVciForNonZeroVpi,
--           atmIfVccTmUsageParameterControl,
--           atmIfCAAbrComponentName,
--           atmIfVptVccRxOamCellCongestionState,
--           atmIfVpcSegSwitchSideLoopbackState,
--           atmIfVptVpdTmBqpValue,
--           atmIfVptStatsTxCell,
--           atmIfTxCellMemoryCongestionState,
--           atmIfVccTmHoldingPriority,
--           atmIfCACbrEmissionPriority,
--           atmIfVpcTmTrafficShaping,
--           atmIfConnMapNumVccsPerNonZeroVpiOper,
--           atmIfVptStatsTxCellDiscardClp,
--           atmIfCAAbrRowStatus,
--           atmIfVccTestOperationalState,
--           atmIfVptVccAdminState,
--           atmIfVpcVpdEndToEndLoopback,
--           atmIfVptVccTmClippingBbc,
--           atmIfCAMinAutoSelectedVciForNonZeroVpi,
--           atmIfVpcTmAbrForwardRmCellLimit,
--           atmIfOperationalState,
--           atmIfVptStatsRxCell,
--           atmIfCACbrCdv,
--           atmIfVccVcdTmAbrDgcraMaximumDelay,
--           atmIfVptVpdCorrelationTag,
--           atmIfVccVcdTmRowStatus,
--           atmIfTxCell,
--           atmIfVptVpdTmTxTdpValue,
--           atmIfVptVpdTmAbrFarEndInitialCellRate,
--           atmIfVpcVpdStorageType,
--           atmIfVccVcdTmFqpValue,
--           atmIfCACbrUnshapedTransmitQueueing,
--           atmIfVptVccTestStorageType,
--           atmIfVptVpdTmAbrInitialCellRate,
--           atmIfVptVccNepRowStatus,
--           atmIfStandbyStatus,
--           atmIfVptTmAbrAcrRateChangeInfo,
--           atmIfVpcComponentName,
--           atmIfCAAbrEmissionPriority,
--           atmIfVpcVpdTmAbrTransientBufferExposure,
--           atmIfVccVcdTmAbrDgcraMinimumDelay,
--           atmIfVptVccTestAdminState,
--           atmIfRxCell,
--           atmIfVptVpdTmRxTdpValue,
--           atmIfVptVccVcdTmAbrRateIncreaseFactor,
--           atmIfCANrtVbrPerVcQueueLimitReferenceRate,
--           atmIfCANrtVbrTrafficShaping,
--           atmIfVccVcdTmTxTrafficDescType,
--           atmIfVptAdminState,
--           atmIfVptVccVcdTmHoldingPriority,
--           atmIfVccNepComponentName,
--           atmIfVptTmAbrTransientBufferExposure,
--           atmIfVptVccVcdTmBearerClassBbc,
--           atmIfVccVcdTmAbrCutoffDecreaseFactor,
--           atmIfVccTestBandwidthElastic,
--           atmIfCACbrShapeRecoupPolicy,
--           atmIfVccTestBytesTx,
--           atmIfVptVpdTmRxPacketWiseDiscard,
--           atmIfVpcTmAbrTxFwdRmCells,
--           atmIfCANrtVbrStorageType,
--           atmIfVccTestCustomizedPattern,
--           atmIfCARtVbrRowStatus,
--           atmIfCAUbrMinPerVcQueueLimit,
--           atmIfVccVcdTmBqpValue,
--           atmIfVccVcdSegSwitchSideLoopback,
--           atmIfVpcTmStorageType,
--           atmIfVpcVpdTmClippingBbc,
--           atmIfVptVpdTmBwdQosClass,
--           atmIfVptVpdTmAbrFarEndAcrDecreaseTimeFactor,
--           atmIfCAUbrCdvt,
--           atmIfVccTestBytesRx,
--           atmIfVccVcdTmAtmServiceCategory,
--           atmIfVptVccTestFrmTypes,
--           atmIfVptVpdTmAbrAcrDecreaseTimeFactor,
--           atmIfVptVccTestOperationalState,
--           atmIfVptTmClippingBbc,
--           atmIfVpcVpdTmTransferCapabilityBbc,
--           atmIfVptVccLoopStorageType,
--           atmIfVptVccVcdRowStatus,
--           atmIfVptVccVcdStorageType,
--           atmIfVpcTmAbrBrmRateChangeInfo,
--           atmIfVpcStatsTxCellClp,
--           atmIfVptVccStatsRxCellDiscard,
--           atmIfVptVpdTmAbrRateDecreaseFactor,
--           atmIfCAMaxMulticastBranches,
--           atmIfCANrtVbrWeightPolicy,
--           atmIfVpcUsageState,
--           atmIfVptTmTransferCapabilityBbc,
--           atmIfCAPoolAdmConnsValue,
--           atmIfMaxVpiBits,
--           atmIfVptVccVcdCorrelationTag,
--           atmIfVptCARtVbrStorageType,
--           atmIfVptVccVcdTmAbrFarEndInitialCellRate,
--           atmIfVccTmAbrCutoffDecreaseFactor,
--           atmIfVptVpdEndToEndLoopback,
--           atmIfCANrtVbrShapeRecoupPolicy,
--           atmIfNAcctAccountConnectionType,
--           atmIfVccVcdComponentName,
--           atmIfVptCANrtVbrCellLossRatio,
--           atmIfVpcStatsRxCellClp,
--           atmIfVptVccVcdTmAbrInitialCellRate,
--           atmIfRxFrameDiscardClp,
--           atmIfCAUbrRowStatus,
--           atmIfCANrtVbrOpUnshapedTransmitQueueing,
--           atmIfVptTmTxQueueLength,
--           atmIfVpcStatsRxUpcViolationOnEnforcer2,
--           atmIfVptVccTmTxQosClass,
--           atmIfEpRowStatus,
--           atmIfLastAal5RxErrorConnection,
--           atmIfVptVccVcdTmTxPacketWiseDiscard,
--           atmIfVptCAUbrMinimumCellRate,
--           atmIfCARtVbrEpdOffset,
--           atmIfCAMaxVccs,
--           atmIfVccSegSwitchSideLoopbackState,
--           atmIfVptVccVcdTmRxTdpValue,
--           atmIfVptCARtVbrPool,
--           atmIfCACbrPerVcQueueLimitReferenceRate,
--           atmIfVpcLoopComponentName,
--           atmIfVptVccTestTimeRemaining,
--           atmIfVpcStatsRxUpcViolationOnEnforcer1,
--           atmIfVccTmAtmServiceCategory,
--           atmIfNAcctAccountCollection,
--           atmIfNAcctStorageType,
--           atmIfCAStorageType,
--           atmIfVccTmAbrForwardRmCellLimit,
--           atmIfVccVcdTmAbrConnectionType,
--           atmIfVptTmAbrFixedRoundTripTime,
--           atmIfVptVccVcdTmRxPacketWiseDiscard,
--           atmIfVptVccRowStatus,
--           atmIfVccTestFrmPatternType,
--           atmIfVptVpdTmForceTagging,
--           atmIfCAUbrUsageParameterControl,
--           atmIfVptCAUbrVccUsage,
--           atmIfVptVccTmTransferCapabilityBbc,
--           atmIfCAUbrTxQueueLimit,
--           atmIfVpcTmBandwidthReduction,
--           atmIfCAAbrAbrConnectionType,
--           atmIfNAcctRowStatus,
--           atmIfCAUbrHoldingPriority,
--           atmIfVptVccVcdTmAbrFarEndAcrDecreaseTimeFactor,
--           atmIfVptVpdTmTxWredMode,
--           atmIfCAComponentName,
--           atmIfVptCAPoolAvailBwValue,
--           atmIfVptVccVcdTmWeight,
--           atmIfLoopbackMonitoring,
--           atmIfVptTmTxQosClass,
--           atmIfVccCallDirection,
--           atmIfVpcStatsTxCell,
--           atmIfVptVccVcdTmAbrAcrDecreaseTimeFactor,
--           atmIfVptVccTmAbrInitialCellRate,
--           atmIfVccStatsTxCellClp,
--           atmIfVccVcdSegLinkSideLoopback,
--           atmIfCAPoolProvBwValue,
--           atmIfVpcVpdRowStatus,
--           atmIfVptVccStatsRxAal5FrameError,
--           atmIfVptVccTestRowStatus,
--           atmIfVccTmTrafficShaping,
--           atmIfVptVccVcdTmAbrRateDecreaseFactor,
--           atmIfVptVpdLoopbackMonitoring,
--           atmIfTxCellMemoryUsage,
--           atmIfCAMaxAutoSelectedVciForVpiZero,
--           atmIfVptTmRxQosClass,
--           atmIfCAAbrPool,
--           atmIfVpcStatsRxCell,
--           atmIfConnMapOvRowStatus,
--           atmIfVccTmAbrTxFwdRmCells,
--           atmIfVptRowStatus,
--           atmIfVpcVpdTmTxTdpValue,
--           atmIfAal5RxErrors,
--           atmIfVpcVpdTmAbrFarEndInitialCellRate,
--           atmIfVptTmRxTrafficDescType,
--           atmIfFaultHoldOffTime,
--           atmIfConnMapNumVccsForVpiZeroOper,
--           atmIfVptVccTmRxPacketWiseDiscard,
--           atmIfVccTestComponentName,
--           atmIfCARtVbrMaxCtd,
--           atmIfVpcVpdTmAbrInitialCellRate,
--           atmIfCARtVbrForceTagging,
--           atmIfVpcTmAbrAcrRateChangeInfo,
--           atmIfCAMinAutoSelectedVciForVpiZero,
--           atmIfVptTmTxTdpValue,
--           atmIfVptCAStorageType,
--           atmIfVpcStorageType,
--           atmIfVpcRxOamCellCongestionState,
--           atmIfVptCAConnectionPoolUsage,
--           atmIfComponentName,
--           atmIfVptTmBearerClassBbc,
--           atmIfVpcVpdTmRxTdpValue,
--           atmIfVptVpdTmBearerClassBbc,
--           atmIfVptTmAbrInitialCellRate,
--           atmIfCAUbrShapeRecoupPolicy,
--           atmIfVptVccTmWeight,
--           atmIfCACbrProvCdvt,
--           atmIfVpcTmAbrTransientBufferExposure,
--           atmIfVptTmTxPacketWiseDiscard,
--           atmIfVccNepStorageType,
--           atmIfVptTmRxTdpValue,
--           atmIfVptVccTmAbrRateIncreaseFactor,
--           atmIfVptVpdTmComponentName,
--           atmIfVpcVpdTmRxPacketWiseDiscard,
--           atmIfVptVccTmTxTdpValue,
--           atmIfVccUsageState,
--           atmIfVccTestVerificationFrmTx,
--           atmIfVptVccVcdTmForceTagging,
--           atmIfVptVpdTmAbrDgcraMinimumDelay,
--           atmIfVptVccTmTxPacketWiseDiscard,
--           atmIfVptVccLoopRowStatus,
--           atmIfVptTmRxPacketWiseDiscard,
--           atmIfVccStatsRxCellClp,
--           atmIfVpcVpdTmAbrFarEndAcrDecreaseTimeFactor,
--           atmIfCACbrMinPerVcQueueLimit,
--           atmIfVptVccTmTrafficShaping,
--           atmIfCANrtVbrSvcMpHoldingPriority,
--           atmIfVptVccVcdTmTxWredMode,
--           atmIfVpcVpdTmWeight,
--           atmIfVptVpdTmAbrMaxCellPerRmCell,
--           atmIfVccStatsRxUpcViolationOnEnforcer2,
--           atmIfVptVccTmTqpValue,
--           atmIfVccStatsTxFrameDiscardClp,
--           atmIfVpcVpdTmAbrAcrDecreaseTimeFactor,
--           atmIfVccTestVerificationFrmRx,
--           atmIfVpcTmClippingBbc,
--           atmIfCAUbrEmissionPriority,
--           atmIfVptVpdSegSwitchSideLoopback,
--           atmIfVccLoopComponentName,
--           atmIfVccStatsRxUpcViolationOnEnforcer1,
--           atmIfVptVccTmAbrComponentName,
--           atmIfVptTmWeight,
--           atmIfVpcStatsRxCellDiscardClp,
--           atmIfVccTestUsageState,
--           atmIfVccTmAbrBrmExplicitRate,
--           atmIfVptVccTmRxTdpValue,
--           atmIfVpcVpdTmAbrRateDecreaseFactor,
--           atmIfCAPoolAvailableBwValue,
--           atmIfVptVccVcdLoopbackMonitoring,
--           atmIfVpcTmTransferCapabilityBbc,
--           atmIfSegLinkSideLoopback,
--           atmIfVptStatsRxCellDiscardClp,
--           atmIfCAPoolRequBwValue,
--           atmIfUsageState,
--           atmIfTxCellDiscardClp,
--           atmIfCAAbrCdvt,
--           atmIfVptCACbrCellLossRatio,
--           atmIfCARtVbrComponentName,
--           atmIfVptVpdTmUnshapedTransmitQueueing,
--           atmIfVptTmAbrRateDecreaseFactor,
--           atmIfVptVccTestDuration,
--           atmIfVpcVpdTmAbrRateIncreaseFactor,
--           atmIfVccNepRowStatus,
--           atmIfVptVccStatsTxCellDiscard,
--           atmIfVccVcdStorageType,
--           atmIfVccTmBandwidthReduction,
--           atmIfVccStatsRxFrameDiscardClp,
--           atmIfVptVccTmForceTagging,
--           atmIfCARowStatus,
--           atmIfVptVccTmRxQosClass,
--           atmIfRxCellDiscardClp,
--           atmIfVccStatsTxCell,
--           atmIfVccVcdTmAbrTransientBufferExposure,
--           atmIfVptVccStatsRxCellDiscardClp,
--           atmIfVpcLoopStorageType,
--           atmIfLastAal5RxAbortConnection,
--           atmIfVptCATroubledVccs,
--           atmIfVptVccRdiState,
--           atmIfVccTestTimeRemaining,
--           atmIfVccTmBearerClassBbc,
--           atmIfVccTmStorageType,
--           atmIfVpcTmAbrRateIncreaseFactor,
--           atmIfVptVpdTmBestEffort,
--           atmIfVccDistributionType,
--           atmIfVptVccVcdTmComponentName,
--           atmIfVptVccTmAbrRxEfci,
--           atmIfVpcVpdTmAbrComponentName,
--           atmIfVptVccConnectionPointType,
--           atmIfVpcVpdTmTxPacketWiseDiscard,
--           atmIfVccStatsRxCell,
--           atmIfVpcVpdTmForceTagging,
--           atmIfVpcTmBearerClassBbc,
--           atmIfVccTestFrmTypes,
--           atmIfCARtVbrCdv,
--           atmIfVptStatsTxCellDiscard,
--           atmIfVptVccAisState,
--           atmIfVptTmTxQThreshValue,
--           atmIfCACbrUsageParameterControl,
--           atmIfVpcVpdTmTxWredMode,
--           atmIfCARtVbrUnshapedTransmitQueueing,
--           atmIfVccTmAbrAcrRateChangeInfo,
--           atmIfCACbrTxQueueLimit,
--           atmIfVptVccVcdTmAbrMaxCellPerRmCell,
--           atmIfVptVccLocalFailureCause,
--           atmIfVpcTmTxQosClass,
--           atmIfVccStorageType,
--           atmIfVptVccVcdTmAbrComponentName,
--           atmIfCACbrHoldingPriority,
--           atmIfCAUbrPerVcQueueLimitReferenceRate,
--           atmIfVptVpdTmTxTrafficDescType,
--           atmIfCAUbrTrafficShaping,
--           atmIfVptTroubled,
--           atmIfVptVccVcdSegSwitchSideLoopback,
--           atmIfVccVcdTmTransferCapabilityBbc,
--           atmIfVptStatsRxCellDiscard,
--           atmIfCATroubledVpts,
--           atmIfLastDroppedRxCellConnection,
--           atmIfTxCellDiscard,
--           atmIfCAAbrUsageParameterControl,
--           atmIfVptRdiState,
--           atmIfVccTmAbrTransientBufferExposure,
--           atmIfVpcVpdLoopbackMonitoring,
--           atmIfCAAbrTxQueueLimit,
--           atmIfVptVccDistributionType,
--           atmIfVpcTmRxQosClass,
--           atmIfVptTmAbrRxEfci,
--           atmIfCAAbrHoldingPriority,
--           atmIfVpcRowStatus,
--           atmIfVptVpdTmRxTrafficDescType,
--           atmIfCARtVbrShapeRecoupPolicy,
--           atmIfVptCASwitchedVccs,
--           atmIfEndToEndLoopback,
--           atmIfVptVccVcdTmUnshapedTransmitQueueing,
--           atmIfVptVccTestCauseOfTermination,
--           atmIfVptVccTmComponentName,
--           atmIfLastLrcFrameErrorConnection,
--           atmIfRxCellDiscard,
--           atmIfVccTestStorageType,
--           atmIfVptAisState,
--           atmIfConnMapOvNumVccsPerNonZeroVpi,
--           atmIfVptConnectionPointType,
--           atmIfVpcTmTxTdpValue,
--           atmIfVptVccTmTxQueueLength,
--           atmIfVptLocalFailureCause,
--           atmIfCAUbrVpcUsage,
--           atmIfStorageType,
--           atmIfVccTestAdminState,
--           atmIfVpcTmAbrInitialCellRate,
--           atmIfVccTmClippingBbc,
--           atmIfVccVcdTmAbrRateIncreaseFactor,
--           atmIfVptSegLinkSideLoopbackState,
--           atmIfVptVpdTmAbrConnectionType,
--           atmIfVpcTmAbrRxEfci,
--           atmIfVpcTmTxPacketWiseDiscard,
--           atmIfCAUbrWeightPolicy,
--           atmIfAdminState,
--           atmIfVptVccVcdTmTransferCapabilityBbc,
--           atmIfVpcTmRxTdpValue,
--           atmIfVpcVpdTmComponentName,
--           atmIfVptVccRxUtilization,
--           atmIfVccTmTransferCapabilityBbc,
--           atmIfVccTmTxQueueLength,
--           atmIfCAAbrFairnessPolicy,
--           atmIfVptCANrtVbrStorageType,
--           atmIfVptVccTmAbrStorageType,
--           atmIfCAAbrDgcraMaximumDelay,
--           atmIfCAMaxAutoSelectedVpi,
--           atmIfCAAbrMaxTimeBetweenRmCells,
--           atmIfVptTmComponentName,
--           atmIfCAUbrOpUnshapedTransmitQueueing,
--           atmIfVpcTmRxPacketWiseDiscard,
--           atmIfVptTmForceTagging,
--           atmIfDroppedRxCells,
--           atmIfVpcVpdTmAbrMaxCellPerRmCell,
--           atmIfVptVccTmUnshapedTransmitQueueing,
--           atmIfVptCABwPoolValue,
--           atmIfVptCAUbrRowStatus,
--           atmIfVpcStatsTxCellDiscardClp,
--           atmIfCANrtVbrEpdOffset,
--           atmIfVptVpdTmAbrStorageType,
--           atmIfVptCANrtVbrPool,
--           atmIfVptVccVcdTmTxTrafficDescType,
--           atmIfCAAbrDgcraMinimumDelay,
--           atmIfVpcVpdSegSwitchSideLoopback,
--           atmIfCAMinAutoSelectedVpi,
--           atmIfCAUbrVccUsage,
--           atmIfVccLoopStorageType,
--           atmIfVpcTmWeight,
--           atmIfVptTmAbrMaxCellPerRmCell,
--           atmIfVccComponentName,
--           atmIfVccVcdRowStatus,
--           atmIfVpcTmAbrAcrDecreaseTimeFactor,
--           atmIfVptTmAbrComponentName,
--           atmIfLrcFrameErrors,
--           atmIfVptVccEndToEndLoopbackState,
--           atmIfVccTmAbrRateIncreaseFactor,
--           atmIfAlarmStatus,
--           atmIfCAAbrCutoffDecreaseFactor,
--           atmIfVptRxUtilization,
--           atmIfVptVccVcdTmRxTrafficDescType,
--           atmIfVptVccTestElapsedTime,
--           atmIfVccVcdCorrelationTag,
--           atmIfVpcVpdTmUnshapedTransmitQueueing,
--           atmIfVpcTmAbrRateDecreaseFactor,
--           atmIfCARtVbrStorageType,
--           atmIfVccVcdTmAbrFarEndInitialCellRate,
--           atmIfVpcTmAtmServiceCategory,
--           atmIfVpcLoopRowStatus,
--           atmIfVpcVpdTmAtmServiceCategory,
--           atmIfCANrtVbrCellLossRatio,
--           atmIfVccVcdTmAbrInitialCellRate,
--           atmIfTxCellEfci,
--           atmIfVptTmUnshapedTransmitQueueing,
--           atmIfVccTmTxQosClass,
--           atmIfVccTestLoadingFrmLost,
--           atmIfVccVcdTmTxPacketWiseDiscard,
--           atmIfCAUbrMinimumCellRate,
--           atmIfVptVccVcdTmTxTdpValue,
--           atmIfVccVcdTmRxTdpValue,
--           atmIfCARtVbrPool,
--           atmIfVptVccVcdEndToEndLoopback,
--           atmIfVptVccVcdTmAbrConnectionType,
--           atmIfVptVccStatsTxCellDiscardClp,
--           atmIfVptVccTmTxTrafficDescType,
--           atmIfVpcVpdTmBestEffort,
--           atmIfVptEndToEndLoopbackState,
--           atmIfRxCellEfci,
--           atmIfVptVccTmAbrRateDecreaseFactor,
--           atmIfVptVccVcdTmStorageType,
--           atmIfVccTmRxQosClass,
--           atmIfVccVcdTmRxPacketWiseDiscard,
--           atmIfCAMinMulticastBranches,
--           atmIfVccRowStatus,
--           atmIfVccTestUnrecognizableFrmRx,
--           atmIfVptTmBestEffort,
--           atmIfVpcStatsTxCellDiscard,
--           atmIfVpcTmTxQThreshValue,
--           atmIfCASwitchedMulticastBranches,
--           atmIfVccRxOamCellCongestionState,
--           atmIfVpcTmForceTagging,
--           atmIfVccVcdTmAbrFarEndAcrDecreaseTimeFactor,
--           atmIfVccTmTxTdpValue,
--           atmIfUnknownStatus,
--           atmIfVptCAPoolAdmitBwValue,
--           atmIfVccVcdTmWeight,
--           atmIfVpcVpdTmTxTrafficDescType,
--           atmIfVpcTroubled,
--           atmIfVccVcdTmAbrAcrDecreaseTimeFactor,
--           atmIfVccTmAbrInitialCellRate,
--           atmIfVpcStatsRxCellDiscard,
--           atmIfCATroubledVpcs,
--           atmIfCAVirtualLinkUnallocatedBandwidth,
--           atmIfCACbrTrafficShaping,
--           atmIfVpcRdiState,
--           atmIfVccTmTxPacketWiseDiscard,
--           atmIfVccTestRowStatus,
--           atmIfVptTmTxTrafficDescType,
--           atmIfVccTmRxTdpValue,
--           atmIfVpcVpdTmBearerClassBbc,
--           atmIfVccVcdTmAbrRateDecreaseFactor,
--           atmIfVptCAUbrComponentName,
--           atmIfVptVpdVptType,
--           atmIfVptVccStatsRxCell,
--           atmIfVptVpdTmFwdQosClass,
--           atmIfVpcVpdTmRxTrafficDescType,
--           atmIfConnMapStorageType,
--           atmIfRowStatus,
--           atmIfVccVcdTmBearerClassBbc,
--           atmIfVptVccStatsTxFrameDiscardClp,
--           atmIfVptVccTmBandwidthElastic,
--           atmIfVptVccTmStorageType,
--           atmIfVptTmAbrAcrDecreaseTimeFactor,
--           atmIfCAAbrPerVcQueueLimitReferenceRate,
--           atmIfCAUbrSvcMpHoldingPriority,
--           atmIfVpcAisState,
--           atmIfVptVpdRowStatus,
--           atmIfVccTmRxPacketWiseDiscard,
--           atmIfVccConnectionPointType,
--           atmIfVptVpdTmAbrFixedRoundTripTime,
--           atmIfVpcConnectionPointType,
--           atmIfVptStorageType,
--           atmIfVpcTmTxQueueCongestionState,
--           atmIfVpcLocalFailureCause,
--           atmIfInterfaceName,
--           atmIfCARtVbrMinPerVcQueueLimit,
--           atmIfVptVpdTmRowStatus,
--           atmIfVccStatsTxCellDiscardClp,
--           atmIfVccTmAbrComponentName,
--           atmIfVptVpdTmTxWredThreshold,
--           atmIfVptVccStatsRxFrameDiscardClp,
--           atmIfVptCANrtVbrRowStatus,
--           atmIfVpcSegLinkSideLoopbackState,
--           atmIfVpcVpdTmAbrConnectionType,
--           atmIfCARtVbrCdvt,
--           atmIfVptVccTmAbrMaxTimeBetweenRmCell,
--           atmIfVptVccTestLoadingFrmRx,
--           atmIfCACbrProvPool,
--           atmIfVccTmAbrAcrDecreaseTimeFactor,
--           atmIfVptVpdStorageType,
--           atmIfVpcVpdTmStorageType,
--           atmIfAvailabilityStatus,
--           atmIfVptStatsTxFrameDiscard,
--           atmIfVccStatsRxCellDiscardClp,
--           atmIfCACbrWeightPolicy,
--           atmIfVptVccTestUnrecognizableFrmRx,
--           atmIfVptTmAbrConnectionType,
--           atmIfCANrtVbrComponentName,
--           atmIfCASwitchedVpcs,
--           atmIfVccVcdTmForceTagging,
--           atmIfVptCARtVbrRowStatus,
--           atmIfVptStatsTxFrameDiscardClp,
--           atmIfVpcTmComponentName,
--           atmIfVptTmStorageType,
--           atmIfVptVpdTmUsageParameterControl,
--           atmIfVptVccNumLeaves,
--           atmIfVptTmBandwidthElastic,
--           atmIfVptVccTestVerificationFrmRx,
--           atmIfVpcVpdTmTxQueueLimit,
--           atmIfVccVcdTmTxWredMode,
--           atmIfVpcTmTxQueueLength,
--           atmIfVptVpdTmHoldingPriority,
--           atmIfVpcTxUtilization,
--           atmIfVptVccTmAbrMaxCellPerRmCell,
--           atmIfVpcVpdTmAbrStorageType,
--           atmIfVptStatsRxFrameDiscardClp,
--           atmIfTxFrameDiscardClp,
--           atmIfVpcTmAbrMaxCellPerRmCell,
--           atmIfVptVccOperStatus,
--           atmIfCAVirtualLinkAdmittedBandwidth,
--           atmIfRemoteAtmInterfaceLabel,
--           atmIfVptTmAbrMaxTimeBetweenRmCell,
--           atmIfVpcTmAbrComponentName,
--           atmIfVptVccTestOverrideHoldingPriority,
--           atmIfEpMinimumBandwidthGuarantee,
--           atmIfVptTmAbrStorageType,
--           atmIfVptVccStatsTxFrameDiscard,
--           atmIfVptVccNepApplicationName,
--           atmIfCATroubledVccs,
--           atmIfVccVcdLoopbackMonitoring,
--           atmIfVpcRxUtilization,
--           atmIfVptVccVcdTmFwdQosClass,
--           atmIfVpcVpdTmFwdQosClass,
--           atmIfVptVccTmBestEffort,
--           atmIfConnMapOvNumNonZeroVpisForVccs,
--           atmIfVptTmTrafficShaping,
--           atmIfVccTestDuration,
--           atmIfVptTmHoldingPriority,
--           atmIfVptCAPermittedAtmServiceCategories,
--           atmIfVccStatsTxCellDiscard,
--           atmIfVptCACbrMaxCtd,
--           atmIfVccTmTxQThreshValue,
--           atmIfVptVccTmRxTrafficDescType,
--           atmIfCANrtVbrUnshapedTransmitQueueing,
--           atmIfVptVccStatsRxFrameDiscard,
--           atmIfCARtVbrCellLossRatio,
--           atmIfVccTmForceTagging,
--           atmIfVpcTmUnshapedTransmitQueueing,
--           atmIfVccTestVerificationFrmBad,
--           atmIfCARtVbrUsageParameterControl,
--           atmIfVptVccVcdTmRowStatus,
--           atmIfConnMapFirstNonZeroVpiForVccsOper,
--           atmIfVptVccVcdTmTxWredThreshold,
--           atmIfCARtVbrTxQueueLimit,
--           atmIfVptVpdTmWeight,
--           atmIfVptVccVcdSegLinkSideLoopback,
--           atmIfVccTroubled,
--           atmIfVptVccTmTxQueueCongestionState,
--           atmIfNAcctAccountClass,
--           atmIfCARtVbrWeightPolicy,
--           atmIfVptVccVcdTmAbrFixedRoundTripTime,
--           atmIfCARtVbrHoldingPriority,
--           atmIfVccStatsRxCellDiscard,
--           atmIfVptOperStatus,
--           atmIfVptVccVcdTmAbrStorageType,
--           atmIfVptCAPermanentVccs,
--           atmIfVccRdiState,
--           atmIfVpcEndToEndLoopbackState,
--           atmIfVptVccVcdTmBwdQosClass,
--           atmIfVccVcdTmComponentName,
--           atmIfVccTmAbrRxEfci,
--           atmIfVptTxUtilization,
--           atmIfVptVccTestFrmSize,
--           atmIfCAMaxCaVpts,
--           atmIfCAVirtualLinkRequestedBandwidth,
--           atmIfVptVccVcdTmAbrRowStatus,
--           atmIfVpcTmBestEffort,
--           atmIfVptVpdTmAbrDgcraMaximumDelay,
--           atmIfVptVccVcdTmUsageParameterControl,
--           atmIfCustomerIdentifier,
--           atmIfVccAisState,
--           atmIfVptVccVcdTmTxQueueLimit,
--           atmIfVptVpdTmFqpValue,
--           atmIfVptStatsRxFrameDiscard,
--           atmIfTxFrameDiscard,
--           atmIfVccVcdTmAbrMaxCellPerRmCell,
--           atmIfVccLocalFailureCause,
--           atmIfTxCellMemory,
--           atmIfVptVccComponentName,
--           atmIfOamSegmentBoundary,
--           atmIfVccVcdTmAbrComponentName,
--           atmIfConnMapRowStatus,
--           atmIfVptVccTmAbrFixedRoundTripTime,
--           atmIfVptVccTmAbrConnectionType,
--           atmIfVptCAUbrMaxVccs,
--           atmIfVptTmTxQueueCongestionState,
--           atmIfVccSegLinkSideLoopbackState,
--           atmIfVptVccTmRowStatus,
--           atmIfVpcTmAbrBrmExplicitRate,
--           atmIfVptVccTmRqpValue,
--           atmIfVpcTmTxTrafficDescType,
--           atmIfCAPermanentVpts,
--           atmIfVptVccTestVerificationFrmBad,
--           atmIfRxLinkUtilization,
--           atmIfVccTestLoadingFrmRx,
--           atmIfVptCAComponentName,
--           atmIfVptVpdTmAbrCutoffDecreaseFactor,
--           atmIfCAAbrStorageType,
--           atmIfRxFrameDiscard,
--           atmIfVptVccOperationalState,
--           atmIfVptCACbrComponentName,
--           atmIfCASwitchedVccs,
--           atmIfNAcctServiceExchange,
--           atmIfVccVcdTmUnshapedTransmitQueueing,
--           atmIfVccTestCauseOfTermination,
--           atmIfVccTmComponentName,
--           atmIfVpcVpdCorrelationTag,
--           atmIfCABwPoolValue,
--           atmIfVpcVpdTmAbrFixedRoundTripTime,
--           atmIfVpcTmRxTrafficDescType,
--           atmIfCACbrRowStatus,
--           atmIfVptVccTmAbrRowStatus,
--           atmIfVptTmTqpValue,
--           atmIfVptVpdTmAbrMaxTimeBetweenRmCells,
--           atmIfVccStatsRxAal5FrameAbort,
--           atmIfVptCAUbrPool,
--           atmIfCACbrSvcMpHoldingPriority,
--           atmIfVpcVpdTmRowStatus,
--           atmIfVpcVpdTmTxWredThreshold,
--           atmIfVccTxUtilization,
--           atmIfVptVccTmUsageParameterControl,
--           atmIfVptCAAbrComponentName,
--           atmIfVptVpdTmAtmServiceCategory,
--           atmIfCAUbrMaxVpts,
--           atmIfVpcAdminState,
--           atmIfVccTmAbrMaxCellPerRmCell,
--           atmIfVptTmRowStatus,
--           atmIfVptStatsRxAal5FrameError,
--           atmIfVptTmRqpValue,
--           atmIfVptVccStatsRxAal5FrameAbort,
--           atmIfVpcVpdTmBwdQosClass,
--           atmIfCAUbrEpdOffset,
--           atmIfVccTmWeight,
--           atmIfCARtVbrEmissionPriority,
--           atmIfVccRxUtilization,
--           atmIfVpcTmAbrConnectionType,
--           atmIfVptVccTmAbrTransientBufferExposure,
--           atmIfVpcVpdTmAbrRowStatus,
--           atmIfVptOperationalState,
--           atmIfVccTmAbrBrmRateChangeInfo,
--           atmIfVpcStatsTxFrameDiscardClp,
--           atmIfVptCACbrCdv,
--           atmIfVptVccVcdTmAbrDgcraMaximumDelay,
--           atmIfVptCACbrRowStatus,
--           atmIfVccVcdTmClippingBbc,
--           atmIfVpcVpdTmUsageParameterControl,
--           atmIfVptVccVcdTmAbrMaxTimeBetweenRmCells,
--           atmIfVpcTmBandwidthElastic,
--           atmIfVptVccVcdTmFqpValue,
--           atmIfVptTmAbrRowStatus,
--           atmIfVpcVpdTmHoldingPriority,
--           atmIfVccVcdTmTxTdpValue,
--           atmIfConnMapComponentName,
--           atmIfVccTmUnshapedTransmitQueueing }
-- STATUS  mandatory
-- DESCRIPTION
--   "A list of all current accessible leaf objects."

atmCoreGroup OBJECT IDENTIFIER ::= { atmCoreMIB 1 }
atmCoreGroupBE OBJECT IDENTIFIER ::= { atmCoreGroup 5 }
atmCoreGroupBE01 OBJECT IDENTIFIER ::= { atmCoreGroupBE 2 }
atmCoreGroupBE01A OBJECT IDENTIFIER ::= { atmCoreGroupBE01 2 }



-- Agent-Capabilities Statement:

-- PRODUCT-RELEASE "Passport Release 7.0 AtmCore."
-- STATUS          mandatory
-- DESCRIPTION     "AtmCore MIB: MIB Version BE01A,
--                  Software Version BG00S4C."
-- SUPPORTS        Nortel-Magellan-Passport-AtmCoreMIB
--    INCLUDES     { atmCoreGroupBE01A }

atmCoreCapabilities OBJECT IDENTIFIER ::= { atmCoreMIB 3 }
atmCoreCapabilitiesBE OBJECT IDENTIFIER ::= { atmCoreCapabilities 5 }
atmCoreCapabilitiesBE01 OBJECT IDENTIFIER ::= { atmCoreCapabilitiesBE 2 }
atmCoreCapabilitiesBE01A OBJECT IDENTIFIER ::= { atmCoreCapabilitiesBE01 2 }





END
