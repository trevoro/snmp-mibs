SK-CONC-MIB DEFINITIONS ::= BEGIN

-- Title:  SysKonnect SK-CONC-MIB Extension version 1.2
-- Date:   February, 1995
-- By:     Georg Klug <gklug@skd.de>

IMPORTS
    enterprises, OBJECT-TYPE, Counter,
    Gauge, TimeTicks, DisplayString      FROM RFC1155-SMI
    fddimibPORTSMTIndex, fddimibPORTIndex, fddimibPORTMyType,
    fddimibPORTConnectState		 FROM FDDI-SMT73-MIB
    TRAP-TYPE                            FROM RFC-1215;


--***********************************************************************
--*   Global Definition of the enterprise
--***********************************************************************

	-- S&K private

	sk		OBJECT IDENTIFIER ::= { enterprises 179 }

	skSystems	OBJECT IDENTIFIER ::= { sk 1 }
	skMibs		OBJECT IDENTIFIER ::= { sk 2 }

--***********************************************************************
--*   Definition of the used sysObjectID
--***********************************************************************

	skRouter	OBJECT IDENTIFIER ::= { skSystems 1 }
	skConcentrator	OBJECT IDENTIFIER ::= { skSystems 2 }
	skSwitch	OBJECT IDENTIFIER ::= { skSystems 3 }

	skDLI		OBJECT IDENTIFIER ::= { skMibs 1 }


--***********************************************************************
--*   Traps used
--***********************************************************************

skfddiPortErrorCondition TRAP-TYPE
        ENTERPRISE sk
        VARIABLES {fddimibPORTSMTIndex, fddimibPORTIndex, fddimibPORTMyType, 
                   fddimibPORTConnectState}
        DESCRIPTION
        "This trap is generated when a FDDI port A/B, S or M is switching
	from any state to the off state. This indicates that the port failed."
        REFERENCE
        "fddiPortErrorCondition of ibm8245"
        ::= 1


skfddiPortErrorConditionResolved TRAP-TYPE
    ENTERPRISE sk
    VARIABLES {fddimibPORTSMTIndex, fddimibPORTIndex, fddimibPORTMyType, 
               fddimibPORTConnectState}
    DESCRIPTION
        "This trap is generated when a FDDI port A/B, S or M is switching
	from the off state to the break state. This indicates that the port
	is working again. "
    REFERENCE
        "fddiPortErrorConditionResolved of ibm8245"
        ::= 2


skfddiPortDisconnect TRAP-TYPE
    ENTERPRISE sk
    VARIABLES {fddimibPORTSMTIndex, fddimibPORTIndex, fddimibPORTMyType, 
               fddimibPORTConnectState}
    DESCRIPTION
        "This trap is generated when a FDDI port A/B, S or M is switching
	from the active state to the break state. This indicates that the
	port was disconnected."
    REFERENCE
        "fddiPortDisconnect of ibm8245"
        ::= 3


skfddiPortReconnect TRAP-TYPE
    ENTERPRISE sk
    VARIABLES {fddimibPORTSMTIndex, fddimibPORTIndex, fddimibPORTMyType, 
               fddimibPORTConnectState}
    DESCRIPTION
        "This trap is generated when a FDDI port A/B, S or M is switching
	from the break state to the active state. This indicates that the
	port was reconnected."
    REFERENCE
        "fddiPortReconnect of ibm8245"
        ::= 4

END
