-- $Workfile:   pgflash.my  $

-- $Revision:   1.5  $
-- $Date:   06 Dec 1999 15:05:20  $

-- Copyright 1999 PairGain Technologies, Inc.  All Rights
-- Reserved.  Reproduction of this document is authorized on
-- condition that the foregoing copyright notice is included.
-- This PairGain SNMP Management Information Base Specification
-- (Specification) embodies PairGain's confidential and
-- proprietary intellectual property.  PairGain retains all
-- title and ownership in the Specification, including any
-- revisions.
--
-- It is PairGain’s intent to encourage the widespread use of
-- this Specification in connection with the management of
-- PairGain products. PairGain grants vendors, end-users,
-- and other interested parties a non-exclusive license to
-- use this Specification in connection with the management
-- of PairGain products.
--
-- This Specification is supplied "AS IS," and PairGain makes
-- no warranty, either expressed or implied, as to the use,
-- operation, condition, or performance of the Specification.

DSLAM-FLASH-MIB DEFINITIONS ::= BEGIN

IMPORTS
        enterprises, Gauge
            FROM RFC1155-SMI
				
		MODULE-IDENTITY FROM SNMPv2-SMI

        OBJECT-TYPE
            FROM RFC-1212

	ifIndex
	    FROM RFC1213-MIB

        pgainDSLAM
            FROM PAIRGAIN-COMMON-HD-MIB;

pgDSLAMFlashMIB MODULE-IDENTITY
	LAST-UPDATED	"9803260000Z"
	ORGANIZATION	"Pairgain Technology"
        CONTACT-INFO	""
	DESCRIPTION	"The module defines the MIB for utilizing the DSLAM flash"
	::= {pgainDSLAM 5}

pgDSLAMFlashObjects		  OBJECT IDENTIFIER ::= { pgDSLAMFlashMIB 1 }

-- pgNand

pgDSLAMFlashOperStatus OBJECT-TYPE
	SYNTAX  INTEGER {
		none(1),
		success(2),
		inProgress(3),
		failed(4)
	}
	ACCESS  read-only
	STATUS  mandatory
	DESCRIPTION
		"This object contains the result of the most recent
		 flash test, or the value none(1) if no tests have been requested 		 since the last reset."
	::= { pgDSLAMFlashObjects 1 }

pgDSLAMFlashDownLoad OBJECT-TYPE
    SYNTAX  OCTET STRING (SIZE (0..255))
    ACCESS  read-write
    STATUS  mandatory
    DESCRIPTION
        "Write to this variable to initiate a  TFTP download.
		 syntax: <remotehost>:<full path to remote file>,<slot>[,<file name>]"
    ::= { pgDSLAMFlashObjects 2 }

pgDSLAMFlashUpLoad OBJECT-TYPE
    SYNTAX  OCTET STRING (SIZE (0..255))
    ACCESS  read-write
    STATUS  mandatory
    DESCRIPTION
        "Write to this variable to initiate a  TFTP upload.
		 syntax: <slot>,<file name>,<remotehost>:<full path to remote file>"
    ::= { pgDSLAMFlashObjects 3 }

pgDSLAMFlashCopyFile OBJECT-TYPE
    SYNTAX  OCTET STRING (SIZE (0..255))
    ACCESS  read-write
    STATUS  mandatory
    DESCRIPTION
        "Write to this variable to copy a file from card to card.
		 syntax: <slot>,<file name>,<slot>[,<file name>]"
    ::= { pgDSLAMFlashObjects 4 }

pgModemXferTable OBJECT-TYPE
	SYNTAX  SEQUENCE OF PgModemXferEntry
	ACCESS  not-accessible
	STATUS  mandatory
	DESCRIPTION
		"The DSLAM Modem File Transfer Table."
	::= { pgDSLAMFlashObjects 5 }

pgModemXferEntry OBJECT-TYPE
	SYNTAX  PgModemXferEntry
	ACCESS  not-accessible
	STATUS  mandatory
	DESCRIPTION
		"Entry in the DSLAM Modem File Transfer Table."
	INDEX   { ifIndex }
	::= { pgModemXferTable 1 }

PgModemXferEntry ::= SEQUENCE {
	pgModemXferOperStatus
		INTEGER,
	pgModemXferSourceFilename
		OCTET STRING (SIZE (0..255)),
	pgModemXferDestinationFilename
		OCTET STRING (SIZE (0..255)),
	pgModemXferAction
		INTEGER
}

pgModemXferOperStatus OBJECT-TYPE
	SYNTAX  INTEGER {
		none(1),
		success(2),
		inProgress(3),
		failed(4)
	}
	ACCESS  read-only
	STATUS  mandatory
	DESCRIPTION
		"This object contains the result of the most recently requested
		 modem file transfer access, or the value none(1) if no action
		 have been requested since the last reset."
	::= { pgModemXferEntry 1 }

pgModemXferSourceFilename OBJECT-TYPE
    SYNTAX  OCTET STRING (SIZE (0..255))
    ACCESS  read-write
    STATUS  mandatory
    DESCRIPTION
        "Specify source filename."
    ::= { pgModemXferEntry 2 }

pgModemXferDestinationFilename OBJECT-TYPE
    SYNTAX  OCTET STRING (SIZE (0..255))
    ACCESS  read-write
    STATUS  optional
    DESCRIPTION
        "Specify destination filename."
    ::= { pgModemXferEntry 3 }

pgModemXferAction OBJECT-TYPE
	SYNTAX  INTEGER {
		abort(1),
		download(2)
	}
	ACCESS  write-only
	STATUS  mandatory
	DESCRIPTION
		"Specify the desired download action.  The options are as follows:

		 download	- Download the file specified by pgModemXferSourceFilename to the modem that is
		 		attached to ifIndex.  The file must be present on the card that contains
				the ifIndex. Specifying pgModemXferDestinationFilename is optional
				and valid only for ADSL modems.

		 abort		- Abort current file transfer."
	::= { pgModemXferEntry 4 }
END
