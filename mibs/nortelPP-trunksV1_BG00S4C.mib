Nortel-Magellan-Passport-TrunksMIB
DEFINITIONS ::= BEGIN



IMPORTS

      OBJECT-TYPE
   FROM RFC-1212

      components,
      passportMIBs
   FROM Nortel-Magellan-Passport-UsefulDefinitionsMIB

      Counter32,
      DisplayString,
      StorageType,
      RowStatus,
      PassportCounter64,
      InterfaceIndex,
      Gauge32,
      Integer32,
      Unsigned32
   FROM Nortel-Magellan-Passport-StandardTextualConventionsMIB

      AsciiString,
      NonReplicated,
      FixedPoint1
   FROM Nortel-Magellan-Passport-TextualConventionsMIB;




-- LAST-UPDATED   "9808030000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     Trunks Enterprise MIB."

trunksMIB OBJECT IDENTIFIER ::= { passportMIBs 43 }










-- Trunk/n
-- The Trunk component provides a Passport to Passport connection. It 
-- controls a protocol stack associated with a logical port on a function 
-- processor that provides an interconnection to another Passport with 
-- a Trunk component.
-- It requires the existence of the Routing component. Note that 
-- dpnRouting also needs to be included in the featureList of CP's 
-- LogicalProcessorType component.
-- Either an AtmAccess or an Unacknowledged subcomponent must be 
-- added to provide the underlying link protocol and associated 
-- hardware that the Trunk will use. 

trk OBJECT IDENTIFIER ::= { components 60 }



trkRowStatusTable OBJECT-TYPE
   SYNTAX     SEQUENCE OF TrkRowStatusEntry
   ACCESS     not-accessible
   STATUS     mandatory
   DESCRIPTION
     "This entry controls the addition and deletion of 
      trk components."
::= { trk 1 }

trkRowStatusEntry OBJECT-TYPE
   SYNTAX     TrkRowStatusEntry
   ACCESS     not-accessible
   STATUS     mandatory
   DESCRIPTION
     "A single entry in the table represents a single 
      trk component."
   INDEX {
      trkIndex }
::= { trkRowStatusTable 1 }

TrkRowStatusEntry ::= SEQUENCE {
   trkRowStatus
      RowStatus,
   trkComponentName
      DisplayString,
   trkStorageType
      StorageType,
   trkIndex
      Integer32 }

trkRowStatus OBJECT-TYPE
   SYNTAX     RowStatus 
   ACCESS     read-write
   STATUS     mandatory
   DESCRIPTION
     "This variable is used as the basis for SNMP naming of
      trk components.
      These components can be added and deleted."
::= { trkRowStatusEntry 1 }

trkComponentName OBJECT-TYPE
   SYNTAX     DisplayString 
   ACCESS     read-only
   STATUS     mandatory
   DESCRIPTION
     "This variable provides the component's string name for
      use with the ASCII Console Interface"
::= { trkRowStatusEntry 2 }

trkStorageType OBJECT-TYPE
   SYNTAX     StorageType 
   ACCESS     read-only
   STATUS     mandatory
   DESCRIPTION
     "This variable represents the storage type value for the
      trk tables."
::= { trkRowStatusEntry 4 }

trkIndex OBJECT-TYPE
   SYNTAX     Integer32 (0..65535)
   ACCESS     not-accessible
   STATUS     mandatory
   DESCRIPTION
     "This variable represents the index for the trk tables."
::= { trkRowStatusEntry 10 }

trkIfEntryTable OBJECT-TYPE
   SYNTAX     SEQUENCE OF TrkIfEntryEntry
   ACCESS     not-accessible
   STATUS     mandatory
   DESCRIPTION
     "This group contains the provisionable attributes for the ifEntry."
::= { trk 100 }

trkIfEntryEntry OBJECT-TYPE
   SYNTAX     TrkIfEntryEntry
   ACCESS     not-accessible
   STATUS     mandatory
   DESCRIPTION
     "An entry in the trkIfEntryTable."
   INDEX {
      trkIndex }
::= { trkIfEntryTable 1 }

TrkIfEntryEntry ::= SEQUENCE {
   trkIfAdminStatus
      INTEGER,
   trkIfIndex
      InterfaceIndex }

trkIfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { trkIfEntryEntry 1 }

trkIfIndex OBJECT-TYPE
   SYNTAX     InterfaceIndex (1..65535)
   ACCESS     read-only
   STATUS     mandatory
   DESCRIPTION
     "This is the index for the IfEntry. Its value is automatically initialized 
      during the provisioning process."
::= { trkIfEntryEntry 2 }

trkProvTable OBJECT-TYPE
   SYNTAX     SEQUENCE OF TrkProvEntry
   ACCESS     not-accessible
   STATUS     mandatory
   DESCRIPTION
     "This group of attributes provides the parameters used by the layer 3 
      Trunk to Trunk staging protocol."
::= { trk 101 }

trkProvEntry OBJECT-TYPE
   SYNTAX     TrkProvEntry
   ACCESS     not-accessible
   STATUS     mandatory
   DESCRIPTION
     "An entry in the trkProvTable."
   INDEX {
      trkIndex }
::= { trkProvTable 1 }

TrkProvEntry ::= SEQUENCE {
   trkExpectedRemoteNodeName
      AsciiString,
   trkRemoteValidationAction
      INTEGER,
   trkMaximumExpectedRoundTripDelay
      Unsigned32,
   trkIdleTimeOut
      Unsigned32 }

trkExpectedRemoteNodeName OBJECT-TYPE
   SYNTAX     AsciiString (SIZE (0..12))
   ACCESS     read-write
   STATUS     mandatory
   DESCRIPTION
     "This attribute specifies the expected node name of the module to 
      which this Trunk is connected. Once entered, the node name must 
      correspond to the Mod nodeName attribute of the remote node. The 
      Trunk end points exchange their node name through the Trunk 
      staging protocol. The staged value is validated and the 
      remoteValidationAction will be executed for those values not 
      matching the value supplied for this attribute.
      If this attribute is an empty string, then the comparison is always 
      successful."
::= { trkProvEntry 1 }

trkRemoteValidationAction OBJECT-TYPE
   SYNTAX     INTEGER  {
                 continue(0),
                 disable(1) }
   ACCESS     read-write
   STATUS     mandatory
   DESCRIPTION
     "This attribute specifies the action to be taken if there is a mismatch 
      between the expectedRemoteNodeName attribute and the value 
      received from the remote end. The remoteValidationAction 
      determines the action when a value is supplied to the 
      expectedRemoteNodeName attribute. If this attribute is provisioned 
      to continue then upon an unsuccessful validation staging continues, 
      otherwise, if disable is set then the Trunk does not continue to stage 
      but, attempts to stage again after a one minute time out.
      All unsuccessful validation when the expectedRemoteNodeName 
      has been set result in the generation of an alarm."
   DEFVAL     { continue }
::= { trkProvEntry 2 }

trkMaximumExpectedRoundTripDelay OBJECT-TYPE
   SYNTAX     Unsigned32 (1..1500)
   ACCESS     read-write
   STATUS     mandatory
   DESCRIPTION
     "This is the maximum round trip delay value used by the Trunk 
      staging protocol, in conjunction with measuredSpeedToIf, to 
      determine if it has taken too long to successfully stage with a 
      remote Trunk. The value specified must be larger than the 
      measuredRoundTripDelay or the Trunk may not successfully stage."
   DEFVAL     { 1500 }
::= { trkProvEntry 3 }

trkIdleTimeOut OBJECT-TYPE
   SYNTAX     Unsigned32 (2..30)
   ACCESS     read-write
   STATUS     mandatory
   DESCRIPTION
     "This attribute specifies the Trunk protocol idle time out duration in 
      units of seconds. If the local Trunk does not receive any packets 
      from the link for the period specified by this attribute, the Trunk 
      enters Are You There (AYT) mode for up to two seconds. If the 
      Trunk does not receive any packets from the remote during the AYT 
      mode it will restage; otherwise, it exits AYT mode and continues to 
      provide service."
   DEFVAL     { 4 }
::= { trkProvEntry 4 }

trkOverridesTable OBJECT-TYPE
   SYNTAX     SEQUENCE OF TrkOverridesEntry
   ACCESS     not-accessible
   STATUS     mandatory
   DESCRIPTION
     "Theses attribute comprise the set of provisionable override 
      parameters supported by both the Trunk and DpnGateway 
      components. The attributes are used when reporting operational 
      attributes (used for metric calculations) to the routing system."
::= { trk 102 }

trkOverridesEntry OBJECT-TYPE
   SYNTAX     TrkOverridesEntry
   ACCESS     not-accessible
   STATUS     mandatory
   DESCRIPTION
     "An entry in the trkOverridesTable."
   INDEX {
      trkIndex }
::= { trkOverridesTable 1 }

TrkOverridesEntry ::= SEQUENCE {
   trkOverrideTransmitSpeed
      Gauge32,
   trkOldOverrideRoundTripDelay
      Gauge32,
   trkOverrideRoundTripUsec
      FixedPoint1 }

trkOverrideTransmitSpeed OBJECT-TYPE
   SYNTAX     Gauge32 (0 | 1000..4294967295)
   ACCESS     read-write
   STATUS     mandatory
   DESCRIPTION
     "This is the overridden value of link speed (bit/s) that, if staged 
      successfully with the remote, is reported to the routing system for 
      metric calculations. A zero indicates that an override value has not 
      been provided and that only the measured value will be reported to 
      the routing system.
      If this value is changed on a Trunk or DpnGateway that is enabled, 
      the LOCK and UNLOCK commands must be issued to the 
      component to restage the override with the remote."
   DEFVAL     { 0 }
::= { trkOverridesEntry 1 }

trkOldOverrideRoundTripDelay OBJECT-TYPE
   SYNTAX     Gauge32 (0..1500)
   ACCESS     read-write
   STATUS     obsolete
   DESCRIPTION
     "This is the overridden value of link delay (ms) that, if staged 
      successfully with the remote, is reported to the routing system for 
      metric calculations. A zero indicates that an override value has not 
      been provided and that only the measured value will be reported to 
      the routing system. 
      If this value is changed on a Trunk or DpnGateway that is enabled, 
      the LOCK and UNLOCK commands must be issued to the 
      component to restage the override with the remote."
   DEFVAL     { 0 }
::= { trkOverridesEntry 2 }

trkOverrideRoundTripUsec OBJECT-TYPE
   SYNTAX     FixedPoint1 (0..15000)
   ACCESS     read-write
   STATUS     mandatory
   DESCRIPTION
     "This is the overridden value of link delay (ms) that, if staged 
      successfully with the remote, is reported to the routing system for 
      metric calculations. A zero indicates that an override value has not 
      been provided and that only the measured value will be reported to 
      the routing system. 
      If this value is changed on a Trunk or DpnGateway that is enabled, 
      the LOCK and UNLOCK commands must be issued to the 
      component to restage the override with the remote."
   DEFVAL     { 0 }
::= { trkOverridesEntry 3 }

trkStateTable OBJECT-TYPE
   SYNTAX     SEQUENCE OF TrkStateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { trk 103 }

trkStateEntry OBJECT-TYPE
   SYNTAX     TrkStateEntry
   ACCESS     not-accessible
   STATUS     mandatory
   DESCRIPTION
     "An entry in the trkStateTable."
   INDEX {
      trkIndex }
::= { trkStateTable 1 }

TrkStateEntry ::= SEQUENCE {
   trkAdminState
      INTEGER,
   trkOperationalState
      INTEGER,
   trkUsageState
      INTEGER,
   trkAvailabilityStatus
      OCTET STRING,
   trkProceduralStatus
      OCTET STRING,
   trkControlStatus
      OCTET STRING,
   trkAlarmStatus
      OCTET STRING,
   trkStandbyStatus
      INTEGER,
   trkUnknownStatus
      INTEGER }

trkAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { trkStateEntry 1 }

trkOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { trkStateEntry 2 }

trkUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { trkStateEntry 3 }

trkAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { trkStateEntry 4 }

trkProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { trkStateEntry 5 }

trkControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { trkStateEntry 6 }

trkAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { trkStateEntry 7 }

trkStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { trkStateEntry 8 }

trkUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { trkStateEntry 9 }

trkOperStatusTable OBJECT-TYPE
   SYNTAX     SEQUENCE OF TrkOperStatusEntry
   ACCESS     not-accessible
   STATUS     mandatory
   DESCRIPTION
     "This group includes the Operational Status attribute. This attribute 
      defines the current operational state of this component."
::= { trk 104 }

trkOperStatusEntry OBJECT-TYPE
   SYNTAX     TrkOperStatusEntry
   ACCESS     not-accessible
   STATUS     mandatory
   DESCRIPTION
     "An entry in the trkOperStatusTable."
   INDEX {
      trkIndex }
::= { trkOperStatusTable 1 }

TrkOperStatusEntry ::= SEQUENCE {
   trkSnmpOperStatus
      INTEGER }

trkSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { trkOperStatusEntry 1 }

trkOperTable OBJECT-TYPE
   SYNTAX     SEQUENCE OF TrkOperEntry
   ACCESS     not-accessible
   STATUS     mandatory
   DESCRIPTION
     "This is the group of operational attributes supported by the Trunk."
::= { trk 105 }

trkOperEntry OBJECT-TYPE
   SYNTAX     TrkOperEntry
   ACCESS     not-accessible
   STATUS     mandatory
   DESCRIPTION
     "An entry in the trkOperTable."
   INDEX {
      trkIndex }
::= { trkOperTable 1 }

TrkOperEntry ::= SEQUENCE {
   trkRemoteComponentName
      AsciiString }

trkRemoteComponentName OBJECT-TYPE
   SYNTAX     AsciiString (SIZE (1..27))
   ACCESS     read-only
   STATUS     mandatory
   DESCRIPTION
     "This attribute is the component name of the remote end which it has 
      supplied through the Trunk staging protocol."
::= { trkOperEntry 1 }

trkTransportTable OBJECT-TYPE
   SYNTAX     SEQUENCE OF TrkTransportEntry
   ACCESS     not-accessible
   STATUS     mandatory
   DESCRIPTION
     "This group of attributes contains the set of operational parameters 
      measured and maintained by both the Trunk and DpnGateway 
      components."
::= { trk 106 }

trkTransportEntry OBJECT-TYPE
   SYNTAX     TrkTransportEntry
   ACCESS     not-accessible
   STATUS     mandatory
   DESCRIPTION
     "An entry in the trkTransportTable."
   INDEX {
      trkIndex }
::= { trkTransportTable 1 }

TrkTransportEntry ::= SEQUENCE {
   trkMeasuredSpeedToIf
      Gauge32,
   trkMeasuredRoundTripDelay
      Gauge32,
   trkMaxTxUnit
      Gauge32,
   trkMeasuredRoundTripDelayUsec
      FixedPoint1 }

trkMeasuredSpeedToIf OBJECT-TYPE
   SYNTAX     Gauge32 (0..4294967295)
   ACCESS     read-only
   STATUS     mandatory
   DESCRIPTION
     "This attribute indicates the current 'transmittable' bandwidth of the 
      underlying facility.
      For a Trunk with a Unack subcomponent, and a DpnGateway with a 
      Utp subcomponent, if a serial port is used, the value is the measured 
      transmit speed of the port; if a channelized port (E1/DS1) is used, 
      the value is the measured transmit speed of the Channel. 
      For a Trunk with an AtmAccess subcomponent, the value is 
      calculated by converting the VCC transmit cell rate to an equivalent 
      bit rate. The VCC transmit cell rate is determined based on the 
      vccReportingBw attribute of the Trunk AtmAccess component. If 
      vccReportingBw has a value of pcr and attribute bwElastic of 
      AtmAccess has a value of no, the peak cell rate (PCR) of the VCC, 
      defined in txTrafficDescParm of AtmIf Vcc Vcd, is used. If 
      vccReportingBw has a value of pcr and attribute bwElastic of 
      AtmAccess has a value of yes, the minimum of the PCR, defined in 
      txTrafficDescParm of AtmIf Vcc Vcd, and the current cell rate 
      (CCR) of the VCC is used. If vccReportingBw has a value of acr, 
      the best measurement of the actual cell rate (ACR) of the VCC is 
      used, which is the minimum of the PCR, the CCR and the actual 
      shaping rate (ASR).
      For a DpnGateway with a FrAccess subcomponent, the value 
      indicates the committedInformationRate of FrAccess FrMuxSetup.
      A value of zero is displayed when the underlying facility is disabled 
      or the current 'transmittable' bandwidth is unknown."
   DEFVAL     { 0 }
::= { trkTransportEntry 1 }

trkMeasuredRoundTripDelay OBJECT-TYPE
   SYNTAX     Gauge32 (0..1500)
   ACCESS     read-only
   STATUS     obsolete
   DESCRIPTION
     "This attribute indicates the measured Round Trip Delay (msec) 
      discovered with the remote through the Trunk and DpnGateway 
      staging protocols. The value includes emission, propagation, and 
      queuing delays. A 512 byte data packet is used to perform the 
      measurement. A value of zero is displayed when the link is disabled 
      or the measured Round Trip Delay is unknown."
   DEFVAL     { 0 }
::= { trkTransportEntry 2 }

trkMaxTxUnit OBJECT-TYPE
   SYNTAX     Gauge32 (0..65535)
   ACCESS     read-only
   STATUS     mandatory
   DESCRIPTION
     "This is the maximum transmission unit (byte size) that is supported 
      by the Trunk or DpnGateway component. This size includes the 
      data and routing headers. A value of zero indicates the MTU has not 
      yet been determined."
   DEFVAL     { 0 }
::= { trkTransportEntry 3 }

trkMeasuredRoundTripDelayUsec OBJECT-TYPE
   SYNTAX     FixedPoint1 (0..15000)
   ACCESS     read-only
   STATUS     mandatory
   DESCRIPTION
     "This attribute indicates the measured Round Trip Delay (msec) 
      discovered with the remote through the Trunk and DpnGateway 
      staging protocols. The value includes emission, propagation, and 
      queuing delays. A 512 byte data packet is used to perform the 
      measurement. A value of zero is displayed when the link is disabled 
      or the measured Round Trip Delay is unknown."
   DEFVAL     { 0 }
::= { trkTransportEntry 4 }

trkStatsTable OBJECT-TYPE
   SYNTAX     SEQUENCE OF TrkStatsEntry
   ACCESS     not-accessible
   STATUS     mandatory
   DESCRIPTION
     "These attributes comprise the statistics collected by the Trunk 
      component."
::= { trk 107 }

trkStatsEntry OBJECT-TYPE
   SYNTAX     TrkStatsEntry
   ACCESS     not-accessible
   STATUS     mandatory
   DESCRIPTION
     "An entry in the trkStatsTable."
   INDEX {
      trkIndex }
::= { trkStatsTable 1 }

TrkStatsEntry ::= SEQUENCE {
   trkAreYouThereModeEntries
      Counter32,
   trkPktFromIf
      PassportCounter64,
   trkTrunkPktFromIf
      Counter32,
   trkTrunkPktToIf
      Counter32,
   trkDiscardUnforward
      PassportCounter64,
   trkDiscardTrunkPktFromIf
      Counter32,
   trkIntPktFromIf
      PassportCounter64,
   trkDiscardIntUnforward
      PassportCounter64,
   trkStagingAttempts
      Counter32,
   trkDiscardTrunkPktToIf
      Counter32,
   trkUtilization
      Gauge32 }

trkAreYouThereModeEntries OBJECT-TYPE
   SYNTAX     Counter32 
   ACCESS     read-only
   STATUS     mandatory
   DESCRIPTION
     "This attribute counts the number of times that the component has 
      entered Are You There mode. This counter wraps around to zero 
      when the maximum value is exceeded."
::= { trkStatsEntry 1 }

trkPktFromIf OBJECT-TYPE
   SYNTAX     PassportCounter64 
   ACCESS     read-only
   STATUS     mandatory
   DESCRIPTION
     "This attribute counts the number of packets received from the 
      remote module. It does not include the packets received from the 
      interrupting queue. This counter wraps around to zero when the 
      maximum value is exceeded."
::= { trkStatsEntry 2 }

trkTrunkPktFromIf OBJECT-TYPE
   SYNTAX     Counter32 
   ACCESS     read-only
   STATUS     mandatory
   DESCRIPTION
     "This attribute counts the number of internal trunk protocol packets 
      (including those from the interrupting queue) received from the 
      remote module. These packets are forwarded to the Trunk 
      component. This counter wraps around to zero when the maximum 
      value is exceeded."
::= { trkStatsEntry 3 }

trkTrunkPktToIf OBJECT-TYPE
   SYNTAX     Counter32 
   ACCESS     read-only
   STATUS     mandatory
   DESCRIPTION
     "This attribute counts the number of internal trunk protocol packets 
      (including those through the interrupting queue) transmitted to the 
      remote module. This counter wraps around to zero when the 
      maximum value is exceeded."
::= { trkStatsEntry 4 }

trkDiscardUnforward OBJECT-TYPE
   SYNTAX     PassportCounter64 
   ACCESS     read-only
   STATUS     mandatory
   DESCRIPTION
     "This attribute counts the number of packets received from the 
      remote module that have been discarded. It does not include the 
      packets received from the interrupting queue that have been 
      discarded. This counter wraps around to zero when the maximum 
      value is exceeded. Two main reasons that cause this counter to 
      increase are: 
      (1) the remote protocol is not compatible with the local protocol 
      stack or, 
      (2) the packet cannot be forwarded due to a recent loss of 
      connectivity or due to congestion."
::= { trkStatsEntry 5 }

trkDiscardTrunkPktFromIf OBJECT-TYPE
   SYNTAX     Counter32 
   ACCESS     read-only
   STATUS     mandatory
   DESCRIPTION
     "This attribute counts the number of internal trunk protocol packets 
      (including those on the interrupting queue) received from the 
      remote module that have been discarded. This counter wraps around 
      to zero when the maximum value is exceeded. The three main 
      reasons that cause this counter to increase are: 
      (1) the two Trunks are not synchronized, 
      (2) the remote trunk protocol is not the same version as the local 
      protocol, and 
      (3) the remote trunk has restaged."
::= { trkStatsEntry 6 }

trkIntPktFromIf OBJECT-TYPE
   SYNTAX     PassportCounter64 
   ACCESS     read-only
   STATUS     mandatory
   DESCRIPTION
     "This attribute counts the number of packets received on the 
      interrupting queue from the remote module. This counter wraps 
      around to zero when the maximum value is exceeded."
::= { trkStatsEntry 7 }

trkDiscardIntUnforward OBJECT-TYPE
   SYNTAX     PassportCounter64 
   ACCESS     read-only
   STATUS     mandatory
   DESCRIPTION
     "This attribute counts the number of packets received on the 
      interrupting queue from the remote module that have been 
      discarded. This counter wraps around to zero when the maximum 
      value is exceeded. Two main reasons that cause this counter to 
      increment are: 
      (1) the remote protocol is not compatible to the local protocol stack 
      and, 
      (2) the packet cannot be forwarded due to either a recent loss of 
      connectivity or due to congestion."
::= { trkStatsEntry 8 }

trkStagingAttempts OBJECT-TYPE
   SYNTAX     Counter32 
   ACCESS     read-only
   STATUS     mandatory
   DESCRIPTION
     "This attribute counts the number of times that the staging protocol 
      has attempted to stage with the remote module. This counter wraps 
      around to zero when the maximum value is exceeded. The main 
      reason that causes this counter to increment is that the local 
      hardware is up but, the local protocol cannot stage with the remote 
      protocol due to a faulty connection. If the value is zero, then the 
      local hardware has never enabled successfully."
::= { trkStatsEntry 9 }

trkDiscardTrunkPktToIf OBJECT-TYPE
   SYNTAX     Counter32 
   ACCESS     read-only
   STATUS     mandatory
   DESCRIPTION
     "This attribute counts the number of internal trunk protocol packets 
      (including those through the interrupting queue) that have been 
      discarded before being transmitted to the remote module. This 
      counter wraps around to zero when the maximum value is 
      exceeded. The main reason that causes this counter to increment is 
      that the trunk can not get sufficient resources to create an internal 
      trunk protocol packet."
::= { trkStatsEntry 10 }

trkUtilization OBJECT-TYPE
   SYNTAX     Gauge32 (0..200)
   ACCESS     read-only
   STATUS     mandatory
   DESCRIPTION
     "This attribute indicates the average trunk utilization.
      
      For a Trunk/n with an Unack subcomponent, the value is the link 
      receive utilization. It is calculated every minute by comparing the 
      number of octets received from the remote module against the value 
      of the Trunk/n measuredSpeedToIf. Since the trunk application 
      solely owns the physical link, the maximum link utilization is 
      100%.
      
      For a Trunk/n with an AtmAccess subcomponent, the value is the 
      VCC(s) transmit utilization. It is calculated every 30 seconds by 
      comparing the number of cells transmitted by AtmIf Vcc(s) against 
      the value of the Trunk/n measuredSpeedToIf. The VCCs include the 
      trunk VCC indicated by atmConnection of Trunk/n AtmAccess and 
      the PORS SPO (Short Path Oriented) multiplexing VCC if 
      applicable. The PORS SPO multiplexing VCC only applies to a 
      Trunk/n with subcomponents Pa AtmAccess, where the mode of 
      AtmAccess is multiplexing, and the AtmAccess is linked to a second 
      VCC indicated by atmConnection of Pa AtmAccess. Since the trunk 
      application shares a physical link with other applications, the VCCs 
      utilization can exceed 100%, and the value 200% is chosen as the 
      maximum calculated utilization."
::= { trkStatsEntry 11 }

trkSpeedReportingTable OBJECT-TYPE
   SYNTAX     SEQUENCE OF TrkSpeedReportingEntry
   ACCESS     not-accessible
   STATUS     mandatory
   DESCRIPTION
     "This group of provisionable attributes provides the ability to disable 
      or enable the generation of speed change alarms by the Trunk 
      component. It also provides the ability to disable or enable the 
      Dynamic Speed Reporting mechanism."
::= { trk 109 }

trkSpeedReportingEntry OBJECT-TYPE
   SYNTAX     TrkSpeedReportingEntry
   ACCESS     not-accessible
   STATUS     mandatory
   DESCRIPTION
     "An entry in the trkSpeedReportingTable."
   INDEX {
      trkIndex }
::= { trkSpeedReportingTable 1 }

TrkSpeedReportingEntry ::= SEQUENCE {
   trkSpeedReportingHoldOff
      Unsigned32,
   trkLowSpeedAlarmThreshold
      Unsigned32,
   trkHighSpeedAlarmThreshold
      Unsigned32 }

trkSpeedReportingHoldOff OBJECT-TYPE
   SYNTAX     Unsigned32 (1..1200)
   ACCESS     read-write
   STATUS     mandatory
   DESCRIPTION
     "This attribute specifies the hold off time for reporting speed 
      increases. When the measuredSpeedToIf reaches a level specified 
      by the speedReportingThresholds attribute, the value specifies the 
      duration (in units of seconds) for which the measuredSpeedToIf 
      must maintain that level before it will be reported."
   DEFVAL     { 30 }
::= { trkSpeedReportingEntry 2 }

trkLowSpeedAlarmThreshold OBJECT-TYPE
   SYNTAX     Unsigned32 (0 | 1..4294967295)
   ACCESS     read-write
   STATUS     mandatory
   DESCRIPTION
     "This attribute specifies the lower end of the range of normal speeds 
      for this Trunk. If the measuredSpeedToIf drops below this value the 
      Trunk component generates a SET alarm. When the 
      measuredSpeedToIf reaches or exceeds the value of this attribute, 
      the Trunk component will generate a CLEAR alarm."
   DEFVAL     { 0 }
::= { trkSpeedReportingEntry 3 }

trkHighSpeedAlarmThreshold OBJECT-TYPE
   SYNTAX     Unsigned32 (1..4294967295)
   ACCESS     read-write
   STATUS     mandatory
   DESCRIPTION
     "This attribute specifies the upper end of the range of normal speeds 
      for this Trunk. If the measuredSpeedToIf exceeds this value the 
      Trunk component generates a SET alarm. When the 
      measuredSpeedToIf returns to or falls below the value of this 
      attribute, the Trunk component will generate a CLEAR alarm."
   DEFVAL     { 4294967295 }
::= { trkSpeedReportingEntry 4 }

trkSpdThTable OBJECT-TYPE
   SYNTAX     SEQUENCE OF TrkSpdThEntry
   ACCESS     not-accessible
   STATUS     mandatory
   DESCRIPTION
     "This attribute controls the behavior of the Dynamic Speed 
      Reporting mechanism. If its value is empty then the mechanism is 
      disabled and neither increases nor decreases are reported. 
      Otherwise, the attribute may contain up to seven threshold levels 
      which are used to control the reporting of speed increases. Speed 
      decreases are always reported immediately. If the 
      measuredSpeedToIf increases such that it reaches one of the 
      threshold levels which is greater than the last reported speed, the 
      Trunk starts the speedReportingHoldOff timer. If the speed remains 
      above this threshold until the timer expires, the Trunk component 
      then reports the measuredSpeedToIf; otherwise the increase is not 
      reported."
::= { trk 318 }

trkSpdThEntry OBJECT-TYPE
   SYNTAX     TrkSpdThEntry
   ACCESS     not-accessible
   STATUS     mandatory
   DESCRIPTION
     "An entry in the trkSpdThTable."
   INDEX {
      trkIndex,
      trkSpdThValue }
::= { trkSpdThTable 1 }

TrkSpdThEntry ::= SEQUENCE {
   trkSpdThValue
      Integer32,
   trkSpdThRowStatus
      RowStatus }

trkSpdThValue OBJECT-TYPE
   SYNTAX     Integer32 (0..268435455)
   ACCESS     read-write
   STATUS     mandatory
   DESCRIPTION
     "This variable represents both the value and the index for the
      trkSpdThTable."
::= { trkSpdThEntry 1 }

trkSpdThRowStatus OBJECT-TYPE
   SYNTAX     RowStatus 
   ACCESS     write-only
   STATUS     mandatory
   DESCRIPTION
     "This variable is used to control the addition and deletion 
      of individual values of the trkSpdThTable."
::= { trkSpdThEntry 2 }

trkPktBpTable OBJECT-TYPE
   SYNTAX     SEQUENCE OF TrkPktBpEntry
   ACCESS     not-accessible
   STATUS     mandatory
   DESCRIPTION
     "This attribute counts the number of packets received by the Trunk. 
      It is a vector indexed by the emission priorities (ep0, ep1, and ep2) 
      of the packets. The highest emission priority is ep0. These counters 
      wrap around to zero when the maximum value is exceeded."
::= { trk 368 }

trkPktBpEntry OBJECT-TYPE
   SYNTAX     TrkPktBpEntry
   ACCESS     not-accessible
   STATUS     mandatory
   DESCRIPTION
     "An entry in the trkPktBpTable."
   INDEX {
      trkIndex,
      trkPktBpIndex }
::= { trkPktBpTable 1 }

TrkPktBpEntry ::= SEQUENCE {
   trkPktBpIndex
      INTEGER,
   trkPktBpValue
      PassportCounter64 }

trkPktBpIndex OBJECT-TYPE
   SYNTAX     INTEGER  {
                 ep0(0),
                 ep1(1),
                 ep2(2) }
   ACCESS     not-accessible
   STATUS     mandatory
   DESCRIPTION
     "This variable represents the trkPktBpTable
      specific index for the trkPktBpTable."
::= { trkPktBpEntry 1 }

trkPktBpValue OBJECT-TYPE
   SYNTAX     PassportCounter64 
   ACCESS     read-only
   STATUS     mandatory
   DESCRIPTION
     "This variable represents an individual value for the
      trkPktBpTable."
::= { trkPktBpEntry 2 }

trkDiscBpTable OBJECT-TYPE
   SYNTAX     SEQUENCE OF TrkDiscBpEntry
   ACCESS     not-accessible
   STATUS     mandatory
   DESCRIPTION
     "This attribute counts the number of packets received from the 
      remote module that have been discarded. It is a vector indexed by 
      the emission priorities (ep0, ep1 and ep2) of the packets. The 
      highest emission priority is ep0. These counters wrap around to zero 
      when the maximum value is exceeded.
      Two main reasons that cause this counter to increment are: 
      (1) the remote protocol is not compatible to the local protocol stack 
      and, 
      (2) the packet cannot be forwarded due to either a recent loss of 
      connectivity or due to congestion.
      DESCRIPTION"
::= { trk 369 }

trkDiscBpEntry OBJECT-TYPE
   SYNTAX     TrkDiscBpEntry
   ACCESS     not-accessible
   STATUS     mandatory
   DESCRIPTION
     "An entry in the trkDiscBpTable."
   INDEX {
      trkIndex,
      trkDiscBpIndex }
::= { trkDiscBpTable 1 }

TrkDiscBpEntry ::= SEQUENCE {
   trkDiscBpIndex
      INTEGER,
   trkDiscBpValue
      PassportCounter64 }

trkDiscBpIndex OBJECT-TYPE
   SYNTAX     INTEGER  {
                 ep0(0),
                 ep1(1),
                 ep2(2) }
   ACCESS     not-accessible
   STATUS     mandatory
   DESCRIPTION
     "This variable represents the trkDiscBpTable
      specific index for the trkDiscBpTable."
::= { trkDiscBpEntry 1 }

trkDiscBpValue OBJECT-TYPE
   SYNTAX     PassportCounter64 
   ACCESS     read-only
   STATUS     mandatory
   DESCRIPTION
     "This variable represents an individual value for the
      trkDiscBpTable."
::= { trkDiscBpEntry 2 }

trkOctBpTable OBJECT-TYPE
   SYNTAX     SEQUENCE OF TrkOctBpEntry
   ACCESS     not-accessible
   STATUS     mandatory
   DESCRIPTION
     "This attribute counts the octets coming from the remote module 
      which are received by the Trunk. It is a vector indexed by the 
      emission priorities (ep0, ep1 and ep2) of the packets. The highest 
      emission priority is ep0. These counters wrap around to zero when 
      the maximum value is exceeded."
::= { trk 370 }

trkOctBpEntry OBJECT-TYPE
   SYNTAX     TrkOctBpEntry
   ACCESS     not-accessible
   STATUS     mandatory
   DESCRIPTION
     "An entry in the trkOctBpTable."
   INDEX {
      trkIndex,
      trkOctBpIndex }
::= { trkOctBpTable 1 }

TrkOctBpEntry ::= SEQUENCE {
   trkOctBpIndex
      INTEGER,
   trkOctBpValue
      PassportCounter64 }

trkOctBpIndex OBJECT-TYPE
   SYNTAX     INTEGER  {
                 ep0(0),
                 ep1(1),
                 ep2(2) }
   ACCESS     not-accessible
   STATUS     mandatory
   DESCRIPTION
     "This variable represents the trkOctBpTable
      specific index for the trkOctBpTable."
::= { trkOctBpEntry 1 }

trkOctBpValue OBJECT-TYPE
   SYNTAX     PassportCounter64 
   ACCESS     read-only
   STATUS     mandatory
   DESCRIPTION
     "This variable represents an individual value for the
      trkOctBpTable."
::= { trkOctBpEntry 2 }


-- Trunk/n PorsStatistics
-- This is a dynamic subcomponent of a Trunk which appears when a 
-- PathAdmin component is provisioned under the Trunk supporting 
-- interrupting priority queue. It contains statistics associated with 
-- PORS traffic for a Trunk component.

trkPorsStats OBJECT IDENTIFIER ::= { trk 6 }



trkPorsStatsRowStatusTable OBJECT-TYPE
   SYNTAX     SEQUENCE OF TrkPorsStatsRowStatusEntry
   ACCESS     not-accessible
   STATUS     mandatory
   DESCRIPTION
     "This entry controls the addition and deletion of 
      trkPorsStats components."
::= { trkPorsStats 1 }

trkPorsStatsRowStatusEntry OBJECT-TYPE
   SYNTAX     TrkPorsStatsRowStatusEntry
   ACCESS     not-accessible
   STATUS     mandatory
   DESCRIPTION
     "A single entry in the table represents a single 
      trkPorsStats component."
   INDEX {
      trkIndex,
      trkPorsStatsIndex }
::= { trkPorsStatsRowStatusTable 1 }

TrkPorsStatsRowStatusEntry ::= SEQUENCE {
   trkPorsStatsRowStatus
      RowStatus,
   trkPorsStatsComponentName
      DisplayString,
   trkPorsStatsStorageType
      StorageType,
   trkPorsStatsIndex
      NonReplicated }

trkPorsStatsRowStatus OBJECT-TYPE
   SYNTAX     RowStatus 
   ACCESS     read-only
   STATUS     mandatory
   DESCRIPTION
     "This variable is used as the basis for SNMP naming of
      trkPorsStats components.
      These components cannot be added nor deleted."
::= { trkPorsStatsRowStatusEntry 1 }

trkPorsStatsComponentName OBJECT-TYPE
   SYNTAX     DisplayString 
   ACCESS     read-only
   STATUS     mandatory
   DESCRIPTION
     "This variable provides the component's string name for
      use with the ASCII Console Interface"
::= { trkPorsStatsRowStatusEntry 2 }

trkPorsStatsStorageType OBJECT-TYPE
   SYNTAX     StorageType 
   ACCESS     read-only
   STATUS     mandatory
   DESCRIPTION
     "This variable represents the storage type value for the
      trkPorsStats tables."
::= { trkPorsStatsRowStatusEntry 4 }

trkPorsStatsIndex OBJECT-TYPE
   SYNTAX     NonReplicated 
   ACCESS     not-accessible
   STATUS     mandatory
   DESCRIPTION
     "This variable represents the index for the trkPorsStats tables."
::= { trkPorsStatsRowStatusEntry 10 }

trkPorsStatsOperTable OBJECT-TYPE
   SYNTAX     SEQUENCE OF TrkPorsStatsOperEntry
   ACCESS     not-accessible
   STATUS     mandatory
   DESCRIPTION
     "This operational group provides the PORS Trunks interrupting and 
      normal traffic statistics for operator console display."
::= { trkPorsStats 10 }

trkPorsStatsOperEntry OBJECT-TYPE
   SYNTAX     TrkPorsStatsOperEntry
   ACCESS     not-accessible
   STATUS     mandatory
   DESCRIPTION
     "An entry in the trkPorsStatsOperTable."
   INDEX {
      trkIndex,
      trkPorsStatsIndex }
::= { trkPorsStatsOperTable 1 }

TrkPorsStatsOperEntry ::= SEQUENCE {
   trkPorsStatsPorsNormPktFromIf
      PassportCounter64,
   trkPorsStatsPorsNormDiscUnforwardFromIf
      PassportCounter64,
   trkPorsStatsPorsNormOctetFromIf
      PassportCounter64,
   trkPorsStatsPorsIntPktFromIf
      PassportCounter64,
   trkPorsStatsPorsIntDiscUnforwardFromIf
      PassportCounter64,
   trkPorsStatsPorsIntOctetFromIf
      PassportCounter64 }

trkPorsStatsPorsNormPktFromIf OBJECT-TYPE
   SYNTAX     PassportCounter64 
   ACCESS     read-only
   STATUS     mandatory
   DESCRIPTION
     "This attribute counts the number of normal priority packets received 
      on the PORS Trunk normal priority queue. This counter wraps 
      around to zero when the maximum value is exceeded."
::= { trkPorsStatsOperEntry 1 }

trkPorsStatsPorsNormDiscUnforwardFromIf OBJECT-TYPE
   SYNTAX     PassportCounter64 
   ACCESS     read-only
   STATUS     mandatory
   DESCRIPTION
     "This attribute counts the number of normal priority packets 
      discarded from the PORS Trunk normal priority queue. This 
      counter wraps around to zero when the maximum value is 
      exceeded."
::= { trkPorsStatsOperEntry 2 }

trkPorsStatsPorsNormOctetFromIf OBJECT-TYPE
   SYNTAX     PassportCounter64 
   ACCESS     read-only
   STATUS     mandatory
   DESCRIPTION
     "This attribute counts the number of normal priority bytes received 
      on the PORS Trunk normal priority queue.This counter wraps 
      around to zero when the maximum value is exceeded."
::= { trkPorsStatsOperEntry 3 }

trkPorsStatsPorsIntPktFromIf OBJECT-TYPE
   SYNTAX     PassportCounter64 
   ACCESS     read-only
   STATUS     mandatory
   DESCRIPTION
     "This attribute counts the number of interrupting priority packets 
      received on the PORS Trunk interrupting priority queue. This 
      counter wraps around to zero when the maximum value is 
      exceeded."
::= { trkPorsStatsOperEntry 4 }

trkPorsStatsPorsIntDiscUnforwardFromIf OBJECT-TYPE
   SYNTAX     PassportCounter64 
   ACCESS     read-only
   STATUS     mandatory
   DESCRIPTION
     "This attribute counts the number of interrupting priority packets 
      discarded from the PORS Trunk interrupting priority queue. This 
      counter wraps around to zero when the maximum value is 
      exceeded."
::= { trkPorsStatsOperEntry 5 }

trkPorsStatsPorsIntOctetFromIf OBJECT-TYPE
   SYNTAX     PassportCounter64 
   ACCESS     read-only
   STATUS     mandatory
   DESCRIPTION
     "This attribute counts the number of interrupting priority bytes 
      received on the PORS Trunk interrupting priority queue. This 
      counter wraps around to zero when the maximum value is 
      exceeded."
::= { trkPorsStatsOperEntry 6 }

trkPorsStatsPktBpTable OBJECT-TYPE
   SYNTAX     SEQUENCE OF TrkPorsStatsPktBpEntry
   ACCESS     not-accessible
   STATUS     mandatory
   DESCRIPTION
     "This attribute counts the number of PORS packets received by the 
      Trunk. It is an array indexed by the emission priorities (ep0, ep1 and 
      ep2) and discard priorities (dp0, dp1, dp2 and dp3) of the packets. 
      The highest emission priority is ep0 and the least discardable 
      priority is dp0. These counters wrap around to zero when the 
      maximum value is exceeded."
::= { trkPorsStats 371 }

trkPorsStatsPktBpEntry OBJECT-TYPE
   SYNTAX     TrkPorsStatsPktBpEntry
   ACCESS     not-accessible
   STATUS     mandatory
   DESCRIPTION
     "An entry in the trkPorsStatsPktBpTable."
   INDEX {
      trkIndex,
      trkPorsStatsIndex,
      trkPorsStatsPktBpEpIndex,
      trkPorsStatsPktBpDpIndex }
::= { trkPorsStatsPktBpTable 1 }

TrkPorsStatsPktBpEntry ::= SEQUENCE {
   trkPorsStatsPktBpEpIndex
      INTEGER,
   trkPorsStatsPktBpDpIndex
      INTEGER,
   trkPorsStatsPktBpValue
      PassportCounter64 }

trkPorsStatsPktBpEpIndex OBJECT-TYPE
   SYNTAX     INTEGER  {
                 ep0(0),
                 ep1(1),
                 ep2(2) }
   ACCESS     not-accessible
   STATUS     mandatory
   DESCRIPTION
     "This variable represents the next to last index for the 
      trkPorsStatsPktBpTable."
::= { trkPorsStatsPktBpEntry 1 }

trkPorsStatsPktBpDpIndex OBJECT-TYPE
   SYNTAX     INTEGER  {
                 dp0(0),
                 dp1(1),
                 dp2(2),
                 dp3(3) }
   ACCESS     not-accessible
   STATUS     mandatory
   DESCRIPTION
     "This variable represents the final index for the 
      trkPorsStatsPktBpTable."
::= { trkPorsStatsPktBpEntry 2 }

trkPorsStatsPktBpValue OBJECT-TYPE
   SYNTAX     PassportCounter64 
   ACCESS     read-only
   STATUS     mandatory
   DESCRIPTION
     "This variable represents an individual value for the
      trkPorsStatsPktBpTable."
::= { trkPorsStatsPktBpEntry 3 }

trkPorsStatsDiscBpTable OBJECT-TYPE
   SYNTAX     SEQUENCE OF TrkPorsStatsDiscBpEntry
   ACCESS     not-accessible
   STATUS     mandatory
   DESCRIPTION
     "This attribute counts the number of PORS packets received from the 
      remote module that have been discarded. It is an array indexed by 
      the emission priorities (ep0, ep1 and ep2) and discard priorities (dp0, 
      dp1, dp2 and dp3) of the packets. The highest emission priority is 
      ep0 and the least discardable priority is dp0. These counters wrap 
      around to zero when the maximum value is exceeded."
::= { trkPorsStats 372 }

trkPorsStatsDiscBpEntry OBJECT-TYPE
   SYNTAX     TrkPorsStatsDiscBpEntry
   ACCESS     not-accessible
   STATUS     mandatory
   DESCRIPTION
     "An entry in the trkPorsStatsDiscBpTable."
   INDEX {
      trkIndex,
      trkPorsStatsIndex,
      trkPorsStatsDiscBpEpIndex,
      trkPorsStatsDiscBpDpIndex }
::= { trkPorsStatsDiscBpTable 1 }

TrkPorsStatsDiscBpEntry ::= SEQUENCE {
   trkPorsStatsDiscBpEpIndex
      INTEGER,
   trkPorsStatsDiscBpDpIndex
      INTEGER,
   trkPorsStatsDiscBpValue
      PassportCounter64 }

trkPorsStatsDiscBpEpIndex OBJECT-TYPE
   SYNTAX     INTEGER  {
                 ep0(0),
                 ep1(1),
                 ep2(2) }
   ACCESS     not-accessible
   STATUS     mandatory
   DESCRIPTION
     "This variable represents the next to last index for the 
      trkPorsStatsDiscBpTable."
::= { trkPorsStatsDiscBpEntry 1 }

trkPorsStatsDiscBpDpIndex OBJECT-TYPE
   SYNTAX     INTEGER  {
                 dp0(0),
                 dp1(1),
                 dp2(2),
                 dp3(3) }
   ACCESS     not-accessible
   STATUS     mandatory
   DESCRIPTION
     "This variable represents the final index for the 
      trkPorsStatsDiscBpTable."
::= { trkPorsStatsDiscBpEntry 2 }

trkPorsStatsDiscBpValue OBJECT-TYPE
   SYNTAX     PassportCounter64 
   ACCESS     read-only
   STATUS     mandatory
   DESCRIPTION
     "This variable represents an individual value for the
      trkPorsStatsDiscBpTable."
::= { trkPorsStatsDiscBpEntry 3 }

trkPorsStatsOctBpTable OBJECT-TYPE
   SYNTAX     SEQUENCE OF TrkPorsStatsOctBpEntry
   ACCESS     not-accessible
   STATUS     mandatory
   DESCRIPTION
     "This attribute counts the number of PORS octets received by the 
      Trunk. It is an array indexed by the emission priorities (ep0, ep1 and 
      ep2) and discard priorities (dp0, dp1, dp2 and dp3) of the packets. 
      The highest emission priority is ep0 and the least discardable 
      priority is dp0. These counters wrap around to zero when the 
      maximum value is exceeded."
::= { trkPorsStats 373 }

trkPorsStatsOctBpEntry OBJECT-TYPE
   SYNTAX     TrkPorsStatsOctBpEntry
   ACCESS     not-accessible
   STATUS     mandatory
   DESCRIPTION
     "An entry in the trkPorsStatsOctBpTable."
   INDEX {
      trkIndex,
      trkPorsStatsIndex,
      trkPorsStatsOctBpEpIndex,
      trkPorsStatsOctBpDpIndex }
::= { trkPorsStatsOctBpTable 1 }

TrkPorsStatsOctBpEntry ::= SEQUENCE {
   trkPorsStatsOctBpEpIndex
      INTEGER,
   trkPorsStatsOctBpDpIndex
      INTEGER,
   trkPorsStatsOctBpValue
      PassportCounter64 }

trkPorsStatsOctBpEpIndex OBJECT-TYPE
   SYNTAX     INTEGER  {
                 ep0(0),
                 ep1(1),
                 ep2(2) }
   ACCESS     not-accessible
   STATUS     mandatory
   DESCRIPTION
     "This variable represents the next to last index for the 
      trkPorsStatsOctBpTable."
::= { trkPorsStatsOctBpEntry 1 }

trkPorsStatsOctBpDpIndex OBJECT-TYPE
   SYNTAX     INTEGER  {
                 dp0(0),
                 dp1(1),
                 dp2(2),
                 dp3(3) }
   ACCESS     not-accessible
   STATUS     mandatory
   DESCRIPTION
     "This variable represents the final index for the 
      trkPorsStatsOctBpTable."
::= { trkPorsStatsOctBpEntry 2 }

trkPorsStatsOctBpValue OBJECT-TYPE
   SYNTAX     PassportCounter64 
   ACCESS     read-only
   STATUS     mandatory
   DESCRIPTION
     "This variable represents an individual value for the
      trkPorsStatsOctBpTable."
::= { trkPorsStatsOctBpEntry 3 }


-- Trunk/n ForwardingStatistics
-- This is a dynamic subcomponent of a Trunk or DpnGateway which 
-- appears when packet forwarding traffic is used over the Trunk or 
-- DpnGateway. It contains statistics associated with packet 
-- forwarding traffic for Trunks and DpnGateways.

trkFwdStats OBJECT IDENTIFIER ::= { trk 7 }



trkFwdStatsRowStatusTable OBJECT-TYPE
   SYNTAX     SEQUENCE OF TrkFwdStatsRowStatusEntry
   ACCESS     not-accessible
   STATUS     mandatory
   DESCRIPTION
     "This entry controls the addition and deletion of 
      trkFwdStats components."
::= { trkFwdStats 1 }

trkFwdStatsRowStatusEntry OBJECT-TYPE
   SYNTAX     TrkFwdStatsRowStatusEntry
   ACCESS     not-accessible
   STATUS     mandatory
   DESCRIPTION
     "A single entry in the table represents a single 
      trkFwdStats component."
   INDEX {
      trkIndex,
      trkFwdStatsIndex }
::= { trkFwdStatsRowStatusTable 1 }

TrkFwdStatsRowStatusEntry ::= SEQUENCE {
   trkFwdStatsRowStatus
      RowStatus,
   trkFwdStatsComponentName
      DisplayString,
   trkFwdStatsStorageType
      StorageType,
   trkFwdStatsIndex
      NonReplicated }

trkFwdStatsRowStatus OBJECT-TYPE
   SYNTAX     RowStatus 
   ACCESS     read-only
   STATUS     mandatory
   DESCRIPTION
     "This variable is used as the basis for SNMP naming of
      trkFwdStats components.
      These components cannot be added nor deleted."
::= { trkFwdStatsRowStatusEntry 1 }

trkFwdStatsComponentName OBJECT-TYPE
   SYNTAX     DisplayString 
   ACCESS     read-only
   STATUS     mandatory
   DESCRIPTION
     "This variable provides the component's string name for
      use with the ASCII Console Interface"
::= { trkFwdStatsRowStatusEntry 2 }

trkFwdStatsStorageType OBJECT-TYPE
   SYNTAX     StorageType 
   ACCESS     read-only
   STATUS     mandatory
   DESCRIPTION
     "This variable represents the storage type value for the
      trkFwdStats tables."
::= { trkFwdStatsRowStatusEntry 4 }

trkFwdStatsIndex OBJECT-TYPE
   SYNTAX     NonReplicated 
   ACCESS     not-accessible
   STATUS     mandatory
   DESCRIPTION
     "This variable represents the index for the trkFwdStats tables."
::= { trkFwdStatsRowStatusEntry 10 }

trkFwdStatsOperTable OBJECT-TYPE
   SYNTAX     SEQUENCE OF TrkFwdStatsOperEntry
   ACCESS     not-accessible
   STATUS     mandatory
   DESCRIPTION
     "This operational group counts the Trunk or DpnGateway packet 
      forwarding traffic statistics for operator console display."
::= { trkFwdStats 10 }

trkFwdStatsOperEntry OBJECT-TYPE
   SYNTAX     TrkFwdStatsOperEntry
   ACCESS     not-accessible
   STATUS     mandatory
   DESCRIPTION
     "An entry in the trkFwdStatsOperTable."
   INDEX {
      trkIndex,
      trkFwdStatsIndex }
::= { trkFwdStatsOperTable 1 }

TrkFwdStatsOperEntry ::= SEQUENCE {
   trkFwdStatsFwdPktFromIf
      PassportCounter64,
   trkFwdStatsFwdDiscUnforwardFromIf
      PassportCounter64,
   trkFwdStatsFwdOctetFromIf
      PassportCounter64 }

trkFwdStatsFwdPktFromIf OBJECT-TYPE
   SYNTAX     PassportCounter64 
   ACCESS     read-only
   STATUS     mandatory
   DESCRIPTION
     "This attribute counts the number of forwarding packets received by 
      the Trunk or DpnGateway. This counter wraps around to zero when 
      the maximum value is exceeded."
::= { trkFwdStatsOperEntry 1 }

trkFwdStatsFwdDiscUnforwardFromIf OBJECT-TYPE
   SYNTAX     PassportCounter64 
   ACCESS     read-only
   STATUS     mandatory
   DESCRIPTION
     "This attribute counts the number of forwarding packets discarded by 
      the Trunk or DpnGateway. This counter wraps around to zero when 
      the maximum value is exceeded."
::= { trkFwdStatsOperEntry 2 }

trkFwdStatsFwdOctetFromIf OBJECT-TYPE
   SYNTAX     PassportCounter64 
   ACCESS     read-only
   STATUS     mandatory
   DESCRIPTION
     "This attribute counts the number of forwarding bytes received by 
      the Trunk or DpnGateway. This counter wraps around to zero when 
      the maximum value is exceeded."
::= { trkFwdStatsOperEntry 3 }


-- Trunk/n VirtualNetworkStatistics
-- This is a dynamic subcomponent of a Trunk which appears when 
-- virtual networking system (VNS) traffic is used over the Trunk. It 
-- contains statistics associated with virtual traffic network for the 
-- Trunk.

trkVnsStats OBJECT IDENTIFIER ::= { trk 8 }



trkVnsStatsRowStatusTable OBJECT-TYPE
   SYNTAX     SEQUENCE OF TrkVnsStatsRowStatusEntry
   ACCESS     not-accessible
   STATUS     mandatory
   DESCRIPTION
     "This entry controls the addition and deletion of 
      trkVnsStats components."
::= { trkVnsStats 1 }

trkVnsStatsRowStatusEntry OBJECT-TYPE
   SYNTAX     TrkVnsStatsRowStatusEntry
   ACCESS     not-accessible
   STATUS     mandatory
   DESCRIPTION
     "A single entry in the table represents a single 
      trkVnsStats component."
   INDEX {
      trkIndex,
      trkVnsStatsIndex }
::= { trkVnsStatsRowStatusTable 1 }

TrkVnsStatsRowStatusEntry ::= SEQUENCE {
   trkVnsStatsRowStatus
      RowStatus,
   trkVnsStatsComponentName
      DisplayString,
   trkVnsStatsStorageType
      StorageType,
   trkVnsStatsIndex
      NonReplicated }

trkVnsStatsRowStatus OBJECT-TYPE
   SYNTAX     RowStatus 
   ACCESS     read-only
   STATUS     mandatory
   DESCRIPTION
     "This variable is used as the basis for SNMP naming of
      trkVnsStats components.
      These components cannot be added nor deleted."
::= { trkVnsStatsRowStatusEntry 1 }

trkVnsStatsComponentName OBJECT-TYPE
   SYNTAX     DisplayString 
   ACCESS     read-only
   STATUS     mandatory
   DESCRIPTION
     "This variable provides the component's string name for
      use with the ASCII Console Interface"
::= { trkVnsStatsRowStatusEntry 2 }

trkVnsStatsStorageType OBJECT-TYPE
   SYNTAX     StorageType 
   ACCESS     read-only
   STATUS     mandatory
   DESCRIPTION
     "This variable represents the storage type value for the
      trkVnsStats tables."
::= { trkVnsStatsRowStatusEntry 4 }

trkVnsStatsIndex OBJECT-TYPE
   SYNTAX     NonReplicated 
   ACCESS     not-accessible
   STATUS     mandatory
   DESCRIPTION
     "This variable represents the index for the trkVnsStats tables."
::= { trkVnsStatsRowStatusEntry 10 }

trkVnsStatsOperTable OBJECT-TYPE
   SYNTAX     SEQUENCE OF TrkVnsStatsOperEntry
   ACCESS     not-accessible
   STATUS     mandatory
   DESCRIPTION
     "This operational group counts the Trunk virtual network traffic 
      statistics for operator console display."
::= { trkVnsStats 10 }

trkVnsStatsOperEntry OBJECT-TYPE
   SYNTAX     TrkVnsStatsOperEntry
   ACCESS     not-accessible
   STATUS     mandatory
   DESCRIPTION
     "An entry in the trkVnsStatsOperTable."
   INDEX {
      trkIndex,
      trkVnsStatsIndex }
::= { trkVnsStatsOperTable 1 }

TrkVnsStatsOperEntry ::= SEQUENCE {
   trkVnsStatsVnsPktFromIf
      PassportCounter64,
   trkVnsStatsVnsDiscUnforwardFromIf
      PassportCounter64,
   trkVnsStatsVnsOctetFromIf
      PassportCounter64 }

trkVnsStatsVnsPktFromIf OBJECT-TYPE
   SYNTAX     PassportCounter64 
   ACCESS     read-only
   STATUS     mandatory
   DESCRIPTION
     "This attribute counts the number of virtual network packets received 
      by a Trunk component handling virtual network traffic. This counter 
      wraps around to zero when the maximum value is exceeded."
::= { trkVnsStatsOperEntry 1 }

trkVnsStatsVnsDiscUnforwardFromIf OBJECT-TYPE
   SYNTAX     PassportCounter64 
   ACCESS     read-only
   STATUS     mandatory
   DESCRIPTION
     "This attribute counts the number of virtual network packets 
      discarded by a Trunk component handling virtual network traffic. 
      This counter wraps around to zero when the maximum value is 
      exceeded."
::= { trkVnsStatsOperEntry 2 }

trkVnsStatsVnsOctetFromIf OBJECT-TYPE
   SYNTAX     PassportCounter64 
   ACCESS     read-only
   STATUS     mandatory
   DESCRIPTION
     "This attribute counts the number of virtual network bytes received 
      by a Trunk component handling virtual network traffic. This counter 
      wraps around to zero when the maximum value is exceeded."
::= { trkVnsStatsOperEntry 3 }

trkVnsStatsPktBpTable OBJECT-TYPE
   SYNTAX     SEQUENCE OF TrkVnsStatsPktBpEntry
   ACCESS     not-accessible
   STATUS     mandatory
   DESCRIPTION
     "This attribute counts the number of Virtual Network packets 
      received by the Trunk. It is an array indexed by the emission 
      priorities (ep0, ep1 and ep2) and discard priorities (dp0, dp1, dp2 
      and dp3) of the packets. The highest emission priority is ep0 and the 
      least discardable priority is dp0. These counters wrap around to zero 
      when the maximum value is exceeded."
::= { trkVnsStats 377 }

trkVnsStatsPktBpEntry OBJECT-TYPE
   SYNTAX     TrkVnsStatsPktBpEntry
   ACCESS     not-accessible
   STATUS     mandatory
   DESCRIPTION
     "An entry in the trkVnsStatsPktBpTable."
   INDEX {
      trkIndex,
      trkVnsStatsIndex,
      trkVnsStatsPktBpEpIndex,
      trkVnsStatsPktBpDpIndex }
::= { trkVnsStatsPktBpTable 1 }

TrkVnsStatsPktBpEntry ::= SEQUENCE {
   trkVnsStatsPktBpEpIndex
      INTEGER,
   trkVnsStatsPktBpDpIndex
      INTEGER,
   trkVnsStatsPktBpValue
      PassportCounter64 }

trkVnsStatsPktBpEpIndex OBJECT-TYPE
   SYNTAX     INTEGER  {
                 ep0(0),
                 ep1(1),
                 ep2(2) }
   ACCESS     not-accessible
   STATUS     mandatory
   DESCRIPTION
     "This variable represents the next to last index for the 
      trkVnsStatsPktBpTable."
::= { trkVnsStatsPktBpEntry 1 }

trkVnsStatsPktBpDpIndex OBJECT-TYPE
   SYNTAX     INTEGER  {
                 dp0(0),
                 dp1(1),
                 dp2(2),
                 dp3(3) }
   ACCESS     not-accessible
   STATUS     mandatory
   DESCRIPTION
     "This variable represents the final index for the 
      trkVnsStatsPktBpTable."
::= { trkVnsStatsPktBpEntry 2 }

trkVnsStatsPktBpValue OBJECT-TYPE
   SYNTAX     PassportCounter64 
   ACCESS     read-only
   STATUS     mandatory
   DESCRIPTION
     "This variable represents an individual value for the
      trkVnsStatsPktBpTable."
::= { trkVnsStatsPktBpEntry 3 }

trkVnsStatsDiscBpTable OBJECT-TYPE
   SYNTAX     SEQUENCE OF TrkVnsStatsDiscBpEntry
   ACCESS     not-accessible
   STATUS     mandatory
   DESCRIPTION
     "This attribute counts the number of Virtual Network packets 
      received from the remote module that have been discarded by the 
      Trunk. It is an array indexed by the emission priorities (ep0, ep1 and 
      ep2) and discard priorities (dp0, dp1, dp2 and dp3) of the packets. 
      The highest emission priority is ep0 and the least discardable 
      priority is dp0. These counters wrap around to zero when the 
      maximum value is exceeded."
::= { trkVnsStats 378 }

trkVnsStatsDiscBpEntry OBJECT-TYPE
   SYNTAX     TrkVnsStatsDiscBpEntry
   ACCESS     not-accessible
   STATUS     mandatory
   DESCRIPTION
     "An entry in the trkVnsStatsDiscBpTable."
   INDEX {
      trkIndex,
      trkVnsStatsIndex,
      trkVnsStatsDiscBpEpIndex,
      trkVnsStatsDiscBpDpIndex }
::= { trkVnsStatsDiscBpTable 1 }

TrkVnsStatsDiscBpEntry ::= SEQUENCE {
   trkVnsStatsDiscBpEpIndex
      INTEGER,
   trkVnsStatsDiscBpDpIndex
      INTEGER,
   trkVnsStatsDiscBpValue
      PassportCounter64 }

trkVnsStatsDiscBpEpIndex OBJECT-TYPE
   SYNTAX     INTEGER  {
                 ep0(0),
                 ep1(1),
                 ep2(2) }
   ACCESS     not-accessible
   STATUS     mandatory
   DESCRIPTION
     "This variable represents the next to last index for the 
      trkVnsStatsDiscBpTable."
::= { trkVnsStatsDiscBpEntry 1 }

trkVnsStatsDiscBpDpIndex OBJECT-TYPE
   SYNTAX     INTEGER  {
                 dp0(0),
                 dp1(1),
                 dp2(2),
                 dp3(3) }
   ACCESS     not-accessible
   STATUS     mandatory
   DESCRIPTION
     "This variable represents the final index for the 
      trkVnsStatsDiscBpTable."
::= { trkVnsStatsDiscBpEntry 2 }

trkVnsStatsDiscBpValue OBJECT-TYPE
   SYNTAX     PassportCounter64 
   ACCESS     read-only
   STATUS     mandatory
   DESCRIPTION
     "This variable represents an individual value for the
      trkVnsStatsDiscBpTable."
::= { trkVnsStatsDiscBpEntry 3 }

trkVnsStatsOctBpTable OBJECT-TYPE
   SYNTAX     SEQUENCE OF TrkVnsStatsOctBpEntry
   ACCESS     not-accessible
   STATUS     mandatory
   DESCRIPTION
     "This attribute counts the number of Virtual Network octets received 
      by the Trunk. It is an array indexed by the emission priorities (ep0, 
      ep1 and ep2) and discard priorities (dp0, dp1, dp2 and dp3) of the 
      packets. The highest emission priority is ep0 and the least 
      discardable priority is dp0. These counters wrap around to zero 
      when the maximum value is exceeded."
::= { trkVnsStats 379 }

trkVnsStatsOctBpEntry OBJECT-TYPE
   SYNTAX     TrkVnsStatsOctBpEntry
   ACCESS     not-accessible
   STATUS     mandatory
   DESCRIPTION
     "An entry in the trkVnsStatsOctBpTable."
   INDEX {
      trkIndex,
      trkVnsStatsIndex,
      trkVnsStatsOctBpEpIndex,
      trkVnsStatsOctBpDpIndex }
::= { trkVnsStatsOctBpTable 1 }

TrkVnsStatsOctBpEntry ::= SEQUENCE {
   trkVnsStatsOctBpEpIndex
      INTEGER,
   trkVnsStatsOctBpDpIndex
      INTEGER,
   trkVnsStatsOctBpValue
      PassportCounter64 }

trkVnsStatsOctBpEpIndex OBJECT-TYPE
   SYNTAX     INTEGER  {
                 ep0(0),
                 ep1(1),
                 ep2(2) }
   ACCESS     not-accessible
   STATUS     mandatory
   DESCRIPTION
     "This variable represents the next to last index for the 
      trkVnsStatsOctBpTable."
::= { trkVnsStatsOctBpEntry 1 }

trkVnsStatsOctBpDpIndex OBJECT-TYPE
   SYNTAX     INTEGER  {
                 dp0(0),
                 dp1(1),
                 dp2(2),
                 dp3(3) }
   ACCESS     not-accessible
   STATUS     mandatory
   DESCRIPTION
     "This variable represents the final index for the 
      trkVnsStatsOctBpTable."
::= { trkVnsStatsOctBpEntry 2 }

trkVnsStatsOctBpValue OBJECT-TYPE
   SYNTAX     PassportCounter64 
   ACCESS     read-only
   STATUS     mandatory
   DESCRIPTION
     "This variable represents an individual value for the
      trkVnsStatsOctBpTable."
::= { trkVnsStatsOctBpEntry 3 }


-- Trunk/n DprsStatistics
-- This is a dynamic subcomponent of a Trunk which appears when 
-- DPRS traffic is used over the Trunk. It contains statistics associated 
-- with packet forwarding traffic for Trunks.

trkDprsStats OBJECT IDENTIFIER ::= { trk 10 }



trkDprsStatsRowStatusTable OBJECT-TYPE
   SYNTAX     SEQUENCE OF TrkDprsStatsRowStatusEntry
   ACCESS     not-accessible
   STATUS     mandatory
   DESCRIPTION
     "This entry controls the addition and deletion of 
      trkDprsStats components."
::= { trkDprsStats 1 }

trkDprsStatsRowStatusEntry OBJECT-TYPE
   SYNTAX     TrkDprsStatsRowStatusEntry
   ACCESS     not-accessible
   STATUS     mandatory
   DESCRIPTION
     "A single entry in the table represents a single 
      trkDprsStats component."
   INDEX {
      trkIndex,
      trkDprsStatsIndex }
::= { trkDprsStatsRowStatusTable 1 }

TrkDprsStatsRowStatusEntry ::= SEQUENCE {
   trkDprsStatsRowStatus
      RowStatus,
   trkDprsStatsComponentName
      DisplayString,
   trkDprsStatsStorageType
      StorageType,
   trkDprsStatsIndex
      NonReplicated }

trkDprsStatsRowStatus OBJECT-TYPE
   SYNTAX     RowStatus 
   ACCESS     read-only
   STATUS     mandatory
   DESCRIPTION
     "This variable is used as the basis for SNMP naming of
      trkDprsStats components.
      These components cannot be added nor deleted."
::= { trkDprsStatsRowStatusEntry 1 }

trkDprsStatsComponentName OBJECT-TYPE
   SYNTAX     DisplayString 
   ACCESS     read-only
   STATUS     mandatory
   DESCRIPTION
     "This variable provides the component's string name for
      use with the ASCII Console Interface"
::= { trkDprsStatsRowStatusEntry 2 }

trkDprsStatsStorageType OBJECT-TYPE
   SYNTAX     StorageType 
   ACCESS     read-only
   STATUS     mandatory
   DESCRIPTION
     "This variable represents the storage type value for the
      trkDprsStats tables."
::= { trkDprsStatsRowStatusEntry 4 }

trkDprsStatsIndex OBJECT-TYPE
   SYNTAX     NonReplicated 
   ACCESS     not-accessible
   STATUS     mandatory
   DESCRIPTION
     "This variable represents the index for the trkDprsStats tables."
::= { trkDprsStatsRowStatusEntry 10 }

trkDprsStatsPktBpTable OBJECT-TYPE
   SYNTAX     SEQUENCE OF TrkDprsStatsPktBpEntry
   ACCESS     not-accessible
   STATUS     mandatory
   DESCRIPTION
     "This attribute counts the number of DPRS packets received by the 
      Trunk. It is an array indexed by the emission priorities (ep0, ep1 and 
      ep2) and discard priorities (dp0, dp1, dp2 and dp3) of the packets. 
      The highest emission priority is ep0 and the least discardable 
      priority is dp0. These counters wrap around to zero when the 
      maximum value is exceeded."
::= { trkDprsStats 374 }

trkDprsStatsPktBpEntry OBJECT-TYPE
   SYNTAX     TrkDprsStatsPktBpEntry
   ACCESS     not-accessible
   STATUS     mandatory
   DESCRIPTION
     "An entry in the trkDprsStatsPktBpTable."
   INDEX {
      trkIndex,
      trkDprsStatsIndex,
      trkDprsStatsPktBpEpIndex,
      trkDprsStatsPktBpDpIndex }
::= { trkDprsStatsPktBpTable 1 }

TrkDprsStatsPktBpEntry ::= SEQUENCE {
   trkDprsStatsPktBpEpIndex
      INTEGER,
   trkDprsStatsPktBpDpIndex
      INTEGER,
   trkDprsStatsPktBpValue
      PassportCounter64 }

trkDprsStatsPktBpEpIndex OBJECT-TYPE
   SYNTAX     INTEGER  {
                 ep0(0),
                 ep1(1),
                 ep2(2) }
   ACCESS     not-accessible
   STATUS     mandatory
   DESCRIPTION
     "This variable represents the next to last index for the 
      trkDprsStatsPktBpTable."
::= { trkDprsStatsPktBpEntry 1 }

trkDprsStatsPktBpDpIndex OBJECT-TYPE
   SYNTAX     INTEGER  {
                 dp0(0),
                 dp1(1),
                 dp2(2),
                 dp3(3) }
   ACCESS     not-accessible
   STATUS     mandatory
   DESCRIPTION
     "This variable represents the final index for the 
      trkDprsStatsPktBpTable."
::= { trkDprsStatsPktBpEntry 2 }

trkDprsStatsPktBpValue OBJECT-TYPE
   SYNTAX     PassportCounter64 
   ACCESS     read-only
   STATUS     mandatory
   DESCRIPTION
     "This variable represents an individual value for the
      trkDprsStatsPktBpTable."
::= { trkDprsStatsPktBpEntry 3 }

trkDprsStatsDiscBpTable OBJECT-TYPE
   SYNTAX     SEQUENCE OF TrkDprsStatsDiscBpEntry
   ACCESS     not-accessible
   STATUS     mandatory
   DESCRIPTION
     "This attribute counts the number of DPRS packets received from the 
      remote module that have been discarded by the Trunk. It is an array 
      indexed by the emission priorities (ep0, ep1 and ep2) and discard 
      priorities (dp0, dp1, dp2 and dp3) of the packets. The highest 
      emission priority is ep0 and the least discardable priority is dp0. 
      These counters wrap around to zero when the maximum value is 
      exceeded."
::= { trkDprsStats 375 }

trkDprsStatsDiscBpEntry OBJECT-TYPE
   SYNTAX     TrkDprsStatsDiscBpEntry
   ACCESS     not-accessible
   STATUS     mandatory
   DESCRIPTION
     "An entry in the trkDprsStatsDiscBpTable."
   INDEX {
      trkIndex,
      trkDprsStatsIndex,
      trkDprsStatsDiscBpEpIndex,
      trkDprsStatsDiscBpDpIndex }
::= { trkDprsStatsDiscBpTable 1 }

TrkDprsStatsDiscBpEntry ::= SEQUENCE {
   trkDprsStatsDiscBpEpIndex
      INTEGER,
   trkDprsStatsDiscBpDpIndex
      INTEGER,
   trkDprsStatsDiscBpValue
      PassportCounter64 }

trkDprsStatsDiscBpEpIndex OBJECT-TYPE
   SYNTAX     INTEGER  {
                 ep0(0),
                 ep1(1),
                 ep2(2) }
   ACCESS     not-accessible
   STATUS     mandatory
   DESCRIPTION
     "This variable represents the next to last index for the 
      trkDprsStatsDiscBpTable."
::= { trkDprsStatsDiscBpEntry 1 }

trkDprsStatsDiscBpDpIndex OBJECT-TYPE
   SYNTAX     INTEGER  {
                 dp0(0),
                 dp1(1),
                 dp2(2),
                 dp3(3) }
   ACCESS     not-accessible
   STATUS     mandatory
   DESCRIPTION
     "This variable represents the final index for the 
      trkDprsStatsDiscBpTable."
::= { trkDprsStatsDiscBpEntry 2 }

trkDprsStatsDiscBpValue OBJECT-TYPE
   SYNTAX     PassportCounter64 
   ACCESS     read-only
   STATUS     mandatory
   DESCRIPTION
     "This variable represents an individual value for the
      trkDprsStatsDiscBpTable."
::= { trkDprsStatsDiscBpEntry 3 }

trkDprsStatsOctBpTable OBJECT-TYPE
   SYNTAX     SEQUENCE OF TrkDprsStatsOctBpEntry
   ACCESS     not-accessible
   STATUS     mandatory
   DESCRIPTION
     "This attribute counts the number of DPRS octets received by the 
      Trunk. It is an array indexed by the emission priorities (ep0, ep1 and 
      ep2) and discard priorities (dp0, dp1, dp2 and dp3) of the packets. 
      The highest emission priority is ep0 and the least discardable 
      priority is dp0. These counters wrap around to zero when the 
      maximum value is exceeded."
::= { trkDprsStats 376 }

trkDprsStatsOctBpEntry OBJECT-TYPE
   SYNTAX     TrkDprsStatsOctBpEntry
   ACCESS     not-accessible
   STATUS     mandatory
   DESCRIPTION
     "An entry in the trkDprsStatsOctBpTable."
   INDEX {
      trkIndex,
      trkDprsStatsIndex,
      trkDprsStatsOctBpEpIndex,
      trkDprsStatsOctBpDpIndex }
::= { trkDprsStatsOctBpTable 1 }

TrkDprsStatsOctBpEntry ::= SEQUENCE {
   trkDprsStatsOctBpEpIndex
      INTEGER,
   trkDprsStatsOctBpDpIndex
      INTEGER,
   trkDprsStatsOctBpValue
      PassportCounter64 }

trkDprsStatsOctBpEpIndex OBJECT-TYPE
   SYNTAX     INTEGER  {
                 ep0(0),
                 ep1(1),
                 ep2(2) }
   ACCESS     not-accessible
   STATUS     mandatory
   DESCRIPTION
     "This variable represents the next to last index for the 
      trkDprsStatsOctBpTable."
::= { trkDprsStatsOctBpEntry 1 }

trkDprsStatsOctBpDpIndex OBJECT-TYPE
   SYNTAX     INTEGER  {
                 dp0(0),
                 dp1(1),
                 dp2(2),
                 dp3(3) }
   ACCESS     not-accessible
   STATUS     mandatory
   DESCRIPTION
     "This variable represents the final index for the 
      trkDprsStatsOctBpTable."
::= { trkDprsStatsOctBpEntry 2 }

trkDprsStatsOctBpValue OBJECT-TYPE
   SYNTAX     PassportCounter64 
   ACCESS     read-only
   STATUS     mandatory
   DESCRIPTION
     "This variable represents an individual value for the
      trkDprsStatsOctBpTable."
::= { trkDprsStatsOctBpEntry 3 }




-- 
-- Version and Compliance statements
-- 



-- Object-Group Statement:
-- A list of all current accessible leaf objects.

-- OBJECTS { trkMeasuredSpeedToIf,
--           trkPorsStatsPorsIntOctetFromIf,
--           trkMaxTxUnit,
--           trkDprsStatsComponentName,
--           trkHighSpeedAlarmThreshold,
--           trkPorsStatsPorsNormOctetFromIf,
--           trkDprsStatsDiscBpValue,
--           trkAvailabilityStatus,
--           trkStorageType,
--           trkPorsStatsPorsNormPktFromIf,
--           trkSnmpOperStatus,
--           trkDprsStatsOctBpValue,
--           trkIfIndex,
--           trkVnsStatsVnsDiscUnforwardFromIf,
--           trkAlarmStatus,
--           trkDiscardTrunkPktToIf,
--           trkPorsStatsPktBpValue,
--           trkSpdThValue,
--           trkExpectedRemoteNodeName,
--           trkPorsStatsRowStatus,
--           trkUnknownStatus,
--           trkStandbyStatus,
--           trkIntPktFromIf,
--           trkOverrideTransmitSpeed,
--           trkOverrideRoundTripUsec,
--           trkMeasuredRoundTripDelayUsec,
--           trkTrunkPktToIf,
--           trkVnsStatsVnsPktFromIf,
--           trkStagingAttempts,
--           trkFwdStatsComponentName,
--           trkFwdStatsFwdOctetFromIf,
--           trkRemoteComponentName,
--           trkPorsStatsComponentName,
--           trkRemoteValidationAction,
--           trkPorsStatsPorsNormDiscUnforwardFromIf,
--           trkVnsStatsStorageType,
--           trkPorsStatsPorsIntDiscUnforwardFromIf,
--           trkDiscardUnforward,
--           trkAdminState,
--           trkPorsStatsPorsIntPktFromIf,
--           trkPktBpValue,
--           trkPorsStatsOctBpValue,
--           trkSpeedReportingHoldOff,
--           trkPorsStatsDiscBpValue,
--           trkIfAdminStatus,
--           trkMaximumExpectedRoundTripDelay,
--           trkProceduralStatus,
--           trkDprsStatsStorageType,
--           trkVnsStatsPktBpValue,
--           trkLowSpeedAlarmThreshold,
--           trkVnsStatsRowStatus,
--           trkFwdStatsStorageType,
--           trkSpdThRowStatus,
--           trkRowStatus,
--           trkUsageState,
--           trkDiscardTrunkPktFromIf,
--           trkVnsStatsVnsOctetFromIf,
--           trkFwdStatsFwdDiscUnforwardFromIf,
--           trkComponentName,
--           trkFwdStatsFwdPktFromIf,
--           trkDiscBpValue,
--           trkDprsStatsPktBpValue,
--           trkTrunkPktFromIf,
--           trkUtilization,
--           trkOctBpValue,
--           trkVnsStatsComponentName,
--           trkOperationalState,
--           trkDprsStatsRowStatus,
--           trkPktFromIf,
--           trkAreYouThereModeEntries,
--           trkVnsStatsDiscBpValue,
--           trkDiscardIntUnforward,
--           trkFwdStatsRowStatus,
--           trkControlStatus,
--           trkVnsStatsOctBpValue,
--           trkIdleTimeOut,
--           trkPorsStatsStorageType }
-- STATUS  mandatory
-- DESCRIPTION
--   "A list of all current accessible leaf objects."

trunksGroup OBJECT IDENTIFIER ::= { trunksMIB 1 }
trunksGroupBE OBJECT IDENTIFIER ::= { trunksGroup 5 }
trunksGroupBE00 OBJECT IDENTIFIER ::= { trunksGroupBE 1 }
trunksGroupBE00A OBJECT IDENTIFIER ::= { trunksGroupBE00 2 }



-- Agent-Capabilities Statement:

-- PRODUCT-RELEASE "Passport Release 7.0 Trunks."
-- STATUS          mandatory
-- DESCRIPTION     "Trunks MIB: MIB Version BE00A,
--                  Software Version BG00S4C."
-- SUPPORTS        Nortel-Magellan-Passport-TrunksMIB
--    INCLUDES     { trunksGroupBE00A }

trunksCapabilities OBJECT IDENTIFIER ::= { trunksMIB 3 }
trunksCapabilitiesBE OBJECT IDENTIFIER ::= { trunksCapabilities 5 }
trunksCapabilitiesBE00 OBJECT IDENTIFIER ::= { trunksCapabilitiesBE 1 }
trunksCapabilitiesBE00A OBJECT IDENTIFIER ::= { trunksCapabilitiesBE00 2 }





END
