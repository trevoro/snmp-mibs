--			HDSL2 Enterprise Mib
--
--			Lucent Technologies
--			1275 Harbor Bay Pkwy
--			Alameda, CA 94502
--			+1 510 769 6001
--			info@ascend.com
--
--		Copyright (c) 1993-1999 Lucent Technologies
--		All rights reserved.
--
-- CVS ID:      $Id: hdsl2.mib,v 1.1.2.1 1999/11/30 22:54:34 cmiller Exp $
--
-- 06 Dec 96:	Initial release

	-- Ascend wanTypeHdsl2 group
	--
	-- This group contains MIB variables used to manage the HDSL2
	-- interface

	-- HDSL2 interface status
	--
	-- The below entries contain interface status information. The slot
	-- number and interface are identified via that hdsl2SlotIndex and 
	-- hdsl2LineIndex parameters. 
	--
ASCEND-HDSL2-MIB DEFINITIONS ::= BEGIN

    IMPORTS
	wanTypeHdsl2
	    FROM ASCEND-WAN-MIB
	OBJECT-TYPE
	    FROM RFC-1212;
	
    hdsl2LineStatusTable	OBJECT-TYPE
	SYNTAX		SEQUENCE OF Hdsl2LineStatusEntry
	ACCESS		not-accessible
	STATUS		mandatory
	DESCRIPTION	"HDSL2 status parameters."
	::= { wanTypeHdsl2 1 }

    hdsl2LineStatusEntry	OBJECT-TYPE
	SYNTAX		Hdsl2LineStatusEntry
	ACCESS		not-accessible
	STATUS		mandatory
	DESCRIPTION	"A interface status entry containing objects to describe the
			interface."
	INDEX		{ hdsl2StatusIfEntryIndex }
	::= { hdsl2LineStatusTable 1 }

    Hdsl2LineStatusEntry ::=
	SEQUENCE {
	    hdsl2StatusIfEntryIndex
		INTEGER,
	    hdsl2StatusShelfIndex
	        INTEGER,
	    hdsl2StatusSlotIndex
		INTEGER,
	    hdsl2StatusLineIndex
		INTEGER,
	    hdsl2StatusUnitType
		INTEGER,
	    hdsl2StatusLineState
		INTEGER,
	    hdsl2StatusOpRate
		INTEGER,
	    hdsl2StatusVendorId
		INTEGER,
	    hdsl2StatusMajorFirmWareVer
		INTEGER,
	    hdsl2StatusMinorFirmWareVer
		INTEGER,
	    hdsl2StatusHardWareVer
		INTEGER
	}

   hdsl2StatusIfEntryIndex    OBJECT-TYPE
	SYNTAX		INTEGER	
	ACCESS		read-only
	STATUS		mandatory
	DESCRIPTION	"Interface group index assigned to this port." 
	::= { hdsl2LineStatusEntry 1 }
   
    hdsl2StatusShelfIndex OBJECT-TYPE
	SYNTAX		INTEGER
	ACCESS		read-only
	STATUS		mandatory
	DESCRIPTION	"TNT's HDSL2 modules Shelf ID."
	::= { hdsl2LineStatusEntry 2 }

    hdsl2StatusSlotIndex	OBJECT-TYPE
	SYNTAX		INTEGER
	ACCESS		read-only
	STATUS		mandatory
	DESCRIPTION	"TNT's HDSL2 modules Slot ID."
	::= { hdsl2LineStatusEntry 3 }

    hdsl2StatusLineIndex	OBJECT-TYPE
	SYNTAX		INTEGER
	ACCESS		read-only
	STATUS		mandatory
	DESCRIPTION	"HDSL2 modules line ID." 
	::= { hdsl2LineStatusEntry 4 }

   hdsl2StatusUnitType	OBJECT-TYPE
	SYNTAX		INTEGER {
			    other( 1 ),		-- none of the following
			    coe( 2 ),		-- Central Office Equipment.
			    cpe( 3 )		-- Customer Premises
						-- Equipment. 
			}
	ACCESS		read-only
	STATUS		mandatory
	DESCRIPTION	"Unit type defines if the unit is operating either as a
			Central Office Equipment (COE) or Customer Premiss
			equipment (CPE)."
	::= { hdsl2LineStatusEntry 5 }

   hdsl2StatusLineState	OBJECT-TYPE
	SYNTAX		INTEGER {
				    other( 1 ),		-- none of the following
			    configure( 2 ),	-- Interface is in
						-- Configuration state. 
			    deactivate( 3 ),    -- Port is down. Deactive 
						-- has been issued. 
			    deactive-lost( 4 ), -- Waiting for LOS or LOST 
						-- indication.
			    start-up( 5 ),	-- Interface is in start-up
						-- mode. 
			    pend-port-up( 6 ), 
			    up( 7 ),		-- Interface is in UP state, and
						-- ready to transfer data.
			    pend-deactivate( 8 ),-- Interface may transition
						-- from UP to DOWN state. 
			    out-of-service( 9 ), -- Interface is placed OOS.
			    analog-loopback( 10 ), 
						-- Port is in some type of 
						-- test state
			    digital-loopback( 11 ) 
						-- Port is in some type of
						-- test state
			}

	ACCESS		read-only
	STATUS		mandatory
	DESCRIPTION	"Interface state describes the current ports
			operating state. States are: Config, Pend Down, 
			Up, Down, Start-up, or N/A."
	::= { hdsl2LineStatusEntry 6 }
	
   hdsl2StatusOpRate		OBJECT-TYPE
	SYNTAX		INTEGER{
                           m1552000(1552000)
                        } 
	ACCESS		read-write
	STATUS		mandatory
	DESCRIPTION	"The current symetrical operation rate"
	::= { hdsl2LineStatusEntry 7 }

   hdsl2StatusVendorId   OBJECT-TYPE
	SYNTAX		INTEGER
	ACCESS		read-only
	STATUS		mandatory
	DESCRIPTION	"Vendor identification."
	::= { hdsl2LineStatusEntry 8 }

   hdsl2StatusMajorFirmWareVer	OBJECT-TYPE
	SYNTAX		INTEGER
	ACCESS		read-only
	STATUS		mandatory
	DESCRIPTION	"Major firmware version."
	::= { hdsl2LineStatusEntry 9 }

   hdsl2StatusMinorFirmWareVer	OBJECT-TYPE
	SYNTAX		INTEGER
	ACCESS		read-only
	STATUS		mandatory
	DESCRIPTION	"Minor firmware version."
	::= { hdsl2LineStatusEntry 10 }

   hdsl2StatusHardWareVer	OBJECT-TYPE
	SYNTAX		INTEGER
	ACCESS		read-only
	STATUS		mandatory
	DESCRIPTION	"Hardware version."
	::= { hdsl2LineStatusEntry 11 }

    hdsl2LineStatisticTable OBJECT-TYPE
	SYNTAX		SEQUENCE OF Hdsl2LineStatisticEntry
	ACCESS		not-accessible
	STATUS		mandatory
	DESCRIPTION	"HDSL2 statistical parameters."
	::= { wanTypeHdsl2 2 }

   hdsl2LineStatisticEntry OBJECT-TYPE
	SYNTAX		Hdsl2LineStatisticEntry
	ACCESS		not-accessible
	STATUS		mandatory
	DESCRIPTION	"A interface statistical entry containing objects to
			describe the interface."
	INDEX		{ hdsl2StatIfEntryIndex }
	::= { hdsl2LineStatisticTable 1 }

    Hdsl2LineStatisticEntry ::=
	SEQUENCE {
	    hdsl2StatIfEntryIndex
		INTEGER,
	    hdsl2StatShelfIndex
		INTEGER,
	    hdsl2StatSlotIndex
		INTEGER,
	    hdsl2StatLineIndex
		INTEGER,
	    hdsl2StatConnUpDays
		INTEGER,
	    hdsl2StatConnUpHours
	        INTEGER,
	    hdsl2StatConnUpMinutes
		INTEGER,
	    hdsl2StatRxSignalPresent
		INTEGER,
	    hdsl2StatLineQualityDb
		INTEGER,
	    hdsl2StatUpDwnCntr
		INTEGER,
	    hdsl2StatLineSelfTest
		INTEGER,
	    hdsl2StatTxPower
		INTEGER,
	    hdsl2StatFramerCrcErrors
		INTEGER,
	    hdsl2StatFramerSyncStatus
		INTEGER,
	    hdsl2StatFramerLosdCnt
		INTEGER,
	    hdsl2StatFramerSegaCnt
		INTEGER,
	    hdsl2StatFramerSegdCnt
		INTEGER,
	    hdsl2StatFramerRxHecErrors
		INTEGER,
	    hdsl2StatBertTimer
		INTEGER,
	    hdsl2StatBertEna
		INTEGER,
	    hdsl2StatBertState
		INTEGER,
	    hdsl2StatBertErrorCounter
		INTEGER
	}

   hdsl2StatIfEntryIndex	OBJECT-TYPE
	SYNTAX		INTEGER
	ACCESS		read-only
	STATUS		mandatory
	DESCRIPTION	"The interface groups interface index is used 
			 to index into this table."
	::= { hdsl2LineStatisticEntry 1 }

   hdsl2StatShelfIndex	OBJECT-TYPE
	SYNTAX		INTEGER
	ACCESS		read-only
	STATUS		mandatory
	DESCRIPTION	"HDSL2 modules Shelf ID."
	::= { hdsl2LineStatisticEntry 2 }

   hdsl2StatSlotIndex	OBJECT-TYPE
	SYNTAX		INTEGER
	ACCESS		read-only
	STATUS		mandatory
	DESCRIPTION	"HDSL2 modules Slot ID."
	::= { hdsl2LineStatisticEntry 3 }

   hdsl2StatLineIndex	OBJECT-TYPE
	SYNTAX		INTEGER
	ACCESS		read-only
	STATUS		mandatory
	DESCRIPTION	"HDSL2 modules interface ID." 
	::= { hdsl2LineStatisticEntry 4 }

   hdsl2StatConnUpDays	OBJECT-TYPE
	SYNTAX		INTEGER
	ACCESS		read-only
	STATUS		mandatory
	DESCRIPTION	"Connection up day count."
	::= { hdsl2LineStatisticEntry 5 }

   hdsl2StatConnUpHours	OBJECT-TYPE
	SYNTAX		INTEGER
	ACCESS		read-only
	STATUS		mandatory
	DESCRIPTION	"Connection Up 24 hour count."
	::= { hdsl2LineStatisticEntry 6 }

   hdsl2StatConnUpMinutes	OBJECT-TYPE
	SYNTAX		INTEGER
	ACCESS		read-only
	STATUS		mandatory
	DESCRIPTION	"Connection up minute count."
	::= { hdsl2LineStatisticEntry 7 }

   hdsl2StatRxSignalPresent	OBJECT-TYPE
	SYNTAX		INTEGER {
			    no( 1 ),	-- LOS of signal detected. 
			    yes( 2 )	-- Receive signal present. 
			}
	ACCESS		read-only
	STATUS		mandatory
	DESCRIPTION	"Receive signal present detection."
	::= { hdsl2LineStatisticEntry 8 }

  hdsl2StatLineQualityDb OBJECT-TYPE
	SYNTAX		INTEGER
	ACCESS		read-only
	STATUS		mandatory
	DESCRIPTION	"Lines noise margin. Reliable data will transfer
			with a reading of ??? or greater."
	::= { hdsl2LineStatisticEntry 9 }


    hdsl2StatUpDwnCntr OBJECT-TYPE
	SYNTAX		INTEGER
	ACCESS		read-only
	STATUS		mandatory
	DESCRIPTION	"Line Up Down counter value displays the number
			of times the interface transitions from a down to up
			state."
	::= { hdsl2LineStatisticEntry 10 }

    hdsl2StatLineSelfTest    OBJECT-TYPE
	SYNTAX		INTEGER {
				other( 4 ),
				selfTestFailed( 1 ),	
				localLoopBackFailed( 2 ),
				passed( 3 )
			}
	ACCESS		read-only
	STATUS		mandatory
	DESCRIPTION	"Line hardware self test results (Passed or 
			 Failed)."
	::= { hdsl2LineStatisticEntry 11 }

    hdsl2StatTxPower    OBJECT-TYPE
	SYNTAX		INTEGER (1..'7fffffff'h)
	ACCESS		read-only
	STATUS		mandatory
	DESCRIPTION	"Lines transmit power."
	::= { hdsl2LineStatisticEntry 12 }

    hdsl2StatFramerCrcErrors    OBJECT-TYPE
	SYNTAX		INTEGER (1..'7fffffff'h)
	ACCESS		read-only
	STATUS		mandatory
	DESCRIPTION	"Lines framer CRC errors."
	::= { hdsl2LineStatisticEntry 13 }

    hdsl2StatFramerSyncStatus    OBJECT-TYPE
	SYNTAX		INTEGER (1..'7fffffff'h)
	ACCESS		read-only
	STATUS		mandatory
	DESCRIPTION	"Lines framer sync status ."
	::= { hdsl2LineStatisticEntry 14 }

    hdsl2StatFramerLosdCnt    OBJECT-TYPE
	SYNTAX		INTEGER (1..'7fffffff'h)
	ACCESS		read-only
	STATUS		mandatory
	DESCRIPTION	"Lines framer ???."
	::= { hdsl2LineStatisticEntry 15 }

    hdsl2StatFramerSegaCnt    OBJECT-TYPE
	SYNTAX		INTEGER (1..'7fffffff'h)
	ACCESS		read-only
	STATUS		mandatory
	DESCRIPTION	"Lines framer ???."
	::= { hdsl2LineStatisticEntry 16 }

    hdsl2StatFramerSegdCnt    OBJECT-TYPE
	SYNTAX		INTEGER (1..'7fffffff'h)
	ACCESS		read-only
	STATUS		mandatory
	DESCRIPTION	"Lines framer ???."
	::= { hdsl2LineStatisticEntry 17 }

    hdsl2StatFramerRxHecErrors    OBJECT-TYPE
	SYNTAX		INTEGER (1..'7fffffff'h)
	ACCESS		read-only
	STATUS		mandatory
	DESCRIPTION	"Lines framer ???."
	::= { hdsl2LineStatisticEntry 18 }

    hdsl2StatBertTimer    OBJECT-TYPE
	SYNTAX		INTEGER {
				one-minute(1),
				two-minutes(2),
				three-minutes(3),
				four-minutes(4),
				five-minutes(5),
				ten-minutes(6),
				fifteen-minutes(7),
				twenty-minutes(8),
				thirty-minutes(9)
			}
	ACCESS		read-write
	STATUS		mandatory
	DESCRIPTION	"BER test duration configuration. The BER test lasts for the 
			 duration of this timer."
	::= { hdsl2LineStatisticEntry 19 }
	
    hdsl2StatBertEna    OBJECT-TYPE
	SYNTAX		INTEGER {
				no( 1 ),
				yes( 2 )
			}
	ACCESS		read-write
	STATUS		mandatory
	DESCRIPTION	"Enable/disable of the BER test. If nodes are
			 connected, then the BER test is ran between the
			 units. If this node is not connected to a remote 
			 node, then the interface is placed into analog 
			 loopback and the BER test is started."
	::= { hdsl2LineStatisticEntry 20 }
	
    hdsl2StatBertState    OBJECT-TYPE
	SYNTAX		INTEGER {
				active(1),
				stopped(2),
				start-up(3),
				waiting(4),
				pend-active(5),
				bert-los(6)
			}
	ACCESS		read-only
	STATUS		mandatory
	DESCRIPTION	"BER test states. When this node is not connected to
			 another node, the test is disabled. When two nodes are connected 
			 then the BER test waits for the other node to start it's BER test and 
			 then starts collecting bit errors immediately."
	::= { hdsl2LineStatisticEntry 21 }
	
    hdsl2StatBertErrorCounter    OBJECT-TYPE
	SYNTAX		INTEGER
	ACCESS		read-only
	STATUS		mandatory
	DESCRIPTION	"BER test bit error counter."
	::= { hdsl2LineStatisticEntry 22 }
END
