-- Packeteer PacketShaper v4.0  Response Time Management MIB
-- November 13,1998
-- Copyright 1998, 1999 Packeteer, Inc.

PACKETEER-RTM-MIB DEFINITIONS ::= BEGIN


   IMPORTS
      IpAddress, Gauge, Counter
         FROM RFC1155-SMI
      OBJECT-TYPE
         FROM RFC-1212
      DateAndTime
	 FROM SNMPv2-TC
      psCommonMib, classIndex
	 FROM PACKETEER-MIB;

   -- Packeteer Response Time Management MIB

   psClassResponseTimes   OBJECT IDENTIFIER ::= { psCommonMib 7 }

   --
   --   Separate statistics are maintained, per class, for aggregate delay,
   --   network delay, and server delay.  Consult Packeteer documentation for
   --   precise details on what these numbers mean.
   --

   -- Configurable settings about how RTM information is kept.  Be aware
   -- that changing these settings invalidates other MIB tables that are
   -- based on them, and thus those tables are zeroed for that class.
   -- Further information is given below.

   classRTMConfigTable OBJECT-TYPE
      SYNTAX  SEQUENCE OF ClassRTMConfigEntry
      ACCESS  not-accessible
      STATUS  mandatory
      DESCRIPTION
         "A table of parameters configuring the Response Time Management
          feature for each class.
          ***  NOTE that these parameters are used to
	  compute the other data in this MIB, and thus changing any of them
	  causes a reset of most RTM data.  Only the histograms
	  (classTotalDelayTable, classServerDelayTable, and
          classNetworkDelayTable ) are unaffected."
      ::= { psClassResponseTimes 1 }

   classRTMConfigEntry OBJECT-TYPE
      SYNTAX  ClassRTMConfigEntry
      ACCESS  not-accessible
      STATUS  mandatory
      DESCRIPTION
         "An entry containing the configurable Response Time Management
          parameters for a given class"
      INDEX   { classIndex }
      ::= { classRTMConfigTable 1 }

   ClassRTMConfigEntry ::=
      SEQUENCE {
	 classTotalDelayThreshold
            INTEGER,
	 classServiceLevelThreshold
            INTEGER
      }

   classTotalDelayThreshold OBJECT-TYPE
      SYNTAX  INTEGER
      ACCESS  read-only
      STATUS  mandatory
      DESCRIPTION
         "The time in milliseconds which constitutes the acceptable limit of
          aggregate delay for this class."
      ::= { classRTMConfigEntry 2 }

   classServiceLevelThreshold OBJECT-TYPE
      SYNTAX  INTEGER
      ACCESS  read-only
      STATUS  mandatory
      DESCRIPTION
         "The percentage of transactions required NOT to be over threshold.
	  If more than this percentage of transactions in an interval are
          over threshold, then this Interval is counted
          in the classIntervalsAboveTotalDelayThreshold variable.  The default is 100."
      ::= { classRTMConfigEntry 6 }

   classTotalDelayTable OBJECT-TYPE
      SYNTAX  SEQUENCE OF ClassTotalDelayEntry
      ACCESS  not-accessible
      STATUS  mandatory
      DESCRIPTION
         "A list of traffic class aggregate delay entries.
          The table is indexed by two variables:
          the classIndex from classTable, and the lower limit of the bucket,
          in milliseconds.  The histogram for any given class 'i' may thus be
          retrieved via GetNext of classTotalDelayBucketCount.i.0"
      ::= { psClassResponseTimes 2 }

   classTotalDelayEntry OBJECT-TYPE
      SYNTAX  ClassTotalDelayEntry
      ACCESS  not-accessible
      STATUS  mandatory
      DESCRIPTION
         "An entry containing the count of observed
          network transactions in a given bucket.  "
      INDEX   { classIndex, classTotalDelayBucketLimit }
      ::= { classTotalDelayTable 1 }

   ClassTotalDelayEntry ::=
      SEQUENCE {
         classTotalDelayBucketLimit
            INTEGER,
         classTotalDelayBucketCount
            Counter
      }

   classTotalDelayBucketLimit OBJECT-TYPE
      SYNTAX  INTEGER
      ACCESS  read-only
      STATUS  mandatory
      DESCRIPTION
         "The lower limit, in milliseconds, of this bucket.  NOTE:  although
          the bucket limits are given for each class, this does NOT imply that
          they are different, and in fact they are the same for all classes.
          This is done to facilitate GetNext'ing through the table;  for example
          the count of the next bucket larger than 1 second for class 'i' can
          be obtained by GetNext classTotalDelayBucketCount.i.1000.  The complete
          histogram for class i, with the limits for each bucket, can be obtained
          by GetNext classTotalDelayBucketCount.i "
      ::= { classTotalDelayEntry 1 }

   classTotalDelayBucketCount OBJECT-TYPE
      SYNTAX  Counter
      ACCESS  read-only
      STATUS  mandatory
      DESCRIPTION
         "The count of transactions whose aggregate delay fell in this bucket.
          Transactions are defined according to classTransactionDefinition."
      ::= { classTotalDelayEntry 2 }


   classNetworkDelayTable OBJECT-TYPE
      SYNTAX  SEQUENCE OF ClassNetworkDelayEntry
      ACCESS  not-accessible
      STATUS  mandatory
      DESCRIPTION
         "A list of traffic class network delay entries.
          The table is indexed by two variables:
          the classIndex from classTable, and the lower limit of the bucket,
          in milliseconds.  The histogram for any given class 'i' may thus be
          retrieved via GetNext of classNetworkDelayBucketCount.i.0"
      ::= { psClassResponseTimes 3 }

   classNetworkDelayEntry OBJECT-TYPE
      SYNTAX  ClassNetworkDelayEntry
      ACCESS  not-accessible
      STATUS  mandatory
      DESCRIPTION
         "An entry containing the count of observed
          network delay transactions in a given bucket.
          Transactions are defined according to classTransactionDefinition."
      INDEX   { classIndex, classNetworkDelayBucketLimit }
      ::= { classNetworkDelayTable 1 }

   ClassNetworkDelayEntry ::=
      SEQUENCE {
         classNetworkDelayBucketLimit
            INTEGER,
         classNetworkDelayBucketCount
            Counter
      }

   classNetworkDelayBucketLimit OBJECT-TYPE
      SYNTAX  INTEGER
      ACCESS  read-only
      STATUS  mandatory
      DESCRIPTION
         "The lower limit, in milliseconds, of this bucket.  NOTE:  although
          the bucket limits are given for each class, this does NOT imply that
          they are different, and in fact they are the same for all classes.
          This is done to facilitate GetNext'ing through the table;  for example
          the count of the next bucket larger than 1 second for class 'i' can
          be obtained by GetNext classNetworkDelayBucketCount.i.1000.  The complete
          histogram for class i, with the limits for each bucket, can be obtained
          by GetNext classNetworkDelayBucketCount.i "
      ::= { classNetworkDelayEntry 1 }

   classNetworkDelayBucketCount OBJECT-TYPE
      SYNTAX  Counter
      ACCESS  read-only
      STATUS  mandatory
      DESCRIPTION
         "The count of observed network transactions for the class in this bucket.
          Transactions are defined according to classTransactionDefinition."
      ::= { classNetworkDelayEntry 2 }


   classServerDelayTable OBJECT-TYPE
      SYNTAX  SEQUENCE OF ClassServerDelayEntry
      ACCESS  not-accessible
      STATUS  mandatory
      DESCRIPTION
         "A list of traffic class Server delay entries.
          The table is indexed by two variables:
          the classIndex from classTable, and the lower limit of the bucket,
          in milliseconds.  The histogram for any given class 'i' may thus be
          retrieved via GetNext of classServerDelayBucketCount.i.0"
      ::= { psClassResponseTimes 4 }

   classServerDelayEntry OBJECT-TYPE
      SYNTAX  ClassServerDelayEntry
      ACCESS  not-accessible
      STATUS  mandatory
      DESCRIPTION
         "An entry containing the count of observed
          network transactions in a given bucket.  "
      INDEX   { classIndex, classServerDelayBucketLimit }
      ::= { classServerDelayTable 1 }

   ClassServerDelayEntry ::=
      SEQUENCE {
         classServerDelayBucketLimit
            INTEGER,
         classServerDelayBucketCount
            Counter
      }

   classServerDelayBucketLimit OBJECT-TYPE
      SYNTAX  INTEGER
      ACCESS  read-only
      STATUS  mandatory
      DESCRIPTION
         "The lower limit, in milliseconds, of this bucket.  NOTE:  although
          the bucket limits are given for each class, this does NOT imply that
          they are different, and in fact they are the same for all classes.
          This is done to facilitate GetNext'ing through the table;  for example
          the count of the next bucket larger than 1 second for class 'i' can
          be obtained by GetNext classServerDelayBucketCount.i.1000.  The complete
          histogram for class i, with the limits for each bucket, can be obtained
          by GetNext classServerDelayBucketCount.i "
      ::= { classServerDelayEntry 1 }

   classServerDelayBucketCount OBJECT-TYPE
      SYNTAX  Counter
      ACCESS  read-only
      STATUS  mandatory
      DESCRIPTION
         "The count of observed network transactions for the class in this bucket.
	  Transactions are defined according to classTransactionDefinition."
      ::= { classServerDelayEntry 2 }

   classRTMTable OBJECT-TYPE
      SYNTAX  SEQUENCE OF ClassRTMEntry
      ACCESS  not-accessible
      STATUS  mandatory
      DESCRIPTION
         "A table of readonly Response Time Management information about this class.
	  All non-histogram information about RTM is kept in this table."
      ::= { psClassResponseTimes 5 }

   classRTMEntry OBJECT-TYPE
      SYNTAX  ClassRTMEntry
      ACCESS  not-accessible
      STATUS  mandatory
      DESCRIPTION
         "An entry containing readonly Response Time Management information about
	  this class."
      INDEX   { classIndex }
      ::= { classRTMTable 1 }

	ClassRTMEntry ::=
		SEQUENCE {
			classTotalDelayMedian
				Gauge,
			classTotalDelayAverage
				Gauge,
			classTransactionsAboveTotalDelayThreshold
				Counter,
			classIntervalsAboveServiceLevelThreshold
				Counter,
			classLastIntervalAboveServiceLevelThreshold
				DateAndTime,
			classServerDelayMedian
				Gauge,
			classServerDelayAverage
				Gauge,
			classNetworkDelayMedian
				Gauge,
			classNetworkDelayAverage
				Gauge,
			classTransactionBytes
				Counter,
			classTransactionBytesHi
				Counter,
			classRoundTripTime
				Counter,
			classRoundTripTimeHi
				Counter,
			classTransactionsTotal
				Counter,
			classTotalDelayMsec
				Counter,
			classTotalDelayMsecHi
				Counter,
			classServerDelayMsec
				Counter,
			classServerDelayMsecHi
				Counter,
			classNetworkDelayMsec
				Counter,
			classNetworkDelayMsecHi
				Counter
   }

   classTotalDelayMedian OBJECT-TYPE
      SYNTAX  Gauge
      ACCESS  read-only
      STATUS  mandatory
      DESCRIPTION
         "The median aggregate delay for this class, in milliseconds.
          Medians are calculated by an approximate method using the
          above histogram, whose error is at most 1/2 of the time interval
          spanned by the bucket into which the exact median falls."
      ::= { classRTMEntry 1 }


   classTotalDelayAverage OBJECT-TYPE
      SYNTAX  Gauge
      ACCESS  read-only
      STATUS  mandatory
      DESCRIPTION
         "The average aggregate delay for this class, in milliseconds.
          Use the average in conjunction with the median, since averages
          can be distorted by a few very large samples."
      ::= { classRTMEntry 2 }


   classTransactionsAboveTotalDelayThreshold OBJECT-TYPE
      SYNTAX  Counter
      ACCESS  read-only
      STATUS  mandatory
      DESCRIPTION
         "The number of network transactions whose aggregate delay was greater
	  than the value of classTotalDelayThreshold.  Transactions
          are defined according to classTransactionDefinition."
      ::= { classRTMEntry 3 }

   classIntervalsAboveServiceLevelThreshold OBJECT-TYPE
      SYNTAX  Counter
      ACCESS  read-only
      STATUS  mandatory
      DESCRIPTION
         "The number of intervals over the aggregate delay threshold,
          defined as those intervals with 'classIntervalServiceLevelThreshold'% or fewer
          transactions with aggregate delay less than 'classTotalDelayThreshold'."
      ::= { classRTMEntry 4 }

   classLastIntervalAboveServiceLevelThreshold OBJECT-TYPE
      SYNTAX  DateAndTime
      ACCESS  read-only
      STATUS  mandatory
      DESCRIPTION
         "The time at which the last interval ended which failed the
	  service level threshold, in other words, the interval in which
	  classIntervalServiceLevelThreshold% of the total transactions, or fewer,
	  had total response times less than classTotalDelayThreshold.  If there
	  was no such interval, then this is set to a zero value."
      ::= { classRTMEntry 5 }


   classServerDelayMedian OBJECT-TYPE
      SYNTAX  Gauge
      ACCESS  read-only
      STATUS  mandatory
      DESCRIPTION
         "The median server delay for this class, in milliseconds.
          Medians are calculated by an approximate method using the
          above histogram, whose error is at most 1/2 of the time interval
          spanned by the bucket into which the exact median falls."
      ::= { classRTMEntry 6 }


   classServerDelayAverage OBJECT-TYPE
      SYNTAX  Gauge
      ACCESS  read-only
      STATUS  mandatory
      DESCRIPTION
         "The average server delay for this class, in milliseconds.
          Use the average in conjunction with the median, since averages
          can be distorted by a few very large samples."
      ::= { classRTMEntry 7 }


   classNetworkDelayMedian OBJECT-TYPE
      SYNTAX  Gauge
      ACCESS  read-only
      STATUS  mandatory
      DESCRIPTION
         "The median network delay for this class, in milliseconds.
          Medians are calculated by an approximate method using the
          above histogram, whose error is at most 1/2 of the time interval
          spanned by the bucket into which the exact median falls."
      ::= { classRTMEntry 11 }


   classNetworkDelayAverage OBJECT-TYPE
      SYNTAX  Gauge
      ACCESS  read-only
      STATUS  mandatory
      DESCRIPTION
         "The average network delay for this class, in milliseconds.
          Use the average in conjunction with the median, since averages
          can be distorted by a few very large samples."
      ::= { classRTMEntry 12 }

   classTransactionBytes OBJECT-TYPE
      SYNTAX  Counter
      ACCESS  read-only
      STATUS  mandatory
      DESCRIPTION
         "The total number of bytes on this class involved in transactions,
	  and thus eligible for RTM.  Dividing this value by classTransactionsTotal
	  provides the average size of a transaction for the class.
          This variable represents the low-order portion of a 64-bit value."
      ::= { classRTMEntry 13 }

   classTransactionBytesHi OBJECT-TYPE
      SYNTAX  Counter
      ACCESS  read-only
      STATUS  mandatory
      DESCRIPTION
         "The total number of bytes on this class involved in transactions,
	  and thus eligible for RTM. Dividing this value by classTransactionsTotal
	  provides the average size of a transaction for the class.
          This variable represents the high-order portion of a 64-bit value."
      ::= { classRTMEntry 14 }

   classRoundTripTime OBJECT-TYPE
      SYNTAX  Counter
      ACCESS  read-only
      STATUS  mandatory
      DESCRIPTION
         "The time, in milliseconds, of a network round-trip, per transaction.
          Dividing this value by classTransactionsTotal gives an indication of the
          effective speed of the network for this class, which includes factors like
          queueing and retransmissions that may be controllable.
          This variable represents the low-order portion of a 64-bit value."
      ::= { classRTMEntry 15 }

   classRoundTripTimeHi OBJECT-TYPE
      SYNTAX  Counter
      ACCESS  read-only
      STATUS  mandatory
      DESCRIPTION
         "The time, in milliseconds, of a network round-trip, per transaction.
          Dividing this value by classTransactionsTotal gives an indication of the
          effective speed of the network for this class, which includes factors like
          queueing and retransmissions that may be controllable.
          This variable represents the high-order portion of a 64-bit value."
      ::= { classRTMEntry 16 }

   classTransactionsTotal OBJECT-TYPE
      SYNTAX  Counter
      ACCESS  read-only
      STATUS  mandatory
      DESCRIPTION
         "The total number of transactions for this class.  "
      ::= { classRTMEntry 17 }

   classTotalDelayMsec OBJECT-TYPE
        SYNTAX  Counter
         ACCESS read-only
         STATUS mandatory
         DESCRIPTION
                 "The time, in milliseconds, of total delay, per transaction.
                  This variable represents the low-order portion of a 64-bit value."
         ::= { classRTMEntry 18 }


   classTotalDelayMsecHi OBJECT-TYPE
        SYNTAX  Counter
        ACCESS  read-only
        STATUS  mandatory
        DESCRIPTION
         "The time, in milliseconds, of total delay, per transaction.
          This variable represents the high-order portion of a 64-bit value."
        ::= { classRTMEntry 19 }

   classServerDelayMsec OBJECT-TYPE
         SYNTAX Counter
         ACCESS read-only
         STATUS mandatory
         DESCRIPTION
         "The time, in milliseconds, of server delay, per transaction.
          This variable represents the low-order portion of a 64-bit value."
         ::= { classRTMEntry 20 }


   classServerDelayMsecHi OBJECT-TYPE
        SYNTAX  Counter
        ACCESS  read-only
        STATUS  mandatory
        DESCRIPTION
         "The time, in milliseconds, of server delay, per transaction.
          This variable represents the high-order portion of a 64-bit value."
        ::= { classRTMEntry 21 }

   classNetworkDelayMsec OBJECT-TYPE
        SYNTAX  Counter
        ACCESS read-only
        STATUS mandatory
        DESCRIPTION
         "The time, in milliseconds, of network delay, per transaction.
          This variable represents the low-order portion of a 64-bit value."
         ::= { classRTMEntry 22 }

   classNetworkDelayMsecHi OBJECT-TYPE
                SYNTAX  Counter
        ACCESS  read-only
        STATUS  mandatory
        DESCRIPTION
         "The time, in milliseconds, of network delay, per transaction.
          This variable represents the high-order portion of a 64-bit value."
        ::= { classRTMEntry 23 }


   -- "drill down" information.  The classWorstServerTable and
   -- classClientsTable tables provides more information about
   --  the servers and clients experiencing aggregate delays above the
   --  configured threshold.

   classWorstServerTable OBJECT-TYPE
      SYNTAX  SEQUENCE OF ClassWorstServerEntry
      ACCESS  not-accessible
      STATUS  mandatory
      DESCRIPTION
         "A list of the N servers which have handled more than M transactions,
          and are experiencing the worst behavior with
          respect to the response time threshold, if one has been set.
          'N' and 'M' are fixed limits for any given release of PacketShaper software
	  and are not settable.  In release 4.0, N and M are 10.
          The table is ordered by classIndex and classWorstServerIndex."
      ::= { psClassResponseTimes 6 }

   classWorstServerEntry OBJECT-TYPE
      SYNTAX  ClassWorstServerEntry
      ACCESS  not-accessible
      STATUS  mandatory
      DESCRIPTION
         "An entry describing a server experiencing the worst behavior with
          respect to the response time threshold."
      INDEX   { classIndex, classWorstServerIndex }
      ::= { classWorstServerTable 1 }

   ClassWorstServerEntry ::=
      SEQUENCE {
	 classWorstServerIndex
	    INTEGER,
	 classWorstServerAddress
            IpAddress,
         classWorstServerTransactionCount
            Counter
      }

   classWorstServerIndex OBJECT-TYPE
      SYNTAX  INTEGER
      ACCESS  read-only
      STATUS  mandatory
      DESCRIPTION
         "A unique index from 1 to N, where N is a fixed limit, and a
          lower value denotes a lower ratio of good transactions."
      ::= { classWorstServerEntry 1 }

   classWorstServerAddress OBJECT-TYPE
      SYNTAX  IpAddress
      ACCESS  read-only
      STATUS  mandatory
      DESCRIPTION
         "The address of this server."
      ::= { classWorstServerEntry 2 }

   classWorstServerTransactionCount OBJECT-TYPE
      SYNTAX  Counter
      ACCESS  read-only
      STATUS  mandatory
      DESCRIPTION
         "The number of transactions recorded for this server."
      ::= { classWorstServerEntry 3 }


   classWorstClientTable OBJECT-TYPE
      SYNTAX  SEQUENCE OF ClassWorstClientEntry
      ACCESS  not-accessible
      STATUS  mandatory
      DESCRIPTION
         "A list of the N clients which have handled more than M transactions,
          and are experiencing the worst behavior with
          respect to the response time threshold, if one has been set.
          'N' and 'M' are fixed limits for any given release of PacketShaper software
	  and are not settable.  In release 4.0, N and M are 10.
          The table is ordered by classIndex and classWorstClientIndex."
      ::= { psClassResponseTimes 7 }

   classWorstClientEntry OBJECT-TYPE
      SYNTAX  ClassWorstClientEntry
      ACCESS  not-accessible
      STATUS  mandatory
      DESCRIPTION
         "An entry describing a client experiencing the most sessions over
          the response time threshold."
      INDEX   { classIndex, classWorstClientIndex }
      ::= { classWorstClientTable 1 }

   ClassWorstClientEntry ::=
      SEQUENCE {
	 classWorstClientIndex
	    INTEGER,
	 classWorstClientAddress
            IpAddress,
         classWorstClientTransactionCount
            Counter
      }

   classWorstClientIndex OBJECT-TYPE
      SYNTAX  INTEGER
      ACCESS  read-only
      STATUS  mandatory
      DESCRIPTION
         "A unique index from 1 to N, where N is a fixed limit, and a
          lower value denotes a higher value of
          classWorstClientSessionCount."
      ::= { classWorstClientEntry 1 }

   classWorstClientAddress OBJECT-TYPE
      SYNTAX  IpAddress
      ACCESS  read-only
      STATUS  mandatory
      DESCRIPTION
         "The address of this client."
      ::= { classWorstClientEntry 2 }

   classWorstClientTransactionCount OBJECT-TYPE
      SYNTAX  Counter
      ACCESS  read-only
      STATUS  mandatory
      DESCRIPTION
         "The number of transactions recorded for this client."
      ::= { classWorstClientEntry 3 }

END
