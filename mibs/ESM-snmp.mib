-- Title:         Fibronics' MIB  
-- MIB Module :   Private MIB for  GigaHUB ESM
-- Version    :   V2.1
-- Date       :   Jan 1, 1995
-- By         :   Gadi K.
-- Contact    :   Edna Ganon
-- Email:     :   edna@fibronics.co.il 
-- 
-- Description:  MIB for the ESM SNMP Agents  
-- Copyright (c) 1991 Fibronics International


          ESM-snmp DEFINITIONS ::= BEGIN

          IMPORTS
			 TRAP-TYPE FROM RFC-1215
		DisplayString FROM SNMPv2-TC
                  mgmt, NetworkAddress, IpAddress, Counter, Gauge,
                          TimeTicks, internet
                      FROM RFC1155-SMI
		  PhysAddress
		  	FROM RFC1213-MIB
		  Party, Context
			FROM SNMPv2-PARTY-MIB
                  OBJECT-TYPE
                          FROM RFC-1212;


 
	Party		::= OBJECT IDENTIFIER
	Context 	::= OBJECT IDENTIFIER

          -- *****************************************
          --       Fibronics Private Part
          -- ****************************************
	   


	private		OBJECT IDENTIFIER ::= { internet 4 }
	enterprises	OBJECT IDENTIFIER ::= { private 1 }


	fibronics	OBJECT IDENTIFIER ::= { enterprises 22 }
	trap            OBJECT IDENTIFIER ::= { fibronics 3 }
	traprun         OBJECT IDENTIFIER ::= { trap 1 }
	traperm         OBJECT IDENTIFIER ::= { trap 2 }
	trapvar         OBJECT IDENTIFIER ::= { trap 3 }
	fm800		OBJECT IDENTIFIER ::= { fibronics 51 }
	fmsystem	OBJECT IDENTIFIER ::= { fm800 1 }
	fmslot		OBJECT IDENTIFIER ::= { fm800 2 }
	fmlu		OBJECT IDENTIFIER ::= { fm800 3 }
	fmdiag		OBJECT IDENTIFIER ::= { fm800 5 }

	fmsystemrun	OBJECT IDENTIFIER ::= { fmsystem 1 }
	fmsystemperm	OBJECT IDENTIFIER ::= { fmsystem 2 }

	fmrptr		OBJECT IDENTIFIER ::= { fm800 11 }
	lc308-129	OBJECT IDENTIFIER ::= { fmrptr 1 }
	lc303-129	OBJECT IDENTIFIER ::= { fmrptr 3 }
	lc312-129	OBJECT IDENTIFIER ::= { fmrptr 5 }

	products	OBJECT IDENTIFIER ::= { fibronics 100 }
	eth-rptrs	OBJECT IDENTIFIER ::= { products  1 }
	tr-concentrators	OBJECT IDENTIFIER ::= { products 2 }
 	fddi-concentrators   	OBJECT IDENTIFIER ::= { products 3 }
 	brouters   		OBJECT IDENTIFIER ::= { products 4 }
         terminal-servers	OBJECT IDENTIFIER ::= { products 5 }
 	chassis   		OBJECT IDENTIFIER ::= { products 6 }
	mux			OBJECT IDENTIFIER ::= { products 7 }
 	atm-switch              OBJECT IDENTIFIER ::= { products 8 }
 	eth-switch              OBJECT IDENTIFIER ::= { products 9 }
	tr-hubs           	OBJECT IDENTIFIER ::= { products 10 }
	bridges                 OBJECT IDENTIFIER ::= { products 11 }

	xmh-rptrs	OBJECT IDENTIFIER ::= { eth-rptrs  1 }

	lc342-rptr	OBJECT IDENTIFIER ::= { xmh-rptrs 1 }
	lc348-rptr	OBJECT IDENTIFIER ::= { xmh-rptrs 2 }
	nm349-sm	OBJECT IDENTIFIER ::= { xmh-rptrs 3 }
	lc343-rptr	OBJECT IDENTIFIER ::= { xmh-rptrs 4 }
	lc344-rptr	OBJECT IDENTIFIER ::= { xmh-rptrs 5 }

-- Token-Ring product OIDS (sysobjid):
 
 	tr-rptrs	OBJECT IDENTIFIER ::= {tr-hubs  2 }
 
 
 	lc366-rptr              OBJECT IDENTIFIER ::= {tr-rptrs 1}
 	lc362-rptr              OBJECT IDENTIFIER ::= {tr-rptrs 2}
	nm369-sm                OBJECT IDENTIFIER ::= {tr-rptrs 3}
        em364-trnk              OBJECT IDENTIFIER ::= {tr-rptrs 4}
        em365-trnk              OBJECT IDENTIFIER ::= {tr-rptrs 5}

        lc366p-rptr             OBJECT IDENTIFIER ::= {lc366-rptr 1}
        lc362p-rptr             OBJECT IDENTIFIER ::= {lc362-rptr 2}
        em364p-trnk             OBJECT IDENTIFIER ::= {em364-trnk 1}

-- eth-switch product OIDS (sysobjid):
 
 	xm512-card              OBJECT IDENTIFIER ::= { eth-switch 1}
 	xm514-card              OBJECT IDENTIFIER ::= { eth-switch 2}
 	xm516-card              OBJECT IDENTIFIER ::= { eth-switch 3}
 
-- atm-switch product OIDS (sysobjid):
 
        xm504-card              OBJECT IDENTIFIER ::= {atm-switch 1}

-- bridges product OIDS (sysobjid):

	eth2fddi                OBJECT IDENTIFIER ::= { bridges 1 }

	fx8616                  OBJECT IDENTIFIER ::= { eth2fddi 1 }


	gigaHUB		OBJECT IDENTIFIER ::= { chassis   1 }


	gigaLocationTypes	OBJECT IDENTIFIER ::= { gigaHUB   1 }
	gigaEsmBay		OBJECT IDENTIFIER ::= { gigaLocationTypes  1 } 

	gigaModuleTypes	OBJECT IDENTIFIER ::= { gigaHUB   2 }
	gigaEsm		OBJECT IDENTIFIER ::= { gigaModuleTypes 1 }
	gigaPowerSupply	OBJECT IDENTIFIER ::= { gigaModuleTypes 2 }

	midiGigaHUB     OBJECT IDENTIFIER ::= { gigaHUB   3 }

	cc010		OBJECT IDENTIFIER ::= { mux       1 }
	cc012		OBJECT IDENTIFIER ::= { mux       2 }
	cc020		OBJECT IDENTIFIER ::= { mux       3 }
	cc031		OBJECT IDENTIFIER ::= { mux       4 }
	cc032		OBJECT IDENTIFIER ::= { mux       5 }
	cc041		OBJECT IDENTIFIER ::= { mux       6 }
	cc042		OBJECT IDENTIFIER ::= { mux       7 }
	cc044		OBJECT IDENTIFIER ::= { mux       8 }
	cc832		OBJECT IDENTIFIER ::= { mux       9 }
	cc201		OBJECT IDENTIFIER ::= { mux      10 }
	cc202		OBJECT IDENTIFIER ::= { mux      11 }
	cc214		OBJECT IDENTIFIER ::= { mux      12 }
	cc321		OBJECT IDENTIFIER ::= { mux      13 }
	cc301		OBJECT IDENTIFIER ::= { mux      14 }
	cc233		OBJECT IDENTIFIER ::= { mux      15 }
	cc260		OBJECT IDENTIFIER ::= { mux      16 }
	sw11X		OBJECT IDENTIFIER ::= { mux      17 }
	cc432		OBJECT IDENTIFIER ::= { mux      18 }
	cc420		OBJECT IDENTIFIER ::= { mux      19 }
	cc421		OBJECT IDENTIFIER ::= { mux      20 }
	cc422		OBJECT IDENTIFIER ::= { mux      21 }
	cc401		OBJECT IDENTIFIER ::= { mux      22 }
	cc24X		OBJECT IDENTIFIER ::= { mux      23 }
	cc427		OBJECT IDENTIFIER ::= { mux      24 }
	cc211		OBJECT IDENTIFIER ::= { mux      25 }
	cc212		OBJECT IDENTIFIER ::= { mux      26 }
	cc010-ID	OBJECT IDENTIFIER ::= { mux      27 }
	cc012-ID	OBJECT IDENTIFIER ::= { mux      28 }
	cc020-ID	OBJECT IDENTIFIER ::= { mux      29 }
	cc041-ID	OBJECT IDENTIFIER ::= { mux      30 }
	cc042-ID	OBJECT IDENTIFIER ::= { mux      31 }
	cc044-ID	OBJECT IDENTIFIER ::= { mux      32 }
	cc046A		OBJECT IDENTIFIER ::= { mux      33 }
	cc046B		OBJECT IDENTIFIER ::= { mux      34 }

-- OID of a GigaHUB slot that doesn't exist:
-- slot 5, if a HALF MultiHUB installed, or
-- slot 9, if a FULL MultiHUB installed.
	not-exist	OBJECT IDENTIFIER ::= { mux     100 }

	cc303		OBJECT IDENTIFIER ::= { eth-rptrs  3 }
	cc308		OBJECT IDENTIFIER ::= { eth-rptrs  4 }
	lc303		OBJECT IDENTIFIER ::= { eth-rptrs  5 }
	lc308		OBJECT IDENTIFIER ::= { eth-rptrs  6 }
	lc312		OBJECT IDENTIFIER ::= { eth-rptrs  7 }


	lc322		OBJECT IDENTIFIER ::= { tr-concentrators 1 }


	mibs		OBJECT IDENTIFIER ::= { fibronics    101 }

        systems                 OBJECT IDENTIFIER ::= { mibs 1 }
        mibsstack-rptrs         OBJECT IDENTIFIER ::= { mibs 2 }
        mibstr-hubs             OBJECT IDENTIFIER ::= { mibs 3 }
        mibsfddi-concentrators  OBJECT IDENTIFIER ::= { mibs 4 }
        mibsbrouters            OBJECT IDENTIFIER ::= { mibs 5 }
	chassis-mibs		OBJECT IDENTIFIER ::= { mibs 6 }
        mibsterminal-servers    OBJECT IDENTIFIER ::= { mibs 7 }
        mibseth-rptrs           OBJECT IDENTIFIER ::= { mibs 8 }
        mibsbridges             OBJECT IDENTIFIER ::= { mibs 9 }

        mibbridges-specific    OBJECT IDENTIFIER ::= { mibsbridges 1 }
	mibbridges-general     OBJECT IDENTIFIER ::= { mibsbridges 2 }

          
        mibeth2fddi	OBJECT IDENTIFIER ::= { mibbridges-specific 1}
	mibeth2eth      OBJECT IDENTIFIER ::= { mibbridges-specific 2} 
	
        mib-fx8616	OBJECT IDENTIFIER ::= { mibeth2fddi 1 }
	mib-xm516	OBJECT IDENTIFIER ::= { mibeth2eth 1  }

	gigaHUBMib		OBJECT IDENTIFIER ::= { chassis-mibs 1 }
	gigaHUBPrivate		OBJECT IDENTIFIER ::= { gigaHUBMib   1 }
	gigaHUBChassis		OBJECT IDENTIFIER ::= { gigaHUBMib   2 }


	nonProductsOids	OBJECT IDENTIFIER ::= { fibronics 102 }
	resource-oids 	OBJECT IDENTIFIER ::= { nonProductsOids  1 }
	entity-oids	OBJECT IDENTIFIER ::= { nonProductsOids  2 }
	sensor-oids	OBJECT IDENTIFIER ::= { nonProductsOids  3 }

	eth-resources	OBJECT IDENTIFIER ::= { resource-oids 1 }
        eth-switch-resources     OBJECT IDENTIFIER ::= { resource-oids 2 }
        atm-switch-resources     OBJECT IDENTIFIER ::= { resource-oids 3 }
	tr-resources	OBJECT IDENTIFIER ::= { resource-oids 4 }
	esb-resource	OBJECT IDENTIFIER ::= { eth-resources 1 }
	eb2-resource	OBJECT IDENTIFIER ::= { eth-resources 2 }
	repeater-manager-resource	OBJECT IDENTIFIER ::= { eth-resources 3 }

-- Eth switch resources
 
        eb2-one-resource	OBJECT IDENTIFIER ::= {eth-switch-resources 1}
        eb2-two-resource        OBJECT IDENTIFIER ::= {eth-switch-resources 2}
        eb2-three-resource      OBJECT IDENTIFIER ::= {eth-switch-resources 3}
        eb2-four-resource       OBJECT IDENTIFIER ::= {eth-switch-resources 4}
 
 
-- ATM switch resources
 
       em501-resource       OBJECT IDENTIFIER ::= {atm-switch-resources 1}
       em502-resource       OBJECT IDENTIFIER ::= {atm-switch-resources 2}

-- Token Ring resources

       tr4-resource	OBJECT IDENTIFIER ::= {tr-resources 1}
       tr16-resource	OBJECT IDENTIFIER ::= {tr-resources 2}

	--Party		::= OBJECT IDENTIFIER
	--Context 	::= OBJECT IDENTIFIER



          -- *****************************************
          --       E D B       M I B
          -- ****************************************
	   
------------------------------------------------
--
--          T R A P     T A B L E
--
------------------------------------------------

--   Trap runtime objects
------------------------------------------------


rTrapAddrTable	OBJECT-TYPE
	SYNTAX  SEQUENCE OF RTrapAddrEntry
	ACCESS  not-accessible
	STATUS  mandatory
	DESCRIPTION "Table of managers to which traps
  		     must be sent. Up to 10 
		     entries in table"
	::= { traprun 1 }

rTrapAddrEntry	OBJECT-TYPE
	SYNTAX  RTrapAddrEntry
	ACCESS  not-accessible
	STATUS  mandatory
	INDEX   { rTrapAddrAddr }
	::= { rTrapAddrTable 1 }

RTrapAddrEntry ::= SEQUENCE {
	rTrapAddrAddr
		IpAddress,
	rTrapAddrComm
	        DisplayString,
	rTrapAddrVer
		INTEGER,
	rTrapAddrType
		OCTET STRING,
	rTrapAddrState
		INTEGER,
	rTrapAddrFlag
		INTEGER,
	rTrapAddrAge
		INTEGER
	}

rTrapAddrAddr 	OBJECT-TYPE
	SYNTAX	IpAddress
        ACCESS  read-write
        STATUS  mandatory
	DESCRIPTION "IP address of entity
		     requesting event notification"
	::= { rTrapAddrEntry 1 }

rTrapAddrComm 	OBJECT-TYPE
        SYNTAX  DisplayString
        ACCESS  read-write
        STATUS  mandatory
	DESCRIPTION "Community name the receiving
 		     entity will expect.
                    When reading the instance of this
                    object the value has no meaning."
	::= { rTrapAddrEntry 2 }

rTrapAddrVer  	OBJECT-TYPE
	SYNTAX  INTEGER
        ACCESS  read-write
        STATUS  mandatory
	DESCRIPTION "Version number supported by
		     destination node"
	::= { rTrapAddrEntry 3 }

rTrapAddrType 	OBJECT-TYPE
	SYNTAX  OCTET STRING
        ACCESS  read-write
        STATUS  mandatory
	DESCRIPTION "Type of event that should be
		     reported to this address,
                     bit 0 - authentication trap
		     bit 1 - other SNMP traps
		     bit 2 - Error Traps
		     bit 3 - Diagnostic Traps
		     bit 4 - Debug Traps
		     bit 5 - Enterprise Traps other than fmDiagGenericTrap"
	::= { rTrapAddrEntry 4 }

rTrapAddrState	OBJECT-TYPE
	SYNTAX  INTEGER {
		active(1),
		inactive(2)
		}
        ACCESS  read-write
        STATUS  mandatory
	DESCRIPTION "Determines status of this entry"
	::= { rTrapAddrEntry 5 }

rTrapAddrFlag	OBJECT-TYPE
	SYNTAX	INTEGER {
		fixed(0),
		removable(1)
		}
	ACCESS	read-write
	STATUS	mandatory
	DESCRIPTION "If the entry is fixed, it can not
		be deleted because of aging"
	::= { rTrapAddrEntry 6 }

rTrapAddrAge	OBJECT-TYPE
	SYNTAX	INTEGER
	ACCESS	read-only
	STATUS	mandatory
	DESCRIPTION "Aging time of the entry (in sec)"
	::= { rTrapAddrEntry 7 }

rTrapLearning	OBJECT-TYPE
	SYNTAX	INTEGER {
		disable(0),
		enable(1)
		}
	ACCESS	read-only
	STATUS  mandatory
	DESCRIPTION "Learn the addresses of the managers
		automatically."
	::= { traprun 2 }

rTrapAging	OBJECT-TYPE
	SYNTAX	INTEGER 
	ACCESS	read-only
	STATUS	mandatory
	DESCRIPTION "Time in sec. until we erase a trap
		entry"
	::= { traprun 3 }


--   Trap permanents objects

pTrapAddrTable	OBJECT-TYPE
	SYNTAX  SEQUENCE OF PTrapAddrEntry
	ACCESS  not-accessible
	STATUS  mandatory
	DESCRIPTION "Table of managers to which traps
  		     must be sent. Up to 10 
		     entries in table"
	::= { traperm 1 }

pTrapAddrEntry	OBJECT-TYPE
	SYNTAX  PTrapAddrEntry
	ACCESS  not-accessible
	STATUS  mandatory
	INDEX   { pTrapAddrAddr }
	::= { pTrapAddrTable 1 }

PTrapAddrEntry ::= SEQUENCE {
	pTrapAddrAddr
		IpAddress,
	pTrapAddrComm
	        DisplayString,
	pTrapAddrVer
		INTEGER,
	pTrapAddrType
		OCTET STRING,
	pTrapAddrState
		INTEGER
	}

pTrapAddrAddr 	OBJECT-TYPE
	SYNTAX	IpAddress
        ACCESS  read-write
        STATUS  mandatory
	DESCRIPTION "IP address of entity
		     requesting event notification"
	::= { pTrapAddrEntry 1 }

pTrapAddrComm 	OBJECT-TYPE
        SYNTAX  DisplayString
        ACCESS  read-write
        STATUS  mandatory
	DESCRIPTION "Community name the receiving
 		     entity will expect.
                    When reading the instance of this
                    object the value has no meaning."
	::= { pTrapAddrEntry 2 }

pTrapAddrVer  	OBJECT-TYPE
	SYNTAX  INTEGER
        ACCESS  read-write
        STATUS  mandatory
	DESCRIPTION "Version number supported by
		     destination node"
	::= { pTrapAddrEntry 3 }

pTrapAddrType 	OBJECT-TYPE
	SYNTAX  OCTET STRING
        ACCESS  read-write
        STATUS  mandatory
	DESCRIPTION "Type of event that should be
		     reported to this address,
                     bit 0 - authentication trap
		     bit 1 - other SNMP traps
		     bit 2 - Error Traps
		     bit 3 - Diagnostic Traps
		     bit 4 - Debug Traps
		     bit 5 - all Enterprise Traps other than fmDiagGenericTrap"
	::= { pTrapAddrEntry 4 }

pTrapAddrState 	OBJECT-TYPE
	SYNTAX  INTEGER {
		active(1),
		inactive(2)
		}
        ACCESS  read-write
        STATUS  mandatory
	DESCRIPTION "Determines status of this entry"
	::= { pTrapAddrEntry 5 }

pTrapLearning	OBJECT-TYPE
	SYNTAX	INTEGER {
		disable(0),
		enable(1)
		}
	ACCESS	read-write
	STATUS  mandatory
	DESCRIPTION "Learn the addresses of the managers
		automatically."
	::= { traperm 2 }

pTrapAging	OBJECT-TYPE
	SYNTAX	INTEGER 
	ACCESS	read-write
	STATUS	mandatory
	DESCRIPTION "Time in sec. until we erase a trap
		entry"
	::= { traperm 3 }

------------------------------------------------

-- System Group RunTime
------------------------------------------------


fmSystemReset	OBJECT-TYPE
	SYNTAX  INTEGER {
		cold-reset(0),
		warm-reset(1),
		power-up(2),
		meaning-less-value(127)
		}
	ACCESS  read-write
	STATUS  mandatory
	DESCRIPTION "Resetting the CARD.
                    When reading the instance of this
	            object the value has no meaning.
		    cold reset is performed with selftest ,
		    while warm start is performed without
		    selftest"

	::= { fmsystemrun 4 }

fmSystemSelfTestLevel	OBJECT-TYPE
	SYNTAX	INTEGER {
		none(0),
		partial(1),
		full(2),
		extended(3)
		}
	ACCESS	read-write
	STATUS	mandatory
	DESCRIPTION "Type of self test to be
		     executed upon cold-reset"
	::= { fmsystemrun 5 }

fmSystemVersion	OBJECT-TYPE
	SYNTAX	DisplayString
	ACCESS	read-only
	STATUS	mandatory
	DESCRIPTION "Version of the station. The version includes
		     station type, hardware version and software version.
		     The string can include CR and LF"
		::= { fmsystemrun 6 }

fmSystemIpAddr		OBJECT-TYPE
	SYNTAX	IpAddress
	ACCESS	read-only
	STATUS  mandatory
	DESCRIPTION "IP address of the agent"
	::= { fmsystemrun 7 }

fmSystemIPNetMask	OBJECT-TYPE
	SYNTAX	IpAddress
	ACCESS	read-only
	STATUS	mandatory
	DESCRIPTION "IP Network Mask"
	::= { fmsystemrun 8 }

fmSystemIPDefGway	OBJECT-TYPE
	SYNTAX	IpAddress
	ACCESS	read-only
	STATUS	mandatory
	DESCRIPTION "Default Gateway Address"
	::= { fmsystemrun 9 }

fmSystemFileServer     OBJECT-TYPE
        SYNTAX  IpAddress
        ACCESS  read-write
        STATUS  mandatory
        DESCRIPTION "IP address to which a TFTP for boot is sent."
        ::= { fmsystemrun 10 }

fmSystemBootFile       OBJECT-TYPE
        SYNTAX  DisplayString
        ACCESS  read-only
        STATUS  mandatory
        DESCRIPTION "Path and file name that is
                   sent as a TFTP request"
        ::= { fmsystemrun 11 }

fmSystemBootMode       OBJECT-TYPE
        SYNTAX  INTEGER {
                internal-memory(1),
                bootp(2)
                }
        ACCESS  read-only
        STATUS  deprecated
        DESCRIPTION "Method for booting"
        ::= { fmsystemrun 12 }

fmSystemDownLoad   OBJECT-TYPE
        SYNTAX  INTEGER {
                download(1),
		meaning-less-value(127)
                }
        ACCESS  read-write
        STATUS  mandatory
        DESCRIPTION "Downloading the ESM.
                     When reading the instance of this
	             object the value has no meaning."
        ::= { fmsystemrun 13 }

fmSystemSlipIpAddr          OBJECT-TYPE
        SYNTAX  IpAddress
        ACCESS  read-only
        STATUS  mandatory
        DESCRIPTION "SLIP IP address.
	            This is object is available
		    only when slip interface exist "
        ::= { fmsystemrun 14 }

fmSystemSlipIPNetMask       OBJECT-TYPE
        SYNTAX  IpAddress
        ACCESS  read-only
        STATUS  mandatory
        DESCRIPTION "SLIP IP Network Mask
	            This is object is available
		    only when slip interface exist "
        ::= { fmsystemrun 15 }

fmSystemSlipBaudRate OBJECT-TYPE
        SYNTAX  INTEGER {
                baud1200(0),
                baud2400(1),
                baud4800(2),
                baud9600(3),
                baud19200(4),
                baud38400(5)
                }
	 
        ACCESS  read-only
        STATUS  mandatory
        DESCRIPTION "SLIP Baud rate
 	             This is object is available
		     only when slip interface exist "
        ::= { fmsystemrun 16 }

fmSystemSlipParity   OBJECT-TYPE
        SYNTAX  INTEGER {
                none(0),
                odd(1),
                even(2)
                }
        ACCESS  read-only
        STATUS  mandatory
        DESCRIPTION "SLIP Parity
	             This is object is available
		     only when slip interface exist "
        ::= { fmsystemrun 17 }

fmSystemSlipStopBits	OBJECT-TYPE
        SYNTAX  INTEGER {
                one(0),
                two(1)
                }
        ACCESS  read-only
        STATUS  mandatory
        DESCRIPTION "SLIP Stop Bits 
	             This is object is available
		     only when slip interface exist "
        ::= { fmsystemrun 18 }


------------------------------------------------
--  System Group Permanent
------------------------------------------------


pfmSystemIpAddr		OBJECT-TYPE
	SYNTAX	IpAddress
	ACCESS	read-write
	STATUS  mandatory
	DESCRIPTION "IP address of the agent"
	::= { fmsystemperm 7 }

pfmSystemIPNetMask	OBJECT-TYPE
	SYNTAX	IpAddress
	ACCESS	read-write
	STATUS	mandatory
	DESCRIPTION "IP Network Mask"
	::= { fmsystemperm 8 }

pfmSystemIPDefGway	OBJECT-TYPE
	SYNTAX	IpAddress
	ACCESS	read-write
	STATUS	mandatory
	DESCRIPTION "Default Gateway Address"
	::= { fmsystemperm 9 }

pfmSystemFileServer	OBJECT-TYPE
	SYNTAX  IpAddress
	ACCESS  read-write
	STATUS  mandatory
	DESCRIPTION "IP address to which a TFTP for boot is sent."
	::= { fmsystemperm 10 }

pfmSystemBootFile	OBJECT-TYPE
	SYNTAX  DisplayString
	ACCESS  read-write
	STATUS  mandatory
	DESCRIPTION "Path and file name that is 
		   sent as a TFTP request"
	::= { fmsystemperm 11 }

pfmSystemBootMode	OBJECT-TYPE
	SYNTAX  INTEGER {
		internal-memory(1),
		bootp(2)
		}
	ACCESS  read-write
	STATUS  mandatory
	DESCRIPTION "Method for booting"
	::= { fmsystemperm 12 }


pfmSystemReadCommunity	OBJECT-TYPE
	SYNTAX	DisplayString
	ACCESS	read-write
	STATUS  mandatory
	DESCRIPTION "Community string for reading
                    When reading the instance of this
                    object the value has no meaning."
	::= { fmsystemperm 13 }

pfmSystemWriteCommunity	OBJECT-TYPE
	SYNTAX	DisplayString
	ACCESS	read-write
	STATUS	mandatory
	DESCRIPTION "Community string for writing
                    When reading the instance of this
                    object the value has no meaning."
	::= { fmsystemperm 14 }
	
pfmSystemSlipIpAddr          OBJECT-TYPE
        SYNTAX  IpAddress
        ACCESS  read-write
        STATUS  mandatory
        DESCRIPTION "SLIP IP address 
                     This is object is available
	             only when slip interface exist "
        ::= { fmsystemperm 15 }

pfmSystemSlipIPNetMask       OBJECT-TYPE
        SYNTAX  IpAddress
        ACCESS  read-write
        STATUS  mandatory
        DESCRIPTION "SLIP IP Network Mask
                     This is object is available
	             only when slip interface exist "
        ::= { fmsystemperm 16 }

	
pfmSystemSlipBaudRate OBJECT-TYPE
        SYNTAX  INTEGER {
                baud1200(0),
                baud2400(1),
                baud4800(2),
                baud9600(3),
                baud19200(4),
                baud38400(5)
                }
        ACCESS  read-write
        STATUS  mandatory
        DESCRIPTION "SLIP Baud rate 
                     This is object is available
	             only when slip interface exist "
        ::= { fmsystemperm 17 }


pfmSystemSlipParity   OBJECT-TYPE
        SYNTAX  INTEGER {
                none(0),
                odd(1),
                even(2)
                }
        ACCESS  read-write
        STATUS  mandatory
        DESCRIPTION "SLIP Parity 
                     This is object is available
	             only when slip interface exist "
        ::= { fmsystemperm 18 }

pfmSystemSlipStopBits    OBJECT-TYPE
        SYNTAX  INTEGER {
                one(0),
                two(1)
                }
        ACCESS  read-write
        STATUS  mandatory
        DESCRIPTION "SLIP Stop Bits 
                     This is object is available
	             only when slip interface exist "
        ::= { fmsystemperm 19 }

------------------------------------------------

-- Slot Group Runtime
------------------------------------------------

fmSlotMasterClear  	OBJECT-TYPE
	SYNTAX	INTEGER
	ACCESS	read-write
	STATUS	mandatory
	DESCRIPTION "Upon writing, performs a master
		     clear command on all the slots.
                   When reading the instance of this
	           object the value has no meaning."
		     
		     
	::= { fmslot 1 }

fmSlotTable	OBJECT-TYPE
	SYNTAX  SEQUENCE OF FmSlotEntry
	ACCESS  not-accessible
	STATUS  mandatory
	::= { fmslot 2 }

fmSlotEntry	OBJECT-TYPE
	SYNTAX  FmSlotEntry
	ACCESS  not-accessible
	STATUS  mandatory
	INDEX   { fmSlotIndex }
	::= { fmSlotTable 1 }


FmSlotEntry ::= SEQUENCE {
	fmSlotIndex
		INTEGER,
        fmSlotID
		INTEGER,
	fmSlotDescr
		DisplayString,
	fmSlotInfo
		DisplayString,
	fmSlotStatus
		OCTET STRING,
	fmSlotPrevStatus
		OCTET STRING,
	fmSlotRLBSet
		INTEGER,
	fmSlotRLBClear
		INTEGER,
	fmSlotExpCode
		INTEGER,
	fmSlotTrapMask
		INTEGER,
	pfmSlotTrapMask
		INTEGER,
        fmSlotIpAddr
                IpAddress,
	fmSlotMngAccess
		INTEGER,
	pfmSlotMngAccess
		INTEGER,
	fmSlotEntityIndex
		INTEGER,
	fmSlotCommunity
		DisplayString,
	fmSlotEntityManager
		INTEGER
	}

fmSlotIndex	OBJECT-TYPE
	SYNTAX  INTEGER
	ACCESS  read-only
	STATUS  mandatory
	DESCRIPTION "Slot Number"
	::= { fmSlotEntry 1 }

fmSlotID	OBJECT-TYPE
	SYNTAX  INTEGER {
		unconfig(0),
		empty(1),
		cc10(2),
		cc12(3),
		cc20(4),
		cc31(5),
		cc32(6),
		cc41(7),
		cc42(8),
		cc44(9),
		cc46A(10),
		not-exist(11),
		cc832(65537),
		lc322(65540),
		cc201(65544),
		cc202(65545),
		cc214(65548),
		cc321(65552),
		cc046B(65553),
		cc301(65560),
		cc303(65562),
		cc308(65563),
		cc233(65568),
		cc260(65576),
		cc427(65580),
		sw11X(65584),
		cc432(65588),
		cc420(65589),
		cc421(65591),
		cc422(65590),
		cc401(65592),
		cc24X(65594),
		cc211(65550),
		cc212(65551),
		lc303(65566),
		lc308(65567),
		lc312(65578),
                cc010-ID(65541),
                cc012-ID(65542),
                cc020-ID(65543),
                cc041-ID(65557),
                cc042-ID(65558),
                cc044-ID(65559),
		general-smartcard(131072),
		lc308-129(131073),
		lc303-129(131075),
		lc312-129(131077),
		lc342(285278465),
		lc348(285278466),
		lc343(285278467),
		lc344(285278468),
		lc342-nm349(285409537),
		lc348-nm349(285409538),
		lc343-nm349(285409539),
		lc344-nm349(285409540),
                lc366(302055681),
                lc362(302055684),
                lc362-em364(302055682),
		lc362-em365(302055683),
                lc362-em364p(302055685),
                lc366p(302055686),
                lc362p(302055689),
                lc362p-em364(302055687),
		lc362p-em365(302055688),
		lc362p-em364p(302055690),				
		xm516(335740929)
	}
	ACCESS  read-write
	STATUS  mandatory
	DESCRIPTION "ID of the card in the slot.
		     Special , not-exist, ID identifies
		     a GigaHUB slot that doesn't exist:
		     slot 5, if a HALF MultiHUB installed, or
		     slot 9, if a FULL MultiHUB installed."
	::= { fmSlotEntry 2 }

fmSlotDescr	OBJECT-TYPE
	SYNTAX  DisplayString
	ACCESS  read-only
	STATUS  mandatory
	DESCRIPTION "Ascii string. Description
		   of the card"
	::= { fmSlotEntry 3 }

fmSlotInfo	OBJECT-TYPE
	SYNTAX	DisplayString
	ACCESS  read-write
	STATUS  mandatory
	DESCRIPTION "User general info for the slot.
		     Can be the use of that slot, its
		     location etc..."
	::= { fmSlotEntry 4 }

fmSlotStatus	OBJECT-TYPE
	SYNTAX  OCTET STRING
	ACCESS  read-only
	STATUS  mandatory
	DESCRIPTION "Status bits of the card in the slot, organized
                     by card channel.  Each channel's status occupies
                     2 bytes. For more information about
		     the meaning of the status, read the
		     specific user manual of each card." 
	::= { fmSlotEntry 5 }

fmSlotPrevStatus	OBJECT-TYPE
	SYNTAX  OCTET STRING
	ACCESS  read-only
	STATUS  mandatory
	DESCRIPTION "Previous status bits of the card in the slot,
                     organized by card channel. Each channel's status
                     occupies 2 bytes.  For more information about
                     the meaning of the status, read the
                     specific user manual of each card.
                     This object id is used 
                     mainly for traps (see Card Trap)."
	::= { fmSlotEntry 6 }

fmSlotRLBSet	OBJECT-TYPE
	SYNTAX  INTEGER
	ACCESS  read-write
	STATUS  mandatory
	DESCRIPTION "Argument: 1 - 4. Perform a
		   RLB set operation on the
   		   channel passed as argument.
                   When reading the instance of this
	           object the value has no meaning."
	::= { fmSlotEntry 7 }

fmSlotRLBClear	OBJECT-TYPE
	SYNTAX  INTEGER
	ACCESS  read-write
	STATUS  mandatory
	DESCRIPTION "Argument: 1 - 4. Perform a
		   RLB clear operation on the
		   channel passed as argument.
                   When reading the instance of this
	           object the value has no meaning."
	::= { fmSlotEntry 8 }

fmSlotExpCode	OBJECT-TYPE
	SYNTAX  INTEGER
	ACCESS  read-write
	STATUS  mandatory
	DESCRIPTION "Perform an expanded command
                     on the slot. For expanded codes,
		     see specific card user manual.
                     When reading the instance of this
	             object the value has no meaning.
		     
		     Extended command codes for NDS cards
		     ------------------------------------

		     1. CC892.303 (Ethernet)
		     
		        Code (Dec/Hex)       Command
			-----------------------------------
			02/02		     Detach Port 13
			03/03		     Attach Port 13
			04/04		     Detach Port 01
			05/05		     Attach Port 01
			06/06		     Detach Port 02
			07/07		     Attach Port 02
			08/08		     Detach Port 03
			09/09		     Attach Port 03
			10/0A		     Detach Port 04
			11/0B		     Attach Port 04
			12/0C		     Detach Port 05
			13/0D		     Attach Port 05
			14/0E		     Detach Port 06
			15/0F		     Attach Port 06
			16/10		     Detach Port 07
			17/11		     Attach Port 07
			18/12		     Detach Port 08
			19/13		     Attach Port 08
			20/14		     Detach Port 09
			21/15		     Attach Port 09
			22/16		     Detach Port 10
			23/17		     Attach Port 10
			24/18		     Detach Port 11
			25/19		     Attach Port 11
			26/1A		     Detach Port 12
			27/1B		     Attach Port 12
			28/1C		     Detach All Ports
			29/1D		     Attach All Ports
			30/1E		     Reset Card       
			31/1F		     Link Select   

			======================================================



		     2. CC892.308 (Ethernet)
		     
		        Code (Dec/Hex)       Command
			-----------------------------------
			02/02		     Detach Port 01
			03/03		     Attach Port 01
			04/04		     Detach Port 02
			05/05		     Attach Port 02
			06/06		     Detach Port 03
			07/07		     Attach Port 03
			08/08		     Detach Port 04
			09/09		     Attach Port 04
			10/0A		     Detach Port 05
			11/0B		     Attach Port 05
			12/0C		     Detach Port 06
			13/0D		     Attach Port 06
			14/0E		     Detach Port 07
			15/0F		     Attach Port 07
			16/10		     Detach Port 08
			17/11		     Attach Port 08
			...
			28/1C		     Detach All Ports
			29/1D		     Attach All Ports
			30/1E		     Reset Card       
			31/1F		     Link Select

			================================================

		     3. CC892.322 (Token-ring)

			Module 323
			----------
		     
		        Code (Dec/Hex)       Command
			-----------------------------------
			02/02		     Detach Port 01
			03/03		     Attach Port 01
			04/04		     Detach Port 02
			05/05		     Attach Port 02
			06/06		     Detach Port 03
			07/07		     Attach Port 03
			08/08		     Detach Port 04
			09/09		     Attach Port 04
			10/0A		     Detach Port 05
			11/0B		     Attach Port 05
			12/0C		     Detach Port 06
			13/0D		     Attach Port 06

			18/12		     Detach Port 07
			19/13		     Attach Port 07
			20/14		     Detach Port 08
			21/15		     Attach Port 08
			22/16		     Detach Port 19
			23/17		     Attach Port 19
			24/18		     Detach Port 10
			25/19		     Attach Port 10
			26/1A		     Detach Port 11
			27/1B		     Attach Port 11
			28/1C		     Detach Port 12
			29/1D		     Attach Port 12

			30/1E		     Reset Card

			34/22		     Detach Port 13
			35/23		     Attach Port 13
			36/24		     Detach Port 14
			37/25		     Attach Port 14
			38/26		     Detach Port 15
			39/27		     Attach Port 15
			40/28		     Detach Port 16
			41/29		     Attach Port 16
			42/2A		     Detach Port 17
			43/2B		     Attach Port 17
			44/2C		     Detach Port 18
			45/2D		     Attach Port 18

			50/32		     Detach Port 19
			51/33		     Attach Port 19
			52/34		     Detach Port 20
			53/35		     Attach Port 20
			54/36		     Detach Port 21
			55/37		     Attach Port 21
			56/38		     Detach Port 22
			57/39		     Attach Port 22
			58/3A		     Detach Port 23
			59/3B		     Attach Port 23
			60/3C		     Detach Port 24
			61/3D		     Attach Port 24

			77/4D		     Detach All Ports
			79/4F		     Attach All Ports

			========================================================

			Module 325
			----------

			30/1E		     Reset Card

			80/50  		     Detach Local Port 1 (channel 1)
			81/51 		     Attach Local Port 1 (channel 1)
			82/52  		     Detach Local Port 2 (channel 1)
			83/53 		     Attach Local Port 2 (channel 1)

			88/58  		     Detach Local Port 1 (channel 3)
			89/59 		     Attach Local Port 1 (channel 3)
			90/5A  		     Detach Local Port 2 (channel 3)
			91/5B 		     Attach Local Port 2 (channel 3)

			77/4D		     Detach All Ports
			79/4F		     Attach All Ports


		     4. CC892.427 (Voice)
		     
		        Code (Dec/Hex)       Command
			-----------------------------------
			04/04		     Loopback OFF on Port 1
			05/05		     Loopback ON on Port 1
			06/06		     Loopback OFF on Port 2
			07/07		     Loopback ON on Port 2
			08/08		     Loopback OFF on Port 3
			09/09		     Loopback ON on Port 3
			10/0A		     Loopback OFF on Port 4
			11/0B		     Loopback ON on Port 4
			12/0C		     Loopback OFF on Port 5
			13/0D		     Loopback ON on Port 5
			14/0E		     Loopback OFF on Port 6
			15/0F		     Loopback ON on Port 6
			16/10		     Loopback OFF on Port 7
			17/11		     Loopback ON on Port 7
			18/12		     Loopback OFF on Port 8
			19/13		     Loopback ON on Port 8
			20/14		     Loopback OFF on Port 9
			21/15		     Loopback ON on Port 9
			22/16		     Loopback OFF on Port 10
			23/17		     Loopback ON on Port 10
			24/18		     Loopback OFF on Port 11
			25/19		     Loopback ON on Port 11
			26/1A		     Loopback OFF on Port 12
			27/1B		     Loopback ON on Port 12
			28/1C		     Loopback OFF on Port 13
			29/1D		     Loopback ON on Port 13
			30/1E		     Loopback OFF on Port 14
			31/1F		     Loopback ON on Port 14
			32/20		     Loopback OFF on Port 15
			33/21		     Loopback ON on Port 15
			34/22		     Loopback OFF on Port 16
			35/23		     Loopback ON on Port 16
			37/25		     Loopback ALL on Ports 1-8
			39/27		     Loopback ALL on Ports 9-16
			40/28		     Alternate Mode on Channel Module #1
			41/29		     Normal Mode on Channel Module #1
			42/2A		     Alternate Mode on Channel Module #2
			43/2B		     Normal Mode on Channel Module #2
			45/2D		     Configuration Load Module #1
			47/2F		     Configuration Load Module #2

			======================================================


			"
	::= { fmSlotEntry 9 }
				

fmSlotTrapMask	OBJECT-TYPE
	SYNTAX	INTEGER {
		no-mask(0),
		mask(1)
		}
	ACCESS	read-write
	STATUS  mandatory
	DESCRIPTION "When the value is 1, no more traps
		     from that slot are sent, until next reset.
		     (temporary mask)"
	::= { fmSlotEntry 10 }

	
pfmSlotTrapMask	OBJECT-TYPE
	SYNTAX	INTEGER {
		no-mask(0),
		mask(1)
		}
	ACCESS	read-write
	STATUS  mandatory
	DESCRIPTION "When the value is 1, no more traps for that slot
	will be sent, starting after next reset (permanent mask)"
	::= { fmSlotEntry 11 }

fmSlotIpAddr          OBJECT-TYPE
        SYNTAX  IpAddress
        ACCESS  read-only
        STATUS  mandatory
        DESCRIPTION " IP address of a channel card."
        ::= { fmSlotEntry 12 }

fmSlotMngAccess          OBJECT-TYPE
	SYNTAX	INTEGER {
		no-SNMP-management(1),
		lan(2),
		management-bus(3)
		}
        ACCESS  read-write
        STATUS  mandatory
        DESCRIPTION 
		"This run-time object determines through which interface the
		SNMP management will be permitted.  The default is
		through the managment bus, via the ESM.  This object value is
		reinitialized to its permanent value after system reset.

		Setting the object is permitted only for slots containing
		active SNMP managers.  Such cards will change management access
		immediately according to the specified value.  Set values must
		be either Management-Bus or LAN and the target slot must 
		contain an active SNMP agent."
        ::= { fmSlotEntry 13 }

pfmSlotMngAccess          OBJECT-TYPE
	SYNTAX	INTEGER {
		no-SNMP-management(1),
		lan(2),
		management-bus(3)
		}
        ACCESS  read-write
        STATUS  mandatory
        DESCRIPTION 
		"This permanent object determines through which interface the
		SNMP management will be permitted.  The default is through the
		managment bus, via the ESM.  

		This object has no effect on slots not containing SNMP agents.

		The run-time object will receive this value after system reset
		only if the value is permitted.

		Setting the object is permitted only for slots containing
		active SNMP managers.  Such cards will change management access
		only the next time the card is initialized.   Set values must
		be either Management-Bus or LAN and the target slot must 
		contain an active SNMP agent."
        ::= { fmSlotEntry 14 }

fmSlotEntityIndex	OBJECT-TYPE
	SYNTAX	INTEGER
        ACCESS  read-only
        STATUS  mandatory
        DESCRIPTION 
		"This object determines the Entity index which the card
		is a memeber in."
        ::= { fmSlotEntry 15 }

fmSlotCommunity		OBJECT-TYPE
	SYNTAX	DisplayString
        ACCESS  read-only
        STATUS  mandatory
        DESCRIPTION 
		"This object determines the Entity Community which the card
		is a memeber in."
        ::= { fmSlotEntry 16 }

fmSlotEntityManager	OBJECT-TYPE
	SYNTAX	INTEGER {
		no-entity-manager(1),
		sNMP-entity-manager(2)
		}
        ACCESS  read-only
        STATUS  mandatory
        DESCRIPTION 
		"This object determines if the card is an SNMP-manageable
		Entity Manager."
        ::= { fmSlotEntry 17 }



------------------------------------------------
-- Logic Unit Group Runtime
------------------------------------------------

fmLUID		OBJECT-TYPE
	SYNTAX  INTEGER {
		unconfig(0),
		none(1),
		lu100(2),  -- for MultiHUB only
		lu101(3),
		lu102(4),
		lu103(5),
		lu104(6),
		lu105(7),
		lu106(8),
		lu107(9),
		lu108(10)
		}
	ACCESS  read-write
	STATUS  mandatory
	DESCRIPTION "Logic unit ID"
	::= { fmlu 1 }

fmLUDescr	OBJECT-TYPE
	SYNTAX  DisplayString
	ACCESS  read-only
	STATUS  mandatory
	DESCRIPTION "Ascii string. Description
		   of the logic unit"
	::= { fmlu 2 }

fmLUStatus	OBJECT-TYPE
	SYNTAX  OCTET STRING
	ACCESS  read-only
	STATUS  mandatory
	DESCRIPTION "One byte of LU status"
	::= { fmlu 3 }


fmLULinkSelect	OBJECT-TYPE
	SYNTAX  INTEGER {
		main-link(0),
		sec-link(1)
		}
	ACCESS  read-write
	STATUS  mandatory
	DESCRIPTION "Setup LU link."
 	::= { fmlu 4 }

fmLULoopBackSet	OBJECT-TYPE
	SYNTAX	INTEGER
	ACCESS	read-write
	STATUS	mandatory
	DESCRIPTION "Upon writing, performs LLB command.
                     When reading the instance of this 
                     object the value has no meaning."
	::= { fmlu 5 }

fmLULoopBackClr	OBJECT-TYPE
	SYNTAX	INTEGER
	ACCESS	read-write
	STATUS	mandatory
	DESCRIPTION "Upon writing, clear LLB command.
                     When reading the instance of this
	             object the value has no meaning."
	::= { fmlu 6 }

fmLUTrapMask	OBJECT-TYPE
	SYNTAX	INTEGER {
		no-mask(0),
		mask(1)
		}
	ACCESS	read-write
	STATUS  mandatory
	DESCRIPTION "When the value is 1, no more traps
		     from the LU are sent, until next reset.
		     (temporary mask)"
	::= { fmlu 7 }

pfmLUTrapMask	OBJECT-TYPE
	SYNTAX	INTEGER {
		no-mask(0),
		mask(1)
		}
	ACCESS	read-write
	STATUS  mandatory
	DESCRIPTION "When the value is 1, no more traps for the LU
	will be sent, starting after next reset (permanent mask)"
	::= { fmlu 8 }



------------------------------------------------
--  Diagnostic Group
------------------------------------------------

fmDiagConfig	OBJECT-TYPE
	SYNTAX	DisplayString
	ACCESS	read-only	
	STATUS	mandatory
	DESCRIPTION "Version of the station. The version includes
		    station type, hardware version and software version.
		    The string can include CR and LF"
		::= { fmdiag 1 }


fmDiagTrapInfo	OBJECT-TYPE
	SYNTAX	DisplayString (SIZE (0..255))
	ACCESS	read-only
	STATUS  mandatory
	DESCRIPTION "Used for generic traps. The first word
		is the trap code. The rest of the string is
		the extra information. Contains CR and LF char."
	::= { fmdiag 2 }


fmDiagFaultTable  OBJECT-TYPE
        SYNTAX  SEQUENCE OF FmDiagFaultEntry 
        ACCESS  not-accessible
	STATUS  optional
  	 DESCRIPTION "Table of fault reports from the agent"
	 ::= { fmdiag 3 }


fmDiagFaultEntry  OBJECT-TYPE
        SYNTAX  FmDiagFaultEntry
	ACCESS  not-accessible
	STATUS  optional
  	INDEX   { fmDiagFaultIndex}
	::=     { fmDiagFaultTable 1 }


FmDiagFaultEntry ::= SEQUENCE {
        fmDiagFaultIndex
	        INTEGER,
        fmDiagFaultReport
	        DisplayString
	}


fmDiagFaultIndex OBJECT-TYPE
        SYNTAX  INTEGER
	ACCESS  read-only
	STATUS  optional
        DESCRIPTION "The fault index in the
  			      fault table"
        ::= { fmDiagFaultEntry 1 }			      		      
						
fmDiagFaultReport	OBJECT-TYPE
	SYNTAX	DisplayString  (SIZE (0..255))
	ACCESS	read-only
	STATUS	optional
  	DESCRIPTION "Get the faults detected by the agent"
        ::= { fmDiagFaultEntry 2 }			      		      

fmDiagDebug     	OBJECT-TYPE
	SYNTAX	INTEGER {
		normal-mode(0),
		debug-mode(1)
		}
	ACCESS	read-write
	STATUS  mandatory
	DESCRIPTION "This object is for factory use only. Users must not
		     write into this variable or improper operation
		     can occur."
	::= { fmdiag 4 }


  -- *********************************************************
  -- **                                                     **
  -- **                                                     **
  -- **        T R A P          D E F I N I T I O N S       **
  -- **                                                     **
  -- **                                                     **
  -- *********************************************************


fmLUOutOfSync		TRAP-TYPE
	ENTERPRISE gigaHUB
	VARIABLES { fmLUID,
		    fmLUStatus
		  }
	DESCRIPTION "Issued when the Logic unit goes
		out of synchronization"
	::= 7

fmLUReturnToSync	TRAP-TYPE
	ENTERPRISE gigaHUB
	VARIABLES { fmLUID,
		    fmLUStatus
		  }
	DESCRIPTION "Issues as soon as the logic unit
		returns to synchronization"
	::= 8

fmLUPassToMain		TRAP-TYPE
	ENTERPRISE gigaHUB
	VARIABLES { fmLUID,
		    fmLUStatus
		  }
	DESCRIPTION "Issues as soon as the logic unit
		pass to main link"
	::= 9

fmLUPassToSecond	TRAP-TYPE
	ENTERPRISE gigaHUB
	VARIABLES { fmLUID,
		    fmLUStatus
		  }
	DESCRIPTION "Issues as soon as the logic unit
		pass to second link"
	::= 10

fmLUPrimaryLinkFail	TRAP-TYPE
	ENTERPRISE gigaHUB
	VARIABLES { fmLUID,
		    fmLUStatus
		  }
	DESCRIPTION "When primary link of the logic unit  fails
		 this trap is issued"
	::= 11

fmLUPrimaryLinkOK	TRAP-TYPE
	ENTERPRISE gigaHUB
	VARIABLES { fmLUID,
		    fmLUStatus
		  }
	DESCRIPTION "When primary link of the logic unit  fails
		 this trap is issued"
	::= 12

fmLUSecondLinkFail	TRAP-TYPE
	ENTERPRISE gigaHUB
	VARIABLES { fmLUID,
		    fmLUStatus
		  }
	DESCRIPTION "When second link of the logic unit  fails
		 this trap is issued"
	::= 13

fmLUSecondLinkOK	TRAP-TYPE
	ENTERPRISE gigaHUB
	VARIABLES { fmLUID,
		    fmLUStatus
		  }
	DESCRIPTION "When second link of the logic unit  fails
		 this trap is issued"
	::= 14

	
fmLULLBOn		TRAP-TYPE
	ENTERPRISE gigaHUB
	VARIABLES { fmLUID,
		    fmLUStatus
		  }
	DESCRIPTION "When the logic unit enters LLB mode"
	::= 15

fmLULLBOff		TRAP-TYPE
	ENTERPRISE gigaHUB
	VARIABLES { fmLUID,
		    fmLUStatus
		  }
	DESCRIPTION "When the logic unit exits LLB mode"
	::= 16

fmLUChangeConfig		TRAP-TYPE
	ENTERPRISE gigaHUB
	VARIABLES { fmLUID,
		    fmLUStatus
		  }
	DESCRIPTION "Issues when a change in the LU configuration
		is done"
	::= 20

fmSlotTrap		TRAP-TYPE
	ENTERPRISE gigaHUB
	VARIABLES { fmSlotIndex,
		    fmSlotID,
		    fmSlotStatus,
		    fmSlotPrevStatus }
	DESCRIPTION "Generated when a significant status has
		changed in a slot. By xoring the 2 statuses,
		the NMS can identify the cause of the trap."
	::= 25

fmSlotChangeConfig	TRAP-TYPE
	ENTERPRISE gigaHUB
	VARIABLES { fmSlotIndex,
		    fmSlotID,
		    fmSlotStatus
		   }
	DESCRIPTION "Issued when the system detects
		 changes in its slots configuration"
	::= 26

fmDiagGenericTrap	TRAP-TYPE
	ENTERPRISE gigaHUB
	VARIABLES { fmDiagTrapInfo }
	DESCRIPTION "Generic Trap information"
	::= 30




------------------------------------------------
--
--          GigaHub Private (non-chassis-MIB) MIB
--
------------------------------------------------

--
-- Gighub Resource Table 
--

gigaPhyResourceTable OBJECT-TYPE
	SYNTAX SEQUENCE OF GigaPhyResourceEntry
	ACCESS  not-accessible
        STATUS mandatory
        DESCRIPTION
	"This table maps resources to backplane segments/ring numbers"
        ::= { gigaHUBPrivate 1 }

gigaPhyResourceEntry OBJECT-TYPE
        SYNTAX GigaPhyResourceEntry
        ACCESS not-accessible
        STATUS mandatory
        DESCRIPTION
	"This table maps resources to backplane segments/ring numbers"
        INDEX { gigaPhyResLocationType, gigaPhyResLocation, gigaPhyResIndex }
        ::= { gigaPhyResourceTable 1 }

GigaPhyResourceEntry ::= SEQUENCE {
	gigaPhyResLocationType
	    INTEGER,
	gigaPhyResLocation
	    INTEGER,
	gigaPhyResIndex
            INTEGER,
	gigaPhyResType
	    OBJECT IDENTIFIER,
	gigaPhyResCapability
            INTEGER,		
	gigaPhyResSegRing
	    INTEGER
      }

gigaPhyResLocationType  OBJECT-TYPE
	SYNTAX INTEGER
	ACCESS read-only
	STATUS mandatory
        DESCRIPTION
		"A unique integer representing the location type index"
	    ::= { gigaPhyResourceEntry 1 }

gigaPhyResLocation OBJECT-TYPE
	SYNTAX INTEGER
	ACCESS read-only
	STATUS mandatory
        DESCRIPTION
		"A unique integer representing the location type instance"
	    ::= { gigaPhyResourceEntry 2 }

gigaPhyResIndex  OBJECT-TYPE
	SYNTAX INTEGER
	ACCESS read-only
	STATUS mandatory
        DESCRIPTION
		"A unique integer representing the resource instance at this 
                 location"
	    ::= { gigaPhyResourceEntry 3 }

gigaPhyResType  OBJECT-TYPE
	SYNTAX OBJECT IDENTIFIER
        ACCESS read-only
	STATUS mandatory
	DESCRIPTION
		"The type of resource."
	    ::= { gigaPhyResourceEntry 4 }

gigaPhyResCapability  OBJECT-TYPE
	SYNTAX INTEGER {
		no-bus(1),
                esb(17),
                eb2(19),
		eb2-one(20),
		eb2-two(21),
		eb2-three(22),
		eb2-four(23),
		tr-4M(33),
		tr-16M(34),
		fddi-100M(49) }
	ACCESS read-only
	STATUS mandatory
        DESCRIPTION
		"A unique integer representing the resource capability for
		 attachment to the serial busses."
	    ::= { gigaPhyResourceEntry 5 }

gigaPhyResSegRing  OBJECT-TYPE
	SYNTAX INTEGER
	ACCESS read-write
	STATUS mandatory
        DESCRIPTION
		"A unique integer representing the ring or segment number in
                 which the resource is attached to."
	    ::= { gigaPhyResourceEntry 6 }


-- the Ebm ( Ethernet Bus Module ) cards table

          gigaEbmTable OBJECT-TYPE
              SYNTAX SEQUENCE OF GigaEbmEntry
              ACCESS not-accessible
              STATUS mandatory
              DESCRIPTION
                      "A list of EBM cards entries, one for each 
		       EBM card in the chassis."
              ::= { gigaHUBPrivate 2 }

          gigaEbmEntry OBJECT-TYPE
              SYNTAX GigaEbmEntry
              ACCESS not-accessible
              STATUS mandatory
              DESCRIPTION
                      "Values for a EBM card."
              INDEX { gigaEbmIndex }
              ::= { gigaEbmTable 1 }

          GigaEbmEntry ::=
              SEQUENCE {
                  gigaEbmIndex
                      INTEGER,
                  gigaEbmDescr
                      DisplayString,
                  gigaEbmOperStatus
                      INTEGER
              }

          gigaEbmIndex OBJECT-TYPE
              SYNTAX INTEGER
              ACCESS read-only
              STATUS mandatory
              DESCRIPTION
                      "An index value that uniquely identifies a 
		       EBM card"
              ::= { gigaEbmEntry 1 }

          gigaEbmDescr OBJECT-TYPE
              SYNTAX DisplayString (SIZE (0..255))
              ACCESS read-only
              STATUS mandatory
              DESCRIPTION
                      "A textual description of the EBM card."
              ::= { gigaEbmEntry 2 }

          gigaEbmOperStatus OBJECT-TYPE
              SYNTAX INTEGER {
		  unknown(1),
                  empty(2),
                  bad(3),
                  good(4),
                  active(5) }
              ACCESS read-only
              STATUS mandatory
              DESCRIPTION
                      "Actual status of the EBM card:
		      - unknown(1) - don't have the information
                      - empty(2) - no EBM card installed in slot
                      - bad(3) - unable to work due to failure
                      - good(4) - the card is good
                      - active(5) - the card is good and active"
              ::= { gigaEbmEntry 3 }


          AutonomousType    ::= OBJECT IDENTIFIER

          -- The object identifier is an independently extensible type
          -- identification value.  It may, for example indicate a
          -- particular sub-tree with further MIB definitions, or
          -- define something like a protocol type or type of
          -- hardware.


          -- Groups within the chassis MIB

          chasInfo            OBJECT IDENTIFIER ::= { gigaHUBChassis 1 }
          chasPhysical        OBJECT IDENTIFIER ::= { gigaHUBChassis 2 }
          chasEntity          OBJECT IDENTIFIER ::= { gigaHUBChassis 3 }
          chasResource        OBJECT IDENTIFIER ::= { gigaHUBChassis 4 }
          chasPowerSupply     OBJECT IDENTIFIER ::= { gigaHUBChassis 5 }
          chasEnviron         OBJECT IDENTIFIER ::= { gigaHUBChassis 6 }

          -- Chassis MIB Know Types

          chasKnownTypes      OBJECT IDENTIFIER ::= { gigaHUBChassis 7 }

          -- Values for known chasPhyLocationType. The types of
          --    location in the chassis.

          chasLocationTypes   OBJECT IDENTIFIER ::= { chasKnownTypes 1 }

          chasModularSlot     OBJECT IDENTIFIER ::= { chasLocationTypes 1 }
          chasPowerSupplyBay  OBJECT IDENTIFIER ::= { chasLocationTypes 2 }
          chasFanTray         OBJECT IDENTIFIER ::= { chasLocationTypes 3 }
          chasBackplane       OBJECT IDENTIFIER ::= { chasLocationTypes 4 }
          chasFrontSlot       OBJECT IDENTIFIER ::= { chasLocationTypes 5 }
          chasBackSlot        OBJECT IDENTIFIER ::= { chasLocationTypes 6 }

          -- Values for chasModuleType.

          chasModuleTypes  OBJECT IDENTIFIER ::= { chasKnownTypes 2 }
          chasLocationEmpty   OBJECT IDENTIFIER ::= { chasModuleTypes 1 }
          chasModuleUnknown   OBJECT IDENTIFIER ::= { chasModuleTypes 2 }

          -- Values for chasEntityObjectId.

          chasEntityTypes  OBJECT IDENTIFIER ::= { chasKnownTypes 3 }

          -- Chassis components non-networking

          chasChassisEntities OBJECT IDENTIFIER ::= { chasEntityTypes 1 }


          chasPowerSource  OBJECT IDENTIFIER ::= { chasChassisEntities  1 }
          chasChassis      OBJECT IDENTIFIER ::= { chasChassisEntities  2 }
          chasMonitor      OBJECT IDENTIFIER ::= { chasChassisEntities  3 }

          -- Basic Network Entities

          chasNetEntities OBJECT IDENTIFIER ::= { chasEntityTypes 2 }

          chas8023Repeater OBJECT IDENTIFIER ::= { chasNetEntities 1 }
          chas8025Ring     OBJECT IDENTIFIER ::= { chasNetEntities 2 }
          chasFddiRing     OBJECT IDENTIFIER ::= { chasNetEntities 3 }
          chasAtmSwitch    OBJECT IDENTIFIER ::= { chasNetEntities 4 }
          chasFrameRelay   OBJECT IDENTIFIER ::= { chasNetEntities 5 }
	  chasEthSwitch    OBJECT IDENTIFIER ::= { chasNetEntities 6 }

          -- Internetworking/Bridging

          chasConnectEntities OBJECT IDENTIFIER ::= { chasEntityTypes 3 }
          chasBridge    OBJECT IDENTIFIER ::= { chasConnectEntities 1 }
          chasRouter    OBJECT IDENTIFIER ::= { chasConnectEntities 2 }
          chasBrouter   OBJECT IDENTIFIER ::= { chasConnectEntities 3 }
          chasGateway   OBJECT IDENTIFIER ::= { chasConnectEntities 4 }

          --  Values for chasResourceType.

          chasResTypes  OBJECT IDENTIFIER ::= { chasKnownTypes 4 }

          --  Chassis type resources.

          chasChassisRes OBJECT IDENTIFIER ::= { chasResTypes 1 }

          --  Basic Network Resource

          chasNetworkRes OBJECT IDENTIFIER ::= { chasResTypes 2 }

          chas8023RptrPort  OBJECT IDENTIFIER ::= { chasNetworkRes 1 }
          chas8025MauPort   OBJECT IDENTIFIER ::= { chasNetworkRes 2 }
          chasFddiPort      OBJECT IDENTIFIER ::= { chasNetworkRes 3 }
          chasAtmPort       OBJECT IDENTIFIER ::= { chasNetworkRes 4 }
          chas8023PortGroup OBJECT IDENTIFIER ::= { chasNetworkRes 5 }
          chas8025PortGroup OBJECT IDENTIFIER ::= { chasNetworkRes 6 }
          chasFddiPortGroup OBJECT IDENTIFIER ::= { chasNetworkRes 7 }
          chasAtmPortGroup  OBJECT IDENTIFIER ::= { chasNetworkRes 8 }

          -- Backplane Network Resources (if required)

          chasBplaneRes  OBJECT IDENTIFIER ::= { chasResTypes 3 }

          chas8023Bplane    OBJECT IDENTIFIER ::= { chasBplaneRes  1 }
          chas8025Bplane    OBJECT IDENTIFIER ::= { chasBplaneRes  2 }
          chasFddiBplane    OBJECT IDENTIFIER ::= { chasBplaneRes  3 }
          chasMgmtBplane    OBJECT IDENTIFIER ::= { chasBplaneRes  4 }
          chasAtmBplane     OBJECT IDENTIFIER ::= { chasBplaneRes  5 }

          -- Internetworking/bridging resources (if required)

          chasConnectRes OBJECT IDENTIFIER ::= { chasResTypes 4 }

          chasBridgeRelay   OBJECT IDENTIFIER ::= { chasConnectRes 1 }
          chasRouterRelay   OBJECT IDENTIFIER ::= { chasConnectRes 2 }
          chasBrouterRelay  OBJECT IDENTIFIER ::= { chasConnectRes 3 }
          chasSwitch        OBJECT IDENTIFIER ::= { chasConnectRes 4 }

          -- Well known environmental sensor types

          wellKnownSensors   OBJECT IDENTIFIER ::= { chasKnownTypes 5 }
          sensorOther        OBJECT IDENTIFIER ::= { wellKnownSensors 1 }
          sensorTemperature  OBJECT IDENTIFIER ::= { wellKnownSensors 2 }
          sensorFans         OBJECT IDENTIFIER ::= { wellKnownSensors 3 }
          sensorHumidity     OBJECT IDENTIFIER ::= { wellKnownSensors 4 }


          -- chasInfo group (chassis information group).

          chasType  OBJECT-TYPE
              SYNTAX  OBJECT IDENTIFIER
              ACCESS  read-only
              STATUS  mandatory
              DESCRIPTION
                      "An authoritative identification of the type of
                      hub-based or standalone chassis.  By convention
                      this value is allocated within the SMI enterprises
                      subtree(1.3.6.1.4.1), and provides an easy and
                      unambiguous means for determining `what kind of
                      box' is being managed.  If this information is not
                      present or unknown, its value should be set to the
                      value: chasTypeUnknown."
              ::= { chasInfo 1 }

          chasPhysicalChanges  OBJECT-TYPE
              SYNTAX   Counter
              ACCESS   read-only
              STATUS   mandatory
              DESCRIPTION
                      "The number of physical changes that have occurred
                      in the chassis since the agent was warm/cold
                      started.  This includes additions and removal of
                      modules and entities.  Other uses are
                      implementation specific."
              ::= { chasInfo 2 }


          chasChassisSerialNumber   OBJECT-TYPE
              SYNTAX    DisplayString (SIZE (0..32))
              ACCESS    read-only
              STATUS    mandatory
              DESCRIPTION
                      "The serial number of the chassis. If no serial
                      number is available then this object should be the
                      zero length string."
              ::= { chasInfo 3 }

-- the MultiHUB configuration in the chassis

          chasMultiConf OBJECT-TYPE
              SYNTAX INTEGER {
                  unknown(1),             --  none of the following
                  none(2),
                  half(3),
                  full(4) }
              ACCESS read-only
              STATUS mandatory
              DESCRIPTION
                      "Which type of MultiHUB is installed in the chassis."
              ::= { chasInfo 4 }


          -- chasPhysical group (physical configuration group).

          chasPhyLocationTable OBJECT-TYPE
              SYNTAX SEQUENCE OF ChasPhyLocationEntry
              ACCESS not-accessible
              STATUS mandatory
              DESCRIPTION
                      "This table summarises the different classes of
                      and types of modular physical locations in the
                      chassis.  This includes but is not limited to slot
                      within a chassis, power supply bay."
              ::= { chasPhysical 1 }

          chasPhyLocationEntry OBJECT-TYPE
              SYNTAX ChasPhyLocationEntry
              ACCESS not-accessible
              STATUS mandatory
              DESCRIPTION
                      "An entry in the phyLocationTable"
              INDEX { chasPhyLocationTypeIndex }
              ::= { chasPhyLocationTable 1 }

          ChasPhyLocationEntry ::= SEQUENCE {
                  chasPhyLocationTypeIndex
                          INTEGER,
                  chasPhyLocationCount
                          INTEGER,
                  chasPhyLocationType
                          OBJECT IDENTIFIER,
                  chasPhyLocationDescr
                          DisplayString
                  }

          chasPhyLocationTypeIndex OBJECT-TYPE
              SYNTAX INTEGER (1..65535)
              ACCESS read-only
              STATUS mandatory
              DESCRIPTION
                      "This uniquely identifies the physical location
                      type within the chassis."
              ::= { chasPhyLocationEntry 1 }

          chasPhyLocationCount  OBJECT-TYPE
              SYNTAX INTEGER (1..65535)
              ACCESS read-only
              STATUS mandatory
              DESCRIPTION
                      "This defines the number of physical locations of
                        this type exist within the chassis."
              ::= { chasPhyLocationEntry 2 }

          chasPhyLocationType OBJECT-TYPE
              SYNTAX OBJECT IDENTIFIER
              ACCESS read-only
              STATUS mandatory
              DESCRIPTION
                      " Uniquely identifies the 'type' of the physical
                      location within the chassis."
              ::= { chasPhyLocationEntry 3 }

          chasPhyLocationDescr OBJECT-TYPE
              SYNTAX DisplayString
              ACCESS read-only
              STATUS mandatory
              DESCRIPTION
                      "Each type of physical location within the chassis
                      is given a textual name."
              ::= { chasPhyLocationEntry 4 }

          chasPhyModuleTable OBJECT-TYPE
              SYNTAX SEQUENCE OF ChasPhyModuleEntry
              ACCESS not-accessible
              STATUS mandatory
              DESCRIPTION
                      "This table defines the physical modules within a
                      chassis.  This is done by defining the type
                      physical modules and the physical location where
                      it resides.  This table also provides a mapping
                      between physical modules and their location
                      within the chassis."
              ::= { chasPhysical 2 }

          chasPhyModuleEntry OBJECT-TYPE
              SYNTAX ChasPhyModuleEntry
              ACCESS not-accessible
              STATUS mandatory
              DESCRIPTION
                      "An entry in this table that describes a physical
                      module that resides at a given physcial location
                      within the chassis."
              INDEX { chasPhyModuleLocationType, chasPhyModuleLocation }
              ::= { chasPhyModuleTable 1 }

          ChasPhyModuleEntry ::= SEQUENCE {
              chasPhyModuleLocationType
                  INTEGER,
              chasPhyModuleLocation
                  INTEGER,
              chasPhyModuleType
                  OBJECT IDENTIFIER,
              chasPhyModuleSwVersion
                  DisplayString,
              chasPhyModuleHwVersion
                  DisplayString,
              chasPhyModuleSerialNumber
                  DisplayString,
              chasPhyModuleDescription
                  DisplayString,
              chasPhyModuleLastChangeTime
                  TimeTicks,
              chasPhyModuleAdminStatus
                  INTEGER,
              chasPhyModuleOperStatus
                  INTEGER
              }

          chasPhyModuleLocationType  OBJECT-TYPE
                  SYNTAX INTEGER
                  ACCESS read-only
                  STATUS mandatory
                  DESCRIPTION
                      "An instance of a module is identified by the
                      physical location in which it resides.  The physical
                      location is identified by location type index and
                      location index (instance of that location type).
                      This object defines an instance of the
                      chasPhyLocationType."
                  ::= { chasPhyModuleEntry 1 }

          chasPhyModuleLocation  OBJECT-TYPE
                  SYNTAX INTEGER
                  ACCESS read-only
                  STATUS mandatory
                  DESCRIPTION
                      "An instance of a module is identified by the
                      physical location which it resides.  The physical
                      location is identified by location type index and
                      location index (instance of that location type).
                      This object defines the instance of a particular
                      location type.  It must be within the bounds
                      defined by chasPhyLocationCount."
                  ::= { chasPhyModuleEntry 2 }

          chasPhyModuleType OBJECT-TYPE
              SYNTAX OBJECT IDENTIFIER
              ACCESS read-only
              STATUS mandatory
              DESCRIPTION
                      "An authoritative identification of the type of
                      physcial module in this physical location.  A
                      value of chasModuleUnknown indicates that the
                      type of physical module is unknown."
              ::= { chasPhyModuleEntry 3 }

          chasPhyModuleSwVersion OBJECT-TYPE
              SYNTAX DisplayString (SIZE (0..32))
              ACCESS read-only
              STATUS mandatory
              DESCRIPTION
                      "A textual description of the version/revision
                      level for this module's software.  If not realized
                      this value should be set to the zero-length
                      string."
              ::= { chasPhyModuleEntry 4 }

          chasPhyModuleHwVersion OBJECT-TYPE
              SYNTAX DisplayString (SIZE (0..32))
              ACCESS read-only
              STATUS mandatory
              DESCRIPTION
                      "A textual description of the version/revision
                      level for this module's firmware.  If not realized
                      this value should be set to the zero-length
                      string."
              ::= { chasPhyModuleEntry 5 }

          chasPhyModuleSerialNumber OBJECT-TYPE
              SYNTAX DisplayString (SIZE (0..32))
              ACCESS read-only
              STATUS mandatory
              DESCRIPTION
                      "The serial number of the physical module present
                      in this physical location.  If the physical
                      location table is implemented as dense and the
                      slot is empty this value will be the zero length
                      string.  If no serial number is available for a
                      physical module this value should set to a zero
                      length string."
              ::= { chasPhyModuleEntry 6 }

          chasPhyModuleDescription OBJECT-TYPE
              SYNTAX DisplayString (SIZE (0..32))
              ACCESS read-only
              STATUS mandatory
              DESCRIPTION
                      "A textual description of the physical module
                      plugged that resides in this physical location.
                      If not available this value should be set to a
                      zero length string."
              ::= { chasPhyModuleEntry 7 }

          chasPhyModuleLastChangeTime OBJECT-TYPE
              SYNTAX TimeTicks
              ACCESS read-only
              STATUS mandatory
              DESCRIPTION
                      "The value of MIB-II's sysUpTime (in the agent
                      supporting this chassis MIB) at which a module was
                      last inserted or initialized.  If the module has
                      not changed since the last network managment
                      system reinitialized then this object has a zero
                      value."
              ::= { chasPhyModuleEntry 8 }

          chasPhyModuleAdminStatus OBJECT-TYPE
              SYNTAX INTEGER {
		  unknown(1),
                  enable(2),
                  disable(3),
                  sw-reset(4),
                  programLoad(5),
                  test(6),
		  hw-reset(7)
              }
              ACCESS read-write
              STATUS mandatory
              DESCRIPTION
                     "Provides desired state of the given physical
                      module.  Notice that not all values may be
                      supported by the specified physical module.  In
                      this case and SNMP error will be returned when the
                      set is attempted.

                      A physical module maybe activated by writing a
                      value of enable(2).

                      A physical module may be de-activated by writing
                      a value of disable(3).  In a disabled state a
                      physical module is present in the chassis but is
                      benign.

                      Writing a value of sw-reset(4) initiates a 
		      software reset sequence.

                      Writing a value of hw-reset(7) initiates a 
		      hardware reset sequence.

                      A value of programLoad(5) initiates a software
                      load sequence.

                      Writing a value of test(6) should start a self
                      test sequence within the physical module."
              ::= { chasPhyModuleEntry 9 }

          chasPhyModuleOperStatus OBJECT-TYPE
              SYNTAX INTEGER {
                  other(1),
                  invalid(2),
                  test(3),
                  operational(4),
                  resetInProgress(5),
                  warning(6),
                  nonFatalError(7),
                  fatalError(8),
		  programLoad(9)
              }
              ACCESS read-only
              STATUS mandatory
              DESCRIPTION
                     "Provides operational status of the module.  The
                      following are possible definitions of the values.
                      The exact definition of the values is
                      implementation specific.  A value of other(1)
                      implies some undetermined state, possibly as a
                      result of setting phyAdminStatus to a value of
                      disable(3).  A value of invalid(2) could have the
                      possible meaning that the module exists but the
                      chassis manager has no direct control over the
                      module.  A value of testing(3) may be a diagnostic
                      state.  A value of operational(4) implies that the
                      entity is running with no errors or warnings.
                      State resetInProgress(5) implies equivalent of
                      setting phyAdminStatus to reset(4). The states of
                      warning(6), nonFatalError(7), fatalError(8)
                      reflect conditions detected during operation.  The
                      entity may or may not be still functional.

                      For example if a modules value of phyAdminStatus
                      is disable(3) and is set to enable(2) then
                      phyOperStatus may enter a state of testing(3) then
                      change to a value of operational(4)."
              ::= { chasPhyModuleEntry 10 }


          -- The chasEntity group. 

          -- Entity Table

          chasEntityTable OBJECT-TYPE
              SYNTAX  SEQUENCE OF ChasEntityEntry
              ACCESS  not-accessible
              STATUS  mandatory
              DESCRIPTION
                      "A table that contains information about the
                      'logical' networking devices (entities) in this
                      chassis."
              ::= { chasEntity 1 }

          chasEntityEntry OBJECT-TYPE
              SYNTAX  ChasEntityEntry
              ACCESS  not-accessible
              STATUS  mandatory
              DESCRIPTION
                      "Information concerning an entity in the chassis.
                      Conceptual rows may not be created or deleted with
                      SNMP operations."
              INDEX  { chasEntityIndex }
              ::= { chasEntityTable 1 }

          ChasEntityEntry ::=
              SEQUENCE {
                  chasEntityIndex
                      INTEGER,
                  chasEntityObjectID
                      OBJECT IDENTIFIER,
                  chasEntityDescr
                      DisplayString,
                  chasEntityAdminStatus
                      INTEGER,
                  chasEntityOperStatus
                      INTEGER,
                  chasEntityTimeStamp
                      TimeTicks,
                  chasEntityParty
                      Party,
                  chasEntityContext
                      Context,
                  chasEntityCommunity
                      DisplayString,
                  chasEntityIpAddress
                      IpAddress
              }

          chasEntityIndex OBJECT-TYPE
              SYNTAX  INTEGER (1..65535)
              ACCESS  read-only
              STATUS  mandatory
              DESCRIPTION
                      "A unique index for the entity for which this
                      entry contains information."
              ::= { chasEntityEntry 1 }

          chasEntityObjectID  OBJECT-TYPE
              SYNTAX  OBJECT IDENTIFIER
              ACCESS  read-only
              STATUS  mandatory
              DESCRIPTION
                      "The specific type of entity.  The value of this
                      object is analagous to MIB-II's sysObjectId.  In
                      particular, it has the same value as would be
                      returned if the SNMP Party (identified by
                      chasEntityParty) and/or the community (identified
                      by chasIpAddress and chasCommunity), were queried
                      for sysObjectId."
              ::= { chasEntityEntry 2 }


          chasEntityDescr  OBJECT-TYPE
              SYNTAX  DisplayString (SIZE (0..255))
              ACCESS  read-write
              STATUS  mandatory
              DESCRIPTION
                      "A textual description of the entity.  The value
                      of this object is analagous to MIB-II's sysDescr.
                      In particular, it has the same value as would be
                      returned if the SNMP Party (identified by
                      chasEntityParty) and/or the community (identified
                      by chasIpAddress and chasCommunity), were queried
                      for sysDescr."
              ::= { chasEntityEntry 3 }

          chasEntityAdminStatus OBJECT-TYPE
              SYNTAX  INTEGER {
                  unknown(1),             --  none of the following
                  enable(2),
                  disable(3),
                  reset(4),
                  programload(5),
                  test(6)
              }
              ACCESS  read-write
              STATUS  mandatory
              DESCRIPTION
                      "Provides the administratively desired state of
                      the given entity.

                      An entity is activated by writing a value of
                      enable(2).

                      An entity may be de-activated by writing a value
                      of disable(3).  In a disabled state, a entity does
                      exist within the given chassis, but is benign.  A
                      disabled entity is available for subsequent
                      activation.

                      Writing a value of reset(4) specifies an entity
                      should initiate a reset sequence.

                      Writing a value of programload(5) specifies an
                      entity should initiate a program load sequence.

                      Writing a value of test(6) specifies an entity
                      should initiate a testing sequence.

                      Agent support of the writing of any of the values
                      of this object is implementation-specific.  For
                      example, this object might be read only for
                      entities that disabling would compromise the
                      integrity of the chassis."
              ::= { chasEntityEntry 4 }

          chasEntityOperStatus OBJECT-TYPE
              SYNTAX  INTEGER {
                  other(1),               --  none of the following
                  invalid(2),
                  testing(3),
                  operational(4),
                  resetInProgress(5),
                  warning(6),
                  nonFatalError(7),
                  fatalError(8),
                  loading(10)
              }
              ACCESS  read-only
              STATUS  mandatory
              DESCRIPTION
                      "Provides operational status of the entity.  The
                      following are possible definitions of the values.
                      The exact definition of the values is
                      implementation specific.  A value of other(1)
                      implies some undetermined state, possibly as a
                      result of setting chasEntityAdminStatus to a value
                      of disable(3).  A value of invalid(2) could have
                      the possible meaning that the entity exists but
                      the chassis manager has no direct control of the
                      entity.  A value of testing(3) may be a diagnostic
                      state.  A value of operational(4) implies that the
                      entity is running with no errors or warnings.
                      State resetInProgress(5) implies equivalent of
                      setting chasEntityAdminStatus to reset(4). The
                      states of warning(6), nonFatalError(7),
                      fatalError(8) reflect conditions detected during
                      operation.  The entity may or may not be still
                      functional.  State loading(10) is a result of
                      asserting programload(5) in chasEntityAdminStatus.

                      For example if an entities value of
                      chasEntityAdminStatus is disable(3) and is set to
                      enable(2) then chasEntityOperStatus may enter a
                      state of testing(3) then change to a value of
                      operational(4)."
              ::= { chasEntityEntry 5 }


          chasEntityTimeStamp  OBJECT-TYPE
              SYNTAX  TimeTicks
              ACCESS  read-only
              STATUS  mandatory
              DESCRIPTION
                      "The value of MIB-II's sysUpTime (in the agent
                      supporting this MIB) at which this entity was last
                      (re-)initialized.  If the entity has not been
                      initialized then this object has a zero value."
              ::= { chasEntityEntry 6 }

          chasEntityParty  OBJECT-TYPE
              SYNTAX  Party
              ACCESS  read-only
              STATUS  mandatory
              DESCRIPTION
                      "The SNMP Party which provides access to the
                      detailed management information for this entity.
                      Note that the definition of a SNMP Party includes
                      the location at which it executes, the
                      authentication and privacy algorithms and
                      parameters required to access the management
                      entity.  In order for a SNMP manager to be able to
                      access the Party, that manager must have prior
                      knowledge of the Party.

                      A party is named by a 'Party'.  For a
                      entity which is not managed through access to a
                      SNMP Party, the value of this object is 0.0 "
              ::= { chasEntityEntry 7 }

          chasEntityContext    OBJECT-TYPE
              SYNTAX  Context
              ACCESS  read-only
              STATUS  mandatory
              DESCRIPTION
                      "The SNMPv2 Context indentifier the
                      chasEntityContext in conjunction with
                      chasEntityParty defines access to the MIB view for
                      this entity."
              ::= { chasEntityEntry 8 }

          chasEntityCommunity  OBJECT-TYPE
              SYNTAX  DisplayString (SIZE (0..255))
              ACCESS  read-only
              STATUS  mandatory
              DESCRIPTION
                      "The SNMP Community which executes at the address
                      chasEntityIpAddress, and provides access to the
                      detailed management information for this entity.

                      For a entity which is not managed through access
                      to a SNMP Community, the value of this object is
                      the zero-length string."
              ::= { chasEntityEntry 9 }

          chasEntityIpAddress  OBJECT-TYPE
              SYNTAX  IpAddress
              ACCESS  read-only
              STATUS  mandatory
              DESCRIPTION
                      "The address of the SNMP agent which responds to
                      messages for the SNMP Community identified by
                      chasEntityCommunity.  When access is via proxy,
                      this variable contains the address of the proxy
                      agent.

                      For a entity which is not managed through access
                      to a SNMP Community, the value of this object is
                      0.0.0.0."
              ::= { chasEntityEntry 10 }


          -- The chasResource group.
          -- This defines a mapping of physical relationship (modules/resources)
          -- and a logical mapping of resource to entities.


          chasPhyResourceTable  OBJECT-TYPE
              SYNTAX  SEQUENCE OF ChasPhyResourceEntry
              ACCESS  not-accessible
              STATUS  mandatory
              DESCRIPTION
                      "This table defines a physical relationship
                      between physical modules and resources.  A
                      resource is a building block.  A resource defines
                      the type of relationship between entities.  This
                      may be a back plane connection between physical
                      modules sharing the same entity.  It may be a
                      network segment that connects multiple entities.

                      This table then defines the physical mapping of
                      resources and physical modules onto entities."
              ::= { chasResource 1 }

          chasPhyResourceEntry  OBJECT-TYPE
              SYNTAX  ChasPhyResourceEntry
              ACCESS  read-only
              STATUS  mandatory
              DESCRIPTION
                      "Defines a particular physical configuration
                      relationship."
              INDEX { chasPhyResLocationType,
                      chasPhyResLocation,
                      chasPhyResIndex }
              ::= { chasPhyResourceTable 1 }

          ChasPhyResourceEntry ::= SEQUENCE {
              chasPhyResLocationType
                  INTEGER,
              chasPhyResLocation
                  INTEGER,
              chasPhyResIndex
                  INTEGER,
              chasPhyResType
                  OBJECT IDENTIFIER,
              chasPhyResAssignment
                  INTEGER,
              chasPhyResEntitySubIndex
                  INTEGER
              }

          chasPhyResLocationType  OBJECT-TYPE
              SYNTAX  INTEGER
              ACCESS  read-only
              STATUS  mandatory
              DESCRIPTION
                      "A resource exists on a particular module.  A
                      module is identified by it's physical location.
                      Physical location is defined by location type and an
                      instance of that physical location type.  This
                      object defines the location type.  This object can
                      be used in conjunction with chasPhyResLocation to
                      index the module table."
              ::= { chasPhyResourceEntry 1 }

          chasPhyResLocation  OBJECT-TYPE
              SYNTAX  INTEGER
              ACCESS  read-only
              STATUS  mandatory
              DESCRIPTION
                      "A resource exists on a particular module.  A
                      module is identified by it's physical location.
                      Physical location is defined by location type and an
                      instance of that physical location type.  This
                      object defines a particular instance of the
                      physical location."
              ::= { chasPhyResourceEntry 2 }

          chasPhyResIndex  OBJECT-TYPE
              SYNTAX  INTEGER
              ACCESS  read-only
              STATUS  mandatory
              DESCRIPTION
                      "A unique index for the chassis resource on this
                      particular physical module."
              ::= { chasPhyResourceEntry 3 }

          chasPhyResType OBJECT-TYPE
              SYNTAX OBJECT IDENTIFIER
              ACCESS read-only
              STATUS mandatory
              DESCRIPTION
                      "The type of resource."
              ::= { chasPhyResourceEntry 4 }

	  chasPhyResAssignment  OBJECT-TYPE
              SYNTAX  INTEGER
              ACCESS  read-only
              STATUS  mandatory
              DESCRIPTION
                      "The physical module resource is
                      assigned to a specific entity.  This object
                      defines the entity to which this resource is
                      currently assigned.

                      Notice, not all implementations may support this
                      object as read-write.  If read-write is supported
                      assignment may still fail due to a number of
                      reasons such as insufficient resources, invalid
                      configuration."
              ::= { chasPhyResourceEntry 5 }

          chasPhyResEntitySubIndex  OBJECT-TYPE
              SYNTAX  INTEGER
              ACCESS  read-only
              STATUS  mandatory
              DESCRIPTION
                      "Provides a unique index that can be used to
                      identify the relationship in terms of the entity."
              ::= { chasPhyResourceEntry 6 }


          -- Logical configuration/resource table


          chasLogResourceTable  OBJECT-TYPE
                  SYNTAX SEQUENCE OF ChasLogResourceEntry
                  ACCESS not-accessible
                  STATUS mandatory
                  DESCRIPTION
                      "Defines a logical configuration relationship
                      which is a relationship between entities and
                      resources and the physical module that the
                      relationship exists on."
                  ::= { chasResource 2 }

          chasLogResourceEntry OBJECT-TYPE
                  SYNTAX ChasLogResourceEntry
                  ACCESS not-accessible
                  STATUS mandatory
                  DESCRIPTION
                      "Defines a single logical relationship."
                  INDEX { chasLogResEntity,
                          chasLogResEntitySubIndex }
                  ::= { chasLogResourceTable 1 }

          ChasLogResourceEntry ::=  SEQUENCE {
                  chasLogResEntity
                          INTEGER,
                  chasLogResEntitySubIndex
                          INTEGER,
                  chasLogResLocationType
                          INTEGER,
                  chasLogResLocation
                          INTEGER,
                  chasLogResIndex
                          INTEGER
                  }

          chasLogResEntity  OBJECT-TYPE
                  SYNTAX INTEGER
                  ACCESS read-only
                  STATUS mandatory
                  DESCRIPTION
                      "The entity ID for which this logical
                      configuration relationship exists."
                  ::= { chasLogResourceEntry 1 }

          chasLogResEntitySubIndex  OBJECT-TYPE
                  SYNTAX INTEGER
                  ACCESS read-only
                  STATUS mandatory
                  DESCRIPTION
                      "The entity sub index for which this logical
                      configuration relationship exists.  The logical
                      relationship is identified by a resource
                      assignment to an entity.  The sub index defines a
                      particular instance of the mapping of physical
                      configuration onto an entity."
                  ::= { chasLogResourceEntry 2 }

          chasLogResLocationType  OBJECT-TYPE
                  SYNTAX INTEGER
                  ACCESS read-only
                  STATUS mandatory
                  DESCRIPTION
                      "A module is defined by it's physical location
                      type and an instance of that physical location.
                      This object defines the physical location type
                      portion of the physical module identifier that
                      this logical configuration exists for."
                  ::= { chasLogResourceEntry 3 }

          chasLogResLocation  OBJECT-TYPE
                  SYNTAX INTEGER
                  ACCESS read-only
                  STATUS mandatory
                  DESCRIPTION
                      "A module is defined by it's physical location
                      type and an instance of that physical location.
                      This object defines the instance physical location
                      (location index) portion of the physical module
                      identifier that this logical configuration exists
                      for."
                  ::= { chasLogResourceEntry 4 }

          chasLogResIndex  OBJECT-TYPE
                  SYNTAX INTEGER
                  ACCESS read-only
                  STATUS mandatory
                  DESCRIPTION
                      "The value of this object refers to a particular
                      instance of a resource, as defined by
                      chasResourceIndex, for which this relationship is
                      defined.  This together with
                      chasLogResLocationType and
                      chasLogResLocation completes the mapping of
                      the logical configuration on to the physical
                      module and resource combination."
                  ::= { chasLogResourceEntry 5 }


          -- The chasPowerSupply (Power Supply) group

          -- the Power Supply table

          chasPowerSupplyTable OBJECT-TYPE
              SYNTAX SEQUENCE OF ChasPowerSupplyEntry
              ACCESS not-accessible
              STATUS mandatory
              DESCRIPTION
                      "A list of power supply entries, one for each
                      power supply in the chassis."
              ::= { chasPowerSupply 1 }

          chasPowerSupplyEntry OBJECT-TYPE
              SYNTAX ChasPowerSupplyEntry
              ACCESS not-accessible
              STATUS mandatory
              DESCRIPTION
                      "Values for a power supply."
              INDEX { chasPowerSupplyIndex }
              ::= { chasPowerSupplyTable 1 }

          ChasPowerSupplyEntry ::=
              SEQUENCE {
                  chasPowerSupplyIndex
                      INTEGER,
                  chasPowerSupplyDescr
                      DisplayString,
                  chasPowerSupplyAdminStatus
                      INTEGER,
                  chasPowerSupplyOperStatus
                      INTEGER,
                  chasPowerSupplyHealthText
                      DisplayString,
                  chasPowerSupplyWarnings
                      Counter,
                  chasPowerSupplyFailures
                      Counter,
                  chasPowerSupplyLocationType
                      INTEGER,
                  chasPowerSupplyLocationIndex
                      INTEGER
              }


          chasPowerSupplyIndex OBJECT-TYPE
              SYNTAX INTEGER
              ACCESS read-only
              STATUS mandatory
              DESCRIPTION
                      "An index value that uniquely identifies a power
                      supply.  This may correspond to a hardware power
                      supply slot, which may or may not be the same as a
                      network device slot (chasSlotIndex)."
              ::= { chasPowerSupplyEntry 1 }

          chasPowerSupplyDescr OBJECT-TYPE
              SYNTAX DisplayString (SIZE (0..255))
              ACCESS read-only
              STATUS mandatory
              DESCRIPTION
                      "A textual description of the power supply,
                      including the vendor's name and version."
              ::= { chasPowerSupplyEntry 2 }

          chasPowerSupplyAdminStatus OBJECT-TYPE
              SYNTAX INTEGER {
                  unknown(1),
                  enable(2),
                  disable(3) }
              ACCESS read-write
              STATUS mandatory
              DESCRIPTION
                      "Desired status of the power supply."
              ::= { chasPowerSupplyEntry 3 }

          chasPowerSupplyOperStatus OBJECT-TYPE
              SYNTAX INTEGER {
                  unknown(1),
                  empty(2),
                  disabled(3),
                  bad(4),
                  warning(5),
                  standby(6),
                  engaged(7),
                  redundant(8) }
              ACCESS read-only
              STATUS mandatory
              DESCRIPTION
                      "Actual status of the power supply:
                      - unknown(1) - status not known.
                      - empty(2) - no power supply installed in slot
                      - disabled(3) - unable to supply power due to
			              chasPowerSupplyAdminStatus
                      - bad(4) - unable to supply power due to failure
                      - warning(5) - supplying power but an output or
			             sensor is bad or warning
                      - standby(6) - believed usable but not supplying power
                      - engaged(7) - supplying power
                      - redundant(8) - supplying power but not needed

                      It is an implementation specific matter whether
                      the agent keeps entries with status unknown(1) or
                      empty(2) in the table."
              ::= { chasPowerSupplyEntry 4 }

          chasPowerSupplyHealthText OBJECT-TYPE
              SYNTAX DisplayString (SIZE (0..255))
              ACCESS read-only
              STATUS mandatory
              DESCRIPTION
                      "A textual description of the power supply's
                      operational status. Agents may use this string to
                      provide detailed information on current failures,
                      including how they were detected, and/or
                      instructions for problem resolution. The contents
                      are agent-specific."
              ::= { chasPowerSupplyEntry 5 }

          chasPowerSupplyWarnings OBJECT-TYPE
              SYNTAX Counter
              ACCESS read-only
              STATUS mandatory
              DESCRIPTION
                      "The number of times chasPowerSupplyOperStatus has
                      gone to warning(5)."
              ::= { chasPowerSupplyEntry 6 }

          chasPowerSupplyFailures OBJECT-TYPE
              SYNTAX Counter
              ACCESS read-only
              STATUS mandatory
              DESCRIPTION
                      "The number of times chasPowerSupplyOperStatus has
                      gone to bad(4)."
              ::= { chasPowerSupplyEntry 7 }


          chasPowerSupplyLocationType OBJECT-TYPE
              SYNTAX INTEGER
              ACCESS read-only
              STATUS mandatory
              DESCRIPTION
                      "This defines the instance of a physical location
                      type of the power supply.  Location Type together
                      with location index completely defines the
                      location of a power supply."
              ::= { chasPowerSupplyEntry 8 }

          chasPowerSupplyLocationIndex  OBJECT-TYPE
                  SYNTAX  INTEGER
                  ACCESS  read-only
                  STATUS  mandatory
                  DESCRIPTION
                      "Defines a particular instance of a physical
                      location type."
                  ::= { chasPowerSupplyEntry 9 }

          -- the Power Supply Output table

          chasPowerSupplyOutputTable OBJECT-TYPE
              SYNTAX SEQUENCE OF ChasPowerSupplyOutputEntry
              ACCESS not-accessible
              STATUS mandatory
              DESCRIPTION
                      "A list of power supply output entries, one for
                      each output of each power supply in the chassis."
              ::= { chasPowerSupply 2 }

          chasPowerSupplyOutputEntry OBJECT-TYPE
              SYNTAX ChasPowerSupplyEntry
              ACCESS not-accessible
              STATUS mandatory
              DESCRIPTION
                      "Values for a power supply output."
              INDEX { chasPowerSupplyIdIndex, chasPowerSupplyOutputIndex }
              ::= { chasPowerSupplyOutputTable 1 }

          ChasPowerSupplyOutputEntry ::=
              SEQUENCE {
		  chasPowerSupplyIdIndex
		      INTEGER,
                  chasPowerSupplyOutputIndex
                      INTEGER,
                  chasPowerSupplyOutputStatus
                      INTEGER,
                  chasPowerSupplyOutputNominalVoltage
                      INTEGER,
                  chasPowerSupplyOutputOfferedVoltage
                      INTEGER,
                  chasPowerSupplyOutputOfferedWattage
                      INTEGER,
                  chasPowerSupplyOutputWarnings
                      Counter,
                  chasPowerSupplyOutputFailures
                      Counter
              }

          chasPowerSupplyIdIndex OBJECT-TYPE
              SYNTAX INTEGER
              ACCESS read-only
              STATUS mandatory
              DESCRIPTION
                      "An index value that uniquely identifies a power
                      supply.  This may correspond to a hardware power
                      supply slot, which may or may not be the same as a
                      network device slot (chasSlotIndex)."
              ::= { chasPowerSupplyOutputEntry 1 }

          chasPowerSupplyOutputIndex OBJECT-TYPE
              SYNTAX INTEGER
              ACCESS read-only
              STATUS mandatory
              DESCRIPTION
                      "An index value that uniquely identifies an output
                      for the power supply."
              ::= { chasPowerSupplyOutputEntry 2 }

          chasPowerSupplyOutputStatus OBJECT-TYPE
              SYNTAX INTEGER {
                  unknown(1),
                  bad(2),
                  warning(3),
                  good(4) }
              ACCESS read-only
              STATUS mandatory
              DESCRIPTION
                      "Actual status of the power supply:

                      - unknown(1)     status not known
                      - bad(2)         unable to supply power due to
                      failure
                      - warning(3)     supplying power but marginally
                      - good(4)        supplying power

                      It is an implementation specific matter whether
                      the agent keeps entries with status unknown(1) in
                      the table.  If unknown(1), offered values and
                      counters are meaningless."
                          ::= { chasPowerSupplyOutputEntry 3 }

          chasPowerSupplyOutputNominalVoltage OBJECT-TYPE
		  SYNTAX INTEGER
		  ACCESS read-only
		  STATUS mandatory
		  DESCRIPTION
			  "In hundredths of a volt, the voltage
			  the output is supposed to supply, such
			  as -5, +5, +12, -15, etc."
	     ::= { chasPowerSupplyOutputEntry 4 }

	     chasPowerSupplyOutputOfferedVoltage OBJECT-TYPE
		 SYNTAX INTEGER
		 ACCESS read-only
		 STATUS mandatory
		 DESCRIPTION
			 "In hundredths of a volt, the voltage
			 actually offered by the output.  If
			 chasPowerSupplyOutputStatus is good(4),
			 the value 0 means offered voltage is
			 not available."
		::= { chasPowerSupplyOutputEntry 5 }

	    chasPowerSupplyOutputOfferedWattage OBJECT-TYPE
		SYNTAX INTEGER
		ACCESS read-only
		STATUS mandatory
		DESCRIPTION
			"In hundredths of a watt, the wattage
			actually offered by the output.  If
			chasPowerSupplyOutputStatus is good(4),
			the value 0 means offered wattage is not
			available."
	       ::= { chasPowerSupplyOutputEntry 6 }

	   chasPowerSupplyOutputWarnings OBJECT-TYPE
	       SYNTAX Counter
	       ACCESS read-only
	       STATUS mandatory
	       DESCRIPTION
		       "The number of times
		       chasPowerSupplyOutputStatus has gone to
		       warning(3)."
	      ::= { chasPowerSupplyOutputEntry 7 }

	  chasPowerSupplyOutputFailures OBJECT-TYPE
	      SYNTAX Counter
	      ACCESS read-only
	      STATUS mandatory
	      DESCRIPTION
		      "The number of times
		      chasPowerSupplyOutputStatus has gone to
		      bad(2)."
	     ::= { chasPowerSupplyOutputEntry 8 }


                 -- the chasEnviron (Environment) group

                 -- the Environment table.

                 chasEnvironTable OBJECT-TYPE
                     SYNTAX SEQUENCE OF ChasEnvironEntry
                     ACCESS not-accessible
                     STATUS mandatory
                     DESCRIPTION
                             "A list of environmental entries, one for
                             each environmental sensor in the chassis."
                    ::= { chasEnviron 1 }

                chasEnvironEntry OBJECT-TYPE
                    SYNTAX ChasEnvironEntry
                    ACCESS not-accessible
                    STATUS mandatory
                    DESCRIPTION
                            "Values for a environmental sensor."
                   INDEX { chasEnvironLocationType,
			   chasEnvironLocationIndex,
			   chasEnvironIndex }
                   ::= { chasEnvironTable 1 }

               ChasEnvironEntry ::= SEQUENCE {
                   chasEnvironLocationType
                       INTEGER,
                   chasEnvironLocationIndex
                       INTEGER,
		   chasEnvironIndex
		       INTEGER,
                   chasEnvironSensor
                       AutonomousType,
                   chasEnvironStatus
                       INTEGER,
                   chasEnvironWarnings
                       Counter,
                   chasEnvironFailures
                       Counter
                   }

               chasEnvironSensor OBJECT-TYPE
                   SYNTAX AutonomousType
                   ACCESS read-only
                   STATUS mandatory
                   DESCRIPTION
                           "The identification of an environmental
                           sensor.  Other AutonomousType values may be
                           defined elsewhere, in association with
                           specific protocols.  However, this document
                           assigns those of known interest as of this
                           writing."
                  ::= { chasEnvironEntry 1 }

              chasEnvironStatus OBJECT-TYPE
                  SYNTAX INTEGER {
                      unknown(1),
                      bad(2),
                      warning(3),
                      good(4) }
                  ACCESS read-only
                  STATUS mandatory
                  DESCRIPTION
                          "Actual status indicated by the sensor.  It is
                          an implementation specific matter whether the
                          agent keeps entries with status unknown(1) in
                          the table.  If unknown(1), counters are
                          meaningless."
                 ::= { chasEnvironEntry 2 }

             chasEnvironWarnings OBJECT-TYPE
                 SYNTAX Counter
                 ACCESS read-only
                 STATUS mandatory
                 DESCRIPTION
                         "The number of times chasEnvironStatus has gone
                         to warning(3)."
                ::= { chasEnvironEntry 3 }

            chasEnvironFailures OBJECT-TYPE
                SYNTAX Counter
                ACCESS read-only
                STATUS mandatory
                DESCRIPTION
                        "The number of times chasEnvironStatus has gone
                        to bad(2)."
               ::= { chasEnvironEntry 4 }

           chasEnvironLocationType OBJECT-TYPE
               SYNTAX INTEGER
               ACCESS read-only
               STATUS mandatory
               DESCRIPTION
                       "Defines the actual type of physical location
                       that this environmental sensor occupies."
              ::= { chasEnvironEntry 5 }

          chasEnvironLocationIndex OBJECT-TYPE
              SYNTAX INTEGER
              ACCESS read-only
              STATUS mandatory
              DESCRIPTION
                      "This defines the particular instance of a
                      physical location type which this environmental
                      sensor occupies."
              ::= { chasEnvironEntry 6 }

          chasEnvironIndex OBJECT-TYPE
              SYNTAX INTEGER
              ACCESS read-only
              STATUS mandatory
              DESCRIPTION
                      "An index value that uniquely identifies an
                       environmental sensor." 
              ::= { chasEnvironEntry 7 }


 -- GigaHUB Traps


gigaPowerSupplyTrap	TRAP-TYPE	
	ENTERPRISE 	gigaHUB
	VARIABLES  {    chasPowerSupplyIndex,
			chasPowerSupplyOperStatus }
        DESCRIPTION "This trap message is generated as soon
		     as one of the power supply has changed its
		     operational status."
	::= 31

gigaSensorTrap	TRAP-TYPE
	ENTERPRISE	gigaHUB
	VARIABLES {     chasEnvironLocationType,
                        chasEnvironLocationIndex,
                        chasEnvironIndex,
                        chasEnvironStatus }
	DESCRIPTION "This trap message is generated when there
		     is a change in enviromental sensor status."
	::= 32

gigaHostAuthTrap      TRAP-TYPE
	ENTERPRISE	gigaHUB
	VARIABLES { fmDiagTrapInfo }
	DESCRIPTION "This trap is generated when an unauthorized host 
		     attempts to perform an SNMP SET operation."
	::= 33

gigaModuleTrap 		TRAP-TYPE
	ENTERPRISE	gigaHUB
	VARIABLES  {    chasPhyModuleLocationType,
			chasPhyModuleLocation,
			chasPhyModuleOperStatus }
	DESCRIPTION "This trap message is generated when there
		     is a change in module operational status"
	::= 34

gigaModuleEmptyTrap  	TRAP-TYPE
	ENTERPRISE	gigaHUB
	VARIABLES {     chasPhyModuleLocationType,
		        chasPhyModuleLocation }
	DESCRIPTION "This trap is generated when a module is removed
		     from a modular slot."
	::= 35

gigaModuleNotEmptyTrap	TRAP-TYPE
	ENTERPRISE	gigaHUB
	VARIABLES {     chasPhyModuleLocationType,
		        chasPhyModuleLocation }
	DESCRIPTION "This trap is generated when a module is inserted
		     in a modular slot."
	::= 36

gigaPhyResAttachChangeTrap  TRAP-TYPE
	ENTERPRISE	gigaHUB
	VARIABLES {     gigaPhyResLocationType,
		        gigaPhyResLocation,
			gigaPhyResIndex,
			gigaPhyResSegRing }
	DESCRIPTION "This trap is generated when physical module resource is
		     changed it's segment/ring attachment."
	::= 37

gigaPhyResConfigChangeTrap  TRAP-TYPE
	ENTERPRISE	gigaHUB
	DESCRIPTION "This trap is generated when there is a global change in
		     physical module resources configuration."
	::= 38

gigaEbmTrap	TRAP-TYPE	
	ENTERPRISE 	gigaHUB
	VARIABLES  {    gigaEbmIndex,
			gigaEbmOperStatus }
        DESCRIPTION "This trap message is generated as soon
		     as one of the EBM cards has changed its
		     operational status."
	::= 39

fmSlotIPAddressChange  TRAP-TYPE
	ENTERPRISE	gigaHUB
	VARIABLES { fmSlotIndex,
		    fmSlotID,
                    fmSlotIpAddr		    
		   }
	DESCRIPTION "This trap is generated when IP Address 
		    is changed in a slot."
	::= 40

  
END
