-- ****************************************************************************
--
--                Console Management Controller- (CMC) MIB
--         Management Information Base for SNMP Network Management
--
--
--      Copyright 2000,2003 Hewlett-Packard Development Company, L.P.
--
--      Hewlett-Packard Company shall not be liable for technical or
--      editorial errors or omissions contained herein. The information in
--      this document is provided "as is" without warranty of any kind and
--      is subject to change without notice. The warranties for HP products
--      are set forth in the express limited warranty statements
--      accompanying such products. Nothing herein should be construed as
--      constituting an additional warranty.
--
--      Confidential computer software. Valid license from HP required for
--      possession, use or copying. Consistent with FAR 12.211 and 12.212,
--      Commercial Computer Software, Computer Software Documentation, and
--      Technical Data for Commercial Items are licensed to the U.S.
--      Government under vendor's standard commercial license.
--
--      Refer to the READMIB.RDM file for more information about the
--      organization of the information in the Compaq Enterprise.
--
--      The Compaq Enterprise number is 232.
--      The ASN.1 prefix to, and including the Compaq Enterprise is:
--           1.3.6.1.4.1.232
--
--      MIB Version 1.2
--      *********************************************************************
--      Release History
--      Date: May 1, 2003 (version 1.2)
--      Revised by M. Spence, changed version to 1.2 to follow standard conventions
--                            no functional changes between 1.11 and 1.2
--      Date: April 14, 2003 (version 1.11)
--      Revised by M. Spence, Fixed more Trap Descriptions that were incorrect.
--      Date: February 17, 2003 (Version 1.11)
--      Revised by M. Spence, Enhance Trap Descriptions
--                            Fixed incorrect variable in Trap 153018
--
--      Date: December 19, 2000 (Version 1.1)
--      Revised by M. Hain, included door locking device
--
--      Date: October 17, 2000 (Version 1.0)
--      Revised by M. Hain
--      *********************************************************************

-- Note: To use this MIB in a Trap Receiver application without CPQHOST.MIB, you must
-- remove the "compaq" line from the IMPORTS section and uncomment the line that defines
-- the "compaq" enterprise as 232.

   CPQCMC-MIB DEFINITIONS ::= BEGIN

     IMPORTS

        compaq                   FROM CPQHOST-MIB
        DisplayString            FROM RFC1213-MIB
        OBJECT-TYPE              FROM RFC-1212
        sysName                  FROM RFC1213-MIB
        sysContact               FROM RFC1213-MIB
        sysLocation              FROM RFC1213-MIB
        sysDescr                 FROM RFC1213-MIB
        TRAP-TYPE                FROM RFC-1215;

-- Uncomment the next line if you are not using the CPQHOST.MIB.
-- compaq            OBJECT IDENTIFIER ::= { enterprises 232 }
   cpqCmc            OBJECT IDENTIFIER ::= { compaq 153 }

     cpqCmcMibRev          OBJECT IDENTIFIER ::= { cpqCmc 1 }
     cpqCmcComponent       OBJECT IDENTIFIER ::= { cpqCmc 2 }
     cpqCmcInterface       OBJECT IDENTIFIER ::= { cpqCmcComponent 1 }
     cpqCmcOsCommon        OBJECT IDENTIFIER ::= { cpqCmcInterface 1 }
     cpqCmcDevice          OBJECT IDENTIFIER ::= { cpqCmcComponent 2 }
     cpqCmcSetup           OBJECT IDENTIFIER ::= { cpqCmcDevice 2 }
     cpqCmcSetupConfig     OBJECT IDENTIFIER ::= { cpqCmcSetup 1 }
     cpqCmcSetupGeneral    OBJECT IDENTIFIER ::= { cpqCmcSetupConfig 1 }
     cpqCmcSetupEvents     OBJECT IDENTIFIER ::= { cpqCmcSetupConfig 2 }
     cpqCmcSetupTemp1      OBJECT IDENTIFIER ::= { cpqCmcSetupEvents 1}
     cpqCmcSetupTemp2      OBJECT IDENTIFIER ::= { cpqCmcSetupEvents 2}
     cpqCmcSetupFan1       OBJECT IDENTIFIER ::= { cpqCmcSetupEvents 3}
     cpqCmcSetupFan2       OBJECT IDENTIFIER ::= { cpqCmcSetupEvents 4}
     cpqCmcSetupVoltage    OBJECT IDENTIFIER ::= { cpqCmcSetupEvents 5}
     cpqCmcSetupHumidity   OBJECT IDENTIFIER ::= { cpqCmcSetupEvents 6}
     cpqCmcSetupInput1     OBJECT IDENTIFIER ::= { cpqCmcSetupEvents 7}
     cpqCmcSetupInput2     OBJECT IDENTIFIER ::= { cpqCmcSetupEvents 8}
     cpqCmcSetupInput3     OBJECT IDENTIFIER ::= { cpqCmcSetupEvents 9}
     cpqCmcSetupInput4     OBJECT IDENTIFIER ::= { cpqCmcSetupEvents 10}
     cpqCmcSetupLock1      OBJECT IDENTIFIER ::= { cpqCmcSetupEvents 11}
     cpqCmcSetupLock2      OBJECT IDENTIFIER ::= { cpqCmcSetupEvents 12}
     cpqCmcSetupSmoke      OBJECT IDENTIFIER ::= { cpqCmcSetupEvents 13}
     cpqCmcSetupShock      OBJECT IDENTIFIER ::= { cpqCmcSetupEvents 14}
     cpqCmcSetupAux1       OBJECT IDENTIFIER ::= { cpqCmcSetupEvents 15}
     cpqCmcSetupAux2       OBJECT IDENTIFIER ::= { cpqCmcSetupEvents 16}
     cpqCmcSetupAlarm1     OBJECT IDENTIFIER ::= { cpqCmcSetupEvents 17}
     cpqCmcSetupAlarm2     OBJECT IDENTIFIER ::= { cpqCmcSetupEvents 18}
     cpqCmcSetupClock      OBJECT IDENTIFIER ::= { cpqCmcSetupConfig 3 }
     cpqCmcSetupThreshold  OBJECT IDENTIFIER ::= { cpqCmcSetup 2 }
     cpqCmcTraps           OBJECT IDENTIFIER ::= { cpqCmcSetup 3 }
     cpqCmcValues          OBJECT IDENTIFIER ::= { cpqCmcDevice 3 }
     cpqCmcStatus          OBJECT IDENTIFIER ::= { cpqCmcDevice 4 }
     cpqCmcControl         OBJECT IDENTIFIER ::= { cpqCmcDevice 5 }
     cpqCmcLog             OBJECT IDENTIFIER ::= { cpqCmcDevice 6 }


--*****************************************************************************
--CMC ConsoleManagementController
--*****************************************************************************
--cpqCmcMibRev-group

   cpqCmcMibRevMajor          OBJECT-TYPE
         SYNTAX  INTEGER (1..65535)
         ACCESS  read-only
         STATUS  mandatory
         DESCRIPTION
         "The Major Revision level.
          A change in the major revision level represents a major change
          in the architecture of the MIB. A change in the major revision
          level may indicate a significant change in the information,
          correct interpretation of data may require a MIB document
          with the same major revision level."
         ::= { cpqCmcMibRev 1 }

   cpqCmcMibRevMinor          OBJECT-TYPE
         SYNTAX  INTEGER (0..65535)
         ACCESS  read-only
         STATUS  mandatory
         DESCRIPTION
         "The Minor Revision level.
          A change in the minor revision level may represent some minor
          additional support, no changes to any pre-existing information
          has occurred."
         ::= { cpqCmcMibRev 2 }

   cpqCmcMibCondition          OBJECT-TYPE
         SYNTAX  INTEGER {
      other (1),
      ok (2),
      degraded (3),
      failed (4)
      }
         ACCESS  read-only
         STATUS  mandatory
         DESCRIPTION
         "The overall condition (status) of the system (rack(s)) represented by
          this MIB.
          (2) OK
           (3) a minor problem, warning condition (yellow LED on CMC)
           (4) a major problem (red LED on CMC)"
         ::= { cpqCmcMibRev 3 }


--********************************************************************************
-- cpqCmcOsCommon-group

   cpqCmcOsCommonPollFreq          OBJECT-TYPE
         SYNTAX  INTEGER (0..65535)
         ACCESS  read-write
         STATUS  mandatory
         DESCRIPTION
         "The Insight Agent's polling frequency.
          The frequency, in seconds, at which the Insight Agent requests
          information from the device driver.  A frequency of zero (0)
          indicates that the Insight Agent retrieves the information upon
          request of a management station, it does not poll the device
          driver at a specific interval."
         ::= { cpqCmcOsCommon 1 }

--********************************************************************************
--cpqCmcDevice-group

     cpqCmcDeviceCondition   OBJECT-TYPE
         SYNTAX  INTEGER {
         other(1),
         ok (2),
         overloadDC(3),
         fuseDC(4)
         }
         ACCESS  read-only
         STATUS  mandatory
         DESCRIPTION
         "Condition of CMC device,
               (3) an overload of the 24V DC supply to the connected accessories occurred
               (4) the overload-protection (fuse) has released "
         ::= { cpqCmcDevice 1 }


--********************************************************************************
--cpqCmcSetupGeneral-group

     cpqCmcsetLanguage     OBJECT-TYPE
         SYNTAX  INTEGER {
         other(1),
         english(2),
         french(3),
         italian(4),
         german(5),
         spanish(6),
         dutch(7),
         japanese(8)
         }
         ACCESS  read-write
         STATUS  mandatory
         DESCRIPTION
         "Language of LCD"
         ::= { cpqCmcSetupGeneral 1 }

     cpqCmcsetTempUnit          OBJECT-TYPE
         SYNTAX  INTEGER {
         other(1),
         celsius(2),
         fahrenheit(3)
         }
         ACCESS  read-write
         STATUS  mandatory
         DESCRIPTION
         "Unit of all temperature values and thresholds, Celsius or Fahrenheit"
         ::= { cpqCmcSetupGeneral 2 }

     cpqCmcsetAudibleAlarm             OBJECT-TYPE
         SYNTAX  INTEGER {
         other(1),
         enableSilence(2),
         disableSilence(3),
         off(4)
         }
         ACCESS  read-write
         STATUS  mandatory
         DESCRIPTION
         "Audible alarm in CMC unit:
           (2): silencing with button on CMC is enabled
           (3): silencing with button on CMC is disabled
           (4): audible alarm is off (general).
          On/off of audible alarm for each event is possible in cpqCmcsetupEvents-group"
         ::= { cpqCmcSetupGeneral 3 }

     cpqCmcPassword     OBJECT-TYPE
        SYNTAX DisplayString (SIZE (0..6))
        ACCESS read-write
        STATUS mandatory
        DESCRIPTION
        "Password to get access to terminal or LCD"
        ::= { cpqCmcSetupGeneral 4 }

     cpqCmcPasswordOption     OBJECT-TYPE
         SYNTAX  INTEGER {
         other(1),
         enabled(2),
         disabled(3)
         }
         ACCESS  read-write
         STATUS  mandatory
         DESCRIPTION
         "Enable or disable password entry to get access to terminal or LCD"
         ::= { cpqCmcSetupGeneral 5 }

     cpqCmcquitRelay1         OBJECT-TYPE
         SYNTAX  INTEGER {
         other(1),
         enabled(2),
         disabled(3)
         }
         ACCESS  read-write
         STATUS  mandatory
         DESCRIPTION
         "Enable or disable acknowledging currently active alarm relay 1
          (with 'ENTER' on CMC)."
         ::= { cpqCmcSetupGeneral 6 }

     cpqCmcquitRelay2         OBJECT-TYPE
         SYNTAX  INTEGER {
         other(1),
         enabled(2),
         disabled(3)
         }
         ACCESS  read-write
         STATUS  mandatory
         DESCRIPTION
         "Enable or disable acknowledging currently active alarm relay 2
          (with 'ENTER' on CMC)."
         ::= { cpqCmcSetupGeneral 7 }

     cpqCmclogicRelay1         OBJECT-TYPE
         SYNTAX  INTEGER {
         other(1),
         closeAtAlarm(2),
         openAtAlarm(3),
         closeAtEPO(4)
         }
         ACCESS  read-write
         STATUS  mandatory
         DESCRIPTION
         "Logic of Relay 1: (2) Relay will pick up in case of an alarm
             (3) Relay will release in case of an alarm
             (4) not used"
         ::= { cpqCmcSetupGeneral 8 }

     cpqCmclogicRelay2         OBJECT-TYPE
         SYNTAX  INTEGER {
         other(1),
         closeAtAlarm(2),
         openAtAlarm(3),
         closeAtEPO(4)
         }
         ACCESS  read-write
         STATUS  mandatory
         DESCRIPTION
         "Logic of Relay 2: (2) Relay will pick up in case of an alarm
             (3) Relay will release in case of an alarm
             (4) not used"
         ::= { cpqCmcSetupGeneral 9 }

--*****************************************************************************
-- cpqCmcSetupEvents-group
-- cpqCmcSetupTemp1-group

     cpqCmcSetupTemp1Avail         OBJECT-TYPE
         SYNTAX  INTEGER {
         other (1),
         available (2),
         notAvailable (3)
         }
         ACCESS  read-write
         STATUS  mandatory
         DESCRIPTION
         "Temperature sensor:
          (2) sensor available
           (3) sensor not available"
         ::= { cpqCmcSetupTemp1 1 }

     cpqCmcSetupTemp1RelaysWarn         OBJECT-TYPE
         SYNTAX  INTEGER {
         other(1),
         off(2),
         relay1(3),
         relay2(4),
         both(5)
         }
         ACCESS  read-write
         STATUS  mandatory
         DESCRIPTION
         "Alert handling of Alarm Relays in case of warning condition
          of temperature sensor 1:
          (2) no switching of Relays
          (3) Relay 1 will switch
          (4) Relay 2 will switch
          (5) both Relays will switch"
         ::= { cpqCmcSetupTemp1 2 }

     cpqCmcSetupTemp1RelaysMax         OBJECT-TYPE
         SYNTAX  INTEGER {
         other(1),
         off(2),
         relay1(3),
         relay2(4),
         both(5)
         }
         ACCESS  read-write
         STATUS  mandatory
         DESCRIPTION
         "Alert handling of Alarm Relays in case of max. alarm condition
          of temperature sensor 1:
          (2) no switching of Relays
          (3) Relay 1 will switch
          (4) Relay 2 will switch
          (5) both Relays will switch"
         ::= { cpqCmcSetupTemp1 3 }

     cpqCmcSetupTemp1RelaysMin         OBJECT-TYPE
         SYNTAX  INTEGER {
         other(1),
         off(2),
         relay1(3),
         relay2(4),
         both(5)
         }
         ACCESS  read-write
         STATUS  mandatory
         DESCRIPTION
         "Alert handling of Alarm Relays in case of min. alarm condition
          of temperature sensor 1:
          (2) no switching of Relays
          (3) Relay 1 will switch
          (4) Relay 2 will switch
          (5) both Relays will switch"
         ::= { cpqCmcSetupTemp1 4 }

     cpqCmcSetupTemp1AudibleAlarmWarn         OBJECT-TYPE
         SYNTAX  INTEGER {
         other(1),
         enabled(2),
         disabled(3)
         }
         ACCESS  read-write
         STATUS  mandatory
         DESCRIPTION
         "Alert handling of Audible Alarm of in case of warning condition
          of temperature sensor 1:
         (2) Start Audible Alarm
         (3) No Audible Alarm"
         ::= { cpqCmcSetupTemp1 5 }

     cpqCmcSetupTemp1AudibleAlarmMax         OBJECT-TYPE
         SYNTAX  INTEGER {
         other(1),
         enabled(2),
         disabled(3)
         }
         ACCESS  read-write
         STATUS  mandatory
         DESCRIPTION
         "Alert handling of Audible Alarm of in case of max. alarm condition
          of temperature sensor 1:
         (2) Start Audible Alarm
         (3) No Audible Alarm"
         ::= { cpqCmcSetupTemp1 6 }

     cpqCmcSetupTemp1AudibleAlarmMin         OBJECT-TYPE
         SYNTAX  INTEGER {
         other(1),
         enabled(2),
         disabled(3)
         }
         ACCESS  read-write
         STATUS  mandatory
         DESCRIPTION
         "Alert handling of Audible Alarm of in case of min. alarm condition
          of temperature sensor 1:
         (2) Start Audible Alarm
         (3) No Audible Alarm"
         ::= { cpqCmcSetupTemp1 7 }


-- cpqCmcSetupTemp2-group

     cpqCmcSetupTemp2Avail         OBJECT-TYPE
         SYNTAX  INTEGER {
         other (1),
         available (2),
         notAvailable (3)
         }
         ACCESS  read-write
         STATUS  mandatory
         DESCRIPTION
         "Temperature sensor:
          (2) sensor available
         (3) sensor not available"
         ::= { cpqCmcSetupTemp2 1 }

     cpqCmcSetupTemp2RelaysWarn         OBJECT-TYPE
         SYNTAX  INTEGER {
         other(1),
         off(2),
         relay1(3),
         relay2(4),
         both(5)
         }
         ACCESS  read-write
         STATUS  mandatory
         DESCRIPTION
         "Alert handling of Alarm Relays in case of warning condition
          of temperature sensor 2:
          (2) no switching of Relays
          (3) Relay 1 will switch
          (4) Relay 2 will switch
          (5) both Relays will switch"
         ::= { cpqCmcSetupTemp2 2 }

     cpqCmcSetupTemp2RelaysMax         OBJECT-TYPE
         SYNTAX  INTEGER {
         other(1),
         off(2),
         relay1(3),
         relay2(4),
         both(5)
         }
         ACCESS  read-write
         STATUS  mandatory
         DESCRIPTION
         "Alert handling of Alarm Relays in case of max. alarm condition
          of temperature sensor 2:
          (2) no switching of Relays
          (3) Relay 1 will switch
          (4) Relay 2 will switch
          (5) both Relays will switch"
         ::= { cpqCmcSetupTemp2 3 }

     cpqCmcSetupTemp2RelaysMin         OBJECT-TYPE
         SYNTAX  INTEGER {
         other(1),
         off(2),
         relay1(3),
         relay2(4),
         both(5)
         }
         ACCESS  read-write
         STATUS  mandatory
         DESCRIPTION
         "Alert handling of Alarm Relays in case of min. alarm condition
          of temperature sensor 2:
          (2) no switching of Relays
          (3) Relay 1 will switch
          (4) Relay 2 will switch
          (5) both Relays will switch"
         ::= { cpqCmcSetupTemp2 4 }

     cpqCmcSetupTemp2AudibleAlarmWarn         OBJECT-TYPE
         SYNTAX  INTEGER {
         other(1),
         enabled(2),
         disabled(3)
         }
         ACCESS  read-write
         STATUS  mandatory
         DESCRIPTION
         "Alert handling of Audible Alarm of in case of warning condition
          of temperature sensor 2:
         (2) Start Audible Alarm
         (3) No Audible Alarm"
         ::= { cpqCmcSetupTemp2 5 }

     cpqCmcSetupTemp2AudibleAlarmMax         OBJECT-TYPE
         SYNTAX  INTEGER {
         other(1),
         enabled(2),
         disabled(3)
         }
         ACCESS  read-write
         STATUS  mandatory
         DESCRIPTION
         "Alert handling of Audible Alarm of in case of max. alarm condition
          of temperature sensor 2:
         (2) Start Audible Alarm
         (3) No Audible Alarm"
         ::= { cpqCmcSetupTemp2 6 }

     cpqCmcSetupTemp2AudibleAlarmMin         OBJECT-TYPE
         SYNTAX  INTEGER {
         other(1),
         enabled(2),
         disabled(3)
         }
         ACCESS  read-write
         STATUS  mandatory
         DESCRIPTION
         "Alert handling of Audible Alarm of in case of min. alarm condition
          of temperature sensor 2:
         (2) Start Audible Alarm
         (3) No Audible Alarm"
         ::= { cpqCmcSetupTemp2 7 }



-- cpqCmcSetupFan1-group

     cpqCmcSetupFan1Avail         OBJECT-TYPE
         SYNTAX  INTEGER {
         other(1),
         available(2),
         notAvailable(3)
         }
         ACCESS  read-write
         STATUS  mandatory
         DESCRIPTION
         "Fan 1:
          (2) Fan 1 available
          (3) Fan 1 not available"
         ::= { cpqCmcSetupFan1 1 }

     cpqCmcSetupFan1Relays         OBJECT-TYPE
         SYNTAX  INTEGER {
         other(1),
         off(2),
         relay1(3),
         relay2(4),
         both(5)
         }
         ACCESS  read-write
         STATUS  mandatory
         DESCRIPTION
         "Alert handling of Alarm Relays in case of alarm condition
          of Fan 1:
          (2) no switching of Relays
          (3) Relay 1 will switch
          (4) Relay 2 will switch
          (5) both Relays will switch"
         ::= { cpqCmcSetupFan1 2 }

     cpqCmcSetupFan1AudibleAlarm         OBJECT-TYPE
         SYNTAX  INTEGER {
         other(1),
         enabled(2),
         disabled(3)
         }
         ACCESS  read-write
         STATUS  mandatory
         DESCRIPTION
         "Alert handling of Audible Alarm of in case of alarm condition
          of Fan 1:
         (2) Start Audible Alarm
         (3) No Audible Alarm"
         ::= { cpqCmcSetupFan1 3 }




-- cpqCmcSetupFan2-group

     cpqCmcSetupFan2Avail         OBJECT-TYPE
         SYNTAX  INTEGER {
         other(1),
         available(2),
         notAvailable(3)
         }
         ACCESS  read-write
         STATUS  mandatory
         DESCRIPTION
         "Fan 2:
          (2) Fan 2 available
          (3) Fan 2 not available"
         ::= { cpqCmcSetupFan2 1 }


     cpqCmcSetupFan2Relays         OBJECT-TYPE
         SYNTAX  INTEGER {
         other(1),
         off(2),
         relay1(3),
         relay2(4),
         both(5)
         }
         ACCESS  read-write
         STATUS  mandatory
         DESCRIPTION
         "Alert handling of Alarm Relays in case of alarm condition
          of Fan 2:
          (2) no switching of Relays
          (3) Relay 1 will switch
          (4) Relay 2 will switch
          (5) both Relays will switch"
         ::= { cpqCmcSetupFan2 2 }

     cpqCmcSetupFan2AudibleAlarm         OBJECT-TYPE
         SYNTAX  INTEGER {
         other(1),
         enabled(2),
         disabled(3)
         }
         ACCESS  read-write
         STATUS  mandatory
         DESCRIPTION
         "Alert handling of Audible Alarm of in case of alarm condition
          of Fan 2:
         (2) Start Audible Alarm
         (3) No Audible Alarm"
         ::= { cpqCmcSetupFan2 3 }



-- cpqCmcSetupVoltage-group

     cpqCmcSetupVoltageAvail         OBJECT-TYPE
         SYNTAX  INTEGER {
         other(1),
         available(2),
         notAvailable(3)
         }
         ACCESS  read-write
         STATUS  mandatory
         DESCRIPTION
         "Voltage monitoring:
          (2) available
         (3) not available"
         ::= { cpqCmcSetupVoltage 1 }

     cpqCmcSetupVoltageRelaysMax         OBJECT-TYPE
         SYNTAX  INTEGER {
         other(1),
         off(2),
         relay1(3),
         relay2(4),
         both(5)
         }
         ACCESS  read-write
         STATUS  mandatory
         DESCRIPTION
         "Alert handling of Alarm Relays in case of max. alarm condition
          of voltage monitoring:
          (2) no switching of Relays
          (3) Relay 1 will switch
          (4) Relay 2 will switch
          (5) both Relays will switch"
         ::= { cpqCmcSetupVoltage 2 }

     cpqCmcSetupVoltageRelaysMin         OBJECT-TYPE
         SYNTAX  INTEGER {
         other(1),
         off(2),
         relay1(3),
         relay2(4),
         both(5)
         }
         ACCESS  read-write
         STATUS  mandatory
         DESCRIPTION
         "Alert handling of Alarm Relays in case of min. alarm condition
          of voltage monitoring:
          (2) no switching of Relays
          (3) Relay 1 will switch
          (4) Relay 2 will switch
          (5) both Relays will switch"
         ::= { cpqCmcSetupVoltage 3 }

     cpqCmcSetupVoltageAudibleAlarmMax         OBJECT-TYPE
         SYNTAX  INTEGER {
         other(1),
         enabled(2),
         disabled(3)
         }
         ACCESS  read-write
         STATUS  mandatory
         DESCRIPTION
         "Alert handling of Audible Alarm of in case of max. alarm condition
          of voltage monitoring:
         (2) Start Audible Alarm
         (3) No Audible Alarm"
         ::= { cpqCmcSetupVoltage 4 }

     cpqCmcSetupVoltageAudibleAlarmMin         OBJECT-TYPE
         SYNTAX  INTEGER {
         other(1),
         enabled(2),
         disabled(3)
         }
         ACCESS  read-write
         STATUS  mandatory
         DESCRIPTION
         "Alert handling of Audible Alarm of in case of min. alarm condition
          of voltage monitoring:
         (2) Start Audible Alarm
         (3) No Audible Alarm"
         ::= { cpqCmcSetupVoltage 5 }


-- cpqCmcSetupHumidity-group

     cpqCmcSetupHumidityAvail         OBJECT-TYPE
         SYNTAX  INTEGER {
         other(1),
         available(2),
         notAvailable(3)
         }
         ACCESS  read-write
         STATUS  mandatory
         DESCRIPTION
         "Humidity sensor:
          (2) available
         (3) not available"
         ::= { cpqCmcSetupHumidity 1 }

     cpqCmcSetupHumidityRelaysMax         OBJECT-TYPE
         SYNTAX  INTEGER {
         other(1),
         off(2),
         relay1(3),
         relay2(4),
         both(5)
         }
         ACCESS  read-write
         STATUS  mandatory
         DESCRIPTION
         "Alert handling of Alarm Relays in case of max. alarm condition
          of humidity monitoring:
          (2) no switching of Relays
          (3) Relay 1 will switch
          (4) Relay 2 will switch
          (5) both Relays will switch"
         ::= { cpqCmcSetupHumidity 2 }


     cpqCmcSetupHumidityRelaysMin         OBJECT-TYPE
         SYNTAX  INTEGER {
         other(1),
         off(2),
         relay1(3),
         relay2(4),
         both(5)
         }
         ACCESS  read-write
         STATUS  mandatory
         DESCRIPTION
         "Alert handling of Alarm Relays in case of min. alarm condition
          of humidity monitoring:
          (2) no switching of Relays
          (3) Relay 1 will switch
          (4) Relay 2 will switch
          (5) both Relays will switch"
         ::= { cpqCmcSetupHumidity 3 }

     cpqCmcSetupHumidityAudibleAlarmMax         OBJECT-TYPE
         SYNTAX  INTEGER {
         other(1),
         enabled(2),
         disabled(3)
         }
         ACCESS  read-write
         STATUS  mandatory
         DESCRIPTION
         "Alert handling of Audible Alarm of in case of max. alarm condition
          of humidity monitoring:
         (2) Start Audible Alarm
         (3) No Audible Alarm"
         ::= { cpqCmcSetupHumidity 4 }

     cpqCmcSetupHumidityAudibleAlarmMin         OBJECT-TYPE
         SYNTAX  INTEGER {
         other(1),
         enabled(2),
         disabled(3)
         }
         ACCESS  read-write
         STATUS  mandatory
         DESCRIPTION
         "Alert handling of Audible Alarm of in case of min. alarm condition
          of humidity monitoring:
         (2) Start Audible Alarm
         (3) No Audible Alarm"
         ::= { cpqCmcSetupHumidity 5 }



-- cpqCmcSetupInput1-group

     cpqCmcSetupInput1Avail         OBJECT-TYPE
         SYNTAX  INTEGER {
         other(1),
         available(2),
         notAvailable(3)
         }
         ACCESS  read-write
         STATUS  mandatory
         DESCRIPTION
         "Input 1 sensor:
          (2) available
         (3) not available"
         ::= { cpqCmcSetupInput1 1 }

     cpqCmcSetupInput1Relays         OBJECT-TYPE
         SYNTAX  INTEGER {
         other(1),
         off(2),
         relay1(3),
         relay2(4),
         both(5)
         }
         ACCESS  read-write
         STATUS  mandatory
         DESCRIPTION
         "Alert handling of Alarm Relays in case of a warning condition
          of Input 1 (Door/Sidewall open):
          (2) no switching of Relays
          (3) Relay 1 will switch
          (4) Relay 2 will switch
          (5) both Relays will switch"
         ::= { cpqCmcSetupInput1 2 }

     cpqCmcSetupInput1AudibleAlarm         OBJECT-TYPE
         SYNTAX  INTEGER {
         other(1),
         enabled(2),
         disabled(3)
         }
         ACCESS  read-write
         STATUS  mandatory
         DESCRIPTION
         "Alert handling of Audible Alarm of in case of a warning condition
          of Input 1 (Door/Sidewall open):
         (2) Start Audible Alarm
         (3) No Audible Alarm"
         ::= { cpqCmcSetupInput1 3 }


     cpqCmcSetupInput1FansOff         OBJECT-TYPE
         SYNTAX  INTEGER {
         other(1),
         both(2),
         fan1(3),
         fan2(4),
         noFan(5)
         }
         ACCESS  read-write
         STATUS  mandatory
         DESCRIPTION
         "Fan switching off if Door/Sidewall 1 is opened:
          (2) both fans would be switched off
          (3) only fan1 will be switched off
          (4) only fan2 will be switched off
          (5) no fan will be switched off"
         ::= { cpqCmcSetupInput1 4 }


     cpqCmcSetupInput1ShockSensor         OBJECT-TYPE
         SYNTAX  INTEGER {
         other(1),
         off(2),
         on(3)
         }
         ACCESS  read-write
         STATUS  mandatory
         DESCRIPTION
         "Shock sensor function if Door/Sidewall 1 is opened:
          (2) Shock Sensor is off (disabled)
          (3) Shock Sensor is on (enabled)"
         ::= { cpqCmcSetupInput1 5 }

     cpqCmcSetupInput1Description     OBJECT-TYPE
        SYNTAX DisplayString (SIZE (0..18))
        ACCESS read-write
        STATUS mandatory
        DESCRIPTION
        "Descriptional text of Input1"
        ::= { cpqCmcSetupInput1 6 }

     cpqCmcSetupInput1Lock         OBJECT-TYPE
         SYNTAX  INTEGER {
         other(1),
         none(2),
         lock1(3),
         lock2(4),
         both(5)
         }
         ACCESS  read-write
         STATUS  mandatory
         DESCRIPTION
         "Door/Sidewall 1 is locked by:
          (2) no locking device
          (3) locking device 1
          (4) locking device 2
          (5) both locking devices"
         ::= { cpqCmcSetupInput1 7 }



-- cpqCmcSetupInput2-group

     cpqCmcSetupInput2Avail         OBJECT-TYPE
         SYNTAX  INTEGER {
         other(1),
         available(2),
         notAvailable(3)
         }
         ACCESS  read-write
         STATUS  mandatory
         DESCRIPTION
         "Input 2 sensor:
          (2) available
         (3) not available"
         ::= { cpqCmcSetupInput2 1 }

     cpqCmcSetupInput2Relays         OBJECT-TYPE
         SYNTAX  INTEGER {
         other(1),
         off(2),
         relay1(3),
         relay2(4),
         both(5)
         }
         ACCESS  read-write
         STATUS  mandatory
         DESCRIPTION
         "Alert handling of Alarm Relays in case of a warning condition
          of Input 2 (Door/Sidewall open):
          (2) no switching of Relays
          (3) Relay 1 will switch
          (4) Relay 2 will switch
          (5) both Relays will switch"
         ::= { cpqCmcSetupInput2 2 }

     cpqCmcSetupInput2AudibleAlarm         OBJECT-TYPE
         SYNTAX  INTEGER {
         other(1),
         enabled(2),
         disabled(3)
         }
         ACCESS  read-write
         STATUS  mandatory
         DESCRIPTION
         "Alert handling of Audible Alarm of in case of a warning condition
          of Input 2 (Door/Sidewall open):
         (2) Start Audible Alarm
         (3) No Audible Alarm"
         ::= { cpqCmcSetupInput2 3 }

     cpqCmcSetupInput2FansOff         OBJECT-TYPE
         SYNTAX  INTEGER {
         other(1),
         both(2),
         fan1(3),
         fan2(4),
         noFan(5)
         }
         ACCESS  read-write
         STATUS  mandatory
         DESCRIPTION
         "Fan switching off if Door/Sidewall 2 is opened:
          (2) both fans would be switched off
          (3) only fan1 will be switched off
          (4) only fan2 will be switched off
          (5) no fan will be switched off"
         ::= { cpqCmcSetupInput2 4 }

     cpqCmcSetupInput2ShockSensor         OBJECT-TYPE
         SYNTAX  INTEGER {
         other(1),
         off(2),
         on(3)
         }
         ACCESS  read-write
         STATUS  mandatory
         DESCRIPTION
         "Shock sensor function if Door/Sidewall 2 is opened:
          (2) Shock Sensor is off (disabled)
          (3) Shock Sensor is on (enabled)"
         ::= { cpqCmcSetupInput2 5 }

     cpqCmcSetupInput2Description     OBJECT-TYPE
        SYNTAX DisplayString (SIZE (0..18))
        ACCESS read-write
        STATUS mandatory
        DESCRIPTION
        "Descriptional text of Input2"
        ::= { cpqCmcSetupInput2 6 }

     cpqCmcSetupInput2Lock         OBJECT-TYPE
         SYNTAX  INTEGER {
         other(1),
         none(2),
         lock1(3),
         lock2(4),
         both(5)
         }
         ACCESS  read-write
         STATUS  mandatory
         DESCRIPTION
         "Door/Sidewall 2 is locked by:
          (2) no locking device
          (3) locking device 1
          (4) locking device 2
          (5) both locking devices"
         ::= { cpqCmcSetupInput2 7 }




-- cpqCmcSetupInput3-group

     cpqCmcSetupInput3Avail         OBJECT-TYPE
         SYNTAX  INTEGER {
         other(1),
         available(2),
         notAvailable(3)
         }
         ACCESS  read-write
         STATUS  mandatory
         DESCRIPTION
         "Input 3 sensor:
          (2) available
         (3) not available"
         ::= { cpqCmcSetupInput3 1 }

     cpqCmcSetupInput3Relays         OBJECT-TYPE
         SYNTAX  INTEGER {
         other(1),
         off(2),
         relay1(3),
         relay2(4),
         both(5)
         }
         ACCESS  read-write
         STATUS  mandatory
         DESCRIPTION
         "Alert handling of Alarm Relays in case of a warning condition
          of Input 3 (Door/Sidewall open):
          (2) no switching of Relays
          (3) Relay 1 will switch
          (4) Relay 2 will switch
          (5) both Relays will switch"
         ::= { cpqCmcSetupInput3 2 }

     cpqCmcSetupInput3AudibleAlarm         OBJECT-TYPE
         SYNTAX  INTEGER {
         other(1),
         enabled(2),
         disabled(3)
         }
         ACCESS  read-write
         STATUS  mandatory
         DESCRIPTION
         "Alert handling of Audible Alarm of in case of a warning condition
          of Input 3 (Door/Sidewall open):
         (2) Start Audible Alarm
         (3) No Audible Alarm"
         ::= { cpqCmcSetupInput3 3 }


     cpqCmcSetupInput3FansOff         OBJECT-TYPE
         SYNTAX  INTEGER {
         other(1),
         both(2),
         fan1(3),
         fan2(4),
         noFan(5)
         }
         ACCESS  read-write
         STATUS  mandatory
         DESCRIPTION
         "Fan switching off if Door/Sidewall 3 is opened:
          (2) both fans would be switched off
          (3) only fan1 will be switched off
          (4) only fan2 will be switched off
          (5) no fan will be switched off"
         ::= { cpqCmcSetupInput3 4 }

     cpqCmcSetupInput3ShockSensor         OBJECT-TYPE
         SYNTAX  INTEGER {
         other(1),
         off(2),
         on(3)
         }
         ACCESS  read-write
         STATUS  mandatory
         DESCRIPTION
         "Shock sensor function if Door/Sidewall 3 is opened:
          (2) Shock Sensor is off (disabled)
          (3) Shock Sensor is on (enabled)"
         ::= { cpqCmcSetupInput3 5 }

     cpqCmcSetupInput3Description     OBJECT-TYPE
        SYNTAX DisplayString (SIZE (0..18))
        ACCESS read-write
        STATUS mandatory
        DESCRIPTION
        "Descriptional text of Input3"
        ::= { cpqCmcSetupInput3 6 }


     cpqCmcSetupInput3Lock         OBJECT-TYPE
         SYNTAX  INTEGER {
         other(1),
         none(2),
         lock1(3),
         lock2(4),
         both(5)
         }
         ACCESS  read-write
         STATUS  mandatory
         DESCRIPTION
         "Door/Sidewall 3 is locked by:
          (2) no locking device
          (3) locking device 1
          (4) locking device 2
          (5) both locking devices"
         ::= { cpqCmcSetupInput3 7 }



-- cpqCmcSetupInput4-group

     cpqCmcSetupInput4Avail         OBJECT-TYPE
         SYNTAX  INTEGER {
         other(1),
         available(2),
         notAvailable(3)
         }
         ACCESS  read-write
         STATUS  mandatory
         DESCRIPTION
         "Input 4 sensor:
          (2) available
         (3) not available"
         ::= { cpqCmcSetupInput4 1 }

     cpqCmcSetupInput4Relays         OBJECT-TYPE
         SYNTAX  INTEGER {
         other(1),
         off(2),
         relay1(3),
         relay2(4),
         both(5)
         }
         ACCESS  read-write
         STATUS  mandatory
         DESCRIPTION
         "Alert handling of Alarm Relays in case of a warning condition
          of Input 4 (Door/Sidewall open):
          (2) no switching of Relays
          (3) Relay 1 will switch
          (4) Relay 2 will switch
          (5) both Relays will switch"
         ::= { cpqCmcSetupInput4 2 }

     cpqCmcSetupInput4AudibleAlarm         OBJECT-TYPE
         SYNTAX  INTEGER {
         other(1),
         enabled(2),
         disabled(3)
         }
         ACCESS  read-write
         STATUS  mandatory
         DESCRIPTION
         "Alert handling of Audible Alarm of in case of a warning condition
          of Input 4 (Door/Sidewall open):
         (2) Start Audible Alarm
         (3) No Audible Alarm"
         ::= { cpqCmcSetupInput4 3 }


     cpqCmcSetupInput4FansOff         OBJECT-TYPE
         SYNTAX  INTEGER {
         other(1),
         both(2),
         fan1(3),
         fan2(4),
         noFan(5)
         }
         ACCESS  read-write
         STATUS  mandatory
         DESCRIPTION
         "Fan switching off if Door/Sidewall 4 is opened:
          (2) both fans would be switched off
          (3) only fan1 will be switched off
          (4) only fan2 will be switched off
          (5) no fan will be switched off"
         ::= { cpqCmcSetupInput4 4 }


     cpqCmcSetupInput4ShockSensor         OBJECT-TYPE
         SYNTAX  INTEGER {
         other(1),
         off(2),
         on(3)
         }
         ACCESS  read-write
         STATUS  mandatory
         DESCRIPTION
         "Shock sensor function if Door/Sidewall 4 is opened:
          (2) Shock Sensor is off (disabled)
          (3) Shock Sensor is on (enabled)"
         ::= { cpqCmcSetupInput4 5 }

     cpqCmcSetupInput4Description     OBJECT-TYPE
        SYNTAX DisplayString (SIZE (0..18))
        ACCESS read-write
        STATUS mandatory
        DESCRIPTION
        "Descriptional text of Input4"
        ::= { cpqCmcSetupInput4 6 }

     cpqCmcSetupInput4Lock         OBJECT-TYPE
         SYNTAX  INTEGER {
         other(1),
         none(2),
         lock1(3),
         lock2(4),
         both(5)
         }
         ACCESS  read-write
         STATUS  mandatory
         DESCRIPTION
         "Door/Sidewall 4 is locked by:
          (2) no locking device
          (3) locking device 1
          (4) locking device 2
          (5) both locking devices"
         ::= { cpqCmcSetupInput4 7 }



-- cpqCmcSetupLock1-group

     cpqCmcSetupLock1Avail       OBJECT-TYPE
         SYNTAX  INTEGER {
         other(1),
         available(2),
          notAvailable(3)
         }
         ACCESS  read-write
         STATUS  mandatory
         DESCRIPTION
         "Door locking device 1:
          (2) device available
          (3) device not available, no alarm, if door is not locked"
         ::= { cpqCmcSetupLock1 1 }

     cpqCmcSetupLock1Relays         OBJECT-TYPE
         SYNTAX  INTEGER {
         other(1),
         off(2),
         relay1(3),
         relay2(4),
         both(5)
         }
         ACCESS  read-write
         STATUS  mandatory
         DESCRIPTION
         "Alert handling of Alarm Relays in case of an alarm condition
          of Lock 1 (door not locked..):
          (2) no switching of Relays
          (3) Relay 1 will switch
          (4) Relay 2 will switch
          (5) both Relays will switch"
         ::= { cpqCmcSetupLock1 2 }

     cpqCmcSetupLock1RelaysDevice         OBJECT-TYPE
         SYNTAX  INTEGER {
         other(1),
         off(2),
         relay1(3),
         relay2(4),
         both(5)
         }
         ACCESS  read-write
         STATUS  mandatory
         DESCRIPTION
         "Alert handling of Alarm Relays in case of an alarm condition
          of Locking device 1 (power fail, low battery...):
          (2) no switching of Relays
          (3) Relay 1 will switch
          (4) Relay 2 will switch
          (5) both Relays will switch"
         ::= { cpqCmcSetupLock1 3 }


     cpqCmcSetupLock1AudibleAlarm         OBJECT-TYPE
         SYNTAX  INTEGER {
         other(1),
         enabled(2),
         disabled(3)
         }
         ACCESS  read-write
         STATUS  mandatory
         DESCRIPTION
         "Alert handling of Audible Alarm of in case of an alarm condition
          of Lock 1:
         (2) Start Audible Alarm
         (3) No Audible Alarm"
         ::= { cpqCmcSetupLock1 4 }

     cpqCmcSetupLock1AudibleAlarmDevice         OBJECT-TYPE
         SYNTAX  INTEGER {
         other(1),
         enabled(2),
         disabled(3)
         }
         ACCESS  read-write
         STATUS  mandatory
         DESCRIPTION
         "Alert handling of Audible Alarm of in case of an alarm condition
          of Locking device 1 (power fail, low battery..):
         (2) Start Audible Alarm
         (3) No Audible Alarm"
         ::= { cpqCmcSetupLock1 5 }


     cpqCmcSetupLock1Time      OBJECT-TYPE
         SYNTAX  INTEGER (3..600)
         ACCESS  read-write
         STATUS  mandatory
         DESCRIPTION
         "Time in seconds while the lock 1 is unlocked
          after getting an unlock-command"
         ::= { cpqCmcSetupLock1 6 }


     cpqCmcSetupLock1PwrFailUnlock         OBJECT-TYPE
         SYNTAX  INTEGER {
         other (1),
         disabled (2),
         auto (3),
         manual (4)
         }
         ACCESS  read-write
         STATUS  mandatory
         DESCRIPTION
         "Unlock door in case of power fail of locking device:
          (2) disabled
          (3) auto unlock the door
          (4) unlock door with remote signal"
         ::= { cpqCmcSetupLock1 7 }


     cpqCmcSetupLock1BattLowUnlock         OBJECT-TYPE
         SYNTAX  INTEGER {
         other (1),
         disabled (2),
         auto (3),
         manual (4)
         }
         ACCESS  read-write
         STATUS  mandatory
         DESCRIPTION
         "Unlock door in case of low battery of locking device:
          (2) disabled
          (3) auto unlock the door
          (4) unlock door with remote signal"
         ::= { cpqCmcSetupLock1 8 }

     cpqCmcSetupLock1NetFailUnlock         OBJECT-TYPE
         SYNTAX  INTEGER {
         other (1),
         disabled (2),
         auto (3),
         manual (4)
         }
         ACCESS  read-write
         STATUS  mandatory
         DESCRIPTION
         "Unlock door in case of network failure:
          (2) disabled
          (3) auto unlock the door
          (4) unlock door with remote signal"
         ::= { cpqCmcSetupLock1 9 }

     cpqCmcSetupLock1LifeFailUnlock         OBJECT-TYPE
         SYNTAX  INTEGER {
         other (1),
         disabled (2),
         auto (3),
         manual (4)
         }
         ACCESS  read-write
         STATUS  mandatory
         DESCRIPTION
         "Unlock door in case of lifecheck failure (connection CMC<->locking device):
          (2) disabled
          (3) auto unlock the door
          (4) unlock door with remote signal"
         ::= { cpqCmcSetupLock1 10 }


-- cpqCmcSetupLock2-group

     cpqCmcSetupLock2Avail       OBJECT-TYPE
         SYNTAX  INTEGER {
         other(1),
         available(2),
          notAvailable(3)
         }
         ACCESS  read-write
         STATUS  mandatory
         DESCRIPTION
         "Door locking device 2:
          (2) device available
          (3) device not available, no alarm, if door is not locked"
         ::= { cpqCmcSetupLock2 1 }

     cpqCmcSetupLock2Relays         OBJECT-TYPE
         SYNTAX  INTEGER {
         other(1),
         off(2),
         relay1(3),
         relay2(4),
         both(5)
         }
         ACCESS  read-write
         STATUS  mandatory
         DESCRIPTION
         "Alert handling of Alarm Relays in case of an alarm condition
          of Lock 2 (door not locked..):
          (2) no switching of Relays
          (3) Relay 1 will switch
          (4) Relay 2 will switch
          (5) both Relays will switch"
         ::= { cpqCmcSetupLock2 2 }

     cpqCmcSetupLock2RelaysDevice         OBJECT-TYPE
         SYNTAX  INTEGER {
         other(1),
         off(2),
         relay1(3),
         relay2(4),
         both(5)
         }
         ACCESS  read-write
         STATUS  mandatory
         DESCRIPTION
         "Alert handling of Alarm Relays in case of an alarm condition
          of Locking device 2 (power fail, low battery...):
          (2) no switching of Relays
          (3) Relay 1 will switch
          (4) Relay 2 will switch
          (5) both Relays will switch"
         ::= { cpqCmcSetupLock2 3 }


     cpqCmcSetupLock2AudibleAlarm         OBJECT-TYPE
         SYNTAX  INTEGER {
         other(1),
         enabled(2),
         disabled(3)
         }
         ACCESS  read-write
         STATUS  mandatory
         DESCRIPTION
         "Alert handling of Audible Alarm of in case of an alarm condition
          of Lock 2:
         (2) Start Audible Alarm
         (3) No Audible Alarm"
         ::= { cpqCmcSetupLock2 4 }

     cpqCmcSetupLock2AudibleAlarmDevice         OBJECT-TYPE
         SYNTAX  INTEGER {
         other(1),
         enabled(2),
         disabled(3)
         }
         ACCESS  read-write
         STATUS  mandatory
         DESCRIPTION
         "Alert handling of Audible Alarm of in case of an alarm condition
          of Locking device 2 (power fail, low battery..):
         (2) Start Audible Alarm
         (3) No Audible Alarm"
         ::= { cpqCmcSetupLock2 5 }


     cpqCmcSetupLock2Time      OBJECT-TYPE
         SYNTAX  INTEGER (3..600)
         ACCESS  read-write
         STATUS  mandatory
         DESCRIPTION
         "Time in seconds while the lock 2 is unlocked
          after getting an unlock-command"
         ::= { cpqCmcSetupLock2 6 }


     cpqCmcSetupLock2PwrFailUnlock         OBJECT-TYPE
         SYNTAX  INTEGER {
         other (1),
         disabled (2),
         auto (3),
         manual (4)
         }
         ACCESS  read-write
         STATUS  mandatory
         DESCRIPTION
         "Unlock door in case of power fail of locking device:
          (2) disabled
          (3) auto unlock the door
          (4) unlock door with remote signal"
         ::= { cpqCmcSetupLock2 7 }

     cpqCmcSetupLock2BattLowUnlock         OBJECT-TYPE
         SYNTAX  INTEGER {
         other (1),
         disabled (2),
         auto (3),
         manual (4)
         }
         ACCESS  read-write
         STATUS  mandatory
         DESCRIPTION
         "Unlock door in case of low battery of locking device:
          (2) disabled
          (3) auto unlock the door
          (4) unlock door with remote signal"
         ::= { cpqCmcSetupLock2 8 }


     cpqCmcSetupLock2NetFailUnlock         OBJECT-TYPE
         SYNTAX  INTEGER {
         other (1),
         disabled (2),
         auto (3),
         manual (4)
         }
         ACCESS  read-write
         STATUS  mandatory
         DESCRIPTION
         "Unlock door in case of network failure:
          (2) disabled
          (3) auto unlock the door
          (4) unlock door with remote signal"
         ::= { cpqCmcSetupLock2 9 }


     cpqCmcSetupLock2LifeFailUnlock         OBJECT-TYPE
         SYNTAX  INTEGER {
         other (1),
         disabled (2),
         auto (3),
         manual (4)
         }
         ACCESS  read-write
         STATUS  mandatory
         DESCRIPTION
         "Unlock door in case of lifecheck failure (connection CMC<->locking device):
          (2) disabled
          (3) auto unlock the door
          (4) unlock door with remote signal"
         ::= { cpqCmcSetupLock2 10 }



-- cpqCmcSetupSmoke-group

     cpqCmcSetupSmokeAvail        OBJECT-TYPE
         SYNTAX  INTEGER {
         other(1),
         available(2),
         notAvailable(3)
         }
         ACCESS  read-write
         STATUS  mandatory
         DESCRIPTION
         "Smoke sensor:
          (2) available
         (3) not available"
         ::= { cpqCmcSetupSmoke 1 }


     cpqCmcSetupSmokeRelays         OBJECT-TYPE
         SYNTAX  INTEGER {
         other(1),
         off(2),
         relay1(3),
         relay2(4),
         both(5)
         }
         ACCESS  read-write
         STATUS  mandatory
         DESCRIPTION
         "Alert handling of Alarm Relays in case of an alarm condition
          of Smoke Sensor:
          (2) no switching of Relays
          (3) Relay 1 will switch
          (4) Relay 2 will switch
          (5) both Relays will switch"
         ::= { cpqCmcSetupSmoke 2 }

     cpqCmcSetupSmokeAudibleAlarm         OBJECT-TYPE
         SYNTAX  INTEGER {
         other(1),
         enabled(2),
         disabled(3)
         }
         ACCESS  read-write
         STATUS  mandatory
         DESCRIPTION
         "Alert handling of Audible Alarm of in case of an alarm condition
          of Smoke Sensor:
         (2) Start Audible Alarm
         (3) No Audible Alarm"
         ::= { cpqCmcSetupSmoke 3 }


     cpqCmcSetupSmokeFansOff         OBJECT-TYPE
         SYNTAX  INTEGER {
         other(1),
         both(2),
         fan1(3),
         fan2(4),
         noFan(5)
         }
         ACCESS  read-write
         STATUS  mandatory
         DESCRIPTION
         "Fan switching off if in case of smoke-alarm:
          (2) both fans would be switched off
          (3) only fan1 will be switched off
          (4) only fan2 will be switched off
          (5) no fan will be switched off"
         ::= { cpqCmcSetupSmoke 4 }

     cpqCmcSetupSmokeUnlock         OBJECT-TYPE
         SYNTAX  INTEGER {
         other(1),
         both(2),
         lock1(3),
         lock2(4),
         noLock(5)
         }
         ACCESS  read-write
         STATUS  mandatory
         DESCRIPTION
         "Lock is unlocked in case of smoke-alarm:
          (2) both locks will be unlocked
          (3) only lock1 will be unlocked
          (4) only lock2 will be unlocked
          (5) no lock will be unlocked"
         ::= { cpqCmcSetupSmoke 5 }




-- cpqCmcSetupShock-group

     cpqCmcSetupShockAvail        OBJECT-TYPE
         SYNTAX  INTEGER {
         other(1),
         available(2),
         notAvailable(3)
         }
         ACCESS  read-write
         STATUS  mandatory
         DESCRIPTION
         "Shock sensor:
          (2) available
         (3) not available"
         ::= { cpqCmcSetupShock 1 }

     cpqCmcSetupShockRelays         OBJECT-TYPE
         SYNTAX  INTEGER {
         other(1),
         off(2),
         relay1(3),
         relay2(4),
         both(5)
         }
         ACCESS  read-write
         STATUS  mandatory
         DESCRIPTION
         "Alert handling of Alarm Relays in case of an alarm condition
          of Shock Sensor:
          (2) no switching of Relays
          (3) Relay 1 will switch
          (4) Relay 2 will switch
          (5) both Relays will switch"
         ::= { cpqCmcSetupShock 2 }


     cpqCmcSetupShockAudibleAlarm         OBJECT-TYPE
         SYNTAX  INTEGER {
         other(1),
         enabled(2),
         disabled(3)
         }
         ACCESS  read-write
         STATUS  mandatory
         DESCRIPTION
         "Alert handling of Audible Alarm of in case of an alarm condition
          of Shock Sensor:
         (2) Start Audible Alarm
         (3) No Audible Alarm"
         ::= { cpqCmcSetupShock 3 }


     cpqCmcSetupShockSensitivity         OBJECT-TYPE
         SYNTAX  INTEGER (1..10)
         ACCESS  read-write
         STATUS  mandatory
         DESCRIPTION
         "Sensitivity of shock-sensor.
          1 = low sensitivity, 10 = high sensitivity"
         ::= { cpqCmcSetupShock 4 }



-- cpqCmcSetupAux1-group

     cpqCmcSetupAux1Avail        OBJECT-TYPE
         SYNTAX  INTEGER {
         other(1),
         available(2),
         notAvailable(3)
         }
         ACCESS  read-write
         STATUS  mandatory
         DESCRIPTION
         "Aux 1 sensor:
          (2) available
         (3) not available"
         ::= { cpqCmcSetupAux1 1 }


     cpqCmcSetupAux1Relays         OBJECT-TYPE
         SYNTAX  INTEGER {
         other(1),
         off(2),
         relay1(3),
         relay2(4),
         both(5)
         }
         ACCESS  read-write
         STATUS  mandatory
         DESCRIPTION
         "Alert handling of Alarm Relays in case of an alarm condition
          of Aux 1:
          (2) no switching of Relays
          (3) Relay 1 will switch
          (4) Relay 2 will switch
          (5) both Relays will switch"
         ::= { cpqCmcSetupAux1 2 }


     cpqCmcSetupAux1AudibleAlarm         OBJECT-TYPE
         SYNTAX  INTEGER {
         other(1),
         enabled(2),
         disabled(3)
         }
         ACCESS  read-write
         STATUS  mandatory
         DESCRIPTION
         "Alert handling of Audible Alarm of in case of an alarm condition
          of Aux 1:
         (2) Start Audible Alarm
         (3) No Audible Alarm"
         ::= { cpqCmcSetupAux1 3 }


     cpqCmcSetupAux1InputType         OBJECT-TYPE
         SYNTAX  INTEGER {
         other(1),
         normOpen(2),
         normClosed(3)
         }
         ACCESS  read-write
         STATUS  mandatory
         DESCRIPTION
         "Type of other digital input (used for any digital signal):
          (2) contact is normally open, no alarm if contact is open,
         alarm if contact is closed
          (3) contact is normally closed, no alarm if contact is closed,
         alarm if contact is open"
         ::= { cpqCmcSetupAux1 4 }


     cpqCmcSetupAux1Description     OBJECT-TYPE
        SYNTAX DisplayString (SIZE (0..18))
        ACCESS read-write
        STATUS mandatory
        DESCRIPTION
        "Descriptional text of the digital input (Aux1) "
        ::= { cpqCmcSetupAux1 5 }


     cpqCmcSetupAux1Unlock         OBJECT-TYPE
         SYNTAX  INTEGER {
         other(1),
         noLock(2),
         lock1(3),
         lock2(4),
         both(5)
         }
         ACCESS  read-write
         STATUS  mandatory
         DESCRIPTION
         "Lock will be unlocked with Aux-Input 1:
          (2) no lock will be unlocked
          (3) only lock1 will be unlocked
          (4) only lock2 will be unlocked
          (5) both locks will be unlocked"
         ::= { cpqCmcSetupAux1 6 }



-- cpqCmcSetupAux2-group

     cpqCmcSetupAux2Avail        OBJECT-TYPE
         SYNTAX  INTEGER {
         other(1),
         available(2),
         notAvailable(3)
         }
         ACCESS  read-write
         STATUS  mandatory
         DESCRIPTION
         "Aux 2 sensor:
          (2) available
         (3) not available"
         ::= { cpqCmcSetupAux2 1 }


     cpqCmcSetupAux2Relays         OBJECT-TYPE
         SYNTAX  INTEGER {
         other(1),
         off(2),
         relay1(3),
         relay2(4),
         both(5)
         }
         ACCESS  read-write
         STATUS  mandatory
         DESCRIPTION
         "Alert handling of Alarm Relays in case of an alarm condition
          of Aux 2:
          (2) no switching of Relays
          (3) Relay 1 will switch
          (4) Relay 2 will switch
          (5) both Relays will switch"
         ::= { cpqCmcSetupAux2 2 }

     cpqCmcSetupAux2AudibleAlarm         OBJECT-TYPE
         SYNTAX  INTEGER {
         other(1),
         enabled(2),
         disabled(3)
         }
         ACCESS  read-write
         STATUS  mandatory
         DESCRIPTION
         "Alert handling of Audible Alarm of in case of an alarm condition
          of Aux 2:
         (2) Start Audible Alarm
         (3) No Audible Alarm"
         ::= { cpqCmcSetupAux2 3 }


     cpqCmcSetupAux2InputType         OBJECT-TYPE
         SYNTAX  INTEGER {
         other(1),
         normOpen(2),
         normClosed(3)
         }
         ACCESS  read-write
         STATUS  mandatory
         DESCRIPTION
         "Type of other digital input (used for any digital signal):
          (2) contact is normally open, no alarm if contact is open,
         alarm if contact is closed
          (3) contact is normally closed, no alarm if contact is closed,
         alarm if contact is open"
         ::= { cpqCmcSetupAux2 4 }


     cpqCmcSetupAux2Description     OBJECT-TYPE
        SYNTAX DisplayString (SIZE (0..18))
        ACCESS read-write
        STATUS mandatory
        DESCRIPTION
        "Descriptional text of the digital input (Aux2) "
        ::= { cpqCmcSetupAux2 5 }


     cpqCmcSetupAux2Unlock         OBJECT-TYPE
         SYNTAX  INTEGER {
         other(1),
         noLock(2),
         lock1(3),
         lock2(4),
         both(5)
         }
         ACCESS  read-write
         STATUS  mandatory
         DESCRIPTION
         "Lock will be unlocked with Aux-Input 2:
          (2) no lock will be unlocked
          (3) only lock1 will be unlocked
          (4) only lock2 will be unlocked
          (5) both locks will be unlocked"
         ::= { cpqCmcSetupAux2 6 }




-- cpqCmcSetupAlarm1-group
-- alarm can be set, see cpqCmcSetAlarm1

     cpqCmcSetupAlarm1Relays         OBJECT-TYPE
         SYNTAX  INTEGER {
         other(1),
         off(2),
         relay1(3),
         relay2(4),
         both(5)
         }
         ACCESS  read-write
         STATUS  mandatory
         DESCRIPTION
         "Alert handling of Alarm Relays in case of an alarm condition
          of Alarm 1:
          (2) no switching of Relays
          (3) Relay 1 will switch
          (4) Relay 2 will switch
          (5) both Relays will switch"
         ::= { cpqCmcSetupAlarm1 1 }

     cpqCmcSetupAlarm1AudibleAlarm         OBJECT-TYPE
         SYNTAX  INTEGER {
         other(1),
         enabled(2),
         disabled(3)
         }
         ACCESS  read-write
         STATUS  mandatory
         DESCRIPTION
         "Alert handling of Audible Alarm of in case of an alarm condition
          of Alarm 1:
         (2) Start Audible Alarm
         (3) No Audible Alarm"
         ::= { cpqCmcSetupAlarm1 2 }


     cpqCmcSetupAlarm1Description     OBJECT-TYPE
         SYNTAX DisplayString (SIZE (0..18))
         ACCESS read-write
         STATUS mandatory
         DESCRIPTION
         "Descriptional text of alarm 1"
         ::= { cpqCmcSetupAlarm1 3 }



-- cpqCmcSetupAlarm2-group
-- alarm can be set, see cpqCmcSetAlarm2

     cpqCmcSetupAlarm2Relays         OBJECT-TYPE
         SYNTAX  INTEGER {
         other(1),
         off(2),
         relay1(3),
         relay2(4),
         both(5)
         }
         ACCESS  read-write
         STATUS  mandatory
         DESCRIPTION
         "Alert handling of Alarm Relays in case of an alarm condition
          of Alarm 2:
          (2) no switching of Relays
          (3) Relay 1 will switch
          (4) Relay 2 will switch
          (5) both Relays will switch"
         ::= { cpqCmcSetupAlarm2 1 }

     cpqCmcSetupAlarm2AudibleAlarm         OBJECT-TYPE
         SYNTAX  INTEGER {
         other(1),
         enabled(2),
         disabled(3)
         }
         ACCESS  read-write
         STATUS  mandatory
         DESCRIPTION
         "Alert handling of Audible Alarm of in case of an alarm condition
          of Alarm 2:
         (2) Start Audible Alarm
         (3) No Audible Alarm"
         ::= { cpqCmcSetupAlarm2 2 }


     cpqCmcSetupAlarm2Description     OBJECT-TYPE
        SYNTAX DisplayString (SIZE (0..18))
        ACCESS read-write
        STATUS mandatory
        DESCRIPTION
        "Descriptional text of alarm 2"
        ::= { cpqCmcSetupAlarm2 3 }



--*****************************************************************************
-- cpqCmcSetupClock

     cpqCmcSetupDate     OBJECT-TYPE
        SYNTAX DisplayString (SIZE (0..10))
        ACCESS read-write
        STATUS mandatory
        DESCRIPTION
        "actual Date in format DD.MM.YYYY"
        ::= { cpqCmcSetupClock 1 }


     cpqCmcSetupTime     OBJECT-TYPE
        SYNTAX DisplayString (SIZE (0..8))
        ACCESS read-write
        STATUS mandatory
        DESCRIPTION
        "actual Time in format HH:MM:SS, HH (0-23), MM (0-59), SS (0-59)"
        ::= { cpqCmcSetupClock 2 }

--*****************************************************************************
-- cpqCmcSetupThreshold-group

     cpqCmcThresholdMaxTemp1     OBJECT-TYPE
         SYNTAX  INTEGER (0..200)
         ACCESS  read-write
         STATUS  mandatory
         DESCRIPTION
         "Threshold value maximum temperature 1"
         ::= { cpqCmcSetupThreshold 1 }

     cpqCmcThresholdWarningTemp1        OBJECT-TYPE
         SYNTAX  INTEGER (0..200)
         ACCESS  read-write
         STATUS  mandatory
         DESCRIPTION
         "Threshold value warning temperature 1"
         ::= { cpqCmcSetupThreshold 2 }

     cpqCmcThresholdMinTemp1        OBJECT-TYPE
         SYNTAX  INTEGER (0..100)
         ACCESS  read-write
         STATUS  mandatory
         DESCRIPTION
         "Threshold value minimum temperature 1"
         ::= { cpqCmcSetupThreshold 3 }


     cpqCmcThresholdMaxTemp2     OBJECT-TYPE
         SYNTAX  INTEGER (0..200)
         ACCESS  read-write
         STATUS  mandatory
         DESCRIPTION
         "Threshold value maximum temperature 2"
         ::= { cpqCmcSetupThreshold 4 }

     cpqCmcThresholdWarningTemp2        OBJECT-TYPE
         SYNTAX  INTEGER (0..200)
         ACCESS  read-write
         STATUS  mandatory
         DESCRIPTION
         "Threshold value warning temperature 2"
         ::= { cpqCmcSetupThreshold 5 }

     cpqCmcThresholdMinTemp2        OBJECT-TYPE
         SYNTAX  INTEGER (0..100)
         ACCESS  read-write
         STATUS  mandatory
         DESCRIPTION
         "Threshold value minimum temperature 2"
         ::= { cpqCmcSetupThreshold 6 }

     cpqCmcThresholdFan1        OBJECT-TYPE
         SYNTAX  INTEGER (0..200)
         ACCESS  read-write
         STATUS  mandatory
         DESCRIPTION
         "Threshold Fan 1 in deg F or deg C, Fan 1 will start
          if temperature 1 exceeds this value"
         ::= { cpqCmcSetupThreshold 7 }

     cpqCmcThresholdFan1Hysteresis     OBJECT-TYPE
         SYNTAX  INTEGER (1..20)
         ACCESS  read-write
         STATUS  mandatory
         DESCRIPTION
         "Hystersis of Fan 1, Fan 1 will stop if temperature 1 falls below
          value of cpqCmcThresholdFan1 minus cpqCmcThresholdFan1Hysteresis"
         ::= { cpqCmcSetupThreshold 8 }

     cpqCmcThresholdFan2             OBJECT-TYPE
         SYNTAX  INTEGER (0..200)
         ACCESS  read-write
         STATUS  mandatory
         DESCRIPTION
         "Threshold Fan 2 in deg F or deg C, Fan 2 will start
          if temperature 2 exceeds this value"
         ::= { cpqCmcSetupThreshold 9 }

     cpqCmcThresholdFan2Hysteresis     OBJECT-TYPE
         SYNTAX  INTEGER (1..20)
         ACCESS  read-write
         STATUS  mandatory
         DESCRIPTION
         "Hystersis of Fan 2, Fan 2 will stop if temperature 2 falls below
          value of cpqCmcThresholdFan2 minus cpqCmcThresholdFan2Hysteresis"
         ::= { cpqCmcSetupThreshold 10 }

     cpqCmcThresholdMaxVoltage            OBJECT-TYPE
         SYNTAX  INTEGER (0..255)
         ACCESS  read-write
         STATUS  mandatory
         DESCRIPTION
         "Threshold high value Voltage alarm"
         ::= { cpqCmcSetupThreshold 11 }

     cpqCmcThresholdMinVoltage            OBJECT-TYPE
         SYNTAX  INTEGER (0..255)
         ACCESS  read-write
         STATUS  mandatory
         DESCRIPTION
         "Threshold low value Voltage alarm"
         ::= { cpqCmcSetupThreshold 12 }

     cpqCmcThresholdMaxHumidity          OBJECT-TYPE
         SYNTAX  INTEGER (0..100)
         ACCESS  read-write
         STATUS  mandatory
         DESCRIPTION
         "Threshold high value Humidity alarm"
         ::= { cpqCmcSetupThreshold 13 }


     cpqCmcThresholdMinHumidity           OBJECT-TYPE
         SYNTAX  INTEGER (0..100)
         ACCESS  read-write
         STATUS  mandatory
         DESCRIPTION
         "Threshold low value Humidity alarm"
         ::= { cpqCmcSetupThreshold 14 }


--*****************************************************************************

--cpqCmcTrapTable-group

     cpqCmcTrapTableNumber            OBJECT-TYPE
         SYNTAX  INTEGER
         ACCESS  read-only
         STATUS  mandatory
         DESCRIPTION
         "Number of trapTable entries. The number of trap-receivers"
         ::= { cpqCmcTraps 1 }

     cpqCmcTrapTable             OBJECT-TYPE
         SYNTAX  SEQUENCE OF CpqCmcTrapEntry
         ACCESS  not-accessible
         STATUS  mandatory
         DESCRIPTION
         "A list of trap-receiver entries"
         ::= { cpqCmcTraps 2 }

     cpqCmcTrapEntry            OBJECT-TYPE
         SYNTAX  CpqCmcTrapEntry
         ACCESS  not-accessible
         STATUS  mandatory
         DESCRIPTION
         "Entries of trapTable"
         INDEX   { cpqCmcTrapIndex }
         ::= { cpqCmcTrapTable 1 }

          CpqCmcTrapEntry ::=
         SEQUENCE {
         cpqCmcTrapIndex
      INTEGER,
         cpqCmcTrapStatus
      INTEGER,
         cpqCmcTrapIPaddress
      DisplayString
         }

         cpqCmcTrapIndex OBJECT-TYPE
        SYNTAX INTEGER (1..4)
        ACCESS read-only
        STATUS mandatory
        DESCRIPTION
        "Index for the trap-receiver-table. Its value ranges between
         1 and the value of cpqCmcTrapTableNumber "
        ::= { cpqCmcTrapEntry 1 }

         cpqCmcTrapStatus OBJECT-TYPE
        SYNTAX INTEGER  {
        other(1),
        enabled(2),
        disabled(3)
        }
        ACCESS read-write
        STATUS mandatory
        DESCRIPTION
        "Enable or disable trap receiver"
        ::= { cpqCmcTrapEntry 2 }

         cpqCmcTrapIPaddress OBJECT-TYPE
        SYNTAX DisplayString (SIZE (0..15))
        ACCESS read-write
        STATUS mandatory
        DESCRIPTION
        "IP-address of trap-receiver"
        ::= { cpqCmcTrapEntry 3 }


--*****************************************************************************
-- cpqCmcValues-group
     cpqCmcValueTemp1 OBJECT-TYPE
         SYNTAX  INTEGER
         ACCESS  read-only
         STATUS  mandatory
         DESCRIPTION
         "Actual temperature value of temperature sensor 1 in deg C or deg F"
         ::= { cpqCmcValues 1 }

     cpqCmcValueTemp2 OBJECT-TYPE
         SYNTAX  INTEGER
         ACCESS  read-only
         STATUS  mandatory
         DESCRIPTION
         "Actual temperature value of temperature sensor 2 in deg C or deg F"
         ::= { cpqCmcValues 2 }

     cpqCmcValueVoltage     OBJECT-TYPE
         SYNTAX  INTEGER
         ACCESS  read-only
         STATUS  mandatory
         DESCRIPTION
         "Actual value of power supply (voltage monitoring and fans) in V"
         ::= { cpqCmcValues 3 }

     cpqCmcValueHumidity  OBJECT-TYPE
         SYNTAX  INTEGER
         ACCESS  read-only
         STATUS  mandatory
         DESCRIPTION
         "Actual value of humidity
         0..100%"
         ::= { cpqCmcValues 4 }

     cpqCmcValueOperatingTime    OBJECT-TYPE
         SYNTAX  DisplayString (SIZE (0..31))
         ACCESS  read-only
         STATUS  mandatory
         DESCRIPTION
         "Operating time CMC-unit"
         ::= { cpqCmcValues 5 }

--******************************************************************************
--cpqCmcStatus-group

     cpqCmcStatusTemp1 OBJECT-TYPE
         SYNTAX  INTEGER {
         other (1),
         normal (2),
         warning (3),
         overMax (4),
         underMin (5),
         noSensor (6),
         error (7)
         }
         ACCESS  read-only
         STATUS  mandatory
         DESCRIPTION
         "The status of temperature 1,
         see thresholds of temperature 1:
         (2) temperature normal
         (3) temperature exceeds warning threshold
         (4) temperature exceeds max. threshold
         (5) temperature drops under min. threshold
         (6) no sensor connected, not available
         (7) error, sensor disconnected"
         ::= { cpqCmcStatus 1 }

     cpqCmcStatusTemp2 OBJECT-TYPE
         SYNTAX  INTEGER {
         other (1),
         normal (2),
         warning (3),
         overMax (4),
         underMin (5),
         noSensor (6),
         error (7)
         }
         ACCESS  read-only
         STATUS  mandatory
         DESCRIPTION
         "The status of temperature 2,
         see thresholds of temperature 2:
         (2) temperature normal
         (3) temperature exceeds warning threshold
         (4) temperature exceeds max. threshold
         (5) temperature drops under min. threshold
         (6) no sensor connected, not available
         (7) error, sensor disconnected"
         ::= { cpqCmcStatus 2 }

     cpqCmcStatusFan1  OBJECT-TYPE
         SYNTAX  INTEGER {
         other (1),
         autoOff (2),
         autoOn (3),
         manualOff (4),
         manualOn (5),
         smokeOff (6),
         doorOff (7),
         noFan (8),
         error (9)
         }
         ACCESS  read-only
         STATUS  mandatory
         DESCRIPTION
         "The status of fan 1:
          (2) fan is switched off by temperature sensor 1
           (3) fan is switched on by temperature sensor 1
          (4) fan is switched off by Manual Control (cpqCmcSetFan1)
          (5) fan is switched on by Manual Control (cpqCmcSetFan1)
          (6) fan is switched off because of smoke alarm
           (7) fan is switched off because door is open
          (8) no fan
           (9) fan error, current monitoring"
         ::= { cpqCmcStatus 3 }

     cpqCmcStatusFan2  OBJECT-TYPE
         SYNTAX  INTEGER {
         other (1),
         autoOff (2),
         autoOn (3),
         manualOff (4),
         manualOn (5),
         smokeOff (6),
         doorOff (7),
         noFan (8),
         error (9)
         }
         ACCESS  read-only
         STATUS  mandatory
         DESCRIPTION
         "The status of fan 2:
          (2) fan is switched off by temperature sensor 2
           (3) fan is switched on by temperature sensor 2
          (4) fan is switched off by Manual Control (cpqCmcSetFan2)
          (5) fan is switched on by Manual Control (cpqCmcSetFan2)
          (6) fan is switched off because of smoke alarm
           (7) fan is switched off because door is open
          (8) no fan
           (9) fan error, current monitoring"
         ::= { cpqCmcStatus 4 }

     cpqCmcStatusVoltage  OBJECT-TYPE
         SYNTAX  INTEGER {
         other (1),
         normal (2),
         overMax (3),
         underMin (4),
         noVoltage (5)
         }
         ACCESS  read-only
         STATUS  mandatory
         DESCRIPTION
         "The voltage-status,
         see thresholds of power supply:
         (2) voltage normal
         (3) voltage exceeds max. threshold
         (4) voltage drops under min. threshold
         (5) no power connected"
         ::= { cpqCmcStatus 5 }

     cpqCmcStatusHumidity  OBJECT-TYPE
         SYNTAX  INTEGER {
         other (1),
         normal (2),
         overMax (3),
         underMin (4),
         noSensor (5),
         error (6)
         }
         ACCESS  read-only
         STATUS  mandatory
         DESCRIPTION
         "The humidity-status,
         see thresholds of humidity:
         (2) humidity normal
         (3) humidity exceeds max. threshold
         (4) humidity drops under min. threshold
         (5) no sensor connected, not available
         (6) error, sensor disconnected"
         ::= { cpqCmcStatus 6 }

     cpqCmcStatusInput1  OBJECT-TYPE
         SYNTAX  INTEGER {
         other (1),
         closed (2),
         open (3),
         noSensor(4)
         }
         ACCESS  read-only
         STATUS  mandatory
         DESCRIPTION
         "The status of door/sidepanel 1, closed (2), open (3)
          or no sensor connected (4)"
         ::= { cpqCmcStatus 7 }

     cpqCmcStatusInput2  OBJECT-TYPE
         SYNTAX  INTEGER {
         other (1),
         closed (2),
         open (3),
         noSensor(4)
         }
         ACCESS  read-only
         STATUS  mandatory
         DESCRIPTION
         "The status of door/sidepanel 2, closed (2), open (3)
          or no sensor connected (4)"
         ::= { cpqCmcStatus 8 }

     cpqCmcStatusInput3  OBJECT-TYPE
         SYNTAX  INTEGER {
         other (1),
         closed (2),
         open (3),
         noSensor(4)
         }
         ACCESS  read-only
         STATUS  mandatory
         DESCRIPTION
         "The status of door/sidepanel 3, closed (2), open (3)
          or no sensor connected (4)"
         ::= { cpqCmcStatus 9 }

     cpqCmcStatusInput4  OBJECT-TYPE
         SYNTAX  INTEGER {
         other (1),
         closed (2),
         open (3),
         noSensor(4)
         }
         ACCESS  read-only
         STATUS  mandatory
         DESCRIPTION
         "The status of door/sidepanel 4, closed (2), open (3)
          or no sensor connected (4)"
         ::= { cpqCmcStatus 10 }


     cpqCmcStatusLock1Lock   OBJECT-TYPE
         SYNTAX  INTEGER {
         other (1),
         locked (2),
         unlockedAuto (3),
         unlockedTime (4),
         unlockedSmoke (5),
         unlockedKey (6),
         unlockedPwrFail (7),
         unlockedBattLow (8),
         unlockedNetFail (9),
         unlockedConnFail (10),
         readyToLock (11),
         alarm (12),
         configError (13),
         notAvail (14)
         }
         ACCESS  read-only
         STATUS  mandatory
         DESCRIPTION
         "The status of door locking 1
          (2) Door locking-device is activated, door is locked
          (3) Door locking-device is not activated, door is unlocked by Network Management
          (4) Door locking-device is not activated for x sec, time see
              cpqCmcSetupLock1Time, door is unlocked by Network Management
          (5) Door locking-device is not activated, door is unlocked because of Smoke alarm
          (6) Door is unlocked from remote-signal
          (7) Door locking-device is not activated, door is unlocked
         because of Power Fail of locking device
          (8) Door locking-device is not activated, door is unlocked
         because of low Battery of locking device
          (9) Door locking-device is not activated, door is unlocked
         because of Network Fail
          (10)Door locking-device is not activated, door is unlocked
         because of connection fail, no connection locking device <-> CMC
          (11)Door locking-device is ready to lock, lock will be activated after doors are closed
          (12)Door locking-device is activated but door is not locked, alarm
          (13)Configuration error, association door to locking-device missing
          (14)Lock not installed"
         ::= { cpqCmcStatus 11 }

     cpqCmcStatusLock2Lock   OBJECT-TYPE
         SYNTAX  INTEGER {
         other (1),
         locked (2),
         unlockedAuto (3),
         unlockedTime (4),
         unlockedSmoke (5),
         unlockedKey (6),
         unlockedPwrFail (7),
         unlockedBattLow (8),
         unlockedNetFail (9),
         unlockedConnFail (10),
         readyToLock (11),
         alarm (12),
         configError (13),
         notAvail (14)
         }
         ACCESS  read-only
         STATUS  mandatory
         DESCRIPTION
         "The status of door locking 2
          (2) Door locking-device is activated, door is locked
          (3) Door locking-device is not activated, door is unlocked by Network Management
          (4) Door locking-device is not activated for x sec, time see
              cpqCmcSetupLock1Time, door is unlocked by Network Management
          (5) Door locking-device is not activated, door is unlocked because of Smoke alarm
          (6) Door is unlocked from remote-signal
          (7) Door locking-device is not activated, door is unlocked
         because of Power Fail of locking device
          (8) Door locking-device is not activated, door is unlocked
         because of low Battery of locking device
          (9) Door locking-device is not activated, door is unlocked
         because of Network Fail
          (10)Door locking-device is not activated, door is unlocked
         because of connection fail, no connection locking device <-> CMC
          (11)Door locking-device is ready to lock, lock will be activated after doors are closed
          (12)Door locking-device is activated but door is not locked, alarm
          (13)Configuration error, association door to locking-device missing
          (14)Lock not installed"
         ::= { cpqCmcStatus 12 }


     cpqCmcStatusSmoke  OBJECT-TYPE
         SYNTAX  INTEGER {
         other (1),
         cleared (2),
         present (3),
         noSensor (4)
         }
         ACCESS    read-only
         STATUS    mandatory
         DESCRIPTION
         "Status smoke-sensor, OK (2), smoke detected (3)
          or no sensor connected (4)"
         ::= { cpqCmcStatus 13 }

     cpqCmcStatusShock  OBJECT-TYPE
         SYNTAX  INTEGER {
         other (1),
         cleared (2),
         present (3),
         noSensor (4)
         }
         ACCESS  read-only
         STATUS  mandatory
         DESCRIPTION
         "Status Shock sensor, OK (2), shock detected (3)
          or no sensor connected (4)"
         ::= { cpqCmcStatus 14 }

     cpqCmcStatusAux1  OBJECT-TYPE
         SYNTAX  INTEGER {
         other (1),
         ok (2),
         alarm (3),
         noSensor(4)
         }
         ACCESS  read-only
         STATUS  mandatory
         DESCRIPTION
         "Status aux. digital input"
         ::= { cpqCmcStatus 15 }

     cpqCmcStatusAux2  OBJECT-TYPE
         SYNTAX  INTEGER {
         other (1),
         ok (2),
         alarm (3),
         noSensor(4)
         }
         ACCESS  read-only
         STATUS  mandatory
         DESCRIPTION
         "Status aux. digital input"
         ::= { cpqCmcStatus 16 }

     cpqCmcStatusAlarm1  OBJECT-TYPE
         SYNTAX  INTEGER {
         other (1),
         ok (2),
         alarm (3)
         }
         ACCESS  read-only
         STATUS  mandatory
         DESCRIPTION
         "Status of alarm 1, see cmpCmcsetAlarm1. This alarm can be set from
         the Network management system. A descriptional text for this alarm
         can be set in cpqCmcSetupAlarm1Description."
         ::= { cpqCmcStatus 17 }

     cpqCmcStatusAlarm2  OBJECT-TYPE
         SYNTAX  INTEGER {
         other (1),
         ok (2),
         alarm (3)
         }
         ACCESS  read-only
         STATUS  mandatory
         DESCRIPTION
         "Status of alarm 2, see cmpCmcsetAlarm2. This alarm can be set from
         the Network management system. A descriptional text for this alarm
         can be set in cpqCmcSetupAlarm2Description."
         ::= { cpqCmcStatus 18 }

-- cpqCmcStatusLock1Dev
-- MIB V1.1



     cpqCmcStatusLock1Dev   OBJECT-TYPE
         SYNTAX  INTEGER {
         other (1),
         ok (2),
         powerFail (3),
         lowBattery (4),
         replaceBatt (5),
         missingBatt (6),
         noConnect (7),
         notAvail (8)
         }
         ACCESS  read-only
         STATUS  mandatory
         DESCRIPTION
         "The status of door-locking device 1
          (2) OK
          (3) Power fail of door locking-device
          (4) Low Battery of door locking-device
          (5) Battery of door locking device needs to be replaced
          (6) Battery missing, insert all batteries
          (7) Connection CMC->door locking device lost
          (8) Lock not installed"
         ::= { cpqCmcStatus 19 }




     cpqCmcStatusLock2Dev   OBJECT-TYPE
         SYNTAX  INTEGER {
         other (1),
         ok (2),
         powerFail (3),
         lowBattery (4),
         replaceBatt (5),
         missingBatt (6),
         noConnect (7),
         notAvail (8)
         }
         ACCESS  read-only
         STATUS  mandatory
         DESCRIPTION
         "The status of door-locking device 2
          (2) OK
          (3) Power fail of door locking-device
          (4) Low Battery of door locking-device
          (5) Battery of door locking device needs to be replaced
          (6) Battery missing, insert all batteries
          (6) Connection CMC->door locking device lost
          (7) Lock not installed"
         ::= { cpqCmcStatus 20 }



-- ***********************************************************************
-- cpqCmcControl-group

     cpqCmcStatusAccess  OBJECT-TYPE
         SYNTAX  DisplayString (SIZE (0..31))
         ACCESS    read-write
         STATUS    mandatory
         DESCRIPTION
         "Status access, for future use"
         ::= { cpqCmcControl 1 }

     cpqCmcSetLock1Lock  OBJECT-TYPE
         SYNTAX    INTEGER {
         other (1),
         lockDoor(2),
         openDoorTime(3),
         openDoor(4)
         }
         ACCESS  read-write
         STATUS  mandatory
         DESCRIPTION
         "Set door locking device 1, see table
          With this command the management-station can set the conditions for
          the door locking device
          (2) Door will be locked
          (3) Door will be unlocked for a defined time,
             time can be changed, see cpqCmcSetupLock1Time
          (4) Door is generally unlocked
          Locking and unlocking with this command can not be
          enabled or disabled with cpqCmcSetLock1Key-command"
         ::= { cpqCmcControl 2 }


     cpqCmcSetLock1Key  OBJECT-TYPE
         SYNTAX    INTEGER {
         other (1),
         disable(2),
         enableBoth(3),
         enableKeypad(4),
         enableRemoteInput(5)
         }
         ACCESS  read-write
         STATUS  mandatory
         DESCRIPTION
         "Enable or disable unlocking of the rack-door with external components
          like keypad or remote input.
          With this command the management station can set the conditions for
          unlocking the door:
          (2) unlocking is disabled, no unlocking with keypad or remote input
          (3) unlocking with keypad or remote signal (both) is enabled
          (4) unlocking with keypad (only) is enabled
          (5) unlocking with remote input (only) is enabled
          Unlocking door with the cpqCmcSetLock1Lock-command does not depend
          on this variable"
         ::= { cpqCmcControl 3 }


     cpqCmcSetLock2Lock  OBJECT-TYPE
         SYNTAX    INTEGER {
         other (1),
         lockDoor(2),
         openDoorTime(3),
         openDoor(4)
         }
         ACCESS  read-write
         STATUS  mandatory
         DESCRIPTION
         "Set door locking device 2, see table
          With this command the management-station can set the conditions for
          the door locking device
          (2) Door will be locked
          (3) Door will be unlocked for a defined time,
            time can be changed, see cpqCmcSetupLock2Time
          (4) Door is generally unlocked
          Locking and unlocking with this command can not be
          enabled or disabled with cpqCmcSetLock2Key-command"
         ::= { cpqCmcControl 4 }


     cpqCmcSetLock2Key  OBJECT-TYPE
         SYNTAX    INTEGER {
         other (1),
         disable(2),
         enableBoth(3),
         enableKeypad(4),
         enableRemoteInput(5)
         }
         ACCESS  read-write
         STATUS  mandatory
         DESCRIPTION
         "Enable or disable unlocking of the rack-door with external components
          like keypad or remote input.
          With this command the management-station can set the conditions for
          unlocking the door:
          (2) unlocking is disabled, no unlocking with keypad or remote input
          (3) unlocking with keypad or remote signal (both) is enabled
          (4) unlocking with keypad (only) is enabled
          (5) unlocking with remote input (only) is enabled
          Unlocking door with the cpqCmcSetDoor2-command does not depend
          on this variable"
         ::= { cpqCmcControl 5 }

     cpqCmcSetMessage  OBJECT-TYPE
         SYNTAX  DisplayString (SIZE (0..31))
         ACCESS    read-write
         STATUS    mandatory
         DESCRIPTION
         "Set message to CMC, for future use"
         ::= { cpqCmcControl 6 }

     cpqCmcSetAlarm1    OBJECT-TYPE
         SYNTAX  INTEGER {
         other (1),
         clearAlarm (2),
         setAlarm (3)
         }
         ACCESS  read-write
         STATUS  mandatory
         DESCRIPTION
         "Is used to set an alarm in the CMC from the management-station.
          With this command the management-station can i.e. switch on an
          alarm-relay or the AudibleAlarm of the CMC.
          Can be used for alert-handling"
         ::= { cpqCmcControl 7 }

     cpqCmcSetAlarm2    OBJECT-TYPE
         SYNTAX  INTEGER {
         other (1),
         clearAlarm (2),
         setAlarm (3)
         }
         ACCESS  read-write
         STATUS  mandatory
         DESCRIPTION
         "Is used to set an alarm in the CMC from the management-station.
          With this command the management-station can i.e. switch on an
          alarm-relay or the AudibleAlarm of the CMC.
          Can be used for alert-handling"
         ::= { cpqCmcControl 8 }

     cpqCmcSetFan1    OBJECT-TYPE
         SYNTAX  INTEGER {
         other (1),
         auto (2),
         on (3),
         off (4)
         }
         ACCESS  read-write
         STATUS  mandatory
         DESCRIPTION
         "Is used for run and stop control of fan1.
          (2) fan will run and stop according to temperature of sensor 1
              and threshold of fan1
          (3) fan will run independent of temperature and threshold
          (4) fan will stop independent of temperature and threshold
          (3) and (4) can be used for alert handling."
         ::= { cpqCmcControl 9 }

     cpqCmcSetFan2    OBJECT-TYPE
         SYNTAX  INTEGER {
         other (1),
         auto (2),
         on (3),
         off (4)
         }
         ACCESS  read-write
         STATUS  mandatory
         DESCRIPTION
         "Is used for run and stop control of fan2.
          (2) fan will run and stop according to temperature of sensor 2
              and threshold of fan2
          (3) fan will run independent of temperature and threshold
          (4) fan will stop independent of temperature and threshold
          (3) and (4) can be used for alert handling"
         ::= { cpqCmcControl 10 }

     cpqCmcSetQuitRelay1    OBJECT-TYPE
         SYNTAX  INTEGER {
         other (1),
         switched (2),
         notSwitched (3),
         quit (4)
         }
         ACCESS  read-write
         STATUS  mandatory
         DESCRIPTION
         "Status and quit of alarm relay 1.
          (2) relay is switched because of an alarm
          (3) relay is not switched, no alarm
          (4) (set) will quit relay 1 in case of alarm"
         ::= { cpqCmcControl 11 }

     cpqCmcSetQuitRelay2    OBJECT-TYPE
         SYNTAX  INTEGER {
         other (1),
         switched (2),
         notSwitched (3),
         quit (4)
         }
         ACCESS  read-write
         STATUS  mandatory
         DESCRIPTION
         "Status and quit of alarm relay 2.
          (2) relay is switched because of an alarm
          (3) relay is not switched, no alarm
          (4) (set) will quit relay 2 in case of alarm"
         ::= { cpqCmcControl 12 }



-- ***********************************************************************

-- cpqCmcLog-group

     cpqCmcLogsNumber  OBJECT-TYPE
         SYNTAX    INTEGER (0..100)
         ACCESS    read-only
         STATUS    mandatory
         DESCRIPTION
         "Number of Log-entries"
         ::= { cpqCmcLog 1 }

     cpqCmcLogTable  OBJECT-TYPE
         SYNTAX    SEQUENCE OF CpqCmcLogEntry
         ACCESS    not-accessible
         STATUS    mandatory
         DESCRIPTION
         "Log-table"
         ::= { cpqCmcLog 2 }

     cpqCmcLogEntry  OBJECT-TYPE
         SYNTAX    CpqCmcLogEntry
         ACCESS    not-accessible
         STATUS    mandatory
         DESCRIPTION
         "Log-table entries"
         INDEX     { cpqCmcLogIndex }
         ::= { cpqCmcLogTable 1 }

     CpqCmcLogEntry ::=
         SEQUENCE {
      cpqCmcLogIndex
         INTEGER,
      cpqCmcLogDate
         DisplayString,
      cpqCmcLogTime
         DisplayString,
      cpqCmcLogText
         DisplayString,
      cpqCmcLogClass
         DisplayString
         }

     cpqCmcLogIndex OBJECT-TYPE
        SYNTAX INTEGER (1..100)
        ACCESS read-only
        STATUS mandatory
        DESCRIPTION
        "Index for the Log-table. Its value ranges between
         1 and the value of cpqCmcLogsNumber "
        ::= { cpqCmcLogEntry 1 }


     cpqCmcLogDate OBJECT-TYPE
        SYNTAX DisplayString (SIZE (0..11))
        ACCESS read-only
        STATUS mandatory
        DESCRIPTION
        "Date of log information. "
        ::= { cpqCmcLogEntry 2 }

     cpqCmcLogTime OBJECT-TYPE
        SYNTAX DisplayString (SIZE (0..11))
        ACCESS read-only
        STATUS mandatory
        DESCRIPTION
        "Time of log information. "
        ::= { cpqCmcLogEntry 3 }

     cpqCmcLogText OBJECT-TYPE
        SYNTAX DisplayString (SIZE (0..31))
        ACCESS read-only
        STATUS mandatory
        DESCRIPTION
        "Log information. "
        ::= { cpqCmcLogEntry 4 }

     cpqCmcLogClass OBJECT-TYPE
        SYNTAX DisplayString (SIZE (0..31))
        ACCESS read-only
        STATUS mandatory
        DESCRIPTION
        "Status of log information. "
        ::= { cpqCmcLogEntry 5 }



--******************************************************************************
-- Traps
-- CMC-Traps
     cpqCmcalarmTemp1 TRAP-TYPE
         ENTERPRISE cpqCmc
         VARIABLES { sysDescr, sysContact, sysName,
           sysLocation, cpqCmcStatusTemp1 }
         DESCRIPTION
         "The temperature at rack sensor 1 is outside the specified threshold.  Action: Check the air handling system for the rack and refer to Trap Details for more information."
--
--#TYPE         "Temperature-alarm"
--#SUMMARY      "Location: %s, Message: Rack temp sensor 1 %s from: %s, contact %s"
--#ARGUMENTS    {3,4,2,1}
--#SEVERITY     MAJOR
--#TIMEINDEX    99
--
         ::= 153001

     cpqCmcalarmTemp2 TRAP-TYPE
         ENTERPRISE cpqCmc
         VARIABLES { sysDescr, sysContact, sysName,
           sysLocation, cpqCmcStatusTemp2 }
         DESCRIPTION
         "The temperature at rack sensor 2 is outside the specified threshold.  Action: Check the air handling system for the rack and refer to Trap Details for more information."
--
--#TYPE         "Temperature-alarm"
--#SUMMARY      "Location: %s, Message: Rack temp sensor 2 %s from: %s, contact %s"
--#ARGUMENTS    {3,4,2,1}
--#SEVERITY     MAJOR
--#TIMEINDEX    99
--
         ::= 153002

     cpqCmcalarmFan1 TRAP-TYPE
         ENTERPRISE cpqCmc
         VARIABLES { sysDescr, sysContact, sysName,
           sysLocation, cpqCmcStatusFan1 }
         DESCRIPTION
         "The status of Fan 1 has changed.  Action: Refer to Trap Details for more information."
--
--#TYPE         "Fan-alarm"
--#SUMMARY      "Location: %s, Rack fan 1 status: %s from: %s, contact %s"
--#ARGUMENTS    {3,4,2,1}
--#SEVERITY     MAJOR
--#TIMEINDEX    99
--
         ::= 153003

     cpqCmcalarmFan2 TRAP-TYPE
         ENTERPRISE cpqCmc
         VARIABLES { sysDescr, sysContact, sysName,
           sysLocation, cpqCmcStatusFan2 }
         DESCRIPTION
         "The status of Fan 2 has changed.  Action: Refer to Trap Details for more information."
--
--#TYPE         "Fan-alarm"
--#SUMMARY      "Location: %s, Rack fan 2 status: %s from: %s, contact %s"
--#ARGUMENTS    {3,4,2,1}
--#SEVERITY     MAJOR
--#TIMEINDEX    99
--
         ::= 153004

     cpqCmcalarmVoltage TRAP-TYPE
         ENTERPRISE cpqCmc
         VARIABLES { sysDescr, sysContact, sysName,
           sysLocation, cpqCmcStatusVoltage }
         DESCRIPTION
         "The AC voltage of the rack is outside the specified threshold.  Action: Check the incoming power source and ensure all cables are inserted correctly."
--
--#TYPE         "Voltage-alarm"
--#SUMMARY      "Location: %s, Message: Rack supply voltage %s from: %s, contact %s"
--#ARGUMENTS    {3,4,2,1}
--#SEVERITY     MAJOR
--#TIMEINDEX    99
--
         ::= 153005

     cpqCmcalarmHumidity TRAP-TYPE
         ENTERPRISE cpqCmc
         VARIABLES { sysDescr, sysContact, sysName,
           sysLocation, cpqCmcStatusHumidity }
         DESCRIPTION
         "The humidity of the rack is outside the specified threshold.  Action: Check the
     air handling system for the rack and refer to Trap Details for more information."
--
--#TYPE         "Humidity-alarm"
--#SUMMARY      "Location: %s, Message: %s from: %s, contact %s"
--#ARGUMENTS    {3,4,2,1}
--#SEVERITY     MAJOR
--#TIMEINDEX    99
--
         ::= 153006

     cpqCmcalarmInput1 TRAP-TYPE
         ENTERPRISE cpqCmc
         VARIABLES { sysDescr, sysContact, sysName,
           sysLocation, cpqCmcStatusInput1 }
         DESCRIPTION
         "The door or sidepanel of the rack has been opened (access point #1).  Action: Check for unauthorized intrusion and refer to Trap Details for more information."
--
--#TYPE         "Door/sidepanel-alarm"
--#SUMMARY      "Location: %s, Message: Rack access point 1 %s from: %s, contact %s"
--#ARGUMENTS    {3,4,2,1}
--#SEVERITY     MINOR
--#TIMEINDEX    99
--
         ::= 153007

     cpqCmcalarmInput2 TRAP-TYPE
         ENTERPRISE cpqCmc
         VARIABLES { sysDescr, sysContact, sysName,
           sysLocation, cpqCmcStatusInput2 }
         DESCRIPTION
         "The door or sidepanel of the rack has been opened (access point #2).  Action: Check for unauthorized intrusion and refer to Trap Details for more information."
--
--#TYPE         "Door/sidepanel-alarm"
--#SUMMARY      "Location: %s, Message: Rack access point 2 %s from: %s, contact %s"
--#ARGUMENTS    {3,4,2,1}
--#SEVERITY     MINOR
--#TIMEINDEX    99
--
         ::= 153008


     cpqCmcalarmInput3 TRAP-TYPE
         ENTERPRISE cpqCmc
         VARIABLES { sysDescr, sysContact, sysName,
           sysLocation, cpqCmcStatusInput3 }
         DESCRIPTION
         "The door or sidepanel of the rack has been opened (access point #3).  Action: Check for unauthorized intrusion and refer to Trap Details for more information."
--
--#TYPE         "Door/sidepanel-alarm"
--#SUMMARY      "Location: %s, Message: Rack access point 3 %s from: %s, contact %s"
--#ARGUMENTS    {3,4,2,1}
--#SEVERITY     MINOR
--#TIMEINDEX    99
--
         ::= 153009


     cpqCmcalarmInput4 TRAP-TYPE
         ENTERPRISE cpqCmc
         VARIABLES { sysDescr, sysContact, sysName,
           sysLocation, cpqCmcStatusInput4 }
         DESCRIPTION
         "The door or sidepanel of the rack has been opened (access point #4).  Action: Check for unauthorized intrusion and refer to Trap Details for more information."
--
--#TYPE         "Door/sidepanel-alarm"
--#SUMMARY      "Location: %s, Message: Rack access point 4 %s from: %s, contact %s"
--#ARGUMENTS    {3,4,2,1}
--#SEVERITY     MINOR
--#TIMEINDEX    99
--
         ::= 153010

     cpqCmcalarmLock1 TRAP-TYPE
         ENTERPRISE cpqCmc
         VARIABLES { sysDescr, sysContact, sysName,
           sysLocation, cpqCmcStatusLock1Lock }
         DESCRIPTION
         "Rack door lock #1 alarm.  Action: Ensure the door is completely closed and check for unauthorized intrusion and refer to Trap Details for more information."
--
--#TYPE         "Door-locking-alarm"
--#SUMMARY      "Location: %s, Message: Rack lock #1 %s from: %s, contact %s"
--#ARGUMENTS    {3,4,2,1}
--#SEVERITY     MAJOR
--#TIMEINDEX    99
--
         ::= 153011

     cpqCmcalarmLock2 TRAP-TYPE
         ENTERPRISE cpqCmc
         VARIABLES { sysDescr, sysContact, sysName,
           sysLocation, cpqCmcStatusLock2Lock }
         DESCRIPTION
         "Rack door lock #2 alarm.  Action: Ensure the door is completely closed and check for unauthorized intrusion and refer to Trap Details for more information."
--
--#TYPE         "Door-locking-alarm"
--#SUMMARY      "Location: %s, Message: Rack lock #1 %s from: %s, contact %s"
--#ARGUMENTS    {3,4,2,1}
--#SEVERITY     MAJOR
--#TIMEINDEX    99
--
         ::= 153012


     cpqCmcalarmSmoke TRAP-TYPE
         ENTERPRISE cpqCmc
         VARIABLES { sysDescr, sysContact, sysName,
           sysLocation, cpqCmcStatusSmoke }
         DESCRIPTION
         "The rack smoke detector has detected smoke.  Action: Investigate rack for an over temperature condition and refer to Trap Details for more information."
--
--#TYPE         "Smoke-alarm"
--#SUMMARY      "Location: %s, Message: Rack smoke detector - smoke: %s from: %s, contact %s"
--#ARGUMENTS    {3,4,2,1}
--#SEVERITY     MAJOR
--#TIMEINDEX    99
--
         ::= 153013

     cpqCmcalarmShock TRAP-TYPE
         ENTERPRISE cpqCmc
         VARIABLES { sysDescr, sysContact, sysName,
           sysLocation, cpqCmcStatusShock }
         DESCRIPTION
         "The rack shock detector has detected a vibration to the rack.  Action: Investigate rack."
--
--#TYPE         "Shock-alarm"
--#SUMMARY      "Location: %s, Message: Rack shock detector - shock: %s from: %s, contact %s"
--#ARGUMENTS    {3,4,2,1}
--#SEVERITY     MAJOR
--#TIMEINDEX    99
--
         ::= 153014


     cpqCmcalarmAux1 TRAP-TYPE
         ENTERPRISE cpqCmc
         VARIABLES { sysDescr, sysContact, sysName,
           sysLocation, cpqCmcStatusAux1 }
         DESCRIPTION
         "The rack auxiliary alarm input #1 has been triggered."
--
--#TYPE         "Aux-alarm"
--#SUMMARY      "Location: %s, Message: aux input #1 %s from: %s, contact %s"
--#ARGUMENTS    {3,4,2,1}
--#SEVERITY     MAJOR
--#TIMEINDEX    99
--
         ::= 153015

     cpqCmcalarmAux2 TRAP-TYPE
         ENTERPRISE cpqCmc
         VARIABLES { sysDescr, sysContact, sysName,
           sysLocation, cpqCmcStatusAux2 }
         DESCRIPTION
         "The rack auxiliary alarm input #2 has been triggered."
--
--#TYPE         "Aux-alarm"
--#SUMMARY      "Location: %s, Message: aux input #2 %s from: %s, contact %s"
--#ARGUMENTS    {3,4,2,1}
--#SEVERITY     MAJOR
--#TIMEINDEX    99
--
         ::= 153016

     cpqCmcalarm1 TRAP-TYPE
         ENTERPRISE cpqCmc
         VARIABLES { sysDescr, sysContact, sysName,
           sysLocation, cpqCmcStatusAlarm1 }
         DESCRIPTION
         "Alarm 1, set from Network management"
--
--#TYPE         "NMS-alarm"
--#SUMMARY      "Location: %s, Message: %s from: %s, contact %s"
--#ARGUMENTS    {3,4,2,1}
--#SEVERITY     MAJOR
--#TIMEINDEX    99
--
         ::= 153017

     cpqCmcalarm2 TRAP-TYPE
         ENTERPRISE cpqCmc
         VARIABLES { sysDescr, sysContact, sysName,
           sysLocation, cpqCmcStatusAlarm2 }
         DESCRIPTION
         "Alarm 2, set from Network management"
--
--#TYPE         "NMS-alarm"
--#SUMMARY      "Location: %s, Message: %s from: %s, contact %s"
--#ARGUMENTS    {3,4,2,1}
--#SEVERITY     MAJOR
--#TIMEINDEX    99
--
         ::= 153018



--MIB V1.1
     cpqCmcalarmLock1Dev TRAP-TYPE
         ENTERPRISE cpqCmc
         VARIABLES { sysDescr, sysContact, sysName,
           sysLocation, cpqCmcStatusLock1Dev }
         DESCRIPTION
         "The rack door locking device #1 has failed.  Action: Check the device lock cable or failed battery and refer to Trap Details for more information."
--
--#TYPE         "Door-locking-alarm of device"
--#SUMMARY      "Location: %s, Status: door lock device #1 %s from: %s, contact %s"
--#ARGUMENTS    {3,4,2,1}
--#SEVERITY     MAJOR
--#TIMEINDEX    99
--
         ::= 153019

     cpqCmcalarmLock2Dev TRAP-TYPE
         ENTERPRISE cpqCmc
         VARIABLES { sysDescr, sysContact, sysName,
           sysLocation, cpqCmcStatusLock2Dev }
         DESCRIPTION
         "The rack door locking device #2 has failed.  Action: Check the device lock cable or failed battery and refer to Trap Details for more information."
--
--#TYPE         "Door-locking-alarm of device"
--#SUMMARY      "Location: %s, Status: door lock device #2 %s from: %s, contact %s"
--#ARGUMENTS    {3,4,2,1}
--#SEVERITY     MAJOR
--#TIMEINDEX    99
--
         ::= 153020

     cpqCmcSetupChanged         TRAP-TYPE
         ENTERPRISE cpqCmc
         VARIABLES { sysDescr, sysContact, sysName,
           sysLocation }
         DESCRIPTION
         "Setup of CMC has changed."
--
--#TYPE         "Setup has changed"
--#SUMMARY      "Location: %s, Name: %s, contact %s"
--#ARGUMENTS    {3,2,1}
--#SEVERITY     INFORMATIONAL
--#TIMEINDEX    99
--
         ::= 153100


       END
