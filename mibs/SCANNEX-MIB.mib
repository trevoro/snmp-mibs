-- SCANNEX-MIB { iso org(3) dod(6) internet(1) private(4) 1 }
--
--Scannex Electronics Limited, info@scannex.co.uk
--  Trap definitions for the NetBuffer & ip.buffer
--  14-March-2003
--  03-May-2007 - Added ip.buffer
--	07-Dec-2007 - Corrected error in ipbufferserial
--	22-Jan-2008 - Additions for memory full traps (var bindings changed in firmware 1.62)
--	15-May-2008	- Additions for temperature (firmware 2.10+)
--	04-Mar-2009 - Added "Low Volts" SNMP trap for ip.buffer (firmware 2.31+)
--	23-Jan-2014 - Added percentage memory used in { ipbuffer 6 } (firmware 2.83+)


SCANNEX-MIB DEFINITIONS ::= BEGIN


IMPORTS 
  enterprises
    FROM RFC1155-SMI
  OBJECT-TYPE
    FROM RFC-1212
  TRAP-TYPE
    FROM RFC-1215;

-- Scannex private enterprises MIB extensions
scannex         OBJECT IDENTIFIER ::= { enterprises 6024 }

buffers   OBJECT IDENTIFIER ::= { scannex 1 }
netbuffer OBJECT IDENTIFIER ::= { buffers 2 }
ipbuffer  OBJECT IDENTIFIER ::= { buffers 3 } 

serialnumber  OBJECT-TYPE
  SYNTAX  OCTET STRING (SIZE(6))
  ACCESS  read-only
        STATUS  mandatory
        DESCRIPTION
    "The serial number / MAC address"
  
  ::= { netbuffer 1 }
  
netbuffername OBJECT-TYPE
  SYNTAX  OCTET STRING
  ACCESS  read-only
  STATUS  mandatory
  DESCRIPTION
    "The programmed name of the NetBuffer"
  ::= { netbuffer 2 } 
  
connectionstatus  OBJECT-TYPE
  SYNTAX  INTEGER (0..15)
  ACCESS  read-only
        STATUS  mandatory
        DESCRIPTION
    "A bit-field in the form:
     D0 = Source Port
     D1 = Destination Port
     D2 = Live Port
     D3 = FTP
     A set bit indicates connected."
  
  ::= { netbuffer 3 }
  
  
bootingTrap TRAP-TYPE
  ENTERPRISE netbuffer
  VARIABLES { serialnumber, connectionstatus, netbuffername }
  DESCRIPTION
    "The NetBuffer has booted and started running code."
  ::= 6
  
rebootTrap  TRAP-TYPE
  ENTERPRISE netbuffer
  VARIABLES { serialnumber, connectionstatus, netbuffername }
  DESCRIPTION
    "A reboot has been requested.
    Expect a bootingTrap to follow as the NetBuffer restarts."    
  ::= 7
  
powerfailTrap TRAP-TYPE
  ENTERPRISE netbuffer
  VARIABLES { serialnumber, connectionstatus, netbuffername }
  DESCRIPTION
    "The power has failed.
    These are the dying words of the NetBuffer!"
  ::= 8
  
ipchangeTrap  TRAP-TYPE
  ENTERPRISE netbuffer
  VARIABLES { serialnumber, connectionstatus, netbuffername }
  DESCRIPTION
    "The NetBuffer has received an IP.
     This can be from BOOTP, DHCP, or arp/ping."
  ::= 9
  
heartbeatTrap TRAP-TYPE
  ENTERPRISE netbuffer
  VARIABLES { serialnumber, connectionstatus, netbuffername }
  DESCRIPTION
    "The regular heartbeat of the NetBuffer.
    Use the connectionstatus variable to see what is connected."  
  ::= 15
  
weblockmismatchTrap TRAP-TYPE
  ENTERPRISE netbuffer
  VARIABLES { serialnumber, connectionstatus, netbuffername }
  DESCRIPTION
    "Someone has tried to unlock the engineer pages with the wrong code.
     The NetBuffer is protected with a secret."
  ::= 16
  
secretmismatchTrap  TRAP-TYPE
  ENTERPRISE netbuffer
  VARIABLES { serialnumber, connectionstatus, netbuffername }
  DESCRIPTION
    "A device has tried to connect to the NetBuffer using the wrong secret."
  ::= 17
  
authenticateconfigTrap  TRAP-TYPE
  ENTERPRISE netbuffer
  VARIABLES { serialnumber, connectionstatus, netbuffername }
  DESCRIPTION
    "The encryption and data mode are configured in an illegal state."
  ::= 18
  
ftppasswordTrap   TRAP-TYPE
  ENTERPRISE netbuffer
  VARIABLES { serialnumber, connectionstatus, netbuffername }
  DESCRIPTION
    "A incorrect username/password has been used to try and connect to the FTP server."
  ::= 29
  
emailsuccessTrap  TRAP-TYPE
  ENTERPRISE netbuffer
  VARIABLES { serialnumber, connectionstatus, netbuffername }
  DESCRIPTION
    "An email has been sent successfully."
  ::= 32
  
emailfailureTrap  TRAP-TYPE
  ENTERPRISE netbuffer
  VARIABLES { serialnumber, connectionstatus, netbuffername }
  DESCRIPTION
    "An email could not be sent.
     See the NetBuffer status page for the SMTP server response code."
  ::= 33
  
autobaudstartTrap TRAP-TYPE
  ENTERPRISE netbuffer
  VARIABLES { serialnumber, connectionstatus, netbuffername }
  DESCRIPTION
    "Autobauding has begun on the serial port."
  ::= 40
  
autobaudcompleteTrap  TRAP-TYPE
  ENTERPRISE netbuffer
  VARIABLES { serialnumber, connectionstatus, netbuffername }
  DESCRIPTION
    "Autobauding has completed on the serial port."
  ::= 41
  
fullupTrap  TRAP-TYPE
  ENTERPRISE netbuffer
  VARIABLES { serialnumber, connectionstatus, netbuffername }
  DESCRIPTION
    "The memory has exceeded the set percentage value."
  ::= 48
  
fullnotTrap TRAP-TYPE
  ENTERPRISE netbuffer
  VARIABLES { serialnumber, connectionstatus, netbuffername }
  DESCRIPTION
    "The memory has gone under the set percentage value."
  ::= 49
  
sourcequietTrap TRAP-TYPE
  ENTERPRISE netbuffer
  VARIABLES { serialnumber, connectionstatus, netbuffername }
  DESCRIPTION
    "The data source has been quiet for the set time."
  ::= 50

sourcenotquietTrap  TRAP-TYPE
  ENTERPRISE netbuffer
  VARIABLES { serialnumber, connectionstatus, netbuffername }
  DESCRIPTION
    "The data source has begun sending data again."
  ::= 51
  
tcpsourceTrap TRAP-TYPE
  ENTERPRISE netbuffer
  VARIABLES { serialnumber, connectionstatus, netbuffername }
  DESCRIPTION
    "The TCP1 channel tried to connect, but could not establish a socket."
  ::= 64
  
tcpdestinationTrap  TRAP-TYPE
  ENTERPRISE netbuffer
  VARIABLES { serialnumber, connectionstatus, netbuffername }
  DESCRIPTION
    "The TCP2 channel tried to connect, but could not establish a socket."
  ::= 65
  
tcpsmtpTrap TRAP-TYPE
  ENTERPRISE netbuffer
  VARIABLES { serialnumber, connectionstatus, netbuffername }
  DESCRIPTION
    "The email client tried to connect to the SMTP server, but could not establish a socket."
  ::= 78
  
connectsourceTrap TRAP-TYPE
  ENTERPRISE netbuffer
  VARIABLES { serialnumber, connectionstatus, netbuffername }
  DESCRIPTION
    "The data source has connected and is ready."
  ::= 80
  
connectdestinationTrap  TRAP-TYPE
  ENTERPRISE netbuffer
  VARIABLES { serialnumber, connectionstatus, netbuffername }
  DESCRIPTION
    "The destination has connected and is ready."
  ::= 81
  
connectftpTrap  TRAP-TYPE
  ENTERPRISE netbuffer
  VARIABLES { serialnumber, connectionstatus, netbuffername }
  DESCRIPTION
    "A client has connected to the FTP server."
  ::= 93
  
connectsmtpTrap TRAP-TYPE
  ENTERPRISE netbuffer
  VARIABLES { serialnumber, connectionstatus, netbuffername }
  DESCRIPTION
    "The email client has connected to the SMTP server."
  ::= 94

connectliveTrap TRAP-TYPE
  ENTERPRISE netbuffer
  VARIABLES { serialnumber, connectionstatus, netbuffername }
  DESCRIPTION
    "The engineer live access has connected."
  ::= 95
  
disconnectsourceTrap  TRAP-TYPE
  ENTERPRISE netbuffer
  VARIABLES { serialnumber, connectionstatus, netbuffername }
  DESCRIPTION
    "The data source has disconnected."
  ::= 96
  
disconnectdestinationTrap TRAP-TYPE
  ENTERPRISE netbuffer
  VARIABLES { serialnumber, connectionstatus, netbuffername }
  DESCRIPTION
    "The destination has disconnected."
  ::= 97
  
disconnectftpTrap TRAP-TYPE
  ENTERPRISE netbuffer
  VARIABLES { serialnumber, connectionstatus, netbuffername }
  DESCRIPTION
    "A client has disconnected from the FTP server."
  ::= 109
  
disconnectliveTrap  TRAP-TYPE
  ENTERPRISE netbuffer
  VARIABLES { serialnumber, connectionstatus, netbuffername }
  DESCRIPTION
    "The engineer live access has disconnected."
  ::= 111

-- ip.buffer definitions

ipbufferserial  OBJECT-TYPE
  SYNTAX  OCTET STRING (SIZE(6))
  ACCESS  read-only
        STATUS  mandatory
        DESCRIPTION
    "The serial number / MAC address"
  ::= { ipbuffer 1 }

ipbuffername  OBJECT-TYPE
  SYNTAX  OCTET STRING
  ACCESS  read-only
  STATUS  mandatory
  DESCRIPTION
    "The programmed name of the ip.buffer"
  ::= { ipbuffer 2 }  
  
ipbuffermessage OBJECT-TYPE
  SYNTAX  OCTET STRING
  ACCESS  read-only
  STATUS  mandatory
  DESCRIPTION
    "The message accompanying the trap"
  ::= { ipbuffer 3 }  

ipbufferchannel OBJECT-TYPE
  SYNTAX  OCTET STRING
  ACCESS  read-only
  STATUS  mandatory
  DESCRIPTION
    "Channel number"
  ::= { ipbuffer 4 }  

ipbuffertemperature OBJECT-TYPE
  SYNTAX  INTEGER
  ACCESS  read-only
  STATUS  optional
  DESCRIPTION
    "Temperature (degree C)"
  ::= { ipbuffer 5 }  

ipbuffermemory OBJECT-TYPE
  SYNTAX  INTEGER
  ACCESS  read-only
  STATUS  optional
  DESCRIPTION
    "Percentage Memory Used"
  ::= { ipbuffer 6 }  


-- ip.buffer Specific Trap Numbers
  
ipbbootingTrap  TRAP-TYPE
  ENTERPRISE ipbuffer
  VARIABLES { ipbufferserial, ipbuffername, ipbuffertemperature }
  DESCRIPTION
    "The ip.buffer has booted and started running code."
  ::= 1
  
ipbpowerfailTrap  TRAP-TYPE
  ENTERPRISE ipbuffer
  VARIABLES { ipbufferserial, ipbuffername, ipbuffertemperature }
  DESCRIPTION
    "The power has failed.
    These are the dying words of the ip.buffer!"
  ::= 2

ipbrebootTrap TRAP-TYPE
  ENTERPRISE ipbuffer
  VARIABLES { ipbufferserial, ipbuffername, ipbuffertemperature }
  DESCRIPTION
    "A reboot has been requested.
    Expect an ipbbootingTrap to follow as the ip.buffer restarts."    
  ::= 3
  
ipbrebootluaTrap  TRAP-TYPE
  ENTERPRISE ipbuffer
  VARIABLES { ipbufferserial, ipbuffername, ipbuffertemperature }
  DESCRIPTION
    "Lua has been rebooted"
  ::= 4

ipbbatteryTrap  TRAP-TYPE
  ENTERPRISE ipbuffer
  VARIABLES { ipbufferserial, ipbuffername, ipbuffertemperature }
  DESCRIPTION
    "The ip.buffer is running on battery power"
  ::= 5

ipbmainsTrap  TRAP-TYPE
  ENTERPRISE ipbuffer
  VARIABLES { ipbufferserial, ipbuffername, ipbuffertemperature }
  DESCRIPTION
    "The ip.buffer is running on mains power"
  ::= 6

ipbconfigTrap TRAP-TYPE
  ENTERPRISE ipbuffer
  VARIABLES { ipbufferserial, ipbuffername, ipbuffertemperature }
  DESCRIPTION
    "The ip.buffer has been reconfigured"
  ::= 7

ipbmainsTrap  TRAP-TYPE
  ENTERPRISE ipbuffer
  VARIABLES { ipbufferserial, ipbuffername, ipbuffertemperature }
  DESCRIPTION
    "The ip.buffer is running on low volts!"
  ::= 8


ipbauthenticationTrap TRAP-TYPE
  ENTERPRISE ipbuffer
  VARIABLES { ipbufferserial, ipbuffername, ipbuffermessage, ipbuffertemperature }
  DESCRIPTION
    "An authentication failure (see the ipbuffermessage field)"
  ::= 16

ipbconnectTrap  TRAP-TYPE
  ENTERPRISE ipbuffer
  VARIABLES { ipbufferserial, ipbuffername, ipbuffermessage, ipbufferchannel, ipbuffertemperature }
  DESCRIPTION
    "A channel has connected (see the ipbuffermessage field and ipbufferchannel fields)"
  ::= 32

ipbdisconnectTrap TRAP-TYPE
  ENTERPRISE ipbuffer
  VARIABLES { ipbufferserial, ipbuffername, ipbuffermessage, ipbufferchannel, ipbuffertemperature }
  DESCRIPTION
    "A channel has disconnected (see the ipbuffermessage and ipbufferchannel fields)"
  ::= 33
  
ipbchannelfullTrap TRAP-TYPE
  ENTERPRISE ipbuffer
  VARIABLES { ipbufferserial, ipbuffername, ipbuffermessage, ipbufferchannel, ipbuffertemperature }
  DESCRIPTION
    "A channel is full (see the ipbuffermessage and ipbufferchannel fields)"
  ::= 34

ipbchannelquietTrap TRAP-TYPE
  ENTERPRISE ipbuffer
  VARIABLES { ipbufferserial, ipbuffername, ipbuffermessage, ipbufferchannel, ipbuffertemperature }
  DESCRIPTION
    "A channel is quiet (see the ipbuffermessage and ipbufferchannel fields)"
  ::= 35


ipbcomfortTrap TRAP-TYPE
  ENTERPRISE ipbuffer
  VARIABLES { ipbufferserial, ipbuffername, ipbuffertemperature }
  DESCRIPTION
    "The ip.buffer is still alive"
  ::= 64

ipbmemoryfullTrap TRAP-TYPE
  ENTERPRISE ipbuffer
  VARIABLES { ipbufferserial, ipbuffername, ipbuffertemperature }
  DESCRIPTION
    "The ip.buffer memory has reached the limit"
  ::= 65

ipbtemperatureloTrap TRAP-TYPE
  ENTERPRISE ipbuffer
  VARIABLES { ipbufferserial, ipbuffername, ipbuffertemperature }
  DESCRIPTION
    "The ip.buffer temperature is too low"
  ::= 66

ipbtemperaturehiTrap TRAP-TYPE
  ENTERPRISE ipbuffer
  VARIABLES { ipbufferserial, ipbuffername, ipbuffertemperature }
  DESCRIPTION
    "The ip.buffer temperature is too high"
  ::= 67


END
