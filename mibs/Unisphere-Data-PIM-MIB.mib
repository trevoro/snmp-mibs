-- *****************************************************************
-- Unisphere-Data-PIM-MIB
--
-- Unisphere Networks Inc. Enterprise MIB
-- Protocol Independent Multicast (PIM) MIB
--
-- Copyright (c) 2000, 2001 Unisphere Networks, Incorporated.
-- All Rights Reserved.
-- *****************************************************************

Unisphere-Data-PIM-MIB DEFINITIONS ::= BEGIN

IMPORTS
    MODULE-IDENTITY, OBJECT-TYPE, Integer32, IpAddress, TimeTicks
        FROM SNMPv2-SMI
    RowStatus, TruthValue, TEXTUAL-CONVENTION
        FROM SNMPv2-TC
    MODULE-COMPLIANCE, OBJECT-GROUP
        FROM SNMPv2-CONF
    pimInterfaceIfIndex, pimRPSetComponent, pimRPSetGroupAddress,
    pimRPSetGroupMask, pimRPSetAddress
        FROM PIM-MIB
    InterfaceIndex
        FROM IF-MIB
    usDataMibs
        FROM Unisphere-Data-MIBs;


usdPimMIB MODULE-IDENTITY
    LAST-UPDATED "200103191537Z"  -- 19-Mar-01 10:37 AM EST
    ORGANIZATION "Unisphere Networks, Inc."
    CONTACT-INFO
        "       Unisphere Networks, Inc.
        Postal: 10 Technology Park Drive
                Westford, MA  01886
                USA
        Tel:    +1 978 589 5800
        Email:  mib@UnisphereNetworks.com"
    DESCRIPTION
        "The enterprise MIB module for management of PIM routers."
    -- Revision History
    REVISION    "200103191537Z"  -- 19-Mar-01 10:37 AM EST  - RX 3.0
    DESCRIPTION
        "Initial enterprise version."
    ::= { usDataMibs 43 }


-- +++++++++++++++++++++++++++++++++++++++++++++++++++++++++++++++++++++++++++++
-- Textual conventions
-- +++++++++++++++++++++++++++++++++++++++++++++++++++++++++++++++++++++++++++++

UsdPimType ::= TEXTUAL-CONVENTION
    STATUS      current
    DESCRIPTION
            "This data type is used do identify Sparse mode and Dense mode PIM
            protocol."
    SYNTAX INTEGER {
            invalid(0),        -- not valid value
            dense(1),          -- dense mode PIM
            sparse(2),         -- sparse mode PIM
            sparseAndDense(3)  -- both sparse and dense mode PIM
        }

usdPimMIBObjects OBJECT IDENTIFIER ::= { usdPimMIB 1 }

usdPimTraps      OBJECT IDENTIFIER ::= { usdPimMIBObjects 0 }

usdPimGlobal     OBJECT IDENTIFIER ::= { usdPimMIBObjects 1 }

-- --------------------------------------------------------------------------
-- 
-- Pim General Group
--
--
-- NOTE: RowStatus rowStatus. This needs to go into virtual-router 
--       mib table so that we can create/destroy PIM

-- PimPktStats: these actually augment the general group of standard mib

usdPimNumHelloRcvd OBJECT-TYPE
    SYNTAX     Integer32
    MAX-ACCESS read-only
    STATUS     current
    DESCRIPTION
            "Total number of Hellos received by PIM on this router."
    ::= { usdPimGlobal 1 }

usdPimNumJoinPruneRcvd OBJECT-TYPE
    SYNTAX     Integer32
    MAX-ACCESS read-only
    STATUS     current
    DESCRIPTION
            "Total number of JoinPrunes received by PIM on this router."
    ::= { usdPimGlobal 2 }

usdPimNumAssertRcvd OBJECT-TYPE
    SYNTAX     Integer32
    MAX-ACCESS read-only
    STATUS     current
    DESCRIPTION
            "Total number of Asserts received by PIM on this router."
    ::= { usdPimGlobal 3 }

usdPimNumGraftRcvd OBJECT-TYPE
    SYNTAX     Integer32
    MAX-ACCESS read-only
    STATUS     current
    DESCRIPTION
            "Total number of Grafts received by PIM on this router."
    ::= { usdPimGlobal 4 }

usdPimNumGraftAckRcvd OBJECT-TYPE
    SYNTAX     Integer32
    MAX-ACCESS read-only
    STATUS     current
    DESCRIPTION
            "Total number of Graft Acks received by PIM on this router."
    ::= { usdPimGlobal 5 }

usdPimNumHelloSent OBJECT-TYPE
    SYNTAX     Integer32
    MAX-ACCESS read-only
    STATUS     current
    DESCRIPTION
            "Total number of Hellos sent by PIM on this router."
    ::= { usdPimGlobal 6 }

usdPimNumJoinPruneSent OBJECT-TYPE
    SYNTAX     Integer32
    MAX-ACCESS read-only
    STATUS     current
    DESCRIPTION
            "Total number of JoinPrunes sent by PIM on this router."
    ::= { usdPimGlobal 7 }

usdPimNumAssertSent OBJECT-TYPE
    SYNTAX     Integer32
    MAX-ACCESS read-only
    STATUS     current
    DESCRIPTION
            "Total number of Asserts sent by PIM on this router."
    ::= { usdPimGlobal 8 }

usdPimNumGraftSent OBJECT-TYPE
    SYNTAX     Integer32
    MAX-ACCESS read-only
    STATUS     current
    DESCRIPTION
            "Total number of Grafts sent by PIM on this router."
    ::= { usdPimGlobal 9 }

usdPimNumGraftAckSent OBJECT-TYPE
    SYNTAX     Integer32
    MAX-ACCESS read-only
    STATUS     current
    DESCRIPTION
            "Total number of Graft Acks sent by PIM on this router."
    ::= { usdPimGlobal 10 }

-- --------------------------------------------------------------------------

-- 
-- Pim Interface Table
--

usdPimInterfaceTable OBJECT-TYPE
    SYNTAX     SEQUENCE OF UsdPimInterfaceEntry
    MAX-ACCESS not-accessible
    STATUS     current
    DESCRIPTION
            "The (conceptual) table listing enterprise specific information on
            a subset of the rows of the pimInterfaceTable defined in the 
            standard PIM MIB."
    ::= { usdPimGlobal 11 }

usdPimInterfaceEntry OBJECT-TYPE
    SYNTAX     UsdPimInterfaceEntry
    MAX-ACCESS not-accessible
    STATUS     current
    DESCRIPTION
            "An entry (conceptual row) in the usdPimInterfaceTable.  There
            is one entry per entry in the pimInterfaceTable."
    INDEX      { pimInterfaceIfIndex }
    ::= { usdPimInterfaceTable 1 }

UsdPimInterfaceEntry ::= SEQUENCE {
    usdPimIntfNumHelloRcvd         Integer32,
    usdPimIntfNumJoinPruneRcvd     Integer32,
    usdPimIntfNumAssertRcvd        Integer32,
    usdPimIntfNumGraftRcvd         Integer32,
    usdPimIntfNumGraftAckRcvd      Integer32,
    usdPimIntfNumHelloSent         Integer32,
    usdPimIntfNumJoinPruneSent     Integer32,
    usdPimIntfNumAssertSent        Integer32,
    usdPimIntfNumGraftSent         Integer32,
    usdPimIntfNumGraftAckSent      Integer32,
    usdPimIntfVersion              INTEGER,
    usdPimIntfNumNbrs              Integer32
}

usdPimIntfNumHelloRcvd OBJECT-TYPE
    SYNTAX     Integer32
    MAX-ACCESS read-write
    STATUS     current
    DESCRIPTION
            "Total number of Hellos received by PIM on this interface.
             It can only be cleared to 0 when doing set. Setting this also
             sets counters for other types of packets to 0."
    ::= { usdPimInterfaceEntry 1 }

usdPimIntfNumJoinPruneRcvd OBJECT-TYPE
    SYNTAX     Integer32
    MAX-ACCESS read-write
    STATUS     current
    DESCRIPTION
            "Total number of JoinPrunes received by PIM on this interface.
             It can only be cleared to 0 when doing set. Setting this also
             sets counters for other types of packets to 0."
    ::= { usdPimInterfaceEntry 2 }

usdPimIntfNumAssertRcvd OBJECT-TYPE
    SYNTAX     Integer32
    MAX-ACCESS read-write
    STATUS     current
    DESCRIPTION
            "Total number of Asserts received by PIM on this interface.
             It can only be cleared to 0 when doing set. Setting this also
             sets counters for other types of packets to 0."
    ::= { usdPimInterfaceEntry 3 }

usdPimIntfNumGraftRcvd OBJECT-TYPE
    SYNTAX     Integer32
    MAX-ACCESS read-write
    STATUS     current
    DESCRIPTION
            "Total number of Grafts received by PIM on this interface.
             It can only be cleared to 0 when doing set. Setting this also
             sets counters for other types of packets to 0."
    ::= { usdPimInterfaceEntry 4 }

usdPimIntfNumGraftAckRcvd OBJECT-TYPE
    SYNTAX     Integer32
    MAX-ACCESS read-write
    STATUS     current
    DESCRIPTION
            "Total number of Graft Acks received by PIM on this interface.
             It can only be cleared to 0 when doing set. Setting this also
             sets counters for other types of packets to 0."
    ::= { usdPimInterfaceEntry 5 }

usdPimIntfNumHelloSent OBJECT-TYPE
    SYNTAX     Integer32
    MAX-ACCESS read-write
    STATUS     current
    DESCRIPTION
            "Total number of Hellos sent by PIM on this interface.
             It can only be cleared to 0 when doing set. Setting this also
             sets counters for other types of packets to 0."
    ::= { usdPimInterfaceEntry 6 }

usdPimIntfNumJoinPruneSent OBJECT-TYPE
    SYNTAX     Integer32
    MAX-ACCESS read-write
    STATUS     current
    DESCRIPTION
            "Total number of JoinPrunes sent by PIM on this interface.
             It can only be cleared to 0 when doing set. Setting this also
             sets counters for other types of packets to 0."
    ::= { usdPimInterfaceEntry 7 }

usdPimIntfNumAssertSent OBJECT-TYPE
    SYNTAX     Integer32
    MAX-ACCESS read-write
    STATUS     current
    DESCRIPTION
            "Total number of Asserts sent by PIM on this interface.
             It can only be cleared to 0 when doing set. Setting this also
             sets counters for other types of packets to 0."
    ::= { usdPimInterfaceEntry 8 }

usdPimIntfNumGraftSent OBJECT-TYPE
    SYNTAX     Integer32
    MAX-ACCESS read-write
    STATUS     current
    DESCRIPTION
            "Total number of Grafts sent by PIM on this interface.
             It can only be cleared to 0 when doing set. Setting this also
             sets counters for other types of packets to 0."
    ::= { usdPimInterfaceEntry 9 }

usdPimIntfNumGraftAckSent OBJECT-TYPE
    SYNTAX     Integer32
    MAX-ACCESS read-write
    STATUS     current
    DESCRIPTION
            "Total number of Graft Acks sent by PIM on this interface.
             It can only be cleared to 0 when doing set. Setting this also
             sets counters for other types of packets to 0."
    ::= { usdPimInterfaceEntry 10 }

usdPimIntfVersion OBJECT-TYPE
    SYNTAX     INTEGER (1..2147483647)
    MAX-ACCESS read-only
    STATUS     current
    DESCRIPTION
            "The version of PIM running on this interface."
    ::= { usdPimInterfaceEntry 11 }

usdPimIntfNumNbrs OBJECT-TYPE
    SYNTAX     Integer32
    MAX-ACCESS read-only
    STATUS     current
    DESCRIPTION
            "Number of PIM neighbors detected on this interface."
    ::= { usdPimInterfaceEntry 12 }
-- --------------------------------------------------------------------------

--
-- The PIM Multicast Route Table
--

usdPimMRouteTable OBJECT-TYPE
    SYNTAX     SEQUENCE OF UsdPimMRouteEntry
    MAX-ACCESS not-accessible
    STATUS     current
    DESCRIPTION
            "The (conceptual) table listing PIM multicast routing information
             describing its <*, *, RP>/ <*, G>/ <S, G> states."
    ::= { usdPimGlobal 12 }

usdPimMRouteEntry OBJECT-TYPE
    SYNTAX     UsdPimMRouteEntry
    MAX-ACCESS not-accessible
    STATUS     current
    DESCRIPTION
            "An entry (conceptual row) in the usdPimMRouteTable."
    INDEX      { usdPimMRouteGroup, usdPimMRouteSource, usdPimMRouteSourceMask, 
                  usdPimMRouteRPAddress }
    ::= { usdPimMRouteTable 1 }

UsdPimMRouteEntry ::= SEQUENCE {
    usdPimMRouteGroup                         IpAddress,
    usdPimMRouteSource                        IpAddress,
    usdPimMRouteSourceMask                    IpAddress,
    usdPimMRouteRPAddress                     IpAddress,
    usdPimMRouteUpstreamAssertTimer           TimeTicks,
    usdPimMRouteAssertMetric                  Integer32,
    usdPimMRouteAssertPref                    Integer32,
    usdPimMRouteAssertRPTBit                  TruthValue,
    usdPimMRouteBits                          BITS,
    usdPimMRouteRPAddrInUse                   IpAddress,
    usdPimMRouteUpstreamNbr                   IpAddress,
    usdPimMRouteIifAddr                       IpAddress,
    usdPimMRouteIsWaitingToSwitchToSPT        TruthValue,
    usdPimMRouteEntryExpiryTimer              TimeTicks,
    usdPimMRouteSenderDRAddr                  IpAddress,
    usdPimMRouteRouteAddr                     IpAddress,
    usdPimMRouteRouteMask                     IpAddress,
    usdPimMRouteGRPAddr                       IpAddress,
    usdPimMRouteGRPMask                       IpAddress,
    usdPimMRouteOtherProtoOifJoinTypeAll      TruthValue,
    usdPimMRouteOtherProtoOifJoinTypeG        TruthValue,
    usdPimMRouteOtherProtoOifJoinTypeSG       TruthValue,
    usdPimMRoutePimType                       UsdPimType 
}

usdPimMRouteGroup OBJECT-TYPE 
    SYNTAX IpAddress
    MAX-ACCESS not-accessible
    STATUS     current
    DESCRIPTION
            "The group address. Specified as 224.0.0.0 for <*, *, RP> entries."
    ::= { usdPimMRouteEntry 1 }

usdPimMRouteSource OBJECT-TYPE  
    SYNTAX IpAddress
    MAX-ACCESS not-accessible
    STATUS     current
    DESCRIPTION
            "The source address. Specified as 0.0.0.0 for <*, *, RP> and 
             <*, G> entries."
    ::= { usdPimMRouteEntry 2 }

usdPimMRouteSourceMask OBJECT-TYPE  
    SYNTAX IpAddress
    MAX-ACCESS not-accessible
    STATUS     current
    DESCRIPTION
            "The source address mask. Specified as 255.255.255.255 for <S, G>
             entries and 0.0.0.0 for <*, *, RP> and <*, G> entries."
    ::= { usdPimMRouteEntry 3 }

usdPimMRouteRPAddress OBJECT-TYPE  
    SYNTAX IpAddress
    MAX-ACCESS not-accessible
    STATUS     current
    DESCRIPTION
            "The RP address used for <*, *, RP>. Specified as 0.0.0.0 for 
             <S, G> and <*, G> entries."
    ::= { usdPimMRouteEntry 4 }

usdPimMRouteUpstreamAssertTimer OBJECT-TYPE  
    SYNTAX TimeTicks
    MAX-ACCESS read-only
    STATUS     current
    DESCRIPTION
            "The time remaining before the router changes its upstream
            neighbor back to its RPF neighbor.  This timer is called the
            Assert timer in the PIM Sparse and Dense mode specification.
            A value of 0 indicates that no Assert has changed the
            upstream neighbor away from the RPF neighbor."
    ::= { usdPimMRouteEntry 5 }

usdPimMRouteAssertMetric OBJECT-TYPE  
    SYNTAX Integer32
    MAX-ACCESS read-only
    STATUS     current
    DESCRIPTION
            "The metric advertised by the assert winner on the upstream
            interface, or 0 if no such assert is in received."
    ::= { usdPimMRouteEntry 6 }

usdPimMRouteAssertPref OBJECT-TYPE  
    SYNTAX Integer32
    MAX-ACCESS read-only
    STATUS     current
    DESCRIPTION
            "The preference advertised by the assert winner on the
            upstream interface, or 0 if no such assert is in effect."
    ::= { usdPimMRouteEntry 7 }

usdPimMRouteAssertRPTBit OBJECT-TYPE  
    SYNTAX TruthValue
    MAX-ACCESS read-only
    STATUS     current
    DESCRIPTION
            "The value of the RPT-bit advertised by the assert winner on
            the upstream interface, or false if no such assert is in
            effect."
    ::= { usdPimMRouteEntry 8 }

usdPimMRouteBits OBJECT-TYPE  
    SYNTAX BITS {
              rpt(0),
              spt(1)
           }
    MAX-ACCESS read-only
    STATUS     current
    DESCRIPTION
            "This object describes whether the entry is on shared tree
            (rpt) or shortest path tree (spt)."
    ::= { usdPimMRouteEntry 9 }

usdPimMRouteRPAddrInUse OBJECT-TYPE  
    SYNTAX IpAddress
    MAX-ACCESS read-only
    STATUS     current
    DESCRIPTION
            "The RP Address being used for the <S, G>RPT/<*, G>/<*, *, RP> 
             entries. Set to 0.0.0.0 for <S, G> entries on shortest path tree."
    ::= { usdPimMRouteEntry 10 }

usdPimMRouteUpstreamNbr OBJECT-TYPE 
    SYNTAX IpAddress
    MAX-ACCESS read-only
    STATUS     current
    DESCRIPTION
            "The address of upstream neighbor being used for the entry. Its
            set to 0.0.0.0 if the router is directly attached to source on 
            one of its interface. "
    ::= { usdPimMRouteEntry 11 }

usdPimMRouteIifAddr OBJECT-TYPE 
    SYNTAX IpAddress
    MAX-ACCESS read-only
    STATUS     current
    DESCRIPTION
            "The address of incoming interface for this entry."
    ::= { usdPimMRouteEntry 12 }

usdPimMRouteIsWaitingToSwitchToSPT OBJECT-TYPE 
    SYNTAX TruthValue
    MAX-ACCESS read-only
    STATUS     current
    DESCRIPTION
            "This object describes whether the entry is still waiting
            to switch completely to shortest path tree in case of <S, G> 
            entries. It waits to do this till it receives first packet from 
            incoming interface towards shortest path tree."
    ::= { usdPimMRouteEntry 13 }

usdPimMRouteEntryExpiryTimer OBJECT-TYPE 
    SYNTAX TimeTicks
    MAX-ACCESS read-only
    STATUS     current
    DESCRIPTION
            "The time after which the entry timer expires for this entry.
            Set to 0 if entry timer is not active."
    ::= { usdPimMRouteEntry 14 }

usdPimMRouteSenderDRAddr OBJECT-TYPE 
    SYNTAX IpAddress
    MAX-ACCESS read-only
    STATUS     current
    DESCRIPTION
            "The address of the designated router on the sender's subnet in 
            case of <S, G> entries. The sender designated router register 
            encapsulates data to RP. Set to 0.0.0.0 for <*, G> and <*, *, RP>
            entries."
    ::= { usdPimMRouteEntry 15 }

usdPimMRouteRouteAddr OBJECT-TYPE 
    SYNTAX IpAddress
    MAX-ACCESS read-only
    STATUS     current
    DESCRIPTION
            "The address of the route being used to do RPF check for this 
            entry. It is set to 0.0.0.0 (with usdPimMRouteRouteMask set to 
            255.255.255.255) if there is no route available."
    ::= { usdPimMRouteEntry 16 }

usdPimMRouteRouteMask OBJECT-TYPE 
    SYNTAX IpAddress
    MAX-ACCESS read-only
    STATUS     current
    DESCRIPTION
            "The mask of the route being used to do RPF check for this 
            entry. It is set to 255.255.255.255 (with usdPimMRouteRoute set to 
            0.0.0.0) if there is no route available."
    ::= { usdPimMRouteEntry 17 }

usdPimMRouteGRPAddr OBJECT-TYPE 
    SYNTAX IpAddress
    MAX-ACCESS read-only
    STATUS     current
    DESCRIPTION
            "The address of the group-to-RP mapping being used to get the RP 
            for this entry. It is set to 0.0.0.0 (with usdPimMRouteGRPMask 
            set to 0.0.0.0) if there is no group-to-RP mapping available or 
            if entry is <*, *, RP>."
    ::= { usdPimMRouteEntry 18 }

usdPimMRouteGRPMask OBJECT-TYPE 
    SYNTAX IpAddress
    MAX-ACCESS read-only
    STATUS     current
    DESCRIPTION
            "The mask of the group-to-RP mapping being used to get the RP 
            for this entry. It is set to 255.255.255.255 (with 
            usdPimMRouteGRPAddr set to 0.0.0.0) if there is no group-to-RP
            mapping available or if entry is <*, *, RP>."
    ::= { usdPimMRouteEntry 19 }

usdPimMRouteOtherProtoOifJoinTypeAll OBJECT-TYPE 
    SYNTAX TruthValue
    MAX-ACCESS read-only
    STATUS     current
    DESCRIPTION
            "This object indicates if some other multicast protocol is also 
            interested in receiving data for this entry as a result of its 
            interest in receiving all data. This will be particularly true 
            for dense mode protocols which would want all data (<*, *>) from 
            PIM sparse mode protocol." 
    ::= { usdPimMRouteEntry 20 }

usdPimMRouteOtherProtoOifJoinTypeG OBJECT-TYPE 
    SYNTAX TruthValue
    MAX-ACCESS read-only
    STATUS     current
    DESCRIPTION
            "This object indicates if some other multicast protocol is also 
            interested in receiving data for this entry as a result of its 
            interest in receiving data for a given group. This will be 
            particularly true for IGMP which would want data for a given
            group (<*, G>) from PIM protocol." 
    ::= { usdPimMRouteEntry 21 }

usdPimMRouteOtherProtoOifJoinTypeSG OBJECT-TYPE 
    SYNTAX TruthValue
    MAX-ACCESS read-only
    STATUS     current
    DESCRIPTION
            "This object indicates if some other multicast protocol is also 
            interested in receiving data for this entry as a result of its 
            interest in receiving data for a given <source, group>. This will 
            be particularly true for IGMPv3 which would want data for a given
            <source, group (<S, G>) from PIM sparse-mode protocol." 
    ::= { usdPimMRouteEntry 22 }

usdPimMRoutePimType OBJECT-TYPE 
    SYNTAX UsdPimType 
    MAX-ACCESS read-only
    STATUS     current
    DESCRIPTION
            "This object indicates if the owner of this entry is Sparse mode
            or Dense mode PIM. Owner is usually determined by the protocol 
            running on the incoming interface of the entry. In case 
            sparse-dense mode PIM is running on the incoming interface, 
            sparse-mode is the owner if RP for the group is known, else dense 
            mode is the owner."
    ::= { usdPimMRouteEntry 23 }
-- --------------------------------------------------------------------------

--
-- The PIM Next Hop Table
--

usdPimMRouteNextHopTable OBJECT-TYPE
    SYNTAX     SEQUENCE OF UsdPimMRouteNextHopEntry
    MAX-ACCESS not-accessible
    STATUS     current
    DESCRIPTION
            "The (conceptual) table listing PIM multicast routing information
             describing its <*, *, RP>/ <*, G>/ <S, G> outgoing interfaces."
    ::= { usdPimGlobal 13 }

usdPimMRouteNextHopEntry OBJECT-TYPE
    SYNTAX UsdPimMRouteNextHopEntry
    MAX-ACCESS not-accessible
    STATUS     current
    DESCRIPTION
            "An entry (conceptual row) in the usdPimMRouteNextHopTable."
    INDEX     { usdPimMRouteNextHopGroupAddr, usdPimMRouteNextHopSrcAddr, 
                usdPimMRouteNextHopSrcMask, usdPimMRouteNextHopRPAddr, 
                usdPimMRouteNextHopIfId, usdPimMRouteNextHopAddress }
    ::= { usdPimMRouteNextHopTable 1 }

UsdPimMRouteNextHopEntry ::= SEQUENCE {
    usdPimMRouteNextHopGroupAddr IpAddress,
    usdPimMRouteNextHopSrcAddr IpAddress,
    usdPimMRouteNextHopSrcMask IpAddress,
    usdPimMRouteNextHopRPAddr IpAddress,
    usdPimMRouteNextHopIfId InterfaceIndex,
    usdPimMRouteNextHopAddress IpAddress,
    usdPimMRouteNextHopPruneReason INTEGER,
    usdPimMRouteNextHopJoinTypeSSRP TruthValue,
    usdPimMRouteNextHopJoinTypeG TruthValue,
    usdPimMRouteNextHopJoinTypeSG TruthValue,
    usdPimMRouteNextHopHasLGM TruthValue,
    usdPimMRouteNextHopHasOifAW TruthValue,
    usdPimMRouteNextHopHasOifSendAssert TruthValue,
    usdPimMRouteNextHopHasOifRegister TruthValue,
    usdPimMRouteNextHopHasOifBorderBit TruthValue,
    usdPimMRouteNextHopHasOifNullEncapsBit TruthValue,
    usdPimMRouteNextHopJoinEndTimer TimeTicks,
    usdPimMRouteNextHopAssertEndTimer TimeTicks,
    usdPimMRouteNextHopNextAssertTimer TimeTicks,
    usdPimMRouteNextHopAssertSrcAddress IpAddress,
    usdPimMRouteNextHopRegisterSuppressionTimer TimeTicks,
    usdPimMRouteNextHopPimType UsdPimType,
    usdPimMRouteNextHopPruneTimeLeft TimeTicks,
    usdPimMRouteNextHopsendingIpAddress IpAddress
}

usdPimMRouteNextHopGroupAddr OBJECT-TYPE
    SYNTAX IpAddress
    MAX-ACCESS not-accessible
    STATUS     current
    DESCRIPTION
            "The group address. Specified as 224.0.0.0 for <*, *, RP> entries."
    ::= { usdPimMRouteNextHopEntry 2 }

usdPimMRouteNextHopSrcAddr OBJECT-TYPE
    SYNTAX IpAddress
    MAX-ACCESS not-accessible
    STATUS     current
    DESCRIPTION
            "The source address. Specified as 0.0.0.0 for <*, *, RP> and 
             <*, G> entries."
    ::= { usdPimMRouteNextHopEntry 3 }

usdPimMRouteNextHopSrcMask OBJECT-TYPE
    SYNTAX IpAddress
    MAX-ACCESS not-accessible
    STATUS     current
    DESCRIPTION
            "The source address mask. Specified as 255.255.255.255 for <S, G>
             entries and 0.0.0.0 for <*, *, RP> and <*, G> entries."
    ::= { usdPimMRouteNextHopEntry 4 }

usdPimMRouteNextHopRPAddr OBJECT-TYPE
    SYNTAX IpAddress
    MAX-ACCESS not-accessible
    STATUS     current
    DESCRIPTION
            "The RP address used for <*, *, RP>. Specified as 0.0.0.0 for 
             <S, G> and <*, G> entries."
    ::= { usdPimMRouteNextHopEntry 5 }

usdPimMRouteNextHopIfId OBJECT-TYPE
    SYNTAX InterfaceIndex
    MAX-ACCESS not-accessible
    STATUS     current
    DESCRIPTION
            " The interface index of the outgoing interface (next hop). 
              Specified as 0 for register outgoing interface. Register 
              outgoing interfaces are created by DR on the source subnet
              to send PIM register encapsulated data (as unicast) to RP.
              It is also used by PIM boundary routers (PMBRs) to register
              data to RP."
    ::= { usdPimMRouteNextHopEntry 6 }

usdPimMRouteNextHopAddress OBJECT-TYPE
    SYNTAX IpAddress
    MAX-ACCESS not-accessible
    STATUS     current
    DESCRIPTION
            " This object takes following different values based on the type of
              next hop. It should be set to the address of RP in case the next 
              hop interface is register interface i.e. usdPimMRouteNextHopIfId 
              object is set to 0. It should be set to the address of neighbor 
              in case the interface is an NBMA interface. In all other cases 
              it should be set to the group address itself."
    ::= { usdPimMRouteNextHopEntry 7 }

usdPimMRouteNextHopPruneReason OBJECT-TYPE
    SYNTAX INTEGER {
            other(1),
            prune(2),
            assert(3)
        }
    MAX-ACCESS read-only
    STATUS     current
    DESCRIPTION
            "This object indicates why the downstream interface was
            pruned, whether in response to a PIM prune message or due to
            PIM Assert processing."
    ::= { usdPimMRouteNextHopEntry 8 }

usdPimMRouteNextHopJoinTypeSSRP OBJECT-TYPE
    SYNTAX TruthValue
    MAX-ACCESS read-only
    STATUS     current
    DESCRIPTION
            "This object indicates whether or not the interface was added as
            a result of receiving <*, *, RP> join in case of  <*, *, RP> entry 
            OR inherited as outgoing interface from corresponding <*, *, RP> 
            entry in case of <*, G> entry."
    ::= { usdPimMRouteNextHopEntry 9 }

usdPimMRouteNextHopJoinTypeG OBJECT-TYPE
    SYNTAX TruthValue
    MAX-ACCESS read-only
    STATUS     current
    DESCRIPTION
            "This object indicates whether or not the interface was added as
            a result of receiving <*, G> join in case of  <*, G> entry 
            OR inherited as outgoing interface from corresponding <*, G> 
            entry in case of <S, G> entry."
    ::= { usdPimMRouteNextHopEntry 10 }

usdPimMRouteNextHopJoinTypeSG OBJECT-TYPE
    SYNTAX TruthValue
    MAX-ACCESS read-only
    STATUS     current
    DESCRIPTION
            "This object indicates whether or not the interface was added as
            a result of receiving <S, G> join in case of  <S, G> entry."
    ::= { usdPimMRouteNextHopEntry 11 }

usdPimMRouteNextHopHasLGM OBJECT-TYPE
    SYNTAX TruthValue
    MAX-ACCESS read-only
    STATUS     current
    DESCRIPTION
            "This object indicates whether or not the interface has local
            group membership (as indicated by IGMP) in case of <*, G> and
            <S, G> entries."
    ::= { usdPimMRouteNextHopEntry 12 }

usdPimMRouteNextHopHasOifAW OBJECT-TYPE
    SYNTAX TruthValue
    MAX-ACCESS read-only
    STATUS     current
    DESCRIPTION
            "This object indicates whether or not this interface is the winner
            of assert for corresponding <*, G>/<S, G> entry."
    ::= { usdPimMRouteNextHopEntry 13 }

usdPimMRouteNextHopHasOifSendAssert OBJECT-TYPE
    SYNTAX TruthValue
    MAX-ACCESS read-only
    STATUS     current
    DESCRIPTION
            "This object indicates whether or not this interface is going to 
            send an assert at the end of assert suppression interval. Assert 
            suppression is used to prevent a flood of assert to be generated
            in response to data or other asserts."
    ::= { usdPimMRouteNextHopEntry 14 }

usdPimMRouteNextHopHasOifRegister OBJECT-TYPE
    SYNTAX TruthValue
    MAX-ACCESS read-only
    STATUS     current
    DESCRIPTION
            "This object indicates whether or not this next hop is a 
            register outgoing interface."
    ::= { usdPimMRouteNextHopEntry 15 }

usdPimMRouteNextHopHasOifBorderBit OBJECT-TYPE
    SYNTAX TruthValue
    MAX-ACCESS read-only
    STATUS     current
    DESCRIPTION
            "This object is used to describe a register outgoing interface.
            It indicates whether or not the border bit is set in the register 
            packet when the packet is sent over the register interface.
            For all other (non-register) interfaces its set to false."
    ::= { usdPimMRouteNextHopEntry 16 }

usdPimMRouteNextHopHasOifNullEncapsBit OBJECT-TYPE
    SYNTAX TruthValue
    MAX-ACCESS read-only
    STATUS     current
    DESCRIPTION
            "This object is used to describe a register outgoing interface.
            It indicates whether or not the NULL encapsulation bit is set 
            (periodically) in the register packet when the packet is sent 
            over the register interface. For all other (non-register) 
            interfaces its set to false."
    ::= { usdPimMRouteNextHopEntry 17 }

usdPimMRouteNextHopJoinEndTimer OBJECT-TYPE
    SYNTAX TimeTicks
    MAX-ACCESS read-only
    STATUS     current
    DESCRIPTION
            "This object indicates the time (in seconds) left when the join
            timer expires for the outgoing interface. Join timer for an 
            outgoing interface of <S, G> entry indicates when the <S, G> join
            expires, for a <*, G> entry indicates when the <*, G> join expires
            and for a <*, *, RP> entry indicates when the <*, *, RP> join 
            expires. Inherited joins (like <S, G> inheriting from <*, G> AND
            <*, G> inheriting from <*, *, RP>) expire when the corresponding 
            parent join expires."
    ::= { usdPimMRouteNextHopEntry 18 }

usdPimMRouteNextHopAssertEndTimer OBJECT-TYPE
    SYNTAX TimeTicks
    MAX-ACCESS read-only
    STATUS     current
    DESCRIPTION
            "This object indicates the time (in seconds) left when the assert
            timer expires on this outgoing inteface."
    ::= { usdPimMRouteNextHopEntry 19 }

usdPimMRouteNextHopNextAssertTimer OBJECT-TYPE
    SYNTAX TimeTicks
    MAX-ACCESS read-only
    STATUS     current
    DESCRIPTION
            "This object indicates the duration (in seconds) left for which 
            sending an assert has been suppressed on this outgoing interface."
    ::= { usdPimMRouteNextHopEntry 20 }

usdPimMRouteNextHopAssertSrcAddress OBJECT-TYPE
    SYNTAX IpAddress
    MAX-ACCESS read-only
    STATUS     current
    DESCRIPTION
            "This object indicates the source address which will be used in 
            the assert packet to send an assert out for the entry on this 
            outgoing interface. For <S, G> entries it is the address of the 
            source S itself. For <*, G> entries it is the address of the 
            source whose data was forwarded using this <*, G> and caused the
            assert situation to happen."
    ::= { usdPimMRouteNextHopEntry 21 }

usdPimMRouteNextHopRegisterSuppressionTimer OBJECT-TYPE
    SYNTAX TimeTicks
    MAX-ACCESS read-only
    STATUS     current
    DESCRIPTION
            "This object is used for register outgoing interfaces. It indicates
            the duration (in seconds) left for which sending a register packet 
            has been suppressed on the register outgoing interface as a result 
            of receiving register-stop from the RP."
    ::= { usdPimMRouteNextHopEntry 22 }

usdPimMRouteNextHopPimType OBJECT-TYPE
    SYNTAX UsdPimType
    MAX-ACCESS read-only
    STATUS     current
    DESCRIPTION
            "This object indicates whether the outgoing interface was 
            contributed by sparse-mode or dense-mode PIM."
    ::= { usdPimMRouteNextHopEntry 23 }

usdPimMRouteNextHopPruneTimeLeft OBJECT-TYPE
    SYNTAX TimeTicks
    MAX-ACCESS read-only
    STATUS     current
    DESCRIPTION
            "This object indicates the time (in seconds) left when the prune
            timer expires on an outgoing inteface. Its used for pruned outgoing
            interfaces contributed by dense-mode PIM."
    ::= { usdPimMRouteNextHopEntry 24 }

usdPimMRouteNextHopsendingIpAddress OBJECT-TYPE
    SYNTAX IpAddress
    MAX-ACCESS read-only
    STATUS     current
    DESCRIPTION
            "This object describes the source IP address used by this interface
             to send PIM packets out on this outgoing interface."
    ::= { usdPimMRouteNextHopEntry 25 }
-- --------------------------------------------------------------------------

--
-- The PIM RP-Set Table
--

usdPimRPSetTable OBJECT-TYPE
    SYNTAX     SEQUENCE OF UsdPimRPSetEntry
    MAX-ACCESS not-accessible
    STATUS     current
    DESCRIPTION
            "The (conceptual) table listing enterprise specific information on
            a subset of the rows of the pimRPSetTable defined in the standard 
            PIM MIB."
    ::= { usdPimGlobal 14 }

usdPimRPSetEntry OBJECT-TYPE
    SYNTAX UsdPimRPSetEntry
    MAX-ACCESS not-accessible
    STATUS     current
    DESCRIPTION
            "An entry (conceptual row) in the usdPimRPSetTable."
    INDEX      { pimRPSetComponent, pimRPSetGroupAddress,
                 pimRPSetGroupMask, pimRPSetAddress }
    ::= { usdPimRPSetTable 1 }

UsdPimRPSetEntry ::= SEQUENCE {
    usdPimRPSetPriority Integer32,
    usdPimRPSetTypeInfo INTEGER,
    usdPimRPSetAccessListName OCTET STRING
}

usdPimRPSetPriority OBJECT-TYPE
    SYNTAX Integer32 (1..'FFFF'h)
    MAX-ACCESS read-only
    STATUS     current
    DESCRIPTION
        "This object describes the priority of the RP for this group-to-RP 
        mapping."
    ::= { usdPimRPSetEntry 1 }

usdPimRPSetTypeInfo OBJECT-TYPE
    SYNTAX INTEGER {
                pimRPTypeInvalid(0),
                pimRPTypeStatic(1),
                pimRPTypeStaticOverride(2),
                pimRPTypeAutoRP(3),
                pimRPTypeBSR(4),
                pimRPTypeStaticNegative(5),
                pimRPTypeStaticOverrideNegative(6),
                pimRPTypeAutoRPNegative(7),
                pimRPTypeBSRNegative(8)
    }
    MAX-ACCESS read-only
    STATUS     current
    DESCRIPTION
        "This object describes the mechanism by which this group to RP mapping
        has been learnt, i.e. whether its statically configured, AutoRP learnt
        or BSR learnt. It also indicates whether the mapping is positive or
        negative. Negative mappings force the groups in that range to fall into
        dense-mode category if sparse-dense mode is configured or no RP if its 
        purely sparse mode configuration."
    ::= { usdPimRPSetEntry 2 }

usdPimRPSetAccessListName OBJECT-TYPE
    SYNTAX OCTET STRING (SIZE (0..32))
    MAX-ACCESS read-only
    STATUS     current
    DESCRIPTION
        "This object lists the name of the access list from which this 
         group-to-RP mapping was picked up in case of statically configured 
         RPs."
    ::= { usdPimRPSetEntry 3 }

-- --------------------------------------------------------------------------

--
-- The PIM Static RP configuration table 
--

usdPimStaticRPConfTable OBJECT-TYPE
    SYNTAX     SEQUENCE OF UsdPimStaticRPConfEntry
    MAX-ACCESS not-accessible
    STATUS     current
    DESCRIPTION
            "The (conceptual) table listing statically configured PIM RPs."
    ::= { usdPimGlobal 15 }

usdPimStaticRPConfEntry OBJECT-TYPE
    SYNTAX UsdPimStaticRPConfEntry
    MAX-ACCESS not-accessible
    STATUS     current
    DESCRIPTION
            "An entry (conceptual row) in the usdPimStaticRPConfTable."
    INDEX     { usdPimStaticRPConfComponentIndex, usdPimStaticRPConfRPAddr, 
                usdPimStaticRPConfAccessListName }
    ::= { usdPimStaticRPConfTable 1 }

UsdPimStaticRPConfEntry ::= SEQUENCE {
    usdPimStaticRPConfComponentIndex Integer32,
    usdPimStaticRPConfRPAddr IpAddress,
    usdPimStaticRPConfAccessListName OCTET STRING,
    usdPimStaticRPConfRowStatus RowStatus,
    usdPimStaticRPConfOverride TruthValue
}

usdPimStaticRPConfComponentIndex OBJECT-TYPE
    SYNTAX Integer32 (0..2147483647)
    MAX-ACCESS not-accessible
    STATUS     current
    DESCRIPTION
            "A number uniquely identifying the component.  Each protocol 
            instance connected to a separate domain should have a different 
            index value."
    ::= { usdPimStaticRPConfEntry 1 }

usdPimStaticRPConfRPAddr OBJECT-TYPE
    SYNTAX IpAddress
    MAX-ACCESS not-accessible
    STATUS     current
    DESCRIPTION
            "Ip address of the RP which for the group-to-RP mapping being 
            configured."
    ::= { usdPimStaticRPConfEntry 2 }

usdPimStaticRPConfAccessListName OBJECT-TYPE
    SYNTAX OCTET STRING (SIZE (0..32))
    MAX-ACCESS not-accessible
    STATUS     current
    DESCRIPTION
            "Name of the access list from which group-ranges are picked up
            for this group-ro-RP mapping. Every deny component in the list 
            is added as negative group-ro-RP mapping."
    ::= { usdPimStaticRPConfEntry 3 }

usdPimStaticRPConfRowStatus OBJECT-TYPE
    SYNTAX RowStatus
    MAX-ACCESS read-create
    STATUS     current
    DESCRIPTION
            "The status of this row, by which new entries may be
            created, or old entries deleted from this table."
    ::= { usdPimStaticRPConfEntry 4 }

usdPimStaticRPConfOverride OBJECT-TYPE
    SYNTAX TruthValue
    MAX-ACCESS read-create
    STATUS     current
    DESCRIPTION
            "The object indicates whether or not this statically configured
            group-to-RP mapping should override the group-to-RP mapping learnt
            via AutoRP for the component group-ranges in the access list. By 
            default AutoRP learnt group-to-RP mappings are preferred over 
            statically configured ones. While setting the rowStatus to create
            a static RP, this field should be assigned to true if the override
            property is desired."
    DEFVAL     { false }
    ::= { usdPimStaticRPConfEntry 5 }
-- --------------------------------------------------------------------------

--
-- The PIM AutoRP Candidate RP configuration table 
--

usdPimAutoRPConfTable OBJECT-TYPE
    SYNTAX     SEQUENCE OF UsdPimAutoRPConfEntry
    MAX-ACCESS not-accessible
    STATUS     current
    DESCRIPTION
            "The (conceptual) table allowing AutoRP configuration of 
            candidate RPs (advertisement agents)."
    ::= { usdPimGlobal 16 }

usdPimAutoRPConfEntry OBJECT-TYPE
    SYNTAX UsdPimAutoRPConfEntry
    MAX-ACCESS not-accessible
    STATUS     current
    DESCRIPTION
            "An entry (conceptual row) in the usdPimAutoRPConfTable."
    INDEX     { usdPimAutoRPConfComponentIndex, usdPimAutoRPConfCandRPAddr,
                usdPimAutoRPConfGroupAccessListName }
    ::= { usdPimAutoRPConfTable 1 }

UsdPimAutoRPConfEntry ::= SEQUENCE {
    usdPimAutoRPConfComponentIndex Integer32,
    usdPimAutoRPConfCandRPAddr IpAddress,
    usdPimAutoRPConfGroupAccessListName OCTET STRING,
    usdPimAutoRPConfRowStatus RowStatus,
    usdPimAutoRPConfTTL Integer32,
    usdPimAutoRPConfAncmntIntvl TimeTicks,
    usdPimAutoRPConfifId InterfaceIndex
}

usdPimAutoRPConfComponentIndex OBJECT-TYPE
    SYNTAX Integer32 (0..2147483647)
    MAX-ACCESS not-accessible
    STATUS     current
    DESCRIPTION
            "A number uniquely identifying the component.  Each protocol 
            instance connected to a separate domain should have a different 
            index value."
    ::= { usdPimAutoRPConfEntry 1 }

usdPimAutoRPConfCandRPAddr OBJECT-TYPE
    SYNTAX IpAddress
    MAX-ACCESS not-accessible
    STATUS     current
    DESCRIPTION
            "The IP address of the candidate RP for this advertising agent
            configuration."
    ::= { usdPimAutoRPConfEntry 2 }

usdPimAutoRPConfGroupAccessListName OBJECT-TYPE
    SYNTAX OCTET STRING (SIZE (0..32))
    MAX-ACCESS not-accessible
    STATUS     current
    DESCRIPTION
            "The access list name from which group ranges are picked up for
            advertising agent configuration."
    ::= { usdPimAutoRPConfEntry 3 }

usdPimAutoRPConfRowStatus OBJECT-TYPE
    SYNTAX RowStatus
    MAX-ACCESS read-create
    STATUS     current
    DESCRIPTION
            "The status of this row, by which new entries may be
            created, or old entries deleted from this table."
    ::= { usdPimAutoRPConfEntry 4 }

usdPimAutoRPConfTTL OBJECT-TYPE
    SYNTAX Integer32(1..'FFFF'h)
    MAX-ACCESS read-create
    STATUS     current
    DESCRIPTION
            "The time-to-live value used while sending AutoRP advertisement 
            out for this group-to-RP mappings created as a result of this
            configuration. This should be set along with 
            usdPimAutoRPConfRowStatus while creating an AutoRP advertising
            agent to denote the TTL value to be used."
    DEFVAL     { 64 }
    ::= { usdPimAutoRPConfEntry 5 }

usdPimAutoRPConfAncmntIntvl OBJECT-TYPE
    SYNTAX TimeTicks
    MAX-ACCESS read-create
    STATUS     current
    DESCRIPTION
            "The time interval at which AutoRP advertisements are sent out 
            for the group-to-RP mappings created as a result of this
            configuration. This should be set along with 
            usdPimAutoRPConfRowStatus while creating an AutoRP advertising
            agent to denote the announcement interval to be used."
    DEFVAL     { 60 }
    ::= { usdPimAutoRPConfEntry 6 }

usdPimAutoRPConfifId OBJECT-TYPE
    SYNTAX InterfaceIndex
    MAX-ACCESS read-only
    STATUS     current
    DESCRIPTION
            "The interface index of the interface for the candidate RP
            if an interface with that address exists else it is set to 0."
    ::= { usdPimAutoRPConfEntry 7 }
-- --------------------------------------------------------------------------

--
-- The PIM AutoRP candidate RP table 
--

usdPimAutoRPCandTable OBJECT-TYPE
    SYNTAX     SEQUENCE OF UsdPimAutoRPCandEntry
    MAX-ACCESS not-accessible
    STATUS     current
    DESCRIPTION
            "The (conceptual) table listing AutoRP candidate RPS (advertising 
            agents)."
    ::= { usdPimGlobal 17 }

usdPimAutoRPCandEntry OBJECT-TYPE
    SYNTAX UsdPimAutoRPCandEntry
    MAX-ACCESS not-accessible
    STATUS     current
    DESCRIPTION
            "An entry (conceptual row) in the usdPimAutoRPCandTable."
    INDEX     { usdPimAutoRPCandComponentIndex, usdPimAutoRPCandRPAddr, 
                usdPimAutoRPCandGroupAddr, usdPimAutoRPCandGroupMask }
    ::= { usdPimAutoRPCandTable 1 }

UsdPimAutoRPCandEntry ::= SEQUENCE {
    usdPimAutoRPCandComponentIndex Integer32,
    usdPimAutoRPCandRPAddr IpAddress,
    usdPimAutoRPCandGroupAddr IpAddress,
    usdPimAutoRPCandGroupMask IpAddress,
    usdPimAutoRPCandRowStatus RowStatus,
    usdPimAutoRPCandAccessListName OCTET STRING,
    usdPimAutoRPCandAutoRPTTL Integer32,
    usdPimAutoRPCandAutoRPAncmntIntvl TimeTicks,
    usdPimAutoRPCandIfId InterfaceIndex 
}

usdPimAutoRPCandComponentIndex OBJECT-TYPE
    SYNTAX Integer32 (0..2147483647)
    MAX-ACCESS not-accessible
    STATUS     current
    DESCRIPTION
            "A number uniquely identifying the component.  Each protocol 
            instance connected to a separate domain should have a different 
            index value."
    ::= { usdPimAutoRPCandEntry 1 }

usdPimAutoRPCandRPAddr OBJECT-TYPE
    SYNTAX IpAddress
    MAX-ACCESS not-accessible
    STATUS     current
    DESCRIPTION
            "The IP address of the candidate RP for this group-to-RP mapping."
    ::= { usdPimAutoRPCandEntry 2 }

usdPimAutoRPCandGroupAddr OBJECT-TYPE
    SYNTAX IpAddress
    MAX-ACCESS not-accessible
    STATUS     current
    DESCRIPTION
            "The group address of the candidate RP for this group-to-RP 
            mapping."
    ::= { usdPimAutoRPCandEntry 3 }

usdPimAutoRPCandGroupMask OBJECT-TYPE
    SYNTAX IpAddress
    MAX-ACCESS not-accessible
    STATUS     current
    DESCRIPTION
            "The group mask of the candidate RP for this group-to-RP 
            mapping."
    ::= { usdPimAutoRPCandEntry 4 }

usdPimAutoRPCandRowStatus OBJECT-TYPE
    SYNTAX RowStatus
    MAX-ACCESS read-only
    STATUS     current
    DESCRIPTION
            "The current status of this row."
    ::= { usdPimAutoRPCandEntry 5 }

usdPimAutoRPCandAccessListName OBJECT-TYPE
    SYNTAX OCTET STRING (SIZE (0..32))
    MAX-ACCESS read-only
    STATUS     current
    DESCRIPTION
            "The name of the group list using which this AutoRP 
            group-to-RP candidate RP mapping was configured."
    ::= { usdPimAutoRPCandEntry 6 }

usdPimAutoRPCandAutoRPTTL OBJECT-TYPE
    SYNTAX Integer32(1..'FFFF'h)
    MAX-ACCESS read-only
    STATUS     current
    DESCRIPTION
            "The time-to-live value used while sending AutoRP advertisement 
            out for this group-to-RP mapping."
    ::= { usdPimAutoRPCandEntry 7 }

usdPimAutoRPCandAutoRPAncmntIntvl OBJECT-TYPE
    SYNTAX TimeTicks
    MAX-ACCESS read-only
    STATUS     current
    DESCRIPTION
            "The time interval at which AutoRP advertisements are sent out 
            for this group-to-RP mapping."
    ::= { usdPimAutoRPCandEntry 8 }

usdPimAutoRPCandIfId OBJECT-TYPE
    SYNTAX InterfaceIndex 
    MAX-ACCESS read-only
    STATUS     current
    DESCRIPTION
            "The interface index of the interface for this AutoRP group-to-RP 
            candidate RP mapping if an interface for RP address exists else
            it is set to 0."
    ::= { usdPimAutoRPCandEntry 9 }

-- --------------------------------------------------------------------------

--
-- The PIM Component Table
--

usdPimComponentTable OBJECT-TYPE
    SYNTAX     SEQUENCE OF UsdPimComponentEntry
    MAX-ACCESS not-accessible
    STATUS     current
    DESCRIPTION
            "The (conceptual) table listing each component (domain) in PIM."
    ::= { usdPimGlobal 18 }

usdPimComponentEntry OBJECT-TYPE
    SYNTAX UsdPimComponentEntry
    MAX-ACCESS not-accessible
    STATUS     current
    DESCRIPTION
            "An entry (conceptual row) in the usdPimComponentTable."
    INDEX     { usdPimComponentIndex }
    ::= { usdPimComponentTable 1 }

UsdPimComponentEntry ::= SEQUENCE {
    usdPimComponentIndex Integer32,
    usdPimComponentAutoRPMappingAgentRowStatus RowStatus,
    usdPimComponentConfiguredAutoRPMappingAgentIfId InterfaceIndex,
    usdPimComponentAutoRPMappingAgentInterval TimeTicks,
    usdPimComponentAutoRPMappingTTL Integer32,
    usdPimComponentAutoRPMappingAgentIntfAddr IpAddress,
    usdPimComponentAutoRPMappingAgentWinnerAddr IpAddress,
    usdPimComponentAutoRPMappingAgentWinnerLastHeard TimeTicks
}

usdPimComponentIndex OBJECT-TYPE
    SYNTAX Integer32 (0..2147483647)
    MAX-ACCESS not-accessible
    STATUS     current
    DESCRIPTION
            "A number uniquely identifying the component.  Each protocol 
            instance connected to a separate domain should have a different 
            index value."
    ::= { usdPimComponentEntry 1 }

usdPimComponentAutoRPMappingAgentRowStatus OBJECT-TYPE
    SYNTAX RowStatus
    MAX-ACCESS read-create
    STATUS     current
    DESCRIPTION
            "The status of AutoRP mapping agent by which this router can be
            made an AutoRP mapping agent or removed from being an AutoRP 
            mapping agent in this component." 
    ::= { usdPimComponentEntry 2 }

usdPimComponentConfiguredAutoRPMappingAgentIfId OBJECT-TYPE
    SYNTAX InterfaceIndex
    MAX-ACCESS read-create
    STATUS     current
    DESCRIPTION
            "The interface index of the interface which mapping agent should
            use to send AutoRP mapping messages. If not specified, the 
            interface with highest IP address in this domain is picked up
            for this purpose."
    ::= { usdPimComponentEntry 3 }

usdPimComponentAutoRPMappingAgentInterval OBJECT-TYPE
    SYNTAX TimeTicks
    MAX-ACCESS read-create
    STATUS     current
    DESCRIPTION
            "The time interval at which AutoRP mapping messages are sent out 
            in this component. The default value is 60 seconds."
    DEFVAL     { 60 }
    ::= { usdPimComponentEntry 4 }

usdPimComponentAutoRPMappingTTL OBJECT-TYPE
    SYNTAX Integer32(1..'FFFF'h)
    MAX-ACCESS read-create
    STATUS     current
    DESCRIPTION
            "The time-to-live value used while sending AutoRP mapping messages
            out in this component."
    DEFVAL     { 64 }
    ::= { usdPimComponentEntry 5 }

usdPimComponentAutoRPMappingAgentIntfAddr OBJECT-TYPE
    SYNTAX IpAddress 
    MAX-ACCESS read-only
    STATUS     current
    DESCRIPTION
            "The IP address of the interface which mapping agent is 
            using to send AutoRP mapping messages."
    ::= { usdPimComponentEntry 6 }

usdPimComponentAutoRPMappingAgentWinnerAddr OBJECT-TYPE
    SYNTAX IpAddress
    MAX-ACCESS read-only
    STATUS     current
    DESCRIPTION
            "The IP address of the winner AutoRP mapping agent. There can be
            multiple mapping agents configured in a given PIM domain(component).
            The mapping agent with highest IP address is chosen as the winner
            and it continues to send AutoRP mapping messages. If the router
            itself is the winner, then this is set to 0.0.0.0."
    ::= { usdPimComponentEntry 7 }

usdPimComponentAutoRPMappingAgentWinnerLastHeard OBJECT-TYPE
    SYNTAX TimeTicks
    MAX-ACCESS read-only
    STATUS     current
    DESCRIPTION
            "The time (in seconds) that has past since an AutoRP mapping message
            was receieved from the winner AutoRP mapping agent. If the router
            itself is the winner, then this is set to 0."
    ::= { usdPimComponentEntry 8 }
-- --------------------------------------------------------------------------

--
-- The PIM Unicast Route Table
--

usdPimUnicastRouteTable OBJECT-TYPE
    SYNTAX     SEQUENCE OF UsdPimUnicastRouteEntry
    MAX-ACCESS not-accessible
    STATUS     current
    DESCRIPTION
            "The (conceptual) table listing all the unicast routes
            currently in use by PIM for diong RPF checking."
    ::= { usdPimGlobal 19 }

usdPimUnicastRouteEntry OBJECT-TYPE
    SYNTAX UsdPimUnicastRouteEntry
    MAX-ACCESS not-accessible
    STATUS     current
    DESCRIPTION
            "An entry (conceptual row) in the usdPimUnicastRouteTable."
    INDEX     { usdPimUnicastRouteEntryAddr, usdPimUnicastRouteEntryMask }
    ::= { usdPimUnicastRouteTable 1 }

UsdPimUnicastRouteEntry ::= SEQUENCE {
    usdPimUnicastRouteEntryAddr IpAddress,
    usdPimUnicastRouteEntryMask IpAddress,
    usdPimUnicastRouteEntryRpfNbr IpAddress,
    usdPimUnicastRouteEntryIifId InterfaceIndex,
    usdPimUnicastRouteEntryIifAddr IpAddress,
    usdPimUnicastRouteEntryPref Integer32,
    usdPimUnicastRouteEntryMetric Integer32,
    usdPimUnicastRouteEntryPimType UsdPimType
}

usdPimUnicastRouteEntryAddr OBJECT-TYPE
    SYNTAX IpAddress
    MAX-ACCESS not-accessible
    STATUS     current
    DESCRIPTION
            "The address of route in use."
    ::= { usdPimUnicastRouteEntry 1 }

usdPimUnicastRouteEntryMask OBJECT-TYPE
    SYNTAX IpAddress
    MAX-ACCESS not-accessible
    STATUS     current
    DESCRIPTION
            "The mask of route in use."
    ::= { usdPimUnicastRouteEntry 2 }

usdPimUnicastRouteEntryRpfNbr OBJECT-TYPE
    SYNTAX IpAddress
    MAX-ACCESS read-only
    STATUS     current
    DESCRIPTION
            "The RPF neighbor (next-hop) to reach the route of this entry.
            It is set to 0.0.0.0 for directly connected routes."
    ::= { usdPimUnicastRouteEntry 3 }

usdPimUnicastRouteEntryIifId OBJECT-TYPE
    SYNTAX InterfaceIndex
    MAX-ACCESS read-only
    STATUS     current
    DESCRIPTION
            "The interface index (next-hop) to reach the route of this entry."
    ::= { usdPimUnicastRouteEntry 4 }

usdPimUnicastRouteEntryIifAddr OBJECT-TYPE
    SYNTAX IpAddress
    MAX-ACCESS read-only
    STATUS     current
    DESCRIPTION
            "The interface address (next-hop) to reach the route of this entry."
    ::= { usdPimUnicastRouteEntry 5 }

usdPimUnicastRouteEntryPref OBJECT-TYPE
    SYNTAX Integer32
    MAX-ACCESS read-only
    STATUS     current
    DESCRIPTION
            "The preference of the route of this entry."
    ::= { usdPimUnicastRouteEntry 6 }

usdPimUnicastRouteEntryMetric OBJECT-TYPE
    SYNTAX Integer32
    MAX-ACCESS read-only
    STATUS     current
    DESCRIPTION
            "The metric of the route of this entry."
    ::= { usdPimUnicastRouteEntry 7 }

usdPimUnicastRouteEntryPimType OBJECT-TYPE
    SYNTAX UsdPimType
    MAX-ACCESS read-only
    STATUS     current
    DESCRIPTION
            "This object indicates whether the route specified in this entry
            is being used by sparse-mode and/or dense-mode PIM."
    ::= { usdPimUnicastRouteEntry 8 }
-- --------------------------------------------------------------------------

--
-- The PIM Shortest Path Tree Threshold Table
--

usdPimSPTThresholdTable OBJECT-TYPE
    SYNTAX     SEQUENCE OF UsdPimSPTThresholdEntry
    MAX-ACCESS not-accessible
    STATUS     current
    DESCRIPTION
            "The (conceptual) table listing threshold values set for
            switching from shared tree to shortest path tree and vice versa
            for data forwarded by PIM sparse-mode."
    ::= { usdPimGlobal 20 }

usdPimSPTThresholdEntry OBJECT-TYPE
    SYNTAX UsdPimSPTThresholdEntry
    MAX-ACCESS not-accessible
    STATUS     current
    DESCRIPTION
            "An entry (conceptual row) in the usdPimSPTThresholdTable."
    INDEX     { usdPimSPTThresholdAccessListName }
    ::= { usdPimSPTThresholdTable 1 }

UsdPimSPTThresholdEntry ::= SEQUENCE {
    usdPimSPTThresholdAccessListName OCTET STRING,
    usdPimSPTThresHoldRowStatus RowStatus,
    usdPimSPTThresholdKbps Integer32
}

usdPimSPTThresholdAccessListName OBJECT-TYPE
    SYNTAX OCTET STRING (SIZE (0..32))
    MAX-ACCESS not-accessible
    STATUS     current
    DESCRIPTION
            "The name of the access list from which group ranges are picked 
            up for setting SPT threshold in this entry."
    ::= { usdPimSPTThresholdEntry 1 }

usdPimSPTThresHoldRowStatus OBJECT-TYPE
    SYNTAX RowStatus
    MAX-ACCESS read-write
    STATUS     current
    DESCRIPTION
            "The status of this row, by which new entries may be
            created, or old entries deleted from this table."
    ::= { usdPimSPTThresholdEntry 2 }

usdPimSPTThresholdKbps OBJECT-TYPE
    SYNTAX Integer32
    MAX-ACCESS read-write
    STATUS     current
    DESCRIPTION
            "The value of SPT threshold in kilobits per second. Default value
             is 0."
    DEFVAL     { 0 }
    ::= { usdPimSPTThresholdEntry 3 }


-- +++++++++++++++++++++++++++++++++++++++++++++++++++++++++++++++++++++++++++++
-- Conformance information
-- +++++++++++++++++++++++++++++++++++++++++++++++++++++++++++++++++++++++++++++

usdPimConformance     OBJECT IDENTIFIER ::= { usdPimMIB 2 }
usdPimCompliances     OBJECT IDENTIFIER ::= { usdPimConformance 1 }
usdPimGroups          OBJECT IDENTIFIER ::= { usdPimConformance 2 }

-- compliance statements

usdPimCompliance MODULE-COMPLIANCE
    STATUS      current
    DESCRIPTION
        "The compliance statement for entities which implement the Unisphere PIM
        MIB."
    MODULE  -- this module
        MANDATORY-GROUPS {
            usdPimGeneralGroup,
            usdPimInterfaceGroup,
            usdPimMRouteConfGroup,
            usdPimMRouteNextHopGroup,
            usdPimRPSetGroup,
            usdPimStaticRPConfGroup,
            usdPimAutoRPConfGroup,
            usdPimAutoRPCandGroup,
            usdPimComponentGroup,
            usdPimUnicastRouteGroup,
            usdPimSPTThresholdGroup }
    ::= { usdPimCompliances 1 }

-- units of conformance

usdPimGeneralGroup OBJECT-GROUP
    OBJECTS {
        usdPimNumHelloRcvd,
        usdPimNumJoinPruneRcvd,
        usdPimNumAssertRcvd,
        usdPimNumGraftRcvd,
        usdPimNumGraftAckRcvd,
        usdPimNumHelloSent,
        usdPimNumJoinPruneSent,
        usdPimNumAssertSent,
        usdPimNumGraftSent,
        usdPimNumGraftAckSent }
    STATUS      current
    DESCRIPTION
        "A collection of objects for managing general PIM capabilities in a
        Unisphere product."
    ::= { usdPimGroups 1 }                                             -- RX 3.0

usdPimInterfaceGroup OBJECT-GROUP
    OBJECTS {
        usdPimIntfNumHelloRcvd,
        usdPimIntfNumJoinPruneRcvd,
        usdPimIntfNumAssertRcvd,
        usdPimIntfNumGraftRcvd,
        usdPimIntfNumGraftAckRcvd,
        usdPimIntfNumHelloSent,
        usdPimIntfNumJoinPruneSent,
        usdPimIntfNumAssertSent,
        usdPimIntfNumGraftSent,
        usdPimIntfNumGraftAckSent,
        usdPimIntfVersion,
        usdPimIntfNumNbrs }
    STATUS      current
    DESCRIPTION
        "A collection of objects for managing PIM interface capabilities in a
        Unisphere product."
    ::= { usdPimGroups 2 }

usdPimMRouteConfGroup OBJECT-GROUP
    OBJECTS {
        usdPimMRouteUpstreamAssertTimer,
        usdPimMRouteAssertMetric,
        usdPimMRouteAssertPref,
        usdPimMRouteAssertRPTBit,
        usdPimMRouteBits,
        usdPimMRouteRPAddrInUse,
        usdPimMRouteUpstreamNbr,
        usdPimMRouteIifAddr,
        usdPimMRouteIsWaitingToSwitchToSPT,
        usdPimMRouteEntryExpiryTimer,
        usdPimMRouteSenderDRAddr,
        usdPimMRouteRouteAddr,
        usdPimMRouteRouteMask,
        usdPimMRouteGRPAddr,
        usdPimMRouteGRPMask,
        usdPimMRouteOtherProtoOifJoinTypeAll,
        usdPimMRouteOtherProtoOifJoinTypeG,
        usdPimMRouteOtherProtoOifJoinTypeSG,
        usdPimMRoutePimType }
    STATUS      current
    DESCRIPTION
        "A collection of objects for managing PIM multicast route capabilities
        in a Unisphere product."
    ::= { usdPimGroups 3 }

usdPimMRouteNextHopGroup OBJECT-GROUP
    OBJECTS {
        usdPimMRouteNextHopPruneReason,
        usdPimMRouteNextHopJoinTypeSSRP,
        usdPimMRouteNextHopJoinTypeG,
        usdPimMRouteNextHopJoinTypeSG,
        usdPimMRouteNextHopHasLGM,
        usdPimMRouteNextHopHasOifAW,
        usdPimMRouteNextHopHasOifSendAssert,
        usdPimMRouteNextHopHasOifRegister,
        usdPimMRouteNextHopHasOifBorderBit,
        usdPimMRouteNextHopHasOifNullEncapsBit,
        usdPimMRouteNextHopJoinEndTimer,
        usdPimMRouteNextHopAssertEndTimer,
        usdPimMRouteNextHopNextAssertTimer,
        usdPimMRouteNextHopAssertSrcAddress,
        usdPimMRouteNextHopRegisterSuppressionTimer,
        usdPimMRouteNextHopPimType,
        usdPimMRouteNextHopPruneTimeLeft,
        usdPimMRouteNextHopsendingIpAddress }
    STATUS      current
    DESCRIPTION
        "A collection of objects for managing PIM multicast route next hop
        capabilities in a Unisphere product."
    ::= { usdPimGroups 4 }

usdPimRPSetGroup OBJECT-GROUP
    OBJECTS {
        usdPimRPSetPriority,
        usdPimRPSetTypeInfo,
        usdPimRPSetAccessListName }
    STATUS      current
    DESCRIPTION
        "A collection of objects for managing PIM RP-Set capabilities in a
        Unisphere product."
    ::= { usdPimGroups 5 }

usdPimStaticRPConfGroup OBJECT-GROUP
    OBJECTS {
        usdPimStaticRPConfRowStatus,
        usdPimStaticRPConfOverride }
    STATUS      current
    DESCRIPTION
        "A collection of objects for managing statically configured PIM RPs
        capabilities in a Unisphere product."
    ::= { usdPimGroups 6 }

usdPimAutoRPConfGroup OBJECT-GROUP
    OBJECTS {
        usdPimAutoRPConfRowStatus,
        usdPimAutoRPConfTTL,
        usdPimAutoRPConfAncmntIntvl,
        usdPimAutoRPConfifId }
    STATUS      current
    DESCRIPTION
        "A collection of objects for managing PIM AutoRP candidate advertisment
        agent RP capabilities in a Unisphere product."
    ::= { usdPimGroups 7 }

usdPimAutoRPCandGroup OBJECT-GROUP
    OBJECTS {
        usdPimAutoRPCandRowStatus,
        usdPimAutoRPCandAccessListName,
        usdPimAutoRPCandAutoRPTTL,
        usdPimAutoRPCandAutoRPAncmntIntvl,
        usdPimAutoRPCandIfId }
    STATUS      current
    DESCRIPTION
        "A collection of objects for managing PIM AutoRP candidate advertising
        agent RP capabilities in a Unisphere product."
    ::= { usdPimGroups 8 }

usdPimComponentGroup OBJECT-GROUP
    OBJECTS {
        usdPimComponentAutoRPMappingAgentRowStatus,
        usdPimComponentConfiguredAutoRPMappingAgentIfId,
        usdPimComponentAutoRPMappingAgentInterval,
        usdPimComponentAutoRPMappingTTL,
        usdPimComponentAutoRPMappingAgentIntfAddr,
        usdPimComponentAutoRPMappingAgentWinnerAddr,
        usdPimComponentAutoRPMappingAgentWinnerLastHeard }
    STATUS      current
    DESCRIPTION
        "A collection of objects for managing PIM component (domain)
        capabilities in a Unisphere product."
    ::= { usdPimGroups 9 }

usdPimUnicastRouteGroup OBJECT-GROUP
    OBJECTS {
        usdPimUnicastRouteEntryRpfNbr,
        usdPimUnicastRouteEntryIifId,
        usdPimUnicastRouteEntryIifAddr,
        usdPimUnicastRouteEntryPref,
        usdPimUnicastRouteEntryMetric,
        usdPimUnicastRouteEntryPimType }
    STATUS      current
    DESCRIPTION
        "A collection of objects for managing PIM unicast route capabilities in
        a Unisphere product."
    ::= { usdPimGroups 10 }

usdPimSPTThresholdGroup OBJECT-GROUP
    OBJECTS {
        usdPimSPTThresHoldRowStatus,
        usdPimSPTThresholdKbps }
    STATUS      current
    DESCRIPTION
        "A collection of objects for managing PIM shortest path tree threshold
        capabilities in a Unisphere product."
    ::= { usdPimGroups 11 }

END
