-- extracted from draft-ietf-pwe3-pw-mpls-mib-03.txt
-- at Tue Oct 28 06:14:44 2003

PW-MPLS-MIB DEFINITIONS ::= BEGIN

IMPORTS
   MODULE-IDENTITY, OBJECT-TYPE, 
   experimental, Unsigned32
      FROM SNMPv2-SMI

   MODULE-COMPLIANCE, OBJECT-GROUP
      FROM SNMPv2-CONF

   RowStatus, StorageType
      FROM SNMPv2-TC

   InterfaceIndexOrZero
      FROM IF-MIB

   MplsTunnelIndex, MplsTunnelInstanceIndex,
   MplsLdpIdentifier, MplsLsrIdentifier
      FROM MPLS-TC-MIB
   
   PwVcIndexType
      FROM PW-TC-MIB

   pwVcIndex
      FROM PW-MIB

;

pwVcMplsMIB MODULE-IDENTITY
   LAST-UPDATED "200307291200Z"  -- 29 July 2003 12:00:00 EST
   ORGANIZATION "Pseudo Wire Edge to Edge Emulation (PWE3) Working
                 Group"
   CONTACT-INFO
       "
        David Zelig
        Postal: Corrigent Systems
                126, Yigal Alon St.
                Tel Aviv, ISRAEL
                Phone: +972-3-6945273
        E-mail: davidz@corrigent.com

        Thomas D. Nadeau
        Postal: Cisco Systems, Inc.
                250 Apollo Drive
                Chelmsford, MA 01824
        Tel:    +1-978-497-3051
        Email:  tnadeau@cisco.com

        Dave Danenberg
        Postal: Litchfield Communications, Inc.
                76 Westbury Park Rd
                Princeton Building East
                Watertown, CT 06795
        Tel:    +1-860-945-1573 x3180
        Email:  dave_danenberg@litchfieldcomm.com
    
        Sharon Mantin
        Postal:  AxONLink (Israel) Ltd 
                 9 Bareket St. 
                 Petah Tikva 49517, Israel 
        Tel:     +972-3-9263972 
        Email:   sharon.mantin@axonlink.com
        
        The PWE3 Working Group (email distribution pwe3@ietf.org) "

   DESCRIPTION
       "This MIB complements the PW-MIB for PW operation over MPLS.
       "
   
   -- Revision history.
   REVISION
       "200307291200Z"  -- 29 July 2003 12:00:00 EST
   DESCRIPTION
      "Draft-ietf-pwe3-pw-mpls-mib-02 version. Changes from 
       previous version:
       1) Removing inbound table (no srict mode and no knowledge 
	      of inbound tunnel).
       2) Provisoning (i.e. RowCreate) done via mapping tables.
	      Outbound table is now read only for sorted search for
		  pwVcIndex.
      "

   REVISION
       "0206021200Z"  -- 02 June 2002 12:00:00 EST
   DESCRIPTION
      "Draft-ietf-pwe3-pw-mpls-mib-00 version. Changes from 
       previous version:
       1) Spliting the mapping table into two tables, one for
          Non TE application and one for TE application.
       2) Object types alignment with MPLS MIBs.
      "
   REVISION
       "0201291200Z"  -- 29 January 2002 12:00:00 EST
   DESCRIPTION
      "Changes from previous version:
       1) Add LDP entity association.
       2) Clarify inbound/outbound directions.
       3) Simplify indexing of outbound and inbound tables
          and providing get next variables.
      "
   REVISION
       "0107111200Z"  -- 7 November 2001 12:00:00 EST
   DESCRIPTION
      "Changes from previous version:
       1) Remove Vc instance from table indexing.
       2) Update descriptions of indexing and protection.
       3) Remove the need for MPLS-LSR in case of VC only.
       4) Change pwVcMplsMplsType to BITS in order to enable
          multiple types of outer tunnel.
       5) Add ifindex to outer tunnel tables to support vcOnly 
          option.
       6) change naming of outbound, inbound and mapping tables to 
          reflect addition of VC only port ifindexes.
       7) Adapt order of items in mapping table to SNMP convention.
      "
   REVISION
       "0107111200Z"  -- July 11 2001 12:00:00 EST
   DESCRIPTION
      "draft-zelig-pw-mib-00.txt - initial version"

   ::= { experimental 888 } -- To be assigned by IANA

-- Top-level components of this MIB.

-- Traps
pwVcMplsNotifications OBJECT IDENTIFIER 
                              ::= { pwVcMplsMIB 0 }
pwVcMplsNotifyPrefix  OBJECT IDENTIFIER
                              ::= { pwVcMplsNotifications 0 }
-- Tables, Scalars
pwVcMplsObjects       OBJECT IDENTIFIER
                              ::= { pwVcMplsMIB 1 }

-- Conformance
pwVcMplsConformance   OBJECT IDENTIFIER 
                              ::= { pwVcMplsMIB 2 }

-- PW VC MPLS table

pwVcMplsTable   OBJECT-TYPE
   SYNTAX        SEQUENCE OF PwVcMplsEntry
   MAX-ACCESS    not-accessible
   STATUS        current
   DESCRIPTION
       "This table specifies information for VC to be carried over 
        MPLS PSN."
   ::= { pwVcMplsObjects 1 }

pwVcMplsEntry   OBJECT-TYPE
   SYNTAX        PwVcMplsEntry
   MAX-ACCESS    not-accessible
   STATUS        current
   DESCRIPTION
        "A row in this table represents parameters specific to MPLS 
         PSN for a pseudo wire connection (VC). The row is created 
         automatically by the local agent if the pwVcPsnType is 
         MPLS. It is indexed by pwVcIndex, which uniquely 
         identifying a singular connection.
        "

   INDEX  { pwVcIndex }

      ::= { pwVcMplsTable 1 }

PwVcMplsEntry ::= SEQUENCE {
      pwVcMplsMplsType          BITS,
      pwVcMplsExpBitsMode       INTEGER,
      pwVcMplsExpBits           Unsigned32,
      pwVcMplsTtl               Unsigned32,
      pwVcMplsLocalLdpID        MplsLdpIdentifier,
      pwVcMplsLocalLdpEntityID  Unsigned32,
      pwVcMplsPeerLdpID         MplsLdpIdentifier,
      pwVcMplsStorageType       StorageType
   }

pwVcMplsMplsType OBJECT-TYPE 
   SYNTAX   BITS {
       mplsTe    (0),
       mplsNonTe (1),
       vcOnly    (2)
            }
   MAX-ACCESS    read-write
   STATUS        current
   DESCRIPTION
        "Set by the operator to indicate the outer tunnel types, if
         exists. mplsTe is used if the outer tunnel was set-up by 
         MPLS-TE, and mplsNonTe is used the outer tunnel was set up
         by LDP or manually. Combination of mplsTe and mplsNonTe 
         may exist in case of outer tunnel protection.
         vcOnly is used if there is no outer tunnel label. vcOnly 
         cannot be combined with mplsNonTe or mplsTe."
   ::= { pwVcMplsEntry 1 }


pwVcMplsExpBitsMode OBJECT-TYPE 
   SYNTAX   INTEGER {
       outerTunnel      (1),
       specifiedValue   (2),
       serviceDependant (3)
            }
           
   MAX-ACCESS    read-write
   STATUS        current
   DESCRIPTION
       "Set by the operator to indicate the way the VC shim label
        EXP bits are to be determined. The value of outerTunnel(1)
        is used where there is an outer tunnel - pwVcMplsMplsType 
        is mplsTe or mplsNonTe. Note that in this case there is no
        need to mark the VC label with the EXP bits since the VC 
        label is not visible to the intermediate nodes.
        If there is no outer tunnel, specifiedValue(2) indicate 
        that the value is specified by pwVcMplsExpBits, and 
        serviceDependant(3) indicate that the EXP bits are setup 
        based on a rule specified in the emulated service specific 
        tables, for example when the EXP bits are a function of 
        802.1p marking for Ethernet emulated service."
   REFERENCE
        "martini et al, <draft-martini-l2circuit-encap-mpls.txt>" 
   DEFVAL { outerTunnel }
   ::= { pwVcMplsEntry 2 }

pwVcMplsExpBits OBJECT-TYPE 
   SYNTAX   	 Unsigned32 (0..7)
   MAX-ACCESS    read-write
   STATUS        current
   DESCRIPTION
        "Set by the operator to indicate the MPLS EXP bits to be 
         used on the VC shim label if pwVcMplsExpBitsMode is  
         specifiedValue(2), zero otherwise."
   DEFVAL { 0 }
   ::= { pwVcMplsEntry 3 }

pwVcMplsTtl OBJECT-TYPE 
   SYNTAX        Unsigned32 (0..255)
   MAX-ACCESS    read-write
   STATUS        current
   DESCRIPTION
        "Set by the operator to indicate the VC TTL bits to be used
         on the VC shim label."
   REFERENCE
        "martini et al, <draft-martini-l2circuit-encap-mpls> " 
   DEFVAL { 2 }
   ::= { pwVcMplsEntry 4 }

pwVcMplsLocalLdpID OBJECT-TYPE 
   SYNTAX        MplsLdpIdentifier
   MAX-ACCESS    read-write
   STATUS        current
   DESCRIPTION
        "The local LDP identifier of the LDP entity creating
         this VC in the local node. As the VC labels are always
         set from the per platform label space, the last two octets 
         in the LDP ID MUST be always both zeros."
   REFERENCE
        "<draft-ietf-ldp-mib>,
         <draft-martini-l2circuit-encap-mpls>.
        "
   ::= { pwVcMplsEntry 5 }

pwVcMplsLocalLdpEntityID OBJECT-TYPE 
   SYNTAX        Unsigned32
   MAX-ACCESS    read-write
   STATUS        current
   DESCRIPTION
        "The local LDP Entity index of the LDP entity to be used 
         for this VC on the local node. Should be set to all zeros 
         if not used."
   REFERENCE
        "<draft-ietf-ldp-mib>
        "
   ::= { pwVcMplsEntry 6 }

pwVcMplsPeerLdpID OBJECT-TYPE 
   SYNTAX        MplsLdpIdentifier
   MAX-ACCESS    read-only
   STATUS        current
   DESCRIPTION
        "The peer LDP identifier as identified from the LDP 
         session. Should be zero if not relevant or not known yet."
   REFERENCE
        "<draft-ietf-ldp-mib>,
         <draft-martini-l2circuit-encap-mpls>.
        "
   ::= { pwVcMplsEntry 7 }

pwVcMplsStorageType OBJECT-TYPE 
   SYNTAX                      StorageType
   MAX-ACCESS                  read-write
   STATUS                      current
   DESCRIPTION
       "This variable indicates the storage type for this row."
   ::= { pwVcMplsEntry 8 }

-- End of PW MPLS VC table

-- Pseudo Wire VC MPLS Outbound Tunnel table

pwVcMplsOutboundTable   OBJECT-TYPE
   SYNTAX        SEQUENCE OF PwVcMplsOutboundEntry
   MAX-ACCESS    not-accessible
   STATUS        current
   DESCRIPTION
       "This table associates VCs using MPLS PSN with the outbound
        MPLS tunnels (i.e. toward the PSN) or the physical 
        interface in case of VC only."
   ::= { pwVcMplsObjects 2 }

pwVcMplsOutboundEntry OBJECT-TYPE
   SYNTAX        PwVcMplsOutboundEntry
   MAX-ACCESS    not-accessible
   STATUS        current
   DESCRIPTION
       "A row in this table represents a link between PW VC (that
        require MPLS tunnels) and MPLS tunnel toward the PSN.
        In the case of VC only, it associate the VC with the 
        interface that shall carry the VC.
        This table is indexed by the pwVcIndex and an additional
        index enabling multiple rows for the same VC index.

        At least one entry is created in this table by the agent 
        for each PW VC that requires MPLS PSN. Note that the first
        entry for each VC can be indexed by pwVcMplsOutboundIndex 
        equal zero without a need for retrieval of 
        pwVcMplsOutboundIndexNext.

        This table points to the appropriate MPLS MIB. In the case 
        of MPLS-TE, the 4 variables relevant to the indexing of 
        a TE MPLS tunnel are set as in Srinivasan, et al, <draft-
        ietf-mpls-te-mib>.
        In case of Non-TE MPLS (an outer tunnel label assigned by 
        LDP or manually) the table points to the XC entry in the 
        LSR MIB as in Srinivasan, et al, <draft-ietf-mpls-lsr-mib>.
        In case of VC only (no outer tunnel) the ifIndex of the
        port to carry the VC is configured. 
        
        Each VC may have multiple rows in this tables if protection 
        is available at the outer tunnel level, each row may be of
        different type except for VC only, on which only rows with
        ifIndex of the port are allowed.
        "

   INDEX { pwVcIndex, pwVcMplsOutboundIndex }
 
      ::= { pwVcMplsOutboundTable 1 }

PwVcMplsOutboundEntry ::= SEQUENCE {
      pwVcMplsOutboundIndex             Unsigned32,
      pwVcMplsOutboundLsrXcIndex        Unsigned32,
      pwVcMplsOutboundTunnelIndex       MplsTunnelIndex,
      pwVcMplsOutboundTunnelInstance    MplsTunnelInstanceIndex,
      pwVcMplsOutboundTunnelLclLSR      MplsLsrIdentifier,
      pwVcMplsOutboundTunnelPeerLSR     MplsLsrIdentifier,
      pwVcMplsOutboundIfIndex           InterfaceIndexOrZero
      }

pwVcMplsOutboundIndex OBJECT-TYPE
   SYNTAX        Unsigned32 (0..4294967295)
   MAX-ACCESS    not-accessible
   STATUS        current
   DESCRIPTION
       "Arbitrary index for enabling multiple rows per VC in
        this table. Next available free index can be retrieved 
        using pwVcMplsOutboundIndexNext.
        "
   ::= { pwVcMplsOutboundEntry 1 }

pwVcMplsOutboundLsrXcIndex 		OBJECT-TYPE
   SYNTAX        Unsigned32
   MAX-ACCESS    read-only
   STATUS        current
   DESCRIPTION
       "This object will be set by the operator. If the outer
        label is defined in the MPL-LSR-MIB, i.e. set by LDP
        or manually, this object points to the XC index 
        of the outer tunnel. Otherwise, it is set to zero."
   ::= { pwVcMplsOutboundEntry 2 }


pwVcMplsOutboundTunnelIndex         OBJECT-TYPE
   SYNTAX                           MplsTunnelIndex
   MAX-ACCESS                       read-only
   STATUS                           current
   DESCRIPTION
        "Part of set of indexes for outbound tunnel in the case of 
         MPLS-TE outer tunnel, otherwise set to zero."
   ::= { pwVcMplsOutboundEntry  3 } 

pwVcMplsOutboundTunnelInstance      OBJECT-TYPE
   SYNTAX                           MplsTunnelInstanceIndex
   MAX-ACCESS                       read-only
   STATUS                           current
   DESCRIPTION
        "Part of set of indexes for outbound tunnel in the case of 
         MPLS-TE outer tunnel, otherwise set to zero."
   ::= { pwVcMplsOutboundEntry   4 } 

pwVcMplsOutboundTunnelLclLSR        OBJECT-TYPE
   SYNTAX                           MplsLsrIdentifier
   MAX-ACCESS                       read-only
   STATUS                           current
   DESCRIPTION 
        "Part of set of indexes for outbound tunnel in the case of 
         MPLS-TE outer tunnel, otherwise set to zero."
   ::= { pwVcMplsOutboundEntry   5 } 

pwVcMplsOutboundTunnelPeerLSR       OBJECT-TYPE
   SYNTAX                           MplsLsrIdentifier
   MAX-ACCESS                       read-only
   STATUS                           current
   DESCRIPTION
        "Part of set of indexes for outbound tunnel in the case of 
         MPLS-TE outer tunnel, otherwise set to zero."
   ::= { pwVcMplsOutboundEntry   6 } 

pwVcMplsOutboundIfIndex       OBJECT-TYPE
   SYNTAX                           InterfaceIndexOrZero
   MAX-ACCESS                       read-only
   STATUS                           current
   DESCRIPTION
        "In case of VC only (no outer tunnel), this object holds
         the ifIndex of the outbound port, otherwise set to zero."
   ::= { pwVcMplsOutboundEntry   7 } 

-- End of Pseudo Wire VC MPLS Outbound Tunnel table

-- MPLS to VC Mapping Tables.

pwVcMplsNonTeMappingTable OBJECT-TYPE 
   SYNTAX           SEQUENCE OF PwVcMplsNonTeMappingEntry
   MAX-ACCESS       not-accessible
   STATUS           current
   DESCRIPTION
       "This table maps an outbound Tunnel to a VC in non-
        TE applications."
   ::= { pwVcMplsObjects 3 }

pwVcMplsNonTeMappingEntry OBJECT-TYPE
   SYNTAX           PwVcMplsNonTeMappingEntry
   MAX-ACCESS       not-accessible
   STATUS           current
   DESCRIPTION
        "A row in this table represents the association
         between the PW VC and it's non TE MPLS outer Tunnel
         it's physical interface if there is no outer tunnel 
         (VC only).
         
         If the operator (or the agent, based on local policy)
		 want to associate the PW with a non TE tunnel, it
create 
		 a row in this table with the tunnel parameters and the 
		 relevant pwVcIndex.

         An application can use this table to quickly retrieve the 
         PW carried over specific non-TE MPLS outer tunnel or 
         physical interface.
         
         The table in indexed by the XC index for MPLS Non-TE 
         tunnel, or ifIndex of the port in VC only case, the 
         direction of the VC in the specific entry and the VCIndex.
         "

   INDEX  { pwVcMplsNonTeMappingXcTunnelIndex,
            pwVcMplsNonTeMappingIfIndex,
            pwVcMplsNonTeMappingVcIndex }

      ::= { pwVcMplsNonTeMappingTable 1 }

PwVcMplsNonTeMappingEntry ::= SEQUENCE {
      pwVcMplsNonTeMappingXcTunnelIndex     Unsigned32,
	  pwVcMplsNonTeMappingIfIndex
InterfaceIndexOrZero,
      pwVcMplsNonTeMappingVcIndex           PwVcIndexType,
      pwVcMplsNonTeMappingRowStatus         RowStatus,
      pwVcMplsNonTeMappingStorageType       StorageType
   }

pwVcMplsNonTeMappingXcTunnelIndex OBJECT-TYPE
   SYNTAX        Unsigned32 (0..4294967295)
   MAX-ACCESS    not-accessible
   STATUS        current
   DESCRIPTION
       "Index for the conceptual XC row identifying Tunnel to VC 
        mappings when the outer tunnel is created by the MPLS-LSR-
        MIB, Zero otherwise."
   ::= { pwVcMplsNonTeMappingEntry 1 }

pwVcMplsNonTeMappingIfIndex  OBJECT-TYPE
   SYNTAX        InterfaceIndexOrZero
   MAX-ACCESS    not-accessible
   STATUS        current
   DESCRIPTION
       "In cases where there is only VC label without outer tunnel,
        this item indicate the ifIndex of the interface this VC 
        would use. In all other cases, this object shgould be set to 
        zero."
   ::= { pwVcMplsNonTeMappingEntry 2 }

pwVcMplsNonTeMappingVcIndex  OBJECT-TYPE
   SYNTAX        PwVcIndexType
   MAX-ACCESS    read-create
   STATUS        current
   DESCRIPTION
       "The value that represent the VC in the pwVcTable."
   ::= { pwVcMplsNonTeMappingEntry 3 }

pwVcMplsNonTeMappingRowStatus   OBJECT-TYPE
   SYNTAX           RowStatus
   MAX-ACCESS       read-create
   STATUS           current
   DESCRIPTION
       "For creating, modifying, and deleting this row."
   ::= { pwVcMplsNonTeMappingEntry 4 }

pwVcMplsNonTeMappingStorageType OBJECT-TYPE
   SYNTAX           StorageType
   MAX-ACCESS       read-create
   STATUS           current
   DESCRIPTION
       "This variable indicates the storage type for this object."
   ::= { pwVcMplsNonTeMappingEntry 5 }

-- End of Non-TE MPLS Tunnel to VC Mapping Table

pwVcMplsTeMappingTable OBJECT-TYPE 
   SYNTAX           SEQUENCE OF PwVcMplsTeMappingEntry
   MAX-ACCESS       not-accessible
   STATUS           current
   DESCRIPTION
       "This table maps an inbound/outbound Tunnel to a VC in 
        MPLS-TE applications."
   ::= { pwVcMplsObjects 4 }

pwVcMplsTeMappingEntry OBJECT-TYPE
   SYNTAX           PwVcMplsTeMappingEntry
   MAX-ACCESS       not-accessible
   STATUS           current
   DESCRIPTION
        "A row in this table represents the association
         between a PW VC and it's MPLS-TE outer Tunnel.
         
         If the operator (or the agent, based on local policy)
		 want to associate the PW with a non TE tunnel, it
create 
		 a row in this table with the tunnel parameters and the 
		 relevant pwVcIndex.

         An application can use this table to quickly retrieve the 
         PW carried over specific TE MPLS outer tunnel.
         
         The table in indexed by the 4 indexes of a TE tunnel,
         the direction of the VC specific entry and the VcIndex.
        "

   INDEX  { pwVcMplsTeMappingTunnelIndex, 
            pwVcMplsTeMappingTunnelInstance,
            pwVcMplsTeMappingTunnelPeerLsrID,
            pwVcMplsTeMappingTunnelLocalLsrID,
            pwVcMplsTeMappingVcIndex }

      ::= { pwVcMplsTeMappingTable 1 }

PwVcMplsTeMappingEntry ::= SEQUENCE {
      pwVcMplsTeMappingTunnelIndex       MplsTunnelIndex,
      pwVcMplsTeMappingTunnelInstance    MplsTunnelInstanceIndex,
      pwVcMplsTeMappingTunnelPeerLsrID   MplsLsrIdentifier,
      pwVcMplsTeMappingTunnelLocalLsrID  MplsLsrIdentifier,
      pwVcMplsTeMappingVcIndex           PwVcIndexType,
      pwVcMplsTeMappingRowStatus         RowStatus,
      pwVcMplsTeMappingStorageType       StorageType

   }

pwVcMplsTeMappingTunnelIndex OBJECT-TYPE
   SYNTAX        MplsTunnelIndex
   MAX-ACCESS    not-accessible
   STATUS        current
   DESCRIPTION
       "Primary index for the conceptual row identifying the 
        MPLS-TE tunnel."
   ::= { pwVcMplsTeMappingEntry 1 }

pwVcMplsTeMappingTunnelInstance OBJECT-TYPE
   SYNTAX        MplsTunnelInstanceIndex
   MAX-ACCESS    not-accessible
   STATUS        current
   DESCRIPTION
       "Identifies an instance of the MPLS-TE tunnel."
   ::= { pwVcMplsTeMappingEntry 2 }

pwVcMplsTeMappingTunnelPeerLsrID  OBJECT-TYPE
   SYNTAX        MplsLsrIdentifier
   MAX-ACCESS    not-accessible
   STATUS        current
   DESCRIPTION
       "Identifies an Peer LSR when the outer tunnel is MPLS-TE 
        based."
   ::= { pwVcMplsTeMappingEntry 3 }

pwVcMplsTeMappingTunnelLocalLsrID  OBJECT-TYPE
   SYNTAX        MplsLsrIdentifier
   MAX-ACCESS    not-accessible
   STATUS        current
   DESCRIPTION
       "Identifies the local LSR."
   ::= { pwVcMplsTeMappingEntry 4 }

pwVcMplsTeMappingVcIndex  OBJECT-TYPE
   SYNTAX        PwVcIndexType
   MAX-ACCESS    read-create
   STATUS        current
   DESCRIPTION
       "The value that represent the VC in the pwVcTable."
   ::= { pwVcMplsTeMappingEntry 5 }

pwVcMplsTeMappingRowStatus   OBJECT-TYPE
   SYNTAX        RowStatus
   MAX-ACCESS    read-create
   STATUS        current
   DESCRIPTION
       "For creating, modifying, and deleting this row."
   ::= { pwVcMplsTeMappingEntry 6 }

pwVcMplsTeMappingStorageType OBJECT-TYPE
   SYNTAX        StorageType
   MAX-ACCESS    read-create
   STATUS        current
   DESCRIPTION
       "This variable indicates the storage type for this object."
   ::= { pwVcMplsTeMappingEntry 7 }


-- End of TE MPLS Tunnel to VC Mapping Table


-- conformance information

   -- Note: Conformance at the object access and values level is 
   -- still FFS, therefore current conformance is defined at the
   -- object existence level only.

pwVcMplsGroups      OBJECT IDENTIFIER ::= { pwVcMplsConformance 1 }
pwVcMplsCompliances OBJECT IDENTIFIER ::= { pwVcMplsConformance 2 }


pwMplsModuleCompliance MODULE-COMPLIANCE
    STATUS  current
    DESCRIPTION
            "The compliance statement for agent that support PW 
             over MPLS PSN operation."

    MODULE  -- this module
        MANDATORY-GROUPS { pwVcMplsGroup,
                           pwVcMplsOutboundGroup,
                           pwVcMplsMappingGroup
                         }

    ::= { pwVcMplsCompliances 1 }

-- Units of conformance.

pwVcMplsGroup OBJECT-GROUP 
   OBJECTS {
            pwVcMplsMplsType,
            pwVcMplsExpBitsMode,
            pwVcMplsExpBits,
            pwVcMplsTtl,
            pwVcMplsLocalLdpID,
            pwVcMplsLocalLdpEntityID,
            pwVcMplsPeerLdpID,
            pwVcMplsStorageType
          }
             
   STATUS  current
   DESCRIPTION
          "Collection of objects needed for PW VC
           over MPLS PSN configuration."
   ::= { pwVcMplsGroups 1 }



pwVcMplsOutboundGroup OBJECT-GROUP 
   OBJECTS {
            pwVcMplsOutboundLsrXcIndex,
            pwVcMplsOutboundTunnelIndex,
            pwVcMplsOutboundTunnelInstance,
            pwVcMplsOutboundTunnelLclLSR,
            pwVcMplsOutboundTunnelPeerLSR,
            pwVcMplsOutboundIfIndex
          }
             
   STATUS  current
   DESCRIPTION
          "Collection of objects needed for outbound association of 
           VC and MPLS tunnel."
   ::= { pwVcMplsGroups 2 }

pwVcMplsMappingGroup OBJECT-GROUP 
   OBJECTS {
            pwVcMplsNonTeMappingVcIndex,
			pwVcMplsNonTeMappingRowStatus,
			pwVcMplsNonTeMappingStorageType,
            pwVcMplsTeMappingVcIndex,
			pwVcMplsTeMappingRowStatus,
			pwVcMplsTeMappingStorageType
          }
             
   STATUS  current
   DESCRIPTION
          "Collection of objects used for mapping of tunnels and VC
           labels to VC index."
   ::= { pwVcMplsGroups 4 }

END -- of PW-MPLS-MIB
