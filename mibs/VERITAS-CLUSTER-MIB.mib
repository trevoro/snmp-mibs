--
-- (c) 2000, 2001 VERITAS Software, Inc.  All rights reserved.
--
-- VERITAS Software: 1.3.6.1.4.1.1302
--
-- 1302 - veritassoftware
--        .3 - products
--             .8 - veritasCluster
--                  .10 - clustertrapsData
--                       .1 - clustertrapsvars
--                       .2 - clustertrapsGroups
--                            .1 - resources
--                            .2 - groups
--                            .3 - systems
--                            .4 - vcsHeartbeat (reserved for future use)
--                            .5 - gcmHeartbeat (reserved for future use)
--                            .6 - vcs
--                            .7 - gcmSite    	(reserved for future use)
--                            .8 - agents
--                            .9 - User defined external traps not recognized by VCS
--                            .10 - RDC traps
--
-- Resources Traps
-- 1302.3.8.10.2.1     : #1 "Resource state is unknown"
--                     : #2 "Resource monitoring has timed out"
--                     : #3 "Resource is not going offline"
--                     : #4 "Resource is being restarted by agent"
--                     : #5 "Resource went online by itself"
--                     : #6 "Resource has faulted"
--           
-- Groups Traps
-- 1302.3.8.10.2.2     : #1 "Service Group is online"
--                     : #2 "Service Group is offline"
--                     : #3 "Service Group is auto disabled"
--                     : #4 "Service Group has faulted"
--                     : #5 "Service Group has faulted and cannot be failed over anywhere"
--                     : #6 "Service Group is restarting"
--                     : #7 "Service Group is being switched"
--                     : #8 "Service Group concurrency violation"
--                     : #9 "Service Group is restarting in responce to persistent
--                           resource going online" 
--
-- Systems Traps
-- 1302.3.8.10.2.3     : #1 "VCS up on first node in Cluster"
--                     : #2 "VCS is being restarted by hashadow"
--                     : #3 "VCS is in jeopardy"
--                     : #4 "VCS has faulted"
--                     : #5 "A node running VCS has joined cluster"
--                     : #6 "VCS has exited manually"
--                     : #7 "VCS is up but not in cluster"
--                     : #8 "CPU Usage exceeded the threshold"
-- 
-- VCS Traps
-- 1302.3.8.10.2.6     : #1 "Cluster has hung" (reserved for future use)
--                     : #2 "User has logged into VCS"
--
-- Agents Traps
-- 1302.3.8.10.2.8     : #1 "Agent restarting"
--                     : #2 "Agent faulted"
--
-- External Traps
-- 1302.3.8.10.2.9     : #  For user defined traps..
--
-- RDC traps
-- 1302.3.8.10.2.10    : #1 "Rlink not consistent"
--		       : #2 "Rlink not up to date"
--		       : #3 "Unable to makeprimary (takeover)"
--		       : #4 "Unable to migrate"
--		       : #5 "RVG promoted to primary (takeover)"
--		       : #6 "RVG promoted to primary (migrate)"
--		       : #7 "Cannot promote, RVG is acting_secondary"
--		       : #8 "Resync failed"
--		       : #9 "Resync successful"
--		       : #10 "(violation) Offlining group"

     VERITAS-CLUSTER-MIB DEFINITIONS ::= BEGIN

     IMPORTS
          enterprises
               FROM RFC1155-SMI
          OBJECT-TYPE
               FROM RFC-1212
          TRAP-TYPE
               FROM RFC-1215
          DisplayString
               FROM RFC1213-MIB
          MODULE-IDENTITY
               FROM SNMPv2-SMI;                                

     veritassoftware         OBJECT IDENTIFIER ::= { enterprises 1302 }
     products                OBJECT IDENTIFIER ::= { veritassoftware 3 }

     veritasCluster MODULE-IDENTITY
     LAST-UPDATED "03202001"
     ORGANIZATION "VERITAS Software, Inc."
     CONTACT-INFO "1600 Plymouth Street.
                   Mountain View, CA 94043 US
                   Subject: veritas-cluster.mib"
     DESCRIPTION "The MIB module for VCS and GCM VERITAS products"

     ::= { products 8 }

 

     clustertraps            OBJECT IDENTIFIER ::= { veritasCluster 10 }
     clustertrapvars         OBJECT IDENTIFIER ::= { clustertraps 1 }
     clustertrapsGroups      OBJECT IDENTIFIER ::= { clustertraps 2 }
     resourcesTraps          OBJECT IDENTIFIER ::= { clustertrapsGroups 1 }
     groupsTraps             OBJECT IDENTIFIER ::= { clustertrapsGroups 2 }
     systemsTraps            OBJECT IDENTIFIER ::= { clustertrapsGroups 3 }
     vcsHeartbeatTraps       OBJECT IDENTIFIER ::= { clustertrapsGroups 4 }
     gcmHeartbeatTraps       OBJECT IDENTIFIER ::= { clustertrapsGroups 5 }
     vcsTraps                OBJECT IDENTIFIER ::= { clustertrapsGroups 6 }                       
     gcmSiteTraps            OBJECT IDENTIFIER ::= { clustertrapsGroups 7 }                       
     agentsTraps             OBJECT IDENTIFIER ::= { clustertrapsGroups 8 }

     externalTraps           OBJECT IDENTIFIER ::= { clustertrapsGroups 9 }
     rdcTraps                OBJECT IDENTIFIER ::= { clustertrapsGroups 10 }
--
--   Trap Variables Section
--

     trapOrigin OBJECT-TYPE
        SYNTAX DisplayString (SIZE (0..50))
        ACCESS read-only
        STATUS mandatory
        DESCRIPTION "Traps originating entity (VCS, GCM, Agent etc.)"
     ::= { clustertrapvars 1 }

    entityType OBJECT-TYPE
        SYNTAX DisplayString (SIZE (0..50))
        ACCESS read-only
        STATUS mandatory
        DESCRIPTION "The entity's type (Cluster, System, Group, Resource, etc.)"
    ::= { clustertrapvars 2 }

    entitySubType OBJECT-TYPE
        SYNTAX DisplayString (SIZE (0..50))
        ACCESS read-only
        STATUS mandatory
        DESCRIPTION "The entity's subtype (resource, group, etc.)"       
    ::= { clustertrapvars 3 }

    entityName OBJECT-TYPE
        SYNTAX DisplayString (SIZE (0..50))
        ACCESS read-only
        STATUS mandatory
        DESCRIPTION "The entity's name (resource name, group name, 
                     cluster name, etc.)"
    ::= { clustertrapvars 4 }

    entityOwner OBJECT-TYPE
        SYNTAX DisplayString (SIZE (0..50))
        ACCESS read-only
        STATUS mandatory
        DESCRIPTION "Entity's owner information. 
                     May include name, phone number, email address."
    ::= { clustertrapvars 5 }

    systemName OBJECT-TYPE
        SYNTAX DisplayString (SIZE (0..80))
        ACCESS read-only
        STATUS mandatory
        DESCRIPTION "The system name, where event occurred"
    ::= { clustertrapvars 6 }

    systemLocation OBJECT-TYPE
        SYNTAX DisplayString (SIZE (0..80))
        ACCESS read-only
        STATUS mandatory
        DESCRIPTION "The system location, where event occurred. 
                     (e.g. 1600 Plymouth Str, Mountain View CA, US)."
    ::= { clustertrapvars 7 }

    entityState OBJECT-TYPE
        SYNTAX DisplayString (SIZE (0..50))
        ACCESS read-only
        STATUS mandatory
        DESCRIPTION "Entity state (e.g. active, faulted, etc."
    ::= { clustertrapvars 8 }

    entityContainerType OBJECT-TYPE
        SYNTAX DisplayString (SIZE (0..50))
        ACCESS read-only
        STATUS mandatory
        DESCRIPTION "The entity container's (parents) type.
                     For resource - Service Group.
                     For service group - Cluster.
                     For system - Cluster.
                     For Cluster - Site."
    ::= { clustertrapvars 9 }

    entityContainerName OBJECT-TYPE
        SYNTAX DisplayString (SIZE (0..50))
        ACCESS read-only
        STATUS mandatory
        DESCRIPTION "The entity container's name."
    ::= { clustertrapvars 10 }

    peerSystemName OBJECT-TYPE
        SYNTAX DisplayString (SIZE (0..80))
        ACCESS read-only
        STATUS mandatory
        DESCRIPTION "The peer system name."
    ::= { clustertrapvars 11 }

    peerSystemLocation OBJECT-TYPE
        SYNTAX DisplayString (SIZE (0..80))
        ACCESS read-only
        STATUS mandatory 
        DESCRIPTION "The peer system location.
                    (e.g. 2500 De Anze Blvd, Sunnyvale CA, US)."
    ::= { clustertrapvars 12 }

    message OBJECT-TYPE
        SYNTAX DisplayString (SIZE (0..80))
        ACCESS read-only
        STATUS mandatory
        DESCRIPTION "Free format text message"
    ::= { clustertrapvars 13 }

    eventTime OBJECT-TYPE
        SYNTAX DisplayString (SIZE (0..50))
        ACCESS read-only
        STATUS mandatory
        DESCRIPTION "Events time since 00:00 Universal Coordinated Time, 
                     January 1, 1970"
    ::= { clustertrapvars 14 }

    severityId OBJECT-TYPE
        SYNTAX INTEGER {
            information(0),
            warning(1),
            error(2),
            severeError(3)
        }
        ACCESS read-only
        STATUS mandatory
        DESCRIPTION "The VCS and GCM traps severity level."
    ::= { clustertrapvars 15 }

--  Trap Definitions

-- Resources states traps section

    clusterResourceStateUnknownTrap TRAP-TYPE
        ENTERPRISE resourcesTraps
        VARIABLES { severityId, eventTime, entityName, entityType,
		    entitySubType, entityState, trapOrigin, systemName,
		    systemLocation, entityContainerName, entityContainerType,
                    entityOwner,message }
        DESCRIPTION "The resource unknown state has occured."
    ::= 1

    clusterResourceMonitorTimeoutTrap TRAP-TYPE
        ENTERPRISE resourcesTraps
        VARIABLES { severityId, eventTime, entityName, entityType,
		    entitySubType, entityState, trapOrigin, systemName,
		    systemLocation, entityContainerName, entityContainerType,
                    entityOwner,message }
        DESCRIPTION "The resource monitor timeout state has occured."
    ::= 2

    clusterResourceNotGoingOfflineTrap TRAP-TYPE
        ENTERPRISE resourcesTraps
        VARIABLES { severityId, eventTime, entityName, entityType,
		    entitySubType, entityState, trapOrigin, systemName,
		    systemLocation, entityContainerName, entityContainerType,
                    entityOwner,message }
        DESCRIPTION "The resource not going offline state has occured."
    ::= 3

    clusterResourceRestartingByAgentTrap TRAP-TYPE
        ENTERPRISE resourcesTraps
        VARIABLES { severityId, eventTime, entityName, entityType,
		    entitySubType, entityState, trapOrigin, systemName,
		    systemLocation, entityContainerName, entityContainerType,
                    entityOwner,message }
        DESCRIPTION "The resource restarting by agent state has occured."
    ::= 4

    clusterResourceWentOnlineByItselfTrap TRAP-TYPE
        ENTERPRISE resourcesTraps
        VARIABLES { severityId, eventTime, entityName, entityType,
		    entitySubType, entityState, trapOrigin, systemName,
		    systemLocation, entityContainerName, entityContainerType,
                    entityOwner,message }
        DESCRIPTION "The resource restarting by agent state has occured."
    ::= 5

    clusterResourceFaultedTrap TRAP-TYPE
        ENTERPRISE resourcesTraps
        VARIABLES { severityId, eventTime, entityName, entityType,
		    entitySubType, entityState, trapOrigin, systemName,
		    systemLocation, entityContainerName, entityContainerType,
                    entityOwner,message }
        DESCRIPTION "The resource faulted state has occured."
        ::= 6

-- Groups states traps section

   clusterGroupOnlineTrap TRAP-TYPE
        ENTERPRISE groupsTraps
        VARIABLES { severityId, eventTime, entityName, entityType,
		    entitySubType, entityState, trapOrigin, systemName,
		    systemLocation, entityContainerName, entityContainerType,
                    entityOwner,message }
        DESCRIPTION "The group online state has occured."
    ::= 1

    clusterGroupOfflineTrap   TRAP-TYPE
        ENTERPRISE groupsTraps
        VARIABLES { severityId, eventTime, entityName, entityType,
		    entitySubType, entityState, trapOrigin, systemName,
		    systemLocation, entityContainerName, entityContainerType,
                    entityOwner,message }
        DESCRIPTION "The group offline state has occured."
    ::= 2 

    clusterGroupAutoDisabledTrap TRAP-TYPE
        ENTERPRISE groupsTraps
        VARIABLES { severityId, eventTime, entityName, entityType,
		    entitySubType, entityState, trapOrigin, systemName,
		    systemLocation, entityContainerName, entityContainerType,
                    entityOwner,message }
        DESCRIPTION "The group auto disabled state has occured."
    ::= 3

    clusterGroupFaultedTrap   TRAP-TYPE
        ENTERPRISE groupsTraps
        VARIABLES { severityId, eventTime, entityName, entityType,
		    entitySubType, entityState, trapOrigin, systemName,
		    systemLocation, entityContainerName, entityContainerType,
                    entityOwner,message }
        DESCRIPTION "The group faulted state has occured."
    ::= 4

    clusterGroupFaultedAndNowhereToFailoverTrap TRAP-TYPE
        ENTERPRISE groupsTraps
        VARIABLES { severityId, eventTime, entityName, entityType,
		    entitySubType, entityState, trapOrigin, systemName,
		    systemLocation, entityContainerName, entityContainerType,
                    entityOwner,message }
        DESCRIPTION "The group faulted and nowhere to failover 
                     state has occured."
    ::= 5

    clusterGroupRestartingTrap TRAP-TYPE
        ENTERPRISE groupsTraps
        VARIABLES { severityId, eventTime, entityName, entityType,
		    entitySubType, entityState, trapOrigin, systemName,
		    systemLocation, entityContainerName, entityContainerType,
                    entityOwner,message }
        DESCRIPTION "The group restarting state has occured."
    ::= 6

    clusterGroupInitiatingForSwitchingTrap TRAP-TYPE
        ENTERPRISE groupsTraps
        VARIABLES { severityId, eventTime, entityName, entityType,
		    entitySubType, entityState, trapOrigin, systemName,
		    systemLocation, entityContainerName, entityContainerType,
                    entityOwner,message }
        DESCRIPTION "The group initiating for switching state has occured."
    ::= 7

    clusterGroupConcurencyViolationTrap   TRAP-TYPE
        ENTERPRISE groupsTraps
        VARIABLES { severityId, eventTime, entityName, entityType,
		    entitySubType, entityState, trapOrigin, systemName,
		    systemLocation, entityContainerName, entityContainerType,
                    entityOwner,message }
        DESCRIPTION "The group concurrency violation state has occured."
    ::= 8

    clusterGroupRestInRspnToPerstResGoOnlineTrap TRAP-TYPE
        ENTERPRISE groupsTraps
        VARIABLES { severityId, eventTime, entityName, entityType,
		    entitySubType, entityState, trapOrigin, systemName,
		    systemLocation, entityContainerName, entityContainerType,
                    entityOwner,message }
        DESCRIPTION "The group restarting in responce to persistent resource
                     going online state has occured."
    ::= 9

-- Systems states traps section

    clusterFirstSystemUpTrap TRAP-TYPE
        ENTERPRISE systemsTraps
        VARIABLES { severityId, eventTime, entityName, entityType,
		    entitySubType, entityState, trapOrigin, systemName,
		    systemLocation, entityContainerName, entityContainerType,
                    entityOwner,message }
        DESCRIPTION "The first system of cluster is up state has occured."
    ::= 1

    clusterSystemRestartingByHashadowTrap TRAP-TYPE
        ENTERPRISE systemsTraps
        VARIABLES { severityId, eventTime, entityName, entityType,
		    entitySubType, entityState, trapOrigin, systemName,
		    systemLocation, entityContainerName, entityContainerType,
                    entityOwner,message }
        DESCRIPTION "The system restarting by hashadow process 
                     state has occured."
    ::= 2

    clusterSystemInJeopardyTrap     TRAP-TYPE
        ENTERPRISE systemsTraps
        VARIABLES { severityId, eventTime, entityName, entityType,
		    entitySubType, entityState, trapOrigin, systemName,
		    systemLocation, entityContainerName, entityContainerType,
                    entityOwner,message }
        DESCRIPTION "The system is in jeopardy state has occured."
    ::= 3

    clusterSystemFaultedTrap TRAP-TYPE
        ENTERPRISE systemsTraps
        VARIABLES { severityId, eventTime, entityName, entityType,
		    entitySubType, entityState, trapOrigin, systemName,
		    systemLocation, entityContainerName, entityContainerType,
                    entityOwner,message }
        DESCRIPTION "The system faulted state has occured."
    ::= 4

    clusterSystemJoinedClusterTrap TRAP-TYPE
        ENTERPRISE systemsTraps
        VARIABLES { severityId, eventTime, entityName, entityType,
		    entitySubType, entityState, trapOrigin, systemName,
		    systemLocation, entityContainerName, entityContainerType,
                    entityOwner,message }
        DESCRIPTION "The system joined cluster state has occured."
    ::= 5

    clusterSystemExitedManuallyTrap TRAP-TYPE
        ENTERPRISE systemsTraps
        VARIABLES { severityId, eventTime, entityName, entityType,
		    entitySubType, entityState, trapOrigin, systemName,
		    systemLocation, entityContainerName, entityContainerType,
                    entityOwner,message }
        DESCRIPTION "The system exited manually state has occured."
    ::= 6


    clusterSystemUpButNotInClusterTrap TRAP-TYPE
        ENTERPRISE systemsTraps
        VARIABLES { severityId, eventTime, entityName, entityType,
		    entitySubType, entityState, trapOrigin, systemName,
		    systemLocation, entityContainerName, entityContainerType,
                    entityOwner,message }
        DESCRIPTION "The cluster system is up but not in cluster, visible only."
    ::= 7

	clusterSystemUsageExceededThresholdTrap TRAP-TYPE
        ENTERPRISE systemsTraps
		VARIABLES { severityId, eventTime, entityName, entityType,
		    entitySubType, entityState, trapOrigin, systemName,
		    systemLocation, entityContainerName, entityContainerType,
                    entityOwner,message }
        DESCRIPTION "CPU Usage exceeded the threshold on the system."
    ::= 8

-- VCS heartbeats traps section
-- not supported in current release

-- GCM heartbeat traps section
-- not supported in current release

-- VCS states traps     section
    clusterGUIUserLoginTrap TRAP-TYPE
        ENTERPRISE vcsTraps
        VARIABLES { severityId, eventTime, entityName, entityType,
		    entitySubType, entityState, trapOrigin, systemName,
		    systemLocation, entityContainerName, entityContainerType,
                    entityOwner,message }
        DESCRIPTION "The VCS GUI user log in."
    ::= 2

-- GCM states traps     section
-- not supported in current release

-- Agents states traps section

    clusterAgentRestartingTrap TRAP-TYPE
        ENTERPRISE agentsTraps
        VARIABLES { severityId, eventTime, entityName, entityType,
		    entitySubType, entityState, trapOrigin, systemName,
		    systemLocation, entityContainerName, entityContainerType,
                    entityOwner,message }
        DESCRIPTION "The agent restarted state has occured."
    ::= 1

    clusterAgentFaultedTrap TRAP-TYPE
        ENTERPRISE agentsTraps
        VARIABLES { severityId, eventTime, entityName, entityType,
		    entitySubType, entityState, trapOrigin, systemName,
		    systemLocation, entityContainerName, entityContainerType,
                    entityOwner,message }
        DESCRIPTION "The agent faulted state has occured."
    ::= 2

-- RDC states traps section

    clusterRDCRlinkInconsistentTrap TRAP-TYPE
        ENTERPRISE rdcTraps
        VARIABLES { severityId, eventTime, entityName, entityType,
		    entitySubType, entityState, trapOrigin, systemName,
		    systemLocation, entityContainerName, entityContainerType,
                    entityOwner,message }
        DESCRIPTION "RLINK is not consistent"
    ::= 1

    clusterRDCRlinkNotUpToDateTrap TRAP-TYPE
        ENTERPRISE rdcTraps
        VARIABLES { severityId, eventTime, entityName, entityType,
		    entitySubType, entityState, trapOrigin, systemName,
		    systemLocation, entityContainerName, entityContainerType,
                    entityOwner,message }
        DESCRIPTION "RLINK is not up to date"
    ::= 2

    clusterRDCTakeoverFailedTrap TRAP-TYPE
        ENTERPRISE rdcTraps
        VARIABLES { severityId, eventTime, entityName, entityType,
		    entitySubType, entityState, trapOrigin, systemName,
		    systemLocation, entityContainerName, entityContainerType,
                    entityOwner,message }
        DESCRIPTION "Unable to makeprimary (takeover)"
    ::= 3

    clusterRDCMigrateFailedTrap TRAP-TYPE
        ENTERPRISE rdcTraps
        VARIABLES { severityId, eventTime, entityName, entityType,
		    entitySubType, entityState, trapOrigin, systemName,
		    systemLocation, entityContainerName, entityContainerType,
                    entityOwner,message }
        DESCRIPTION "Unable to makeprimary (migrate)"
    ::= 4

    clusterRDCTakeoverSuccessTrap TRAP-TYPE
        ENTERPRISE rdcTraps
        VARIABLES { severityId, eventTime, entityName, entityType,
		    entitySubType, entityState, trapOrigin, systemName,
		    systemLocation, entityContainerName, entityContainerType,
                    entityOwner,message }
        DESCRIPTION "RVG promoted to primary (takeover)"
    ::= 5

    clusterRDCMigrateSuccessTrap TRAP-TYPE
        ENTERPRISE rdcTraps
        VARIABLES { severityId, eventTime, entityName, entityType,
		    entitySubType, entityState, trapOrigin, systemName,
		    systemLocation, entityContainerName, entityContainerType,
                    entityOwner,message }
        DESCRIPTION "RVG promoted to primary (migrate)"
    ::= 6

    clusterRDCActingSecondaryTrap TRAP-TYPE
        ENTERPRISE rdcTraps
        VARIABLES { severityId, eventTime, entityName, entityType,
		    entitySubType, entityState, trapOrigin, systemName,
		    systemLocation, entityContainerName, entityContainerType,
                    entityOwner,message }
        DESCRIPTION "Cannot promote, RVG is acting_secondary"
    ::= 7

    clusterRDCResyncFailedTrap TRAP-TYPE
        ENTERPRISE rdcTraps
        VARIABLES { severityId, eventTime, entityName, entityType,
		    entitySubType, entityState, trapOrigin, systemName,
		    systemLocation, entityContainerName, entityContainerType,
                    entityOwner,message }
        DESCRIPTION "Resync failed"
    ::= 8

    clusterRDCResyncSuccessTrap TRAP-TYPE
        ENTERPRISE rdcTraps
        VARIABLES { severityId, eventTime, entityName, entityType,
		    entitySubType, entityState, trapOrigin, systemName,
		    systemLocation, entityContainerName, entityContainerType,
                    entityOwner,message }
        DESCRIPTION "Resync completed successfully"
    ::= 9

    clusterRDCGroupOfflineTrap TRAP-TYPE
        ENTERPRISE rdcTraps
        VARIABLES { severityId, eventTime, entityName, entityType,
		    entitySubType, entityState, trapOrigin, systemName,
		    systemLocation, entityContainerName, entityContainerType,
                    entityOwner,message }
        DESCRIPTION "(violation) Offlining group"
    ::= 10

END
