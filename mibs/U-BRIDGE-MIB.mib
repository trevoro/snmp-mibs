-- extracted from draft-ietf-bridge-rstpmib-01.txt
-- at Tue Nov 27 06:07:10 2001

U-BRIDGE-MIB DEFINITIONS ::= BEGIN

-- -------------------------------------------------------------
-- MIB for IEEE 802.1u Restricted Group Registration
-- -------------------------------------------------------------

IMPORTS
    MODULE-IDENTITY, OBJECT-TYPE, NOTIFICATION-TYPE
        FROM SNMPv2-SMI
    TruthValue, MacAddress
        FROM SNMPv2-TC
    MODULE-COMPLIANCE, OBJECT-GROUP, NOTIFICATION-GROUP
        FROM SNMPv2-CONF
    dot1dBridge, dot1dBasePort, dot1dBasePortEntry
        FROM BRIDGE-MIB
    dot1qPvid, dot1qVlan
        FROM Q-BRIDGE-MIB
    dot1dGmrp
        FROM P-BRIDGE-MIB;

uBridgeMIB MODULE-IDENTITY
    LAST-UPDATED "200111160000Z"
    ORGANIZATION "IETF Bridge MIB Working Group"
    CONTACT-INFO
        "Email: Bridge-mib@ietf.org"
    DESCRIPTION
        "The Bridge MIB Extension module for managing devices
         that allow control over dynamic VLAN registration through
         Restricted VLAN Registration as defined by IEEE 802.1u."
    REVISION     "200111160000Z"
    DESCRIPTION
         "Draft 1"
    ::= { dot1dBridge 12 }

-- -------------------------------------------------------------
-- Augmentation to the dot1dGmrpTable
-- -------------------------------------------------------------

dot1dExtPortGmrpTable OBJECT-TYPE
    SYNTAX      SEQUENCE OF Dot1dExtPortGmrpEntry
    MAX-ACCESS  not-accessible
    STATUS      current
    DESCRIPTION
        "A table containing per port Restricted Group Registration
         control information."
    ::= { dot1dGmrp 2 }

dot1dExtPortGmrpEntry OBJECT-TYPE
    SYNTAX      Dot1dExtPortGmrpEntry
    MAX-ACCESS  not-accessible
    STATUS      current
    DESCRIPTION
        "Information controlling Group Registration for a port
         on the device.  This is indexed by dot1dBasePort."
    AUGMENTS { dot1dBasePortEntry }
    ::= { dot1dExtPortGmrpTable 1 }

Dot1dExtPortGmrpEntry ::=
    SEQUENCE {
        dot1dPortRestrictedGroupRegistration
            TruthValue,
        dot1dPortLastGroupFailed
            MacAddress,
        dot1dPortGmrpFailingReason
            INTEGER
    }

dot1dPortRestrictedGroupRegistration OBJECT-TYPE
    SYNTAX      TruthValue
    MAX-ACCESS  read-write
    STATUS      current
    DESCRIPTION
        "The state of Restricted Group Registration on this port.
         If the value of this control is true(1), then creation
         of a new dynamic entry is permitted only if there is a
         Static Filtering Entry for the VLAN concerned, in which
         the Registrar Administrative Control value is Normal
         Registration."
    REFERENCE
        "IEEE 802.1t clause 10.3.2.3, 14.10.1.3."
    DEFVAL      { false }
    ::= { dot1dExtPortGmrpEntry 1 }

dot1dPortLastGroupFailed OBJECT-TYPE
    SYNTAX      MacAddress
    MAX-ACCESS  accessible-for-notify
    STATUS      current
    DESCRIPTION
        "The MAC address of the Group GMRP failed to register
         on this port.  This object is accessible only through
         gmrpFailure notification."
    REFERENCE
        "IEEE 802.1t clause 14.10.1.2.3a."
    ::= { dot1dExtPortGmrpEntry 2 }

dot1dPortGmrpFailingReason OBJECT-TYPE
    SYNTAX      INTEGER {
                    lackOfResources(1),
                    registrationRestricted(2)
                }
    MAX-ACCESS  accessible-for-notify
    STATUS      current
    DESCRIPTION
        "The reason for the last registration failure on this
         port.  The value 'lackofResources(1)' indicates that
         GMRP failed due to lack of resources in the Filtering
         Database for the creation of a Group Registration
         Entry.  The value 'registrationRestricted(2)'
         indicates that GMRP failed because dynamic group is
         restricted.  This object is accessible only through
         gmrpFailure notification."
    REFERENCE
         "IEEE 802.1t clause 14.10.1.2.3c."
    ::= { dot1dExtPortGmrpEntry 3 }

-- -------------------------------------------------------------
-- Augmentation to the dot1qPortVlanTable
-- -------------------------------------------------------------

dot1qExtPortVlanTable OBJECT-TYPE
    SYNTAX      SEQUENCE OF Dot1qExtPortVlanEntry
    MAX-ACCESS  not-accessible
    STATUS      current
    DESCRIPTION
        "A table containing per port Restricted VLAN Registration
         control information."
    ::= { dot1qVlan 11 }

dot1qExtPortVlanEntry OBJECT-TYPE
    SYNTAX      Dot1qExtPortVlanEntry
    MAX-ACCESS  not-accessible
    STATUS      current
    DESCRIPTION
        "Information controlling VLAN Registration for a port
         on the device.  This is indexed by dot1dBasePort."
    AUGMENTS { dot1dBasePortEntry }
    ::= { dot1qExtPortVlanTable 1 }

Dot1qExtPortVlanEntry ::=
    SEQUENCE {
        dot1qPortRestrictedVlanRegistration
            TruthValue,
        dot1qPortGvrpFailingReason
            INTEGER
    }

dot1qPortRestrictedVlanRegistration OBJECT-TYPE
    SYNTAX      TruthValue
    MAX-ACCESS  read-write
    STATUS      current
    DESCRIPTION
        "The state of Restricted VLAN Registration on this port.
         If the value of this control is true(1), then creation
         of a new dynamic VLAN entry is permitted only if there
         is a Static VLAN Registration Entry for the VLAN concerned,
         in which the Registrar Administrative Control value for
         this port is Normal Registration."
    REFERENCE
        "IEEE 802.1u clause 11.2.3.2.3, 12.10.1.7."
    DEFVAL      { false }
    ::= { dot1qExtPortVlanEntry 1 }

dot1qPortGvrpFailingReason OBJECT-TYPE
    SYNTAX      INTEGER {
                    lackOfResources(1),
                    registrationRestricted(2),
                    unsupportedVID(3)
                }
    MAX-ACCESS  accessible-for-notify
    STATUS      current
    DESCRIPTION
        "The reason for the last registration failure on this
         port.  The value 'lackofResources(1)' indicates that
         GVRP failed due to lack of resources in the Filtering
         Database for the creation of a VLAN Registration
         Entry.  The value 'registrationRestricted(2)' indicates
         that GVRP failed because dynamic VLAN registration is
         restricted.  And the value 'unsupportedVID(3)'
         indicates that a registration request for an
         unsupported VID is received."
    REFERENCE
         "IEEE 802.1u clause 12.10.1.6.3c."
    ::= { dot1qExtPortVlanEntry 2 }


-- Traps for Registration Failures

gmrpFailure NOTIFICATION-TYPE
    OBJECTS   { dot1dPortLastGroupFailed,
                dot1dBasePort,
                dot1dPortGmrpFailingReason }

    STATUS      current
    DESCRIPTION
        "The trap that is generated when there is a GMRP
         failure.  dot1dPortLastGroupFailed indicates the
         MAC address of the Group that has failed to be
         registered, dot1dBasePort indicates the port on
         which the registration is received, and
         dot1dPortGmrpFailingReason indicates the reason for
         the failure."
    REFERENCE
        "IEEE 802.1t 14.10.1.2."
    ::= { dot1dBridge 0 3 }

gvrpFailure NOTIFICATION-TYPE
    OBJECTS   { dot1qPvid,
                dot1dBasePort,
                dot1qPortGvrpFailingReason }
    STATUS      current
    DESCRIPTION
        "The trap that is generated when there is a GVRP
         failure.  dot1qPvid indicates the VID of he VLAN
         that GVRP has failed to register, dot1dBasePort
         indicates the port on which the registration is
         received, and dot1qPortGvrpFailingReason indicates
         the reason for the failure."
    REFERENCE
        "IEEE 802.1t 12.10.1.6."
    ::= { dot1dBridge 0 4 }

-- -------------------------------------------------------------
-- uBridgeMIB - Conformance Information
-- -------------------------------------------------------------

uBridgeConformance OBJECT IDENTIFIER ::= { uBridgeMIB 1 }

uBridgeGroups OBJECT IDENTIFIER ::= { uBridgeConformance 1 }

uBridgeCompliances OBJECT IDENTIFIER ::= { uBridgeConformance 2 }

-- -------------------------------------------------------------
-- Units of conformance
-- -------------------------------------------------------------

uBridgePortVlanGroup OBJECT-GROUP
    OBJECTS {
        dot1qPortRestrictedVlanRegistration,
        dot1qPortGvrpFailingReason
    }
    STATUS      current
    DESCRIPTION
        "Per-port Restricted VLAN Registration Control parameter"
    ::= { uBridgeGroups 1 }

uBridgePortGmrpGroup OBJECT-GROUP
    OBJECTS {
        dot1dPortRestrictedGroupRegistration,
        dot1dPortLastGroupFailed,
        dot1dPortGmrpFailingReason
    }
    STATUS      current
    DESCRIPTION
        "Per-port Restricted Group Registration Control parameter"
    ::= { uBridgeGroups 2 }

uBridgeTrapGroup NOTIFICATION-GROUP
    NOTIFICATIONS {
        gmrpFailure,
        gvrpFailure
    }
    STATUS      current
    DESCRIPTION
        "GMRP and GVRP notifications"
    ::= { uBridgeGroups 3 }

-- -------------------------------------------------------------
-- Compliance statements
-- -------------------------------------------------------------

uBridgeCompliance MODULE-COMPLIANCE
    STATUS      current
    DESCRIPTION
        "The compliance statement for device support of bridging
         services."

    MODULE
        GROUP uBridgePortVlanGroup
        DESCRIPTION
            "Support for this object group is optional."

        GROUP uBridgePortGmrpGroup
        DESCRIPTION
            "Support for this object group is optional."

        GROUP uBridgeTrapGroup
        DESCRIPTION
            "Support for this notification group is optional."
    ::= { uBridgeCompliances 1 }

END
