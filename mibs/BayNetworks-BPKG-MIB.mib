--BPKG mib file for BAC PktGen
--Created  4/22/98  cying      Initial version.

BayNetworks-BPKG-MIB DEFINITIONS ::= BEGIN
 
 
    IMPORTS
 
      Counter
        FROM RFC1155-SMI
      OBJECT-TYPE
        FROM RFC-1212
      DisplayString
        FROM RFC1213-MIB
      wfBacPktGenGroup
        FROM Wellfleet-COMMON-MIB;


    wfBacPktGenBase	OBJECT IDENTIFIER ::= { wfBacPktGenGroup 1 }

    wfBacPktGenDelete OBJECT-TYPE
        SYNTAX	INTEGER {
    		    created(1),
    		    deleted(2)
    		}
        ACCESS	read-write
        STATUS	mandatory
        DESCRIPTION
		"Create/Delete parameter. Default is created.
		Users perform a set operation on this object
		in order to create/delete BAC PktGen."
        DEFVAL	{ created }
        ::= { wfBacPktGenBase 1 }

    wfBacPktGenDisable OBJECT-TYPE
        SYNTAX	INTEGER {
    		    enabled(1),
    		    disabled(2)
    		}
        ACCESS	read-write
        STATUS	mandatory
        DESCRIPTION
		"Enable/Disable parameter.  Default is disabled.
		Users perform a set operation on this object
		in order to enable/disable BAC PktGen."
        DEFVAL	{ disabled }
        ::= { wfBacPktGenBase 2 }

    wfBacPktGenState OBJECT-TYPE
        SYNTAX	INTEGER {
    		    up(1),
    		    down(2),
		    init(3),
		    notpresent(4)
    		}
        ACCESS	read-only
        STATUS	mandatory
        DESCRIPTION
		"The current state of the entire BAC PktGen:
		      up         - BAC PktGen is sending and 
		                   receiving frames;
		      down       - BAC PktGen is disabled;
		      init       - BAC PktGen is initializing;
		      notpresent - BAC PktGen is not present.
		"
        DEFVAL	{ notpresent }
        ::= { wfBacPktGenBase 3 }

    wfBacPktGenTxTabSum OBJECT-TYPE
        SYNTAX	Counter
        ACCESS	read-only
        STATUS	mandatory
        DESCRIPTION
		"Total number of TXTAB records added to CXP's."
        ::= { wfBacPktGenBase 4 }

    wfBacPktGenRxTabSum OBJECT-TYPE
        SYNTAX	Counter
        ACCESS	read-only
        STATUS	mandatory
        DESCRIPTION
		"Total number of RXTAB records added to CXP's."
        ::= { wfBacPktGenBase 5 }


----------------------------------------------------------------------
--
-- end of wfBacPktGenBase
--
----------------------------------------------------------------------
     
    wfBacPktGenCxpTable	OBJECT-TYPE
        SYNTAX	SEQUENCE OF WfBacPktGenCxpEntry
	ACCESS	not-accessible
        STATUS	mandatory
        DESCRIPTION
		"The BAC PktGen CXP table contains relevant
		information concerning packet generation on
		each CXP.

		Note that, the processing of PktGen CXP
		entries supercedes that of 
		wfBacPktGenCxpGlobal MIB record."
	::= { wfBacPktGenGroup 2 }

    wfBacPktGenCxpEntry OBJECT-TYPE
        SYNTAX	WfBacPktGenCxpEntry
        ACCESS	not-accessible
        STATUS	mandatory
        DESCRIPTION
		"Information concerning packet generation on
		the CXP."
	INDEX { wfBacPktGenCxpId }
	::= { wfBacPktGenCxpTable 1 }

    WfBacPktGenCxpEntry ::= SEQUENCE {
    	    wfBacPktGenCxpDelete
    		INTEGER,
    	    wfBacPktGenCxpId
    		INTEGER,
    	    wfBacPktGenStreamMask
    		Counter
        }

    wfBacPktGenCxpDelete OBJECT-TYPE
        SYNTAX	INTEGER {
    		    created(1),
    		    deleted(2)
    		}
        ACCESS	read-write
        STATUS	mandatory
        DESCRIPTION
		"Create/Delete parameter. Default is created.
		Users perform a set operation on this object
		in order to create/delete BAC PktGen CXP table
		entry."
        DEFVAL	{ created }
        ::= { wfBacPktGenCxpEntry 1 }

    wfBacPktGenCxpId OBJECT-TYPE
        SYNTAX	INTEGER(6..8)
        ACCESS	read-only
        STATUS	mandatory
        DESCRIPTION
		"Uniquely identifies the CXP from which test
		packets are generated.  Currently, the CXP
		is identified by its slot number, which
		must be between 6 and 8."
        ::= { wfBacPktGenCxpEntry 2 }

    wfBacPktGenStreamMask OBJECT-TYPE
        SYNTAX	Counter
        ACCESS	read-write
        STATUS	mandatory
        DESCRIPTION
		"Bit mask for generating test packets on
		the CXP streams 1-31.  The least 
		significant bit is ignored.  The second least 
		significant bit represents stream 1, the next 
		least significant bit represents stream 2, 
		and so forth.  The most significant bit
		represents stream 31."
        ::= { wfBacPktGenCxpEntry 3 }


----------------------------------------------------------------------
--
-- end of wfBacPktGenCxpEntry
--
----------------------------------------------------------------------

    wfBacPktGenPktSeed	OBJECT IDENTIFIER ::= { wfBacPktGenGroup 3 }

    wfBacPktGenSeedPkts OBJECT-TYPE
        SYNTAX	INTEGER {
    		    seedpackets(1),
    		    unseedpackets(2)
    		}
        ACCESS	read-write
        STATUS	mandatory
        DESCRIPTION
		"Seed/Unseed packet parameter.  Default is 
		unseedpackets.  Users perform a set operation 
		on this object in order to seed/unseed 
		test packets."
        DEFVAL	{ unseedpackets }
        ::= { wfBacPktGenPktSeed 1 }

    wfBacPktGenPktSeedState OBJECT-TYPE
        SYNTAX	INTEGER {
    		    packetseeded(1),
    		    packetunseeded(2),
		    operationstarted(3),
		    idle(4)
    		}
        ACCESS	read-only
        STATUS	mandatory
        DESCRIPTION
		"Based on the set operation performed on the
		Seed/Unseed packet parameter, this object reflects
		the status of the operation.  Default is idle.
		This object goes to the operationstarted state
		as soon as the BAC PktGen application detects the
		set operation on the Seed/Unseed parameter.  The 
		object remains in this state until the operation
		is completed, and the appropriate state is 
		registered."
        DEFVAL	{ idle }
        ::= { wfBacPktGenPktSeed 2 }


----------------------------------------------------------------------
--
-- end of wfBacPktGenPktSeed
--
----------------------------------------------------------------------

    wfBacPktGenCxpGlobal	OBJECT IDENTIFIER ::= { wfBacPktGenGroup 4 }

    wfBacPktGenCxpGlobalDelete OBJECT-TYPE
        SYNTAX	INTEGER {
    		    created(1),
    		    deleted(2)
    		}
        ACCESS	read-write
        STATUS	mandatory
        DESCRIPTION
		"Create/Delete parameter. Default is created.
		Users perform a set operation on this object
		in order to create/delete BAC PktGen CXP Global 
		record.
	
		Note that, the PktGen Global record is processed
		as long as no wfBacPktGenCxpEntry MIB records
		exist.  When one or more wfBacPktGenCxpEntry MIB 
		records are configured, the PktGen CXP Global record 
		is ignored and its processing is disabled."
        DEFVAL	{ created }
        ::= { wfBacPktGenCxpGlobal 1 }

    wfBacPktGenGlobalStreamMask OBJECT-TYPE
        SYNTAX	Counter
        ACCESS	read-write
        STATUS	mandatory
        DESCRIPTION
		"Bit mask for generating test packets on
		all CXP streams 1-31.  The least 
		significant bit is ignored.  The second least 
		significant bit represents stream 1, the next 
		least significant bit represents stream 2, 
		and so forth.  The most significant bit
		represents stream 31."
        ::= { wfBacPktGenCxpGlobal 2 }

    wfBacPktGenGlobalRecActive OBJECT-TYPE
        SYNTAX	INTEGER {
		    active(1),
		    inactive(2)
		}
        ACCESS	read-only
        STATUS	mandatory
        DESCRIPTION
		"Indicates if the processing of this MIB record
		is active.  It is active only when NO
		wfBacPktGenCxpEntry MIB record is configured."
        DEFVAL	{ inactive }
        ::= { wfBacPktGenCxpGlobal 3 }


----------------------------------------------------------------------
--
-- end of wfBacPktGenCxpGlobal
--
----------------------------------------------------------------------

    wfBacPktGenCctTable	OBJECT-TYPE
        SYNTAX	SEQUENCE OF WfBacPktGenCctEntry
	ACCESS	not-accessible
        STATUS	mandatory
        DESCRIPTION
		"The BAC PktGen Circuit table."
	::= { wfBacPktGenGroup 5 }

    wfBacPktGenCctEntry OBJECT-TYPE
        SYNTAX	WfBacPktGenCctEntry
        ACCESS	not-accessible
        STATUS	mandatory
        DESCRIPTION
		"Information concerning a BAC PktGen circuit 
		table entry."
	INDEX { wfBacPktGenCctNumber }
	::= { wfBacPktGenCctTable 1 }

    WfBacPktGenCctEntry ::= SEQUENCE {
    	    wfBacPktGenCctDelete
    		INTEGER,
    	    wfBacPktGenCctNumber
    		INTEGER,
    	    wfBacPktGenCctState
    		INTEGER,
    	    wfBacPktGenCctName
    		DisplayString
        }

    wfBacPktGenCctDelete OBJECT-TYPE
        SYNTAX	INTEGER {
    		    created(1),
    		    deleted(2)
    		}
        ACCESS	read-write
        STATUS	mandatory
        DESCRIPTION
		"Create/Delete parameter. Default is created.
		Users perform a set operation on this object
		in order to create/delete BAC PktGen Circuit 
		table entry."
        DEFVAL	{ created }
        ::= { wfBacPktGenCctEntry 1 }

    wfBacPktGenCctNumber OBJECT-TYPE
        SYNTAX	INTEGER
        ACCESS	read-only
        STATUS	mandatory
        DESCRIPTION
                "BAC PktGen circuit number."
        ::= { wfBacPktGenCctEntry 2 }

    wfBacPktGenCctState OBJECT-TYPE
        SYNTAX	INTEGER {
    		    up(1),
    		    down(2),
    		    init(3),
    		    notpresent(4)
		}
        ACCESS	read-only
        STATUS	mandatory
        DESCRIPTION
                "The current state of the BAC PktGen circuit:
		      up         - The circuit is up;
		      down       - The circuit is down;
		      init       - The circuit is initializing;
		      notpresent - The circuit is not present.
		"
        DEFVAL	{ notpresent }
        ::= { wfBacPktGenCctEntry 3 }

    wfBacPktGenCctName OBJECT-TYPE
        SYNTAX	DisplayString
        ACCESS	read-write
        STATUS	mandatory
        DESCRIPTION
                "BAC PktGen circuit name."
        ::= { wfBacPktGenCctEntry 4 }

----------------------------------------------------------------------
--
-- end of wfBacPktGenCctEntry 
--
----------------------------------------------------------------------


    wfBacPktGenPktFile	OBJECT IDENTIFIER ::= { wfBacPktGenGroup 6 }

    wfBacPktGenPktFileAppend OBJECT-TYPE
        SYNTAX	INTEGER {
    		    enable(1),
    		    disable(2)
    		}
        ACCESS	read-only
        STATUS	mandatory
        DESCRIPTION
		"Append disable/enable parameter. Default is
		to release previous table contents instead of
		appending to previously processed pkt files.
		This feature is currently not supported."
        DEFVAL	{ disable }
        ::= { wfBacPktGenPktFile 1 }

	wfBacPktGenPktFileName OBJECT-TYPE
		SYNTAX DisplayString
		ACCESS  read-write
		STATUS  mandatory
		DESCRIPTION
		"The user-defined name of the pktfile to process."
		::= { wfBacPktGenPktFile 2 }

----------------------------------------------------------------------
--
-- end of wfBacPktGenPktFile
--
----------------------------------------------------------------------

    wfBacPktGenPktGrpTable	OBJECT-TYPE
        SYNTAX	SEQUENCE OF WfBacPktGenPktGrpEntry
	ACCESS	not-accessible
        STATUS	mandatory
        DESCRIPTION
		"The BAC PktGen packet group table."
	::= { wfBacPktGenGroup 7 }

    wfBacPktGenPktGrpEntry OBJECT-TYPE
        SYNTAX	WfBacPktGenPktGrpEntry
        ACCESS	not-accessible
        STATUS	mandatory
        DESCRIPTION
		"Information concerning a BAC PktGen packet
		group table entry."
	INDEX { wfBacPktGenPktGrpNumber }
	::= { wfBacPktGenPktGrpTable 1 }

    WfBacPktGenPktGrpEntry ::= SEQUENCE {
    	    wfBacPktGenPktGrpNumber
    		INTEGER,
    	    wfBacPktGenPktGrpDelay1
    		INTEGER,
    	    wfBacPktGenPktGrpDelay2
    		INTEGER,
    	    wfBacPktGenPktGrpDelay3
    		INTEGER,
    	    wfBacPktGenPktGrpDelay4
    		INTEGER,
    	    wfBacPktGenPktGrpCount1
    		INTEGER,
    	    wfBacPktGenPktGrpCount2
    		INTEGER,
    	    wfBacPktGenPktGrpCount3
    		INTEGER,
    	    wfBacPktGenPktGrpCount4
    		INTEGER,
    	    wfBacPktGenPktSeedSum
    		Counter,
    	    wfBacPktGenPktGrpCxp
    		INTEGER
        }

    wfBacPktGenPktGrpNumber OBJECT-TYPE
        SYNTAX	INTEGER
        ACCESS	read-only
        STATUS	mandatory
        DESCRIPTION
		"Uniquely identifies the packet group number."
        ::= { wfBacPktGenPktGrpEntry 1 }

    wfBacPktGenPktGrpDelay1 OBJECT-TYPE
        SYNTAX	INTEGER
        ACCESS	read-write
        STATUS	mandatory
        DESCRIPTION
		"Delay parameter 1 for this packet group."
        ::= { wfBacPktGenPktGrpEntry 2 }

    wfBacPktGenPktGrpDelay2 OBJECT-TYPE
        SYNTAX	INTEGER
        ACCESS	read-write
        STATUS	mandatory
        DESCRIPTION
		"Delay parameter 2 for this packet group."
        ::= { wfBacPktGenPktGrpEntry 3 }

    wfBacPktGenPktGrpDelay3 OBJECT-TYPE
        SYNTAX	INTEGER
        ACCESS	read-write
        STATUS	mandatory
        DESCRIPTION
		"Delay parameter 3 for this packet group."
        ::= { wfBacPktGenPktGrpEntry 4 }

    wfBacPktGenPktGrpDelay4 OBJECT-TYPE
        SYNTAX	INTEGER
        ACCESS	read-write
        STATUS	mandatory
        DESCRIPTION
		"Delay parameter 4 for this packet group."
        ::= { wfBacPktGenPktGrpEntry 5 }

    wfBacPktGenPktGrpCount1 OBJECT-TYPE
        SYNTAX	INTEGER
        ACCESS	read-write
        STATUS	mandatory
        DESCRIPTION
		"Count parameter 1 for this packet group."
        ::= { wfBacPktGenPktGrpEntry 6 }

    wfBacPktGenPktGrpCount2 OBJECT-TYPE
        SYNTAX	INTEGER
        ACCESS	read-write
        STATUS	mandatory
        DESCRIPTION
		"Count parameter 2 for this packet group."
        ::= { wfBacPktGenPktGrpEntry 7 }

    wfBacPktGenPktGrpCount3 OBJECT-TYPE
        SYNTAX	INTEGER
        ACCESS	read-write
        STATUS	mandatory
        DESCRIPTION
		"Count parameter 3 for this packet group."
        ::= { wfBacPktGenPktGrpEntry 8 }

    wfBacPktGenPktGrpCount4 OBJECT-TYPE
        SYNTAX	INTEGER
        ACCESS	read-write
        STATUS	mandatory
        DESCRIPTION
		"Count parameter 4 for this packet group."
        ::= { wfBacPktGenPktGrpEntry 9 }

    wfBacPktGenPktSeedSum OBJECT-TYPE
        SYNTAX	Counter
        ACCESS	read-only
        STATUS	mandatory
        DESCRIPTION
		"Total number of packet seeds that belong
		to this packet group."
        ::= { wfBacPktGenPktGrpEntry 10 }

    wfBacPktGenPktGrpCxp OBJECT-TYPE
        SYNTAX	INTEGER
        ACCESS	read-only
        STATUS	mandatory
        DESCRIPTION
		"The eligible CXP slot number on which this
		packet group can be thrown."
        ::= { wfBacPktGenPktGrpEntry 11 }

----------------------------------------------------------------------
--
-- end of wfBacPktGenPktGrpEntry
--
----------------------------------------------------------------------

    wfBacPktGenStrmCtrlTable	OBJECT-TYPE
        SYNTAX	SEQUENCE OF WfBacPktGenStrmCtrlEntry
	ACCESS	not-accessible
        STATUS	mandatory
        DESCRIPTION
		"The BAC PktGen stream control table."
	::= { wfBacPktGenGroup 8 }

    wfBacPktGenStrmCtrlEntry OBJECT-TYPE
        SYNTAX	WfBacPktGenStrmCtrlEntry
        ACCESS	not-accessible
        STATUS	mandatory
        DESCRIPTION
		"Information concerning a BAC PktGen 
		stream control table entry."
	INDEX { wfBacPktGenStrmNumber,
		wfBacPktGenStrmCxp }
	::= { wfBacPktGenStrmCtrlTable 1 }

    WfBacPktGenStrmCtrlEntry ::= SEQUENCE {
    	    wfBacPktGenStrmNumber
    		INTEGER,
    	    wfBacPktGenStrmCxp
    		INTEGER,
    	    wfBacPktGenStrmState
    		INTEGER,
    	    wfBacPktGenSetStrmPktGrp
    		INTEGER,
    	    wfBacPktGenStrmPktGrp
    		INTEGER
        }

    wfBacPktGenStrmNumber OBJECT-TYPE
        SYNTAX	INTEGER(1..31)
        ACCESS	read-only
        STATUS	mandatory
        DESCRIPTION
		"Uniquely identifies the PktGen stream number
		on each CXP."
        ::= { wfBacPktGenStrmCtrlEntry 1 }

    wfBacPktGenStrmCxp OBJECT-TYPE
        SYNTAX	INTEGER(6..8)
        ACCESS	read-only
        STATUS	mandatory
        DESCRIPTION
		"Uniquely identifies the CXP."
        ::= { wfBacPktGenStrmCtrlEntry 2 }

    wfBacPktGenStrmState OBJECT-TYPE
        SYNTAX	INTEGER {
    		    pktgen(1),
		    killed(2),
		    notpresent(4)
    		}
        ACCESS	read-only
        STATUS	mandatory
        DESCRIPTION
		"The current state of this PktGen stream:
		      pktgen     - Stream is transmitting 
		                   test packets;
		      killed     - Stream is being killed;
		      notpresent - Stream is not present.
		"
        DEFVAL	{ notpresent }
        ::= { wfBacPktGenStrmCtrlEntry 3 }

    wfBacPktGenSetStrmPktGrp OBJECT-TYPE
        SYNTAX	INTEGER
        ACCESS	read-write
        STATUS	mandatory
        DESCRIPTION
		"Set the packet group to be thrown by
		this PktGen stream. "
        ::= { wfBacPktGenStrmCtrlEntry 4 }

    wfBacPktGenStrmPktGrp OBJECT-TYPE
        SYNTAX	INTEGER
        ACCESS	read-only
        STATUS	mandatory
        DESCRIPTION
		"The packet group which will be thrown by
		this PktGen stream. "
        ::= { wfBacPktGenStrmCtrlEntry 5 }

----------------------------------------------------------------------
--
-- end of wfBacPktGenStrmCtrlEntry
--
----------------------------------------------------------------------


    END  -- BayNetworks-BPKG-MIB
