Wellfleet-RESOURCE-MIB DEFINITIONS ::= BEGIN

-- Created by mdl2asn version 3.1
-- Creation date: Tue Sep  5 17:05:27 EDT 1995
-- Modified  4/23/98  cying      Added resource for BAC PktGen.


    IMPORTS

      Gauge, Counter
        FROM RFC1155-SMI
      OBJECT-TYPE
        FROM RFC-1212
      DisplayString
        FROM RFC1213-MIB
      wfGameGroup
        FROM Wellfleet-COMMON-MIB;


    wfResourceUseTable OBJECT-TYPE
        SYNTAX  SEQUENCE OF WfResourceUseEntry
        ACCESS  not-accessible
        STATUS  mandatory
        DESCRIPTION
                "Table of Resource Use Statistic entries, indexed by
                entity number and slot number"
        ::= { wfGameGroup 6 }

    wfResourceUseEntry OBJECT-TYPE
        SYNTAX  WfResourceUseEntry
        ACCESS  not-accessible
        STATUS  mandatory
        DESCRIPTION
                "A particular entity's resource use statistics on a slot"
        INDEX   { wfResourceUseEntity,
                  wfResourceUseSlot }
        ::= { wfResourceUseTable 1 }

    WfResourceUseEntry ::= SEQUENCE {
            wfResourceUseEntity
                INTEGER,
            wfResourceUseSlot
                INTEGER,
            wfResourceUseEntityName
                DisplayString,
            wfResourceUseCpu
                INTEGER,
            wfResourceUseMemory
                Gauge,
            wfResourceUseBuffers
                Gauge
        }

    wfResourceUseEntity OBJECT-TYPE
        SYNTAX  INTEGER {
                    kernel(1),
                    enet2(2),
                    qenet(3),
                    fddi(4),
                    dsde2(5),
                    qsync(6),
                    dtok(7),
                    dst(8),
                    t1(9),
                    e1(10),
                    hssi(11),
                    lance(12),
                    ilacc(13),
                    fsi(14),
                    tms380(15),
                    hdlc(16),
                    ds2180(17),
                    ds2181(18),
                    hwf(19),
                    hfsi(20),
                    ip(21),
                    drs(22),
                    vines(23),
                    at(24),
                    xns(25),
                    ipx(26),
                    osi(27),
                    x25(28),
                    fr(29),
                    rarp(30),
                    atmdxi(31),
                    dls(32),
                    arp(33),
                    tftp(34),
                    snmp(35),
                    tn(36),
                    tcp(37),
                    bgp(38),
                    egp(39),
                    ospf(40),
                    wan(41),
                    llc(42),
                    lnm(43),
                    ppp(44),
                    pcap(45),
                    mct1e1(46),
                    munich(47),
                    quicsync(48),
                    hilance(49),
                    asnmod(50),
                    lapb(51),
                    efddi(52),
                    hlsin(53),
                    debug(54),
                    frswcngc(55),
                    swmgr(56),
                    mct1(57),
                    municht1(58),
                    frswmap(59),
                    atm(60),
                    atmalc(61),
                    nbase(62),
                    sdlc(63),
                    nbip(64),
                    dvmrp(65),
                    igmp(66),
                    isdn(67),
                    lm(68),
                    ping(69),
                    appnls(70),
                    appncp(71),
                    wcp(72),
                    isac(73),
                    chipcom(74),
                    ftp(75),
                    smdssw(76),
                    hdwanlm(77),
                    sysl(78),
                    atmcmod(79),
                    bgprs(80),
                    crm(81),
                    st2(82),
                    dcmmw(83),
                    nsc100m(84),
                    de100(85),
                    nlsp(86),
                    hwcomp(87),
                    stats(88),
                    atmzdrv(89),
                    ipex(90),
                    npt(91),
                    rredund(92),
                    atmsig(93),
                    atmle(94),
                    atmc5000(95),
                    ip6(96),
                    bot(97),
                    pim(98),
                    lbc(99),
                    atmmcs(100),
                    atmasm(101),
                    cpm(102),
                    baysig(103),
                    scmipc(104),
                    ntp(105),
                    raesa(106),
                    radius(107),
                    hdwancop(108),
	                rcmds(109),
		            dns(110),
                    fnts(111),
                    fntsatm(112),
		            wep(113),
		            rip6(114),
                    frsvc(115),
		            aot(116),
                    mospf(117),
                    rsvp(118),
                    nat(119),
                    frpt(120),
                    http(121),
                    stacppp(122),
                    asr(123),
                    nhrp(124),
                    ahb(125),
                    l2tp(126),
                    isdb(127),
                    vcct(128),
                    rmonstat(129),
                    tag1q(130),
                    mps(131),
                    mpc(132),
                    dvs(133),
                    vrrp(134),
                    dhcp(135),
                    capi(136),
                    ipsec(137),
                    mplsLdp(138),
                    mplsMlm(139),
                    hid(140), 
                    scd(141), 
                    iftab(142),
                    gns(143),
                    acct(144),
                    bpkg(145),
                    bacdmux(146),
                    atmtp(147),
                    ifpdrv(148),
                    amd100m(149),
                    iisis(150),
                    sqe100(151),
                    seeq100m(152),
                    gigenet(153),
                    sgig(154),
                    diffserv(155),
                    copsc(156),
                    ike(157),
                    bcc(158),
                    tdmmgr(159),
                    pq2dsync(160),
		    voip(161),
		    dsqms(162),
                    qscop(163)
                }

        ACCESS  read-only
        STATUS  mandatory
        DESCRIPTION
                "The entity number is the first index"
        ::= { wfResourceUseEntry 1 }

    wfResourceUseSlot OBJECT-TYPE
        SYNTAX  INTEGER
        ACCESS  read-only
        STATUS  mandatory
        DESCRIPTION
                "The slot number is the second index"
        ::= { wfResourceUseEntry 2 }

    wfResourceUseEntityName OBJECT-TYPE
        SYNTAX  DisplayString
        ACCESS  read-only
        STATUS  mandatory
        DESCRIPTION
                "The name of the entity"
        ::= { wfResourceUseEntry 3 }

    wfResourceUseCpu OBJECT-TYPE
        SYNTAX  INTEGER
        ACCESS  read-only
        STATUS  mandatory
        DESCRIPTION
                "The amount of CPU used by the entity on this slot
                in centiseconds since the slot started"
        ::= { wfResourceUseEntry 4 }

    wfResourceUseMemory OBJECT-TYPE
        SYNTAX  Gauge
        ACCESS  read-only
        STATUS  mandatory
        DESCRIPTION
                "The current number of bytes of memory used by the
                entity on this slot"
        ::= { wfResourceUseEntry 5 }

    wfResourceUseBuffers OBJECT-TYPE
        SYNTAX  Gauge
        ACCESS  read-only
        STATUS  mandatory
        DESCRIPTION
                "The current number of buffers used by the entity
                on this slot"
        ::= { wfResourceUseEntry 6 }

    wfResourceTotalTable OBJECT-TYPE
        SYNTAX  SEQUENCE OF WfResourceTotalEntry
        ACCESS  not-accessible
        STATUS  mandatory
        DESCRIPTION
                "Table of Total Resource Use Statistics
                indexed by slot number"
        ::= { wfGameGroup 7 }

    wfResourceTotalEntry OBJECT-TYPE
        SYNTAX  WfResourceTotalEntry
        ACCESS  not-accessible
        STATUS  mandatory
        DESCRIPTION
                "A particular slot's total resource use statistics"
        INDEX   { wfResourceTotalSlot }
        ::= { wfResourceTotalTable 1 }

    WfResourceTotalEntry ::= SEQUENCE {
            wfResourceTotalSlot
                INTEGER,
            wfResourceTotalCpuUsed
                Counter,
            wfResourceTotalCpuIdle
                Counter,
            wfResourceTotalCpuMax
                Counter,
            wfResourceTotalMemoryUsed
                Gauge,
            wfResourceTotalMemoryFree
                Gauge,
            wfResourceTotalMemoryMax
                Gauge,
            wfResourceTotalBuffersUsed
                Gauge,
            wfResourceTotalBuffersFree
                Gauge,
            wfResourceTotalBuffersMax
                Gauge
        }

    wfResourceTotalSlot OBJECT-TYPE
        SYNTAX  INTEGER
        ACCESS  read-only
        STATUS  mandatory
        DESCRIPTION
                "The slot number is the index"
        ::= { wfResourceTotalEntry 1 }

    wfResourceTotalCpuUsed OBJECT-TYPE
        SYNTAX  Counter
        ACCESS  read-only
        STATUS  mandatory
        DESCRIPTION
                "The amount of CPU used by all the entities on this
                slot in centiseconds since the slot started"
        ::= { wfResourceTotalEntry 2 }

    wfResourceTotalCpuIdle OBJECT-TYPE
        SYNTAX  Counter
        ACCESS  read-only
        STATUS  mandatory
        DESCRIPTION
                "The amount of Idle CPU on this slot in centiseconds
                since the slot started"
        ::= { wfResourceTotalEntry 3 }

    wfResourceTotalCpuMax OBJECT-TYPE
        SYNTAX  Counter
        ACCESS  read-only
        STATUS  mandatory
        DESCRIPTION
                "The maximum amount of CPU time possible on this slot
                in centiseconds since the slot started"
        ::= { wfResourceTotalEntry 4 }

    wfResourceTotalMemoryUsed OBJECT-TYPE
        SYNTAX  Gauge
        ACCESS  read-only
        STATUS  mandatory
        DESCRIPTION
                "The current number of bytes of memory used by all the
                entities on the slot"
        ::= { wfResourceTotalEntry 5 }

    wfResourceTotalMemoryFree OBJECT-TYPE
        SYNTAX  Gauge
        ACCESS  read-only
        STATUS  mandatory
        DESCRIPTION
                "The current number of bytes of free memory on the
                slot"
        ::= { wfResourceTotalEntry 6 }

    wfResourceTotalMemoryMax OBJECT-TYPE
        SYNTAX  Gauge
        ACCESS  read-only
        STATUS  mandatory
        DESCRIPTION
                "The maximum amount of Memory available in bytes
                on the slot"
        ::= { wfResourceTotalEntry 7 }

    wfResourceTotalBuffersUsed OBJECT-TYPE
        SYNTAX  Gauge
        ACCESS  read-only
        STATUS  mandatory
        DESCRIPTION
                "The current number of buffers used by all the
                entities on the slot"
        ::= { wfResourceTotalEntry 8 }

    wfResourceTotalBuffersFree OBJECT-TYPE
        SYNTAX  Gauge
        ACCESS  read-only
        STATUS  mandatory
        DESCRIPTION
                "The current number of free buffers on the slot"
        ::= { wfResourceTotalEntry 9 }

    wfResourceTotalBuffersMax OBJECT-TYPE
        SYNTAX  Gauge
        ACCESS  read-only
        STATUS  mandatory
        DESCRIPTION
                "The maximum number of buffers on the slot"
        ::= { wfResourceTotalEntry 10 }

    END  -- Wellfleet-RESOURCE-MIB
