--
-- ***** Passport Frame Relay Access Device MIB File - CSU Interfaces  *****
--
-- Based on CSU Requirements documents (T1, E1, 56K).
-- MIB module applicable to Software versions beginning with Release 3.0.
-- 
-- MIB Revision : 1.0 dated 6/1/98
-- Change Desc. : Initial submittal - R. Carmona, A. Llanes, S. Gaur. 
-- 
-- MIB Revision : 1.1 dated 6/11/98
-- Change Desc. : Revised CSU MIB as per Chien Lee's request:
--                Moved mcmT1E1CsuCfgDS0Connection to the end of 
--                mcmT1E1CsuCfgTable.  Changed the 
--                mcmE1CsuGenStatusLnCdViolations object name to
--				  mcmE1CsuGenStatusBpvOrLnCdViolations. - A. Llanes
-- 
-- MIB Revision : 1.2 dated 7/02/98
-- Change Desc. : Revised CSU MIB as per Nina Tranle's request:
-- 				  Due to the CLI unable to support imported indices,
--				  imported ifindex has been removed and an ifindex
--				  object has been added to each table. 
--				  Note:  This revision has caused OID's to change. 
--						 This revision has caused the traps' ifindex
--						 variable OID to change. - A. Llanes
-- MIB Revision : 1.3 dated 11/17/98
-- Change Desc. : Removed all "56k" from mcm56kCsuCfgTable and mcm56kCsuStatusTable.
--                This change fixed the issue of duplicated names in mcm56kcsu.mib
--                and mcmcsu.mib.

MICOM-CSU-MIB DEFINITIONS ::= BEGIN

IMPORTS

	OBJECT-TYPE
		FROM RFC-1212
	mcmSysAsciiTimeOfDay
		FROM MICOM-SYS-MIB
	TRAP-TYPE
		FROM RFC-1215
	DisplayString 
		FROM SNMPv2-TC
	micom-oscar 
		FROM MICOM-OSCAR-MIB;


-- group OBJECT IDENTIFIERs

	micom-csu			OBJECT IDENTIFIER ::= {micom-oscar 29}
	csu-configuration	OBJECT IDENTIFIER ::= {micom-csu 1}
	csu-status			OBJECT IDENTIFIER ::= {micom-csu 2}


--  the T1/E1 CSU Configuration Table
--  This table provides the T1/E1 CSU configuration parameters.

mcmT1E1CsuCfgTable OBJECT-TYPE
    SYNTAX  SEQUENCE OF McmT1E1CsuCfgEntry
    ACCESS  not-accessible
    STATUS  mandatory
    DESCRIPTION
      "NAME = ;
           DESC = The T1/E1 CSU Configuration table.;
       HELP = ;
           CAPABILITIES = NET_CFG, VPN_CFG;"
    ::= { csu-configuration 1 }

mcmT1E1CsuCfgEntry OBJECT-TYPE
    SYNTAX  McmT1E1CsuCfgEntry
    ACCESS  not-accessible
    STATUS  mandatory
    DESCRIPTION
      "NAME = ;
           DESC = An entry in the T1/E1 CSU Configuration \
                  table.;
           HELP = ;
           CAPABILITIES = ;"
    INDEX   { mcmT1E1CsuCfgifIndex }
    ::= { mcmT1E1CsuCfgTable 1 }

McmT1E1CsuCfgEntry ::= SEQUENCE {
	mcmT1E1CsuCfgifIndex			INTEGER,
    mcmT1E1CsuCfgLineType			INTEGER,
    mcmT1E1CsuCfgLineSpeed		INTEGER,
    mcmT1E1CsuCfgLineBuildOut		INTEGER,
    mcmT1E1CsuCfgTxIdleCode		INTEGER,
    mcmT1E1CsuCfgTxRxClkSource  	INTEGER,
    mcmT1E1CsuCfgDS0BasicRate		INTEGER,
    mcmT1E1CsuCfgLocalLoopback		INTEGER,
    mcmT1E1CsuCfgRemoteLoopback		INTEGER,
    mcmT1E1CsuCfgFramerLoopback  	INTEGER,
    mcmT1E1CsuCfgTrapEnable		INTEGER,
    mcmT1E1CsuCfgFrameFmt		INTEGER,
    mcmT1E1CsuCfgTxRx0CodeSuppress	INTEGER,
    mcmT1E1CsuCfgTxB7ZeroSuppress	INTEGER,
    mcmT1E1CsuCfgPayloadLoopback	INTEGER,
    mcmT1E1CsuCfgTransmitLoopUp		INTEGER,
    mcmT1E1CsuCfgTransmitLoopDown	INTEGER,
    mcmT1E1CsuCfgTxRxHDB3		INTEGER,
    mcmT1E1CsuCfgTxRxCRC4		INTEGER,
    mcmT1E1CsuCfgDS0Connection		DisplayString
    }

mcmT1E1CsuCfgifIndex OBJECT-TYPE
	SYNTAX	INTEGER (1..255)
	ACCESS	read-only
	STATUS	mandatory
	DESCRIPTION
	  "NAME = ;
	   DESC = The T1E1 Csu Cfg interface index \
				value of the specifc entry.;
	   HELP = ;
	   CAPABILITIES = ;"
	::= { mcmT1E1CsuCfgEntry 1 }

mcmT1E1CsuCfgLineType OBJECT-TYPE
	SYNTAX	INTEGER {
		t1Csu (1),
		e1Csu (2)
		}
	ACCESS	read-only
	STATUS	mandatory
	DESCRIPTION
	  "NAME = ;
	   DESC = The value of this object determines  \
		  whether the line is a T1 CSU or E1 CSU.;
	   HELP = ;
	   CAPABILITIES = ;"
	::= { mcmT1E1CsuCfgEntry 2 }

mcmT1E1CsuCfgLineSpeed OBJECT-TYPE
	SYNTAX	INTEGER {
		ls-1ds0Times64K-64K (1),
		ls-2ds0Times64K-128K (2),
		ls-3ds0Times64K-192K (3),
		ls-4ds0Times64K-256K (4),
		ls-5ds0Times64K-320K (5),
		ls-6ds0Times64K-384K (6),
		ls-7ds0Times64K-448K (7),
		ls-8ds0Times64K-512K (8),
		ls-9ds0Times64K-576K (9),
		ls-10ds0Times64K-640K (10),
		ls-11ds0Times64K-704K (11),
		ls-12ds0Times64K-768K (12),
		ls-13ds0Times64K-832K (13),
		ls-14ds0Times64K-896K (14),
		ls-15ds0Times64K-960K (15),
		ls-16ds0Times64K-1024K (16),
		ls-17ds0Times64K-1088K (17),
		ls-18ds0Times64K-1152K (18),
		ls-19ds0Times64K-1216K (19),
		ls-20ds0Times64K-1280K (20),
		ls-21ds0Times64K-1344K (21),
		ls-22ds0Times64K-1408K (22),
		ls-23ds0Times64K-1472K (23),
		ls-24ds0Times64K-1536K (24),
		ls-25ds0Times64K-1600K (25),
		ls-26ds0Times64K-1664K (26),
		ls-27ds0Times64K-1728K (27),
		ls-28ds0Times64K-1792K (28),
		ls-29ds0Times64K-1856K (29),
		ls-30ds0Times64K-1920K (30),
		ls-1ds0Times56K-56K (31),
		ls-2ds0Times56K-112K (32),
		ls-3ds0Times56K-168K (33),
		ls-4ds0Times56K-224K (34),
		ls-5ds0Times56K-280K (35),
		ls-6ds0Times56K-336K (36),
		ls-7ds0Times56K-392K (37),
		ls-8ds0Times56K-448K (38),
		ls-9ds0Times56K-504K (39),
		ls-10ds0Times56K-560K (40),
		ls-11ds0Times56K-616K (41),
		ls-12ds0Times56K-672K (42),
		ls-13ds0Times56K-728K (43),
		ls-14ds0Times56K-784K (44),
		ls-15ds0Times56K-840K (45),
		ls-16ds0Times56K-896K (46),
		ls-17ds0Times56K-952K (47),
		ls-18ds0Times56K-1008K (48),
		ls-19ds0Times56K-1064K (49),
		ls-20ds0Times56K-1120K (50),
		ls-21ds0Times56K-1176K (51),
		ls-22ds0Times56K-1232K (52),
		ls-23ds0Times56K-1288K (53),
		ls-24ds0Times56K-1344K (54),
		ls-25ds0Times56K-1400K (55),
		ls-26ds0Times56K-1456K (56),
		ls-27ds0Times56K-1512K (57),
		ls-28ds0Times56K-1568K (58),
		ls-29ds0Times56K-1624K (59),
		ls-30ds0Times56K-1680K (60),
		idle (61)
		}
	ACCESS	read-only
	STATUS	mandatory
	DESCRIPTION
	  "NAME = ;
	   DESC = The value of this object indicates the T1/E1 CSU \
		  total configured DS0 line speed.;
	   HELP = ;
	   CAPABILITIES = ;"
	::= { mcmT1E1CsuCfgEntry 3 }

mcmT1E1CsuCfgLineBuildOut OBJECT-TYPE
	SYNTAX	INTEGER {
		dist-0-133-feet (1),
		dist-133-266-feet (2),
		dist-266-399-feet (3),
		dist-399-533-feet (4),
		dist-533-655-feet (5),
		neg-7pt5-db (6),
		neg-15-db (7),
		neg-22pt5-db (8),
		ohm-75-normal (9),
		ohm-120-normal (10),
		ohm-75-protection-resistors (11),
		ohm-120-protection-resistors (12),
		ohm-75-high-return-loss-1-1pt15-step-up (13),
		ohm-75-high-return-loss-1-1pt36-step-up (14),
		ohm-120-high-return-loss-1-1pt36-step-up (15)
		}
	ACCESS	read-write
	STATUS	mandatory
	DESCRIPTION
	  "NAME = ;
	   DESC = The value of this object selects the T1/E1 CSU \
		  line build out.  For a T1 CSU, the default value \
		  is neg-7pt5-db (6).  For an E1 CSU, the default \
		  value is either ohm-75-normal (9) (an E1 CSU interface \
		  with 2 BNC connectors) or ohm-120-normal (10) \
		  (an E1 CSU interface with an RJ48 connector). \
		  Note that the ranges of enumeration values 1-8 and \
		  9-15 apply uniquely to T1 and E1 interfaces; respectively.;
	   HELP = ;
	   CAPABILITIES = ;"
	::= { mcmT1E1CsuCfgEntry 4 }

mcmT1E1CsuCfgTxIdleCode OBJECT-TYPE
	SYNTAX	INTEGER (0..'ff'h)
	ACCESS	read-write
	STATUS	mandatory
	DESCRIPTION
	  "NAME = ;
	   DESC = The value of this object selects the T1/E1 CSU \
		  transmit idle code. For a T1 CSU, the default value is \
		  hex 0x7F. For an E1 CSU, the default value is hex 0x55.;
	   HELP = ;
	   CAPABILITIES = ;"
	::= { mcmT1E1CsuCfgEntry 5 }

mcmT1E1CsuCfgTxRxClkSource OBJECT-TYPE
	SYNTAX	INTEGER {
		internalClockingSource (1),
		externalClockingSource (2)
		}
	ACCESS	read-write
	STATUS	mandatory
	DESCRIPTION
	  "NAME = ;
	   DESC = The value of this object selects the T1/E1 CSU \
		  line clocking source.;
	   HELP = ;
	   CAPABILITIES = ;"
	DEFVAL { externalClockingSource }
	::= { mcmT1E1CsuCfgEntry 6 }

mcmT1E1CsuCfgDS0BasicRate OBJECT-TYPE
	SYNTAX	INTEGER {
		br64K-basicRate (1),
		br56K-basicRate (2)
		}
	ACCESS	read-write
	STATUS	mandatory
	DESCRIPTION
	  "NAME = ;
	   DESC = The value of this object selects the T1/E1 CSU \
		  line speed to be a multiple of the specified \
		  basic rate.  E.g., Line Speed 256K = 4 x 64K.;
	   HELP = ;
	   CAPABILITIES = ;"
	DEFVAL { br64K-basicRate }
	::= { mcmT1E1CsuCfgEntry 7 }

mcmT1E1CsuCfgLocalLoopback OBJECT-TYPE
	SYNTAX	INTEGER {
		disable (1),
		enable (2)
		}
	ACCESS	read-write
	STATUS	mandatory
	DESCRIPTION
	  "NAME = ;
	   DESC = The value of this object selects the T1/E1 CSU \
		  local loopback.;
	   HELP = ;
	   CAPABILITIES = ;"
	DEFVAL { disable }
	::= { mcmT1E1CsuCfgEntry 8 }

mcmT1E1CsuCfgRemoteLoopback OBJECT-TYPE
	SYNTAX	INTEGER {
		disable (1),
		enable (2)
		}
	ACCESS	read-write
	STATUS	mandatory
	DESCRIPTION
	  "NAME = ;
	   DESC = The value of this object selects the T1/E1 CSU \
		  remote loopback.;
	   HELP = ;
	   CAPABILITIES = ;"
	DEFVAL { disable }
	::= { mcmT1E1CsuCfgEntry 9 }

mcmT1E1CsuCfgFramerLoopback OBJECT-TYPE
	SYNTAX	INTEGER {
		disable (1),
		enable (2)
		}
	ACCESS	read-write
	STATUS	mandatory
	DESCRIPTION
	  "NAME = ;
	   DESC = The value of this object selects the T1/E1 CSU \
		  framer loopback.;
	   HELP = ;
	   CAPABILITIES = ;"
	DEFVAL { disable }
	::= { mcmT1E1CsuCfgEntry 10 }

mcmT1E1CsuCfgTrapEnable OBJECT-TYPE
	SYNTAX	INTEGER {
		disable (1),
		enable (2)
		}
	ACCESS	read-write
	STATUS	mandatory
	DESCRIPTION
	  "NAME = ;
	   DESC = The value of this object selects whether the T1/E1 \
		  CSU traps should be generated for this interface.;
	   HELP = ;
	   CAPABILITIES = ;"
	DEFVAL { enable }
	::= { mcmT1E1CsuCfgEntry 11 }

mcmT1E1CsuCfgFrameFmt OBJECT-TYPE
	SYNTAX	INTEGER {
		d4FramingMode (1),
		esfFramingMode (2)
		}
	ACCESS	read-write
	STATUS	mandatory
	DESCRIPTION
	  "NAME = ;
	   DESC = The value of this object selects the T1 CSU \
		  frame format. \
		  Note that for an E1 CSU interface, this object is not used.;
	   HELP = ;
	   CAPABILITIES = ;"
	DEFVAL { esfFramingMode }
	::= { mcmT1E1CsuCfgEntry 12 }

mcmT1E1CsuCfgTxRx0CodeSuppress OBJECT-TYPE
	SYNTAX	INTEGER {
		disable-b8zs (1),
		enable-b8zs (2)
		}
	ACCESS	read-write
	STATUS	mandatory
	DESCRIPTION
	  "NAME = ;
	   DESC = The value of this object selects zero \
		  code suppression for a T1 CSU interface. \
		  Note that for an E1 CSU interface, this object is not used.;
	   HELP = ;
	   CAPABILITIES = ;"
	DEFVAL { enable-b8zs }
	::= { mcmT1E1CsuCfgEntry 13 }

mcmT1E1CsuCfgTxB7ZeroSuppress OBJECT-TYPE
	SYNTAX	INTEGER {
		disable-b7zs (1),
		enable-b7zs (2)
		}
	ACCESS	read-write
	STATUS	mandatory
	DESCRIPTION
	  "NAME = ;
	   DESC = The value of this object selects bit 7 zero\
		  suppression for a T1 CSU interface.  Selects stuffing \
		  bit 7 to 1 if 8 consecutive zeros occurred. \
		  Note that for an E1 CSU interface, this object is not used.;
	   HELP = b7zsDisable (1): no stuffing occurred. \
		  b7zsEnable (2): bit 7 forced to a one in \
		  channels with all zeros.;
	   CAPABILITIES = ;"
	DEFVAL { disable-b7zs }
	::= { mcmT1E1CsuCfgEntry 14 }

mcmT1E1CsuCfgPayloadLoopback OBJECT-TYPE
	SYNTAX	INTEGER {
		disable (1),
		enable (2)
		}
	ACCESS	read-write
	STATUS	mandatory
	DESCRIPTION
	  "NAME = ;
	   DESC = The value of this object selects the T1 CSU \
		  payload loopback. \
		  Note that for an E1 CSU interface, this object is not used.;
	   HELP = ;
	   CAPABILITIES = ;"
	DEFVAL { disable }
	::= { mcmT1E1CsuCfgEntry 15 }

mcmT1E1CsuCfgTransmitLoopUp OBJECT-TYPE
	SYNTAX	INTEGER {
		disable (1),
		enable (2)
		}
	ACCESS	read-write
	STATUS	mandatory
	DESCRIPTION
	  "NAME = ;
	   DESC = The value of this object selects the T1 CSU \
		  transmit loop up. \
		  Note that for an E1 CSU interface, this object is not used.;
	   HELP = ;
	   CAPABILITIES = ;"
	DEFVAL { disable }
	::= { mcmT1E1CsuCfgEntry 16 }

mcmT1E1CsuCfgTransmitLoopDown OBJECT-TYPE
	SYNTAX	INTEGER {
		disable (1),
		enable (2)
		}
	ACCESS	read-write
	STATUS	mandatory
	DESCRIPTION
	  "NAME = ;
	   DESC = The value of this object selects the T1 CSU \
		  transmit loop down. \
		  Note that for an E1 CSU interface, this object is not used.;
	   HELP = ;
	   CAPABILITIES = ;"
	DEFVAL { disable }
	::= { mcmT1E1CsuCfgEntry 17 }

mcmT1E1CsuCfgTxRxHDB3	 OBJECT-TYPE
	SYNTAX	INTEGER {
		disable (1),
		enable  (2)
		}
	ACCESS	read-write
	STATUS	mandatory
	DESCRIPTION
	  "NAME = ;
	   DESC = The value of this object selects the E1 CSU HDB3. \
		  Note that for a T1 CSU interface, this object is not used.;
	   HELP = ;
	   CAPABILITIES = ;"
	DEFVAL { enable }
	::= { mcmT1E1CsuCfgEntry 18 }

mcmT1E1CsuCfgTxRxCRC4	 OBJECT-TYPE
	SYNTAX	INTEGER {
		disable (1),
		enable  (2)
		}
	ACCESS	read-write
	STATUS	mandatory
	DESCRIPTION
	  "NAME = ;
	   DESC = The value of this object selects the E1 CSU CRC4. \
		  Note that for a T1 CSU interface, this object is not used.;
	   HELP = ;
	   CAPABILITIES = ;"
	DEFVAL { disable }
	::= { mcmT1E1CsuCfgEntry 19 }

mcmT1E1CsuCfgDS0Connection OBJECT-TYPE
	SYNTAX	DisplayString (SIZE (0..83))
	ACCESS	read-write
	STATUS	mandatory
	DESCRIPTION
	  "NAME = ;
	   DESC = The value of this object selects the DS0 \
		  channels for the T1/E1 CSU line connection. \
		  Valid characters are decimal digits, comma \
		  (','), and hyphen ('-').;
	   HELP = Comma (',') is used as a delimiter between \
		  individual channel selections. \
		  e.g., 13,16 means DS0 channels 13 and 16. \
		  Hyphen ('-') is used only in Set operations \
		  to indicate a range of DS0 channels. \
		  e.g., 2,5-8 means DS0 channels 2,5,6,7, and 8.;
	   CAPABILITIES = ;"
	DEFVAL { "" }
	::= { mcmT1E1CsuCfgEntry 20 }



--  the 56K CSU Configuration Table 
--  This table provides the 56K CSU configuration parameters.

mcmCsuCfgTable  OBJECT-TYPE
    SYNTAX  SEQUENCE OF McmCsuCfgEntry
    ACCESS  not-accessible
    STATUS  mandatory
    DESCRIPTION
      "NAME = ;
           DESC = The 56K CSU Configuration table.;
       HELP = ;
           CAPABILITIES = NET_CFG, VPN_CFG;"
    ::= { csu-configuration 2 }

mcmCsuCfgEntry OBJECT-TYPE
    SYNTAX  McmCsuCfgEntry
    ACCESS  not-accessible
    STATUS  mandatory
    DESCRIPTION
      "NAME = ;
           DESC = An entry in the 56K CSU Configuration \
                  table.);
           HELP = ;
           CAPABILITIES = ;"
    INDEX   { mcmCsuCfgifIndex }
    ::= { mcmCsuCfgTable 1 }

McmCsuCfgEntry ::= SEQUENCE {
	mcmCsuCfgifIndex				INTEGER,
    mcmCsuCfgOperatingMode		INTEGER,
    mcmCsuCfgClockingSource		INTEGER,
    mcmCsuCfgTxOutOfFrame		INTEGER,
    mcmCsuCfgTxOutOfService		INTEGER,
    mcmCsuCfgTxControlModeIdle  	INTEGER,
    mcmCsuCfgZeroSuppressDisable 	INTEGER,
    mcmCsuCfgTxIdle			INTEGER,
    mcmCsuCfgCSULoopback		INTEGER,
    mcmCsuCfgFilterForceEnable  	INTEGER,
    mcmCsuCfgFilterForcingCntl   	INTEGER
    }

mcmCsuCfgifIndex OBJECT-TYPE
	SYNTAX	INTEGER (1..255)
	ACCESS	read-only
	STATUS	mandatory
	DESCRIPTION
	  "NAME = ;
	   DESC = The 56k Csu Cfg interface index \
				value of the specifc entry.;
	   HELP = ;
	   CAPABILITIES = ;"
	::= { mcmCsuCfgEntry 1 }

mcmCsuCfgOperatingMode OBJECT-TYPE
	SYNTAX	INTEGER {
		dds-pri-4Wire-56k (1),
		dds-sc-WithSecondaryChannel-72k (2),
		cc-64k-ClearChannel-64k (3),
		dds-pri-2Wire-56k (4)
		}
	ACCESS	read-write
	STATUS	mandatory	
	DESCRIPTION
	  "NAME = ;
	   DESC = The value of this object selects the 56K CSU \
		  operating mode.;
	   HELP = ;
	   CAPABILITIES = ;"
	DEFVAL { dds-pri-4Wire-56k }
	::= { mcmCsuCfgEntry 2 }

mcmCsuCfgClockingSource OBJECT-TYPE
	SYNTAX	INTEGER {
		externalClock (1),
		internalClock (2)
		}
	ACCESS	read-write
	STATUS	mandatory	
	DESCRIPTION
	  "NAME = ;
	   DESC = The value of this object selects the 56K CSU \
		  clocking source.;
	   HELP = ;
	   CAPABILITIES = ;"
	DEFVAL { externalClock }
	::= { mcmCsuCfgEntry 3 }

mcmCsuCfgTxOutOfFrame OBJECT-TYPE
	SYNTAX	INTEGER {
		normalTransmitCondition (1),
		transmitOutOfFrame (2)
		}
	ACCESS	read-write
	STATUS	mandatory
	DESCRIPTION
	  "NAME = ;
	   DESC = This object selects transmission of the 56K CSU \
		  Out Of Frame sequence for DDS-PRI mode, or \
		  transmission of Multiplexer Out Of Sync \
		  sequence for DDS-SC mode.;
	   HELP = ;
	   CAPABILITIES = ;"
	DEFVAL { normalTransmitCondition }
	::= { mcmCsuCfgEntry 4 }

mcmCsuCfgTxOutOfService OBJECT-TYPE
	SYNTAX	INTEGER {
		normalTransmitCondition (1),
		transmitOutOfService (2)
		}
	ACCESS	read-write
	STATUS	mandatory	
	DESCRIPTION
	  "NAME = ;
	   DESC = This object selects transmission of the 56K CSU \
		  Out Of Service sequence for DDS-PRI mode, or \
		  transmission of Abnormal Station Code \
		  sequence for DDS-SC mode.;
	   HELP = ;
	   CAPABILITIES = ;"
	DEFVAL { normalTransmitCondition }
	::= { mcmCsuCfgEntry 5 }

mcmCsuCfgTxControlModeIdle OBJECT-TYPE
	SYNTAX	INTEGER {
		normalTransmitCondition (1),
		transmitControlModeIdle (2)
		}
	ACCESS	read-write
	STATUS	mandatory	
	DESCRIPTION
	  "NAME = ;
	   DESC = This object selects transmission of the 56K CSU \
		  Control Mode Idle sequence.;
	   HELP = ;
	   CAPABILITIES = ;"
	DEFVAL { normalTransmitCondition }
	::= { mcmCsuCfgEntry 6 }

mcmCsuCfgZeroSuppressDisable OBJECT-TYPE
	SYNTAX	INTEGER {
		normalTransmitCondition (1),
		zeroSuppressionDisable (2)
		}
	ACCESS	read-write
	STATUS	mandatory	
	DESCRIPTION
	  "NAME = ;
	   DESC = This object selects the 56K CSU disable \
		  transmit Zero Suppression for DDS-PRI mode, \
		  or transmission of all zeros for DDS-SC mode.;
	   HELP = ;
	   CAPABILITIES = ;"
	DEFVAL { normalTransmitCondition }
	::= { mcmCsuCfgEntry 7 }

mcmCsuCfgTxIdle OBJECT-TYPE
	SYNTAX	INTEGER {
		normalTransmitCondition (1),
		transmitIdle (2)
		}
	ACCESS	read-write
	STATUS	mandatory
	DESCRIPTION
	  "NAME = ;
	   DESC = This object selects transmission of the 56K CSU \
		  All Marks (or 1s) of the Data Mode Idle sequence \
		  for all the modes.;
	   HELP = ;
	   CAPABILITIES = ;"
	DEFVAL { normalTransmitCondition }
	::= { mcmCsuCfgEntry 8 }

mcmCsuCfgCSULoopback OBJECT-TYPE
	SYNTAX	INTEGER {
		normalReceiveCondition (1),
		forceCSUtoLoopback (2)
		}
	ACCESS	read-write
	STATUS	mandatory
	DESCRIPTION
	  "NAME = ;
	   DESC = This object selects the 56K CSU to force the CSU \
		  to be in a loopback mode.;
	   HELP = ;
	   CAPABILITIES = ;"
	DEFVAL { normalReceiveCondition }
	::= { mcmCsuCfgEntry 9 }

mcmCsuCfgFilterForceEnable OBJECT-TYPE
	SYNTAX	INTEGER {
		normalReceiveCondition (1),
		filterForceEnable (2)
		}
	ACCESS	read-write
	STATUS	mandatory
	DESCRIPTION
	  "NAME = ;
	   DESC = This object selects the 56K CSU to have \
		  filter forcing enabled or not.;
	   HELP = ;
	   CAPABILITIES = ;"
	DEFVAL { normalReceiveCondition }
	::= { mcmCsuCfgEntry 10 }

mcmCsuCfgFilterForcingCntl OBJECT-TYPE
	SYNTAX	INTEGER {
		fg90db-FilterGain (1),
		fg84db-FilterGain (2),
		fg78db-FilterGain (3),
		fg72db-FilterGain (4),
		fg66db-FilterGain (5),
		fg60db-FilterGain (6),
		fg54db-FilterGain (7),
		fg48db-FilterGain (8),
		fg42db-FilterGain (9),
		fg36db-FilterGain (10),
		fg30db-FilterGain (11),
		fg24db-FilterGain (12),
		fg18db-FilterGain (13),
		fg12db-FilterGain (14),
		fg6db-FilterGain (15),
		fg0db-FilterGain (16)
		}
	ACCESS	read-write
	STATUS	mandatory
	DESCRIPTION
	  "NAME = ;
	   DESC = This object selects the 56K CSU filter \
		  gain if filter force is enabled.;
	   HELP = ;
	   CAPABILITIES = ;"
	DEFVAL { fg0db-FilterGain }
	::= { mcmCsuCfgEntry 11 }



--  the T1/E1 CSU Control Register Status Table 
--  This table provides the T1/E1 CSU Control Register status parameters. 

mcmT1E1CsuCntlRegStatusTable OBJECT-TYPE
    SYNTAX  SEQUENCE OF McmT1E1CsuCntlRegStatusEntry
    ACCESS  not-accessible
    STATUS  mandatory
    DESCRIPTION
      "NAME = ;
           DESC = The T1/E1 CSU Control Register Status \
           table.;
       HELP = ;
           CAPABILITIES = NET_DISP, VPN_DISP;"
    ::= {  csu-status 1 }

mcmT1E1CsuCntlRegStatusEntry OBJECT-TYPE
    SYNTAX  McmT1E1CsuCntlRegStatusEntry
    ACCESS  not-accessible
    STATUS  mandatory
    DESCRIPTION
      "NAME = ;
           DESC = An entry in the T1/E1 CSU Control Register \
                  Status table.;
           HELP = ;
           CAPABILITIES = ;"
    INDEX   { mcmT1E1CSUStatusifIndex }
    ::= { mcmT1E1CsuCntlRegStatusTable 1 }

McmT1E1CsuCntlRegStatusEntry ::= SEQUENCE {
	mcmT1E1CSUStatusifIndex			INTEGER,
    mcmT1E1CSUStatusCntlReg1		INTEGER,
    mcmT1E1CSUStatusCntlReg2		INTEGER,
    mcmT1E1CSUStatusCntlReg3		INTEGER,
    mcmT1E1CSUStatusCntlReg4		INTEGER,
    mcmT1E1CSUStatusCntlReg5		INTEGER,
    mcmT1E1CSUStatusCntlReg6		INTEGER,
    mcmT1E1CSUStatusCntlReg7		INTEGER,
    mcmT1E1CSUStatusCntlReg8		INTEGER,
    mcmT1E1CSUStatusCntlReg9		INTEGER,
    mcmT1E1CSUStatusCntlReg10		INTEGER
    }

mcmT1E1CSUStatusifIndex OBJECT-TYPE
	SYNTAX	INTEGER (1..255)
	ACCESS	read-only
	STATUS	mandatory
	DESCRIPTION
	  "NAME = ;
	   DESC = The T1E1 CSU Status interface index \
				value of the specifc entry.;
	   HELP = ;
	   CAPABILITIES = ;"
	::= { mcmT1E1CsuCntlRegStatusEntry 1 }

mcmT1E1CSUStatusCntlReg1 OBJECT-TYPE
	SYNTAX	INTEGER (0..255)
	ACCESS	read-only
	STATUS	mandatory
	DESCRIPTION
	  "NAME = ;
	   DESC = The value of this object indicates RCR1, the \
		  value of Receive Control Register 1 for a T1/E1 \
		  CSU line type.;
	   HELP = ;
	   CAPABILITIES =;"
	::= { mcmT1E1CsuCntlRegStatusEntry 2 }

mcmT1E1CSUStatusCntlReg2 OBJECT-TYPE
	SYNTAX	INTEGER (0..255)
	ACCESS	read-only
	STATUS	mandatory
	DESCRIPTION
	  "NAME = ;
	   DESC = The value of this object indicates RCR2, the \
		  value of Receive Control Register 2 for a T1/E1 \
		  CSU line type.;
	   HELP = ;
	   CAPABILITIES =;"
	::= { mcmT1E1CsuCntlRegStatusEntry 3 }

mcmT1E1CSUStatusCntlReg3 OBJECT-TYPE
	SYNTAX	INTEGER (0..255)
	ACCESS	read-only
	STATUS	mandatory
	DESCRIPTION
	  "NAME = ;
	   DESC = The value of this object indicates TCR1, the \
		  value of Transmit Control Register 1 for a T1/E1 \
		  CSU line type.;
	   HELP = ;
	   CAPABILITIES =;"
	::= { mcmT1E1CsuCntlRegStatusEntry 4 }

mcmT1E1CSUStatusCntlReg4 OBJECT-TYPE
	SYNTAX	INTEGER (0..255)
	ACCESS	read-only
	STATUS	mandatory
	DESCRIPTION
	  "NAME = ;
	   DESC = The value of this object indicates TCR2, the \
		  value of Transmit Control Register 2 for a T1/E1 \
		  CSU line type.;
	   HELP = ;
	   CAPABILITIES =;"
	::= { mcmT1E1CsuCntlRegStatusEntry 5 }

mcmT1E1CSUStatusCntlReg5 OBJECT-TYPE
	SYNTAX	INTEGER (0..255)
	ACCESS	read-only
	STATUS	mandatory
	DESCRIPTION
	  "NAME = ;
	   DESC = The value of this object indicates CCR1, the \
		  value of Common Control Register 1 for a T1/E1 \
		  CSU line type.;
	   HELP = ;
	   CAPABILITIES =;"
	::= { mcmT1E1CsuCntlRegStatusEntry 6 }

mcmT1E1CSUStatusCntlReg6 OBJECT-TYPE
	SYNTAX	INTEGER (0..255)
	ACCESS	read-only
	STATUS	mandatory
	DESCRIPTION
	  "NAME = ;
	   DESC = The value of this object indicates CCR2, the \
		  value of Common Control Register 2 for a T1/E1 \
		  CSU line type.;
	   HELP = ;
	   CAPABILITIES =;"
	::= { mcmT1E1CsuCntlRegStatusEntry 7 }

mcmT1E1CSUStatusCntlReg7 OBJECT-TYPE
	SYNTAX	INTEGER (0..255)
	ACCESS	read-only
	STATUS	mandatory
	DESCRIPTION
	  "NAME = ;
	   DESC = The value of this object indicates CCR3, the \
		  value of Common Control Register 3 for a T1/E1 \
		  CSU line type.;
	   HELP = ;
	   CAPABILITIES =;"
	::= { mcmT1E1CsuCntlRegStatusEntry 8 }

mcmT1E1CSUStatusCntlReg8 OBJECT-TYPE
	SYNTAX	INTEGER (0..255)
	ACCESS	read-only
	STATUS	mandatory
	DESCRIPTION
	  "NAME = ;
	   DESC = The value of this object indicates LICR, the value of \
		  the Line Interface Control Register for a T1 CSU line type.\
		  The value of this object indicates CCR4, the value of \
		  Common Control Register 4 for an E1 line type.;
	   HELP = ;
	   CAPABILITIES =;"
	::= { mcmT1E1CsuCntlRegStatusEntry 9 }

mcmT1E1CSUStatusCntlReg9 OBJECT-TYPE
	SYNTAX	INTEGER (0..255)
	ACCESS	read-only
	STATUS	mandatory
	DESCRIPTION
	  "NAME = ;
	   DESC = The value of this object indicates CCR5, the \
		  value of Common Control Register 5 for an E1 CSU \
		  line type. \
		  Note that for a T1 CSU interface, this object is not used.;
	   HELP = ;
	   CAPABILITIES =;"
	::= { mcmT1E1CsuCntlRegStatusEntry 10 }

mcmT1E1CSUStatusCntlReg10 OBJECT-TYPE
	SYNTAX	INTEGER (0..255)
	ACCESS	read-only
	STATUS	mandatory
	DESCRIPTION
	  "NAME = ;
	   DESC = The value of this object indicates LICR, the \
		  value of the Line Interface Control Register for \
		  an E1 CSU line type. \
		  Note that for a T1 CSU interface, this object is not used.;
	   HELP = ;
	   CAPABILITIES =;"
	::= { mcmT1E1CsuCntlRegStatusEntry 11 }



--  the T1 CSU General Status and Statistics Table 
--  This table provides the T1 CSU general status and statistics parameters. 

mcmT1CsuGenStatusTable OBJECT-TYPE
    SYNTAX  SEQUENCE OF McmT1CsuGenStatusEntry
    ACCESS  not-accessible
    STATUS  mandatory
    DESCRIPTION
      "NAME = ;
           DESC = The T1 CSU General Status and \
           Statistics table.;
       HELP = ;
           CAPABILITIES = NET_DISP, VPN_DISP;"
    ::= {  csu-status 2 }

mcmT1CsuGenStatusEntry OBJECT-TYPE
    SYNTAX  McmT1CsuGenStatusEntry
    ACCESS  not-accessible
    STATUS  mandatory
    DESCRIPTION
      "NAME = ;
           DESC = An entry in the T1 CSU General \
                  Status and Statistics table.;
           HELP = ;
           CAPABILITIES = ;"
    INDEX   { mcmT1CsuGenStatusifIndex }
    ::= { mcmT1CsuGenStatusTable 1 }

McmT1CsuGenStatusEntry ::= SEQUENCE {
	mcmT1CsuGenStatusifIndex			INTEGER,
    mcmT1CsuGenStatusLineStatus			INTEGER,
    mcmT1CsuGenStatusRedAlarm			INTEGER,
    mcmT1CsuGenStatusYellowAlarm 		INTEGER,
    mcmT1CsuGenStatusBlueAlarm			INTEGER,
    mcmT1CsuGenStatusRxLevel			INTEGER,
    mcmT1CsuGenStatusRxElasStrFull		INTEGER,
    mcmT1CsuGenStatusRxElasStrEmpty		INTEGER,
    mcmT1CsuGenStatusRxPlsDensViolate		INTEGER,
    mcmT1CsuGenStatusTxPlsDensViolate		INTEGER,
    mcmT1CsuGenStatusRxCarrierLoss		INTEGER,
    mcmT1CsuGenStatusRxSyncLoss 		INTEGER,
    mcmT1CsuGenStatusLnCdViolations	  	INTEGER,
    mcmT1CsuGenStatusRxLoopUpCdDetect 		INTEGER,
    mcmT1CsuGenStatusRxLoopDnCdDetect  		INTEGER
    }

mcmT1CsuGenStatusifIndex OBJECT-TYPE
	SYNTAX	INTEGER (1..255)
	ACCESS	read-only
	STATUS	mandatory
	DESCRIPTION
	  "NAME = ;
	   DESC = The T1 CSU General Status interface \
				index value of the specifc entry.;
	   HELP = ;
	   CAPABILITIES = ;"
	::= { mcmT1CsuGenStatusEntry 1 }

mcmT1CsuGenStatusLineStatus OBJECT-TYPE
	SYNTAX	INTEGER {
		operational (1),
		alarmMode (2),
		testMode (3)
		}
	ACCESS	read-only
	STATUS	mandatory
	DESCRIPTION
	  "NAME = ;
	   DESC = The value of this object indicates the \
		  T1 CSU line status.;
	   HELP = ;
	   CAPABILITIES = ;"
	::= { mcmT1CsuGenStatusEntry 2 }

mcmT1CsuGenStatusRedAlarm OBJECT-TYPE
	SYNTAX	INTEGER {
		redAlarm (1),
		noRedAlarm (2)
		}
	ACCESS	read-only
	STATUS	mandatory
	DESCRIPTION
	  "NAME = ;
	   DESC = The value of this object indicates the \
		  T1 CSU red alarm status.;
	   HELP = ;
	   CAPABILITIES = ;"
	::= { mcmT1CsuGenStatusEntry 3 }

mcmT1CsuGenStatusYellowAlarm OBJECT-TYPE
	SYNTAX	INTEGER {
		yellowAlarm (1),
		noYellowAlarm (2)
		}
	ACCESS	read-only
	STATUS	mandatory
	DESCRIPTION
	  "NAME = ;
	   DESC = The value of this object indicates the \
		  T1 CSU yellow alarm status.;
	   HELP = ;
	   CAPABILITIES = ;"
	::= { mcmT1CsuGenStatusEntry 4 }

mcmT1CsuGenStatusBlueAlarm OBJECT-TYPE
	SYNTAX	INTEGER {
		blueAlarm (1),
		noBlueAlarm (2)
		}
	ACCESS	read-only
	STATUS	mandatory
	DESCRIPTION
	  "NAME = ;
	   DESC = The value of this object indicates the \
		  T1 CSU blue alarm status.;
	   HELP = ;
	   CAPABILITIES = ;"
	::= { mcmT1CsuGenStatusEntry 5 }

mcmT1CsuGenStatusRxLevel OBJECT-TYPE
	SYNTAX	INTEGER {
		plus2db-to-neg7pt5db (1),
		neg7pt5db-to-neg15db (2),
		neg15db-to-neg22pt5db (3),
		lessThan-neg22pt5db (4)
		}
	ACCESS	read-only
	STATUS	mandatory
	DESCRIPTION
	  "NAME = ;
	   DESC = The value of this object indicates the T1 \
		  CSU line receive level status.;
	   HELP = ;
	   CAPABILITIES = ;"
	::= { mcmT1CsuGenStatusEntry 6 }

mcmT1CsuGenStatusRxElasStrFull OBJECT-TYPE
	SYNTAX	INTEGER {
		yes (1),
		no (2)
		}
	ACCESS	read-only
	STATUS	mandatory
	DESCRIPTION
	  "NAME = ;
	   DESC = The value of this object indicates the T1 \
		  CSU receive elastic store full status.;
	   HELP = ;
	   CAPABILITIES = ;"
	::= { mcmT1CsuGenStatusEntry 7 }

mcmT1CsuGenStatusRxElasStrEmpty OBJECT-TYPE
	SYNTAX	INTEGER {
		yes (1),
		no (2)
		}
	ACCESS	read-only
	STATUS	mandatory
	DESCRIPTION
	  "NAME = ;
	   DESC = The value of this object indicates the T1 \
		  CSU receive elastic store empty status.;
	   HELP = ;
	   CAPABILITIES = ;"
	::= { mcmT1CsuGenStatusEntry 8 }

mcmT1CsuGenStatusRxPlsDensViolate OBJECT-TYPE
	SYNTAX	INTEGER {
		yes (1),
		no (2)
		}
	ACCESS	read-only
	STATUS	mandatory
	DESCRIPTION
	  "NAME = ;
	   DESC = The value of this object indicates the T1 \
		  CSU receive pulse density violation status.;
	   HELP = ;
	   CAPABILITIES = ;"
	::= { mcmT1CsuGenStatusEntry 9 }

mcmT1CsuGenStatusTxPlsDensViolate OBJECT-TYPE
	SYNTAX	INTEGER {
		yes (1),
		no (2)
		}
	ACCESS	read-only
	STATUS	mandatory
	DESCRIPTION
	  "NAME = ;
	   DESC = The value of this object indicates the T1 \
		  CSU transmit pulse density violation status.;
	   HELP = ;
	   CAPABILITIES = ;"
	::= { mcmT1CsuGenStatusEntry 10 }

mcmT1CsuGenStatusRxCarrierLoss OBJECT-TYPE
	SYNTAX	INTEGER {
		yes (1),
		no (2)
		}
	ACCESS	read-only
	STATUS	mandatory
	DESCRIPTION
	  "NAME = ;
	   DESC = The value of this object indicates the T1 \
		  CSU receive carrier loss status.;
	   HELP = ;
	   CAPABILITIES = ;"
	::= { mcmT1CsuGenStatusEntry 11 }

mcmT1CsuGenStatusRxSyncLoss OBJECT-TYPE
	SYNTAX	INTEGER {
		yes (1),
		no (2)
		}
	ACCESS	read-only
	STATUS	mandatory
	DESCRIPTION
	  "NAME = ;
	   DESC = The value of this object indicates the T1 \
		  CSU receive loss of sync status.;
	   HELP = ;
	   CAPABILITIES = ;"
	::= { mcmT1CsuGenStatusEntry 12 }

mcmT1CsuGenStatusLnCdViolations OBJECT-TYPE
	SYNTAX	INTEGER (0..65535)
	ACCESS	read-only
	STATUS	mandatory
	DESCRIPTION
	  "NAME = ;
	   DESC = The value of this object indicates the number \
		  of T1 CSU line code violations. \
		  Note that this is a 16-bit counter.;
	   HELP = ;
	   CAPABILITIES = ;"
	::= { mcmT1CsuGenStatusEntry 13 }

mcmT1CsuGenStatusRxLoopUpCdDetect OBJECT-TYPE
	SYNTAX	INTEGER {
		yes (1),
		no (2)
		}
	ACCESS	read-only
	STATUS	mandatory
	DESCRIPTION
	  "NAME = ;
	   DESC = The value of this object indicates the T1 \
		  CSU receive loop up code status.;
	   HELP = ;
	   CAPABILITIES = ;"
	::= { mcmT1CsuGenStatusEntry 14 }

mcmT1CsuGenStatusRxLoopDnCdDetect OBJECT-TYPE
	SYNTAX	INTEGER {
		yes (1),
		no (2)
		}
	ACCESS	read-only
	STATUS	mandatory
	DESCRIPTION
	  "NAME = ;
	   DESC = The value of this object indicates the T1 \
		  CSU receive loop down code status.;
	   HELP = ;
	   CAPABILITIES = ;"
	::= { mcmT1CsuGenStatusEntry 15 }



--  the E1 CSU General Status and Statistics Table 
--  This table provides the E1 CSU general status and statistics parameters. 

mcmE1CsuGenStatusTable OBJECT-TYPE
    SYNTAX  SEQUENCE OF McmE1CsuGenStatusEntry
    ACCESS  not-accessible
    STATUS  mandatory
    DESCRIPTION
      "NAME = ;
           DESC = The E1 CSU General Status and \
           Statistics table.;
       HELP = ;
           CAPABILITIES = NET_DISP, VPN_DISP;"
    ::= {  csu-status 3 }

mcmE1CsuGenStatusEntry OBJECT-TYPE
    SYNTAX  McmE1CsuGenStatusEntry
    ACCESS  not-accessible
    STATUS  mandatory
    DESCRIPTION
      "NAME = ;
           DESC = An entry in the E1 CSU General \
                  Status and Statistics table.;
           HELP = ;
           CAPABILITIES = ;"
    INDEX   { mcmE1CsuGenStatusifIndex }
    ::= { mcmE1CsuGenStatusTable 1 }

McmE1CsuGenStatusEntry ::= SEQUENCE {
	mcmE1CsuGenStatusifIndex				INTEGER,
    mcmE1CsuGenStatusLineStatus				INTEGER,
    mcmE1CsuGenStatusRedAlarm				INTEGER,
    mcmE1CsuGenStatusRemoteAlarm			INTEGER,
    mcmE1CsuGenStatusAISAlarm				INTEGER,
    mcmE1CsuGenStatusRxCarrierLoss			INTEGER,
    mcmE1CsuGenStatusRxSyncLoss  			INTEGER,
    mcmE1CsuGenStatusTxElasStrFull			INTEGER,
    mcmE1CsuGenStatusTxElasStrEmpty			INTEGER,
    mcmE1CsuGenStatusRxElasStrFull			INTEGER,
    mcmE1CsuGenStatusRxElasStrEmpty			INTEGER,
    mcmE1CsuGenStatusBpvOrLnCdViolations	INTEGER,
    mcmE1CsuGenStatusFASErrors		  		INTEGER,
    mcmE1CsuGenStatusCRC4Errors				INTEGER
    }

mcmE1CsuGenStatusifIndex OBJECT-TYPE
	SYNTAX	INTEGER (1..255)
	ACCESS	read-only
	STATUS	mandatory
	DESCRIPTION
	  "NAME = ;
	   DESC = The E1 CSU General Status interface \
				index value of the specifc entry.;
	   HELP = ;
	   CAPABILITIES = ;"
	::= { mcmE1CsuGenStatusEntry 1 }

mcmE1CsuGenStatusLineStatus OBJECT-TYPE
	SYNTAX	INTEGER {
		operational (1),
		alarmMode (2),
		testMode (3)
		}
	ACCESS	read-only
	STATUS	mandatory
	DESCRIPTION
	  "NAME = ;
	   DESC = The value of this object indicates the \
		  E1 CSU line status.;
	   HELP = ;
	   CAPABILITIES = ;"
	::= { mcmE1CsuGenStatusEntry 2 }

mcmE1CsuGenStatusRedAlarm OBJECT-TYPE
	SYNTAX	INTEGER {
		redAlarm (1),
		noRedAlarm (2)
		}
	ACCESS	read-only
	STATUS	mandatory
	DESCRIPTION
	  "NAME = ;
	   DESC = The value of this object indicates the \
		  E1 CSU red alarm status. It includes both \
		  receive carrier loss and receive loss of sync.;
	   HELP = ;
	   CAPABILITIES = ;"
	::= { mcmE1CsuGenStatusEntry 3 }

mcmE1CsuGenStatusRemoteAlarm OBJECT-TYPE
	SYNTAX	INTEGER {
		remoteAlarm (1),
		noRemoteAlarm (2)
		}
	ACCESS	read-only
	STATUS	mandatory
	DESCRIPTION
	  "NAME = ;
	   DESC = The value of this object indicates the \
		  E1 CSU remote alarm status. It includes both \
		  receive remote alarm and receive distant MF \
		  alarm.;
	   HELP = ;
	   CAPABILITIES = ;"
	::= { mcmE1CsuGenStatusEntry 4 }

mcmE1CsuGenStatusAISAlarm OBJECT-TYPE
	SYNTAX	INTEGER {
		aisAlarm (1),
		noAISAlarm (2)
		}
	ACCESS	read-only
	STATUS	mandatory
	DESCRIPTION
	  "NAME = ;
	   DESC = The value of this object indicates the \
		  E1 CSU AIS Alarm status.;
	   HELP = ;
	   CAPABILITIES = ;"
	::= { mcmE1CsuGenStatusEntry 5 }

mcmE1CsuGenStatusRxCarrierLoss OBJECT-TYPE
	SYNTAX	INTEGER {
		yes (1),
		no (2)
		}
	ACCESS	read-only
	STATUS	mandatory
	DESCRIPTION
	  "NAME = ;
	   DESC = The value of this object indicates the \
		  E1 CSU receive carrier loss status.;
	   HELP = ;
	   CAPABILITIES = ;"
	::= { mcmE1CsuGenStatusEntry 6 }

mcmE1CsuGenStatusRxSyncLoss OBJECT-TYPE
	SYNTAX	INTEGER {
		yes (1),
		no (2)
		}
	ACCESS	read-only
	STATUS	mandatory
	DESCRIPTION
	  "NAME = ;
	   DESC = The value of this object indicates the E1 \
		  CSU receive loss of sync status.;
	   HELP = ;
	   CAPABILITIES = ;"
	::= { mcmE1CsuGenStatusEntry 7 }

mcmE1CsuGenStatusTxElasStrFull OBJECT-TYPE
	SYNTAX	INTEGER {
		yes (1),
		no (2)
		}
	ACCESS	read-only
	STATUS	mandatory
	DESCRIPTION
	  "NAME = ;
	   DESC = The value of this object indicates the E1 \
		  CSU transmit elastic store full status. This \
		  indicates that the E1 CSU transmit side \
		  elastic store buffer fills and a frame is deleted.;
	   HELP = ;
	   CAPABILITIES = ;"
	::= { mcmE1CsuGenStatusEntry 8 }

mcmE1CsuGenStatusTxElasStrEmpty OBJECT-TYPE
	SYNTAX	INTEGER {
		yes (1),
		no (2)
		}
	ACCESS	read-only
	STATUS	mandatory
	DESCRIPTION
	  "NAME = ;
	   DESC = The value of this object indicates the E1 \
		  CSU transmit elastic store empty status. This \
		  indicates that the E1 CSU transmit side elastic \
		  store buffer empties and a frame is repeated.;
	   HELP = ;
	   CAPABILITIES = ;"
	::= { mcmE1CsuGenStatusEntry 9 }

mcmE1CsuGenStatusRxElasStrFull OBJECT-TYPE
	SYNTAX	INTEGER {
		yes (1),
		no (2)
		}
	ACCESS	read-only
	STATUS	mandatory
	DESCRIPTION
	  "NAME = ;
	   DESC = The value of this object indicates the E1 \
		  CSU receive elastic store full status. This \
		  indicates that the E1 CSU receive side elastic \
		  store buffer fills and a frame is deleted.;
	   HELP = ;
	   CAPABILITIES = ;"
	::= { mcmE1CsuGenStatusEntry 10 }

mcmE1CsuGenStatusRxElasStrEmpty OBJECT-TYPE
	SYNTAX	INTEGER {
		yes (1),
		no (2)
		}
	ACCESS	read-only
	STATUS	mandatory
	DESCRIPTION
	  "NAME = ;
	   DESC = The value of this object indicates the E1 \
		  CSU receive elastic store empty status. This \
		  indicates that the E1 CSU receive side elastic \
		  store buffer empties and a frame is repeated.;
	   HELP = ;
	   CAPABILITIES = ;"
	::= { mcmE1CsuGenStatusEntry 11 }

mcmE1CsuGenStatusBpvOrLnCdViolations OBJECT-TYPE
	SYNTAX	INTEGER (0..65535)
	ACCESS	read-only
	STATUS	mandatory
	DESCRIPTION
	  "NAME = ;
	   DESC = The value of this object indicates the number \
		  of E1 CSU line code violations. \
		  Bipolar violation counts if HDB3 disabled, code \
		  violation counts if HDB3 enabled. \
		  Note that this is a 16-bit counter.;
	   HELP = ;
	   CAPABILITIES = ;"
	::= { mcmE1CsuGenStatusEntry 12 }

mcmE1CsuGenStatusFASErrors OBJECT-TYPE
	SYNTAX	INTEGER (0..4095)
	ACCESS	read-only
	STATUS	mandatory
	DESCRIPTION
	  "NAME = ;
	   DESC = The value of this object indicates the number \
		  of E1 CSU FAS error counts.  FAS error counts \
		  record word errors in the frame alignment \
		  signal in timeslot 0. \
		  Note that this is a 12-bit counter.;
	   HELP = ;
	   CAPABILITIES = ;"
 	::= { mcmE1CsuGenStatusEntry 13 }

mcmE1CsuGenStatusCRC4Errors OBJECT-TYPE
	SYNTAX	INTEGER (0..1023)	
	ACCESS	read-only
	STATUS	mandatory
	DESCRIPTION
	  "NAME = ;
	   DESC = The value of this object indicates the number \
		  of E1 CSU CRC4 error counts.  This object \
		  is only applicable when CRC4 is enabled. \
		  Note that this is a 10-bit counter.;
	   HELP = ;
	   CAPABILITIES = ;"
	::= { mcmE1CsuGenStatusEntry 14 }



--  the 56K CSU Status and Statistics Table 
--  This table provides the 56K CSU status and statistics parameters.

mcmCsuStatusTable  OBJECT-TYPE
    SYNTAX  SEQUENCE OF McmCsuStatusEntry
    ACCESS  not-accessible
    STATUS  mandatory
    DESCRIPTION
      "NAME = ;
           DESC = The 56K CSU Status and Statistics table.;
       HELP = ;
           CAPABILITIES = NET_DISP, VPN_DISP;"
    ::= { csu-status 4 }

mcmCsuStatusEntry OBJECT-TYPE
    SYNTAX  McmCsuStatusEntry
    ACCESS  not-accessible
    STATUS  mandatory
    DESCRIPTION
      "NAME = ;
           DESC = An entry in the 56K CSU Status \
                  and Statistics table.;
           HELP = ;
           CAPABILITIES = ;"
    INDEX   { mcmCsuStatusifIndex }
    ::= { mcmCsuStatusTable 1 }

McmCsuStatusEntry ::= SEQUENCE {
	mcmCsuStatusifIndex				INTEGER,
    mcmCsuStatusLineStatus			INTEGER,
    mcmCsuStatusRxLossOfSignal		INTEGER,
    mcmCsuStatusFAWSync			INTEGER,
    mcmCsuStatusLoopPresent			INTEGER,
    mcmCsuStatusInsertLossLineLength    	INTEGER,
    mcmCsuStatusRxSignalMag			INTEGER,
    mcmCsuStatusInvalidBPVcounts		INTEGER	
    }

mcmCsuStatusifIndex OBJECT-TYPE
	SYNTAX	INTEGER (1..255)
	ACCESS	read-only
	STATUS	mandatory
	DESCRIPTION
	  "NAME = ;
	   DESC = The 56k CSU Status interface index \
				value of the specifc entry.;
	   HELP = ;
	   CAPABILITIES = ;"
	::= { mcmCsuStatusEntry 1 }

mcmCsuStatusLineStatus OBJECT-TYPE
	SYNTAX	INTEGER {
		operational (1),
		linkDown (2),
		testMode (3)
		}
	ACCESS	read-only
	STATUS	mandatory
	DESCRIPTION
	  "NAME = ;
	   DESC = The value of this object indicates the 56K \
		  CSU line status.;
	   HELP = ;
	   CAPABILITIES = ;"
	::= { mcmCsuStatusEntry 2 }

mcmCsuStatusRxLossOfSignal OBJECT-TYPE
	SYNTAX	INTEGER {
		yes (1),
		no (2)
		}
	ACCESS	read-only
	STATUS	mandatory
	DESCRIPTION
	  "NAME = ;
	   DESC = The value of this object indicates if the 56K \
		  CSU receiver has lost signal.;
	   HELP = ;
	   CAPABILITIES = ;"
	::= { mcmCsuStatusEntry 3 }

mcmCsuStatusFAWSync OBJECT-TYPE
	SYNTAX	INTEGER {
		yes (1),
		no (2)
		}
	ACCESS	read-only
	STATUS	mandatory
	DESCRIPTION
	  "NAME = ;
	   DESC = The value of this object indicates the 56K \
		  CSU DDS FAW Sync in DDS-SC or CC-64K.;
	   HELP = ;
	   CAPABILITIES = ;"
	::= { mcmCsuStatusEntry 4 }

mcmCsuStatusLoopPresent OBJECT-TYPE
	SYNTAX	INTEGER {
		yes (1),
		no (2)
		}
	ACCESS	read-only
	STATUS	mandatory
	DESCRIPTION
	  "NAME = ;
	   DESC = The value of this object indicates if the 56K \
		  CSU loop is currently present.;
	   HELP = ;
	   CAPABILITIES = ;"
	::= { mcmCsuStatusEntry 5 }

mcmCsuStatusInsertLossLineLength OBJECT-TYPE
	SYNTAX	INTEGER {
		iL50pt5db-LL8pt5km (7),
		iL44pt4db-LL7pt5km (8),
		iL38pt4db-LL6pt4km (9),
		iL32pt3db-LL5pt3km (10),
		iL26pt0db-LL4pt2km (11),
		iL19pt7db-LL3pt2km (12),
		iL13pt6db-LL2pt1km (13),
		iL7pt3db-LL1pt1km (14),
		iL0db-LL0km (15)
		}	
	ACCESS	read-only
	STATUS	mandatory
	DESCRIPTION
	  "NAME = ;
	   DESC = The value of this object indicates the 56K \
		  CSU receiver Insertion loss (iL) in db, and \
		  Line Length (LL) in kilometers.;
	   HELP = ;
	   CAPABILITIES = ;"
	::= { mcmCsuStatusEntry 6 }

mcmCsuStatusRxSignalMag OBJECT-TYPE
	SYNTAX	INTEGER (0..255)
	ACCESS	read-only
	STATUS	mandatory
	DESCRIPTION
	  "NAME = ;
	   DESC = The value of this object indicates the 56K \
		  CSU receive signal magnitude expressed as \
		  the 'receiver slicer level'.  This value \
		  is used in conjunction with the db Insertion \
		  Loss ('iL' from InsertLossLineLength object) \
		  to compute the signal magnitude as follows: \
		  Nyquist frequency loop attn (in db) = \
		    [(iL)**2 + 20log10(51/RxSignalMag)].;
	   HELP = ;
	   CAPABILITIES = ;"
	::= { mcmCsuStatusEntry 7 }

mcmCsuStatusInvalidBPVcounts OBJECT-TYPE
	SYNTAX	INTEGER (0..255)	
	ACCESS	read-only
	STATUS	mandatory
	DESCRIPTION
	  "NAME = ;
	   DESC = The value of this object indicates the 56K \
		  CSU invalid BPV (Bipolar Violation) count. \
		  Note that this is an 8-bit counter.;
	   HELP = ;
	   CAPABILITIES = ;"
	::= { mcmCsuStatusEntry 8 }



-- Trap Messages


-- T1 CSU Trap Messages 

mcmT1CsuRedAlarmSet TRAP-TYPE
    ENTERPRISE  micom-csu
    VARIABLES   { mcmSysAsciiTimeOfDay, mcmT1E1CsuCfgifIndex }
    DESCRIPTION
      "NAME = ;
       DESC =  When a downstream node detects a loss of \
               synchronization in its receive pair of a \
               T1 line, it is in red alarm condition. \
               Severity Level: CRITICAL.;
       HELP = ;"
    ::= 1

mcmT1CsuRedAlarmClear TRAP-TYPE
    ENTERPRISE  micom-csu
    VARIABLES   { mcmSysAsciiTimeOfDay, mcmT1E1CsuCfgifIndex }
    DESCRIPTION
      "NAME = ;
       DESC =  When a downstream node is back in \
               synchronization with its receive pair \
               of a T1 line. This trap clears the node \
               that has the Red Alarm condition. \
               Severity Level : INFORMATIVE.;
       HELP = ;"
    ::= 2

mcmT1CsuYellowAlarmSet TRAP-TYPE
    ENTERPRISE  micom-csu
    VARIABLES   { mcmSysAsciiTimeOfDay, mcmT1E1CsuCfgifIndex }
    DESCRIPTION
      "NAME = ;
       DESC =  When a downstream node detects a loss of \
               synchronization in its receive pair of a \
               T1 line, it is in red alarm condition. \
               In turn, it transmits a yellow alarm \
               signal upstream to the previous node. \
               Severity Level: MAJOR.;
       HELP = ;"
    ::= 3

mcmT1CsuYellowAlarmClear TRAP-TYPE
    ENTERPRISE  micom-csu
    VARIABLES   { mcmSysAsciiTimeOfDay, mcmT1E1CsuCfgifIndex }
    DESCRIPTION
      "NAME = ;
       DESC =  When a downstream node detects a loss of \
               synchronization in its receive pair of a \
               T1 line, it is in red alarm condition. \
               In turn, it transmits a yellow alarm \
               signal upstream to the previous node. \
               This trap clears the node that has the \
               Yellow Alarm condition.;
               Severity Level: INFORMATIVE.;
       HELP = ;"
    ::= 4

mcmT1CsuBlueAlarmSet TRAP-TYPE
    ENTERPRISE  micom-csu
    VARIABLES   { mcmSysAsciiTimeOfDay, mcmT1E1CsuCfgifIndex }
    DESCRIPTION
      "NAME = ;
       DESC =  When a downstream node detects a loss of \
               synchronization in its receive pair of a \
               T1 line, it is in red alarm condition. \
               In turn, it transmits a yellow alarm \
               signal upstream to the previous node \
               and a blue alarm signal downstream to \
               the next node.\
               Severity Level: MINOR.;
       HELP = ;"
    ::= 5

mcmT1CsuBlueAlarmClear TRAP-TYPE
    ENTERPRISE  micom-csu
    VARIABLES   { mcmSysAsciiTimeOfDay, mcmT1E1CsuCfgifIndex }
    DESCRIPTION
      "NAME = ;
       DESC =  When a downstream node detects a loss of \
               synchronization in its receive pair of a \
               T1 line, it is in red alarm condition. \
               In turn, it transmits a yellow alarm \
               signal upstream to the previous node \
               and a blue alarm signal downstream to \
               the next node. This trap clears the \
               node that has the Blue Alarm condition. \
               Severity Level: INFORMATIVE.;
       HELP = ;"
    ::= 6


-- E1 CSU Trap Messages 

mcmE1CsuRedAlarmSet TRAP-TYPE
    ENTERPRISE  micom-csu
    VARIABLES   { mcmSysAsciiTimeOfDay, mcmT1E1CsuCfgifIndex }
    DESCRIPTION
      "NAME = ;
       DESC =  This trap is generated upon the occurrence \
	  of an E1 CSU Red Alarm. A red alarm indicates that \
	  an out-of-frame condition existed for the last 100 \
	  milliseconds or longer. \
	  Severity Level: CRITICAL.;
       HELP = ;"
    ::= 7

mcmE1CsuRedAlarmClear TRAP-TYPE
    ENTERPRISE  micom-csu
    VARIABLES   { mcmSysAsciiTimeOfDay, mcmT1E1CsuCfgifIndex }
    DESCRIPTION
      "NAME = ;
       DESC = This trap is generated upon the clearance \
	  of an E1 CSU Red Alarm. A red alarm is cleared \
	  when the out-of-frame condition has been absent \
	  for 100 milliseconds. \
	  Severity Level : INFORMATIVE.;
       HELP = ;"
    ::= 8

mcmE1CsuRemoteAlarmSet TRAP-TYPE
    ENTERPRISE  micom-csu
    VARIABLES   { mcmSysAsciiTimeOfDay, mcmT1E1CsuCfgifIndex }
    DESCRIPTION
      "NAME = ;
       DESC = This trap is generated upon the occurrence \
	  of an E1 CSU Remote Alarm. \
	  Severity Level: MAJOR.;
       HELP = ;"
    ::= 9

mcmE1CsuRemoteAlarmClear TRAP-TYPE
    ENTERPRISE  micom-csu
    VARIABLES   { mcmSysAsciiTimeOfDay, mcmT1E1CsuCfgifIndex }
    DESCRIPTION
      "NAME = ;
       DESC = This trap is generated upon the clearance \
	  of an E1 CSU Remote Alarm. \
	  Severity Level: INFORMATIVE.;
       HELP = ;"
    ::= 10

mcmE1CsuAISAlarmSet TRAP-TYPE
    ENTERPRISE  micom-csu
    VARIABLES   { mcmSysAsciiTimeOfDay, mcmT1E1CsuCfgifIndex }
    DESCRIPTION
      "NAME = ;
       DESC = This trap is generated upon the occurrence \
	  of an E1 CSU AIS Alarm. The AIS (alarm indication \
	  signal) alarm is detected as an all ones condition \
	  on the E1 line persisting for 100ms or longer. \
	  This indicates the E1 line is unavailable. \
	  Severity Level: MINOR.;
       HELP = ;"
    ::= 11

mcmE1CsuAISAlarmClear TRAP-TYPE
    ENTERPRISE  micom-csu
    VARIABLES   { mcmSysAsciiTimeOfDay, mcmT1E1CsuCfgifIndex }
    DESCRIPTION
      "NAME = ;
       DESC = This trap is generated upon the clearance \
	  of an E1 CSU AIS Alarm. \
	  Severity Level: INFORMATIVE.;
       HELP = ;"
    ::= 12


END
