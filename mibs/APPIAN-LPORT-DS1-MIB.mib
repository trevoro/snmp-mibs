--
--      Title:  Appian Logical Port DS1 MIB 
--
--      Author: Brian Johnson
--
--      Description:
--
--      This MIB file contains the definitions and support for the Appian
--      Optical Services Access Platform(s).
--      
--      This mib contains configuration, 15 minute and day statitics,
--      and threshold values for the logical port DS1 for this OSAP.
--
--      The information in these tables is NOT SHARED by OSAPs.
--      All information from these tables that was shared has been moved
--      to the Shared Timeslot Table.
--


APPIAN-LPORT-DS1-MIB DEFINITIONS ::= BEGIN

     IMPORTS
      acLport, AcAdminStatus, AcNodeId          FROM APPIAN-SMI-MIB

      acChassisCurrentTime, acChassisRingId     FROM APPIAN-CHASSIS-MIB

      MODULE-IDENTITY, OBJECT-TYPE,
      NOTIFICATION-TYPE                         FROM SNMPv2-SMI
      DisplayString, TimeStamp, TruthValue      FROM SNMPv2-TC
      PerfIntervalCount                         FROM PerfHist-TC-MIB;

     acLogicalDs1 MODULE-IDENTITY
         LAST-UPDATED   "0008210000Z"
         ORGANIZATION   "Appian Communications, Inc."
         CONTACT-INFO   "Brian Johnson"
         DESCRIPTION
              "The MIB module to describe the Appian Logical DS1 
               interfaces objects."

         ::= { acLport 2 }

     -- The Appian Logical DS1 Near End Group

     -- The Appian Logical DS1 Near End Group consists of three tables:
     --    DS1 Logical Configuration
     --    DS1 Logical Interval
     --    DS1 Logical Day

     -- The Appian Logical DS1 Configuration Table

     acLogicalDs1ConfigTable OBJECT-TYPE
          SYNTAX  SEQUENCE OF AcLogicalDs1ConfigEntry
          MAX-ACCESS  not-accessible
          STATUS  current
          DESCRIPTION
                 "The Appian Logical DS1 Configuration table.  This table
                 is created by the EMS/CLI."  
          ::= { acLogicalDs1 1 }

     acLogicalDs1ConfigEntry OBJECT-TYPE
          SYNTAX  AcLogicalDs1ConfigEntry
          MAX-ACCESS  not-accessible
          STATUS  current
          DESCRIPTION
                 "An entry in the Appian Logical DS1 Configuration table."
          INDEX   { acLogicalDs1ConfigNodeId, acLogicalDs1ConfigIndex }
          ::= { acLogicalDs1ConfigTable 1 }

     AcLogicalDs1ConfigEntry ::=
          SEQUENCE {
              acLogicalDs1ConfigNodeId                     AcNodeId,
              acLogicalDs1ConfigIndex                      INTEGER,
              acLogicalDs1ConfigAdminStatus                AcAdminStatus,
              acLogicalDs1ConfigTimeElapsedInterval        INTEGER,
              acLogicalDs1ConfigValidIntervals             INTEGER,
              acLogicalDs1ConfigTimeElapsedDay             INTEGER,
              acLogicalDs1ConfigValidDays                  INTEGER,
              acLogicalDs1ConfigTimeElapsedFarEndInterval  INTEGER,
              acLogicalDs1ConfigValidFarEndIntervals       INTEGER,
              acLogicalDs1ConfigTimeElapsedFarEndDay       INTEGER,
              acLogicalDs1ConfigValidFarEndDays            INTEGER,
              acLogicalDs1ConfigSendCode                   INTEGER,
              acLogicalDs1ConfigCircuitIdentifier          DisplayString,
              acLogicalDs1ConfigLoopbackConfig             INTEGER,
              acLogicalDs1ConfigLineStatus                 INTEGER,
              acLogicalDs1ConfigTransmitClockSource        INTEGER,
              acLogicalDs1ConfigInvalidIntervals           INTEGER,
              acLogicalDs1ConfigInvalidDays                INTEGER,
              acLogicalDs1ConfigInvalidFarEndIntervals     INTEGER,
              acLogicalDs1ConfigInvalidFarEndDays          INTEGER,
              acLogicalDs1ConfigLineStatusLastChange       TimeStamp,
              acLogicalDs1ConfigLineStatusChangeTrapEnable INTEGER,
              acLogicalDs1ConfigLoopbackStatus             INTEGER,
              acLogicalDs1ConfigVTNumber                   INTEGER
     }

     acLogicalDs1ConfigNodeId OBJECT-TYPE
          SYNTAX  AcNodeId
          MAX-ACCESS  accessible-for-notify
          STATUS  current
          DESCRIPTION
                 "The node id is the id for this specific node in the OSAP 
                 ring."
          ::= { acLogicalDs1ConfigEntry 1 }

     acLogicalDs1ConfigIndex OBJECT-TYPE
          SYNTAX  INTEGER
          MAX-ACCESS  accessible-for-notify
          STATUS  current
          DESCRIPTION
                 "This value for this object is equal to the value of index 
                 from the Time Slot Table that this DS1 corresponds.  The value
                 can be a number between 1 and 65535 (64k - 1)."
          ::= { acLogicalDs1ConfigEntry 2 }

     acLogicalDs1ConfigAdminStatus OBJECT-TYPE
          SYNTAX      AcAdminStatus
          MAX-ACCESS  read-create
          STATUS      current
          DESCRIPTION
          "Appian Administrative Status attribute used to set the provisioning
          state as either activate(1), inactivate(2) or delete(3).  Refer to
          the Appian-SMI.mib file for additional information."

          DEFVAL { inactivate }
          ::= { acLogicalDs1ConfigEntry 3 }


     acLogicalDs1ConfigTimeElapsedInterval OBJECT-TYPE
          SYNTAX  INTEGER (0..899)
          MAX-ACCESS  read-only
          STATUS  current
          DESCRIPTION
                   "The number of seconds that have elapsed since
                   the beginning of the near end current error-
                   measurement period.  If, for some reason, such
                   as an adjustment in the system's time-of-day
                   clock, the current interval exceeds the maximum
                   value, the agent will return the maximum value."
          ::= { acLogicalDs1ConfigEntry 4 }

     acLogicalDs1ConfigValidIntervals OBJECT-TYPE
          SYNTAX  INTEGER (0..96)
          MAX-ACCESS  read-only
          STATUS  current
          DESCRIPTION
                 "The number of previous near end intervals for
                 which data was collected.  The value will be
                 96 unless the interface was brought online within
                 the last 24 hours, in which case the value will be
                 the number of complete 15 minute near end
                 intervals since the interface has been online.  In
                 the case where the agent is a proxy, it is
                 possible that some intervals are unavailable.  In
                 this case, this interval is the maximum interval
                 number for which data is available."
          ::= { acLogicalDs1ConfigEntry 5 }

     acLogicalDs1ConfigTimeElapsedDay OBJECT-TYPE
          SYNTAX  INTEGER (0..86399)
          MAX-ACCESS  read-only
          STATUS  current
          DESCRIPTION
                   "The number of seconds that have elapsed since
                   the beginning of the near end current day error-
                   measurement period.  If, for some reason, such
                   as an adjustment in the system's time-of-day
                   clock, the current day interval exceeds the maximum
                   value, the agent will return the maximum value."
          ::= { acLogicalDs1ConfigEntry 6 }

     acLogicalDs1ConfigValidDays OBJECT-TYPE
          SYNTAX  INTEGER (0..30)
          MAX-ACCESS  read-only
          STATUS  current
          DESCRIPTION
                 "The number of previous near end days for
                 which data was collected.  The value will be
                 30 unless the interface was brought online within
                 the last 30 days, in which case the value will be
                 the number of complete 24 hr near end days
                 since the interface has been online.  In
                 the case where the agent is a proxy, it is
                 possible that some intervals are unavailable.  In
                 this case, this interval is the maximum interval
                 number for which data is available."
          ::= { acLogicalDs1ConfigEntry 7 }

     acLogicalDs1ConfigTimeElapsedFarEndInterval OBJECT-TYPE
          SYNTAX  INTEGER (0..899)
          MAX-ACCESS  read-only
          STATUS  current
          DESCRIPTION
                 "The number of seconds that have elapsed since the
                 beginning of the far end current error-measurement
                 period.  If, for some reason, such as an
                 adjustment in the system's time-of-day clock, the
                 current interval exceeds the maximum value, the
                 agent will return the maximum value."
          ::= { acLogicalDs1ConfigEntry 8 }

     acLogicalDs1ConfigValidFarEndIntervals OBJECT-TYPE
          SYNTAX  INTEGER (0..96)
          MAX-ACCESS  read-only
          STATUS  current
          DESCRIPTION
                 "The number of previous near end intervals for
                 which data was collected.  The value will be
                 96 unless the interface was brought online within
                 the last 24 hours, in which case the value will be
                 the number of complete 15 minute near end
                 intervals since the interface has been online.  In
                 the case where the agent is a proxy, it is
                 possible that some intervals are unavailable.  In
                 this case, this interval is the maximum interval
                 number for which data is available."
          ::= { acLogicalDs1ConfigEntry 9 }

     acLogicalDs1ConfigTimeElapsedFarEndDay OBJECT-TYPE
          SYNTAX  INTEGER (0..86399)
          MAX-ACCESS  read-only
          STATUS  current
          DESCRIPTION
                   "The number of seconds that have elapsed since
                   the beginning of the far end current day error-
                   measurement period.  If, for some reason, such
                   as an adjustment in the system's time-of-day
                   clock, the current day interval exceeds the maximum
                   value, the agent will return the maximum value."
          ::= { acLogicalDs1ConfigEntry 10 }

     acLogicalDs1ConfigValidFarEndDays OBJECT-TYPE
          SYNTAX  INTEGER (0..30)
          MAX-ACCESS  read-only
          STATUS  current
          DESCRIPTION
                 "The number of previous near end days for
                 which data was collected.  The value will be
                 30 unless the far/near end interface was brought online 
                 within the last 30 days, in which case the value will be
                 the number of complete 24 hr far end days
                 since the interface has been online.  In
                 the case where the agent is a proxy, it is
                 possible that some intervals are unavailable.  In
                 this case, this interval is the maximum interval
                 number for which data is available."
          ::= { acLogicalDs1ConfigEntry 11 }


     acLogicalDs1ConfigSendCode OBJECT-TYPE
          SYNTAX  INTEGER {
                    ds1SendNoCode(1),
                    ds1SendLineCode(2),
                    ds1SendPayloadCode(3),
                    ds1SendResetCode(4),
                    ds1SendQRS(5),
                    ds1Send511Pattern(6),
                    ds1Send3in24Pattern(7),
                    ds1SendOtherTestPattern(8)
                    }
          MAX-ACCESS  read-create
          STATUS  current
          DESCRIPTION
                 "This variable indicates what type of code is
                 being sent across the DS1 interface by the device.
                 Setting this variable causes the interface to send
                 the code requested.  The values mean:
           ds1SendNoCode
                sending looped or normal data

           ds1SendLineCode
                sending a request for a line loopback

           ds1SendPayloadCode
                sending a request for a payload loopback

           ds1SendResetCode
                sending a loopback termination request

           ds1SendQRS
                sending a Quasi-Random Signal  (QRS)  test
                pattern

           ds1Send511Pattern
                sending a 511 bit fixed test pattern

           ds1Send3in24Pattern
                sending a fixed test pattern of 3 bits set
                in 24

           ds1SendOtherTestPattern
                sending a test pattern  other  than  those
                described by this object"
          DEFVAL { ds1SendNoCode }
          ::= { acLogicalDs1ConfigEntry 12 }

     acLogicalDs1ConfigCircuitIdentifier OBJECT-TYPE
          SYNTAX  DisplayString (SIZE (0..255))
          MAX-ACCESS  read-create
          STATUS  current
          DESCRIPTION
                 "This variable contains the transmission vendor's
                 circuit identifier, for the purpose of
                 facilitating troubleshooting."
          DEFVAL { "" }

          ::= { acLogicalDs1ConfigEntry 13 }

     acLogicalDs1ConfigLoopbackConfig OBJECT-TYPE
          SYNTAX  INTEGER {
                      ds1NoLoop(1),
                      ds1PayloadLoop(2),
                      ds1LineLoop(3),
                      ds1OtherLoop(4),
                      ds1InwardLoop(5),
                      ds1DualLoop(6)
                    }
          MAX-ACCESS  read-create
          STATUS  current
          DESCRIPTION
                 "This variable represents the desired loopback
                 configuration of the DS1 interface.  Agents
                 supporting read/write access should return
                 inconsistentValue in response to a requested
                 loopback state that the interface does not
                 support.  The values mean:

                 ds1NoLoop
                  Not in the loopback state.  A device that is not
                 capable of performing a loopback on the interface
                 shall always return this as its value.

                 ds1PayloadLoop
                  The received signal at this interface is looped
                 through the device.  Typically the received signal
                 is looped back for retransmission after it has
                 passed through the device's framing function.

                 ds1LineLoop
                  The received signal at this interface does not go
                 through the device (minimum penetration) but is
                 looped back out.

                 ds1OtherLoop
                  Loopbacks that are not defined here.

                 ds1InwardLoop
                  The transmitted signal at this interface is
                 looped back and received by the same interface.
                 What is transmitted onto the line is product
                 dependent.

                 ds1DualLoop
                  Both ds1LineLoop and ds1InwardLoop will be
                 active simultaneously."
          DEFVAL { ds1NoLoop }
          ::= { acLogicalDs1ConfigEntry 14 }

     acLogicalDs1ConfigLineStatus OBJECT-TYPE
          SYNTAX  INTEGER (1..131071)
          MAX-ACCESS  read-only
          STATUS  current
          DESCRIPTION
                 "This variable indicates the Line Status of the
                 interface.  It contains loopback, failure,
                 received 'alarm' and transmitted 'alarms
                 information.

                 The ds1LineStatus is a bit map represented as a
                 sum, therefore, it can represent multiple failures
                 (alarms) and a LoopbackState simultaneously.

                 ds1NoAlarm must be set if and only if no other
                 flag is set.

                 If the ds1loopbackState bit is set, the loopback
                 in effect can be determined from the
                 ds1loopbackConfig object.
       The various bit positions are:
      1     ds1NoAlarm           No alarm present
      2     ds1RcvFarEndLOF      Far end LOF (a.k.a., Yellow Alarm)
      4     ds1XmtFarEndLOF      Near end sending LOF Indication
      8     ds1RcvAIS            Far end sending AIS
     16     ds1XmtAIS            Near end sending AIS
     32     ds1LossOfFrame       Near end LOF (a.k.a., Red Alarm)
     64     dsLossOfSignal       Near end Loss Of Signal
    128     ds1LoopbackState     Near end is looped
    256     ds1RcvFarEndLOMF     Far End Sending TS16 LOMF
    512     ds1XmtFarEndLOMF     Near End Sending TS16 LOMF
   1024     ds1RcvTestCode       Near End detects a test code
   2048     ds1OtherFailure      any line status not defined here
   4096     ds1UnavailSigState   Near End in Unavailable Signal
                                  State
  16384     ds1NetEquipOOS       Carrier Equipment Out of Service"

     ::= { acLogicalDs1ConfigEntry 15 }

     acLogicalDs1ConfigTransmitClockSource OBJECT-TYPE
          SYNTAX  INTEGER {
                     loopTiming(1),
                     localTiming(2),
                     throughTiming(3)
                 }
          MAX-ACCESS  read-only
          STATUS  current
          DESCRIPTION
            "The source of Transmit Clock.  For the logicalDs1, the
             timing will be throughTiming. This is not currently a 
             configurable parameter.

             The options are:
             'loopTiming' indicates that the recovered receive clock 
             is used as the transmit clock.

             'localTiming' indicates that a local clock source is used 
             or when an external clock is attached to the box containing 
             the interface.

             'throughTiming' indicates that recovered receive clock from 
             another interface is used as the transmit clock."

          ::= { acLogicalDs1ConfigEntry 16 }

     acLogicalDs1ConfigInvalidIntervals OBJECT-TYPE
          SYNTAX  INTEGER (0..96)
          MAX-ACCESS  read-only
          STATUS  current
          DESCRIPTION
                 "The number of intervals in the range from 0 to
                 ds1ValidIntervals for which no data is
                 available.  This object will typically be zero
                 except in cases where the data for some intervals
                 are not available (e.g., in proxy situations)."
          ::= { acLogicalDs1ConfigEntry 17 }

     acLogicalDs1ConfigInvalidDays OBJECT-TYPE
          SYNTAX  INTEGER (0..30)
          MAX-ACCESS  read-only
          STATUS  current
          DESCRIPTION
                 "The number of days in the range from 0 to
                 ds1ValidDays for which no data is
                 available.  This object will typically be zero
                 except in cases where the data for some days 
                 are not available (e.g., in proxy situations)."
          ::= { acLogicalDs1ConfigEntry 18 }

     acLogicalDs1ConfigInvalidFarEndIntervals OBJECT-TYPE
          SYNTAX  INTEGER (0..96)
          MAX-ACCESS  read-only
          STATUS  current
          DESCRIPTION
                 "The number of intervals in the range from 0 to
                 acLogicalDs1ConfigValidFarEndIntervals for which no data is
                 available.  This object will typically be zero
                 except in cases where the data for some intervals
                 are not available (e.g., in proxy situations)."
          ::= { acLogicalDs1ConfigEntry 19 }

     acLogicalDs1ConfigInvalidFarEndDays OBJECT-TYPE
          SYNTAX  INTEGER (0..30)
          MAX-ACCESS  read-only
          STATUS  current
          DESCRIPTION
                 "The number of days in the range from 0 to
                 acLogicalDs1ConfigValidFarEndDays for which no data is
                 available.  This object will typically be zero
                 except in cases where the data for some days 
                 are not available (e.g., in proxy situations)."
          ::= { acLogicalDs1ConfigEntry 20 }

     acLogicalDs1ConfigLineStatusLastChange OBJECT-TYPE
          SYNTAX  TimeStamp
          MAX-ACCESS  read-only
          STATUS  current
          DESCRIPTION
                 "The value of MIB II's sysUpTime object at the
                 time this DS1 entered its current line status
                 state.  If the current state was entered prior to
                 the last re-initialization of the proxy-agent,
                 then this object contains a zero value."
          ::= { acLogicalDs1ConfigEntry 21 }

     acLogicalDs1ConfigLineStatusChangeTrapEnable  OBJECT-TYPE
          SYNTAX      INTEGER {
                         enabled(1),
                         disabled(2)
                      }
          MAX-ACCESS  read-create
          STATUS      current
          DESCRIPTION
                 "Indicates whether acLogicalDs1ConfigLineStatusChange traps
                 should be generated for this interface."
          DEFVAL { disabled }
          ::= { acLogicalDs1ConfigEntry 22 }

     acLogicalDs1ConfigLoopbackStatus  OBJECT-TYPE
          SYNTAX      INTEGER (1..127)
          MAX-ACCESS  read-only
          STATUS      current
          DESCRIPTION
                 "This variable represents the current state of the
                 loopback on the DS1 interface.  It contains
                 information about loopbacks established by a
                 manager and remotely from the far end.

                 The ds1LoopbackStatus is a bit map represented as
                 a sum, therefore is can represent multiple
                 loopbacks simultaneously.

                 The various bit positions are:
                  1  ds1NoLoopback
                  2  ds1NearEndPayloadLoopback
                  4  ds1NearEndLineLoopback
                  8  ds1NearEndOtherLoopback
                 16  ds1NearEndInwardLoopback
                 32  ds1FarEndPayloadLoopback
                 64  ds1FarEndLineLoopback"

          DEFVAL { 1 }
          ::= { acLogicalDs1ConfigEntry 23 }

     acLogicalDs1ConfigVTNumber  OBJECT-TYPE
          SYNTAX      INTEGER (1..28)
          MAX-ACCESS  read-only
          STATUS      current
          DESCRIPTION
                 "This variable represents the virtual tributary number
                 in the STS-1 frame that this DS1 corresponds to."

          ::= { acLogicalDs1ConfigEntry 24 }


     -- The Appian DS1 Interval Table
     acLogicalDs1IntervalTable OBJECT-TYPE
          SYNTAX  SEQUENCE OF AcLogicalDs1IntervalEntry
          MAX-ACCESS  not-accessible
          STATUS  current
          DESCRIPTION
                 "The Appian DS1 Interval Table contains various
                 statistics collected by each DS1 Interface over
                 the previous 24 hours of operation as well as over
                 the current period.  The past 24 hours are broken 
                 into 96 completed 15 minute intervals.  The first
                 row in this table (identified by acLogicalDs1IntervalNumber=1)
                 represents the current interval statistics.  The next 96
                 rows in this table (represented by 
                 acLogicalDs1IntervalNumber=2..97) represents one of the past 
                 15 minute intervals. The final row (identified by 
                 acLogicalDs1IntervalNumber=98) is the total of all the past 
                 intervals (2..97).  This table is created automatically."
          ::= { acLogicalDs1 2 }

     acLogicalDs1IntervalEntry OBJECT-TYPE
          SYNTAX  AcLogicalDs1IntervalEntry
          MAX-ACCESS  not-accessible
          STATUS  current
          DESCRIPTION
                 "An entry in the Appian DS1 Interval table."
          INDEX   { acLogicalDs1IntervalNodeId, 
                    acLogicalDs1IntervalIndex, 
                    acLogicalDs1IntervalNumber }
          ::= { acLogicalDs1IntervalTable 1 }

     AcLogicalDs1IntervalEntry ::=
          SEQUENCE {
              acLogicalDs1IntervalNodeId            AcNodeId,
              acLogicalDs1IntervalIndex             INTEGER,
              acLogicalDs1IntervalNumber            INTEGER,
              acLogicalDs1IntervalValidStats        TruthValue,
              acLogicalDs1IntervalResetStats        TruthValue,
              acLogicalDs1IntervalESs               PerfIntervalCount,
              acLogicalDs1IntervalSESs              PerfIntervalCount,
              acLogicalDs1IntervalSEFSs             PerfIntervalCount,
              acLogicalDs1IntervalUASs              PerfIntervalCount,
              acLogicalDs1IntervalCSSs              PerfIntervalCount,
              acLogicalDs1IntervalPCVs              PerfIntervalCount,
              acLogicalDs1IntervalLESs              PerfIntervalCount,
              acLogicalDs1IntervalBESs              PerfIntervalCount,
              acLogicalDs1IntervalDMs               PerfIntervalCount,
              acLogicalDs1IntervalLCVs              PerfIntervalCount
     }

     acLogicalDs1IntervalNodeId OBJECT-TYPE
          SYNTAX  AcNodeId
          MAX-ACCESS  accessible-for-notify
          STATUS  current
          DESCRIPTION
                 "The node id is the id for this specific node in the OSAP 
                 ring."
          ::= { acLogicalDs1IntervalEntry 1 }

     acLogicalDs1IntervalIndex OBJECT-TYPE
          SYNTAX  INTEGER
          MAX-ACCESS  accessible-for-notify
          STATUS  current
          DESCRIPTION
                 "The index value which uniquely identifies the DS1
                 interface to which this entry is applicable.  The
                 interface identified by a particular value of this
                 index is the same interface as identified by the
                 same value as a acLogicalDs1Index object instance."
          ::= { acLogicalDs1IntervalEntry 2 }

     acLogicalDs1IntervalNumber OBJECT-TYPE
          SYNTAX  INTEGER (1..98)
          MAX-ACCESS  accessible-for-notify
          STATUS  current
          DESCRIPTION
                 "A number between 1 and 98, where 1 is the current
                 15 minute interval in progress, 2 is the most
                 recently completed 15 minute interval and 97 is
                 the 15 minutes interval completed 23 hours and 45
                 minutes prior to interval 2, and 98 is the total (sum)
                 of all of the previous completed intervals (2..97)."
          ::= { acLogicalDs1IntervalEntry 3 }

     acLogicalDs1IntervalValidStats OBJECT-TYPE
          SYNTAX TruthValue
          MAX-ACCESS read-only
          STATUS current
          DESCRIPTION
                 "This variable indicates if the data for this
                 interval is valid. For acLogicalDs1IntervalNumber=98,
                 this value will only be true if all data is valid
                 for intervals 2..97."
          ::= { acLogicalDs1IntervalEntry 4 }

     acLogicalDs1IntervalResetStats OBJECT-TYPE
          SYNTAX TruthValue
          MAX-ACCESS read-write
          STATUS current
          DESCRIPTION
                 "This variable allows the data for the current
                 interval (acLogicalDs1IntervalNumber = 1) to be reset.
                 The acLogicalDs1IntervalValidStats will be set to False
                 after the reset for the current interval.  This 
                 field has no effect on acLogicalDs1IntervalNumber 2..98.
                 This field will always show a value of False when
                 read."
          ::= { acLogicalDs1IntervalEntry 5 }

     acLogicalDs1IntervalESs OBJECT-TYPE
          SYNTAX  PerfIntervalCount
          MAX-ACCESS  read-only
          STATUS  current
          DESCRIPTION
                 "The number of Errored Seconds."
          ::= { acLogicalDs1IntervalEntry 6 }

     acLogicalDs1IntervalSESs OBJECT-TYPE
          SYNTAX  PerfIntervalCount
          MAX-ACCESS  read-only
          STATUS  current
          DESCRIPTION
                 "The number of Severely Errored Seconds."
          ::= { acLogicalDs1IntervalEntry 7 }

     acLogicalDs1IntervalSEFSs OBJECT-TYPE
          SYNTAX  PerfIntervalCount
          MAX-ACCESS  read-only
          STATUS  current
          DESCRIPTION
                 "The number of Severely Errored Framing Seconds."
          ::= { acLogicalDs1IntervalEntry 8 }

     acLogicalDs1IntervalUASs OBJECT-TYPE
          SYNTAX  PerfIntervalCount
          MAX-ACCESS  read-only
          STATUS  current
          DESCRIPTION
                 "The number of Unavailable Seconds.  This object
                 may decrease if the occurance of unavailable
                 seconds occurs across an inteval boundary."
          ::= { acLogicalDs1IntervalEntry 9 }

     acLogicalDs1IntervalCSSs OBJECT-TYPE
          SYNTAX  PerfIntervalCount
          MAX-ACCESS  read-only
          STATUS  current
          DESCRIPTION
                 "The number of Controlled Slip Seconds."
          ::= { acLogicalDs1IntervalEntry 10 }

     acLogicalDs1IntervalPCVs OBJECT-TYPE
          SYNTAX  PerfIntervalCount
          MAX-ACCESS  read-only
          STATUS  current
          DESCRIPTION
                 "The number of Path Coding Violations."
          ::= { acLogicalDs1IntervalEntry 11 }

     acLogicalDs1IntervalLESs OBJECT-TYPE
          SYNTAX  PerfIntervalCount
          MAX-ACCESS  read-only
          STATUS  current
          DESCRIPTION
                 "The number of Line Errored Seconds."
          ::= { acLogicalDs1IntervalEntry 12 }

     acLogicalDs1IntervalBESs OBJECT-TYPE
          SYNTAX PerfIntervalCount
          MAX-ACCESS read-only
          STATUS current
          DESCRIPTION
                 "The number of Bursty Errored Seconds."
          ::= { acLogicalDs1IntervalEntry 13 }

     acLogicalDs1IntervalDMs OBJECT-TYPE
          SYNTAX PerfIntervalCount
          MAX-ACCESS read-only
          STATUS current
          DESCRIPTION
                 "The number of Degraded Minutes."
          ::= { acLogicalDs1IntervalEntry 14 }

     acLogicalDs1IntervalLCVs OBJECT-TYPE
          SYNTAX PerfIntervalCount
          MAX-ACCESS read-only
          STATUS current
          DESCRIPTION
                 "The number of Line Code Violations."
          ::= { acLogicalDs1IntervalEntry 15 }

     -- The Appian DS1 Day Table
     acLogicalDs1DayTable OBJECT-TYPE
          SYNTAX  SEQUENCE OF AcLogicalDs1DayEntry
          MAX-ACCESS  not-accessible
          STATUS  current
          DESCRIPTION
                 "The Appian Logical DS1 Day Table contains various
                 statistics collected by each DS1 Interface over
                 the previous 30 days of operation as well as over
                 the current day period. The first row in this table 
                 (identified by acLogicalDs1DayNumber=1) represents the current 
                 day statistics.  The next 30 rows in this table 
                 (represented by acLogicalDs1DayNumber=2..31) represents one 
                 of the past 24 hr periods (day).  This table is created
                 automatically."
          ::= { acLogicalDs1 3 }

     acLogicalDs1DayEntry OBJECT-TYPE
          SYNTAX  AcLogicalDs1DayEntry
          MAX-ACCESS  not-accessible
          STATUS  current
          DESCRIPTION
                 "An entry in the Appian DS1 Day table."
          INDEX   { acLogicalDs1DayNodeId, 
                    acLogicalDs1DayIndex, 
                    acLogicalDs1DayNumber }
          ::= { acLogicalDs1DayTable 1 }

     AcLogicalDs1DayEntry ::=
          SEQUENCE {
              acLogicalDs1DayNodeId            AcNodeId,
              acLogicalDs1DayIndex             INTEGER,
              acLogicalDs1DayNumber            INTEGER,
              acLogicalDs1DayValidStats        TruthValue,
              acLogicalDs1DayResetStats        TruthValue,
              acLogicalDs1DayESs               PerfIntervalCount,
              acLogicalDs1DaySESs              PerfIntervalCount,
              acLogicalDs1DaySEFSs             PerfIntervalCount,
              acLogicalDs1DayUASs              PerfIntervalCount,
              acLogicalDs1DayCSSs              PerfIntervalCount,
              acLogicalDs1DayPCVs              PerfIntervalCount,
              acLogicalDs1DayLESs              PerfIntervalCount,
              acLogicalDs1DayBESs              PerfIntervalCount,
              acLogicalDs1DayDMs               PerfIntervalCount,
              acLogicalDs1DayLCVs              PerfIntervalCount
     }


     acLogicalDs1DayNodeId OBJECT-TYPE
          SYNTAX  AcNodeId
          MAX-ACCESS  accessible-for-notify
          STATUS  current
          DESCRIPTION
                 "The node id is the id for this specific node in the OSAP 
                 ring."
          ::= { acLogicalDs1DayEntry 1 }

     acLogicalDs1DayIndex OBJECT-TYPE
          SYNTAX  INTEGER
          MAX-ACCESS  accessible-for-notify
          STATUS  current
          DESCRIPTION
                 "The index value which uniquely identifies the DS1
                 interface to which this entry is applicable.  The
                 interface identified by a particular value of this
                 index is the same interface as identified by the
                 same value as a acLogicalDs1Index object instance."
          ::= { acLogicalDs1DayEntry 2 }

     acLogicalDs1DayNumber OBJECT-TYPE
          SYNTAX  INTEGER (1..31)
          MAX-ACCESS  accessible-for-notify
          STATUS  current
          DESCRIPTION
                 "A number between 1 and 31, where 1 is the current
                 24 hour interval in progress (day), 2 is the most
                 recently completed 24 hour interval and 31 is
                 the 24 hour interval completed 29 days prior to 
                 interval 1."
          ::= { acLogicalDs1DayEntry 3 }

     acLogicalDs1DayValidStats OBJECT-TYPE
          SYNTAX TruthValue
          MAX-ACCESS read-only
          STATUS current
          DESCRIPTION
                 "This variable indicates if the data for this
                 interval is valid."
          ::= { acLogicalDs1DayEntry 4 }

     acLogicalDs1DayResetStats OBJECT-TYPE
          SYNTAX TruthValue
          MAX-ACCESS read-write
          STATUS current
          DESCRIPTION
                 "This variable allows the data for the current
                 day (acLogicalDs1DayIndex = 1) to be reset.
                 The acLogicalDs1DayValidStats will be set to False
                 after the reset for the current day.  This 
                 field has no effect on acLogicalDs1DayIndex 2..31.
                 This field will always show a value of False 
                 when read."
          ::= { acLogicalDs1DayEntry 5 }


     acLogicalDs1DayESs OBJECT-TYPE
          SYNTAX  PerfIntervalCount
          MAX-ACCESS  read-only
          STATUS  current
          DESCRIPTION
                 "The number of Errored Seconds."
          ::= { acLogicalDs1DayEntry 6 }

     acLogicalDs1DaySESs OBJECT-TYPE
          SYNTAX  PerfIntervalCount
          MAX-ACCESS  read-only
          STATUS  current
          DESCRIPTION
                 "The number of Severely Errored Seconds."
          ::= { acLogicalDs1DayEntry 7 }

     acLogicalDs1DaySEFSs OBJECT-TYPE
          SYNTAX  PerfIntervalCount
          MAX-ACCESS  read-only
          STATUS  current
          DESCRIPTION
                 "The number of Severely Errored Framing Seconds."
          ::= { acLogicalDs1DayEntry 8 }

     acLogicalDs1DayUASs OBJECT-TYPE
          SYNTAX  PerfIntervalCount
          MAX-ACCESS  read-only
          STATUS  current
          DESCRIPTION
                 "The number of Unavailable Seconds.  This object
                 may decrease if the occurance of unavailable
                 seconds occurs across an inteval boundary."
          ::= { acLogicalDs1DayEntry 9 }

     acLogicalDs1DayCSSs OBJECT-TYPE
          SYNTAX  PerfIntervalCount
          MAX-ACCESS  read-only
          STATUS  current
          DESCRIPTION
                 "The number of Controlled Slip Seconds."
          ::= { acLogicalDs1DayEntry 10 }

     acLogicalDs1DayPCVs OBJECT-TYPE
          SYNTAX  PerfIntervalCount
          MAX-ACCESS  read-only
          STATUS  current
          DESCRIPTION
                 "The number of Path Coding Violations."
          ::= { acLogicalDs1DayEntry 11 }

     acLogicalDs1DayLESs OBJECT-TYPE
          SYNTAX  PerfIntervalCount
          MAX-ACCESS  read-only
          STATUS  current
          DESCRIPTION
                 "The number of Line Errored Seconds."
          ::= { acLogicalDs1DayEntry 12 }

     acLogicalDs1DayBESs OBJECT-TYPE
          SYNTAX PerfIntervalCount
          MAX-ACCESS read-only
          STATUS current
          DESCRIPTION
                 "The number of Bursty Errored Seconds."
          ::= { acLogicalDs1DayEntry 13 }

     acLogicalDs1DayDMs OBJECT-TYPE
          SYNTAX PerfIntervalCount
          MAX-ACCESS read-only
          STATUS current
          DESCRIPTION
                 "The number of Degraded Minutes."
          ::= { acLogicalDs1DayEntry 14 }

     acLogicalDs1DayLCVs OBJECT-TYPE
          SYNTAX PerfIntervalCount
          MAX-ACCESS read-only
          STATUS current
          DESCRIPTION
                 "The number of Line Code Violations."
          ::= { acLogicalDs1DayEntry 15 }


     -- The Appian DS1 Far End Group

     -- The Appian DS1 Far End Group consists of two tables:
     --    DS1 Far End Interval
     --    DS1 Far End Day

     -- The Appian DS1 Logical Far End Interval Table


     acLogicalDs1FarEndIntervalTable OBJECT-TYPE
          SYNTAX  SEQUENCE OF AcLogicalDs1FarEndIntervalEntry
          MAX-ACCESS  not-accessible
          STATUS  current
          DESCRIPTION
                 "The DS1 Logical Far End Interval Table contains 
                 various statistics collected by each DS1 interface over
                 the previous 24 hours of operation.  The past 24
                 hours are broken into 96 completed 15 minute
                 intervals. Each row in this table represents one
                 such interval (identified by acLogicalDs1FarEndIntervalNumber) 
                 for one specific instance (identified by 
                 acLogicalDs1FarEndIntervalIndex).  This table is created
                 automatically."
          ::= { acLogicalDs1 4 }

     acLogicalDs1FarEndIntervalEntry OBJECT-TYPE
          SYNTAX  AcLogicalDs1FarEndIntervalEntry
          MAX-ACCESS  not-accessible
          STATUS  current
          DESCRIPTION
                 "An entry in the DS1 Far End Interval table."

          INDEX   { acLogicalDs1FarEndIntervalNodeId, 
                    acLogicalDs1FarEndIntervalIndex,
                    acLogicalDs1FarEndIntervalNumber }
          ::= { acLogicalDs1FarEndIntervalTable 1 }

     AcLogicalDs1FarEndIntervalEntry ::=
          SEQUENCE {
              acLogicalDs1FarEndIntervalNodeId      AcNodeId,
              acLogicalDs1FarEndIntervalIndex       INTEGER,
              acLogicalDs1FarEndIntervalNumber      INTEGER,
              acLogicalDs1FarEndIntervalValidStats  TruthValue,
              acLogicalDs1FarEndIntervalResetStats  TruthValue,
              acLogicalDs1FarEndIntervalESs         PerfIntervalCount,
              acLogicalDs1FarEndIntervalSESs        PerfIntervalCount,
              acLogicalDs1FarEndIntervalSEFSs       PerfIntervalCount,
              acLogicalDs1FarEndIntervalUASs        PerfIntervalCount,
              acLogicalDs1FarEndIntervalCSSs        PerfIntervalCount,
              acLogicalDs1FarEndIntervalLESs        PerfIntervalCount,
              acLogicalDs1FarEndIntervalPCVs        PerfIntervalCount,
              acLogicalDs1FarEndIntervalBESs        PerfIntervalCount,
              acLogicalDs1FarEndIntervalDMs         PerfIntervalCount
     }

     acLogicalDs1FarEndIntervalNodeId OBJECT-TYPE
          SYNTAX  AcNodeId
          MAX-ACCESS  accessible-for-notify
          STATUS  current
          DESCRIPTION
                 "The node id is the id for this specific node in the OSAP 
                 ring."
          ::= { acLogicalDs1FarEndIntervalEntry 1 }

     acLogicalDs1FarEndIntervalIndex OBJECT-TYPE
          SYNTAX  INTEGER
          MAX-ACCESS  accessible-for-notify
          STATUS  current
          DESCRIPTION
                 "The index value which uniquely identifies the DS1
                 interface to which this entry is applicable.  The
                 interface identified by a particular value of this
                 index is identical to the interface identified by
                 the same value of acLogicalDs1Index."
          ::= { acLogicalDs1FarEndIntervalEntry 2 }

     acLogicalDs1FarEndIntervalNumber OBJECT-TYPE
          SYNTAX  INTEGER (1..98)
          MAX-ACCESS  accessible-for-notify
          STATUS  current
          DESCRIPTION
                 "A number between 1 and 98, where 1 is current
                 15 minute interval in progress, 2 is the most
                 recently completed 15 minute interval and 97 is
                 the 15 minutes interval completed 23 hours and 45
                 minutes prior to interval 2, and 98 is the total
                 of intervals 2..97 (sum)."
          ::= { acLogicalDs1FarEndIntervalEntry 3 }

     acLogicalDs1FarEndIntervalValidStats OBJECT-TYPE
          SYNTAX TruthValue
          MAX-ACCESS read-only
          STATUS current
          DESCRIPTION
                 "This variable indicates if the data for this
                 interval is valid.  For acLogicalDs1FarEndIntervalNumber=98,
                 this value will only be true if all data is valid
                 for intervals 2..97."
          ::= { acLogicalDs1FarEndIntervalEntry 4 }

     acLogicalDs1FarEndIntervalResetStats OBJECT-TYPE
          SYNTAX TruthValue
          MAX-ACCESS read-write
          STATUS current
          DESCRIPTION
                 "This variable allows the data for the current
                 interval (acLogicalDs1FarEndIntervalNumber = 1) to be reset.
                 The acLogicalDs1FarEndIntervalValidStats will be set to False
                 after the reset for the current interval.  This 
                 field has no effect on acLogicalDs1FarEndIntervalNumber 2..98. 
                 This field will always show a value of false when read."
          ::= { acLogicalDs1FarEndIntervalEntry 5 }

     acLogicalDs1FarEndIntervalESs OBJECT-TYPE
          SYNTAX  PerfIntervalCount
          MAX-ACCESS  read-only
          STATUS  current
          DESCRIPTION
                 "The number of Far End Errored Seconds."
          ::= { acLogicalDs1FarEndIntervalEntry 6 }

     acLogicalDs1FarEndIntervalSESs OBJECT-TYPE
          SYNTAX  PerfIntervalCount
          MAX-ACCESS  read-only
          STATUS  current
          DESCRIPTION
                 "The number of Far End Severely Errored Seconds."
          ::= { acLogicalDs1FarEndIntervalEntry 7 }

     acLogicalDs1FarEndIntervalSEFSs OBJECT-TYPE
          SYNTAX  PerfIntervalCount
          MAX-ACCESS  read-only
          STATUS  current
          DESCRIPTION
                 "The number of Far End Severely Errored Framing
                 Seconds."
          ::= { acLogicalDs1FarEndIntervalEntry 8 }

     acLogicalDs1FarEndIntervalUASs OBJECT-TYPE
          SYNTAX  PerfIntervalCount
          MAX-ACCESS  read-only
          STATUS  current
          DESCRIPTION
                 "The number of Unavailable Seconds."
          ::= { acLogicalDs1FarEndIntervalEntry 9 }

     acLogicalDs1FarEndIntervalCSSs OBJECT-TYPE
          SYNTAX  PerfIntervalCount
          MAX-ACCESS  read-only
          STATUS  current
          DESCRIPTION
                 "The number of Far End Controlled Slip Seconds."
          ::= { acLogicalDs1FarEndIntervalEntry 10 }

     acLogicalDs1FarEndIntervalLESs OBJECT-TYPE
          SYNTAX  PerfIntervalCount
          MAX-ACCESS  read-only
          STATUS  current
          DESCRIPTION
                 "The number of Far End Line Errored Seconds."

          ::= { acLogicalDs1FarEndIntervalEntry 11 }

     acLogicalDs1FarEndIntervalPCVs OBJECT-TYPE
          SYNTAX  PerfIntervalCount
          MAX-ACCESS  read-only
          STATUS  current
          DESCRIPTION
                 "The number of Far End Path Coding Violations."
          ::= { acLogicalDs1FarEndIntervalEntry 12 }

     acLogicalDs1FarEndIntervalBESs OBJECT-TYPE
          SYNTAX PerfIntervalCount
          MAX-ACCESS read-only
          STATUS current
          DESCRIPTION
                 "The number of Far End Bursty Errored Seconds."
          ::= { acLogicalDs1FarEndIntervalEntry 13 }

     acLogicalDs1FarEndIntervalDMs OBJECT-TYPE
          SYNTAX PerfIntervalCount
          MAX-ACCESS read-only
          STATUS current
          DESCRIPTION
                 "The number of Far End Degraded Minutes."
          ::= { acLogicalDs1FarEndIntervalEntry 14 }


   -- The Appian DS1 Logical Far End Day Table

     acLogicalDs1FarEndDayTable OBJECT-TYPE
          SYNTAX  SEQUENCE OF AcLogicalDs1FarEndDayEntry
          MAX-ACCESS  not-accessible
          STATUS  current
          DESCRIPTION
                 "The DS1 Logical Far End Day Table contains various
                 statistics collected by each DS1 interface over
                 the previous 30 days of operation. Each row in this 
                 table represents a one day interval (identified by 
                 acLogicalDs1FarEndDayNumber).  This table is created
                 automatically."
          ::= { acLogicalDs1 5 }

     acLogicalDs1FarEndDayEntry OBJECT-TYPE
          SYNTAX  AcLogicalDs1FarEndDayEntry
          MAX-ACCESS  not-accessible
          STATUS  current
          DESCRIPTION
                 "An entry in the DS1 Far End Day table."

          INDEX   { acLogicalDs1FarEndDayNodeId,
                    acLogicalDs1FarEndDayIndex,
                    acLogicalDs1FarEndDayNumber }
          ::= { acLogicalDs1FarEndDayTable 1 }

     AcLogicalDs1FarEndDayEntry ::=
          SEQUENCE {
              acLogicalDs1FarEndDayNodeId      AcNodeId,
              acLogicalDs1FarEndDayIndex       INTEGER,
              acLogicalDs1FarEndDayNumber      INTEGER,
              acLogicalDs1FarEndDayValidStats  TruthValue,
              acLogicalDs1FarEndDayResetStats  TruthValue,
              acLogicalDs1FarEndDayESs         PerfIntervalCount,
              acLogicalDs1FarEndDaySESs        PerfIntervalCount,
              acLogicalDs1FarEndDaySEFSs       PerfIntervalCount,
              acLogicalDs1FarEndDayUASs        PerfIntervalCount,
              acLogicalDs1FarEndDayCSSs        PerfIntervalCount,
              acLogicalDs1FarEndDayLESs        PerfIntervalCount,
              acLogicalDs1FarEndDayPCVs        PerfIntervalCount,
              acLogicalDs1FarEndDayBESs        PerfIntervalCount,
              acLogicalDs1FarEndDayDMs         PerfIntervalCount
     }

     acLogicalDs1FarEndDayNodeId OBJECT-TYPE
          SYNTAX  AcNodeId
          MAX-ACCESS  accessible-for-notify
          STATUS  current
          DESCRIPTION
                 "The node id is the id for this specific node in the OSAP 
                 ring."
          ::= { acLogicalDs1FarEndDayEntry 1 }

     acLogicalDs1FarEndDayIndex OBJECT-TYPE
          SYNTAX  INTEGER
          MAX-ACCESS  accessible-for-notify
          STATUS  current
          DESCRIPTION
                 "The index value which uniquely identifies the DS1
                 interface to which this entry is applicable.  The
                 interface identified by a particular value of this
                 index is identical to the interface identified by
                 the same value of acLogicalDs1Index."
          ::= { acLogicalDs1FarEndDayEntry 2 }

     acLogicalDs1FarEndDayNumber OBJECT-TYPE
          SYNTAX  INTEGER (1..31)
          MAX-ACCESS  accessible-for-notify
          STATUS  current
          DESCRIPTION
                 "A number between 1 and 31, where 1 is current
                 24 hour day interval in progress, 2 is the most
                 recently completed 24 hour day interval and 31 is
                 the 24 hour day interval completed 29 days prior 
                 to interval 2."
          ::= { acLogicalDs1FarEndDayEntry 3 }

     acLogicalDs1FarEndDayValidStats OBJECT-TYPE
          SYNTAX TruthValue
          MAX-ACCESS read-only
          STATUS current
          DESCRIPTION
                 "This variable indicates if the data for this
                 interval is valid."
          ::= { acLogicalDs1FarEndDayEntry 4 }

     acLogicalDs1FarEndDayResetStats OBJECT-TYPE
          SYNTAX TruthValue
          MAX-ACCESS read-write
          STATUS current
          DESCRIPTION
                 "This variable allows the data for the current
                 day (acLogicalDs1FarEndDayIndex = 1) to be reset.
                 The acLogicalDs1FarEndDayValidStats will be set to False
                 after the reset for the current interval.  This 
                 field has no effect on acLogicalDs1FarEndDayIndex 2..31. 
                 This field will always show a value of false when read."
          ::= { acLogicalDs1FarEndDayEntry 5 }

     acLogicalDs1FarEndDayESs OBJECT-TYPE
          SYNTAX  PerfIntervalCount
          MAX-ACCESS  read-only
          STATUS  current
          DESCRIPTION
                 "The number of Far End Errored Seconds."
          ::= { acLogicalDs1FarEndDayEntry 6 }

     acLogicalDs1FarEndDaySESs OBJECT-TYPE
          SYNTAX  PerfIntervalCount
          MAX-ACCESS  read-only
          STATUS  current
          DESCRIPTION
                 "The number of Far End Severely Errored Seconds."
          ::= { acLogicalDs1FarEndDayEntry 7 }

     acLogicalDs1FarEndDaySEFSs OBJECT-TYPE
          SYNTAX  PerfIntervalCount
          MAX-ACCESS  read-only
          STATUS  current
          DESCRIPTION
                 "The number of Far End Severely Errored Framing
                 Seconds."
          ::= { acLogicalDs1FarEndDayEntry 8 }

     acLogicalDs1FarEndDayUASs OBJECT-TYPE
          SYNTAX  PerfIntervalCount
          MAX-ACCESS  read-only
          STATUS  current
          DESCRIPTION
                 "The number of Unavailable Seconds."
          ::= { acLogicalDs1FarEndDayEntry 9 }

     acLogicalDs1FarEndDayCSSs OBJECT-TYPE
          SYNTAX  PerfIntervalCount
          MAX-ACCESS  read-only
          STATUS  current
          DESCRIPTION
                 "The number of Far End Controlled Slip Seconds."
          ::= { acLogicalDs1FarEndDayEntry 10 }

     acLogicalDs1FarEndDayLESs OBJECT-TYPE
          SYNTAX  PerfIntervalCount
          MAX-ACCESS  read-only
          STATUS  current
          DESCRIPTION
                 "The number of Far End Line Errored Seconds."

          ::= { acLogicalDs1FarEndDayEntry 11 }

     acLogicalDs1FarEndDayPCVs OBJECT-TYPE
          SYNTAX  PerfIntervalCount
          MAX-ACCESS  read-only
          STATUS  current
          DESCRIPTION
                 "The number of Far End Path Coding Violations."
          ::= { acLogicalDs1FarEndDayEntry 12 }

     acLogicalDs1FarEndDayBESs OBJECT-TYPE
          SYNTAX PerfIntervalCount
          MAX-ACCESS read-only
          STATUS current
          DESCRIPTION
                 "The number of Far End Bursty Errored Seconds."
          ::= { acLogicalDs1FarEndDayEntry 13 }

     acLogicalDs1FarEndDayDMs OBJECT-TYPE
          SYNTAX PerfIntervalCount
          MAX-ACCESS read-only
          STATUS current
          DESCRIPTION
                 "The number of Far End Degraded Minutes."
          ::= { acLogicalDs1FarEndDayEntry 14 }


     --
     -- The Appian DS1 Logical Threshold Table
     -- 


     acLogicalDs1ThresholdTable OBJECT-TYPE
          SYNTAX SEQUENCE OF AcLogicalDs1ThresholdEntry
          MAX-ACCESS  not-accessible
          STATUS  current
          DESCRIPTION
                 "The Appian DS1 Logical Threshold Table allows the 
                 user to configure the threshold values for each of the 
                 statistics found in the interval table base on
                 the 15 minute interval on the day.  This table is
                 created automatically."
          ::= { acLogicalDs1 6 }

     acLogicalDs1ThresholdEntry OBJECT-TYPE
          SYNTAX  AcLogicalDs1ThresholdEntry
          MAX-ACCESS  not-accessible
          STATUS  current
          DESCRIPTION
                 "An entry in the Appian DS1 Threshold table."
          INDEX   { acLogicalDs1ThresholdNodeId, 
                    acLogicalDs1ThresholdIndex }
          ::= { acLogicalDs1ThresholdTable 1 }

     AcLogicalDs1ThresholdEntry ::=
          SEQUENCE {
              acLogicalDs1ThresholdNodeId                 AcNodeId,
              acLogicalDs1ThresholdIndex                  INTEGER,
              acLogicalDs1ThresholdNEIntervalESs          INTEGER,
              acLogicalDs1ThresholdNEIntervalSESs         INTEGER,
              acLogicalDs1ThresholdNEIntervalSEFSs        INTEGER,
              acLogicalDs1ThresholdNEIntervalUASs         INTEGER,
              acLogicalDs1ThresholdNEIntervalCSSs         INTEGER,
              acLogicalDs1ThresholdNEIntervalPCVs         INTEGER,
              acLogicalDs1ThresholdNEIntervalLESs         INTEGER,
              acLogicalDs1ThresholdNEIntervalBESs         INTEGER,
              acLogicalDs1ThresholdNEIntervalDMs          INTEGER,
              acLogicalDs1ThresholdNEIntervalLCVs         INTEGER,
              acLogicalDs1ThresholdNEDayESs               INTEGER,
              acLogicalDs1ThresholdNEDaySESs              INTEGER,
              acLogicalDs1ThresholdNEDaySEFSs             INTEGER,
              acLogicalDs1ThresholdNEDayUASs              INTEGER,
              acLogicalDs1ThresholdNEDayCSSs              INTEGER,
              acLogicalDs1ThresholdNEDayPCVs              INTEGER,
              acLogicalDs1ThresholdNEDayLESs              INTEGER,
              acLogicalDs1ThresholdNEDayBESs              INTEGER,
              acLogicalDs1ThresholdNEDayDMs               INTEGER,
              acLogicalDs1ThresholdNEDayLCVs              INTEGER,
              acLogicalDs1ThresholdFEIntervalESs          INTEGER,
              acLogicalDs1ThresholdFEIntervalSESs         INTEGER,
              acLogicalDs1ThresholdFEIntervalSEFSs        INTEGER,
              acLogicalDs1ThresholdFEIntervalUASs         INTEGER,
              acLogicalDs1ThresholdFEIntervalCSSs         INTEGER,
              acLogicalDs1ThresholdFEIntervalLESs         INTEGER,
              acLogicalDs1ThresholdFEIntervalPCVs         INTEGER,
              acLogicalDs1ThresholdFEIntervalBESs         INTEGER,
              acLogicalDs1ThresholdFEIntervalDMs          INTEGER,
              acLogicalDs1ThresholdFEDayESs               INTEGER,
              acLogicalDs1ThresholdFEDaySESs              INTEGER,
              acLogicalDs1ThresholdFEDaySEFSs             INTEGER,
              acLogicalDs1ThresholdFEDayUASs              INTEGER,
              acLogicalDs1ThresholdFEDayCSSs              INTEGER,
              acLogicalDs1ThresholdFEDayLESs              INTEGER,
              acLogicalDs1ThresholdFEDayPCVs              INTEGER,
              acLogicalDs1ThresholdFEDayBESs              INTEGER,
              acLogicalDs1ThresholdFEDayDMs               INTEGER
     }

     acLogicalDs1ThresholdNodeId OBJECT-TYPE
          SYNTAX  AcNodeId
          MAX-ACCESS  accessible-for-notify
          STATUS  current
          DESCRIPTION
                 "The node id is the id for this specific node in the OSAP 
                 ring."
          ::= { acLogicalDs1ThresholdEntry 1 }

     acLogicalDs1ThresholdIndex OBJECT-TYPE
          SYNTAX  INTEGER
          MAX-ACCESS  accessible-for-notify
          STATUS  current
          DESCRIPTION
                 "The index value which uniquely identifies the DS1
                 interface to which this entry is applicable.  The
                 interface identified by a particular value of this
                 index is the same interface as identified by the
                 same value as a acLogicalDs1Index object instance. 
                 This table is created automatically."
          ::= { acLogicalDs1ThresholdEntry 2 }

     acLogicalDs1ThresholdNEIntervalESs OBJECT-TYPE
          SYNTAX  INTEGER
          MAX-ACCESS  read-write
          STATUS  current
          DESCRIPTION
                 "The threshold value for interval number of Errored 
                 Seconds.   A value of 0 disables the threshold for this 
                 error."
          DEFVAL { 0 }
          ::= { acLogicalDs1ThresholdEntry 3 }

     acLogicalDs1ThresholdNEIntervalSESs OBJECT-TYPE
          SYNTAX  INTEGER
          MAX-ACCESS  read-write
          STATUS  current
          DESCRIPTION
                 "The threshold value for the interval number of 
                  Severely Errored Seconds.  A value of 0 disables the
                  threshold for this error."
          DEFVAL { 0 }
          ::= { acLogicalDs1ThresholdEntry 4 }

     acLogicalDs1ThresholdNEIntervalSEFSs OBJECT-TYPE
          SYNTAX  INTEGER
          MAX-ACCESS  read-write
          STATUS  current
          DESCRIPTION
                 "The threshold for the interval number of Severely 
                 Errored Framing Seconds.  A value of 0 disables the
                  threshold for this error."
          DEFVAL { 0 }
          ::= { acLogicalDs1ThresholdEntry 5 }

     acLogicalDs1ThresholdNEIntervalUASs OBJECT-TYPE
          SYNTAX  INTEGER
          MAX-ACCESS  read-write
          STATUS  current
          DESCRIPTION
                 "The threshold for the interval number of Unavailable 
                 Seconds.  A value of 0 disables the threshold for this 
                 error."
          DEFVAL { 0 }
          ::= { acLogicalDs1ThresholdEntry 6 }

     acLogicalDs1ThresholdNEIntervalCSSs OBJECT-TYPE
          SYNTAX  INTEGER
          MAX-ACCESS  read-write
          STATUS  current
          DESCRIPTION
                 "The threshold for the interval number of Controlled 
                 Slip Seconds.  A value of 0 disables the threshold for  
                 this error."
          DEFVAL { 0 }
          ::= { acLogicalDs1ThresholdEntry 7 }

     acLogicalDs1ThresholdNEIntervalPCVs OBJECT-TYPE
          SYNTAX  INTEGER
          MAX-ACCESS  read-write
          STATUS  current
          DESCRIPTION
                 "The threshold for the interval number of Path Coding 
                 Violations.  A value of 0 disables the threshold for this 
                 error."
          DEFVAL { 0 }
          ::= { acLogicalDs1ThresholdEntry 8 }

     acLogicalDs1ThresholdNEIntervalLESs OBJECT-TYPE
          SYNTAX  INTEGER
          MAX-ACCESS  read-write
          STATUS  current
          DESCRIPTION
                 "The threshold value for the interval number of 
                 Line Errored Seconds.  A value of 0 disables the
                 threshold for this error."
          DEFVAL { 0 }
          ::= { acLogicalDs1ThresholdEntry 9 }

     acLogicalDs1ThresholdNEIntervalBESs OBJECT-TYPE
          SYNTAX INTEGER
          MAX-ACCESS read-write
          STATUS current
          DESCRIPTION
                 "The threshold for the interval number of Bursty Errored 
                 Seconds.  A value of 0 disables the threshold for this 
                 error."
          DEFVAL { 0 }
          ::= { acLogicalDs1ThresholdEntry 10 }


     acLogicalDs1ThresholdNEIntervalDMs OBJECT-TYPE
          SYNTAX INTEGER
          MAX-ACCESS read-write
          STATUS current
          DESCRIPTION
                 "The threshold for the interval number of Degraded 
                 Minutes.  A value of 0 disables the threshold for this 
                 error."
          DEFVAL { 0 }
          ::= { acLogicalDs1ThresholdEntry 11 }

     acLogicalDs1ThresholdNEIntervalLCVs OBJECT-TYPE
          SYNTAX INTEGER
          MAX-ACCESS read-write
          STATUS current
          DESCRIPTION
                 "The threshold for the interval number of Line Code 
                 Violations.  A value of 0 disables the threshold for this 
                 error."
          DEFVAL { 0 }
          ::= { acLogicalDs1ThresholdEntry 12 }

     acLogicalDs1ThresholdNEDayESs OBJECT-TYPE
          SYNTAX  INTEGER
          MAX-ACCESS  read-write
          STATUS  current
          DESCRIPTION
                 "The threshold value for day number of Errored Seconds.  
                  A value of 0 disables the threshold for this error."
          DEFVAL { 0 }
          ::= { acLogicalDs1ThresholdEntry 13 }

     acLogicalDs1ThresholdNEDaySESs OBJECT-TYPE
          SYNTAX  INTEGER
          MAX-ACCESS  read-write
          STATUS  current
          DESCRIPTION
                 "The threshold for the day number of Severely Errored 
                 Seconds.  A value of 0 disables the threshold for this
                 error."
          DEFVAL { 0 }
          ::= { acLogicalDs1ThresholdEntry 14 }

     acLogicalDs1ThresholdNEDaySEFSs OBJECT-TYPE
          SYNTAX  INTEGER
          MAX-ACCESS  read-write
          STATUS  current
          DESCRIPTION
                 "The threshold value for the day number of Severely 
                 Errored Framing Seconds.  A value of 0 disables the
                 threshold for this error."
          DEFVAL { 0 }
          ::= { acLogicalDs1ThresholdEntry 15 }

     acLogicalDs1ThresholdNEDayUASs OBJECT-TYPE
          SYNTAX  INTEGER
          MAX-ACCESS  read-write
          STATUS  current
          DESCRIPTION
                 "The threshold value for the day number of Unavailable 
                 Seconds.  A value of 0 disables the threshold for this 
                 error."
          DEFVAL { 0 }
          ::= { acLogicalDs1ThresholdEntry 16 }

     acLogicalDs1ThresholdNEDayCSSs OBJECT-TYPE
          SYNTAX  INTEGER
          MAX-ACCESS  read-write
          STATUS  current
          DESCRIPTION
                 "The threshold for the day number of Controlled Slip 
                 Seconds.  A value of 0 disables the threshold for this 
                 error."
          DEFVAL { 0 }
          ::= { acLogicalDs1ThresholdEntry 17 }

     acLogicalDs1ThresholdNEDayPCVs OBJECT-TYPE
          SYNTAX  INTEGER
          MAX-ACCESS  read-write
          STATUS  current
          DESCRIPTION
                 "The threshold value for the day number of Path Coding 
                 Violations.  A value of 0 disables the threshold for 
                 this error."
          DEFVAL { 0 }
          ::= { acLogicalDs1ThresholdEntry 18 }

     acLogicalDs1ThresholdNEDayLESs OBJECT-TYPE
          SYNTAX  INTEGER
          MAX-ACCESS  read-write
          STATUS  current
          DESCRIPTION
                 "The threshold for the day number of Line Errored Seconds. 
                  A value of 0 disables the threshold for this error."
          DEFVAL { 0 }
          ::= { acLogicalDs1ThresholdEntry 19 }

     acLogicalDs1ThresholdNEDayBESs OBJECT-TYPE
          SYNTAX INTEGER
          MAX-ACCESS read-write
          STATUS current
          DESCRIPTION
                 "The threshold for the day number of Bursty Errored 
                 Seconds.  A value of 0 disables the threshold for this 
                 error."
          DEFVAL { 0 }
          ::= { acLogicalDs1ThresholdEntry 20 }

     acLogicalDs1ThresholdNEDayDMs OBJECT-TYPE
          SYNTAX INTEGER
          MAX-ACCESS read-write
          STATUS current
          DESCRIPTION
                 "The threshold for the day number of Degraded Minutes.  
                  A value of 0 disables the threshold for this error."
          DEFVAL { 0 }
          ::= { acLogicalDs1ThresholdEntry 21 }

     acLogicalDs1ThresholdNEDayLCVs OBJECT-TYPE
          SYNTAX INTEGER
          MAX-ACCESS read-write
          STATUS current
          DESCRIPTION
                 "The threshold for the day number of Line Code Violations. 
                  A value of 0 disables the threshold for this error."
          DEFVAL { 0 }
          ::= { acLogicalDs1ThresholdEntry 22 }

     acLogicalDs1ThresholdFEIntervalESs OBJECT-TYPE
          SYNTAX  INTEGER
          MAX-ACCESS  read-write
          STATUS  current
          DESCRIPTION
                 "The threshold for the far end interval number of 
                 Far End Errored Seconds.  A value of 0 disables the
                 threshold for this error."
          DEFVAL { 0 }
          ::= { acLogicalDs1ThresholdEntry 23 }

     acLogicalDs1ThresholdFEIntervalSESs OBJECT-TYPE
          SYNTAX  INTEGER
          MAX-ACCESS  read-write
          STATUS  current
          DESCRIPTION
                 "The threshold for the far end interval number of Far
                 End Severely Errored Seconds.  A value of 0 disables the
                 threshold for this error."
          DEFVAL { 0 }
          ::= { acLogicalDs1ThresholdEntry 24 }

     acLogicalDs1ThresholdFEIntervalSEFSs OBJECT-TYPE
          SYNTAX  INTEGER
          MAX-ACCESS  read-write
          STATUS  current
          DESCRIPTION
                 "The threshold for the far end interval number of Far 
                 End Severely Errored Framing Seconds.  A value of 0 
                 disables the threshold for this error."
          DEFVAL { 0 }
          ::= { acLogicalDs1ThresholdEntry 25 }

     acLogicalDs1ThresholdFEIntervalUASs OBJECT-TYPE
          SYNTAX  INTEGER
          MAX-ACCESS  read-write
          STATUS  current
          DESCRIPTION
                 "The threshold value for the far end interval number of 
                 Unavailable Seconds.  A value of 0 disables the
                  threshold for this error."
          DEFVAL { 0 }
          ::= { acLogicalDs1ThresholdEntry 26 }

     acLogicalDs1ThresholdFEIntervalCSSs OBJECT-TYPE
          SYNTAX  INTEGER
          MAX-ACCESS  read-write
          STATUS  current
          DESCRIPTION
                 "The threshold value for the far end interval number of 
                 Far End Controlled Slip Seconds.  A value of 0 disables the
                  threshold for this error."
          DEFVAL { 0 }
          ::= { acLogicalDs1ThresholdEntry 27 }

     acLogicalDs1ThresholdFEIntervalLESs OBJECT-TYPE
          SYNTAX  INTEGER
          MAX-ACCESS  read-write
          STATUS  current
          DESCRIPTION
                 "The threshold value for the far end interal number of 
                 Far End Line Errored Seconds.  A value of 0 disables the
                  threshold for this error."
          DEFVAL { 0 }
          ::= { acLogicalDs1ThresholdEntry 28 }

     acLogicalDs1ThresholdFEIntervalPCVs OBJECT-TYPE
          SYNTAX  INTEGER
          MAX-ACCESS  read-write
          STATUS  current
          DESCRIPTION
                 "The threshold for the far end internal number of Far
                 End Path Coding Violations.  A value of 0 disables the
                  threshold for this error."
          DEFVAL { 0 }
          ::= { acLogicalDs1ThresholdEntry 29 }

     acLogicalDs1ThresholdFEIntervalBESs OBJECT-TYPE
          SYNTAX INTEGER
          MAX-ACCESS read-write
          STATUS current
          DESCRIPTION
                 "The threshold for the far end interval number of Far 
                 End Bursty Errored Seconds.  A value of 0 disables the
                  threshold for this error."
          DEFVAL { 0 }
          ::= { acLogicalDs1ThresholdEntry 30 }

     acLogicalDs1ThresholdFEIntervalDMs OBJECT-TYPE
          SYNTAX INTEGER
          MAX-ACCESS read-write
          STATUS current
          DESCRIPTION
                 "The threshold for the far end interval number of Far 
                 End Degraded Minutes.  A value of 0 disables the
                  threshold for this error."
          DEFVAL { 0 }
          ::= { acLogicalDs1ThresholdEntry 31 }

     acLogicalDs1ThresholdFEDayESs OBJECT-TYPE
          SYNTAX  INTEGER
          MAX-ACCESS  read-write
          STATUS  current
          DESCRIPTION
                 "The threshold for the far end day number of 
                 Far End Errored Seconds.  A value of 0 disables the
                  threshold for this error."
          DEFVAL { 0 }
          ::= { acLogicalDs1ThresholdEntry 32 }

     acLogicalDs1ThresholdFEDaySESs OBJECT-TYPE
          SYNTAX  INTEGER
          MAX-ACCESS  read-write
          STATUS  current
          DESCRIPTION
                 "The threshold for the far end day number of Far
                 End Severely Errored Seconds.  A value of 0 disables the
                  threshold for this error."
          DEFVAL { 0 }
          ::= { acLogicalDs1ThresholdEntry 33 }

     acLogicalDs1ThresholdFEDaySEFSs OBJECT-TYPE
          SYNTAX  INTEGER
          MAX-ACCESS  read-write
          STATUS  current
          DESCRIPTION
                 "The threshold for the far end day number of Far 
                 End Severely Errored Framing Seconds.  A value of 0 
                 disables the threshold for this error."
          DEFVAL { 0 }
          ::= { acLogicalDs1ThresholdEntry 34 }

     acLogicalDs1ThresholdFEDayUASs OBJECT-TYPE
          SYNTAX  INTEGER
          MAX-ACCESS  read-write
          STATUS  current
          DESCRIPTION
                 "The threshold value for the far end day number of 
                 Unavailable Seconds.  A value of 0 disables the
                  threshold for this error."
          DEFVAL { 0 }
          ::= { acLogicalDs1ThresholdEntry 35 }

     acLogicalDs1ThresholdFEDayCSSs OBJECT-TYPE
          SYNTAX  INTEGER
          MAX-ACCESS  read-write
          STATUS  current
          DESCRIPTION
                 "The threshold value for the far end day number of 
                 Far End Controlled Slip Seconds.  A value of 0 disables the
                  threshold for this error."
          DEFVAL { 0 }
          ::= { acLogicalDs1ThresholdEntry 36 }

     acLogicalDs1ThresholdFEDayLESs OBJECT-TYPE
          SYNTAX  INTEGER
          MAX-ACCESS  read-write
          STATUS  current
          DESCRIPTION
                 "The threshold value for the far end interal number of 
                 Far End Line Errored Seconds.  A value of 0 disables the
                  threshold for this error."
          DEFVAL { 0 }
          ::= { acLogicalDs1ThresholdEntry 37 }

     acLogicalDs1ThresholdFEDayPCVs OBJECT-TYPE
          SYNTAX  INTEGER
          MAX-ACCESS  read-write
          STATUS  current
          DESCRIPTION
                 "The threshold for the far end internal number of Far
                 End Path Coding Violations.  A value of 0 disables the
                  threshold for this error."
          DEFVAL { 0 }
          ::= { acLogicalDs1ThresholdEntry 38 }

     acLogicalDs1ThresholdFEDayBESs OBJECT-TYPE
          SYNTAX INTEGER
          MAX-ACCESS read-write
          STATUS current
          DESCRIPTION
                 "The threshold for the far end day number of Far 
                 End Bursty Errored Seconds.  A value of 0 disables the
                  threshold for this error."
          DEFVAL { 0 }
          ::= { acLogicalDs1ThresholdEntry 39 }

     acLogicalDs1ThresholdFEDayDMs OBJECT-TYPE
          SYNTAX INTEGER
          MAX-ACCESS read-write
          STATUS current
          DESCRIPTION
                 "The threshold for the far end day number of Far 
                 End Degraded Minutes.  A value of 0 disables the
                  threshold for this error."
          DEFVAL { 0 }
          ::= { acLogicalDs1ThresholdEntry 40 }

-- 
--   Logical Ds1 TRAPS
--
--

acLogicalDs1Traps   OBJECT IDENTIFIER ::= { acLogicalDs1 0 }


acLogicalDs1LineStatusChangeTrap NOTIFICATION-TYPE
    OBJECTS { acChassisCurrentTime, acChassisRingId, acLogicalDs1ConfigNodeId,
              acLogicalDs1ConfigIndex,
              acLogicalDs1ConfigLineStatus, 
              acLogicalDs1ConfigLineStatusLastChange }
    STATUS  current
    DESCRIPTION
    "An acLogcialDs1LineStatusChange trap is sent when the value of an 
    instance acLogicalDs1ConfigLineStatus changes. It can be utilized by 
    an NMS to trigger polls."

    ::= { acLogicalDs1Traps 1 }

acLogicalDs1StatsResetTrap  NOTIFICATION-TYPE 
    OBJECTS { acChassisCurrentTime, acChassisRingId, acLogicalDs1ConfigNodeId,
              acLogicalDs1ConfigIndex }
    STATUS  current
    DESCRIPTION
    "The Logical Ds1 statistics for this interface have been reset to zero (0) 
    which may effect long term trending functions monitoring this interface."
    
    ::= { acLogicalDs1Traps 2 }

acLogicalDs1CfgErrorTrap  NOTIFICATION-TYPE 
    OBJECTS { acChassisCurrentTime, acChassisRingId, acLogicalDs1ConfigNodeId,
              acLogicalDs1ConfigIndex }
    STATUS  current
    DESCRIPTION
    "A configuration request to the Logical Ds1 configuration table for an 
    interface has been detected as invalid or corrupt."
    
    ::= { acLogicalDs1Traps 3 }

acLogicalDs1LinkDownTrap  NOTIFICATION-TYPE
    OBJECTS { acChassisCurrentTime, acChassisRingId, acLogicalDs1ConfigNodeId,
              acLogicalDs1ConfigIndex }
    STATUS  current
    DESCRIPTION
    "The link for this ds1 interface has obtained sync."

    ::= { acLogicalDs1Traps 4 }

acLogicalDs1LinkUpTrap  NOTIFICATION-TYPE
    OBJECTS { acChassisCurrentTime, acChassisRingId, acLogicalDs1ConfigNodeId,
              acLogicalDs1ConfigIndex }
    STATUS  current
    DESCRIPTION
    "The link for this ds1 interface has lost sync."

    ::= { acLogicalDs1Traps 5 }

--acLogicalDs1ExceededThresholdNEIntervalESsTrap NOTIFICATION-TYPE
--    OBJECTS { acChassisCurrentTime, acChassisRingId, acLogicalDs1ThresholdNodeId,
--              acLogicalDs1ThresholdIndex }
--    STATUS  current
--    DESCRIPTION
--    "The specified threshold for this interface has been exceeded."
--
--    ::= { acLogicalDs1Traps 6 }
        
acLogicalDs1ExceededThresholdNEIntervalESsTrap NOTIFICATION-TYPE
    OBJECTS { acChassisCurrentTime, acChassisRingId, acLogicalDs1ThresholdNodeId,
              acLogicalDs1ThresholdIndex }
    STATUS  current
    DESCRIPTION
    "The specified threshold for this interface has been exceeded."

    ::= { acLogicalDs1Traps 7 }
        
acLogicalDs1ExceededThresholdNEIntervalSESsTrap NOTIFICATION-TYPE
    OBJECTS { acChassisCurrentTime, acChassisRingId, acLogicalDs1ThresholdNodeId,
              acLogicalDs1ThresholdIndex }
    STATUS  current
    DESCRIPTION
    "The specified threshold for this interface has been exceeded."

    ::= { acLogicalDs1Traps 8 }
        
acLogicalDs1ExceededThresholdNEIntervalSEFSsTrap NOTIFICATION-TYPE
    OBJECTS { acChassisCurrentTime, acChassisRingId, acLogicalDs1ThresholdNodeId,
              acLogicalDs1ThresholdIndex }
    STATUS  current
    DESCRIPTION
    "The specified threshold for this interface has been exceeded."

    ::= { acLogicalDs1Traps 9 }
        
acLogicalDs1ExceededThresholdNEIntervalUASsTrap NOTIFICATION-TYPE
    OBJECTS { acChassisCurrentTime, acChassisRingId, acLogicalDs1ThresholdNodeId,
              acLogicalDs1ThresholdIndex }
    STATUS  current
    DESCRIPTION
    "The specified threshold for this interface has been exceeded."

    ::= { acLogicalDs1Traps 10 }
        
acLogicalDs1ExceededThresholdNEIntervalCSSsTrap NOTIFICATION-TYPE
    OBJECTS { acChassisCurrentTime, acChassisRingId, acLogicalDs1ThresholdNodeId,
              acLogicalDs1ThresholdIndex }
    STATUS  current
    DESCRIPTION
    "The specified threshold for this interface has been exceeded."

    ::= { acLogicalDs1Traps 11 }
        
acLogicalDs1ExceededThresholdNEIntervalPCVsTrap NOTIFICATION-TYPE
    OBJECTS { acChassisCurrentTime, acChassisRingId, acLogicalDs1ThresholdNodeId,
              acLogicalDs1ThresholdIndex }
    STATUS  current
    DESCRIPTION
    "The specified threshold for this interface has been exceeded."

    ::= { acLogicalDs1Traps 12 }
        
acLogicalDs1ExceededThresholdNEIntervalLESsTrap NOTIFICATION-TYPE
    OBJECTS { acChassisCurrentTime, acChassisRingId, acLogicalDs1ThresholdNodeId,
              acLogicalDs1ThresholdIndex }
    STATUS  current
    DESCRIPTION
    "The specified threshold for this interface has been exceeded."

    ::= { acLogicalDs1Traps 13 }
        
acLogicalDs1ExceededThresholdNEIntervalBESsTrap NOTIFICATION-TYPE
    OBJECTS { acChassisCurrentTime, acChassisRingId, acLogicalDs1ThresholdNodeId,
              acLogicalDs1ThresholdIndex }
    STATUS  current
    DESCRIPTION
    "The specified threshold for this interface has been exceeded."

    ::= { acLogicalDs1Traps 14 }
        
acLogicalDs1ExceededThresholdNEIntervalDMsTrap NOTIFICATION-TYPE
    OBJECTS { acChassisCurrentTime, acChassisRingId, acLogicalDs1ThresholdNodeId,
              acLogicalDs1ThresholdIndex }
    STATUS  current
    DESCRIPTION
    "The specified threshold for this interface has been exceeded."

    ::= { acLogicalDs1Traps 15 }
        
acLogicalDs1ExceededThresholdNEIntervalLCVsTrap NOTIFICATION-TYPE
    OBJECTS { acChassisCurrentTime, acChassisRingId, acLogicalDs1ThresholdNodeId,
              acLogicalDs1ThresholdIndex }
    STATUS  current
    DESCRIPTION
    "The specified threshold for this interface has been exceeded."

    ::= { acLogicalDs1Traps 16 }
        
acLogicalDs1ExceededThresholdNEDayESsTrap NOTIFICATION-TYPE
    OBJECTS { acChassisCurrentTime, acChassisRingId, acLogicalDs1ThresholdNodeId,
              acLogicalDs1ThresholdIndex }
    STATUS  current
    DESCRIPTION
    "The specified threshold for this interface has been exceeded."

    ::= { acLogicalDs1Traps 17 }
        
acLogicalDs1ExceededThresholdNEDaySESsTrap NOTIFICATION-TYPE
    OBJECTS { acChassisCurrentTime, acChassisRingId, acLogicalDs1ThresholdNodeId,
              acLogicalDs1ThresholdIndex }
    STATUS  current
    DESCRIPTION
    "The specified threshold for this interface has been exceeded."

    ::= { acLogicalDs1Traps 18 }
        
acLogicalDs1ExceededThresholdNEDaySEFSsTrap NOTIFICATION-TYPE
    OBJECTS { acChassisCurrentTime, acChassisRingId, acLogicalDs1ThresholdNodeId,
              acLogicalDs1ThresholdIndex }
    STATUS  current
    DESCRIPTION
    "The specified threshold for this interface has been exceeded."

    ::= { acLogicalDs1Traps 19 }
        
acLogicalDs1ExceededThresholdNEDayUASsTrap NOTIFICATION-TYPE
    OBJECTS { acChassisCurrentTime, acChassisRingId, acLogicalDs1ThresholdNodeId,
              acLogicalDs1ThresholdIndex }
    STATUS  current
    DESCRIPTION
    "The specified threshold for this interface has been exceeded."

    ::= { acLogicalDs1Traps 20 }
        
acLogicalDs1ExceededThresholdNEDayCSSsTrap NOTIFICATION-TYPE
    OBJECTS { acChassisCurrentTime, acChassisRingId, acLogicalDs1ThresholdNodeId,
              acLogicalDs1ThresholdIndex }
    STATUS  current
    DESCRIPTION
    "The specified threshold for this interface has been exceeded."

    ::= { acLogicalDs1Traps 21 }
        
acLogicalDs1ExceededThresholdNEDayPCVsTrap NOTIFICATION-TYPE
    OBJECTS { acChassisCurrentTime, acChassisRingId, acLogicalDs1ThresholdNodeId,
              acLogicalDs1ThresholdIndex }
    STATUS  current
    DESCRIPTION
    "The specified threshold for this interface has been exceeded."

    ::= { acLogicalDs1Traps 22 }
        
acLogicalDs1ExceededThresholdNEDayLESsTrap NOTIFICATION-TYPE
    OBJECTS { acChassisCurrentTime, acChassisRingId, acLogicalDs1ThresholdNodeId,
              acLogicalDs1ThresholdIndex }
    STATUS  current
    DESCRIPTION
    "The specified threshold for this interface has been exceeded."

    ::= { acLogicalDs1Traps 23 }
        
acLogicalDs1ExceededThresholdNEDayBESsTrap NOTIFICATION-TYPE
    OBJECTS { acChassisCurrentTime, acChassisRingId, acLogicalDs1ThresholdNodeId,
              acLogicalDs1ThresholdIndex }
    STATUS  current
    DESCRIPTION
    "The specified threshold for this interface has been exceeded."

    ::= { acLogicalDs1Traps 24 }
        
acLogicalDs1ExceededThresholdNEDayDMsTrap NOTIFICATION-TYPE
    OBJECTS { acChassisCurrentTime, acChassisRingId, acLogicalDs1ThresholdNodeId,
              acLogicalDs1ThresholdIndex }
    STATUS  current
    DESCRIPTION
    "The specified threshold for this interface has been exceeded."

    ::= { acLogicalDs1Traps 25 }
        
acLogicalDs1ExceededThresholdNEDayLCVsTrap NOTIFICATION-TYPE
    OBJECTS { acChassisCurrentTime, acChassisRingId, acLogicalDs1ThresholdNodeId,
              acLogicalDs1ThresholdIndex }
    STATUS  current
    DESCRIPTION
    "The specified threshold for this interface has been exceeded."

    ::= { acLogicalDs1Traps 26 }
        
acLogicalDs1ExceededThresholdFEIntervalESsTrap NOTIFICATION-TYPE
    OBJECTS { acChassisCurrentTime, acChassisRingId, acLogicalDs1ThresholdNodeId,
              acLogicalDs1ThresholdIndex }
    STATUS  current
    DESCRIPTION
    "The specified threshold for this interface has been exceeded."

    ::= { acLogicalDs1Traps 27 }
        
acLogicalDs1ExceededThresholdFEIntervalSESsTrap NOTIFICATION-TYPE
    OBJECTS { acChassisCurrentTime, acChassisRingId, acLogicalDs1ThresholdNodeId,
              acLogicalDs1ThresholdIndex }
    STATUS  current
    DESCRIPTION
    "The specified threshold for this interface has been exceeded."

    ::= { acLogicalDs1Traps 28 }
        
acLogicalDs1ExceededThresholdFEIntervalSEFSsTrap NOTIFICATION-TYPE
    OBJECTS { acChassisCurrentTime, acChassisRingId, acLogicalDs1ThresholdNodeId,
              acLogicalDs1ThresholdIndex }
    STATUS  current
    DESCRIPTION
    "The specified threshold for this interface has been exceeded."

    ::= { acLogicalDs1Traps 29 }
        
acLogicalDs1ExceededThresholdFEIntervalUASsTrap NOTIFICATION-TYPE
    OBJECTS { acChassisCurrentTime, acChassisRingId, acLogicalDs1ThresholdNodeId,
              acLogicalDs1ThresholdIndex }
    STATUS  current
    DESCRIPTION
    "The specified threshold for this interface has been exceeded."

    ::= { acLogicalDs1Traps 30 }
        
acLogicalDs1ExceededThresholdFEIntervalCSSsTrap NOTIFICATION-TYPE
    OBJECTS { acChassisCurrentTime, acChassisRingId, acLogicalDs1ThresholdNodeId,
              acLogicalDs1ThresholdIndex }
    STATUS  current
    DESCRIPTION
    "The specified threshold for this interface has been exceeded."

    ::= { acLogicalDs1Traps 31 }
        
acLogicalDs1ExceededThresholdFEIntervalLESsTrap NOTIFICATION-TYPE
    OBJECTS { acChassisCurrentTime, acChassisRingId, acLogicalDs1ThresholdNodeId,
              acLogicalDs1ThresholdIndex }
    STATUS  current
    DESCRIPTION
    "The specified threshold for this interface has been exceeded."

    ::= { acLogicalDs1Traps 32 }
        
acLogicalDs1ExceededThresholdFEIntervalPCVsTrap NOTIFICATION-TYPE
    OBJECTS { acChassisCurrentTime, acChassisRingId, acLogicalDs1ThresholdNodeId,
              acLogicalDs1ThresholdIndex }
    STATUS  current
    DESCRIPTION
    "The specified threshold for this interface has been exceeded."

    ::= { acLogicalDs1Traps 33 }
        
acLogicalDs1ExceededThresholdFEIntervalBESsTrap NOTIFICATION-TYPE
    OBJECTS { acChassisCurrentTime, acChassisRingId, acLogicalDs1ThresholdNodeId,
              acLogicalDs1ThresholdIndex }
    STATUS  current
    DESCRIPTION
    "The specified threshold for this interface has been exceeded."

    ::= { acLogicalDs1Traps 34 }
        
acLogicalDs1ExceededThresholdFEIntervalDMsTrap NOTIFICATION-TYPE
    OBJECTS { acChassisCurrentTime, acChassisRingId, acLogicalDs1ThresholdNodeId,
              acLogicalDs1ThresholdIndex }
    STATUS  current
    DESCRIPTION
    "The specified threshold for this interface has been exceeded."

    ::= { acLogicalDs1Traps 35 }
        
acLogicalDs1ExceededThresholdFEDayESsTrap NOTIFICATION-TYPE
    OBJECTS { acChassisCurrentTime, acChassisRingId, acLogicalDs1ThresholdNodeId,
              acLogicalDs1ThresholdIndex }
    STATUS  current
    DESCRIPTION
    "The specified threshold for this interface has been exceeded."

    ::= { acLogicalDs1Traps 36 }
        
acLogicalDs1ExceededThresholdFEDaySESsTrap NOTIFICATION-TYPE
    OBJECTS { acChassisCurrentTime, acChassisRingId, acLogicalDs1ThresholdNodeId,
              acLogicalDs1ThresholdIndex }
    STATUS  current
    DESCRIPTION
    "The specified threshold for this interface has been exceeded."

    ::= { acLogicalDs1Traps 37 }
        
acLogicalDs1ExceededThresholdFEDaySEFSsTrap NOTIFICATION-TYPE
    OBJECTS { acChassisCurrentTime, acChassisRingId, acLogicalDs1ThresholdNodeId,
              acLogicalDs1ThresholdIndex }
    STATUS  current
    DESCRIPTION
    "The specified threshold for this interface has been exceeded."

    ::= { acLogicalDs1Traps 38 }
        
acLogicalDs1ExceededThresholdFEDayUASsTrap NOTIFICATION-TYPE
    OBJECTS { acChassisCurrentTime, acChassisRingId, acLogicalDs1ThresholdNodeId,
              acLogicalDs1ThresholdIndex }
    STATUS  current
    DESCRIPTION
    "The specified threshold for this interface has been exceeded."

    ::= { acLogicalDs1Traps 39 }
        
acLogicalDs1ExceededThresholdFEDayCSSsTrap NOTIFICATION-TYPE
    OBJECTS { acChassisCurrentTime, acChassisRingId, acLogicalDs1ThresholdNodeId,
              acLogicalDs1ThresholdIndex }
    STATUS  current
    DESCRIPTION
    "The specified threshold for this interface has been exceeded."

    ::= { acLogicalDs1Traps 40 }
        
acLogicalDs1ExceededThresholdFEDayLESsTrap NOTIFICATION-TYPE
    OBJECTS { acChassisCurrentTime, acChassisRingId, acLogicalDs1ThresholdNodeId,
              acLogicalDs1ThresholdIndex }
    STATUS  current
    DESCRIPTION
    "The specified threshold for this interface has been exceeded."

    ::= { acLogicalDs1Traps 41 }
        
acLogicalDs1ExceededThresholdFEDayPCVsTrap NOTIFICATION-TYPE
    OBJECTS { acChassisCurrentTime, acChassisRingId, acLogicalDs1ThresholdNodeId,
              acLogicalDs1ThresholdIndex }
    STATUS  current
    DESCRIPTION
    "The specified threshold for this interface has been exceeded."

    ::= { acLogicalDs1Traps 42 }
        
acLogicalDs1ExceededThresholdFEDayBESsTrap NOTIFICATION-TYPE
    OBJECTS { acChassisCurrentTime, acChassisRingId, acLogicalDs1ThresholdNodeId,
              acLogicalDs1ThresholdIndex }
    STATUS  current
    DESCRIPTION
    "The specified threshold for this interface has been exceeded."

    ::= { acLogicalDs1Traps 43 }
        
acLogicalDs1ExceededThresholdFEDayDMsTrap NOTIFICATION-TYPE
    OBJECTS { acChassisCurrentTime, acChassisRingId, acLogicalDs1ThresholdNodeId,
              acLogicalDs1ThresholdIndex }
    STATUS  current
    DESCRIPTION
    "The specified threshold for this interface has been exceeded."

    ::= { acLogicalDs1Traps 44 }


END
