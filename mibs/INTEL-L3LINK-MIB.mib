INTEL-L3LINK-MIB DEFINITIONS ::= BEGIN

-- Copyright (C) 1997 Intel Corporation. All rights reserved.
--
-- Proprietary Layer 3 link MIB
--
-- Build 1
--

IMPORTS
        mib2ext	                FROM INTEL-GEN-MIB
        OBJECT-TYPE             FROM RFC-1212;

l3Link              OBJECT IDENTIFIER ::= { mib2ext 12 }
  interface         OBJECT IDENTIFIER ::= { l3Link 1 }


l3lkInterfaceTable OBJECT-TYPE
    SYNTAX SEQUENCE OF L3lkInterfaceEntry
    ACCESS not-accessible
    STATUS mandatory
    DESCRIPTION
        ""
    ::= { interface 1 }

l3lkInterfaceEntry OBJECT-TYPE
    SYNTAX L3lkInterfaceEntry
    ACCESS not-accessible
    STATUS mandatory
    DESCRIPTION
        ""
    INDEX { l3lkInterfaceIfIndex }
    ::= { l3lkInterfaceTable 1 }

L3lkInterfaceEntry ::=
    SEQUENCE {
	l3lkInterfaceIfIndex
	    INTEGER,
	l3lkInterfaceVlanId
	    INTEGER,
	l3lkInterfaceStatus
	    INTEGER,
	l3lkInterfaceCreateObj
	    OCTET STRING (SIZE (3)),
	l3lkInterfaceDeleteObj
	    INTEGER
    }


l3lkInterfaceIfIndex OBJECT-TYPE
    SYNTAX INTEGER
    ACCESS read-only
    STATUS mandatory
    DESCRIPTION
        "Reference to ifIndex"
    ::= { l3lkInterfaceEntry 1 }


l3lkInterfaceVlanId OBJECT-TYPE
    SYNTAX INTEGER
    ACCESS read-write
    STATUS mandatory
    DESCRIPTION
        "The id of the vlan this table is based on"
    ::= { l3lkInterfaceEntry 2 }


l3lkInterfaceStatus OBJECT-TYPE
    SYNTAX INTEGER { enabled(1), disabled(2) }
    ACCESS read-write
    STATUS mandatory
    DESCRIPTION
        "The status of the layer 3 interface
		 which is the same as ifAdminStatus"
    ::= { l3lkInterfaceEntry 3 }


l3lkInterfaceCreateObj OBJECT-TYPE
    SYNTAX OCTET STRING (SIZE (3))
    ACCESS read-write
    STATUS mandatory
    DESCRIPTION
        "Create a non existing table entry. If the entry already exist,
        genError is returned.
         Binary format: [status(1 byte),vlanId(2 bytes)]"
    ::= { l3lkInterfaceEntry 4 }


l3lkInterfaceDeleteObj OBJECT-TYPE
    SYNTAX INTEGER { delete(1) }
    ACCESS read-write
    STATUS mandatory
    DESCRIPTION
        "Delete an existing table entry"
    ::= { l3lkInterfaceEntry 5 }



END
