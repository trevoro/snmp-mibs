-- *****************************************************************
-- tiaranet-pf.mib:  Tiara Networks Packet Filter MIB
--
-- July, 1st 1999, kumar
--
-- Copyright (c) 1998-2005 by Tiara Networks, Inc.
-- All rights reserved.
--
-- *****************************************************************

TIARA-PACKETFILTER-MIB DEFINITIONS ::= BEGIN

IMPORTS
	MODULE-IDENTITY, OBJECT-TYPE, 
		 Integer32, IpAddress,Counter32  FROM SNMPv2-SMI
	TruthValue, RowStatus            FROM SNMPv2-TC
	DisplayString                 FROM RFC1213-MIB
	tiaraIpIfIndex		FROM	TIARA-IP-MIB
	tiaraMgmt
                              FROM TIARA-NETWORKS-SMI; 

tiaraPacketFilterMib MODULE-IDENTITY
	LAST-UPDATED "9407272253Z" --to be corrected
	ORGANIZATION "Tiara Networks Inc."
	CONTACT-INFO
	 "       Tiara Networks
                        Customer Service

                Postal: 525 Race Street, Suite 100,
                        San Jose, CA 95126
                        USA

                   Tel: +1 408-216-4700
                   Fax: +1 408-216-4701

                E-mail: support@tiaranetworks.com"
	
	DESCRIPTION
		"The MIB module to describe Tiara's Packet Filter MIB"
	::= { tiaraMgmt 51 } 

--Tiara PacketFilter MIB

filterRuleClearCounters      OBJECT-TYPE
	SYNTAX          DisplayString 
	MAX-ACCESS      read-write
	STATUS          current
	DESCRIPTION     " This variable is used to clear counters for a given
                          Rule Set Name or All the counters. Whenever a set on 
                          this variable is done , the value given by the manager 
                          will be interpreted as the filter rule set name for 
                          which the counters will be cleared. 
                          As a special case if 'all' is the value of this 
                          variable then counters corresponding to all the 
                          filter rule set names will be cleared."
	DEFVAL { "" }
	::= {tiaraPacketFilterMib 1}


-- filterRule Name-Index table

filterNameIndexTable	OBJECT-TYPE
	SYNTAX			SEQUENCE OF FilterNameIndexEntry
        MAX-ACCESS		not-accessible
        STATUS			current
        DESCRIPTION
                "This Table maintains a mapping of
		 filter name and Filter Index"
        ::= {tiaraPacketFilterMib 2}



filterNameIndexEntry        OBJECT-TYPE
        SYNTAX                  FilterNameIndexEntry
        MAX-ACCESS              not-accessible
        STATUS                  current
        DESCRIPTION
		"An entry in the filterRuleNameIndexTable" 
	INDEX	{ filterNameIndex }
        ::= {filterNameIndexTable 1}


FilterNameIndexEntry ::= SEQUENCE {
	filterEntryName			DisplayString,
	filterNameIndex			Integer32,
	filterEntryRowStatus		RowStatus
	}


filterEntryName		OBJECT-TYPE
	SYNTAX			DisplayString
	MAX-ACCESS		read-create	
	STATUS			current
	DESCRIPTION 
		"A unique name for the filter rule"
	::= { filterNameIndexEntry  1 }

filterNameIndex			OBJECT-TYPE
        SYNTAX                  Integer32 
        MAX-ACCESS              not-accessible 
        STATUS                  current
        DESCRIPTION
                "A unique identifier for the filter rule"
        ::= { filterNameIndexEntry  2 }

filterEntryRowStatus	OBJECT-TYPE
        SYNTAX                  RowStatus 
        MAX-ACCESS              read-create
        STATUS                  current
        DESCRIPTION
                "Used to add or delete a row in the table"
        ::= { filterNameIndexEntry  3 }





-- filterRuleAssignTable definition

filterRuleAssignTable 	OBJECT-TYPE
	SYNTAX		SEQUENCE OF FilterRuleAssignTableEntry
	MAX-ACCESS	not-accessible
	STATUS 		current
	DESCRIPTION
		"FilterRuleAssign Table"
	::= {tiaraPacketFilterMib 3}

filterRuleAssignTableEntry	OBJECT-TYPE
	SYNTAX			FilterRuleAssignTableEntry
	MAX-ACCESS		not-accessible
	STATUS			current
	DESCRIPTION
		"An entry in the filterRuleName Table"
	INDEX	{ tiaraIpIfIndex}
	::= {filterRuleAssignTable 1}

FilterRuleAssignTableEntry ::= SEQUENCE {
         filterRuleSetNameIn              		DisplayString, 
         filterRuleSetNameOut              		DisplayString, 
	 filterRuleAssignTableRowStatus		 RowStatus
	}

filterRuleSetNameIn	OBJECT-TYPE
	SYNTAX	DisplayString
	MAX-ACCESS		read-create
	STATUS	current
	DESCRIPTION 
		" Rule Set Name for IN coming Direction" 
	DEFVAL { "" }
	::= { filterRuleAssignTableEntry 1}

filterRuleSetNameOut	OBJECT-TYPE
	SYNTAX	DisplayString
	MAX-ACCESS		read-create
	STATUS	current
	DESCRIPTION 
		" Rule Set Name for OUT going Direction" 
	DEFVAL { "" }
	::= { filterRuleAssignTableEntry 2}

filterRuleAssignTableRowStatus        OBJECT-TYPE
        SYNTAX  RowStatus
        MAX-ACCESS      read-create
        STATUS  current
        DESCRIPTION
                " Used to Add or Delete a Row in the table"
        ::= { filterRuleAssignTableEntry 3 }






--FilterRuleSetTable Definition
filterRuleSetTable 	OBJECT-TYPE
	SYNTAX		SEQUENCE OF FilterRuleSetTableEntry
	MAX-ACCESS	not-accessible
	STATUS 		current
	DESCRIPTION
		"Filter Rule SetTable"
	::= {tiaraPacketFilterMib 4}

filterRuleSetTableEntry	OBJECT-TYPE
	SYNTAX			FilterRuleSetTableEntry
	MAX-ACCESS		not-accessible
	STATUS			current
	DESCRIPTION
		"An entry in the Filter Rule Table"
	INDEX { filterNameIndex, filterRuleSetLineNo }
	::= {filterRuleSetTable 1}

FilterRuleSetTableEntry ::= SEQUENCE {
	filterRuleSetLineNo			Integer32,
        filterRuleName				DisplayString,
        filterRuleSetAction			INTEGER,	
	filterRuleSetProtocolType		INTEGER,
        filterRuleSetSrcIpAddr			IpAddress,
        filterRuleSetSrcMask		        IpAddress,	
        filterRuleSetDestIpAddr			IpAddress,  
        filterRuleSetDestMask			IpAddress, 
	filterRuleSetPrecedence			Integer32,
	filterRuleSetTos			Integer32,
	filterRuleSetIcmpType			Integer32,
	filterRuleSetIcmpCode			Integer32,
	filterRuleSetSrcPortOne			Integer32,	
	filterRuleSetSrcPortTwo			Integer32,	
	filterRuleSetDestPortOne		Integer32,	
	filterRuleSetDestPortTwo		Integer32,	
	filterRuleSetSrcRelationBetnPorts	INTEGER,
	filterRuleSetDestRelationBetnPorts	INTEGER,
	filterRuleSetTcpFlags			BITS,	
	filterRuleSetLogAction			TruthValue,	
	filterRuleSetConfigure			INTEGER,
	filterRuleSetTableRowStatus		RowStatus
	}


filterRuleSetLineNo  OBJECT-TYPE
        SYNTAX  Integer32 -- RANGE?
        MAX-ACCESS      not-accessible
        STATUS  current
        DESCRIPTION
	" Line Number where the Rule has to be inserted or an 
        invalid number (0XFFFF) when a row has to be appeded"
        ::= { filterRuleSetTableEntry 1 }

filterRuleName	OBJECT-TYPE
	SYNTAX	DisplayString
	MAX-ACCESS	read-create	
	STATUS	current
	DESCRIPTION 
		"A unique name for the filter rule"
	::= { filterRuleSetTableEntry 2 }

filterRuleSetAction	OBJECT-TYPE
	SYNTAX INTEGER {
		permit(1),
		deny(2),
		reject(3)
		}
	MAX-ACCESS	read-create
	STATUS	current
	DESCRIPTION 
		" Specifies Action to be taken by the filter when a 
                  match occurs to corresponding filter rule"
	::= { filterRuleSetTableEntry 3 }

filterRuleSetProtocolType OBJECT-TYPE
	SYNTAX INTEGER {
			icmp (1) ,
			tcp (6),
			udp(17),
			ip(0)
		}
        MAX-ACCESS      read-create
        STATUS  current
        DESCRIPTION
                " where protocol type ip will have value "
        ::= { filterRuleSetTableEntry 4 }

filterRuleSetSrcIpAddr	OBJECT-TYPE
	SYNTAX		IpAddress
	MAX-ACCESS	read-create
	STATUS	current
	DESCRIPTION 
		" Number of the Source Network"
	::= { filterRuleSetTableEntry 5 }

filterRuleSetSrcMask  OBJECT-TYPE
        SYNTAX  	IpAddress
        MAX-ACCESS      read-create
        STATUS  current
        DESCRIPTION
                " Wild card Address to be applied to source Address"
	DEFVAL { 0 }
        ::= { filterRuleSetTableEntry 6 } 

filterRuleSetDestIpAddr	OBJECT-TYPE
	SYNTAX		IpAddress	
	MAX-ACCESS	read-create
	STATUS	current
	DESCRIPTION 
		" Number of the Destination Network"
	::= { filterRuleSetTableEntry 7 }

filterRuleSetDestMask  OBJECT-TYPE
        SYNTAX  	IpAddress
        MAX-ACCESS      read-create
        STATUS  current
        DESCRIPTION
                " Wild card Address to be applied to destination Address"
	DEFVAL { 0 }
        ::= { filterRuleSetTableEntry 8 } 

filterRuleSetPrecedence  OBJECT-TYPE
        SYNTAX  Integer32(0..7)
        MAX-ACCESS      read-create
        STATUS  current
        DESCRIPTION
                "Ip address  precedence feild can be used to filter packets"
	DEFVAL { 0 } -- CHECK IT OUT
        ::= { filterRuleSetTableEntry 9 } 

filterRuleSetTos  OBJECT-TYPE
        SYNTAX  Integer32(0..15)
        MAX-ACCESS      read-create
        STATUS  current
        DESCRIPTION
                " Ip header TOS feild can be used to filter the packets"
	DEFVAL { 0 } -- CHECK IT OUT
        ::= { filterRuleSetTableEntry 10 }

filterRuleSetIcmpType  OBJECT-TYPE
        SYNTAX  Integer32(0..255)
        MAX-ACCESS      read-create
        STATUS  current
        DESCRIPTION
                " ICMP message type  can be used to filter the packets "
	DEFVAL { 0 } -- CHECK IT OUT
        ::= { filterRuleSetTableEntry 11 } 

filterRuleSetIcmpCode  OBJECT-TYPE
        SYNTAX  Integer32(0..255)
        MAX-ACCESS      read-create
        STATUS  current
        DESCRIPTION
                "ICMP message Code  can be used to filter the packets"
	DEFVAL { 0 } -- CHECK IT OUT
        ::= { filterRuleSetTableEntry 12 } 

filterRuleSetSrcPortOne		OBJECT-TYPE
        SYNTAX 	Integer32(0..65535) 
        MAX-ACCESS      read-create
        STATUS  current
        DESCRIPTION
                " Source Port 1"
	DEFVAL { 0 } -- CHECK IT OUT
        ::= { filterRuleSetTableEntry 13 }

filterRuleSetSrcPortTwo		OBJECT-TYPE
        SYNTAX 	Integer32(0..65535) 
        MAX-ACCESS      read-create
        STATUS  current
        DESCRIPTION
                " Source Port 2"
	DEFVAL { 0 } -- CHECK IT OUT
        ::= { filterRuleSetTableEntry 14 }

filterRuleSetDestPortOne	OBJECT-TYPE
        SYNTAX 	Integer32(0..65535) 
        MAX-ACCESS      read-create
        STATUS  current
        DESCRIPTION
                " Destination Port 1"
	DEFVAL { 0 } -- CHECK IT OUT
        ::= { filterRuleSetTableEntry 15 }

filterRuleSetDestPortTwo	OBJECT-TYPE
        SYNTAX 	Integer32(0..65535) 
        MAX-ACCESS      read-create
        STATUS  current
        DESCRIPTION
                " Destination Port 2"
	DEFVAL { 0 } -- CHECK IT OUT
        ::= { filterRuleSetTableEntry 16 }

filterRuleSetSrcRelationBetnPorts  OBJECT-TYPE
        SYNTAX INTEGER {
                equalto(1),
                notequalto(2),
                lessthan(3),
                greaterthan(4),
                lessthanorequalto(5),
                greaterthanorequalto(6),
                range(7),
                none(8)
                }  
        MAX-ACCESS      read-create
        STATUS  current
        DESCRIPTION
                " relation between the Source port"
        DEFVAL { none }
        ::= { filterRuleSetTableEntry 17 }

filterRuleSetDestRelationBetnPorts  OBJECT-TYPE
        SYNTAX INTEGER {
                equalto(1),
                notequalto(2),
                lessthan(3),
                greaterthan(4),
                lessthanorequalto(5),
                greaterthanorequalto(6),
                range(7),
                none(8)
                }  
        MAX-ACCESS      read-create
        STATUS  current
        DESCRIPTION
                " relation between the Destination ports"
        DEFVAL { none }
        ::= { filterRuleSetTableEntry 18 }


filterRuleSetTcpFlags  OBJECT-TYPE
        SYNTAX	BITS
			 { fin(0), 
			   syn(1), 
			   rst(2), 
			   psh(3), 
			   ack(4), 
			   urg(5),
		       estaslished(6)} 
        MAX-ACCESS      read-create
        STATUS  current
        DESCRIPTION
                " TCP flags  can be used to filter the packets"
        ::= { filterRuleSetTableEntry 19 }

filterRuleSetLogAction  OBJECT-TYPE
        SYNTAX	TruthValue	
        MAX-ACCESS      read-create
        STATUS  current
        DESCRIPTION
                " When a rule match occurs a logging message about the packet 
	  	  which the match occured the entry will be logged"
	DEFVAL { false }
        ::= { filterRuleSetTableEntry 20 }

filterRuleSetConfigure  OBJECT-TYPE
        SYNTAX  INTEGER		{
			add(1),
			insert(2)
			}
        MAX-ACCESS     read-create 
        STATUS  current
        DESCRIPTION
                " This variable is used to append  or insert  a given filter 
                  rule to the filter rule set. If 'insert' is the command the 
                  linenumber at which the rule is inserted should be available 
                  in filterRuleSetLineNumber.'If command is 'add' then the line
                  number should contain the invalid value (OxFFFF).
                  Incase of 'add' to know the line number at which the filter 
                  rule was added the manager should do a SNMP walk "

::= { filterRuleSetTableEntry 21 }

filterRuleSetTableRowStatus	OBJECT-TYPE
        SYNTAX  RowStatus
        MAX-ACCESS      read-create
        STATUS  current
        DESCRIPTION
                " Used to Add or Delete a Row in the table"
        ::= { filterRuleSetTableEntry 22 }

--FilterRuleStats Table Definition

filterRuleStatsTable 	OBJECT-TYPE
	SYNTAX		SEQUENCE OF FilterRuleStatsTableEntry
	MAX-ACCESS	not-accessible
	STATUS 		current
	DESCRIPTION
		"Filter Rule Statistics Table"
	::= {tiaraPacketFilterMib 5}

filterRuleStatsTableEntry	OBJECT-TYPE
	SYNTAX			FilterRuleStatsTableEntry
	MAX-ACCESS		not-accessible
	STATUS			current
	DESCRIPTION
		"An entry in the Filter Rule Statistics Table"
	INDEX	{ tiaraIpIfIndex }
	::= {filterRuleStatsTable 1}

FilterRuleStatsTableEntry ::= SEQUENCE {
	filterRuleStatsInBoundPermittedPkts     Counter32,
        filterRuleStatsInBoundDeniedPkts      Counter32,
        filterRuleStatsInBoundUnMatchedPkts        Counter32,
	filterRuleStatsOutBoundPermittedPkts     Counter32,
        filterRuleStatsOutBoundDeniedPkts      Counter32,
        filterRuleStatsOutBoundUnMatchedPkts        Counter32,
        filterRuleStatsNonIpInBoundPkts                 Counter32,
        filterRuleStatsNonIpOutBoundPkts               Counter32,
        filterRuleStatsBadIpInBoundPkts                Counter32,
        filterRuleStatsBadIpOutBoundPkts               Counter32
	}
	
filterRuleStatsInBoundPermittedPkts	OBJECT-TYPE
	SYNTAX	Counter32
	MAX-ACCESS	read-only
	STATUS	current
	DESCRIPTION 
		" Number of InBound Permitted Packets"
	::= { filterRuleStatsTableEntry 1 }

filterRuleStatsInBoundDeniedPkts    OBJECT-TYPE
        SYNTAX  Counter32
        MAX-ACCESS      read-only
        STATUS  current
        DESCRIPTION
                " Number of InBound Denied Packets"
        ::= { filterRuleStatsTableEntry 2 }

filterRuleStatsInBoundUnMatchedPkts	OBJECT-TYPE
	SYNTAX	Counter32
	MAX-ACCESS	read-only
	STATUS	current
	DESCRIPTION 
		" Number of InBound UnMatched Packets"
	::= { filterRuleStatsTableEntry 3 }

filterRuleStatsOutBoundPermittedPkts	OBJECT-TYPE
	SYNTAX	Counter32
	MAX-ACCESS	read-only
	STATUS	current
	DESCRIPTION 
		" Number of OutBound Permitted Packets"
	::= { filterRuleStatsTableEntry 4 }

filterRuleStatsOutBoundDeniedPkts    OBJECT-TYPE
        SYNTAX  Counter32
        MAX-ACCESS      read-only
        STATUS  current
        DESCRIPTION
                " Number of OutBound Denied Packets"
        ::= { filterRuleStatsTableEntry 5 }

filterRuleStatsOutBoundUnMatchedPkts	OBJECT-TYPE
	SYNTAX	Counter32
	MAX-ACCESS	read-only
	STATUS	current
	DESCRIPTION 
		" Number of OutBound UnMatched Packets"
	::= { filterRuleStatsTableEntry 6 }

filterRuleStatsNonIpInBoundPkts    OBJECT-TYPE
        SYNTAX  Counter32
        MAX-ACCESS      read-only
        STATUS  current
        DESCRIPTION
                " Number of Non Ip  InBound Packets"
        ::= { filterRuleStatsTableEntry 7 }

filterRuleStatsNonIpOutBoundPkts    OBJECT-TYPE
        SYNTAX  Counter32
        MAX-ACCESS      read-only
        STATUS  current
        DESCRIPTION
                " Number of Non Ip  OutBound Packets"
        ::= { filterRuleStatsTableEntry 8 }

filterRuleStatsBadIpInBoundPkts    OBJECT-TYPE
        SYNTAX  Counter32
        MAX-ACCESS      read-only
        STATUS  current
        DESCRIPTION
                " Number of Bad Non Ip  InBound Packets"

        ::= { filterRuleStatsTableEntry 9 }

filterRuleStatsBadIpOutBoundPkts    OBJECT-TYPE
        SYNTAX  Counter32
        MAX-ACCESS      read-only
        STATUS  current
        DESCRIPTION
                " Number of Bad Non Ip  OutBound Packets"
        ::= { filterRuleStatsTableEntry 10 }

END
