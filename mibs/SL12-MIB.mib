--  sl12 MIB version 3.10 8 Apr 05
--  for use with 3.10 and up
--  added ES definitions, subtree 40.9 for status and 40.10 for config
--  deprecated SNMP Manager 1, 40.1.4
--  added contact 6 snmp objects and traps
--  added traps for eventsensor points
--  added analog1 and analog2 names
--  modified analog1 and analog2 traps to send analog names
--  input78mode changed to read-only, deprecated
--  added humidityName
--  added temperatureName
--  modified sensor name comments to indicate 30 character wide names


SL12-MIB DEFINITIONS ::= BEGIN

IMPORTS
 private, internet, mgmt, NetworkAddress, IpAddress,
 Counter, Gauge, TimeTicks, enterprises
    FROM RFC1155-SMI 
 OBJECT-TYPE
    FROM RFC-1212
 DisplayString
    FROM SNMPv2-TC
 TRAP-TYPE
    FROM RFC-1215 ;



  asentria  OBJECT IDENTIFIER   ::= { enterprises 3052 }
  --1.3.6.1.4.1.3052

  sl12  OBJECT IDENTIFIER      ::= { asentria 41 }
  --1.3.6.1.4.1.3052.41

  device OBJECT IDENTIFIER  ::= { sl12 1 }
  --1.3.6.1.4.1.3052.41.1

  contacts OBJECT IDENTIFIER  ::= { sl12 2 }
  --1.3.6.1.4.1.3052.41.2

  relays OBJECT IDENTIFIER  ::= { sl12 3 }
  --1.3.6.1.4.1.3052.41.3

  tempsensor OBJECT IDENTIFIER  ::= { sl12 4 }
  --1.3.6.1.4.1.3052.41.4

  humiditysensor OBJECT IDENTIFIER  ::= { sl12 5 }
  --1.3.6.1.4.1.3052.41.5

  passthrough OBJECT IDENTIFIER ::= { sl12 6 }
  --1.3.6.1.4.1.3052.41.6

  ftp OBJECT IDENTIFIER ::= { sl12 7 }
  --1.3.6.1.4.1.3052.41.7

  analog OBJECT IDENTIFIER ::= { sl12 8 }
  --1.3.6.1.4.1.3052.41.8

  eventSensorStatus OBJECT IDENTIFIER ::= { sl12 10 }
  --1.3.6.1.4.1.3052.41.10
  
  eventSensorConfig OBJECT IDENTIFIER ::= { sl12 11 }
  --1.3.6.1.4.1.3052.41.11
  
  techsupport OBJECT IDENTIFIER  ::= { sl12 99 }
  --1.3.6.1.4.1.3052.41.99

  mibend  OBJECT IDENTIFIER  ::= { sl12 100 }
  --1.3.6.1.4.1.3052.41.100

  contact1 OBJECT IDENTIFIER  ::= { contacts 1 }
  --1.3.6.1.4.1.3052.41.2.1

  contact2 OBJECT IDENTIFIER  ::= { contacts 2 }
  --1.3.6.1.4.1.3052.41.2.2

  contact3 OBJECT IDENTIFIER  ::= { contacts 3 }
  --1.3.6.1.4.1.3052.41.2.3

  contact4 OBJECT IDENTIFIER  ::= { contacts 4 }
  --1.3.6.1.4.1.3052.41.2.4

  contact5 OBJECT IDENTIFIER  ::= { contacts 5 }
  --1.3.6.1.4.1.3052.41.2.5

  contact6 OBJECT IDENTIFIER  ::= { contacts 6 }
  --1.3.6.1.4.1.3052.41.2.6

  relay1 OBJECT IDENTIFIER  ::= { relays 1 }
  --1.3.6.1.4.1.3052.41.3.1

  relay2 OBJECT IDENTIFIER  ::= { relays 2 }
  --1.3.6.1.4.1.3052.41.3.2

  analog1 OBJECT IDENTIFIER  ::= { analog 1 }
  --1.3.6.1.4.1.3052.41.8.1

  analog2 OBJECT IDENTIFIER  ::= { analog 2 }
  --1.3.6.1.4.1.3052.41.8.2

-- device section

serialNumber OBJECT-TYPE
  SYNTAX DisplayString
  ACCESS read-only
  STATUS mandatory
  DESCRIPTION
  "8-character serial number"
  ::= { device 1 }
  --1.3.6.1.4.1.3052.41.1.1

firmwareVersion OBJECT-TYPE
  SYNTAX DisplayString
  ACCESS read-only
  STATUS mandatory
  DESCRIPTION
  "Firmware version text string"
  ::= { device 2 }
  --1.3.6.1.4.1.3052.41.1.2

siteID OBJECT-TYPE
  SYNTAX DisplayString
  ACCESS read-write
  STATUS mandatory
  DESCRIPTION
  "Site Identifier, up to 12 characters."
  ::= { device 3 }
  --1.3.6.1.4.1.3052.41.1.3

snmpManager OBJECT-TYPE
  SYNTAX IpAddress
  ACCESS read-write
  STATUS deprecated
  DESCRIPTION
  "This is snmp manager #1 "
  ::= { device 4 }
  --1.3.6.1.4.1.3052.41.1.4

forceTraps OBJECT-TYPE
  SYNTAX INTEGER
  ACCESS read-write
  STATUS mandatory
  DESCRIPTION
  "Any write non-zero forces set of traps to be send to the SNMP Manager"
  ::= { device 6 }
  --1.3.6.1.4.1.3052.41.1.6

thisTrapText OBJECT-TYPE
  SYNTAX DisplayString
  ACCESS read-write
  STATUS mandatory
  DESCRIPTION
  "A text string included in all traps"
  ::= { device 7 }
  --1.3.6.1.4.1.3052.41.1.7

alarmStatus OBJECT-TYPE
  SYNTAX DisplayString
  ACCESS read-only
  STATUS mandatory
  DESCRIPTION
  "A text status of all alarms"
  ::= { device 8 }
  --1.3.6.1.4.1.3052.41.1.8

snmpManager1 OBJECT-TYPE
  SYNTAX IpAddress
  ACCESS read-write
  STATUS mandatory
  DESCRIPTION
  "SNMP manager #1 "
  ::= { device 9 }
  --1.3.6.1.4.1.3052.41.1.9

snmpManager2 OBJECT-TYPE
  SYNTAX IpAddress
  ACCESS read-write
  STATUS mandatory
  DESCRIPTION
  "SNMP manager #2 "
  ::= { device 10 }
  --1.3.6.1.4.1.3052.41.1.10

snmpManager3 OBJECT-TYPE
  SYNTAX IpAddress
  ACCESS read-write
  STATUS mandatory
  DESCRIPTION
  "SNMP manager #3 "
  ::= { device 11 }
  --1.3.6.1.4.1.3052.41.1.11

snmpManager4 OBJECT-TYPE
  SYNTAX IpAddress
  ACCESS read-write
  STATUS mandatory
  DESCRIPTION
  "SNMP manager #4 "
  ::= { device 12 }
  --1.3.6.1.4.1.3052.41.1.12

statusRepeatHours OBJECT-TYPE
    SYNTAX INTEGER
    ACCESS read-write
    STATUS mandatory
    DESCRIPTION
    "0=none, 1-24 Number of Hours between Status Traps being Sent"
    ::= { device 13 }
    --1.3.6.1.4.1.3052.41.1.13

serialTimeout OBJECT-TYPE
    SYNTAX INTEGER
    ACCESS read-write
    STATUS mandatory
    DESCRIPTION
    "5-30, Minutes of non-activity timeout on serial setup"
    ::= { device 14 }
    --1.3.6.1.4.1.3052.41.1.14

powerupTrapsend OBJECT-TYPE
    SYNTAX INTEGER
    ACCESS read-write
    STATUS mandatory
    DESCRIPTION
    "0-no, 1-yes, send traps for all sensors on powerup"
    ::= { device 15 }
    --1.3.6.1.4.1.3052.41.1.15

netlossTrapsend OBJECT-TYPE
    SYNTAX INTEGER
    ACCESS read-write
    STATUS mandatory
    DESCRIPTION
    "0-no, 1-yes, send traps for detected netloss and back up"
    ::= { device 16 }
    --1.3.6.1.4.1.3052.41.1.16

buildID OBJECT-TYPE
    SYNTAX DisplayString
    ACCESS read-only
    STATUS mandatory
    DESCRIPTION
    "5-chars max text for build identifier"
    ::= { device 17 }
    --1.3.6.1.4.1.3052.41.1.17

-- contacts section

contact1Name OBJECT-TYPE
    SYNTAX DisplayString
    ACCESS read-write
    STATUS mandatory
    DESCRIPTION
    "Name for contact, up to 30 characters"
    ::= { contact1 1 }
    --1.3.6.1.4.1.3052.41.2.1.1

contact1State OBJECT-TYPE
    SYNTAX INTEGER
    ACCESS read-only
    STATUS mandatory
    DESCRIPTION
    "Current State of Contact, 0-open 1-closed"
    ::= { contact1 2 }
    --1.3.6.1.4.1.3052.41.2.1.2

contact1AlarmEnable OBJECT-TYPE
    SYNTAX INTEGER
    ACCESS read-write
    STATUS mandatory
    DESCRIPTION
    "0-alarms disabled 1-alarms enabled"
    ::= { contact1 3 }
    --1.3.6.1.4.1.3052.41.2.1.3

contact1ActiveDirection OBJECT-TYPE
    SYNTAX INTEGER
    ACCESS read-write
    STATUS mandatory
    DESCRIPTION
    "0-alarm on open 1-alarm on closed"
    ::= { contact1 4 }
    --1.3.6.1.4.1.3052.41.2.1.4

contact1Threshold OBJECT-TYPE
    SYNTAX INTEGER
    ACCESS read-write
    STATUS mandatory
    DESCRIPTION
    "Number of seconds that the contact must remain in a state before generating a trap, range 0-255"
    ::= { contact1 5 }
    --1.3.6.1.4.1.3052.41.2.1.5

contact1ReturnNormalTrap OBJECT-TYPE
    SYNTAX INTEGER
    ACCESS read-write
    STATUS mandatory
    DESCRIPTION
    "0-return to normal traps not sent, 1-sent"
    ::= { contact1 6 }
    --1.3.6.1.4.1.3052.41.2.1.6

contact1TrapRepeat OBJECT-TYPE
    SYNTAX INTEGER
    ACCESS read-write
    STATUS mandatory
    DESCRIPTION
    "0-no repeats.  1-255 number of minutes between repeats of alarm traps."
    ::= { contact1 7 }
    --1.3.6.1.4.1.3052.41.2.1.7

contact1Severity OBJECT-TYPE
    SYNTAX INTEGER
    ACCESS read-write
    STATUS mandatory
    DESCRIPTION
    "1-minor 2-major 3-critical 4-severe 5-warning"
    ::= { contact1 8 }
    --1.3.6.1.4.1.3052.41.2.1.8

contact2Name OBJECT-TYPE
    SYNTAX DisplayString
    ACCESS read-write
    STATUS mandatory
    DESCRIPTION
    "Name for contact, up to 30 characters"
    ::= { contact2 1 }
    --1.3.6.1.4.1.3052.41.2.2.1

contact2State OBJECT-TYPE
    SYNTAX INTEGER
    ACCESS read-only
    STATUS mandatory
    DESCRIPTION
    "Current State of Contact, 0-open 1-closed"
    ::= { contact2 2 }
    --1.3.6.1.4.1.3052.41.2.2.2

contact2AlarmEnable OBJECT-TYPE
    SYNTAX INTEGER
    ACCESS read-write
    STATUS mandatory
    DESCRIPTION
    "0-no alarms 1-alarms enabled"
    ::= { contact2 3 }
    --1.3.6.1.4.1.3052.41.2.2.3

contact2ActiveDirection OBJECT-TYPE
    SYNTAX INTEGER
    ACCESS read-write
    STATUS mandatory
    DESCRIPTION
    "0-alarm on open 1-alarm on closed"
    ::= { contact2 4 }
    --1.3.6.1.4.1.3052.41.2.2.4

contact2Threshold OBJECT-TYPE
    SYNTAX INTEGER
    ACCESS read-write
    STATUS mandatory
    DESCRIPTION
    "Number of seconds must be in a state to be 'open' or 'closed'"
    ::= { contact2 5 }
    --1.3.6.1.4.1.3052.41.2.2.5

contact2ReturnNormalTrap OBJECT-TYPE
    SYNTAX INTEGER
    ACCESS read-write
    STATUS mandatory
    DESCRIPTION
    "0-not sent, 1-sent"
    ::= { contact2 6 }
    --1.3.6.1.4.1.3052.41.2.2.6

contact2TrapRepeat OBJECT-TYPE
    SYNTAX INTEGER
    ACCESS read-write
    STATUS mandatory
    DESCRIPTION
    "0-no repeats.  1-255 number of minutes between repeats of alarm traps"
    ::= { contact2 7 }
    --1.3.6.1.4.1.3052.41.2.2.7

contact2Severity OBJECT-TYPE
    SYNTAX INTEGER
    ACCESS read-write
    STATUS mandatory
    DESCRIPTION
    "1-minor 2-major 3-critical 4-severe 5-warning"
    ::= { contact2 8 }
    --1.3.6.1.4.1.3052.41.2.2.8

contact3Name OBJECT-TYPE
    SYNTAX DisplayString
    ACCESS read-write
    STATUS mandatory
    DESCRIPTION
    "Name for contact, up to 30 characters"
    ::= { contact3 1 }
    --1.3.6.1.4.1.3052.41.2.3.1

contact3State OBJECT-TYPE
    SYNTAX INTEGER
    ACCESS read-only
    STATUS mandatory
    DESCRIPTION
    "Current State of Contact, 0-open 1-closed"
    ::= { contact3 2 }
    --1.3.6.1.4.1.3052.41.2.3.2

contact3AlarmEnable OBJECT-TYPE
    SYNTAX INTEGER
    ACCESS read-write
    STATUS mandatory
    DESCRIPTION
    "0-no alarms 1-alarms enabled"
    ::= { contact3 3 }
    --1.3.6.1.4.1.3052.41.2.3.3

contact3ActiveDirection OBJECT-TYPE
    SYNTAX INTEGER
    ACCESS read-write
    STATUS mandatory
    DESCRIPTION
    "0-alarm on open 1-alarm on closed"
    ::= { contact3 4 }
    --1.3.6.1.4.1.3052.41.2.3.4

contact3Threshold OBJECT-TYPE
    SYNTAX INTEGER
    ACCESS read-write
    STATUS mandatory
    DESCRIPTION
    "Number of seconds must be in a state to be 'open' or 'closed'"
    ::= { contact3 5 }
    --1.3.6.1.4.1.3052.41.2.3.5

contact3ReturnNormalTrap OBJECT-TYPE
    SYNTAX INTEGER
    ACCESS read-write
    STATUS mandatory
    DESCRIPTION
    "0-not sent, 1-sent"
    ::= { contact3 6 }
    --1.3.6.1.4.1.3052.41.2.3.6

contact3TrapRepeat OBJECT-TYPE
    SYNTAX INTEGER
    ACCESS read-write
    STATUS mandatory
    DESCRIPTION
    "0-no repeats.  1-255 number of minutes between repeats of alarm traps"
    ::= { contact3 7 }
    --1.3.6.1.4.1.3052.41.2.3.7

contact3Severity OBJECT-TYPE
    SYNTAX INTEGER
    ACCESS read-write
    STATUS mandatory
    DESCRIPTION
    "1-minor 2-major 3-critical 4-severe 5-warning"
    ::= { contact3 8 }
    --1.3.6.1.4.1.3052.41.2.3.8

contact4Name OBJECT-TYPE
    SYNTAX DisplayString
    ACCESS read-write
    STATUS mandatory
    DESCRIPTION
    "Name for contact, up to 30 characters"
    ::= { contact4 1 }
    --1.3.6.1.4.1.3052.41.2.4.1

contact4State OBJECT-TYPE
    SYNTAX INTEGER
    ACCESS read-only
    STATUS mandatory
    DESCRIPTION
    "Current State of Contact, 0-open 1-closed"
    ::= { contact4 2 }
    --1.3.6.1.4.1.3052.41.2.4.2

contact4AlarmEnable OBJECT-TYPE
    SYNTAX INTEGER
    ACCESS read-write
    STATUS mandatory
    DESCRIPTION
    "0-no alarms 1-alarms enabled"
    ::= { contact4 3 }
    --1.3.6.1.4.1.3052.41.2.4.3

contact4ActiveDirection OBJECT-TYPE
    SYNTAX INTEGER
    ACCESS read-write
    STATUS mandatory
    DESCRIPTION
    "0-alarm on open 1-alarm on closed"
    ::= { contact4 4 }
    --1.3.6.1.4.1.3052.41.2.4.4

contact4Threshold OBJECT-TYPE
    SYNTAX INTEGER
    ACCESS read-write
    STATUS mandatory
    DESCRIPTION
    "Number of seconds must be in a state to be 'open' or 'closed'"
    ::= { contact4 5 }
    --1.3.6.1.4.1.3052.41.2.4.5

contact4ReturnNormalTrap OBJECT-TYPE
    SYNTAX INTEGER
    ACCESS read-write
    STATUS mandatory
    DESCRIPTION
    "0-not sent, 1-sent"
    ::= { contact4 6 }
    --1.3.6.1.4.1.3052.41.2.4.6

contact4TrapRepeat OBJECT-TYPE
    SYNTAX INTEGER
    ACCESS read-write
    STATUS mandatory
    DESCRIPTION
    "0-no repeats.  1-255 number of minutes between repeats of alarm traps"
    ::= { contact4 7 }
    --1.3.6.1.4.1.3052.41.2.4.7

contact4Severity OBJECT-TYPE
    SYNTAX INTEGER
    ACCESS read-write
    STATUS mandatory
    DESCRIPTION
    "1-minor 2-major 3-critical 4-severe 5-warning"
    ::= { contact4 8 }
    --1.3.6.1.4.1.3052.41.2.4.8

contact5Name OBJECT-TYPE
    SYNTAX DisplayString
    ACCESS read-write
    STATUS mandatory
    DESCRIPTION
    "Name for contact, up to 30 characters"
    ::= { contact5 1 }
    --1.3.6.1.4.1.3052.41.2.5.1

contact5State OBJECT-TYPE
    SYNTAX INTEGER
    ACCESS read-only
    STATUS mandatory
    DESCRIPTION
    "Current State of Contact, 0-open 1-closed"
    ::= { contact5 2 }
    --1.3.6.1.4.1.3052.41.2.5.2

contact5AlarmEnable OBJECT-TYPE
    SYNTAX INTEGER
    ACCESS read-write
    STATUS mandatory
    DESCRIPTION
    "0-no alarms 1-alarms enabled"
    ::= { contact5 3 }
    --1.3.6.1.4.1.3052.41.2.5.3

contact5ActiveDirection OBJECT-TYPE
    SYNTAX INTEGER
    ACCESS read-write
    STATUS mandatory
    DESCRIPTION
    "0-alarm on open 1-alarm on closed"
    ::= { contact5 4 }
    --1.3.6.1.4.1.3052.41.2.5.4

contact5Threshold OBJECT-TYPE
    SYNTAX INTEGER
    ACCESS read-write
    STATUS mandatory
    DESCRIPTION
    "Number of seconds must be in a state to be 'open' or 'closed'"
    ::= { contact5 5 }
    --1.3.6.1.4.1.3052.41.2.5.5

contact5ReturnNormalTrap OBJECT-TYPE
    SYNTAX INTEGER
    ACCESS read-write
    STATUS mandatory
    DESCRIPTION
    "0-not sent, 1-sent"
    ::= { contact5 6 }
    --1.3.6.1.4.1.3052.41.2.5.6

contact5TrapRepeat OBJECT-TYPE
    SYNTAX INTEGER
    ACCESS read-write
    STATUS mandatory
    DESCRIPTION
    "0-no repeats.  1-255 number of minutes between repeats of alarm traps"
    ::= { contact5 7 }
    --1.3.6.1.4.1.3052.41.2.5.7

contact5Severity OBJECT-TYPE
    SYNTAX INTEGER
    ACCESS read-write
    STATUS mandatory
    DESCRIPTION
    "1-minor 2-major 3-critical 4-severe 5-warning"
    ::= { contact5 8 }
    --1.3.6.1.4.1.3052.41.2.5.8

contact6Name OBJECT-TYPE
    SYNTAX DisplayString
    ACCESS read-write
    STATUS mandatory
    DESCRIPTION
    "Name for contact, up to 30 characters"
    ::= { contact6 1 }
    --1.3.6.1.4.1.3052.41.2.6.1

contact6State OBJECT-TYPE
    SYNTAX INTEGER
    ACCESS read-only
    STATUS mandatory
    DESCRIPTION
    "Current State of Contact, 0-open 1-closed"
    ::= { contact6 2 }
    --1.3.6.1.4.1.3052.41.2.6.2

contact6AlarmEnable OBJECT-TYPE
    SYNTAX INTEGER
    ACCESS read-write
    STATUS mandatory
    DESCRIPTION
    "0-no alarms 1-alarms enabled"
    ::= { contact6 3 }
    --1.3.6.1.4.1.3052.41.2.6.3

contact6ActiveDirection OBJECT-TYPE
    SYNTAX INTEGER
    ACCESS read-write
    STATUS mandatory
    DESCRIPTION
    "0-alarm on open 1-alarm on closed"
    ::= { contact6 4 }
    --1.3.6.1.4.1.3052.41.2.6.4

contact6Threshold OBJECT-TYPE
    SYNTAX INTEGER
    ACCESS read-write
    STATUS mandatory
    DESCRIPTION
    "Number of seconds must be in a state to be 'open' or 'closed'"
    ::= { contact6 5 }
    --1.3.6.1.4.1.3052.41.2.6.5

contact6ReturnNormalTrap OBJECT-TYPE
    SYNTAX INTEGER
    ACCESS read-write
    STATUS mandatory
    DESCRIPTION
    "0-not sent, 1-sent"
    ::= { contact6 6 }
    --1.3.6.1.4.1.3052.41.2.6.6

contact6TrapRepeat OBJECT-TYPE
    SYNTAX INTEGER
    ACCESS read-write
    STATUS mandatory
    DESCRIPTION
    "0-no repeats.  1-255 number of minutes between repeats of alarm traps."
    ::= { contact6 7 }
    --1.3.6.1.4.1.3052.41.2.6.7

contact6Severity OBJECT-TYPE
    SYNTAX INTEGER
    ACCESS read-write
    STATUS mandatory
    DESCRIPTION
    "1-minor 2-major 3-critical 4-severe 5-warning"
    ::= { contact6 8 }
    --1.3.6.1.4.1.3052.41.2.6.8

-- relays section

relay1Name OBJECT-TYPE
    SYNTAX DisplayString
    ACCESS read-write
    STATUS mandatory
    DESCRIPTION
    "Name for relay, up to 30 characters"
    ::= { relay1 1 }
    --1.3.6.1.4.1.3052.41.3.1.1

relay1CurrentState OBJECT-TYPE
    SYNTAX INTEGER
    ACCESS read-write
    STATUS mandatory
    DESCRIPTION
    "0-opened, 1-closed"
    ::= { relay1 2 }
    --1.3.6.1.4.1.3052.41.3.1.2

relay1PowerupState OBJECT-TYPE
    SYNTAX INTEGER
    ACCESS read-write
    STATUS mandatory
    DESCRIPTION
    "0-opened, 1-closed"
    ::= { relay1 3 }
    --1.3.6.1.4.1.3052.41.3.1.3

relay2Name OBJECT-TYPE
    SYNTAX DisplayString
    ACCESS read-write
    STATUS mandatory
    DESCRIPTION
    "Name for relay, up to 30 characters"
    ::= { relay2 1 }
    --1.3.6.1.4.1.3052.41.3.2.1

relay2CurrentState OBJECT-TYPE
    SYNTAX INTEGER
    ACCESS read-write
    STATUS mandatory
    DESCRIPTION
    "0-opened, 1-closed"
    ::= { relay2 2 }
    --1.3.6.1.4.1.3052.41.3.2.2

relay2PowerupState OBJECT-TYPE
    SYNTAX INTEGER
    ACCESS read-write
    STATUS mandatory
    DESCRIPTION
    "0-opened, 1-closed"
    ::= { relay2 3 }
    --1.3.6.1.4.1.3052.41.3.2.3


-- temp sensor section

tempValue OBJECT-TYPE
    SYNTAX INTEGER
    ACCESS read-only
    STATUS mandatory
    DESCRIPTION
    "Current Temperature Value, in C or F based on 1.3.6.1.4.1.3052.41.4.10"
    ::= { tempsensor 1 }
    --1.3.6.1.4.1.3052.41.4.1

tempAlarmEnable OBJECT-TYPE
    SYNTAX INTEGER
    ACCESS read-write
    STATUS mandatory
    DESCRIPTION
    "0=alarms disabled, 1=alarms enabled"
    ::= { tempsensor 2 }
    --1.3.6.1.4.1.3052.41.4.2

tempHighLevel OBJECT-TYPE
    SYNTAX INTEGER
    ACCESS read-write
    STATUS mandatory
    DESCRIPTION
    "Level at which the High alarm goes active"
    ::= { tempsensor 3 }
    --1.3.6.1.4.1.3052.41.4.3

tempVeryHighLevel OBJECT-TYPE
    SYNTAX INTEGER
    ACCESS read-write
    STATUS mandatory
    DESCRIPTION
    "Level at which the Very High alarm goes active"
    ::= { tempsensor 4 }
    --1.3.6.1.4.1.3052.41.4.4

tempLowLevel OBJECT-TYPE
    SYNTAX INTEGER
    ACCESS read-write
    STATUS mandatory
    DESCRIPTION
    "Level at which the Low alarm goes active"
    ::= { tempsensor 5 }
    --1.3.6.1.4.1.3052.41.4.5

tempVeryLowLevel OBJECT-TYPE
    SYNTAX INTEGER
    ACCESS read-write
    STATUS mandatory
    DESCRIPTION
    "Level at which the Very Low alarm goes active"
    ::= { tempsensor 6 }
    --1.3.6.1.4.1.3052.41.4.6

tempAlarmThreshold OBJECT-TYPE
    SYNTAX INTEGER
    ACCESS read-write
    STATUS mandatory
    DESCRIPTION
    "Seconds must be in a range to be an alarm"
    ::= { tempsensor 7 }
    --1.3.6.1.4.1.3052.41.4.7

tempReturnNormalTrap OBJECT-TYPE
    SYNTAX INTEGER
    ACCESS read-write
    STATUS mandatory
    DESCRIPTION
    "0-not sent, 1-send trap on return to normal range"
    ::= { tempsensor 8 }
    --1.3.6.1.4.1.3052.41.4.8

tempTrapRepeat OBJECT-TYPE
    SYNTAX INTEGER
    ACCESS read-write
    STATUS mandatory
    DESCRIPTION
    "0-no repeats.  1-255 number of minutes between repeats of alarm traps."
    ::= { tempsensor 9 }
    --1.3.6.1.4.1.3052.41.4.9

tempMode OBJECT-TYPE
  SYNTAX INTEGER
  ACCESS read-write
  STATUS mandatory
  DESCRIPTION
  "0=all temp readings and levels in degrees F, 1=in degrees C"
  ::= { tempsensor 10 }
  --1.3.6.1.4.1.3052.41.4.10

tempHighSeverity OBJECT-TYPE
    SYNTAX INTEGER
    ACCESS read-write
    STATUS mandatory
    DESCRIPTION
    "High Level Severity 1-minor 2-major 3-critical 4-severe 5-warning"
    ::= { tempsensor 11 }
    --1.3.6.1.4.1.3052.41.4.11

tempVeryHighSeverity OBJECT-TYPE
    SYNTAX INTEGER
    ACCESS read-write
    STATUS mandatory
    DESCRIPTION
    "Very High Level Severity 1-minor 2-major 3-critical 4-severe 5-warning"
    ::= { tempsensor 12 }
    --1.3.6.1.4.1.3052.41.4.12

tempLowSeverity OBJECT-TYPE
    SYNTAX INTEGER
    ACCESS read-write
    STATUS mandatory
    DESCRIPTION
    "Low Level Severity 1-minor 2-major 3-critical 4-severe 5-warning"
    ::= { tempsensor 13 }
    --1.3.6.1.4.1.3052.41.4.13

tempVeryLowSeverity OBJECT-TYPE
    SYNTAX INTEGER
    ACCESS read-write
    STATUS mandatory
    DESCRIPTION
    "Very Low Level Severity 1-minor 2-major 3-critical 4-severe 5-warning"
    ::= { tempsensor 14 }
    --1.3.6.1.4.1.3052.41.4.14

tempName OBJECT-TYPE
    SYNTAX DisplayString
    ACCESS read-write
    STATUS mandatory
    DESCRIPTION
    "Name for temperature sensor, up to 30 characters"
    ::= { tempsensor 15 }
    --1.3.6.1.4.1.3052.41.4.15


-- humidity sensor section

humidityValue OBJECT-TYPE
    SYNTAX INTEGER
    ACCESS read-only
    STATUS mandatory
    DESCRIPTION
    "Current Relative Humidity Value (0-100%)"
    ::= { humiditysensor 1 }
    --1.3.6.1.4.1.3052.41.5.1

humidityAlarmEnable OBJECT-TYPE
    SYNTAX INTEGER
    ACCESS read-write
    STATUS mandatory
    DESCRIPTION
    "0=alarms disabled, 1=alarms enabled"
    ::= { humiditysensor 2 }
    --1.3.6.1.4.1.3052.41.5.2

humidityHighLevel OBJECT-TYPE
    SYNTAX INTEGER
    ACCESS read-write
    STATUS mandatory
    DESCRIPTION
    "Level at which the High alarm goes active"
    ::= { humiditysensor 3 }
    --1.3.6.1.4.1.3052.41.5.3

humidityVeryHighLevel OBJECT-TYPE
    SYNTAX INTEGER
    ACCESS read-write
    STATUS mandatory
    DESCRIPTION
    "Level at which the Very High alarm goes active"
    ::= { humiditysensor 4 }
    --1.3.6.1.4.1.3052.41.5.4

humidityLowLevel OBJECT-TYPE
    SYNTAX INTEGER
    ACCESS read-write
    STATUS mandatory
    DESCRIPTION
    "Level at which the Low alarm goes active"
    ::= { humiditysensor 5 }
    --1.3.6.1.4.1.3052.41.5.5

humidityVeryLowLevel OBJECT-TYPE
    SYNTAX INTEGER
    ACCESS read-write
    STATUS mandatory
    DESCRIPTION
    "Level at which the Very Low alarm goes active"
    ::= { humiditysensor 6 }
    --1.3.6.1.4.1.3052.41.5.6

humidityAlarmThreshold OBJECT-TYPE
    SYNTAX INTEGER
    ACCESS read-write
    STATUS mandatory
    DESCRIPTION
    "Seconds must be in a range to be an alarm"
    ::= { humiditysensor 7 }
    --1.3.6.1.4.1.3052.41.5.7

humidityReturnNormalTrap OBJECT-TYPE
    SYNTAX INTEGER
    ACCESS read-write
    STATUS mandatory
    DESCRIPTION
    "0-not sent, 1-send trap on return to normal range"
    ::= { humiditysensor 8 }
    --1.3.6.1.4.1.3052.41.5.8

humidityTrapRepeat OBJECT-TYPE
    SYNTAX INTEGER
    ACCESS read-write
    STATUS mandatory
    DESCRIPTION
    "0-no repeats.  1-255 number of minutes between repeats of alarm traps."
    ::= { humiditysensor 9 }
    --1.3.6.1.4.1.3052.41.5.9

humidityHighSeverity OBJECT-TYPE
    SYNTAX INTEGER
    ACCESS read-write
    STATUS mandatory
    DESCRIPTION
    "High Level Severity 1-minor 2-major 3-critical 4-severe 5-warning"
    ::= { humiditysensor 10 }
    --1.3.6.1.4.1.3052.41.5.10

humidityVeryHighSeverity OBJECT-TYPE
    SYNTAX INTEGER
    ACCESS read-write
    STATUS mandatory
    DESCRIPTION
    "Very High Level Severity 1-minor 2-major 3-critical 4-severe 5-warning"
    ::= { humiditysensor 11 }
    --1.3.6.1.4.1.3052.41.5.11

humidityLowSeverity OBJECT-TYPE
    SYNTAX INTEGER
    ACCESS read-write
    STATUS mandatory
    DESCRIPTION
    "Low Level Severity 1-minor 2-major 3-critical 4-severe 5-warning"
    ::= { humiditysensor 12 }
    --1.3.6.1.4.1.3052.41.5.12

humidityVeryLowSeverity OBJECT-TYPE
    SYNTAX INTEGER
    ACCESS read-write
    STATUS mandatory
    DESCRIPTION
    "Very Low Level Severity 1-minor 2-major 3-critical 4-severe 5-warning"
    ::= { humiditysensor 13 }
    --1.3.6.1.4.1.3052.41.5.13

humidityName OBJECT-TYPE
    SYNTAX DisplayString
    ACCESS read-write
    STATUS mandatory
    DESCRIPTION
    "Name for humidity sensor, up to 30 characters"
    ::= { humiditysensor 14 }
    --1.3.6.1.4.1.3052.41.5.14
    
    
-- passthrough section

ptNeedPassword OBJECT-TYPE
    SYNTAX INTEGER
    ACCESS read-write
    STATUS mandatory
    DESCRIPTION
    "0-no 1-yes, is password required for passthrough connection."
    ::= { passthrough 1 }
    --1.3.6.1.4.1.3052.41.6.1

ptSayLoginText OBJECT-TYPE
    SYNTAX INTEGER
    ACCESS read-write
    STATUS mandatory
    DESCRIPTION
    "0-no 1-yes, is passthrough login text displayed on connection."
    ::= { passthrough 2 }
    --1.3.6.1.4.1.3052.41.6.2
 
ptLoginText OBJECT-TYPE
    SYNTAX DisplayString
    ACCESS read-write
    STATUS mandatory
    DESCRIPTION
    "0-24 char string which may be displayed on socket connection. 
         Requires that ptSayLoginText be enabled to display this string."
    ::= { passthrough 3 }
    --1.3.6.1.4.1.3052.41.6.3

ptSaySiteID OBJECT-TYPE
    SYNTAX INTEGER
    ACCESS read-write
    STATUS mandatory
    DESCRIPTION
    "0-no 1-yes, is SiteID displayed on pass through connection."
    ::= { passthrough 4 }
    --1.3.6.1.4.1.3052.41.6.4

ptUsername OBJECT-TYPE
    SYNTAX DisplayString
    ACCESS read-write
    STATUS mandatory
    DESCRIPTION
    "0-16 char string for Username used in serial passthrough connections"
    ::= { passthrough 5 }
    --1.3.6.1.4.1.3052.41.6.5 

ptPassword OBJECT-TYPE
    SYNTAX DisplayString
    ACCESS read-write
    STATUS mandatory
    DESCRIPTION
    "0-16 char string for Password used in serial passthrough connections"
    ::= { passthrough 6 }
    --1.3.6.1.4.1.3052.41.6.6

ptTimeout OBJECT-TYPE
    SYNTAX INTEGER
    ACCESS read-write
    STATUS mandatory
    DESCRIPTION
    "number of minutes (1-255) of idle activity (both directions) which causes disconnect.  0-never"
    ::= { passthrough 7 }
    --1.3.6.1.4.1.3052.41.6.7

ptEscChar OBJECT-TYPE
    SYNTAX INTEGER
    ACCESS read-write
    STATUS mandatory
    DESCRIPTION
    "ASCII character code (e.g, Escape=27) which if entered on the tcp port three times 
        in a row causes disconnect.  0-none"
    ::= { passthrough 8 }
    --1.3.6.1.4.1.3052.41.6.8

ptLfstripToPort OBJECT-TYPE
    SYNTAX INTEGER
    ACCESS read-write
    STATUS mandatory
    DESCRIPTION
    "0-no 1-yes linefeed characters received on TCP connection are removed from stream to serial port"
    ::= { passthrough 9 }
    --1.3.6.1.4.1.3052.41.6.9

ptLfstripFromPort OBJECT-TYPE
    SYNTAX INTEGER
    ACCESS read-write
    STATUS mandatory
    DESCRIPTION
    "0-no 1-yes linefeed characters received on serial port are removed from stream to TCP connection"
    ::= { passthrough 10 }
    --1.3.6.1.4.1.3052.41.6.10

ptSerialBaudrate OBJECT-TYPE
    SYNTAX INTEGER
    ACCESS read-write
    STATUS mandatory
    DESCRIPTION
    "300 600 1200 2400 4800 9600 19200 baud are allowed values"
    ::= { passthrough 11 }
    --1.3.6.1.4.1.3052.41.6.11

ptSerialWordlength OBJECT-TYPE
    SYNTAX INTEGER
    ACCESS read-write
    STATUS mandatory
    DESCRIPTION
    "7 or 8 bit word selection"
    ::= { passthrough 12 }
    --1.3.6.1.4.1.3052.41.6.12

ptSerialParity OBJECT-TYPE
    SYNTAX DisplayString
    ACCESS read-write
    STATUS mandatory
    DESCRIPTION
    "N E O are allowed values for parity (none, even, odd) [a single-character string]"
    ::= { passthrough 13 }
    --1.3.6.1.4.1.3052.41.6.13

ptTCPPortnumber OBJECT-TYPE
    SYNTAX INTEGER
    ACCESS read-write
    STATUS mandatory
    DESCRIPTION
    "IP port number for passthrough connection (range 1024-65534)"
    ::= { passthrough 14 }
    --1.3.6.1.4.1.3052.41.6.14

-- ftp branch

ftpUsername OBJECT-TYPE
    SYNTAX DisplayString
    ACCESS read-write
    STATUS mandatory
    DESCRIPTION
    "0-16 char string for Username used in ftp server for updates"
    ::= { ftp 1 }
    --1.3.6.1.4.1.3052.41.7.1

ftpPassword OBJECT-TYPE
    SYNTAX DisplayString
    ACCESS read-write
    STATUS mandatory
    DESCRIPTION
    "0-16 char string for Password used in ftp server for updates"
    ::= { ftp 2 }
    --1.3.6.1.4.1.3052.41.7.2

-- analog sensor section

analog1Value OBJECT-TYPE
    SYNTAX INTEGER
    ACCESS read-only
    STATUS mandatory
    DESCRIPTION
    "Value of current analog reading, in 1/100 volt, +- 9999 range"
    ::= { analog1 1 }
    --1.3.6.1.4.1.3052.41.8.1.1

analog1AlarmEnable OBJECT-TYPE
    SYNTAX INTEGER
    ACCESS read-write
    STATUS mandatory
    DESCRIPTION
    "0=no alarms, 1=send alarms"
    ::= { analog1 2 }
    --1.3.6.1.4.1.3052.41.8.1.2

analog1HighLevel OBJECT-TYPE
    SYNTAX INTEGER
    ACCESS read-write
    STATUS mandatory
    DESCRIPTION
    "Level at which the High alarm goes active"
    ::= { analog1 3 }
    --1.3.6.1.4.1.3052.41.8.1.3

analog1VeryHighLevel OBJECT-TYPE
    SYNTAX INTEGER
    ACCESS read-write
    STATUS mandatory
    DESCRIPTION
    "Level at which the Very High alarm goes active"
    ::= { analog1 4 }
    --1.3.6.1.4.1.3052.41.8.1.4

analog1LowLevel OBJECT-TYPE
    SYNTAX INTEGER
    ACCESS read-write
    STATUS mandatory
    DESCRIPTION
    "Level at which the Low alarm goes active"
    ::= { analog1 5 }
    --1.3.6.1.4.1.3052.41.8.1.5

analog1VeryLowLevel OBJECT-TYPE
    SYNTAX INTEGER
    ACCESS read-write
    STATUS mandatory
    DESCRIPTION
    "Level at which the Very Low alarm goes active"
    ::= { analog1 6 }
    --1.3.6.1.4.1.3052.41.8.1.6

analog1AlarmThreshold OBJECT-TYPE
    SYNTAX INTEGER
    ACCESS read-write
    STATUS mandatory
    DESCRIPTION
    "Seconds must be in a range to be an alarm"
    ::= { analog1 7 }
    --1.3.6.1.4.1.3052.41.8.1.7

analog1ReturnNormalTrap OBJECT-TYPE
    SYNTAX INTEGER
    ACCESS read-write
    STATUS mandatory
    DESCRIPTION
    "0-not sent, 1-send trap on return to normal range"
    ::= { analog1 8 }
    --1.3.6.1.4.1.3052.41.8.1.8

analog1TrapRepeat OBJECT-TYPE
    SYNTAX INTEGER
    ACCESS read-write
    STATUS mandatory
    DESCRIPTION
    "0-no repeats else number of  minutes between repeats of trap"
    ::= { analog1 9 }
    --1.3.6.1.4.1.3052.41.8.1.9

analog1HighSeverity OBJECT-TYPE
    SYNTAX INTEGER
    ACCESS read-write
    STATUS mandatory
    DESCRIPTION
    "High Level Severity 1-minor 2-major 3-critical 4-severe 5-warning"
    ::= { analog1 10 }
    --1.3.6.1.4.1.3052.41.8.1.10

analog1VeryHighSeverity OBJECT-TYPE
    SYNTAX INTEGER
    ACCESS read-write
    STATUS mandatory
    DESCRIPTION
    "Very High Level Severity 1-minor 2-major 3-critical 4-severe 5-warning"
    ::= { analog1 11 }
    --1.3.6.1.4.1.3052.41.8.1.11

analog1LowSeverity OBJECT-TYPE
    SYNTAX INTEGER
    ACCESS read-write
    STATUS mandatory
    DESCRIPTION
    "Low Level Severity 1-minor 2-major 3-critical 4-severe 5-warning"
    ::= { analog1 12 }
    --1.3.6.1.4.1.3052.41.8.1.12

analog1VeryLowSeverity OBJECT-TYPE
    SYNTAX INTEGER
    ACCESS read-write
    STATUS mandatory
    DESCRIPTION
    "Very Low Level Severity 1-minor 2-major 3-critical 4-severe 5-warning"
    ::= { analog1 13 }
    --1.3.6.1.4.1.3052.41.8.1.13

analog1Name OBJECT-TYPE
    SYNTAX DisplayString
    ACCESS read-write
    STATUS mandatory
    DESCRIPTION
    "Name for analog sensor 1, up to 30 characters"
    ::= { analog1 14 }
    --1.3.6.1.4.1.3052.41.8.1.14

analog2Value OBJECT-TYPE
    SYNTAX INTEGER
    ACCESS read-only
    STATUS mandatory
    DESCRIPTION
    "Value of current analog reading, in 1/100 volt, +- 9999 range"
    ::= { analog2 1 }
    --1.3.6.1.4.1.3052.41.8.2.1

analog2AlarmEnable OBJECT-TYPE
    SYNTAX INTEGER
    ACCESS read-write
    STATUS mandatory
    DESCRIPTION
    "0=no alarms, 1=send alarms"
    ::= { analog2 2 }
    --1.3.6.1.4.1.3052.41.8.2.2

analog2HighLevel OBJECT-TYPE
    SYNTAX INTEGER
    ACCESS read-write
    STATUS mandatory
    DESCRIPTION
    "Level at which the High alarm goes active"
    ::= { analog2 3 }
    --1.3.6.1.4.1.3052.41.8.2.3

analog2VeryHighLevel OBJECT-TYPE
    SYNTAX INTEGER
    ACCESS read-write
    STATUS mandatory
    DESCRIPTION
    "Level at which the Very High alarm goes active"
    ::= { analog2 4 }
    --1.3.6.1.4.1.3052.41.8.2.4

analog2LowLevel OBJECT-TYPE
    SYNTAX INTEGER
    ACCESS read-write
    STATUS mandatory
    DESCRIPTION
    "Level at which the Low alarm goes active"
    ::= { analog2 5 }
    --1.3.6.1.4.1.3052.41.8.2.5

analog2VeryLowLevel OBJECT-TYPE
    SYNTAX INTEGER
    ACCESS read-write
    STATUS mandatory
    DESCRIPTION
    "Level at which the Very Low alarm goes active"
    ::= { analog2 6 }
    --1.3.6.1.4.1.3052.41.8.2.6

analog2AlarmThreshold OBJECT-TYPE
    SYNTAX INTEGER
    ACCESS read-write
    STATUS mandatory
    DESCRIPTION
    "Seconds must be in a range to be an alarm"
    ::= { analog2 7 }
    --1.3.6.1.4.1.3052.41.8.2.7

analog2ReturnNormalTrap OBJECT-TYPE
    SYNTAX INTEGER
    ACCESS read-write
    STATUS mandatory
    DESCRIPTION
    "0-not sent, 1-send trap on return to normal range"
    ::= { analog2 8 }
    --1.3.6.1.4.1.3052.41.8.2.8

analog2TrapRepeat OBJECT-TYPE
    SYNTAX INTEGER
    ACCESS read-write
    STATUS mandatory
    DESCRIPTION
    "0-no repeats else number of  minutes between repeats of trap"
    ::= { analog2 9 }
    --1.3.6.1.4.1.3052.41.8.2.9

analog2HighSeverity OBJECT-TYPE
    SYNTAX INTEGER
    ACCESS read-write
    STATUS mandatory
    DESCRIPTION
    "High Level Severity 1-minor 2-major 3-critical 4-severe 5-warning"
    ::= { analog2 10 }
    --1.3.6.1.4.1.3052.41.8.2.10

analog2VeryHighSeverity OBJECT-TYPE
    SYNTAX INTEGER
    ACCESS read-write
    STATUS mandatory
    DESCRIPTION
    "Very High Level Severity 1-minor 2-major 3-critical 4-severe 5-warning"
    ::= { analog2 11 }
    --1.3.6.1.4.1.3052.41.8.2.11

analog2LowSeverity OBJECT-TYPE
    SYNTAX INTEGER
    ACCESS read-write
    STATUS mandatory
    DESCRIPTION
    "Low Level Severity 1-minor 2-major 3-critical 4-severe 5-warning"
    ::= { analog2 12 }
    --1.3.6.1.4.1.3052.41.8.2.12

analog2VeryLowSeverity OBJECT-TYPE
    SYNTAX INTEGER
    ACCESS read-write
    STATUS mandatory
    DESCRIPTION
    "Very Low Level Severity 1-minor 2-major 3-critical 4-severe 5-warning"
    ::= { analog2 13 }
    --1.3.6.1.4.1.3052.41.8.2.13

analog2Name OBJECT-TYPE
    SYNTAX DisplayString
    ACCESS read-write
    STATUS mandatory
    DESCRIPTION
    "Name for analog sensor 2, up to 30 characters"
    ::= { analog2 14 }
    --1.3.6.1.4.1.3052.41.8.2.14
    
-- voltage section


-- ES status section

esPointTable OBJECT-TYPE
    SYNTAX SEQUENCE OF ESPoint
    ACCESS not-accessible
    STATUS mandatory
    DESCRIPTION
        "
        This table organizes 4 basic attributes of points.  A point
        is a particular sensor on an EventSensor (e.g., temperature,
        humidity, contact closure 2, relay 5, etc.).  The 4 point
        attributes are its name, whether it's in its event state,
        the point's value as a number and its value as a string.
        
        Points are referenced by a point index.  The point index 
        is a string of 3 numbers separated by periods.
        It contains all the information necessary for getting a piece 
        of data off an event sensor; namely, which EventSensor, 
        point class, and which-sensor-of-that-class (a.k.a. point).     
        "
    ::= { eventSensorStatus 1 }
    --1.3.6.1.4.1.3052.41.10.1
    
esPointEntry OBJECT-TYPE
    SYNTAX ESPoint
    ACCESS not-accessible
    STATUS mandatory
    DESCRIPTION
        "Entry for EventSensor point table"
    INDEX { esIndexES, esIndexPC, esIndexPoint }
    ::= { esPointTable 1 }
    --1.3.6.1.4.1.3052.41.10.1.1
    
esIndexES OBJECT-TYPE
    SYNTAX INTEGER
    ACCESS read-only
    STATUS mandatory
    DESCRIPTION
        "The part of the point index that refers to an 
        EventSensor.
        
        The point index is a string of 3 numbers separated 
        by periods.  It contains all the information 
        necessary for getting a piece of data off an event 
        sensor; namely, which EventSensor, point class, 
        and which-sensor-of-that-class (a.k.a. point).
        
        This object's allowable values are 1 through 4,
        which refer to attached EventSensors.
        
        The number corresponding to an EventSensor is 
        determined by the user at the initial configuration 
        time.  If there is an internal sensor in the unit, 
        it will always be the first item in the Sensor 
        Events setup menu.  
        
        For example, if a new EventSensor is configured as 
        the 2nd entry AFTER the internal EventSensor (if 
        one exists) in the Sensor Events Setup Menu, then 
        that EventSensor will be known from then on as 
        EventSensor 2.  All point indeces with esIndexES=2 
        will now refer to that particular EventSensor.
        "
    ::= { esPointEntry 1 }
    --1.3.6.1.4.1.3052.41.10.1.1.1

esIndexPC OBJECT-TYPE
    SYNTAX INTEGER
    ACCESS read-only
    STATUS mandatory
    DESCRIPTION
        "The part of the point index that refers to point class.
        
        The point index is a string of 3 numbers separated by periods.
        It contains all the information necessary for getting a piece 
        of data off an event sensor; namely, which EventSensor, 
        point class, and which-sensor-of-that-class (a.k.a. point).
        
        The values for this object are:
        1=temperature sensor
        2=contact closure
        3=humidity sensor
        4=noise sensor
        5=analog input
        6=relay
        "
    ::= { esPointEntry 2 }
    --1.3.6.1.4.1.3052.41.10.1.1.2
    
esIndexPoint OBJECT-TYPE
    SYNTAX INTEGER
    ACCESS read-only
    STATUS mandatory
    DESCRIPTION
        "The part of the point index that delineates which 
        sensor on the EventSensor.

        So this combined with esIndexPC (Point Class or type) 
        and esIndexES (which EventSensor) uniquely defines each 
        point (sensor or relay) attached to a unit.  For 
        example, if esIndexES is 3, esIndexPC is 1 and 
        esIndexPoint is 4 then this is the Fourth Temperature 
        Sensor on EventSensor number 3."
    ::= { esPointEntry 3 }
    --1.3.6.1.4.1.3052.41.10.1.1.3
    
esPointName OBJECT-TYPE
    SYNTAX DisplayString
    ACCESS read-write
    STATUS mandatory
    DESCRIPTION
        "The name of the point on an EventSensor. For example, 
        'AC temp' (in the case of the temperature sensor on an 
        EventSensor).
        
        There can be multiple points of the same point class on an 
        EventSensor (e.g., 8 contact closures) and multiple sensor
        classes on an EventSensor (e.g., temperature, contact closure,
        humidity).
        
        If the point referenced by a given point index is solitary
        (e.g., temperature sensor, because there can be only one on 
        an EventSensor), then this object reads as '<EventSensor 
        name>'.  Setting this object for solitary point indices sets 
        the EventSensor name only.
        
        On the other hand, if a given point is among other points of 
        the same point class on an EventSensor, then this object reads 
        as '<Sensor name>'.  Setting this object for these NON-
        solitary point indices sets the sensor name only - not the 
        EventSensor name."
    ::= { esPointEntry 4 }
    --1.3.6.1.4.1.3052.41.10.1.1.4

esPointInEventState OBJECT-TYPE
    SYNTAX INTEGER
    ACCESS read-write
    STATUS mandatory
    DESCRIPTION
        "A number referring to the event state of a point 
        on an EventSensor.  This number can have different
        meanings depending on the point class.  
        
        If the point class is temperature, humidity, or
        analog input, then the values of this object are:
        1=very low
        2=low
        3=normal
        4=high
        5=very high
        
        For contact closures and relays the values of this 
        object are:
        1=point in event state
        2=point in normal state
        
        For any point class and any point, if the event 
        state is undefined, then the value of this object 
        is 0.
        
        For any point class except relay, this object is
        read-only.  For relays, setting this object to 1
        puts the relay into its open state.  
        Setting it to 2 puts the relay into its closed
        state.
        "
    ::= { esPointEntry 5 }
    --1.3.6.1.4.1.3052.41.10.1.1.5

esPointValueInt OBJECT-TYPE
    SYNTAX INTEGER (-32768..32767)
    ACCESS read-write
    STATUS mandatory
    DESCRIPTION
        "A number referring to the value of a point on an 
        EventSensor.  
        
        If the point class is temperature, then this object
        is the temperature in its configured scale (default
        is Fahrenheit).
        
        If the point class is contact closure or relay, then 
        this object is either 0 (open) or 1 (closed).
        
        If the point class is humidity, then this object
        is the percent relative humidity.
        
        If the point class is analog input, then this 
        object is the signed input value in tenths of the 
        configured units.
        
        For any point class except relay, this object is
        read-only.  For relays, setting this object to 1 
        closes the relay, while setting it to 0 opens it.
        This works regardless of the control mode of the
        relay.
        "
    ::= { esPointEntry 6 }
    --1.3.6.1.4.1.3052.41.10.1.1.6
    
esPointValueStr OBJECT-TYPE
    SYNTAX DisplayString
    ACCESS read-only
    STATUS mandatory
    DESCRIPTION
        "A string referring to the value of a point on an
        EventSensor.
        
        For contact closures and relays this object is 
        either 'Open' or 'Closed'.
        
        For temperature and humidity point classes, this
        object is the string representation of the
        esPointValueInt object.  For temperature, 'C' or
        'F' is including in the string to indicate scale.
        
        For analog inputs, this object is the string 
        representation of the plus/minus input in volts.
        "
    ::= { esPointEntry 7 }
    --1.3.6.1.4.1.3052.41.10.1.1.7
   
-- ES config section

esNumberEventSensors OBJECT-TYPE
    SYNTAX INTEGER
    ACCESS read-only
    STATUS mandatory
    DESCRIPTION
        "The number of EventSensors recognized by the SL12
        Range: 0-4"
    ::= { eventSensorConfig 1 }
    --1.3.6.1.4.1.3052.41.11.1

esTable OBJECT-TYPE
    SYNTAX SEQUENCE OF ESExist
    ACCESS not-accessible
    STATUS mandatory
    DESCRIPTION
        "The table of what EventSensors are attached to the unit"
    ::= { eventSensorConfig 2 }
    --1.3.6.1.4.1.3052.41.11.2
    
esEntry OBJECT-TYPE
    SYNTAX ESExist
    ACCESS not-accessible
    STATUS mandatory
    DESCRIPTION
        "Table entry for EventSensor table"
    INDEX { esIndex }
    ::= { esTable 1 }
    --1.3.6.1.4.1.3052.41.11.2.1
    
esIndex OBJECT-TYPE
    SYNTAX INTEGER
    ACCESS read-only
    STATUS mandatory
    DESCRIPTION
        "This number refers to an EventSensor; it has the 
        same meaning as the esIndexES object (see above), 
        except that this object is used only within the 
        esTable branch.
        
        This object's allowable values are 1 through 4, 
        which refer to additional attached EventSensors.
        
        The number corresponding to an EventSensor is 
        determined by the user at the initial configuration 
        time.
        "
    ::= { esEntry 1 }
    --1.3.6.1.4.1.3052.41.11.2.1.1

esID    OBJECT-TYPE
    SYNTAX DisplayString
    ACCESS read-only
    STATUS mandatory
    DESCRIPTION
        "The factory-assigned ID of the EventSensor"
    ::= { esEntry 2 }
    --1.3.6.1.4.1.3052.41.11.2.1.2
    
    
esNumberTempSensors OBJECT-TYPE
    SYNTAX INTEGER
    ACCESS read-only
    STATUS mandatory
    DESCRIPTION
        "The number of temperature sensors on the EventSensor"
    ::= { esEntry 3 }
    --1.3.6.1.4.1.3052.41.11.2.1.3

esTempReportingMode OBJECT-TYPE
    SYNTAX DisplayString
    ACCESS read-only
    STATUS mandatory
    DESCRIPTION
        "Description of how temperature values should
        be interpreted."
    ::= { esEntry 4 }
    --1.3.6.1.4.1.3052.41.11.2.1.4
    
esNumberCCs OBJECT-TYPE
    SYNTAX INTEGER
    ACCESS read-only
    STATUS mandatory
    DESCRIPTION
        "The number of contact closures on the EventSensor."
    ::= { esEntry 5 }
    --1.3.6.1.4.1.3052.41.11.2.1.5

esCCReportingMode OBJECT-TYPE
    SYNTAX DisplayString
    ACCESS read-only
    STATUS mandatory
    DESCRIPTION
        "Description of how CC values should be interpreted."
    ::= { esEntry 6 }
    --1.3.6.1.4.1.3052.41.11.2.1.6

esNumberHumidSensors OBJECT-TYPE
    SYNTAX INTEGER
    ACCESS read-only
    STATUS mandatory
    DESCRIPTION
        "The number of humidity sensors on the EventSensor."
    ::= { esEntry 7 }
    --1.3.6.1.4.1.3052.41.11.2.1.7

esHumidReportingMode OBJECT-TYPE
    SYNTAX DisplayString
    ACCESS read-only
    STATUS mandatory
    DESCRIPTION
        "Description of how humidity sensor values should be 
        interpreted."
    ::= { esEntry 8 }
    --1.3.6.1.4.1.3052.41.11.2.1.8


    
esNumberAnalog OBJECT-TYPE
    SYNTAX INTEGER
    ACCESS read-only
    STATUS mandatory
    DESCRIPTION
        "The number of analog inputs on the EventSensor."
    ::= { esEntry 13 }
    --1.3.6.1.4.1.3052.41.11.2.1.13

esAnalogReportingMode OBJECT-TYPE
    SYNTAX DisplayString
    ACCESS read-only
    STATUS mandatory
    DESCRIPTION
        "Description of how analog input values should be 
        interpreted."
    ::= { esEntry 14 }
    --1.3.6.1.4.1.3052.41.11.2.1.14
    
esNumberRelayOutputs OBJECT-TYPE
    SYNTAX INTEGER
    ACCESS read-only
    STATUS mandatory
    DESCRIPTION
        "The number of relay outputs on the EventSensor"
    ::= { esEntry 15 }
    --1.3.6.1.4.1.3052.41.11.2.1.15
    
esRelayReportingMode OBJECT-TYPE
    SYNTAX DisplayString
    ACCESS read-only
    STATUS mandatory
    DESCRIPTION
        "Description of how relay output values 
        should be interpreted."
    ::= { esEntry 16 }
    --1.3.6.1.4.1.3052.41.11.2.1.16
    
    
-- tech support (and windows setup application) section
-- requires special community name for writes

techsupportIPAddress OBJECT-TYPE
    SYNTAX IpAddress
    ACCESS read-write
    STATUS mandatory
    DESCRIPTION
    "May read or Set IP Address, takes effect on restart"
    ::= { techsupport 1 }
    --1.3.6.1.4.1.3052.41.99.1

techsupportNetMask OBJECT-TYPE
    SYNTAX IpAddress
    ACCESS read-write
    STATUS mandatory
    DESCRIPTION
    "May read or Set NetMask, takes effect on restart"
    ::= { techsupport 2 }
    --1.3.6.1.4.1.3052.41.99.2

techsupportRouter OBJECT-TYPE
    SYNTAX IpAddress
    ACCESS read-write
    STATUS mandatory
    DESCRIPTION
    "May read or Set Router IP Address, takes effect on restart"
    ::= { techsupport 3 }
    --1.3.6.1.4.1.3052.41.99.3

techsupportRestart OBJECT-TYPE
    SYNTAX INTEGER
    ACCESS read-write
    STATUS mandatory
    DESCRIPTION
    "Reads as 0, any Write resets unit so new IP, Netmask, Router may be used"
    ::= { techsupport 4 }
    --1.3.6.1.4.1.3052.41.99.4

techsupportVersionNumber OBJECT-TYPE
    SYNTAX DisplayString
    ACCESS read-write
    STATUS mandatory
    DESCRIPTION
    "Version Number of Firmware"
    ::= { techsupport 5 }
    --1.3.6.1.4.1.3052.41.99.5


mibendObject OBJECT-TYPE
    SYNTAX INTEGER
    ACCESS read-only
    STATUS mandatory
    DESCRIPTION
    "An object after all active mib items, to help some managers compile"
    ::= { mibend 1 }
    --1.3.6.1.4.1.3052.41.100.1

-- object definitions

ESPoint ::= 
    SEQUENCE {
        esIndexES       
            INTEGER,
        esIndexPC
            INTEGER,
        esIndexPoint
            INTEGER,
        esPointName
            DisplayString,
        esPointInEventState
            INTEGER,
        esPointValueInt
            INTEGER,
        esPointValueStr
            DisplayString
}

ESExist ::= 
    SEQUENCE {
        esIndex     
            INTEGER,
        esID
            DisplayString,
        esNumberTempSensors
            INTEGER,
        esTempReportingMode
            DisplayString,
        esNumberCCs
            INTEGER,
        esCCReportingMode
            DisplayString,
        esNumberHumidSensors
            INTEGER,
        esHumidReportingMode
            DisplayString,
        esNumberAnalog
            INTEGER,
        esAnalogReportingMode
            DisplayString,
        esNumberRelayOutputs
            INTEGER,
        esRelayReportingMode
            DisplayString
}


-- end of MIB objects


-- TRAP DEFINITIONS


contact1ActiveTrap  TRAP-TYPE
  ENTERPRISE sl12
  VARIABLES { thisTrapText, siteID, contact1Name, contact1State }
  DESCRIPTION
    "Sent to show Contact 1 is in the alarm state"
  ::= 20001

contact2ActiveTrap  TRAP-TYPE
  ENTERPRISE sl12
  VARIABLES { thisTrapText, siteID, contact2Name, contact2State }
  DESCRIPTION
    "Sent to show Contact 2 is in the alarm state"
  ::= 20002

contact3ActiveTrap  TRAP-TYPE
  ENTERPRISE sl12
  VARIABLES { thisTrapText, siteID, contact3Name, contact3State }
  DESCRIPTION
    "Sent to show Contact 3 is in the alarm state"
  ::= 20003

contact4ActiveTrap  TRAP-TYPE
  ENTERPRISE sl12
  VARIABLES { thisTrapText, siteID, contact4Name, contact4State }
  DESCRIPTION
    "Sent to show Contact 4 is in the alarm state"
  ::= 20004

contact5ActiveTrap  TRAP-TYPE
  ENTERPRISE sl12
  VARIABLES { thisTrapText, siteID, contact5Name, contact5State }
  DESCRIPTION
    "Sent to show Contact 5 is in the alarm state"
  ::= 20005

contact6ActiveTrap  TRAP-TYPE
  ENTERPRISE sl12
  VARIABLES { thisTrapText, siteID, contact6Name, contact6State }
  DESCRIPTION
    "Sent to show Contact 6 is in the alarm state"
  ::= 20006

tempHighTrap  TRAP-TYPE
  ENTERPRISE sl12
  VARIABLES { thisTrapText, siteID, tempValue }
  DESCRIPTION
    "Sent to show Temp exceeded High Temp Threshold"
  ::= 20010

tempVeryHighTrap  TRAP-TYPE
  ENTERPRISE sl12
  VARIABLES { thisTrapText, siteID, tempValue }
  DESCRIPTION
    "Sent to show Temp exceeded Very High Temp Threshold"
  ::= 20011

tempLowTrap  TRAP-TYPE
  ENTERPRISE sl12
  VARIABLES { thisTrapText, siteID, tempValue }
  DESCRIPTION
    "Sent to show Temp went below Low Temp Threshold"
  ::= 20012

tempVeryLowTrap  TRAP-TYPE
  ENTERPRISE sl12
  VARIABLES { thisTrapText, siteID, tempValue }
  DESCRIPTION
    "Sent to show Temp went below Very Low Temp Threshold"
  ::= 20013

humidityHighTrap  TRAP-TYPE
  ENTERPRISE sl12
  VARIABLES { thisTrapText, siteID, humidityValue }
  DESCRIPTION
    "Sent to show humidity exceeded High humidity Threshold"
  ::= 20020

humidityVeryHighTrap  TRAP-TYPE
  ENTERPRISE sl12
  VARIABLES { thisTrapText, siteID, humidityValue }
  DESCRIPTION
    "Sent to show humidity exceeded Very High humidity Threshold"
  ::= 20021

humidityLowTrap  TRAP-TYPE
  ENTERPRISE sl12
  VARIABLES { thisTrapText, siteID, humidityValue }
  DESCRIPTION
    "Sent to show humidity went below Low humidity Threshold"
  ::= 20022

humidityVeryLowTrap  TRAP-TYPE
  ENTERPRISE sl12
  VARIABLES { thisTrapText, siteID, humidityValue }
  DESCRIPTION
    "Sent to show humidity went below Very Low humidity Threshold"
  ::= 20023

analog1HighTrap  TRAP-TYPE
  ENTERPRISE sl12
  VARIABLES { thisTrapText, siteID, analog1Name, analog1Value }
  DESCRIPTION
    "Sent to show analog1 exceeded High analog1 Threshold"
  ::= 20030

analog1VeryHighTrap  TRAP-TYPE
  ENTERPRISE sl12
  VARIABLES { thisTrapText, siteID, analog1Name, analog1Value }
  DESCRIPTION
    "Sent to show analog1 exceeded Very High analog1 Threshold"
  ::= 20031

analog1LowTrap  TRAP-TYPE
  ENTERPRISE sl12
  VARIABLES { thisTrapText, siteID, analog1Name, analog1Value }
  DESCRIPTION
    "Sent to show analog1 went below Low analog1 Threshold"
  ::= 20032

analog1VeryLowTrap  TRAP-TYPE
  ENTERPRISE sl12
  VARIABLES { thisTrapText, siteID, analog1Name, analog1Value }
  DESCRIPTION
    "Sent to show analog1 went below Very Low analog1 Threshold"
  ::= 20033

analog2HighTrap  TRAP-TYPE
  ENTERPRISE sl12
  VARIABLES { thisTrapText, siteID, analog2Name, analog2Value }
  DESCRIPTION
    "Sent to show analog2 exceeded High analog2 Threshold"
  ::= 20040

analog2VeryHighTrap  TRAP-TYPE
  ENTERPRISE sl12
  VARIABLES { thisTrapText, siteID, analog2Name, analog2Value }
  DESCRIPTION
    "Sent to show analog2 exceeded Very High analog2 Threshold"
  ::= 20041

analog2LowTrap  TRAP-TYPE
  ENTERPRISE sl12
  VARIABLES { thisTrapText, siteID, analog2Name, analog2Value }
  DESCRIPTION
    "Sent to show analog2 went below Low analog2 Threshold"
  ::= 20042

analog2VeryLowTrap  TRAP-TYPE
  ENTERPRISE sl12
  VARIABLES { thisTrapText, siteID, analog2Name, analog2Value }
  DESCRIPTION
    "Sent to show analog2 went below Very Low analog2 Threshold"
  ::= 20043

contactESActiveTrap  TRAP-TYPE
  ENTERPRISE sl12
  VARIABLES { thisTrapText, siteID, esPointName, esPointValueInt, esIndexES, esIndexPoint }
  DESCRIPTION
    "Sent to show EventSensor contact is in the alarm state"
  ::= 20101
  
tempESHighTrap  TRAP-TYPE
  ENTERPRISE sl12
  VARIABLES { thisTrapText, siteID, esPointName, esPointValueInt, esIndexES, esIndexPoint }
  DESCRIPTION
    "Sent to show Temp exceeded High Threshold on an EventSensor"
  ::= 20110

tempESVeryHighTrap  TRAP-TYPE
  ENTERPRISE sl12
  VARIABLES { thisTrapText, siteID, esPointName, esPointValueInt, esIndexES, esIndexPoint }
  DESCRIPTION
    "Sent to show Temp exceeded Very High Threshold on an EventSensor"
  ::= 20111

tempESLowTrap  TRAP-TYPE
  ENTERPRISE sl12
  VARIABLES { thisTrapText, siteID, esPointName, esPointValueInt, esIndexES, esIndexPoint }
  DESCRIPTION
    "Sent to show Temp went below Low Threshold on an EventSensor"
  ::= 20112

tempESVeryLowTrap  TRAP-TYPE
  ENTERPRISE sl12
  VARIABLES { thisTrapText, siteID, esPointName, esPointValueInt, esIndexES, esIndexPoint }
  DESCRIPTION
    "Sent to show Temp went below Very Low Threshold on an EventSensor"
  ::= 20113

humidityESHighTrap  TRAP-TYPE
  ENTERPRISE sl12
  VARIABLES { thisTrapText, siteID, esPointName, esPointValueInt, esIndexES, esIndexPoint }
  DESCRIPTION
    "Sent to show humidity exceeded High Threshold on an EventSensor"
  ::= 20120

humidityESVeryHighTrap  TRAP-TYPE
  ENTERPRISE sl12
  VARIABLES { thisTrapText, siteID, esPointName, esPointValueInt, esIndexES, esIndexPoint }
  DESCRIPTION
    "Sent to show humidity exceeded Very High Threshold on an EventSensor"
  ::= 20121

humidityESLowTrap  TRAP-TYPE
  ENTERPRISE sl12
  VARIABLES { thisTrapText, siteID, esPointName, esPointValueInt, esIndexES, esIndexPoint }
  DESCRIPTION
    "Sent to show humidity went below Low Threshold on an EventSensor"
  ::= 20122

humidityESVeryLowTrap  TRAP-TYPE
  ENTERPRISE sl12
  VARIABLES { thisTrapText, siteID, esPointName, esPointValueInt, esIndexES, esIndexPoint }
  DESCRIPTION
    "Sent to show humidity went below Very Low Threshold on an EventSensor"
  ::= 20123

voltageESHighTrap  TRAP-TYPE
  ENTERPRISE sl12
  VARIABLES { thisTrapText, siteID, esPointName, esPointValueInt, esIndexES, esIndexPoint }
  DESCRIPTION
    "Sent to show voltage exceeded High Threshold on an EventSensor"
  ::= 20130

voltageESVeryHighTrap  TRAP-TYPE
  ENTERPRISE sl12
  VARIABLES { thisTrapText, siteID, esPointName, esPointValueInt, esIndexES, esIndexPoint }
  DESCRIPTION
    "Sent to show voltage exceeded Very High Threshold on an EventSensor"
  ::= 20131

voltageESLowTrap  TRAP-TYPE
  ENTERPRISE sl12
  VARIABLES { thisTrapText, siteID, esPointName, esPointValueInt, esIndexES, esIndexPoint }
  DESCRIPTION
    "Sent to show voltage went below Low Threshold on an EventSensor"
  ::= 20132

voltageESVeryLowTrap  TRAP-TYPE
  ENTERPRISE sl12
  VARIABLES { thisTrapText, siteID, esPointName, esPointValueInt, esIndexES, esIndexPoint }
  DESCRIPTION
    "Sent to show voltage went below Very Low Threshold on an EventSensor"
  ::= 20133

contact1NormalTrap  TRAP-TYPE
  ENTERPRISE sl12
  VARIABLES { thisTrapText, siteID, contact1Name, contact1State }
  DESCRIPTION
    "Sent to show Contact 1 is in the normal state"
  ::= 21001

contact2NormalTrap  TRAP-TYPE
  ENTERPRISE sl12
  VARIABLES { thisTrapText, siteID, contact2Name, contact2State }
  DESCRIPTION
    "Sent to show Contact 2 is in the normal state"
  ::= 21002

contact3NormalTrap  TRAP-TYPE
  ENTERPRISE sl12
  VARIABLES { thisTrapText, siteID, contact3Name, contact3State }
  DESCRIPTION
    "Sent to show Contact 3 is in the normal state"
  ::= 21003

contact4NormalTrap  TRAP-TYPE
  ENTERPRISE sl12
  VARIABLES { thisTrapText, siteID, contact4Name, contact4State }
  DESCRIPTION
    "Sent to show Contact 4 is in the normal state"
  ::= 21004

contact5NormalTrap  TRAP-TYPE
  ENTERPRISE sl12
  VARIABLES { thisTrapText, siteID, contact5Name, contact5State }
  DESCRIPTION
    "Sent to show Contact 5 is in the normal state"
  ::= 21005

contact6NormalTrap  TRAP-TYPE
  ENTERPRISE sl12
  VARIABLES { thisTrapText, siteID, contact6Name, contact6State }
  DESCRIPTION
    "Sent to show Contact 6 is in the normal state"
  ::= 21006

tempNormalTrap  TRAP-TYPE
  ENTERPRISE sl12
  VARIABLES { thisTrapText, siteID, tempValue }
  DESCRIPTION
    "Sent to show Temp went back to Normal range"
  ::= 21010

humidityNormalTrap  TRAP-TYPE
  ENTERPRISE sl12
  VARIABLES { thisTrapText, siteID, humidityValue }
  DESCRIPTION
    "Sent to show Humidity went back to Normal range"
  ::= 21020

analog1NormalTrap  TRAP-TYPE
  ENTERPRISE sl12
  VARIABLES { thisTrapText, siteID, analog1Name, analog1Value }
  DESCRIPTION
    "Sent to show analog1 went back to Normal range"
  ::= 21030

analog2NormalTrap  TRAP-TYPE
  ENTERPRISE sl12
  VARIABLES { thisTrapText, siteID, analog2Name, analog2Value }
  DESCRIPTION
    "Sent to show analog2 went back to Normal range"
  ::= 21040

contactESNormalTrap TRAP-TYPE
  ENTERPRISE sl12
  VARIABLES { thisTrapText, siteID, esPointName, esPointValueInt, esIndexES, esIndexPoint }
  DESCRIPTION
    "Send to show EventSensor contact has returned to normal state"
  ::= 21101
    
tempESNormalTrap  TRAP-TYPE
  ENTERPRISE sl12
  VARIABLES { thisTrapText, siteID, esPointName, esPointValueInt, esIndexES, esIndexPoint }
  DESCRIPTION
    "Sent to show EventSensor Temp went back to Normal range"
  ::= 21110

humidityESNormalTrap  TRAP-TYPE
  ENTERPRISE sl12
  VARIABLES { thisTrapText, siteID, esPointName, esPointValueInt, esIndexES, esIndexPoint }
  DESCRIPTION
    "Sent to show EventSensor Humidity went back to Normal range"
  ::= 21120

voltageESNormalTrap  TRAP-TYPE
  ENTERPRISE sl12
  VARIABLES { thisTrapText, siteID, esPointName, esPointValueInt, esIndexES, esIndexPoint }
  DESCRIPTION
    "Sent to show EventSensor voltage went back to Normal range"
  ::= 21130
  
testTrap  TRAP-TYPE
  ENTERPRISE sl12
  VARIABLES { thisTrapText, siteID }
  DESCRIPTION
    "Sent for testing the SNMP interface"
  ::= 22000



END
