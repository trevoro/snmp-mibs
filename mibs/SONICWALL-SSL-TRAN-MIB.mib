SONICWALL-SSL-TRAN-MIB DEFINITIONS ::= BEGIN

IMPORTS
    enterprises, IpAddress, Integer32,
	MODULE-IDENTITY 			FROM SNMPv2-SMI
	TRAP-TYPE				FROM RFC-1215
	OBJECT-TYPE				FROM RFC-1212;

-- Our enterprise

sonicWALL	OBJECT IDENTIFIER ::= { enterprises 8714 }

-- security devices such as ssl devices are a type 2 device
sonicSEC	OBJECT IDENTIFIER ::= { sonicWALL 2 }
sonicSSL	OBJECT IDENTIFIER ::= { sonicSEC 1 }

sonicSSLTran MODULE-IDENTITY
    LAST-UPDATED "200203061330Z"
    ORGANIZATION "SonicWALL, Inc."
    CONTACT-INFO
                "       SonicWall Inc.

                Postal: 1160 Bordeaux Dr.
                        Sunnyvale, CA 94089
                        USA

                   Tel: +1 408 745 9600
                   Fax: +1 408 745 9300

                E-mail: support@sonicwall.com"
    DESCRIPTION
        "The MIB module for SonicWALL enterprise SSL Transaction parameters
         statistics, and configuration objects and traps."
    ::= { sonicSSL 7 }
--
-- ----------------------------------------------------------------
sslTranStats     OBJECT IDENTIFIER ::= { sonicSSLTran 2 }
-- 1.3.6.1.4.1.8714.2.1.7.2
-- ----------------------------------------------------------------
-- SSL Status Objects:
-- Connection Group

totalRSAOperations	OBJECT-TYPE
	SYNTAX		Integer32
	MAX-ACCESS	read-only
	STATUS		mandatory
	DESCRIPTION
		"The total number of RSA operations performed on
		 the device."
	::= { sslTranStats 20 }
 
connRejNoRes	OBJECT-TYPE
	SYNTAX		Integer32
	MAX-ACCESS	read-only
	STATUS		mandatory
	DESCRIPTION
		"SSL connections rejected due to low resources - 
		 indicates that the limit to server connections
		 for existing resources was reached resulting in 
		 the rejection of additional connections."
	::= { sslTranStats 21 }
 
activeConnBlock	OBJECT-TYPE
	SYNTAX		Integer32
	MAX-ACCESS	read-only
	STATUS		mandatory
	DESCRIPTION
		"Active SSL connection blocks - 
		 equivalent to number of active client SSL connections"
	::= { sslTranStats 22 }
 
activeClientConns	OBJECT-TYPE
	SYNTAX		Integer32
	MAX-ACCESS	read-only
	STATUS		mandatory
	DESCRIPTION
		"Active client SSL connections."
	::= { sslTranStats 23 }
 
connAccepted	OBJECT-TYPE
	SYNTAX		Integer32
	MAX-ACCESS	read-only
	STATUS		mandatory
	DESCRIPTION
		"Total SSL connections accepted"
	::= { sslTranStats 24 }
 
activeServerConns	OBJECT-TYPE
	SYNTAX		Integer32
	MAX-ACCESS	read-only
	STATUS		mandatory
	DESCRIPTION
		"Active backend webserver connections"
	::= { sslTranStats 25 }
 
sslNegRefused	OBJECT-TYPE
	SYNTAX		Integer32
	MAX-ACCESS	read-only
	STATUS		mandatory
	DESCRIPTION
		"SSL Connection negotiations refused"
	::= { sslTranStats 31 }
 
sslNegAccept	OBJECT-TYPE
	SYNTAX		Integer32
	MAX-ACCESS	read-only
	STATUS		mandatory
	DESCRIPTION
		"Number of successful SSL socket negotiations"
	::= { sslTranStats 32 }
 
activeOpenSockets	OBJECT-TYPE
	SYNTAX		Integer32
	MAX-ACCESS	read-only
	STATUS		mandatory
	DESCRIPTION
		"Active SSL related open socket count. Includes client,
                 server, and listening sockets."
	::= { sslTranStats 33 }
 
-- ----------------------------------------------------------------
sslTranErrs     OBJECT IDENTIFIER ::= { sonicSSLTran 3 }
-- 1.3.6.1.4.1.8714.2.1.7.3
-- ----------------------------------------------------------------
connErrs	OBJECT-TYPE
	SYNTAX		Integer32
	MAX-ACCESS	read-only
	STATUS		mandatory
	DESCRIPTION
		"Connection failures to the remote server."
	::= { sslTranErrs 26 }
 
connBlockErrs	OBJECT-TYPE
	SYNTAX		Integer32
	MAX-ACCESS	read-only
	STATUS		mandatory
	DESCRIPTION
		"SSL Connection Block errors"
	::= { sslTranErrs 27 }
 
sslNegErrs	OBJECT-TYPE
	SYNTAX		Integer32
	MAX-ACCESS	read-only
	STATUS		mandatory
	DESCRIPTION
		"SSL Connection Negotiation errors"
	::= { sslTranErrs 34 }
 
sslErrors	OBJECT-TYPE
	SYNTAX		Integer32
	MAX-ACCESS	read-only
	STATUS		mandatory
	DESCRIPTION
		"Total SSL errors"
	::= { sslTranErrs 35 }
 
openSSLAcceptErrs	OBJECT-TYPE
	SYNTAX		Integer32
	MAX-ACCESS	read-only
	STATUS		mandatory
	DESCRIPTION
		"Total SSL accept errors"
	::= { sslTranErrs 36 }
 
openSSLConnErrs	OBJECT-TYPE
	SYNTAX		Integer32
	MAX-ACCESS	read-only
	STATUS		mandatory
	DESCRIPTION
		"Total SSL connection errors"
	::= { sslTranErrs 37 }
 
totSocketErrs	OBJECT-TYPE
	SYNTAX		Integer32
	MAX-ACCESS	read-only
	STATUS		mandatory
	DESCRIPTION
		"Total SSL socket errors"
	::= { sslTranErrs 38 }
 
openSSLWriteErr	OBJECT-TYPE
	SYNTAX		Integer32
	MAX-ACCESS	read-only
	STATUS		mandatory
	DESCRIPTION
		"SSL client write errors"
	::= { sslTranErrs 41 }
 
sslPipeWriteErr	OBJECT-TYPE
	SYNTAX		Integer32
	MAX-ACCESS	read-only
	STATUS		mandatory
	DESCRIPTION
		"SSL client pipe write errors"
	::= { sslTranErrs 42 }
 
toServerWriteErr	OBJECT-TYPE
	SYNTAX		Integer32
	MAX-ACCESS	read-only
	STATUS		mandatory
	DESCRIPTION
		"Backend server write errors"
	::= { sslTranErrs 43 }
 
toServerPipeWriteErr	OBJECT-TYPE
	SYNTAX		Integer32
	MAX-ACCESS	read-only
	STATUS		mandatory
	DESCRIPTION
		"Backend server write pipe errors"
	::= { sslTranErrs 44 }

openSSLReadErr	OBJECT-TYPE
	SYNTAX		Integer32
	MAX-ACCESS	read-only
	STATUS		mandatory
	DESCRIPTION
		"SSL client read errors"
	::= { sslTranErrs 45 }
 
sslPipeReadErr	OBJECT-TYPE
	SYNTAX		Integer32
	MAX-ACCESS	read-only
	STATUS		mandatory
	DESCRIPTION
		"SSL client read pipe errors"
	::= { sslTranErrs 46 }
 
toServerReadErr	OBJECT-TYPE
	SYNTAX		Integer32
	MAX-ACCESS	read-only
	STATUS		mandatory
	DESCRIPTION
		"Backend server read errors"
	::= { sslTranErrs 47 }

toServerPipeReadErr	OBJECT-TYPE
	SYNTAX		Integer32
	MAX-ACCESS	read-only
	STATUS		mandatory
	DESCRIPTION
		"Backend server pipe read errors"
	::= { sslTranErrs 48 }

-- ----------------------------------------------------------------
sslTranEvents	     OBJECT IDENTIFIER ::= { sonicSSLTran 10 }
-- 1.3.6.1.4.1.8714.2.1.7.10
-- ----------------------------------------------------------------
 
sslTpsChangeHi TRAP-TYPE
    ENTERPRISE sslTranEvents
    DESCRIPTION
	"The number of SSL negotiations per second has transitioned
	 above the upper threshold limit."
    ::= 4 

sslTpsChangeLo TRAP-TYPE
    ENTERPRISE sslTranEvents
    DESCRIPTION
	"The number of SSL transactions per second has transitioned
	 below the lower threshold limit."
    ::= 5

sslTotalConnectsChangeHi TRAP-TYPE
    ENTERPRISE sslTranEvents
    DESCRIPTION
	"The number of SSL connections has transitioned above the upper
	 threshold limit."
    ::= 6

sslTotalConnectsChangeLo TRAP-TYPE
    ENTERPRISE sslTranEvents
    DESCRIPTION
	"The number of SSL connections has transitioned below the
	 lower threshould limit."
    ::= 7

END
