--			Ascend mibx25 MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBX25-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibx25Profile  OBJECT IDENTIFIER ::= { configuration 140}

	-- The mibx25Profile table
	--
	-- This table contains parameters for the mibx25Profile profile
	--

    mibx25ProfileTable	OBJECT-TYPE
	SYNTAX		SEQUENCE OF Mibx25ProfileEntry
	ACCESS		not-accessible
	STATUS		mandatory
	DESCRIPTION	"A list of mibx25Profile profile entries."
	::= { mibx25Profile 1 }

    mibx25ProfileEntry	OBJECT-TYPE
	SYNTAX		Mibx25ProfileEntry
	ACCESS		not-accessible
	STATUS		mandatory
	DESCRIPTION	"A mibx25Profile entry containing objects that
			 maps to the parameters of mibx25Profile profile."
	INDEX		{ x25Profile-X25Name }
	::= { mibx25ProfileTable 1 }

    Mibx25ProfileEntry ::=
	SEQUENCE {
	    x25Profile-X25Name
		DisplayString,
	    x25Profile-Active
		INTEGER,
	    x25Profile-Kludge
		INTEGER,
	    x25Profile-NailedUpGroup
		INTEGER,
	    x25Profile-NailedMode
		INTEGER,
	    x25Profile-CalledNumberType
		INTEGER,
	    x25Profile-SwitchedCallType
		INTEGER,
	    x25Profile-PhoneNumber
		DisplayString,
	    x25Profile-BillingNumber
		DisplayString,
	    x25Profile-TransitNumber
		DisplayString,
	    x25Profile-CallByCallId
		INTEGER,
	    x25Profile-oT1Val
		INTEGER,
	    x25Profile-oT2Val
		INTEGER,
	    x25Profile-oN2Val
		INTEGER,
	    x25Profile-KVal
		INTEGER,
	    x25Profile-IdleVal
		INTEGER,
	    x25Profile-oPktWindow
		INTEGER,
	    x25Profile-Maxwinsize
		INTEGER,
	    x25Profile-Defwinsize
		INTEGER,
	    x25Profile-oPktSize
		INTEGER,
	    x25Profile-oMinPktSize
		INTEGER,
	    x25Profile-Defpktsize
		INTEGER,
	    x25Profile-oMaxPktSize
		INTEGER,
	    x25Profile-LowestPVC
		INTEGER,
	    x25Profile-HighestPVC
		INTEGER,
	    x25Profile-LowestSVC
		INTEGER,
	    x25Profile-HighestSVC
		INTEGER,
	    x25Profile-ClearDiag
		INTEGER,
	    x25Profile-ResetDiag
		INTEGER,
	    x25Profile-RestartDiag
		INTEGER,
	    x25Profile-Pktdiag
		INTEGER,
	    x25Profile-PktOptions
		INTEGER,
	    x25Profile-PktT20
		INTEGER,
	    x25Profile-PktR20
		INTEGER,
	    x25Profile-PktT21
		INTEGER,
	    x25Profile-PktT22
		INTEGER,
	    x25Profile-PktR22
		INTEGER,
	    x25Profile-PktT23
		INTEGER,
	    x25Profile-PktR23
		INTEGER,
	    x25Profile-X25SrcAddress
		DisplayString,
	    x25Profile-DteFlag
		INTEGER,
	    x25Profile-NetType
		INTEGER,
	    x25Profile-oDiscMode
		INTEGER,
	    x25Profile-oSeqNumbers
		INTEGER,
	    x25Profile-ReverseChargeAcceptance
		INTEGER,
	    x25Profile-ClosedUserGroups
		INTEGER,
	    x25Profile-oVceTimerVal
		INTEGER,
	    x25Profile-oX25DTeiValue
		INTEGER,
	    x25Profile-oPriNumberValue
		DisplayString,
	    x25Profile-Action-o
		INTEGER
	}

    x25Profile-X25Name	OBJECT-TYPE
	SYNTAX	DisplayString
	ACCESS	read-only
	STATUS	mandatory
	DESCRIPTION	"Name of the X.25 profile."
	::= { mibx25ProfileEntry 1 }

    x25Profile-Active	OBJECT-TYPE
	SYNTAX	INTEGER {
		    no (1),
		    yes (2)
		}
	ACCESS	read-write
	STATUS	mandatory
	DESCRIPTION	"Indicates whether this profile is to be included in the X.25 table."
	::= { mibx25ProfileEntry 2 }

    x25Profile-Kludge	OBJECT-TYPE
	SYNTAX	INTEGER {
		    no (1),
		    yes (2)
		}
	ACCESS	read-write
	STATUS	mandatory
	DESCRIPTION	"This is a kludge to indicate that the physical line is to be brought down before connecting. It is also used for outsequence on a reset. This byte formally a fill."
	::= { mibx25ProfileEntry 3 }

    x25Profile-NailedUpGroup	OBJECT-TYPE
	SYNTAX	INTEGER
	ACCESS	read-write
	STATUS	mandatory
	DESCRIPTION	"Specifies the nailed group number."
	::= { mibx25ProfileEntry 4 }

    x25Profile-NailedMode	OBJECT-TYPE
	SYNTAX	INTEGER {
		    off (1),
		    ft1 (2),
		    ft1Mpp (3),
		    bri (4),
		    ft1Bo (5),
		    dChan (6),
		    aodi (7),
		    megamax (8)
		}
	ACCESS	read-write
	STATUS	mandatory
	DESCRIPTION	"Specifies whether it is a nailed or switched."
	::= { mibx25ProfileEntry 5 }

    x25Profile-CalledNumberType	OBJECT-TYPE
	SYNTAX	INTEGER
	ACCESS	read-write
	STATUS	mandatory
	DESCRIPTION	"Indication of whether national national number, international number, etc. is specified."
	::= { mibx25ProfileEntry 6 }

    x25Profile-SwitchedCallType	OBJECT-TYPE
	SYNTAX	INTEGER {
		    voice (1),
		    n-56kRestricted (2),
		    n-64kClear (3),
		    n-64kRestricted (4),
		    n-56kClear (5),
		    n-384kRestricted (6),
		    n-384kClear (7),
		    n-1536kClear (8),
		    n-1536kRestricted (9),
		    n-128kClear (10),
		    n-192kClear (11),
		    n-256kClear (12),
		    n-320kClear (13),
		    dws384Clear (14),
		    n-448Clear (15),
		    n-512Clear (16),
		    n-576Clear (17),
		    n-640Clear (18),
		    n-704Clear (19),
		    n-768Clear (20),
		    n-832Clear (21),
		    n-896Clear (22),
		    n-960Clear (23),
		    n-1024Clear (24),
		    n-1088Clear (25),
		    n-1152Clear (26),
		    n-1216Clear (27),
		    n-1280Clear (28),
		    n-1344Clear (29),
		    n-1408Clear (30),
		    n-1472Clear (31),
		    n-1600Clear (32),
		    n-1664Clear (33),
		    n-1728Clear (34),
		    n-1792Clear (35),
		    n-1856Clear (36),
		    n-1920Clear (37),
		    x30RestrictedBearer (39),
		    v110ClearBearer (40),
		    n-64kX30Restricted (41),
		    n-56kV110Clear (42),
		    modem (43),
		    atmodem (44),
		    n-2456kV110 (46),
		    n-4856kV110 (47),
		    n-9656kV110 (48),
		    n-19256kV110 (49),
		    n-38456kV110 (50),
		    n-2456krV110 (51),
		    n-4856krV110 (52),
		    n-9656krV110 (53),
		    n-19256krV110 (54),
		    n-38456krV110 (55),
		    n-2464kV110 (56),
		    n-4864kV110 (57),
		    n-9664kV110 (58),
		    n-19264kV110 (59),
		    n-38464kV110 (60),
		    n-2464krV110 (61),
		    n-4864krV110 (62),
		    n-9664krV110 (63),
		    n-19264krV110 (64),
		    n-38464krV110 (65),
		    v32 (66),
		    phs64k (67),
		    voiceOverIp (68),
		    atmSvc (70),
		    frameRelaySvc (71),
		    vpnTunnel (72),
		    wormarq (73),
		    n-14456kV110 (74),
		    n-28856kV110 (75),
		    n-14456krV110 (76),
		    n-28856krV110 (77),
		    n-14464kV110 (78),
		    n-28864kV110 (79),
		    n-14464krV110 (80),
		    n-28864krV110 (81),
		    modem31khzAudio (82),
		    x25Svc (83),
		    n-144kClear (255),
		    iptoip (263)
		}
	ACCESS	read-write
	STATUS	mandatory
	DESCRIPTION	"Type of bearer channel capability to set up for each switched call in the session."
	::= { mibx25ProfileEntry 7 }

    x25Profile-PhoneNumber	OBJECT-TYPE
	SYNTAX	DisplayString
	ACCESS	read-write
	STATUS	mandatory
	DESCRIPTION	"The phonenumber of the named host."
	::= { mibx25ProfileEntry 8 }

    x25Profile-BillingNumber	OBJECT-TYPE
	SYNTAX	DisplayString
	ACCESS	read-write
	STATUS	mandatory
	DESCRIPTION	"A number used for billing purposes."
	::= { mibx25ProfileEntry 9 }

    x25Profile-TransitNumber	OBJECT-TYPE
	SYNTAX	DisplayString
	ACCESS	read-write
	STATUS	mandatory
	DESCRIPTION	"The string for use in the 'transit network ie' for PRI calling when going through a LEC."
	::= { mibx25ProfileEntry 10 }

    x25Profile-CallByCallId	OBJECT-TYPE
	SYNTAX	INTEGER
	ACCESS	read-write
	STATUS	mandatory
	DESCRIPTION	"Id for the call-by-call signalling for PRI."
	::= { mibx25ProfileEntry 11 }

    x25Profile-oT1Val	OBJECT-TYPE
	SYNTAX	INTEGER
	ACCESS	read-write
	STATUS	mandatory
	DESCRIPTION	"The time interval during which the LAPB shall expect to receive an acknowledgment to an outstanding I PDU or an expected response to a sent unnumbered PDU."
	::= { mibx25ProfileEntry 12 }

    x25Profile-oT2Val	OBJECT-TYPE
	SYNTAX	INTEGER
	ACCESS	read-write
	STATUS	mandatory
	DESCRIPTION	"The maximum delay at LAPB before transmitting a delayed RR. This must be considerably less than T1 the Acknowledgment Timer value."
	::= { mibx25ProfileEntry 13 }

    x25Profile-oN2Val	OBJECT-TYPE
	SYNTAX	INTEGER
	ACCESS	read-write
	STATUS	mandatory
	DESCRIPTION	"Maximum number of times that a PDU is sent following the expiry of the Acknowledgment Timer."
	::= { mibx25ProfileEntry 14 }

    x25Profile-KVal	OBJECT-TYPE
	SYNTAX	INTEGER
	ACCESS	read-write
	STATUS	mandatory
	DESCRIPTION	"LAPB Window size specifying the number of unacknowledged I PDUs which may be sent."
	::= { mibx25ProfileEntry 15 }

    x25Profile-IdleVal	OBJECT-TYPE
	SYNTAX	INTEGER
	ACCESS	read-write
	STATUS	mandatory
	DESCRIPTION	"Timer used to poll the the remote LAPB when there is no activity on the link to ensure the remote station is still alive. A value of zero disables this function."
	::= { mibx25ProfileEntry 45 }

    x25Profile-oPktWindow	OBJECT-TYPE
	SYNTAX	INTEGER
	ACCESS	read-write
	STATUS	mandatory
	DESCRIPTION	"X.25 Packet Window size."
	::= { mibx25ProfileEntry 16 }

    x25Profile-Maxwinsize	OBJECT-TYPE
	SYNTAX	INTEGER
	ACCESS	read-write
	STATUS	mandatory
	DESCRIPTION	"Maximum X.25 Window size which will be negotiated on calls."
	::= { mibx25ProfileEntry 46 }

    x25Profile-Defwinsize	OBJECT-TYPE
	SYNTAX	INTEGER
	ACCESS	read-write
	STATUS	mandatory
	DESCRIPTION	"Default X.25 Window size to use if not specified during call establishment."
	::= { mibx25ProfileEntry 47 }

    x25Profile-oPktSize	OBJECT-TYPE
	SYNTAX	INTEGER
	ACCESS	read-write
	STATUS	mandatory
	DESCRIPTION	"X.25 default Packet size."
	::= { mibx25ProfileEntry 17 }

    x25Profile-oMinPktSize	OBJECT-TYPE
	SYNTAX	INTEGER {
		    n-6 (7),
		    n-7 (8),
		    n-8 (9),
		    n-9 (10),
		    n-10 (11),
		    n-11 (12),
		    n-12 (13)
		}
	ACCESS	read-write
	STATUS	mandatory
	DESCRIPTION	"X.25 log base 2 of min packet size in negotiation."
	::= { mibx25ProfileEntry 18 }

    x25Profile-Defpktsize	OBJECT-TYPE
	SYNTAX	INTEGER {
		    n-6 (7),
		    n-7 (8),
		    n-8 (9),
		    n-9 (10),
		    n-10 (11),
		    n-11 (12),
		    n-12 (13)
		}
	ACCESS	read-write
	STATUS	mandatory
	DESCRIPTION	"Default X.25 Packet size to use if not specified during call establishment."
	::= { mibx25ProfileEntry 48 }

    x25Profile-oMaxPktSize	OBJECT-TYPE
	SYNTAX	INTEGER {
		    n-6 (7),
		    n-7 (8),
		    n-8 (9),
		    n-9 (10),
		    n-10 (11),
		    n-11 (12),
		    n-12 (13)
		}
	ACCESS	read-write
	STATUS	mandatory
	DESCRIPTION	"Maximum X.25 Packet size which will be negotiated on calls."
	::= { mibx25ProfileEntry 19 }

    x25Profile-LowestPVC	OBJECT-TYPE
	SYNTAX	INTEGER
	ACCESS	read-write
	STATUS	mandatory
	DESCRIPTION	"X.25 logical channel number assigned to the lowest PVC."
	::= { mibx25ProfileEntry 20 }

    x25Profile-HighestPVC	OBJECT-TYPE
	SYNTAX	INTEGER
	ACCESS	read-write
	STATUS	mandatory
	DESCRIPTION	"X.25 logical channel number assigned to the highest PVC."
	::= { mibx25ProfileEntry 21 }

    x25Profile-LowestSVC	OBJECT-TYPE
	SYNTAX	INTEGER
	ACCESS	read-write
	STATUS	mandatory
	DESCRIPTION	"X.25 logical channel number assigned to the lowest SVC."
	::= { mibx25ProfileEntry 22 }

    x25Profile-HighestSVC	OBJECT-TYPE
	SYNTAX	INTEGER
	ACCESS	read-write
	STATUS	mandatory
	DESCRIPTION	"X.25 logical channel number assigned to the highest SVC."
	::= { mibx25ProfileEntry 23 }

    x25Profile-ClearDiag	OBJECT-TYPE
	SYNTAX	INTEGER {
		    no (1),
		    yes (2)
		}
	ACCESS	read-write
	STATUS	mandatory
	DESCRIPTION	"X.25 Clear request has DIAG."
	::= { mibx25ProfileEntry 24 }

    x25Profile-ResetDiag	OBJECT-TYPE
	SYNTAX	INTEGER {
		    no (1),
		    yes (2)
		}
	ACCESS	read-write
	STATUS	mandatory
	DESCRIPTION	"X.25 reset request has DIAG."
	::= { mibx25ProfileEntry 25 }

    x25Profile-RestartDiag	OBJECT-TYPE
	SYNTAX	INTEGER {
		    no (1),
		    yes (2)
		}
	ACCESS	read-write
	STATUS	mandatory
	DESCRIPTION	"X.25 restart request has DIAG."
	::= { mibx25ProfileEntry 26 }

    x25Profile-Pktdiag	OBJECT-TYPE
	SYNTAX	INTEGER {
		    no (1),
		    yes (2)
		}
	ACCESS	read-write
	STATUS	mandatory
	DESCRIPTION	"Incoming Restart, Clear and Reset Indications will contain the diagnostic byte"
	::= { mibx25ProfileEntry 49 }

    x25Profile-PktOptions	OBJECT-TYPE
	SYNTAX	INTEGER {
		    none (1),
		    npws (2),
		    afna (3),
		    npwsAfna (4)
		}
	ACCESS	read-write
	STATUS	mandatory
	DESCRIPTION	"X.25 packet level options."
	::= { mibx25ProfileEntry 27 }

    x25Profile-PktT20	OBJECT-TYPE
	SYNTAX	INTEGER
	ACCESS	read-write
	STATUS	mandatory
	DESCRIPTION	"X.25 restart request response timer."
	::= { mibx25ProfileEntry 28 }

    x25Profile-PktR20	OBJECT-TYPE
	SYNTAX	INTEGER
	ACCESS	read-write
	STATUS	mandatory
	DESCRIPTION	"Number of times an X.25 restart request will be retried."
	::= { mibx25ProfileEntry 29 }

    x25Profile-PktT21	OBJECT-TYPE
	SYNTAX	INTEGER
	ACCESS	read-write
	STATUS	mandatory
	DESCRIPTION	"X.25 call request response timer."
	::= { mibx25ProfileEntry 30 }

    x25Profile-PktT22	OBJECT-TYPE
	SYNTAX	INTEGER
	ACCESS	read-write
	STATUS	mandatory
	DESCRIPTION	"X.25 reset request response timer."
	::= { mibx25ProfileEntry 31 }

    x25Profile-PktR22	OBJECT-TYPE
	SYNTAX	INTEGER
	ACCESS	read-write
	STATUS	mandatory
	DESCRIPTION	"Number of times an X.25 reset request will be retried."
	::= { mibx25ProfileEntry 32 }

    x25Profile-PktT23	OBJECT-TYPE
	SYNTAX	INTEGER
	ACCESS	read-write
	STATUS	mandatory
	DESCRIPTION	"X.25 clear request response timer."
	::= { mibx25ProfileEntry 33 }

    x25Profile-PktR23	OBJECT-TYPE
	SYNTAX	INTEGER
	ACCESS	read-write
	STATUS	mandatory
	DESCRIPTION	"Number of times an X.25 clear request will be retried."
	::= { mibx25ProfileEntry 34 }

    x25Profile-X25SrcAddress	OBJECT-TYPE
	SYNTAX	DisplayString
	ACCESS	read-write
	STATUS	mandatory
	DESCRIPTION	"X.25 source address"
	::= { mibx25ProfileEntry 50 }

    x25Profile-DteFlag	OBJECT-TYPE
	SYNTAX	INTEGER {
		    dce (1),
		    dte (2)
		}
	ACCESS	read-write
	STATUS	mandatory
	DESCRIPTION	"Indicates the DTE/DCE nature of the X.25 protocol."
	::= { mibx25ProfileEntry 36 }

    x25Profile-NetType	OBJECT-TYPE
	SYNTAX	INTEGER {
		    ccitt (1),
		    ddn (2)
		}
	ACCESS	read-write
	STATUS	mandatory
	DESCRIPTION	"Net Type Enum"
	::= { mibx25ProfileEntry 37 }

    x25Profile-oDiscMode	OBJECT-TYPE
	SYNTAX	INTEGER {
		    passive (1),
		    active (2)
		}
	ACCESS	read-write
	STATUS	mandatory
	DESCRIPTION	"Disc Mode: Active or passive"
	::= { mibx25ProfileEntry 38 }

    x25Profile-oSeqNumbers	OBJECT-TYPE
	SYNTAX	INTEGER {
		    normal (1),
		    extended (2)
		}
	ACCESS	read-write
	STATUS	mandatory
	DESCRIPTION	"Sequence numbers mode: normal or extended"
	::= { mibx25ProfileEntry 39 }

    x25Profile-ReverseChargeAcceptance	OBJECT-TYPE
	SYNTAX	INTEGER {
		    no (1),
		    yes (2)
		}
	ACCESS	read-write
	STATUS	mandatory
	DESCRIPTION	"Reverse Charge Acceptance if set permits the use of reverse charges on Incoming Call packets."
	::= { mibx25ProfileEntry 40 }

    x25Profile-ClosedUserGroups	OBJECT-TYPE
	SYNTAX	INTEGER {
		    none (1),
		    noiob (2),
		    noioe (3),
		    prefb (4),
		    prefe (5),
		    oab (6),
		    oae (7)
		}
	ACCESS	read-write
	STATUS	mandatory
	DESCRIPTION	"Type of Closed User Group facilities subscribed to."
	::= { mibx25ProfileEntry 51 }

    x25Profile-oVceTimerVal	OBJECT-TYPE
	SYNTAX	INTEGER
	ACCESS	read-write
	STATUS	mandatory
	DESCRIPTION	"Virtual Call Establishment Timer Interval: number of seconds to maintain a connection to a character oriented device that has not established a virtual call. A value of 0 disables the timer box-wide"
	::= { mibx25ProfileEntry 41 }

    x25Profile-oX25DTeiValue	OBJECT-TYPE
	SYNTAX	INTEGER
	ACCESS	read-write
	STATUS	mandatory
	DESCRIPTION	"TEI to be used when D-channel X.25"
	::= { mibx25ProfileEntry 42 }

    x25Profile-oPriNumberValue	OBJECT-TYPE
	SYNTAX	DisplayString
	ACCESS	read-write
	STATUS	mandatory
	DESCRIPTION	"Phone number to be used for BAP"
	::= { mibx25ProfileEntry 43 }

    x25Profile-Action-o	OBJECT-TYPE
	SYNTAX	INTEGER {
		    noAction (1),
		    createProfile (2),
		    deleteProfile (3)
		}
	ACCESS	read-write
	STATUS	mandatory
	DESCRIPTION	""
	::= { mibx25ProfileEntry 44 }

END
