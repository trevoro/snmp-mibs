-- This MIB contains a description of the I/O port data generator

CXLANIOGEN-PORT-MIB
DEFINITIONS ::= BEGIN

IMPORTS
   Counter                 FROM RFC1155-SMI
   OBJECT-TYPE             FROM RFC-1212
   cxLanIoPort             FROM CXProduct-SMI;

   PhysAddress ::=         OCTET STRING

-- Table to configure data generation on the physical LAN ports.

   cxLanIoGenPortTable        OBJECT-TYPE
      SYNTAX  SEQUENCE OF CxLanIoGenPortEntry
      ACCESS  not-accessible
      STATUS  mandatory
      DESCRIPTION
	 "Table which holds all the basic information on a  
	 hardware port"
      ::= { cxLanIoPort 2 }

   cxLanIoGenPortEntry        OBJECT-TYPE
      SYNTAX  CxLanIoGenPortEntry
      ACCESS  not-accessible
      STATUS  mandatory
      DESCRIPTION
	 " Entry in the table, defines basic attributes of
	 any LAN port."
      INDEX           {cxLanIoGenPortIndex}
      ::= {cxLanIoGenPortTable 1}

   CxLanIoGenPortEntry ::=

      SEQUENCE {
	 cxLanIoGenPortIndex
	    INTEGER,
	 cxLanIoGenMacAddrSrc
	    PhysAddress,
	 cxLanIoGenMacAddrDst
	    PhysAddress,
	 cxLanIoGenType
	    INTEGER,
	 cxLanIoGenDelay
	    INTEGER,
	 cxLanIoGenFrameSize
	    INTEGER,
	 cxLanIoGenStatus
	    INTEGER,
	 cxLanIoGenRxError
	    Counter
      }

      cxLanIoGenPortIndex        OBJECT-TYPE
      SYNTAX  INTEGER
      ACCESS  read-only
      STATUS  mandatory
      DESCRIPTION
	 " An index value which identifies the LAN port where the data generation 
	   will take place.  This is corrolated to the index in the cxLanIoPortTable."
      ::= {cxLanIoGenPortEntry 1 }

      cxLanIoGenMacAddrSrc       OBJECT-TYPE
      SYNTAX  PhysAddress
      ACCESS  read-write
      STATUS  mandatory
      DESCRIPTION
	 " Source MAC Address inserted in the frame generated."
      ::= {cxLanIoGenPortEntry 2 }

      cxLanIoGenMacAddrDst       OBJECT-TYPE
      SYNTAX  PhysAddress
      ACCESS  read-write
      STATUS  mandatory
      DESCRIPTION
	 " Destination MAC Address inserted in the frame generated."
      ::= {cxLanIoGenPortEntry 3 }

      cxLanIoGenType             OBJECT-TYPE
      SYNTAX  INTEGER {
		 invalid(1),                    -- used to delete this row entry
		 disabled(2),                   -- generator is disabled
		 internalLoopbackLevel1(3), -- generator will set up the chip 
						--  for internal loopback at level 1
		 internalLoopbackLevel2(4), -- generator will set up the chip 
						--  for internal loopback at level 2
		 noLoopbackFrameVerify(5),  -- generator will not be set up for loopback but
									--  will verify the frame if destaddr == local addr.
		 noLoopbackFrameForward(6)  -- generator will not be set up for loopback but
									--  frame will be pass to upper layers.
	      }
      ACCESS  read-write
      STATUS  mandatory
      DESCRIPTION
	 " Object to control the generator behavior."
      ::= {cxLanIoGenPortEntry 4 }

      cxLanIoGenDelay            OBJECT-TYPE
      SYNTAX  INTEGER (1..255)
      ACCESS  read-write
      STATUS  mandatory
      DESCRIPTION
	 " Indication on the delay between the frame generated."
      ::= {cxLanIoGenPortEntry 5 }

      cxLanIoGenFrameSize        OBJECT-TYPE
      SYNTAX  INTEGER (64..4096)
      ACCESS  read-write
      STATUS  mandatory
      DESCRIPTION
	 " Frame size generated."
      ::= {cxLanIoGenPortEntry 6 }

      cxLanIoGenStatus           OBJECT-TYPE
      SYNTAX  INTEGER {
		 disabled(2),                   -- generator is disabled
		 internalLoopbackLevel1(3), -- generator will set up the chip 
						--  for internal loopback at level 1
		 internalLoopbackLevel2(4), -- generator will set up the chip 
						--  for internal loopback at level 2
		 noLoopbackFrameVerify(5),  -- generator will not be set up for loopback but
									--  will verify the frame if destaddr == local addr.
		 noLoopbackFrameForward(6)  -- generator will not be set up for loopback but
									--  frame will be pass to upper layers.
	      }
      ACCESS  read-only
      STATUS  mandatory
      DESCRIPTION
	 " Object to report the current status of the data generator."
      ::= {cxLanIoGenPortEntry 7 }

      cxLanIoGenRxError          OBJECT-TYPE
      SYNTAX  Counter
      ACCESS  read-only
      STATUS  mandatory
      DESCRIPTION
	 " Number of error the data generator detected."
      ::= {cxLanIoGenPortEntry 8 }

END
