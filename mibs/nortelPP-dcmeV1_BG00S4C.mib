Nortel-Magellan-Passport-DcmeMIB
DEFINITIONS ::= BEGIN



IMPORTS

      OBJECT-TYPE
   FROM RFC-1212

      components,
      passportMIBs
   FROM Nortel-Magellan-Passport-UsefulDefinitionsMIB

      Counter32,
      RowPointer,
      DisplayString,
      StorageType,
      RowStatus,
      PassportCounter64,
      Gauge32,
      Integer32,
      Unsigned32
   FROM Nortel-Magellan-Passport-StandardTextualConventionsMIB

      AsciiString,
      Hex,
      NonReplicated,
      EnterpriseDateAndTime,
      FixedPoint1,
      Link,
      DigitString
   FROM Nortel-Magellan-Passport-TextualConventionsMIB;




-- LAST-UPDATED   "9906090000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     Dcme Enterprise MIB."

dcmeMIB OBJECT IDENTIFIER ::= { passportMIBs 134 }










-- Dcme/n
-- This component defines the common characteristics of a set of 
-- connections to an International Switching Centre (ISC) equipment.

dcme OBJECT IDENTIFIER ::= { components 129 }



dcmeRowStatusTable OBJECT-TYPE
   SYNTAX     SEQUENCE OF DcmeRowStatusEntry
   ACCESS     not-accessible
   STATUS     mandatory
   DESCRIPTION
     "This entry controls the addition and deletion of 
      dcme components."
::= { dcme 1 }

dcmeRowStatusEntry OBJECT-TYPE
   SYNTAX     DcmeRowStatusEntry
   ACCESS     not-accessible
   STATUS     mandatory
   DESCRIPTION
     "A single entry in the table represents a single 
      dcme component."
   INDEX {
      dcmeIndex }
::= { dcmeRowStatusTable 1 }

DcmeRowStatusEntry ::= SEQUENCE {
   dcmeRowStatus
      RowStatus,
   dcmeComponentName
      DisplayString,
   dcmeStorageType
      StorageType,
   dcmeIndex
      Integer32 }

dcmeRowStatus OBJECT-TYPE
   SYNTAX     RowStatus 
   ACCESS     read-write
   STATUS     mandatory
   DESCRIPTION
     "This variable is used as the basis for SNMP naming of
      dcme components.
      These components can be added and deleted."
::= { dcmeRowStatusEntry 1 }

dcmeComponentName OBJECT-TYPE
   SYNTAX     DisplayString 
   ACCESS     read-only
   STATUS     mandatory
   DESCRIPTION
     "This variable provides the component's string name for
      use with the ASCII Console Interface"
::= { dcmeRowStatusEntry 2 }

dcmeStorageType OBJECT-TYPE
   SYNTAX     StorageType 
   ACCESS     read-only
   STATUS     mandatory
   DESCRIPTION
     "This variable represents the storage type value for the
      dcme tables."
::= { dcmeRowStatusEntry 4 }

dcmeIndex OBJECT-TYPE
   SYNTAX     Integer32 (1..16)
   ACCESS     not-accessible
   STATUS     mandatory
   DESCRIPTION
     "This variable represents the index for the dcme tables."
::= { dcmeRowStatusEntry 10 }

dcmeProvTable OBJECT-TYPE
   SYNTAX     SEQUENCE OF DcmeProvEntry
   ACCESS     not-accessible
   STATUS     mandatory
   DESCRIPTION
     "This group contains the provisionable attributes of a Dcme 
      component."
::= { dcme 10 }

dcmeProvEntry OBJECT-TYPE
   SYNTAX     DcmeProvEntry
   ACCESS     not-accessible
   STATUS     mandatory
   DESCRIPTION
     "An entry in the dcmeProvTable."
   INDEX {
      dcmeIndex }
::= { dcmeProvTable 1 }

DcmeProvEntry ::= SEQUENCE {
   dcmeCommentText
      AsciiString,
   dcmePreestablishedConnections
      Unsigned32,
   dcmeTrmThreshold
      Unsigned32,
   dcmeTrmSignalChangeInterval
      Unsigned32,
   dcmeSpeechAlarmThreshold
      Unsigned32,
   dcmeAudio3kHzAlarmThreshold
      Unsigned32,
   dcmeUnrestricted64kAlarmThreshold
      Unsigned32,
   dcmeAlarmTimeInterval
      Unsigned32,
   dcmeMaxUnrestricted64kCalls
      Unsigned32 }

dcmeCommentText OBJECT-TYPE
   SYNTAX     AsciiString (SIZE (0..40))
   ACCESS     read-write
   STATUS     mandatory
   DESCRIPTION
     "Use of this attribute is at the discretion of the system administrator. 
      Typically, it specifies the name of the customer that is using this 
      Dcme."
   DEFVAL     { ''H }  -- ""
::= { dcmeProvEntry 1 }

dcmePreestablishedConnections OBJECT-TYPE
   SYNTAX     Unsigned32 (1..30)
   ACCESS     read-write
   STATUS     mandatory
   DESCRIPTION
     "This attribute specifies the number of Logical Connections (LC) 
      preestablished between each DcmeLink associated with this Dcme 
      and its remote peer, that are established beyond those that are 
      required to carry established connections. Those are the standby 
      LCs to be used for the subsequent user speech or audio 3.1 kHz 
      calls. This attribute should be set to the number of speech and audio 
      3.1 kHz calls expected in a typical burst of calls received from the 
      ISC on one DcmeLink."
   DEFVAL     { 5 }
::= { dcmeProvEntry 2 }

dcmeTrmThreshold OBJECT-TYPE
   SYNTAX     Unsigned32 (0..30)
   ACCESS     read-write
   STATUS     mandatory
   DESCRIPTION
     "This attribute is used to determine when the DcmeLink may be 
      unable to handle incoming calls from the ISC. If the Dcme fails to 
      replenish the number of preestablished connections the 'No trunk(s) 
      available for 3.1 kHz audio or speech' TRM signal is sent to the 
      ISC."
   DEFVAL     { 1 }
::= { dcmeProvEntry 3 }

dcmeTrmSignalChangeInterval OBJECT-TYPE
   SYNTAX     Unsigned32 (10..300)
   ACCESS     read-write
   STATUS     mandatory
   DESCRIPTION
     "This attribute specifies a minimum time interval between TRM 
      signal change from 'No trunk(s) available for 3.1 kHz audio or 
      speech' or 'No 64 kbit/s capacity available' to 'DCME normal' 
      signal."
   DEFVAL     { 20 }
::= { dcmeProvEntry 4 }

dcmeSpeechAlarmThreshold OBJECT-TYPE
   SYNTAX     Unsigned32 (0..1000)
   ACCESS     read-write
   STATUS     mandatory
   DESCRIPTION
     "This attribute specifies how many normal speech calls can be 
      rejected by one dcmeLink within the alarmTimeInterval time before 
      a SET alarm is generated. This alarm is cleared when the number of 
      rejected speech calls is less than speechAlarmThreshold in a 
      subsequent interval. 
      If the value is 0 the rejected speech calls are not monitored."
   DEFVAL     { 0 }
::= { dcmeProvEntry 5 }

dcmeAudio3kHzAlarmThreshold OBJECT-TYPE
   SYNTAX     Unsigned32 (0..1000)
   ACCESS     read-write
   STATUS     mandatory
   DESCRIPTION
     "This attribute specifies how many audio 3.1 kHz calls can be 
      rejected by one dcmeLink within the alarmTimeInterval time before 
      a SET alarm is generated. This alarm is cleared when the number of 
      rejected audio 3.1 kHz calls is less than audio3kHzAlarmThreshold 
      in a subsequent interval. 
      If the value is 0 the rejected audio 3.1 kHz calls are not monitored."
   DEFVAL     { 0 }
::= { dcmeProvEntry 6 }

dcmeUnrestricted64kAlarmThreshold OBJECT-TYPE
   SYNTAX     Unsigned32 (0..1000)
   ACCESS     read-write
   STATUS     mandatory
   DESCRIPTION
     "This attribute specifies how many unrestricted 64 kbit/s calls can be 
      rejected by one dcmeLink within the alarmTimeInterval time before 
      a SET alarm is generated. This alarm is cleared when the number of 
      rejected unrestricted 64 kbit/s calls is less than 
      unrestricted64kAlarmThreshold in a subsequent interval. 
      If the value is 0 the rejected unrestricted 64 kbit/s calls are not 
      monitored."
   DEFVAL     { 0 }
::= { dcmeProvEntry 7 }

dcmeAlarmTimeInterval OBJECT-TYPE
   SYNTAX     Unsigned32 (0..120)
   ACCESS     read-write
   STATUS     mandatory
   DESCRIPTION
     "This attribute specifies the time interval within which the rejected 
      speech calls, audio 3.1 kHz calls, and unrestricted 64 kbit/s calls are 
      monitored. It is used in the conjunction with the 
      speechAlarmThreshold, audio3kHzAlarmThreshold, and 
      unrestricted64kAlarmThreshold attributes."
   DEFVAL     { 5 }
::= { dcmeProvEntry 8 }

dcmeMaxUnrestricted64kCalls OBJECT-TYPE
   SYNTAX     Unsigned32 (0..420)
   ACCESS     read-write
   STATUS     mandatory
   DESCRIPTION
     "This attribute specifies the maximum number of simultaneous 
      dynamic unrestricted 64 kbit/s calls that can be established. A value 
      of 0 means that no dynamic unrestricted 64 kbit/s calls can be 
      established."
   DEFVAL     { 420 }
::= { dcmeProvEntry 9 }

dcmeStateTable OBJECT-TYPE
   SYNTAX     SEQUENCE OF DcmeStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { dcme 11 }

dcmeStateEntry OBJECT-TYPE
   SYNTAX     DcmeStateEntry
   ACCESS     not-accessible
   STATUS     mandatory
   DESCRIPTION
     "An entry in the dcmeStateTable."
   INDEX {
      dcmeIndex }
::= { dcmeStateTable 1 }

DcmeStateEntry ::= SEQUENCE {
   dcmeAdminState
      INTEGER,
   dcmeOperationalState
      INTEGER,
   dcmeUsageState
      INTEGER }

dcmeAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { dcmeStateEntry 1 }

dcmeOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { dcmeStateEntry 2 }

dcmeUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { dcmeStateEntry 3 }

dcmeStatsTable OBJECT-TYPE
   SYNTAX     SEQUENCE OF DcmeStatsEntry
   ACCESS     not-accessible
   STATUS     mandatory
   DESCRIPTION
     "This group contains the statistics maintained by this Dcme."
::= { dcme 13 }

dcmeStatsEntry OBJECT-TYPE
   SYNTAX     DcmeStatsEntry
   ACCESS     not-accessible
   STATUS     mandatory
   DESCRIPTION
     "An entry in the dcmeStatsTable."
   INDEX {
      dcmeIndex }
::= { dcmeStatsTable 1 }

DcmeStatsEntry ::= SEQUENCE {
   dcmeTrm64kNotAvailable
      Counter32,
   dcmeTrmSpeechNotAvailable
      Counter32 }

dcmeTrm64kNotAvailable OBJECT-TYPE
   SYNTAX     Counter32 
   ACCESS     read-only
   STATUS     mandatory
   DESCRIPTION
     "This attribute counts the total number of times the TRM signal was 
      changed to the 'No 64 kbit/s capacity available' signal.
      This counter wraps to zero when it exceeds its maximum."
::= { dcmeStatsEntry 1 }

dcmeTrmSpeechNotAvailable OBJECT-TYPE
   SYNTAX     Counter32 
   ACCESS     read-only
   STATUS     mandatory
   DESCRIPTION
     "This attribute counts the total number of times the TRM signal was 
      changed to the 'No trunk(s) available for 3.1 kHz audio or speech' 
      signal.
      This counter wraps to zero when it exceeds its maximum."
::= { dcmeStatsEntry 2 }

dcmeDLinksTable OBJECT-TYPE
   SYNTAX     SEQUENCE OF DcmeDLinksEntry
   ACCESS     not-accessible
   STATUS     mandatory
   DESCRIPTION
     "This attribute specifies all of the DcmeLinks which are associated 
      with this Dcme. There can be up to 14 DcmeLinks associated with 
      one Dcme."
::= { dcme 419 }

dcmeDLinksEntry OBJECT-TYPE
   SYNTAX     DcmeDLinksEntry
   ACCESS     not-accessible
   STATUS     mandatory
   DESCRIPTION
     "An entry in the dcmeDLinksTable."
   INDEX {
      dcmeIndex,
      dcmeDLinksValue }
::= { dcmeDLinksTable 1 }

DcmeDLinksEntry ::= SEQUENCE {
   dcmeDLinksValue
      Link,
   dcmeDLinksRowStatus
      RowStatus }

dcmeDLinksValue OBJECT-TYPE
   SYNTAX     Link 
   ACCESS     read-write
   STATUS     mandatory
   DESCRIPTION
     "This variable represents both the value and the index for the
      dcmeDLinksTable."
::= { dcmeDLinksEntry 1 }

dcmeDLinksRowStatus OBJECT-TYPE
   SYNTAX     RowStatus 
   ACCESS     write-only
   STATUS     mandatory
   DESCRIPTION
     "This variable is used to control the addition and deletion 
      of individual values of the dcmeDLinksTable."
::= { dcmeDLinksEntry 2 }

dcmeActiveDcmeLinksTable OBJECT-TYPE
   SYNTAX     SEQUENCE OF DcmeActiveDcmeLinksEntry
   ACCESS     not-accessible
   STATUS     mandatory
   DESCRIPTION
     "This attribute indicates all of the DcmeLink components that are 
      currently active and have registered with this Dcme."
::= { dcme 420 }

dcmeActiveDcmeLinksEntry OBJECT-TYPE
   SYNTAX     DcmeActiveDcmeLinksEntry
   ACCESS     not-accessible
   STATUS     mandatory
   DESCRIPTION
     "An entry in the dcmeActiveDcmeLinksTable."
   INDEX {
      dcmeIndex,
      dcmeActiveDcmeLinksValue }
::= { dcmeActiveDcmeLinksTable 1 }

DcmeActiveDcmeLinksEntry ::= SEQUENCE {
   dcmeActiveDcmeLinksValue
      RowPointer }

dcmeActiveDcmeLinksValue OBJECT-TYPE
   SYNTAX     RowPointer 
   ACCESS     read-only
   STATUS     mandatory
   DESCRIPTION
     "This variable represents both the value and the index for the
      dcmeActiveDcmeLinksTable."
::= { dcmeActiveDcmeLinksEntry 1 }


-- Dcme/n DcmeProfile		
-- This component defines the ISC interface characteristics of the 
-- Dcme component.

dcmeProfile OBJECT IDENTIFIER ::= { dcme 2 }



dcmeProfileRowStatusTable OBJECT-TYPE
   SYNTAX     SEQUENCE OF DcmeProfileRowStatusEntry
   ACCESS     not-accessible
   STATUS     mandatory
   DESCRIPTION
     "This entry controls the addition and deletion of 
      dcmeProfile components."
::= { dcmeProfile 1 }

dcmeProfileRowStatusEntry OBJECT-TYPE
   SYNTAX     DcmeProfileRowStatusEntry
   ACCESS     not-accessible
   STATUS     mandatory
   DESCRIPTION
     "A single entry in the table represents a single 
      dcmeProfile component."
   INDEX {
      dcmeIndex,
      dcmeProfileIndex }
::= { dcmeProfileRowStatusTable 1 }

DcmeProfileRowStatusEntry ::= SEQUENCE {
   dcmeProfileRowStatus
      RowStatus,
   dcmeProfileComponentName
      DisplayString,
   dcmeProfileStorageType
      StorageType,
   dcmeProfileIndex
      NonReplicated }

dcmeProfileRowStatus OBJECT-TYPE
   SYNTAX     RowStatus 
   ACCESS     read-only
   STATUS     mandatory
   DESCRIPTION
     "This variable is used as the basis for SNMP naming of
      dcmeProfile components.
      These components cannot be added nor deleted."
::= { dcmeProfileRowStatusEntry 1 }

dcmeProfileComponentName OBJECT-TYPE
   SYNTAX     DisplayString 
   ACCESS     read-only
   STATUS     mandatory
   DESCRIPTION
     "This variable provides the component's string name for
      use with the ASCII Console Interface"
::= { dcmeProfileRowStatusEntry 2 }

dcmeProfileStorageType OBJECT-TYPE
   SYNTAX     StorageType 
   ACCESS     read-only
   STATUS     mandatory
   DESCRIPTION
     "This variable represents the storage type value for the
      dcmeProfile tables."
::= { dcmeProfileRowStatusEntry 4 }

dcmeProfileIndex OBJECT-TYPE
   SYNTAX     NonReplicated 
   ACCESS     not-accessible
   STATUS     mandatory
   DESCRIPTION
     "This variable represents the index for the dcmeProfile tables."
::= { dcmeProfileRowStatusEntry 10 }

dcmeProfileLCOpsTable OBJECT-TYPE
   SYNTAX     SEQUENCE OF DcmeProfileLCOpsEntry
   ACCESS     not-accessible
   STATUS     mandatory
   DESCRIPTION
     "This group contains attributes used in setting up Switched Logical 
      Connections (SLC) over the network using the Path Oriented 
      Routing System (PORS) between two peer DcmeLink components."
::= { dcmeProfile 10 }

dcmeProfileLCOpsEntry OBJECT-TYPE
   SYNTAX     DcmeProfileLCOpsEntry
   ACCESS     not-accessible
   STATUS     mandatory
   DESCRIPTION
     "An entry in the dcmeProfileLCOpsTable."
   INDEX {
      dcmeIndex,
      dcmeProfileIndex }
::= { dcmeProfileLCOpsTable 1 }

DcmeProfileLCOpsEntry ::= SEQUENCE {
   dcmeProfileSetupPriority
      Unsigned32,
   dcmeProfileHoldingPriority
      Unsigned32,
   dcmeProfileBumpPreference
      INTEGER,
   dcmeProfileRequiredTrafficType
      INTEGER,
   dcmeProfilePermittedTrunkTypes
      OCTET STRING,
   dcmeProfileRequiredSecurity
      Unsigned32,
   dcmeProfileRequiredCustomerParm
      Unsigned32,
   dcmeProfilePathAttributeToMinimize
      INTEGER,
   dcmeProfileMaximumAcceptableCost
      Unsigned32,
   dcmeProfileMaximumAcceptableDelay
      Unsigned32,
   dcmeProfileEmissionPriority
      Unsigned32,
   dcmeProfileDiscardPriority
      Unsigned32,
   dcmeProfilePathFailureAction
      INTEGER,
   dcmeProfileOptimization
      INTEGER }

dcmeProfileSetupPriority OBJECT-TYPE
   SYNTAX     Unsigned32 (0..4)
   ACCESS     read-write
   STATUS     mandatory
   DESCRIPTION
     "This attribute specifies the priority at which a path is established. 
      Zero is the highest priority and four is the lowest. When PORS 
      establishes a path through the network, it uses the setupPriority 
      attribute to determine its potential for bumping established paths to 
      acquire their bandwidth. The holdingPriority, a complementary 
      attribute of this attribute, indicates the priority a path maintains 
      once it is established. A new path can bump an existing path if the 
      new path's setupPriority is higher (numerically less) than the 
      existing path's holdingPriority."
   DEFVAL     { 2 }
::= { dcmeProfileLCOpsEntry 1 }

dcmeProfileHoldingPriority OBJECT-TYPE
   SYNTAX     Unsigned32 (0..4)
   ACCESS     read-write
   STATUS     mandatory
   DESCRIPTION
     "This attribute specifies the priority that a path holds once it is 
      established. Zero is the highest priority and four is the lowest. A 
      path's holdingPriority determines its likelihood of being bumped by 
      a new path to acquire its bandwidth. The setupPriority, a 
      complementary attribute, indicates the priority of a path at 
      establishment time. A new path can bump an existing path if the 
      new path's setupPriority is higher (numerically less) than the 
      existing path's holdingPriority."
   DEFVAL     { 2 }
::= { dcmeProfileLCOpsEntry 2 }

dcmeProfileBumpPreference OBJECT-TYPE
   SYNTAX     INTEGER  {
                 bumpWhenNecessary(0),
                 bumpToObtainBestRoute(1) }
   ACCESS     read-write
   STATUS     mandatory
   DESCRIPTION
     "This attribute specifies when bumping occurs in the route selection 
      process. A connection with higher (numerically less) setupPriority 
      may bump a connection with lower (numerically higher) 
      setupPriority in order to acquire its bandwidth and be established. If 
      bumpPreference is bumpWhenNecessary, bumping occurs only 
      when it is necessary. That is, a connection will bump another 
      connection only if there is no other way for the connection to be 
      established. If bumpPreference is bumpToObtainBestRoute, 
      bumping occurs in order to use the best available route it may have."
   DEFVAL     { bumpWhenNecessary }
::= { dcmeProfileLCOpsEntry 3 }

dcmeProfileRequiredTrafficType OBJECT-TYPE
   SYNTAX     INTEGER  {
                 voice(0),
                 data(1),
                 video(2),
                 trafficType1(3),
                 trafficType2(4),
                 trafficType3(5),
                 trafficType4(6),
                 trafficType5(7) }
   ACCESS     read-write
   STATUS     mandatory
   DESCRIPTION
     "This attribute specifies the type of traffic transmitted over the path. 
      There are eight possible traffic types, and the path can transmit only 
      one of them. The originating end of the connection determines the 
      type. The voice, data and video traffic types are defined, and five 
      other arbitrary traffic types can be defined by the network 
      administration. This attribute is used in the route selection process 
      to restrict the route to trunks that support this traffic type. The 
      supportedTrafficType trunk attribute lists all the types of traffic 
      allowed on the trunk. For example, if requiredTrafficType is 
      specified as trafficType1, then only trunks that include trafficType1 
      in supportedTrafficType will be candidates for this connection."
   DEFVAL     { voice }
::= { dcmeProfileLCOpsEntry 4 }

dcmeProfilePermittedTrunkTypes OBJECT-TYPE
   SYNTAX     OCTET STRING (SIZE (1))
   ACCESS     read-write
   STATUS     mandatory
   DESCRIPTION
     "This attribute specifies up to eight types of trunks that can be used 
      on the route. The terrestrial and satellite trunk types are defined, 
      leaving six remaining arbitrary types that can be defined by the 
      network administration. The trunk's type is indicated in the 
      trunkType attribute of the Trunk component. When selecting a 
      route, PORS chooses only trunks whose trunkTypes are in the 
      permittedTrunkTypes for the path.

      Description of bits:
      terrestrial(0)
      satellite(1)
      trunkType1(2)
      trunkType2(3)
      trunkType3(4)
      trunkType4(5)
      trunkType5(6)
      trunkType6(7)"
   DEFVAL     { 'f8'H }
::= { dcmeProfileLCOpsEntry 5 }

dcmeProfileRequiredSecurity OBJECT-TYPE
   SYNTAX     Unsigned32 (0..7)
   ACCESS     read-write
   STATUS     mandatory
   DESCRIPTION
     "This attribute specifies the required minimum level of security of 
      the trunks on the route. Zero represents the most secure and seven 
      represents the least secure. The trunk's security is indicated by the 
      trunkSecurity attribute of the Trunk component, and has values 
      identical in range and meaning to the requiredSecurity attribute. 
      PORS ensures that any route selected does not contain a trunk 
      whose trunkSecurity attribute is numerically greater than the 
      requiredSecurity."
   DEFVAL     { 4 }
::= { dcmeProfileLCOpsEntry 6 }

dcmeProfileRequiredCustomerParm OBJECT-TYPE
   SYNTAX     Unsigned32 (0..7)
   ACCESS     read-write
   STATUS     mandatory
   DESCRIPTION
     "This attribute specifies the allowed customer defined parameter of 
      the trunks on the route. The value of requiredCustomerParm ranges 
      from 0 to 7. The meaning of each value is specific to a particular 
      network, thus allowing them to customize the use of their trunks. A 
      complementary trunk attribute, customerParameter, also has a value 
      from zero to seven. The route selection process does not consider 
      trunks whose customerParameter is greater than the 
      requiredCustomerParameter of the path."
   DEFVAL     { 4 }
::= { dcmeProfileLCOpsEntry 7 }

dcmeProfilePathAttributeToMinimize OBJECT-TYPE
   SYNTAX     INTEGER  {
                 cost(0),
                 delay(1) }
   ACCESS     read-write
   STATUS     mandatory
   DESCRIPTION
     "This attribute specifies whether a route is selected on the basis of 
      minimizing the cost or the delay. Each trunk has a cost and a delay 
      metric associated with it. The cost of a selected route is the sum of 
      the trunk cost metrics for all trunks included in the route. The delay 
      of a selected route is the sum of the trunk delay metrics for all 
      trunks included in the route."
   DEFVAL     { cost }
::= { dcmeProfileLCOpsEntry 8 }

dcmeProfileMaximumAcceptableCost OBJECT-TYPE
   SYNTAX     Unsigned32 (0..65535)
   ACCESS     read-write
   STATUS     mandatory
   DESCRIPTION
     "This attribute specifies an upper bound on the cost metric of a route, 
      which is the sum of the cost metrics of all trunks on the route. The 
      cost metric is the trunkCost attribute of the Trunk component. If for 
      any trunk the trunkCost is larger than the maximumAcceptableCost, 
      then that trunk is not considered during the route selection. While a 
      shortest route is being selected, the route cost is being compared 
      with the maximumAcceptableCost attribute, and this is done for any 
      minimization criterion. No route is selected if the cost metric of the 
      shortest route is larger than the maximumAcceptableCost."
   DEFVAL     { 1280 }
::= { dcmeProfileLCOpsEntry 9 }

dcmeProfileMaximumAcceptableDelay OBJECT-TYPE
   SYNTAX     Unsigned32 (0..100000)
   ACCESS     read-write
   STATUS     mandatory
   DESCRIPTION
     "This attribute specifies an upper bound on the delay of a route, 
      which is the sum of the delays of all trunks on the route. It should 
      be provisioned with a reasonable maximum acceptable delay for the 
      end to end one way delay of a 512-byte packet. During its staging, a 
      trunk measures a measuredRoundTripDelay. This delay is divided 
      by two and truncated to an integer number of milliseconds to 
      provide a one way delay which is used to populate the delay in this 
      trunk object in the topological database. The value includes 
      emission, propagation, and queuing delays. A 512-byte packet is 
      used to perform the measurement. 
      If for any trunk the half of the trunk's measuredRoundTripDelay is 
      larger than the maximumAcceptableDelay, then that trunk is not 
      considered during the route selection.
      While a shortest route is being selected, the route delay is being 
      compared with the maximumAcceptableDelay attribute, and this is 
      done for any minimization criterion. No route is selected if the 
      delay metric of the shortest route is larger than the 
      maximumAcceptableDelay."
   DEFVAL     { 100000 }
::= { dcmeProfileLCOpsEntry 10 }

dcmeProfileEmissionPriority OBJECT-TYPE
   SYNTAX     Unsigned32 (0..2)
   ACCESS     read-write
   STATUS     mandatory
   DESCRIPTION
     "This attribute specifies the urgency with which packets on the path 
      are emitted by the trunks on the route. An emissionPriority of 0 
      indicates the highest emission priority, while 2 indicates the lowest 
      emission priority. Packets with a higher emissionPriority (or 
      numerically less) are serviced and sent out before the packets with a 
      lower emissionPriority (or numerically higher)."
   DEFVAL     { 0 }
::= { dcmeProfileLCOpsEntry 11 }

dcmeProfileDiscardPriority OBJECT-TYPE
   SYNTAX     Unsigned32 (1..3)
   ACCESS     read-write
   STATUS     mandatory
   DESCRIPTION
     "This attribute specifies the importance of the packets on the path. A 
      discardPriority of 1 is used for paths carrying the most important 
      traffic, and three is used for paths carrying the least important 
      traffic. Packets with lower discardPriority(numerically lower) are 
      discarded after packets with a higher discardPriority(numerically 
      higher)."
   DEFVAL     { 1 }
::= { dcmeProfileLCOpsEntry 12 }

dcmeProfilePathFailureAction OBJECT-TYPE
   SYNTAX     INTEGER  {
                 disconnectConnection(0),
                 reRoutePath(1) }
   ACCESS     read-write
   STATUS     mandatory
   DESCRIPTION
     "This attribute specifies whether the application can tolerate 
      momentary interruption of a path while a new path is selected. If 
      pathFailureAction is disconnectConnection, the application is 
      informed as soon as possible about a failure by disconnection. If 
      pathFailureAction is reRoutePath, the path may attempt an 
      immediate reroute, provided the failure is a recoverable failure. If 
      rerouting fails, the application is informed of the failure. 
      If pathFailureAction is reRoutePath, the LCo may wait up to 30 
      seconds before informing the service of complete disconnection in 
      order to allow both ends to attempt to reconnect. Note that if PLC 
      components are different at both ends only the calling end is 
      allowed to reconnect.
      All pathTypes respect this attribute. Also on a manualPath with 
      both ends provisioned with independent paths (at least with respect 
      to the failure) this option has the desired effect that the path is 
      rerouted without complete disconnection at both ends."
   DEFVAL     { reRoutePath }
::= { dcmeProfileLCOpsEntry 13 }

dcmeProfileOptimization OBJECT-TYPE
   SYNTAX     INTEGER  {
                 disabled(0),
                 enabled(1) }
   ACCESS     read-write
   STATUS     mandatory
   DESCRIPTION
     "This attribute specifies whether this connection should attempt to 
      optimize its path when requested by the Rtg Pors component. Every 
      path is optimal when it is established, but as network traffic patterns 
      and configurations change this path may no longer be optimal. The 
      PORS connection manager on a module requests circuits to 
      optimize at the optimizationInterval."
   DEFVAL     { enabled }
::= { dcmeProfileLCOpsEntry 14 }

dcmeProfileFrOpsTable OBJECT-TYPE
   SYNTAX     SEQUENCE OF DcmeProfileFrOpsEntry
   ACCESS     not-accessible
   STATUS     mandatory
   DESCRIPTION
     "This group contains attributes which define how audio data will be 
      carried across the Passport network."
::= { dcmeProfile 11 }

dcmeProfileFrOpsEntry OBJECT-TYPE
   SYNTAX     DcmeProfileFrOpsEntry
   ACCESS     not-accessible
   STATUS     mandatory
   DESCRIPTION
     "An entry in the dcmeProfileFrOpsTable."
   INDEX {
      dcmeIndex,
      dcmeProfileIndex }
::= { dcmeProfileFrOpsTable 1 }

DcmeProfileFrOpsEntry ::= SEQUENCE {
   dcmeProfileVoiceEncoding
      INTEGER,
   dcmeProfileMaxVoiceBitRate
      INTEGER,
   dcmeProfileMinVoiceBitRate
      INTEGER,
   dcmeProfileVoiceTrafficOptimization
      INTEGER,
   dcmeProfileSilenceSuppression
      INTEGER,
   dcmeProfileSilenceSuppressionFactor
      Unsigned32,
   dcmeProfileEchoCancellation
      INTEGER,
   dcmeProfileModemFaxEncoding
      INTEGER,
   dcmeProfileMaxModemFaxG711G726Rate
      INTEGER,
   dcmeProfileMinModemFaxG711G726Rate
      INTEGER,
   dcmeProfileFaxIdleSuppressionG711G726
      INTEGER,
   dcmeProfileInsertedOutputDelay
      INTEGER,
   dcmeProfileIngressAudioGain
      INTEGER,
   dcmeProfileEgressAudioGain
      INTEGER,
   dcmeProfileSpeechHangoverTime
      Unsigned32,
   dcmeProfileComfortNoiseCap
      INTEGER,
   dcmeProfileModemFaxSpeechDiscrim
      INTEGER,
   dcmeProfileV17EncodedAsG711G726
      INTEGER,
   dcmeProfileDtmfRegeneration
      INTEGER,
   dcmeProfileMaxFaxRelayRate
      FixedPoint1 }

dcmeProfileVoiceEncoding OBJECT-TYPE
   SYNTAX     INTEGER  {
                 g711G726(0),
                 g728at16(1),
                 g729at8(2) }
   ACCESS     read-write
   STATUS     mandatory
   DESCRIPTION
     "This attribute specifies the encoding of voice traffic.
      
      A voiceEncoding setting of g711G726 specifies that either pulse 
      code modulation (PCM) defined by ITU-T G.711 or adaptive 
      differential pulse code modulation (ADPCM) defined by ITU-T 
      G.726 is used to encode voice traffic. The actual encoding 
      performed depends on congestion in the network and the settings of 
      minVoiceG711G726Rate and maxVoiceG711G726Rate. If 
      voiceEncoding is g711G726, the bit rate of voice traffic can change 
      during a call due to congestion in the network. In this case, the 
      minimum and maximum rates that can occur during a call are 
      specified by minVoiceG711G726Rate and maxVoiceG711G726Rate 
      respectively. If voiceEncoding is g711G726, 
      minVoiceG711G726Rate is 64 and maxVoiceG711G726Rate is 64, 
      G.711 (PCM) encoding is always performed on voice traffic on this 
      channel and all voice traffic is carried uncompressed at 64 kbit/s.
      
      A voiceEncoding setting of g728at16 specifies that the Low Delay 
      Coded Excited Linear Predictive Coder (LD-CELP) algorithm 
      defined by ITU-T G.728 is always performed on voice traffic. If 
      voiceEncoding is g728at16, the bit rate of all voice traffic is fixed at 
      16 kbit/s. The minVoiceG711G726Rate and 
      maxVoiceG711G726Rate attributes do not apply if voiceEncoding is 
      g728at16.
      
      A voiceEncoding setting of g729at8 indicates that the Conjugated 
      Structure Algebraic Code Excited Linear Predictive Coder (CS-
      ACELP) algorithm defined by ITU-T G.729 is always performed on 
      voice traffic. If voiceEncoding is g729at8, the bit rate of all voice 
      traffic is fixed at 8 kbit/s. The minVoiceG711G726Rate and 
      maxVoiceG711G726Rate attributes do not apply if voiceEncoding is 
      g729at8."
   DEFVAL     { g728at16 }
::= { dcmeProfileFrOpsEntry 1 }

dcmeProfileMaxVoiceBitRate OBJECT-TYPE
   SYNTAX     INTEGER  {
                 n64(0),
                 n32(1),
                 n24(2) }
   ACCESS     read-write
   STATUS     mandatory
   DESCRIPTION
     "This attribute specifies the maximum possible bit rate (minimum 
      possible compression rate) during a voice call on this channel when 
      voiceEncoding is g711G726. It applies only to voice traffic, not 
      modem or fax traffic. It also applies only if voiceEncoding is 
      g711G726.
      
      If voiceEncoding is g711G726, the bit rate of voice traffic can 
      change during a call due to congestion in the network. In this case, 
      the minimum and maximum rates that can occur during a call are 
      specified by minVoiceG711G726Rate and maxVoiceG711G726Rate 
      respectively. If voiceEncoding is g711G726, 
      minVoiceG711G726Rate is 64 and maxVoiceG711G726Rate is 64, 
      the G.711 (PCM) algorithm is always performed on voice traffic on 
      this channel and all voice traffic is carried uncompressed at 64 
      kbit/s."
   DEFVAL     { n64 }
::= { dcmeProfileFrOpsEntry 2 }

dcmeProfileMinVoiceBitRate OBJECT-TYPE
   SYNTAX     INTEGER  {
                 n64(0),
                 n32(1),
                 n24(2) }
   ACCESS     read-write
   STATUS     mandatory
   DESCRIPTION
     "This attribute specifies the minimum possible bit rate (maximum 
      possible compression rate) during a voice call on this channel when 
      voiceEncoding is g711G726. It applies only to voice traffic, not 
      modem or fax traffic. It also applies only if voiceEncoding is 
      g711G726.
      
      If voiceEncoding is g711G726, the bit rate of voice traffic can 
      change during a call due to congestion in the network. In this case, 
      the minimum and maximum rates that can occur during a call are 
      specified by minVoiceG711G726Rate and maxVoiceG711G726Rate 
      respectively. If voiceEncoding is g711G726, 
      minVoiceG711G726Rate is 64 and maxVoiceG711G726Rate is 64, 
      the G.711 (PCM) algorithm is always performed on voice traffic on 
      this channel and all voice traffic is carried uncompressed at 64 
      kbit/s."
   DEFVAL     { n64 }
::= { dcmeProfileFrOpsEntry 3 }

dcmeProfileVoiceTrafficOptimization OBJECT-TYPE
   SYNTAX     INTEGER  {
                 bandwidth(0),
                 delay(1) }
   ACCESS     read-write
   STATUS     mandatory
   DESCRIPTION
     "This attribute specifies how to optimize voice traffic. If 
      voiceTrafficOptimization is bandwidth, voice traffic is optimized to 
      preserve bandwidth. If voiceTrafficOptimization is delay, voice 
      traffic is optimized to minimize delay."
   DEFVAL     { bandwidth }
::= { dcmeProfileFrOpsEntry 4 }

dcmeProfileSilenceSuppression OBJECT-TYPE
   SYNTAX     INTEGER  {
                 off(0),
                 on(1),
                 congested(2),
                 slow(3),
                 slowAndCongested(4) }
   ACCESS     read-write
   STATUS     mandatory
   DESCRIPTION
     "This attribute specifies when silence suppression is performed. It 
      applies to both voice and modem calls.
      If silenceSuppression is off, silence suppression is never performed.
      If silenceSuppression is on, silence suppression is always 
      performed. 
      If silenceSuppression is congested, silence suppression is 
      performed only when the network is congested.
      If silenceSuppression is slow, silence suppression begins after 10 to 
      20 seconds without any detected speech or modem traffic.
      If silenceSuppression is slowAndCongested, both the slow and 
      congested options are applied."
   DEFVAL     { on }
::= { dcmeProfileFrOpsEntry 5 }

dcmeProfileSilenceSuppressionFactor OBJECT-TYPE
   SYNTAX     Unsigned32 (0..60)
   ACCESS     read-write
   STATUS     mandatory
   DESCRIPTION
     "This attribute specifies the expected savings (percent reduction) in 
      required bandwidth if silence suppression is used. If silence 
      suppression is used, the bandwidth required for the connection will 
      be lower than if silence suppression is not used. However, the 
      routing system will not be aware of the unused bandwidth unless 
      that bandwidth is specified by this attribute. 
      If the value specified for the expected savings is too low, then some 
      bandwidth made available by the use of silence suppression will be 
      wasted. If the value specified for the expected savings is too high, 
      then some connections may fail to set up because the routing system 
      will over-calculate the amount of bandwidth available.
      The effectiveness of silence suppression can be influenced by 
      language related speech patterns."
   DEFVAL     { 40 }
::= { dcmeProfileFrOpsEntry 6 }

dcmeProfileEchoCancellation OBJECT-TYPE
   SYNTAX     INTEGER  {
                 off(0),
                 on(1) }
   ACCESS     read-write
   STATUS     mandatory
   DESCRIPTION
     "This attribute specifies whether echo cancellation is performed on 
      calls using this profile as specified by ITU-T G.165. It applies 
      mainly to voice traffic. Echo cancellation is usually (but not always) 
      disabled during modem and fax calls. If echoCancellation is on, the 
      traffic that is echo cancelled is determined by ITU-T G.165."
   DEFVAL     { off }
::= { dcmeProfileFrOpsEntry 7 }

dcmeProfileModemFaxEncoding OBJECT-TYPE
   SYNTAX     INTEGER  {
                 g711G726(0),
                 faxRelayOnly(1),
                 faxRelayG711G726(2),
                 useVoiceEncoding(3) }
   ACCESS     read-write
   STATUS     mandatory
   DESCRIPTION
     "This attribute specifies how modem and fax traffic is encoded. 
      Modem and fax traffic are identified by an inband 2100 Hz tone. 
      Prior to the detection of a 2100 Hz tone, all traffic is handled 
      according to voiceEncoding.
      
      If modemFaxEncoding is useVoiceEncoding, 2100 Hz tones are not 
      detected on the channel. In this case, the channel does not 
      differentiate between modem and fax traffic and voice traffic. All 
      traffic is handled according to voiceEncoding. If voiceEncoding is 
      g728at16 or g729at8, modem and fax calls will not work.
      
      If a 2100 Hz tone is detected and modemFaxEncoding is g711G726, 
      all subsequent traffic during a call is encoded using pulse code 
      modulation (PCM) defined by ITU-T G.711 or adaptive differential 
      pulse code modulation (ADPCM) defined by ITU-T G.726. When 
      the 2100 Hz tone is detected, traffic is initially encoded at the rate 
      specified by maxModemFaxG711G726Rate. For the duration of the 
      call, the bit rate can change due to network congestion. In this case, 
      the minimum and maximum rates that can occur during the call are 
      specified by minModemFaxG711G726Rate and 
      maxModemFaxG711G726Rate respectively.
      
      If a 2100 Hz tone is detected and modemFaxEncoding is 
      faxRelayG711G726, encoding switches to G.711 or G.726 at the 
      rate specified in maxModemFaxG711G726Rate, exactly as it does if 
      modemFaxEncoding is g711G726. Until a fax preamble is detected, 
      the rate may fluctuate between maxModemFaxG711G726Rate and 
      minModemFaxG711G726Rate due to network congestion, exactly 
      as it does if modemFaxEncoding is g711G726. If a fax preamble is 
      detected, all subsequent traffic during a call is demodulated and sent 
      through the network as cells at the base rate of the sending machine. 
      Supported demodulation methods are V.29 (up to 9.6 kbit/s) and 
      V.27 (up to 4.8 kbit/s). The modulation and demodulation of fax 
      traffic is called 'fax relay'.
      
      If a 2100 Hz tone is detected and modemFaxEncoding is 
      faxRelayOnly, this channel does not wait for a fax preamble to 
      switch to 'fax relay'. Instead, 'fax relay' is entered immediately. If 
      modemFaxEncoding is faxRelayOnly, modem calls do not work on 
      this Dcme. Therefore, this setting is only appropriate if modem calls 
      are not made on the channel.
      
      The faxRelay feature is required to set modemFaxEncoding to 
      faxRelayG711G726 or faxRelayOnly.
      
      modemFaxEncoding must have the same value at both ends of a 
      Dcme. If modemFaxEncoding is not provisioned with the same 
      values at both ends of a Dcme, the Dcme will not be able to carry 
      the modem and fax traffic successfully."
   DEFVAL     { faxRelayOnly }
::= { dcmeProfileFrOpsEntry 9 }

dcmeProfileMaxModemFaxG711G726Rate OBJECT-TYPE
   SYNTAX     INTEGER  {
                 n64(0),
                 n32(1) }
   ACCESS     read-write
   STATUS     mandatory
   DESCRIPTION
     "This attribute specifies the maximum possible bit rate (minimum 
      possible compression rate) during a modem call on this channel. It 
      also specifies the maximum possible bit rate (minimum possible 
      compression rate) during a fax call on this channel, but only if 
      faxEncoding is g711G726. maxModemFaxG711G726Rate always 
      applies to modem traffic, and never applies to voice traffic. If 
      faxEncoding is g711G726, maxModemFaxG711G726Rate also 
      applies to fax traffic. If faxEncoding is faxRelay, 
      maxModemFaxG711G726Rate does not apply to fax traffic.
      Rates can change during a call due to congestion in the network."
   DEFVAL     { n64 }
::= { dcmeProfileFrOpsEntry 10 }

dcmeProfileMinModemFaxG711G726Rate OBJECT-TYPE
   SYNTAX     INTEGER  {
                 n64(0),
                 n32(1) }
   ACCESS     read-write
   STATUS     mandatory
   DESCRIPTION
     "This attribute specifies the minimum possible bit rate (maximum 
      possible compression rate) during a modem call on this channel. It 
      also specifies the minimum possible bit rate (maximum possible 
      compression rate) during a fax call on this channel, but only if 
      faxEncoding is g711G726. minModemFaxG711G726Rate always 
      applies to modem traffic, and never applies to voice traffic. If 
      faxEncoding is g711G726, minModemFaxG711G726Rate also 
      applies to fax traffic. If faxEncoding is faxRelay, 
      minModemFaxG711G726Rate does not apply to fax traffic. 
      Rates can change during a call due to congestion in the network."
   DEFVAL     { n64 }
::= { dcmeProfileFrOpsEntry 11 }

dcmeProfileFaxIdleSuppressionG711G726 OBJECT-TYPE
   SYNTAX     INTEGER  {
                 off(0),
                 on(1) }
   ACCESS     read-write
   STATUS     mandatory
   DESCRIPTION
     "This attribute specifies whether fax idle suppression is performed on 
      fax traffic on calls using this profile. It only applies to fax traffic, not 
      voice or modem traffic. It also only applies if fax traffic is carried 
      using G.711 or G.726."
   DEFVAL     { off }
::= { dcmeProfileFrOpsEntry 12 }

dcmeProfileInsertedOutputDelay OBJECT-TYPE
   SYNTAX     INTEGER  {
                 n5(5),
                 n15(15),
                 n22(22),
                 n30(30),
                 n35(35),
                 n40(40),
                 n45(45),
                 n50(50),
                 n75(75),
                 n100(100),
                 n125(125),
                 n150(150) }
   ACCESS     read-write
   STATUS     mandatory
   DESCRIPTION
     "This attribute specifies the amount of added output delay used to 
      compensate for cross network delay variations. It applies to voice, 
      modem and fax traffic. It is required to add output delay so that the 
      statistical variation in the transit time of cells crossing the network 
      does not cause gaps in speech. Backbone networks where high 
      priority traffic consumes a high percentage of trunk bandwidth will 
      require a higher insertedOutputDelay to compensate for the greater 
      cell delay variation (CDV)."
   DEFVAL     { n22 }
::= { dcmeProfileFrOpsEntry 13 }

dcmeProfileIngressAudioGain OBJECT-TYPE
   SYNTAX     INTEGER (-12..12)
   ACCESS     read-write
   STATUS     mandatory
   DESCRIPTION
     "This attribute specifies the gain in dB that is applied to data coming 
      from outside the network before it is transferred across the network. 
      It applies to voice, modem and fax traffic. For example, ingress gain 
      is applied to audio data coming from a PBX. If ingressAudioGain is 
      negative, a loss is applied.
      
      ingressAudioGain and egressAudioGain are used in loss planning, 
      which is the configuration of the devices in a network to ensure that 
      the signal level from any point in the network to any other point is 
      correct."
   DEFVAL     { 0 }
::= { dcmeProfileFrOpsEntry 14 }

dcmeProfileEgressAudioGain OBJECT-TYPE
   SYNTAX     INTEGER (-12..12)
   ACCESS     read-write
   STATUS     mandatory
   DESCRIPTION
     "This attribute specifies the gain in dB that is applied to data leaving 
      the network on this route. It applies to voice, modem and fax traffic. 
      For example, egress gain is applied to audio data going to a PBX. If 
      egressAudioGain is negative, a loss is applied.
      
      ingressAudioGain and egressAudioGain are used in loss planning, 
      which is the configuration of the devices in the network to ensure 
      that the signal level from any point in the network to any other point 
      is correct."
   DEFVAL     { 0 }
::= { dcmeProfileFrOpsEntry 15 }

dcmeProfileSpeechHangoverTime OBJECT-TYPE
   SYNTAX     Unsigned32 (10..500)
   ACCESS     read-write
   STATUS     mandatory
   DESCRIPTION
     "This attribute specifies the time after the end of speech before 
      silence suppression starts. It applies only to voice traffic.
      
      Higher values of speechHangoverTime reduce undesirable clipping 
      but increase bandwidth usage."
   DEFVAL     { 150 }
::= { dcmeProfileFrOpsEntry 16 }

dcmeProfileComfortNoiseCap OBJECT-TYPE
   SYNTAX     INTEGER (-78 | -65 | -60 | -54 | -52 | -50 | -48 | -46 | -44 | -42 | -40)
   ACCESS     read-write
   STATUS     mandatory
   DESCRIPTION
     "This attribute specifies the maximum level at which comfort noise is 
      generated. The comfort noise is limited by comfortNoiseCap before 
      egressAudioGain is applied. The default value of -40 dBm0 equates 
      to the maximum level of comfort noise available and effectively 
      disables the comfortNoiseCap."
   DEFVAL     { -40 }
::= { dcmeProfileFrOpsEntry 17 }

dcmeProfileModemFaxSpeechDiscrim OBJECT-TYPE
   SYNTAX     INTEGER  {
                 off(0),
                 on(1) }
   ACCESS     read-write
   STATUS     mandatory
   DESCRIPTION
     "This attribute specifies whether this Dcme differentiates between 
      modemFax traffic and speech. If modemFaxSpeechDiscrim is on 
      and a false 2100 Hz tone is detected, any Vs under this Dcme reverts 
      to speech mode when speech is detected."
   DEFVAL     { on }
::= { dcmeProfileFrOpsEntry 18 }

dcmeProfileV17EncodedAsG711G726 OBJECT-TYPE
   SYNTAX     INTEGER  {
                 no(0),
                 yes(1) }
   ACCESS     read-write
   STATUS     mandatory
   DESCRIPTION
     "This attribute specifies how services using this Profile negotiate 
      with V.17 fax machines. This attribute is not used unless the 
      modemFaxEncoding, defined in this Profile, is faxRelayG711G726 
      
      If v17EncodedAsG711G726 is no, V.17 fax machines are instructed 
      to use V.29 and V.29 fax traffic sent by fax machines is demodulated 
      and encoded using fax relay.
      
      If v17EncodedAsG711G726 is yes, V.17 fax machines are permitted 
      to use V.17 and V.17 fax traffic sent by fax machines is encoded 
      using G.711 or G.726. The actual encoding performed depends on 
      the minModemFaxG711G726Rate and 
      maxModemFaxG711G726Rate, available in this Profile."
   DEFVAL     { no }
::= { dcmeProfileFrOpsEntry 19 }

dcmeProfileDtmfRegeneration OBJECT-TYPE
   SYNTAX     INTEGER  {
                 off(0),
                 on(1) }
   ACCESS     read-write
   STATUS     mandatory
   DESCRIPTION
     "This attribute specifies the DTMF regeneration parameter used 
      during negotiation with the remote end across the subnet. 
      
      If dtmfRegeneration is on, it is desired that DTMF tones received 
      from the link are first converted to digits before being sent to the 
      subnet. When a digit is received from the subnet, its respective 
      DTMF tone is desired to be generated before being sent to the link.
      
      If dtmfRegeneration is off, it is desired that DTMF tones are 
      transported transparently as audio."
   DEFVAL     { off }
::= { dcmeProfileFrOpsEntry 20 }

dcmeProfileMaxFaxRelayRate OBJECT-TYPE
   SYNTAX     FixedPoint1 (24 | 48 | 72 | 96 | 120 | 144)
   ACCESS     read-write
   STATUS     mandatory
   DESCRIPTION
     "This attribute specifies the maximum desired fax relay rate. This 
      attribute only applies if modemFaxEncoding is faxRelayOnly or 
      faxRelayG711G726."
   DEFVAL     { 144 }
::= { dcmeProfileFrOpsEntry 21 }


-- DcmeLink/n		
-- This component defines the characteristics of a connection to an 
-- International Switching Centre (ISC). A DcmeLink is a collection of 
-- 64 kbit/s channels on the same physical E1 interface. There is one 
-- DcmeLink per physical link. 

dcl OBJECT IDENTIFIER ::= { components 130 }



dclRowStatusTable OBJECT-TYPE
   SYNTAX     SEQUENCE OF DclRowStatusEntry
   ACCESS     not-accessible
   STATUS     mandatory
   DESCRIPTION
     "This entry controls the addition and deletion of 
      dcl components."
::= { dcl 1 }

dclRowStatusEntry OBJECT-TYPE
   SYNTAX     DclRowStatusEntry
   ACCESS     not-accessible
   STATUS     mandatory
   DESCRIPTION
     "A single entry in the table represents a single 
      dcl component."
   INDEX {
      dclIndex }
::= { dclRowStatusTable 1 }

DclRowStatusEntry ::= SEQUENCE {
   dclRowStatus
      RowStatus,
   dclComponentName
      DisplayString,
   dclStorageType
      StorageType,
   dclIndex
      Integer32 }

dclRowStatus OBJECT-TYPE
   SYNTAX     RowStatus 
   ACCESS     read-write
   STATUS     mandatory
   DESCRIPTION
     "This variable is used as the basis for SNMP naming of
      dcl components.
      These components can be added and deleted."
::= { dclRowStatusEntry 1 }

dclComponentName OBJECT-TYPE
   SYNTAX     DisplayString 
   ACCESS     read-only
   STATUS     mandatory
   DESCRIPTION
     "This variable provides the component's string name for
      use with the ASCII Console Interface"
::= { dclRowStatusEntry 2 }

dclStorageType OBJECT-TYPE
   SYNTAX     StorageType 
   ACCESS     read-only
   STATUS     mandatory
   DESCRIPTION
     "This variable represents the storage type value for the
      dcl tables."
::= { dclRowStatusEntry 4 }

dclIndex OBJECT-TYPE
   SYNTAX     Integer32 (1..14)
   ACCESS     not-accessible
   STATUS     mandatory
   DESCRIPTION
     "This variable represents the index for the dcl tables."
::= { dclRowStatusEntry 10 }

dclProvTable OBJECT-TYPE
   SYNTAX     SEQUENCE OF DclProvEntry
   ACCESS     not-accessible
   STATUS     mandatory
   DESCRIPTION
     "This group contains the provisionable attributes of a DcmeLink."
::= { dcl 10 }

dclProvEntry OBJECT-TYPE
   SYNTAX     DclProvEntry
   ACCESS     not-accessible
   STATUS     mandatory
   DESCRIPTION
     "An entry in the dclProvTable."
   INDEX {
      dclIndex }
::= { dclProvTable 1 }

DclProvEntry ::= SEQUENCE {
   dclCommentText
      AsciiString,
   dclRemoteNpi
      INTEGER,
   dclRemoteDna
      DigitString,
   dclDcme
      Link,
   dclIdlePattern
      Hex,
   dclAlternateIdlePattern
      Hex }

dclCommentText OBJECT-TYPE
   SYNTAX     AsciiString (SIZE (0..40))
   ACCESS     read-write
   STATUS     mandatory
   DESCRIPTION
     "Use of this attribute is at the discretion of the system administrator. 
      Typically, it specifies the name of the customer that is using this 
      DcmeLink."
   DEFVAL     { ''H }  -- ""
::= { dclProvEntry 1 }

dclRemoteNpi OBJECT-TYPE
   SYNTAX     INTEGER  {
                 x121(0),
                 e164(1) }
   ACCESS     read-write
   STATUS     mandatory
   DESCRIPTION
     "This attribute specifies the Numbering Plan Indicator used for the 
      remoteDna attribute of this DcmeLink."
   DEFVAL     { e164 }
::= { dclProvEntry 2 }

dclRemoteDna OBJECT-TYPE
   SYNTAX     DigitString (SIZE (1..15))
   ACCESS     read-write
   STATUS     mandatory
   DESCRIPTION
     "This attribute specifies the Data Network Address (DNA) of the 
      remote DcmeLink. This is the DNA of the peer DcmeLink to which 
      the DcmeLink component establishes its Logical Connection (LC)."
::= { dclProvEntry 3 }

dclDcme OBJECT-TYPE
   SYNTAX     Link 
   ACCESS     read-write
   STATUS     mandatory
   DESCRIPTION
     "This attribute specifies the Dcme component that this DcmeLink 
      belongs to."
::= { dclProvEntry 4 }

dclIdlePattern OBJECT-TYPE
   SYNTAX     Hex (0..255)
   ACCESS     read-write
   STATUS     mandatory
   DESCRIPTION
     "This attribute specifies an idlePattern in the channel received from 
      the E1 interface, which is required to determine if the channel is 
      active or not. 
      When the end of the idlePattern is detected it indicates the start of a 
      new speech call.
      When this idlePattern is detected it indicates the end of a speech 
      call.
      When changing this attribute make sure that the 
      alternateIdlePattern attibute is set correctly."
   DEFVAL     { 213 }
::= { dclProvEntry 5 }

dclAlternateIdlePattern OBJECT-TYPE
   SYNTAX     Hex (0..255)
   ACCESS     read-write
   STATUS     mandatory
   DESCRIPTION
     "This attribute specifies an alternateIdlePattern in the channel 
      received from the E1 interface, after the end of a 64kbit/s call.
      The value of this attribute should be different than the value of the 
      idlePattern attribute only if the ISC is programmed for Even/Odd 
      Bit Inversion (EBI/OBI). This is only the case when the ISC is 
      performing A to Mu or Mu to A Law conversion.
      When the end of the alternateIdlePattern is detected it indicates the 
      start of a new speech call."
   DEFVAL     { 213 }
::= { dclProvEntry 6 }

dclStateTable OBJECT-TYPE
   SYNTAX     SEQUENCE OF DclStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { dcl 11 }

dclStateEntry OBJECT-TYPE
   SYNTAX     DclStateEntry
   ACCESS     not-accessible
   STATUS     mandatory
   DESCRIPTION
     "An entry in the dclStateTable."
   INDEX {
      dclIndex }
::= { dclStateTable 1 }

DclStateEntry ::= SEQUENCE {
   dclAdminState
      INTEGER,
   dclOperationalState
      INTEGER,
   dclUsageState
      INTEGER }

dclAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { dclStateEntry 1 }

dclOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { dclStateEntry 2 }

dclUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { dclStateEntry 3 }

dclOperTable OBJECT-TYPE
   SYNTAX     SEQUENCE OF DclOperEntry
   ACCESS     not-accessible
   STATUS     mandatory
   DESCRIPTION
     "This group provides the operational attributes for the DcmeLink 
      component."
::= { dcl 12 }

dclOperEntry OBJECT-TYPE
   SYNTAX     DclOperEntry
   ACCESS     not-accessible
   STATUS     mandatory
   DESCRIPTION
     "An entry in the dclOperTable."
   INDEX {
      dclIndex }
::= { dclOperTable 1 }

DclOperEntry ::= SEQUENCE {
   dclActiveSpeechCalls
      Gauge32,
   dclActive3kHzCalls
      Gauge32,
   dclActive64kCalls
      Gauge32,
   dclReceivedTrmSignal
      INTEGER,
   dclTransmittedTrmSignal
      INTEGER }

dclActiveSpeechCalls OBJECT-TYPE
   SYNTAX     Gauge32 (0..30)
   ACCESS     read-only
   STATUS     mandatory
   DESCRIPTION
     "This attribute indicates the number of speech calls that are currently 
      in progress on this DcmeLink."
   DEFVAL     { 0 }
::= { dclOperEntry 1 }

dclActive3kHzCalls OBJECT-TYPE
   SYNTAX     Gauge32 (0..30)
   ACCESS     read-only
   STATUS     mandatory
   DESCRIPTION
     "This attribute indicates the number of audio 3.1 kHz calls that are 
      currently in progress on this DcmeLink."
   DEFVAL     { 0 }
::= { dclOperEntry 2 }

dclActive64kCalls OBJECT-TYPE
   SYNTAX     Gauge32 (0..30)
   ACCESS     read-only
   STATUS     mandatory
   DESCRIPTION
     "This attribute indicates the number of unrestricted 64 kbit/s calls 
      that are currently in progress on this DcmeLink."
   DEFVAL     { 0 }
::= { dclOperEntry 3 }

dclReceivedTrmSignal OBJECT-TYPE
   SYNTAX     INTEGER  {
                 none000(0),
                 invalid001(1),
                 invalid010(2),
                 invalid011(3),
                 invalid100(4),
                 switchingCentreNormal101(5),
                 maintenanceReleaseAck110(6),
                 dcmeClearOfTraffic111(7) }
   ACCESS     read-only
   STATUS     mandatory
   DESCRIPTION
     "This attribute indicates the last TRM signal received from the ISC.
      The received TRM signal can be one of:
      Invalid (xxx):	 this signal should never be received,
      Switching Centre normal (101): this signal is allways transmitted 
      by the ISC when there is no other signal to be sent,
      Maintenance release ack(110): this signal is transmitted by the ISC 
      if it accepts the maintenance release request,
      Dcme clear of traffic: this signal is transmitted by the ISC if it has 
      accepted the maintenance release request signal and now informs 
      the DCME when all circuits are idle,"
::= { dclOperEntry 4 }

dclTransmittedTrmSignal OBJECT-TYPE
   SYNTAX     INTEGER  {
                 none000(0),
                 dcmeNormal100(4),
                 no64KbitSCapacity101(5),
                 maintenanceReleaseRequest110(6),
                 noCapacityAvailable111(7) }
   ACCESS     read-only
   STATUS     mandatory
   DESCRIPTION
     "This attribute indicates the last TRM signal transmitted to the ISC.
      The transmitted TRM signal can be one of:
      Dcme normal (100):	 , this signal is allways transmitted by the 
      DCME when there is no other signal to be sent,
      No 64 kbit/s capacity (101): this signal is transmitted by the DCME 
      when it is not able to handle new 64 kbit/s call requests,
      Maintenance release request(110): this signal is transmitted by the 
      DCME when the DCME is to be removed from the service for 
      maintenance,
      No capacity available (111) this signal is transmitted by the DCME 
      when there is bearer capacity available to set up new 3.1 kHz audio 
      or speech calls,"
::= { dclOperEntry 5 }

dclStatsTable OBJECT-TYPE
   SYNTAX     SEQUENCE OF DclStatsEntry
   ACCESS     not-accessible
   STATUS     mandatory
   DESCRIPTION
     "This group contains statistics for the DcmeLink component."
::= { dcl 13 }

dclStatsEntry OBJECT-TYPE
   SYNTAX     DclStatsEntry
   ACCESS     not-accessible
   STATUS     mandatory
   DESCRIPTION
     "An entry in the dclStatsTable."
   INDEX {
      dclIndex }
::= { dclStatsTable 1 }

DclStatsEntry ::= SEQUENCE {
   dclTotalSpeechCalls
      Counter32,
   dclTotal3kHzCalls
      Counter32,
   dclTotal64kCalls
      Counter32,
   dclRejectedSpeechCalls
      Counter32,
   dclRejected3kHzCalls
      Counter32,
   dclRejected64kCalls
      Counter32,
   dclInvalidTrmSignals
      Counter32 }

dclTotalSpeechCalls OBJECT-TYPE
   SYNTAX     Counter32 
   ACCESS     read-only
   STATUS     mandatory
   DESCRIPTION
     "This attribute counts the total number of speech calls that have been 
      handled by this DcmeLink, including rejected calls.
      This counter wraps to zero when it exceeds its maximum."
::= { dclStatsEntry 1 }

dclTotal3kHzCalls OBJECT-TYPE
   SYNTAX     Counter32 
   ACCESS     read-only
   STATUS     mandatory
   DESCRIPTION
     "This attribute counts the total number of audio 3.1 kHz calls that 
      have been handled by this DcmeLink, including rejected calls.
      This counter wraps to zero when it exceeds its maximum."
::= { dclStatsEntry 2 }

dclTotal64kCalls OBJECT-TYPE
   SYNTAX     Counter32 
   ACCESS     read-only
   STATUS     mandatory
   DESCRIPTION
     "This attribute counts the total number of unrestricted 64 kbit/s calls 
      that have been handled by this DcmeLink, including rejected calls.
      This counter wraps to zero when it exceeds its maximum."
::= { dclStatsEntry 3 }

dclRejectedSpeechCalls OBJECT-TYPE
   SYNTAX     Counter32 
   ACCESS     read-only
   STATUS     mandatory
   DESCRIPTION
     "This attribute counts the total number of speech calls that have been 
      rejected by this DcmeLink because there was no preestablished LC 
      available.
      This counter wraps to zero when it exceeds its maximum."
::= { dclStatsEntry 4 }

dclRejected3kHzCalls OBJECT-TYPE
   SYNTAX     Counter32 
   ACCESS     read-only
   STATUS     mandatory
   DESCRIPTION
     "This attribute counts the total number of audio 3.1 KHz calls that 
      have been rejected by this DcmeLink because there was no 
      preestablished LC available.
      This counter wraps to zero when it exceeds its maximum."
::= { dclStatsEntry 5 }

dclRejected64kCalls OBJECT-TYPE
   SYNTAX     Counter32 
   ACCESS     read-only
   STATUS     mandatory
   DESCRIPTION
     "This attribute counts the total number of unrestricted 64 kbit/s calls 
      that have been rejected by this DcmeLink.
      This counter wraps to zero when it reaches its maximum."
::= { dclStatsEntry 6 }

dclInvalidTrmSignals OBJECT-TYPE
   SYNTAX     Counter32 
   ACCESS     read-only
   STATUS     mandatory
   DESCRIPTION
     "This attribute counts the number of invalid TRM/Maintenance 
      signals received from the ISC by this DcmeLink. The most probable 
      cause of an invalid TRM/Maintenance signal is an invalid ISC 
      provisionning or a transmission error.
      The invalid bit settings are 000, 001, 010, 011, 100.
      This counter wraps to zero when it exceeds its maximum."
::= { dclStatsEntry 7 }


-- DcmeLink/n DataNetworkAddress
-- This is the description of the DCME link Dna component. It 
-- includes the attributes which apply to all connections established 
-- between DcmeLink and its peer DcmeLink.

dclDna OBJECT IDENTIFIER ::= { dcl 2 }



dclDnaRowStatusTable OBJECT-TYPE
   SYNTAX     SEQUENCE OF DclDnaRowStatusEntry
   ACCESS     not-accessible
   STATUS     mandatory
   DESCRIPTION
     "This entry controls the addition and deletion of 
      dclDna components."
::= { dclDna 1 }

dclDnaRowStatusEntry OBJECT-TYPE
   SYNTAX     DclDnaRowStatusEntry
   ACCESS     not-accessible
   STATUS     mandatory
   DESCRIPTION
     "A single entry in the table represents a single 
      dclDna component."
   INDEX {
      dclIndex,
      dclDnaIndex }
::= { dclDnaRowStatusTable 1 }

DclDnaRowStatusEntry ::= SEQUENCE {
   dclDnaRowStatus
      RowStatus,
   dclDnaComponentName
      DisplayString,
   dclDnaStorageType
      StorageType,
   dclDnaIndex
      NonReplicated }

dclDnaRowStatus OBJECT-TYPE
   SYNTAX     RowStatus 
   ACCESS     read-only
   STATUS     mandatory
   DESCRIPTION
     "This variable is used as the basis for SNMP naming of
      dclDna components.
      These components cannot be added nor deleted."
::= { dclDnaRowStatusEntry 1 }

dclDnaComponentName OBJECT-TYPE
   SYNTAX     DisplayString 
   ACCESS     read-only
   STATUS     mandatory
   DESCRIPTION
     "This variable provides the component's string name for
      use with the ASCII Console Interface"
::= { dclDnaRowStatusEntry 2 }

dclDnaStorageType OBJECT-TYPE
   SYNTAX     StorageType 
   ACCESS     read-only
   STATUS     mandatory
   DESCRIPTION
     "This variable represents the storage type value for the
      dclDna tables."
::= { dclDnaRowStatusEntry 4 }

dclDnaIndex OBJECT-TYPE
   SYNTAX     NonReplicated 
   ACCESS     not-accessible
   STATUS     mandatory
   DESCRIPTION
     "This variable represents the index for the dclDna tables."
::= { dclDnaRowStatusEntry 10 }

dclDnaAddressTable OBJECT-TYPE
   SYNTAX     SEQUENCE OF DclDnaAddressEntry
   ACCESS     not-accessible
   STATUS     mandatory
   DESCRIPTION
     "The Address group contains attributes common to all Dna's. Every 
      Dna used in the network is defined with this group of 2 attributes. 
      The string of address digits is complemented by the type of address 
      or Npi. These attributes are used to interpret the format of the 
      address digits."
::= { dclDna 10 }

dclDnaAddressEntry OBJECT-TYPE
   SYNTAX     DclDnaAddressEntry
   ACCESS     not-accessible
   STATUS     mandatory
   DESCRIPTION
     "An entry in the dclDnaAddressTable."
   INDEX {
      dclIndex,
      dclDnaIndex }
::= { dclDnaAddressTable 1 }

DclDnaAddressEntry ::= SEQUENCE {
   dclDnaNumberingPlanIndicator
      INTEGER,
   dclDnaDataNetworkAddress
      DigitString }

dclDnaNumberingPlanIndicator OBJECT-TYPE
   SYNTAX     INTEGER  {
                 x121(0),
                 e164(1) }
   ACCESS     read-write
   STATUS     mandatory
   DESCRIPTION
     "This attribute indicates the Numbering Plan Indicator (NPI) of the 
      Dna that is entered. An address may belong to the X.121 or E.164 
      numbering plans. X.121 is used in packet switched data networks."
   DEFVAL     { e164 }
::= { dclDnaAddressEntry 1 }

dclDnaDataNetworkAddress OBJECT-TYPE
   SYNTAX     DigitString (SIZE (1..15))
   ACCESS     read-write
   STATUS     mandatory
   DESCRIPTION
     "The Dna attribute contains digits which form a unique identifier of 
      the customer interface. It can be compared (approximation only) to 
      a telephone number where each phone number identifies a unique 
      telephone set. Dna digits are selected and assigned by network 
      operators."
::= { dclDnaAddressEntry 2 }


-- DcmeLink/n Framer
-- The Framer component controls link layer framing for application 
-- components sending and receiving data on the link interface to the 
-- ISC. It is also through the Framer that an application component is 
-- associated with a specific hardware link interface.
-- 
-- The Framer component provides provisionable attributes related to 
-- datapath aspects of the hardware interface (such as CRC and frame 
-- length). The Framer component also provides a provisionable 
-- attribute which binds the application component to a specific 
-- hardware component.
-- 
-- The Framer component contains operational attributes for link 
-- interface datapath statistics (such as frame counts and aborts).
-- 

dclFramer OBJECT IDENTIFIER ::= { dcl 3 }



dclFramerRowStatusTable OBJECT-TYPE
   SYNTAX     SEQUENCE OF DclFramerRowStatusEntry
   ACCESS     not-accessible
   STATUS     mandatory
   DESCRIPTION
     "This entry controls the addition and deletion of 
      dclFramer components."
::= { dclFramer 1 }

dclFramerRowStatusEntry OBJECT-TYPE
   SYNTAX     DclFramerRowStatusEntry
   ACCESS     not-accessible
   STATUS     mandatory
   DESCRIPTION
     "A single entry in the table represents a single 
      dclFramer component."
   INDEX {
      dclIndex,
      dclFramerIndex }
::= { dclFramerRowStatusTable 1 }

DclFramerRowStatusEntry ::= SEQUENCE {
   dclFramerRowStatus
      RowStatus,
   dclFramerComponentName
      DisplayString,
   dclFramerStorageType
      StorageType,
   dclFramerIndex
      NonReplicated }

dclFramerRowStatus OBJECT-TYPE
   SYNTAX     RowStatus 
   ACCESS     read-only
   STATUS     mandatory
   DESCRIPTION
     "This variable is used as the basis for SNMP naming of
      dclFramer components.
      These components cannot be added nor deleted."
::= { dclFramerRowStatusEntry 1 }

dclFramerComponentName OBJECT-TYPE
   SYNTAX     DisplayString 
   ACCESS     read-only
   STATUS     mandatory
   DESCRIPTION
     "This variable provides the component's string name for
      use with the ASCII Console Interface"
::= { dclFramerRowStatusEntry 2 }

dclFramerStorageType OBJECT-TYPE
   SYNTAX     StorageType 
   ACCESS     read-only
   STATUS     mandatory
   DESCRIPTION
     "This variable represents the storage type value for the
      dclFramer tables."
::= { dclFramerRowStatusEntry 4 }

dclFramerIndex OBJECT-TYPE
   SYNTAX     NonReplicated 
   ACCESS     not-accessible
   STATUS     mandatory
   DESCRIPTION
     "This variable represents the index for the dclFramer tables."
::= { dclFramerRowStatusEntry 10 }

dclFramerProvTable OBJECT-TYPE
   SYNTAX     SEQUENCE OF DclFramerProvEntry
   ACCESS     not-accessible
   STATUS     mandatory
   DESCRIPTION
     "This group contains the base provisioning data for the Framer 
      component. Application or hardware interface specific provisioning 
      data is contained in other provisionable Framer groups."
::= { dclFramer 10 }

dclFramerProvEntry OBJECT-TYPE
   SYNTAX     DclFramerProvEntry
   ACCESS     not-accessible
   STATUS     mandatory
   DESCRIPTION
     "An entry in the dclFramerProvTable."
   INDEX {
      dclIndex,
      dclFramerIndex }
::= { dclFramerProvTable 1 }

DclFramerProvEntry ::= SEQUENCE {
   dclFramerInterfaceName
      Link }

dclFramerInterfaceName OBJECT-TYPE
   SYNTAX     Link 
   ACCESS     read-write
   STATUS     mandatory
   DESCRIPTION
     "This attribute contains a hardware component name.
      
      The attribute associates the application with a specific link. This 
      defines the module processor on which Framer's parent component 
      (as well as Framer itself) will run."
::= { dclFramerProvEntry 1 }

dclFramerStateTable OBJECT-TYPE
   SYNTAX     SEQUENCE OF DclFramerStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { dclFramer 12 }

dclFramerStateEntry OBJECT-TYPE
   SYNTAX     DclFramerStateEntry
   ACCESS     not-accessible
   STATUS     mandatory
   DESCRIPTION
     "An entry in the dclFramerStateTable."
   INDEX {
      dclIndex,
      dclFramerIndex }
::= { dclFramerStateTable 1 }

DclFramerStateEntry ::= SEQUENCE {
   dclFramerAdminState
      INTEGER,
   dclFramerOperationalState
      INTEGER,
   dclFramerUsageState
      INTEGER }

dclFramerAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { dclFramerStateEntry 1 }

dclFramerOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { dclFramerStateEntry 2 }

dclFramerUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { dclFramerStateEntry 3 }


-- DcmeLink/n DcmeVoiceService/n		
-- The DcmeVoiceService component defines the operational 
-- characteristics of the connection to a International Switching Centre 
-- (ISC). One instance of this component is required for each channel 
-- (that is, timeslot) which is part of the DcmeLink.

dclVs OBJECT IDENTIFIER ::= { dcl 4 }



dclVsRowStatusTable OBJECT-TYPE
   SYNTAX     SEQUENCE OF DclVsRowStatusEntry
   ACCESS     not-accessible
   STATUS     mandatory
   DESCRIPTION
     "This entry controls the addition and deletion of 
      dclVs components."
::= { dclVs 1 }

dclVsRowStatusEntry OBJECT-TYPE
   SYNTAX     DclVsRowStatusEntry
   ACCESS     not-accessible
   STATUS     mandatory
   DESCRIPTION
     "A single entry in the table represents a single 
      dclVs component."
   INDEX {
      dclIndex,
      dclVsIndex }
::= { dclVsRowStatusTable 1 }

DclVsRowStatusEntry ::= SEQUENCE {
   dclVsRowStatus
      RowStatus,
   dclVsComponentName
      DisplayString,
   dclVsStorageType
      StorageType,
   dclVsIndex
      Integer32 }

dclVsRowStatus OBJECT-TYPE
   SYNTAX     RowStatus 
   ACCESS     read-write
   STATUS     mandatory
   DESCRIPTION
     "This variable is used as the basis for SNMP naming of
      dclVs components.
      These components can be added and deleted."
::= { dclVsRowStatusEntry 1 }

dclVsComponentName OBJECT-TYPE
   SYNTAX     DisplayString 
   ACCESS     read-only
   STATUS     mandatory
   DESCRIPTION
     "This variable provides the component's string name for
      use with the ASCII Console Interface"
::= { dclVsRowStatusEntry 2 }

dclVsStorageType OBJECT-TYPE
   SYNTAX     StorageType 
   ACCESS     read-only
   STATUS     mandatory
   DESCRIPTION
     "This variable represents the storage type value for the
      dclVs tables."
::= { dclVsRowStatusEntry 4 }

dclVsIndex OBJECT-TYPE
   SYNTAX     Integer32 (1..31)
   ACCESS     not-accessible
   STATUS     mandatory
   DESCRIPTION
     "This variable represents the index for the dclVs tables."
::= { dclVsRowStatusEntry 10 }

dclVsProvTable OBJECT-TYPE
   SYNTAX     SEQUENCE OF DclVsProvEntry
   ACCESS     not-accessible
   STATUS     mandatory
   DESCRIPTION
     "This group contains the provisionable attributes of a DcmeVs 
      component."
::= { dclVs 10 }

dclVsProvEntry OBJECT-TYPE
   SYNTAX     DclVsProvEntry
   ACCESS     not-accessible
   STATUS     mandatory
   DESCRIPTION
     "An entry in the dclVsProvTable."
   INDEX {
      dclIndex,
      dclVsIndex }
::= { dclVsProvTable 1 }

DclVsProvEntry ::= SEQUENCE {
   dclVsVsType
      INTEGER }

dclVsVsType OBJECT-TYPE
   SYNTAX     INTEGER  {
                 dynamicVs(0),
                 permanent64kVs(1) }
   ACCESS     read-write
   STATUS     mandatory
   DESCRIPTION
     "This attribute specifies the type of calls offered by this DcmeVs. If 
      the value permanent64kVs is selected the 64 kbit/s call is 
      established on the channel associated with this DcmeVs upon 
      system activation. If this call is cleared due to the subnet failure it is 
      reestablished again by the DcmeLink. If the value dynamicVs is 
      selected this channel can be used to establish user selected calls."
   DEFVAL     { dynamicVs }
::= { dclVsProvEntry 1 }

dclVsOperTable OBJECT-TYPE
   SYNTAX     SEQUENCE OF DclVsOperEntry
   ACCESS     not-accessible
   STATUS     mandatory
   DESCRIPTION
     "This group provides the operational attributes for the 
      DcmeVoiceService component."
::= { dclVs 11 }

dclVsOperEntry OBJECT-TYPE
   SYNTAX     DclVsOperEntry
   ACCESS     not-accessible
   STATUS     mandatory
   DESCRIPTION
     "An entry in the dclVsOperTable."
   INDEX {
      dclIndex,
      dclVsIndex }
::= { dclVsOperTable 1 }

DclVsOperEntry ::= SEQUENCE {
   dclVsStatus
      INTEGER,
   dclVsCallType
      INTEGER,
   dclVsReceivedAbBits
      INTEGER,
   dclVsTransmittedAbBits
      INTEGER }

dclVsStatus OBJECT-TYPE
   SYNTAX     INTEGER  {
                 idle(0),
                 seized(1) }
   ACCESS     read-only
   STATUS     mandatory
   DESCRIPTION
     "This attribute indicates the current status of the channel. 
      idle means that there is no call currently active on this channel.
      seized means that the channel has currently an active call."
::= { dclVsOperEntry 1 }

dclVsCallType OBJECT-TYPE
   SYNTAX     INTEGER  {
                 none(0),
                 speech(1),
                 n31KHz(2),
                 n64KbitS(3) }
   ACCESS     read-only
   STATUS     mandatory
   DESCRIPTION
     "This attribute indicates the type of call that this channel is currently 
      carrying. If no call is active, then it displays the value for the last 
      call."
::= { dclVsOperEntry 3 }

dclVsReceivedAbBits OBJECT-TYPE
   SYNTAX     INTEGER  {
                 none00(0),
                 normalServiceAvailable01(1),
                 n31KHzRequest10(2),
                 n64KbitSRequest11(3) }
   ACCESS     read-only
   STATUS     mandatory
   DESCRIPTION
     "This attribute indicates the most recently received AB bits."
::= { dclVsOperEntry 4 }

dclVsTransmittedAbBits OBJECT-TYPE
   SYNTAX     INTEGER  {
                 none00(0),
                 normalServiceAvailable01(1),
                 specialServiceAck10(2),
                 channelOutOfService11(3) }
   ACCESS     read-only
   STATUS     mandatory
   DESCRIPTION
     "This attribute indicates the AB bits currently being transmitted."
::= { dclVsOperEntry 5 }

dclVsStatsTable OBJECT-TYPE
   SYNTAX     SEQUENCE OF DclVsStatsEntry
   ACCESS     not-accessible
   STATUS     mandatory
   DESCRIPTION
     "This group provides the operational attributes for the 
      DcmeVoiceService component."
::= { dclVs 12 }

dclVsStatsEntry OBJECT-TYPE
   SYNTAX     DclVsStatsEntry
   ACCESS     not-accessible
   STATUS     mandatory
   DESCRIPTION
     "An entry in the dclVsStatsTable."
   INDEX {
      dclIndex,
      dclVsIndex }
::= { dclVsStatsTable 1 }

DclVsStatsEntry ::= SEQUENCE {
   dclVsTotalCalls
      Counter32,
   dclVsTotalCallSeconds
      Counter32,
   dclVsInvalidAbBits
      Counter32 }

dclVsTotalCalls OBJECT-TYPE
   SYNTAX     Counter32 
   ACCESS     read-only
   STATUS     mandatory
   DESCRIPTION
     "This attribute counts the call attempts processed on this channel (in 
      both directions). This count includes both successful and 
      unsuccessful calls.
      The value wraps when it exceeds its maximum."
::= { dclVsStatsEntry 1 }

dclVsTotalCallSeconds OBJECT-TYPE
   SYNTAX     Counter32 
   ACCESS     read-only
   STATUS     mandatory
   DESCRIPTION
     "This attribute counts the total number of seconds that this channel is 
      handling a call. This is regardless of whether the call is successful 
      or not. In other words, this is the amount of time that the channel is 
      not in the idle state.
      The value wraps when it reaches its maximum."
::= { dclVsStatsEntry 2 }

dclVsInvalidAbBits OBJECT-TYPE
   SYNTAX     Counter32 
   ACCESS     read-only
   STATUS     mandatory
   DESCRIPTION
     "This attribute counts the number of invalid AB bits signals received 
      from the ISC on this channel. The invalid bit setting is 00.
      This counter wraps to zero when it reaches its maximum."
::= { dclVsStatsEntry 3 }

dclVsStateTable OBJECT-TYPE
   SYNTAX     SEQUENCE OF DclVsStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { dclVs 13 }

dclVsStateEntry OBJECT-TYPE
   SYNTAX     DclVsStateEntry
   ACCESS     not-accessible
   STATUS     mandatory
   DESCRIPTION
     "An entry in the dclVsStateTable."
   INDEX {
      dclIndex,
      dclVsIndex }
::= { dclVsStateTable 1 }

DclVsStateEntry ::= SEQUENCE {
   dclVsAdminState
      INTEGER,
   dclVsOperationalState
      INTEGER,
   dclVsUsageState
      INTEGER }

dclVsAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { dclVsStateEntry 1 }

dclVsOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { dclVsStateEntry 2 }

dclVsUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { dclVsStateEntry 3 }


-- Vsr/n Svs/n Framer
-- The Framer component controls link layer framing for application 
-- components sending and receiving data on a link interface. It is also 
-- through Framer, that an application component is associated with a 
-- specific hardware link interface.
-- The Framer component provides provisionable attributes related to 
-- datapath aspects of the hardware interface rather than interface 
-- specific attributes (such as modem leads and clocking) which are 
-- associated with specific hardware components (such as E1 or DS1).
-- The Framer component also provides a provisionable attribute 
-- which binds the application component to a specific hardware 
-- component.
-- The Framer component contains operational attributes for link 
-- interface datapath statistics (such as frame counts).

dclVsFramer OBJECT IDENTIFIER ::= { dclVs 2 }



dclVsFramerRowStatusTable OBJECT-TYPE
   SYNTAX     SEQUENCE OF DclVsFramerRowStatusEntry
   ACCESS     not-accessible
   STATUS     mandatory
   DESCRIPTION
     "This entry controls the addition and deletion of 
      dclVsFramer components."
::= { dclVsFramer 1 }

dclVsFramerRowStatusEntry OBJECT-TYPE
   SYNTAX     DclVsFramerRowStatusEntry
   ACCESS     not-accessible
   STATUS     mandatory
   DESCRIPTION
     "A single entry in the table represents a single 
      dclVsFramer component."
   INDEX {
      dclIndex,
      dclVsIndex,
      dclVsFramerIndex }
::= { dclVsFramerRowStatusTable 1 }

DclVsFramerRowStatusEntry ::= SEQUENCE {
   dclVsFramerRowStatus
      RowStatus,
   dclVsFramerComponentName
      DisplayString,
   dclVsFramerStorageType
      StorageType,
   dclVsFramerIndex
      NonReplicated }

dclVsFramerRowStatus OBJECT-TYPE
   SYNTAX     RowStatus 
   ACCESS     read-only
   STATUS     mandatory
   DESCRIPTION
     "This variable is used as the basis for SNMP naming of
      dclVsFramer components.
      These components cannot be added nor deleted."
::= { dclVsFramerRowStatusEntry 1 }

dclVsFramerComponentName OBJECT-TYPE
   SYNTAX     DisplayString 
   ACCESS     read-only
   STATUS     mandatory
   DESCRIPTION
     "This variable provides the component's string name for
      use with the ASCII Console Interface"
::= { dclVsFramerRowStatusEntry 2 }

dclVsFramerStorageType OBJECT-TYPE
   SYNTAX     StorageType 
   ACCESS     read-only
   STATUS     mandatory
   DESCRIPTION
     "This variable represents the storage type value for the
      dclVsFramer tables."
::= { dclVsFramerRowStatusEntry 4 }

dclVsFramerIndex OBJECT-TYPE
   SYNTAX     NonReplicated 
   ACCESS     not-accessible
   STATUS     mandatory
   DESCRIPTION
     "This variable represents the index for the dclVsFramer tables."
::= { dclVsFramerRowStatusEntry 10 }

dclVsFramerProvTable OBJECT-TYPE
   SYNTAX     SEQUENCE OF DclVsFramerProvEntry
   ACCESS     not-accessible
   STATUS     mandatory
   DESCRIPTION
     "This group contains the base provisioning data for the Framer 
      component. Application or hardware interface specific provisioning 
      data is contained in other provisionable Framer groups."
::= { dclVsFramer 10 }

dclVsFramerProvEntry OBJECT-TYPE
   SYNTAX     DclVsFramerProvEntry
   ACCESS     not-accessible
   STATUS     mandatory
   DESCRIPTION
     "An entry in the dclVsFramerProvTable."
   INDEX {
      dclIndex,
      dclVsIndex,
      dclVsFramerIndex }
::= { dclVsFramerProvTable 1 }

DclVsFramerProvEntry ::= SEQUENCE {
   dclVsFramerInterfaceName
      Link }

dclVsFramerInterfaceName OBJECT-TYPE
   SYNTAX     Link 
   ACCESS     read-write
   STATUS     mandatory
   DESCRIPTION
     "This attribute contains a hardware component name.
      
      The attribute associates the application with a specific link. This 
      defines the module processor on which Framer's parent component 
      (as well as Framer itself) will run."
::= { dclVsFramerProvEntry 1 }

dclVsFramerStateTable OBJECT-TYPE
   SYNTAX     SEQUENCE OF DclVsFramerStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { dclVsFramer 14 }

dclVsFramerStateEntry OBJECT-TYPE
   SYNTAX     DclVsFramerStateEntry
   ACCESS     not-accessible
   STATUS     mandatory
   DESCRIPTION
     "An entry in the dclVsFramerStateTable."
   INDEX {
      dclIndex,
      dclVsIndex,
      dclVsFramerIndex }
::= { dclVsFramerStateTable 1 }

DclVsFramerStateEntry ::= SEQUENCE {
   dclVsFramerAdminState
      INTEGER,
   dclVsFramerOperationalState
      INTEGER,
   dclVsFramerUsageState
      INTEGER }

dclVsFramerAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { dclVsFramerStateEntry 1 }

dclVsFramerOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { dclVsFramerStateEntry 2 }

dclVsFramerUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { dclVsFramerStateEntry 3 }

dclVsFramerStatsTable OBJECT-TYPE
   SYNTAX     SEQUENCE OF DclVsFramerStatsEntry
   ACCESS     not-accessible
   STATUS     mandatory
   DESCRIPTION
     "This group contains the operational statistics data for a Framer 
      component."
::= { dclVsFramer 15 }

dclVsFramerStatsEntry OBJECT-TYPE
   SYNTAX     DclVsFramerStatsEntry
   ACCESS     not-accessible
   STATUS     mandatory
   DESCRIPTION
     "An entry in the dclVsFramerStatsTable."
   INDEX {
      dclIndex,
      dclVsIndex,
      dclVsFramerIndex }
::= { dclVsFramerStatsTable 1 }

DclVsFramerStatsEntry ::= SEQUENCE {
   dclVsFramerTotalCells
      Unsigned32,
   dclVsFramerAudioCells
      Unsigned32,
   dclVsFramerSilenceCells
      Unsigned32,
   dclVsFramerModemCells
      Unsigned32,
   dclVsFramerCurrentEncodingRate
      INTEGER,
   dclVsFramerLrcErrors
      Unsigned32,
   dclVsFramerFrmLostInNetwork
      Unsigned32,
   dclVsFramerFrmUnderRuns
      Unsigned32,
   dclVsFramerFrmDumped
      Unsigned32,
   dclVsFramerModemSilenceCells
      Counter32,
   dclVsFramerCurrentEncoding
      INTEGER,
   dclVsFramerTptStatus
      INTEGER,
   dclVsFramerFaxRelayCells
      Counter32,
   dclVsFramerModemFaxCells
      Unsigned32,
   dclVsFramerFaxIdleCells
      Counter32 }

dclVsFramerTotalCells OBJECT-TYPE
   SYNTAX     Unsigned32 (0..4294967295)
   ACCESS     read-only
   STATUS     mandatory
   DESCRIPTION
     "This attribute counts the total number of cells received from the 
      interface.
      Each cell contains 44 bytes of data from the DS0 channel. Since a 
      DS0 provides data at 64 kbit/s, each cell contains 5.5 ms of audio 
      data.
      This data flow is measured before compression is performed on the 
      channel.
      This counter wraps to zero after reaching its maximum value."
::= { dclVsFramerStatsEntry 1 }

dclVsFramerAudioCells OBJECT-TYPE
   SYNTAX     Unsigned32 (0..4294967295)
   ACCESS     read-only
   STATUS     mandatory
   DESCRIPTION
     "This attribute counts the total number of cells containing audio data 
      received from the interface while the channel was seized. A CCS 
      channel is always considered to be seized. Audio data includes cells 
      containing voice as well modem audio, but not silence. 
      A cell contains 44 bytes of data from the DS0 channel(5.5 ms).
      This flow is measured before compression is performed on the 
      channel.
      This counter wraps to zero after reaching its maximum value."
::= { dclVsFramerStatsEntry 2 }

dclVsFramerSilenceCells OBJECT-TYPE
   SYNTAX     Unsigned32 (0..4294967295)
   ACCESS     read-only
   STATUS     mandatory
   DESCRIPTION
     "This attribute counts the total number of cells containing silence 
      data received from the interface which was not forwarded into the 
      network, thus saving bandwidth. A channel may go into silence due 
      to the operation of the silence suppression feature or for CAS 
      channels when the ABCD signalling bits go idle.
      A cell contains 44 bytes of data from the DS0 channel(5.5 ms).
      This flow is measured before compression is performed on the 
      channel.
      This counter wraps to zero after reaching its maximum value."
::= { dclVsFramerStatsEntry 4 }

dclVsFramerModemCells OBJECT-TYPE
   SYNTAX     Unsigned32 (0..4294967295)
   ACCESS     read-only
   STATUS     obsolete
   DESCRIPTION
     "This attribute is migrated into modemFaxCells."
::= { dclVsFramerStatsEntry 5 }

dclVsFramerCurrentEncodingRate OBJECT-TYPE
   SYNTAX     INTEGER  {
                 n640(1),
                 n320(2),
                 n240(3),
                 n160(4),
                 n80(5),
                 n144(6),
                 n120(7),
                 n96(8),
                 n72(9),
                 n63(10),
                 n53(11),
                 n48(12),
                 n24(13),
                 n12(14),
                 n03(15) }
   ACCESS     read-only
   STATUS     obsolete
   DESCRIPTION
     "This attribute has been migrated to currentRate in Operational 
      group."
::= { dclVsFramerStatsEntry 6 }

dclVsFramerLrcErrors OBJECT-TYPE
   SYNTAX     Unsigned32 (0..4294967295)
   ACCESS     read-only
   STATUS     mandatory
   DESCRIPTION
     "This attribute counts the number of frames received from the 
      network with LRC errors."
::= { dclVsFramerStatsEntry 7 }

dclVsFramerFrmLostInNetwork OBJECT-TYPE
   SYNTAX     Unsigned32 (0..4294967295)
   ACCESS     read-only
   STATUS     mandatory
   DESCRIPTION
     "This attribute counts the number of frames which the service knows 
      it did not receive from the network although they were sent in to the 
      network from the far end."
::= { dclVsFramerStatsEntry 8 }

dclVsFramerFrmUnderRuns OBJECT-TYPE
   SYNTAX     Unsigned32 (0..4294967295)
   ACCESS     read-only
   STATUS     mandatory
   DESCRIPTION
     "This attribute counts the number of times that a frame was needed 
      but was not available because it had been delayed too long in the 
      network.
      This error may occur repeatedly if the interface clocks at the two 
      access points to the network are operating at different rates."
::= { dclVsFramerStatsEntry 9 }

dclVsFramerFrmDumped OBJECT-TYPE
   SYNTAX     Unsigned32 (0..4294967295)
   ACCESS     read-only
   STATUS     mandatory
   DESCRIPTION
     "This attribute counts the number of frames which have been 
      dumped because the output queue grew too large. This can occur if 
      the clock rate on the incoming interface is faster than the clock rate 
      on the outgoing interface and there are no silence periods to absorb 
      the difference, or when a compression rate change occurs.
      This count wraps to zero after reaching its maximum value."
::= { dclVsFramerStatsEntry 10 }

dclVsFramerModemSilenceCells OBJECT-TYPE
   SYNTAX     Counter32 
   ACCESS     read-only
   STATUS     obsolete
   DESCRIPTION
     "This attribute is migrated into faxIdleCells."
::= { dclVsFramerStatsEntry 26 }

dclVsFramerCurrentEncoding OBJECT-TYPE
   SYNTAX     INTEGER  {
                 g729(1),
                 g728(2),
                 g723(3),
                 g726(4),
                 g711(5),
                 v22(32),
                 v22bis(33),
                 faxRelay(64),
                 v27(65),
                 v29(66),
                 v17(67),
                 none(255) }
   ACCESS     read-only
   STATUS     obsolete
   DESCRIPTION
     "This attribute has been migrated to currentEncoding in Operational 
      group."
::= { dclVsFramerStatsEntry 27 }

dclVsFramerTptStatus OBJECT-TYPE
   SYNTAX     INTEGER  {
                 operating(0),
                 rejected(1),
                 monitoring(2),
                 disabled(3) }
   ACCESS     read-only
   STATUS     obsolete
   DESCRIPTION
     "This attribute has been migrated to tptStatus in Operational group."
::= { dclVsFramerStatsEntry 28 }

dclVsFramerFaxRelayCells OBJECT-TYPE
   SYNTAX     Counter32 
   ACCESS     read-only
   STATUS     mandatory
   DESCRIPTION
     "This attribute counts the total number of fax relay cells sent to the 
      network.
      
      This counter wraps to zero after reaching its maximum value."
::= { dclVsFramerStatsEntry 35 }

dclVsFramerModemFaxCells OBJECT-TYPE
   SYNTAX     Unsigned32 (0..4294967295)
   ACCESS     read-only
   STATUS     mandatory
   DESCRIPTION
     "This attribute counts the total number of cells containing modem 
      data received from the interface while the channel was seized. A 
      CCS channel is always considered to be seized. Cells are considered 
      to be modem data if a constant energy level above          -25 dBmO 
      is detected for more than 900 ms. An energy level below -36 dBmO 
      for more than 650 ms is required to detect that the modem is no 
      longer present. 
      A cell contains 44 bytes of data from the DS0 channel (5.5 ms).
      This flow is measured before compression is performed on the 
      channel.
      This counter wraps to zero after reaching its maximum value."
::= { dclVsFramerStatsEntry 36 }

dclVsFramerFaxIdleCells OBJECT-TYPE
   SYNTAX     Counter32 
   ACCESS     read-only
   STATUS     mandatory
   DESCRIPTION
     "This attribute counts the total number of cells containing silent fax 
      data received from the interface which were not forwarded into the 
      network, thus saving bandwidth. A channel may go into silence due 
      to the silence Suppression feature or for CAS channels when the 
      ABCD signalling bits go idle.
      
      A cell contains 44 bytes of data from the DS0 channel (5.5 ms). 
      This flow is measured before compression is performed on the 
      channel.
      
      This counter wraps to zero after reaching its maximum value."
::= { dclVsFramerStatsEntry 37 }

dclVsFramerOperTable OBJECT-TYPE
   SYNTAX     SEQUENCE OF DclVsFramerOperEntry
   ACCESS     not-accessible
   STATUS     mandatory
   DESCRIPTION
     "This group contains the operational data for a Svs Framer."
::= { dclVsFramer 16 }

dclVsFramerOperEntry OBJECT-TYPE
   SYNTAX     DclVsFramerOperEntry
   ACCESS     not-accessible
   STATUS     mandatory
   DESCRIPTION
     "An entry in the dclVsFramerOperTable."
   INDEX {
      dclIndex,
      dclVsIndex,
      dclVsFramerIndex }
::= { dclVsFramerOperTable 1 }

DclVsFramerOperEntry ::= SEQUENCE {
   dclVsFramerOpCurrentEncoding
      INTEGER,
   dclVsFramerCurrentRate
      INTEGER,
   dclVsFramerOpTptStatus
      INTEGER }

dclVsFramerOpCurrentEncoding OBJECT-TYPE
   SYNTAX     INTEGER  {
                 g729(1),
                 g728(2),
                 g723(3),
                 g726(4),
                 g711(5),
                 v22(32),
                 v22bis(33),
                 faxRelay(64),
                 v27(65),
                 v29(66),
                 v17(67),
                 none(255) }
   ACCESS     read-only
   STATUS     mandatory
   DESCRIPTION
     "This attribute indicates the encoding currently being performed on 
      this channel. g711 indicates that pulse code modulation (PCM) 
      defined by ITU-T G.711 is being performed. g726 indicates that 
      adaptive differential pulse code modulation (ADPCM) defined by 
      ITU-T G.726 is being performed. g728 indicates that the Low Delay 
      Coded Excited Linear Predictive Coder (LD-CELP) algorithm 
      defined by ITU-T G.728 is being performed. g729 indicates that the 
      Conjunctive Structure Algebraic Code Excited Linear Predictive 
      Coder (CS-ACELP) algorithm defined by ITU-T G.729 is being 
      performed. v27 indicates that the algorithm defined by ITU-T V.27 
      is being performed. v29 indicates that the algorithm defined by 
      ITU-T V.29 is being performed."
::= { dclVsFramerOperEntry 1 }

dclVsFramerCurrentRate OBJECT-TYPE
   SYNTAX     INTEGER  {
                 n0(0),
                 n640(1),
                 n320(2),
                 n240(3),
                 n160(4),
                 n80(5),
                 n144(6),
                 n120(7),
                 n96(8),
                 n72(9),
                 n63(10),
                 n53(11),
                 n48(12),
                 n24(13),
                 n12(14),
                 n03(15) }
   ACCESS     read-only
   STATUS     mandatory
   DESCRIPTION
     "This attribute indicates the current encoding rate for frames being 
      sent to the network."
::= { dclVsFramerOperEntry 2 }

dclVsFramerOpTptStatus OBJECT-TYPE
   SYNTAX     INTEGER  {
                 operating(0),
                 monitoring(2),
                 disabled(3) }
   ACCESS     read-only
   STATUS     mandatory
   DESCRIPTION
     "This attribute indicates the current status of the tandem pass through 
      algorithm. If tptStatus is operating, the tandem pass through 
      algorithm is cutting through a voice switch. If tptStatus is 
      monitoring, negotiatedTandemPassThrough is enabled, but the 
      tandem pass through algorithm is not cutting through a voice 
      switch. If tptStatus is disabled, negotiatedTandemPassThrough is 
      disabled."
::= { dclVsFramerOperEntry 3 }

dclVsFramerNegTable OBJECT-TYPE
   SYNTAX     SEQUENCE OF DclVsFramerNegEntry
   ACCESS     not-accessible
   STATUS     mandatory
   DESCRIPTION
     "This group contains the attributes indicating the results of voice 
      networking end to end negotiation."
::= { dclVsFramer 17 }

dclVsFramerNegEntry OBJECT-TYPE
   SYNTAX     DclVsFramerNegEntry
   ACCESS     not-accessible
   STATUS     mandatory
   DESCRIPTION
     "An entry in the dclVsFramerNegTable."
   INDEX {
      dclIndex,
      dclVsIndex,
      dclVsFramerIndex }
::= { dclVsFramerNegTable 1 }

DclVsFramerNegEntry ::= SEQUENCE {
   dclVsFramerNegotiatedSilenceSuppression
      INTEGER,
   dclVsFramerNegotiatedFisG711G726
      INTEGER,
   dclVsFramerNegotiatedDtmfRegeneration
      INTEGER,
   dclVsFramerNegotiatedV17AsG711G726
      INTEGER,
   dclVsFramerNegotiatedTandemPassThrough
      INTEGER }

dclVsFramerNegotiatedSilenceSuppression OBJECT-TYPE
   SYNTAX     INTEGER  {
                 off(0),
                 on(1),
                 congested(2),
                 slow(3),
                 slowAndCongested(4) }
   ACCESS     read-write
   STATUS     mandatory
   DESCRIPTION
     "This attribute indicates the result of negotiating silence suppression 
      with the remote end across the subnet. The parameter used for 
      negotiating with the remote end is provisioned in Vncs Vp 
      silenceSuppression.
      
      If negotiatedSilenceSuppression is off, silence suppression is never 
      performed.
      If negotiatedSilenceSuppression is on, silence suppression is always 
      performed.
      If negotiatedSilenceSuppression is congested, silence suppression is 
      performed only when the network is congested.
      If negotiatedSilenceSuppression is slow, silence suppression begins 
      after 10 to 20 seconds without any speech or audio being detected.
      If negotiatedSilenceSuppression is slowAndCongested, both the 
      slow and congested options are applied."
::= { dclVsFramerNegEntry 1 }

dclVsFramerNegotiatedFisG711G726 OBJECT-TYPE
   SYNTAX     INTEGER  {
                 off(0),
                 on(1) }
   ACCESS     read-write
   STATUS     mandatory
   DESCRIPTION
     "This attribute indicates the result of negotiating G.711/G.726 fax 
      idle suppression with the remote end across the subnet. The 
      parameter used for negotiating with the remote end is provisioned in 
      Vncs Vp faxIdleSuppressionG711G726."
::= { dclVsFramerNegEntry 2 }

dclVsFramerNegotiatedDtmfRegeneration OBJECT-TYPE
   SYNTAX     INTEGER  {
                 off(0),
                 on(1) }
   ACCESS     read-write
   STATUS     mandatory
   DESCRIPTION
     "This attribute indicates the result of negotiating DTMF regeneration 
      with the remote end across the subnet. The parameter used for 
      negotiating with the remote end is provisioned in Vncs Vp 
      dtmfRegeneration.
      
      If negotiatedDtmfRegeneration is on, DTMF tones received from 
      the link are first converted to digits before being sent to the subnet. 
      When a digit is received from the subnet, its respective DTMF tone 
      is generated before being sent to the link. 
      
      If negotiatedDtmfRegeneration is off, DTMF tones are transported 
      transparently."
::= { dclVsFramerNegEntry 3 }

dclVsFramerNegotiatedV17AsG711G726 OBJECT-TYPE
   SYNTAX     INTEGER  {
                 no(0),
                 yes(1) }
   ACCESS     read-only
   STATUS     mandatory
   DESCRIPTION
     "This attribute indicates how this SwitchedVoiceService negotiates 
      with V.17 fax machines, as determined by negotiation with the 
      remote end across the subnet. The parameter used for negotiating 
      with the remote end is provisioned in Vncs Vp 
      v17EncodedAsG711G726.
      
      If negotiatedV17AsG711G726 is no, V.17 fax machines are 
      instructed to use V.29, and V.29 fax traffic sent by fax machines is 
      demodulated and encoded using fax relay.
      
      If negotiatedV17AsG711G726 is yes, V.17 fax machines are 
      permitted to use V.17 and V.17 fax traffic sent by fax machines is 
      encoded using G.711 or G.726, at the rates given in 
      negotiatedRates."
::= { dclVsFramerNegEntry 4 }

dclVsFramerNegotiatedTandemPassThrough OBJECT-TYPE
   SYNTAX     INTEGER  {
                 disabled(0),
                 enabled(1) }
   ACCESS     read-only
   STATUS     mandatory
   DESCRIPTION
     "This attribute indicates the result of negotiating tandem pass 
      through with the remote end across the subnet. The parameter used 
      for negotiating with the remote end is provisioned in Vncs Vp 
      tandemPassThrough."
::= { dclVsFramerNegEntry 5 }

dclVsFramerFrmToNetworkTable OBJECT-TYPE
   SYNTAX     SEQUENCE OF DclVsFramerFrmToNetworkEntry
   ACCESS     not-accessible
   STATUS     mandatory
   DESCRIPTION
     "This attribute counts the number of frames sent to the network at 
      each encoding rate. Fax relay cells are not included."
::= { dclVsFramer 315 }

dclVsFramerFrmToNetworkEntry OBJECT-TYPE
   SYNTAX     DclVsFramerFrmToNetworkEntry
   ACCESS     not-accessible
   STATUS     mandatory
   DESCRIPTION
     "An entry in the dclVsFramerFrmToNetworkTable."
   INDEX {
      dclIndex,
      dclVsIndex,
      dclVsFramerIndex,
      dclVsFramerFrmToNetworkIndex }
::= { dclVsFramerFrmToNetworkTable 1 }

DclVsFramerFrmToNetworkEntry ::= SEQUENCE {
   dclVsFramerFrmToNetworkIndex
      INTEGER,
   dclVsFramerFrmToNetworkValue
      Unsigned32 }

dclVsFramerFrmToNetworkIndex OBJECT-TYPE
   SYNTAX     INTEGER  {
                 n64KbitS(0),
                 n32KbitS(1),
                 n24KbitS(2),
                 n16KbitS(3),
                 n8KbitS(4) }
   ACCESS     not-accessible
   STATUS     mandatory
   DESCRIPTION
     "This variable represents the dclVsFramerFrmToNetworkTable
      specific index for the dclVsFramerFrmToNetworkTable."
::= { dclVsFramerFrmToNetworkEntry 1 }

dclVsFramerFrmToNetworkValue OBJECT-TYPE
   SYNTAX     Unsigned32 (0..4294967295)
   ACCESS     read-only
   STATUS     mandatory
   DESCRIPTION
     "This variable represents an individual value for the
      dclVsFramerFrmToNetworkTable."
::= { dclVsFramerFrmToNetworkEntry 2 }

dclVsFramerFrmFromNetworkTable OBJECT-TYPE
   SYNTAX     SEQUENCE OF DclVsFramerFrmFromNetworkEntry
   ACCESS     not-accessible
   STATUS     mandatory
   DESCRIPTION
     "This attribute counts the number of frames received from the 
      network at each encoding rate."
::= { dclVsFramer 316 }

dclVsFramerFrmFromNetworkEntry OBJECT-TYPE
   SYNTAX     DclVsFramerFrmFromNetworkEntry
   ACCESS     not-accessible
   STATUS     mandatory
   DESCRIPTION
     "An entry in the dclVsFramerFrmFromNetworkTable."
   INDEX {
      dclIndex,
      dclVsIndex,
      dclVsFramerIndex,
      dclVsFramerFrmFromNetworkIndex }
::= { dclVsFramerFrmFromNetworkTable 1 }

DclVsFramerFrmFromNetworkEntry ::= SEQUENCE {
   dclVsFramerFrmFromNetworkIndex
      INTEGER,
   dclVsFramerFrmFromNetworkValue
      Unsigned32 }

dclVsFramerFrmFromNetworkIndex OBJECT-TYPE
   SYNTAX     INTEGER  {
                 n64KbitS(0),
                 n32KbitS(1),
                 n24KbitS(2),
                 n16KbitS(3),
                 n8KbitS(4) }
   ACCESS     not-accessible
   STATUS     mandatory
   DESCRIPTION
     "This variable represents the dclVsFramerFrmFromNetworkTable
      specific index for the dclVsFramerFrmFromNetworkTable."
::= { dclVsFramerFrmFromNetworkEntry 1 }

dclVsFramerFrmFromNetworkValue OBJECT-TYPE
   SYNTAX     Unsigned32 (0..4294967295)
   ACCESS     read-only
   STATUS     mandatory
   DESCRIPTION
     "This variable represents an individual value for the
      dclVsFramerFrmFromNetworkTable."
::= { dclVsFramerFrmFromNetworkEntry 2 }

dclVsFramerNEncodingTable OBJECT-TYPE
   SYNTAX     SEQUENCE OF DclVsFramerNEncodingEntry
   ACCESS     not-accessible
   STATUS     mandatory
   DESCRIPTION
     "This attribute indicates the results of negotiating audio call 
      encodings for voice, modemFax and fax traffic with the remote end 
      across the subnet. The parameters used for negotiating with the 
      remote end are provisioned in Vncs Vp voiceEncodingChoice and 
      Vncs Vp modemFaxEncodingChoice.
      
      voice traffic is all traffic from the start of a call or speech until a 
      2100 Hz tone or call release. modemFax traffic is all traffic after a 
      2100 Hz tone but before a fax preamble, speech or call release. fax 
      traffic is all traffic after a fax preamble but before speech or call 
      release.
      
      g711 indicates that pulse code modulation (PCM) defined by ITU-T 
      G.711 is the negotiated encoding.
      g726 indicates that Adaptive Differential Pulse Code Modulation 
      (ADPCM) defined by ITU-T G.726 is the negotiated encoding. 
      g711G726 indicates that pulse code modulation (PCM) defined by 
      ITU-T G.711 and Adaptive Differential Pulse Code Modulation 
      (ADPCM) defined by ITU-T G.726 are both negotiated encodings. 
      If negotiatedEncoding is g711G726, the actual encoding performed 
      can be either G.711 or G.726, depending on network congestion.
      g728 indicates that Low Delay Coded Excited Linear Predictive 
      Coder (CS-ACELP) defined by ITU-T G.728 is the negotiated 
      encoding.
      g729 indicates that Conjunctive Structure Algebraic Code Excited 
      Linear Predictive Coder (CS-ACELP) defined by ITU-T G.729 is 
      the negotiated encoding.
      v29V27Relay indicates that fax relay using ITU-T V.27 or ITU-T 
      V.29 is the negotiated encoding.
      v17V29V27Relay indicates that fax relay using ITU-T V.17, ITU-T 
      V.27, or ITU-T V.29 is the negotiated encoding.
      
      If all negotiated encodings are none, the negotiation of audio call 
      encodings is not complete."
::= { dclVsFramer 467 }

dclVsFramerNEncodingEntry OBJECT-TYPE
   SYNTAX     DclVsFramerNEncodingEntry
   ACCESS     not-accessible
   STATUS     mandatory
   DESCRIPTION
     "An entry in the dclVsFramerNEncodingTable."
   INDEX {
      dclIndex,
      dclVsIndex,
      dclVsFramerIndex,
      dclVsFramerNEncodingIndex }
::= { dclVsFramerNEncodingTable 1 }

DclVsFramerNEncodingEntry ::= SEQUENCE {
   dclVsFramerNEncodingIndex
      INTEGER,
   dclVsFramerNEncodingValue
      INTEGER }

dclVsFramerNEncodingIndex OBJECT-TYPE
   SYNTAX     INTEGER  {
                 voice(0),
                 modemFax(1),
                 fax(2) }
   ACCESS     not-accessible
   STATUS     mandatory
   DESCRIPTION
     "This variable represents the dclVsFramerNEncodingTable
      specific index for the dclVsFramerNEncodingTable."
::= { dclVsFramerNEncodingEntry 1 }

dclVsFramerNEncodingValue OBJECT-TYPE
   SYNTAX     INTEGER  {
                 g729(1),
                 g728(2),
                 g726(4),
                 g711(5),
                 g711G726(31),
                 v29V27Relay(64),
                 v17V29V27Relay(68),
                 none(255) }
   ACCESS     read-write
   STATUS     mandatory
   DESCRIPTION
     "This variable represents an individual value for the
      dclVsFramerNEncodingTable."
::= { dclVsFramerNEncodingEntry 2 }

dclVsFramerNRatesTable OBJECT-TYPE
   SYNTAX     SEQUENCE OF DclVsFramerNRatesEntry
   ACCESS     not-accessible
   STATUS     mandatory
   DESCRIPTION
     "This attribute indicates the results of negotiating minimum and 
      maximum rates for voice, modemFax and fax traffic with the 
      remote end across the subnet. The parameters used for negotiating 
      with the remote end are provisioned in Vncs Vp voiceRates and 
      Vncs Vp modemFaxRates."
::= { dclVsFramer 479 }

dclVsFramerNRatesEntry OBJECT-TYPE
   SYNTAX     DclVsFramerNRatesEntry
   ACCESS     not-accessible
   STATUS     mandatory
   DESCRIPTION
     "An entry in the dclVsFramerNRatesTable."
   INDEX {
      dclIndex,
      dclVsIndex,
      dclVsFramerIndex,
      dclVsFramerNRatesTrafficIndex,
      dclVsFramerNRatesRateIndex }
::= { dclVsFramerNRatesTable 1 }

DclVsFramerNRatesEntry ::= SEQUENCE {
   dclVsFramerNRatesTrafficIndex
      INTEGER,
   dclVsFramerNRatesRateIndex
      INTEGER,
   dclVsFramerNRatesValue
      INTEGER }

dclVsFramerNRatesTrafficIndex OBJECT-TYPE
   SYNTAX     INTEGER  {
                 voice(0),
                 modemFax(1),
                 fax(2) }
   ACCESS     not-accessible
   STATUS     mandatory
   DESCRIPTION
     "This variable represents the next to last index for the 
      dclVsFramerNRatesTable."
::= { dclVsFramerNRatesEntry 1 }

dclVsFramerNRatesRateIndex OBJECT-TYPE
   SYNTAX     INTEGER  {
                 min(0),
                 max(1) }
   ACCESS     not-accessible
   STATUS     mandatory
   DESCRIPTION
     "This variable represents the final index for the 
      dclVsFramerNRatesTable."
::= { dclVsFramerNRatesEntry 2 }

dclVsFramerNRatesValue OBJECT-TYPE
   SYNTAX     INTEGER  {
                 n00(0),
                 n03(1),
                 n12(2),
                 n24(3),
                 n48(4),
                 n72(5),
                 n96(6),
                 n120(7),
                 n144(8),
                 n80(66),
                 n160(67),
                 n240(68),
                 n320(69),
                 n640(70) }
   ACCESS     read-write
   STATUS     mandatory
   DESCRIPTION
     "This variable represents an individual value for the
      dclVsFramerNRatesTable."
::= { dclVsFramerNRatesEntry 3 }


-- Vsr/m Svs/n Framer VfpDebug
-- This component contains debugging attributes for a voice service 
-- running on a DS1V, E1V, 1pDS1V, 1pE1V or J2MV functional 
-- processor.

dclVsFramerVfpDebug OBJECT IDENTIFIER ::= { dclVsFramer 5 }



dclVsFramerVfpDebugRowStatusTable OBJECT-TYPE
   SYNTAX     SEQUENCE OF DclVsFramerVfpDebugRowStatusEntry
   ACCESS     not-accessible
   STATUS     mandatory
   DESCRIPTION
     "This entry controls the addition and deletion of 
      dclVsFramerVfpDebug components."
::= { dclVsFramerVfpDebug 1 }

dclVsFramerVfpDebugRowStatusEntry OBJECT-TYPE
   SYNTAX     DclVsFramerVfpDebugRowStatusEntry
   ACCESS     not-accessible
   STATUS     mandatory
   DESCRIPTION
     "A single entry in the table represents a single 
      dclVsFramerVfpDebug component."
   INDEX {
      dclIndex,
      dclVsIndex,
      dclVsFramerIndex,
      dclVsFramerVfpDebugIndex }
::= { dclVsFramerVfpDebugRowStatusTable 1 }

DclVsFramerVfpDebugRowStatusEntry ::= SEQUENCE {
   dclVsFramerVfpDebugRowStatus
      RowStatus,
   dclVsFramerVfpDebugComponentName
      DisplayString,
   dclVsFramerVfpDebugStorageType
      StorageType,
   dclVsFramerVfpDebugIndex
      NonReplicated }

dclVsFramerVfpDebugRowStatus OBJECT-TYPE
   SYNTAX     RowStatus 
   ACCESS     read-only
   STATUS     mandatory
   DESCRIPTION
     "This variable is used as the basis for SNMP naming of
      dclVsFramerVfpDebug components.
      These components cannot be added nor deleted."
::= { dclVsFramerVfpDebugRowStatusEntry 1 }

dclVsFramerVfpDebugComponentName OBJECT-TYPE
   SYNTAX     DisplayString 
   ACCESS     read-only
   STATUS     mandatory
   DESCRIPTION
     "This variable provides the component's string name for
      use with the ASCII Console Interface"
::= { dclVsFramerVfpDebugRowStatusEntry 2 }

dclVsFramerVfpDebugStorageType OBJECT-TYPE
   SYNTAX     StorageType 
   ACCESS     read-only
   STATUS     mandatory
   DESCRIPTION
     "This variable represents the storage type value for the
      dclVsFramerVfpDebug tables."
::= { dclVsFramerVfpDebugRowStatusEntry 4 }

dclVsFramerVfpDebugIndex OBJECT-TYPE
   SYNTAX     NonReplicated 
   ACCESS     not-accessible
   STATUS     mandatory
   DESCRIPTION
     "This variable represents the index for the dclVsFramerVfpDebug tables."
::= { dclVsFramerVfpDebugRowStatusEntry 10 }


-- Vsr/m Svs/n Framer MvpDebug
-- This component contains debugging attributes on a voice service's 
-- framer running on a 1pE1Mvp, 1pDS1Mvp or 1pTTC2mMvp 
-- functional processor.

dclVsFramerMvpDebug OBJECT IDENTIFIER ::= { dclVsFramer 6 }



dclVsFramerMvpDebugRowStatusTable OBJECT-TYPE
   SYNTAX     SEQUENCE OF DclVsFramerMvpDebugRowStatusEntry
   ACCESS     not-accessible
   STATUS     mandatory
   DESCRIPTION
     "This entry controls the addition and deletion of 
      dclVsFramerMvpDebug components."
::= { dclVsFramerMvpDebug 1 }

dclVsFramerMvpDebugRowStatusEntry OBJECT-TYPE
   SYNTAX     DclVsFramerMvpDebugRowStatusEntry
   ACCESS     not-accessible
   STATUS     mandatory
   DESCRIPTION
     "A single entry in the table represents a single 
      dclVsFramerMvpDebug component."
   INDEX {
      dclIndex,
      dclVsIndex,
      dclVsFramerIndex,
      dclVsFramerMvpDebugIndex }
::= { dclVsFramerMvpDebugRowStatusTable 1 }

DclVsFramerMvpDebugRowStatusEntry ::= SEQUENCE {
   dclVsFramerMvpDebugRowStatus
      RowStatus,
   dclVsFramerMvpDebugComponentName
      DisplayString,
   dclVsFramerMvpDebugStorageType
      StorageType,
   dclVsFramerMvpDebugIndex
      NonReplicated }

dclVsFramerMvpDebugRowStatus OBJECT-TYPE
   SYNTAX     RowStatus 
   ACCESS     read-only
   STATUS     mandatory
   DESCRIPTION
     "This variable is used as the basis for SNMP naming of
      dclVsFramerMvpDebug components.
      These components cannot be added nor deleted."
::= { dclVsFramerMvpDebugRowStatusEntry 1 }

dclVsFramerMvpDebugComponentName OBJECT-TYPE
   SYNTAX     DisplayString 
   ACCESS     read-only
   STATUS     mandatory
   DESCRIPTION
     "This variable provides the component's string name for
      use with the ASCII Console Interface"
::= { dclVsFramerMvpDebugRowStatusEntry 2 }

dclVsFramerMvpDebugStorageType OBJECT-TYPE
   SYNTAX     StorageType 
   ACCESS     read-only
   STATUS     mandatory
   DESCRIPTION
     "This variable represents the storage type value for the
      dclVsFramerMvpDebug tables."
::= { dclVsFramerMvpDebugRowStatusEntry 4 }

dclVsFramerMvpDebugIndex OBJECT-TYPE
   SYNTAX     NonReplicated 
   ACCESS     not-accessible
   STATUS     mandatory
   DESCRIPTION
     "This variable represents the index for the dclVsFramerMvpDebug tables."
::= { dclVsFramerMvpDebugRowStatusEntry 10 }


-- Vsr/n Svs/m Framer PcmCapture
-- This component contains attributes for PCM data capture.

dclVsFramerPcmCapture OBJECT IDENTIFIER ::= { dclVsFramer 7 }



dclVsFramerPcmCaptureRowStatusTable OBJECT-TYPE
   SYNTAX     SEQUENCE OF DclVsFramerPcmCaptureRowStatusEntry
   ACCESS     not-accessible
   STATUS     mandatory
   DESCRIPTION
     "This entry controls the addition and deletion of 
      dclVsFramerPcmCapture components."
::= { dclVsFramerPcmCapture 1 }

dclVsFramerPcmCaptureRowStatusEntry OBJECT-TYPE
   SYNTAX     DclVsFramerPcmCaptureRowStatusEntry
   ACCESS     not-accessible
   STATUS     mandatory
   DESCRIPTION
     "A single entry in the table represents a single 
      dclVsFramerPcmCapture component."
   INDEX {
      dclIndex,
      dclVsIndex,
      dclVsFramerIndex,
      dclVsFramerPcmCaptureIndex }
::= { dclVsFramerPcmCaptureRowStatusTable 1 }

DclVsFramerPcmCaptureRowStatusEntry ::= SEQUENCE {
   dclVsFramerPcmCaptureRowStatus
      RowStatus,
   dclVsFramerPcmCaptureComponentName
      DisplayString,
   dclVsFramerPcmCaptureStorageType
      StorageType,
   dclVsFramerPcmCaptureIndex
      NonReplicated }

dclVsFramerPcmCaptureRowStatus OBJECT-TYPE
   SYNTAX     RowStatus 
   ACCESS     read-only
   STATUS     mandatory
   DESCRIPTION
     "This variable is used as the basis for SNMP naming of
      dclVsFramerPcmCapture components.
      These components cannot be added nor deleted."
::= { dclVsFramerPcmCaptureRowStatusEntry 1 }

dclVsFramerPcmCaptureComponentName OBJECT-TYPE
   SYNTAX     DisplayString 
   ACCESS     read-only
   STATUS     mandatory
   DESCRIPTION
     "This variable provides the component's string name for
      use with the ASCII Console Interface"
::= { dclVsFramerPcmCaptureRowStatusEntry 2 }

dclVsFramerPcmCaptureStorageType OBJECT-TYPE
   SYNTAX     StorageType 
   ACCESS     read-only
   STATUS     mandatory
   DESCRIPTION
     "This variable represents the storage type value for the
      dclVsFramerPcmCapture tables."
::= { dclVsFramerPcmCaptureRowStatusEntry 4 }

dclVsFramerPcmCaptureIndex OBJECT-TYPE
   SYNTAX     NonReplicated 
   ACCESS     not-accessible
   STATUS     mandatory
   DESCRIPTION
     "This variable represents the index for the dclVsFramerPcmCapture tables."
::= { dclVsFramerPcmCaptureRowStatusEntry 10 }


-- ...Lc
-- This component contains all of the operation attributes for a Path 
-- Oriented Logical Connection.

dclVsLCo OBJECT IDENTIFIER ::= { dclVs 3 }



dclVsLCoRowStatusTable OBJECT-TYPE
   SYNTAX     SEQUENCE OF DclVsLCoRowStatusEntry
   ACCESS     not-accessible
   STATUS     mandatory
   DESCRIPTION
     "This entry controls the addition and deletion of 
      dclVsLCo components."
::= { dclVsLCo 1 }

dclVsLCoRowStatusEntry OBJECT-TYPE
   SYNTAX     DclVsLCoRowStatusEntry
   ACCESS     not-accessible
   STATUS     mandatory
   DESCRIPTION
     "A single entry in the table represents a single 
      dclVsLCo component."
   INDEX {
      dclIndex,
      dclVsIndex,
      dclVsLCoIndex }
::= { dclVsLCoRowStatusTable 1 }

DclVsLCoRowStatusEntry ::= SEQUENCE {
   dclVsLCoRowStatus
      RowStatus,
   dclVsLCoComponentName
      DisplayString,
   dclVsLCoStorageType
      StorageType,
   dclVsLCoIndex
      NonReplicated }

dclVsLCoRowStatus OBJECT-TYPE
   SYNTAX     RowStatus 
   ACCESS     read-only
   STATUS     mandatory
   DESCRIPTION
     "This variable is used as the basis for SNMP naming of
      dclVsLCo components.
      These components cannot be added nor deleted."
::= { dclVsLCoRowStatusEntry 1 }

dclVsLCoComponentName OBJECT-TYPE
   SYNTAX     DisplayString 
   ACCESS     read-only
   STATUS     mandatory
   DESCRIPTION
     "This variable provides the component's string name for
      use with the ASCII Console Interface"
::= { dclVsLCoRowStatusEntry 2 }

dclVsLCoStorageType OBJECT-TYPE
   SYNTAX     StorageType 
   ACCESS     read-only
   STATUS     mandatory
   DESCRIPTION
     "This variable represents the storage type value for the
      dclVsLCo tables."
::= { dclVsLCoRowStatusEntry 4 }

dclVsLCoIndex OBJECT-TYPE
   SYNTAX     NonReplicated 
   ACCESS     not-accessible
   STATUS     mandatory
   DESCRIPTION
     "This variable represents the index for the dclVsLCo tables."
::= { dclVsLCoRowStatusEntry 10 }

dclVsLCoPathDataTable OBJECT-TYPE
   SYNTAX     SEQUENCE OF DclVsLCoPathDataEntry
   ACCESS     not-accessible
   STATUS     mandatory
   DESCRIPTION
     "This group contains all operational attributes for the path oriented 
      LCo."
::= { dclVsLCo 10 }

dclVsLCoPathDataEntry OBJECT-TYPE
   SYNTAX     DclVsLCoPathDataEntry
   ACCESS     not-accessible
   STATUS     mandatory
   DESCRIPTION
     "An entry in the dclVsLCoPathDataTable."
   INDEX {
      dclIndex,
      dclVsIndex,
      dclVsLCoIndex }
::= { dclVsLCoPathDataTable 1 }

DclVsLCoPathDataEntry ::= SEQUENCE {
   dclVsLCoState
      INTEGER,
   dclVsLCoOverrideRemoteName
      AsciiString,
   dclVsLCoEnd
      INTEGER,
   dclVsLCoCostMetric
      Unsigned32,
   dclVsLCoDelayMetric
      Unsigned32,
   dclVsLCoRoundTripDelay
      Unsigned32,
   dclVsLCoSetupPriority
      Unsigned32,
   dclVsLCoHoldingPriority
      Unsigned32,
   dclVsLCoRequiredTxBandwidth
      Gauge32,
   dclVsLCoRequiredRxBandwidth
      Gauge32,
   dclVsLCoRequiredTrafficType
      INTEGER,
   dclVsLCoPermittedTrunkTypes
      OCTET STRING,
   dclVsLCoRequiredSecurity
      Unsigned32,
   dclVsLCoRequiredCustomerParameter
      Unsigned32,
   dclVsLCoEmissionPriority
      Unsigned32,
   dclVsLCoDiscardPriority
      Unsigned32,
   dclVsLCoPathType
      INTEGER,
   dclVsLCoRetryCount
      Unsigned32,
   dclVsLCoPathFailureCount
      Unsigned32,
   dclVsLCoReasonForNoRoute
      INTEGER,
   dclVsLCoLastTearDownReason
      INTEGER,
   dclVsLCoPathFailureAction
      INTEGER,
   dclVsLCoBumpPreference
      INTEGER,
   dclVsLCoOptimization
      INTEGER,
   dclVsLCoPathUpDateTime
      EnterpriseDateAndTime }

dclVsLCoState OBJECT-TYPE
   SYNTAX     INTEGER  {
                 pathDown(0),
                 selectingRoute(1),
                 connecting(2),
                 pathUp(3),
                 pathDownRetrying(4) }
   ACCESS     read-only
   STATUS     mandatory
   DESCRIPTION
     "This attribute reflects the current state of the connection. The 
      pathDown state indicates a connection that has no remote end 
      provisioned or the application has not yet signalled for a path. The 
      selectingRoute state occurs when a request has been sent to route 
      selector and it has not yet responded. The connectingState occurs 
      while a path is being established. The pathUp state is the normal 
      operational state of a path. The pathDownRetrying state indicates a 
      path that attempted route selection but received no route and is now 
      waiting to retry route selection again."
::= { dclVsLCoPathDataEntry 1 }

dclVsLCoOverrideRemoteName OBJECT-TYPE
   SYNTAX     AsciiString (SIZE (0..40))
   ACCESS     read-write
   STATUS     mandatory
   DESCRIPTION
     "If set and the current PLC remoteName is blank this remoteName 
      will override the blank PLC remoteName. Usually you would set 
      this attribute and then lock/unlock the service component which 
      will result in this new overrideRemoteName being used as if it had 
      been provisioned into the PLC remoteName. The advantage of this 
      attribute is that the connection's remoteName can be changed 
      immediately without having to 'activate prov' but the disadvantage 
      is that the overrideRemoteName is not permanent and if the card or 
      switch is reset the override will be lost."
::= { dclVsLCoPathDataEntry 2 }

dclVsLCoEnd OBJECT-TYPE
   SYNTAX     INTEGER  {
                 calling(0),
                 called(1) }
   ACCESS     read-only
   STATUS     mandatory
   DESCRIPTION
     "This attribute identifies whether this is the calling or called end of 
      the path."
::= { dclVsLCoPathDataEntry 3 }

dclVsLCoCostMetric OBJECT-TYPE
   SYNTAX     Unsigned32 (0..65535)
   ACCESS     read-only
   STATUS     mandatory
   DESCRIPTION
     "This attribute gives the route's total cost metric. It is calculated as 
      the sum of the cost metric of all trunks in the path at the time the 
      connection was established. The cost metric of a trunk is defined by 
      the trunkCost attribute of the Trunk component. The costMetric for 
      an LCo that is originated and terminated on the same module is 0."
::= { dclVsLCoPathDataEntry 4 }

dclVsLCoDelayMetric OBJECT-TYPE
   SYNTAX     Unsigned32 (0..100000)
   ACCESS     read-only
   STATUS     mandatory
   DESCRIPTION
     "This attribute gives the total delay of the route as the one way delay 
      for a 512 byte packet. It is calculated as the sum of the delays of all 
      trunks in the path stored in topology at the time the connection was 
      established. The delay for an LCo that is originated and terminated 
      on the same module is 0."
::= { dclVsLCoPathDataEntry 5 }

dclVsLCoRoundTripDelay OBJECT-TYPE
   SYNTAX     Unsigned32 (0..200000)
   ACCESS     read-only
   STATUS     mandatory
   DESCRIPTION
     "This attribute contains the time taken for a packet (cell) of 44 bytes 
      to be transmitted to the remote LCo and return to this LCo. The 
      number reported is given in milliseconds to the nearest millisecond. 
      A value of one millisecond is reported if the time is less than 1 
      millisecond even though the delay may be less than 1 Millisecond 
      when the LCo is originated and terminated on the same module."
::= { dclVsLCoPathDataEntry 6 }

dclVsLCoSetupPriority OBJECT-TYPE
   SYNTAX     Unsigned32 (0..4)
   ACCESS     read-only
   STATUS     mandatory
   DESCRIPTION
     "This attribute gives the priority at which the current path is 
      established. Zero is the highest priority and four is the lowest. The 
      holdingPriority, a complementary attribute of this component, 
      indicates the priority a path maintains once it is established."
::= { dclVsLCoPathDataEntry 7 }

dclVsLCoHoldingPriority OBJECT-TYPE
   SYNTAX     Unsigned32 (0..4)
   ACCESS     read-only
   STATUS     mandatory
   DESCRIPTION
     "This attribute gives the priority at which a path holds its current 
      path once the path is established. Zero is the highest priority and 
      four is the lowest. The setupPriority, a complementary attribute, 
      indicates the priority of a path at establishment time."
::= { dclVsLCoPathDataEntry 8 }

dclVsLCoRequiredTxBandwidth OBJECT-TYPE
   SYNTAX     Gauge32 (0..4294967295)
   ACCESS     read-only
   STATUS     mandatory
   DESCRIPTION
     "This attribute gives the actual bandwidth (in bits per second) 
      reserved by this path on each of the trunks of its route. This attribute 
      represents the bandwidth for traffic outgoing to the remote end 
      point. The originating end of the connection determines this value."
::= { dclVsLCoPathDataEntry 9 }

dclVsLCoRequiredRxBandwidth OBJECT-TYPE
   SYNTAX     Gauge32 (0..4294967295)
   ACCESS     read-only
   STATUS     mandatory
   DESCRIPTION
     "This attribute gives the actual bandwidth (in bits per second) 
      reserved by this path on each of trunks of its route. This attribute 
      represents the bandwidth for traffic incoming from the remote end 
      point. The originating end of the connection determines this value"
::= { dclVsLCoPathDataEntry 10 }

dclVsLCoRequiredTrafficType OBJECT-TYPE
   SYNTAX     INTEGER  {
                 voice(0),
                 data(1),
                 video(2),
                 trafficType1(3),
                 trafficType2(4),
                 trafficType3(5),
                 trafficType4(6),
                 trafficType5(7) }
   ACCESS     read-only
   STATUS     mandatory
   DESCRIPTION
     "This operational attribute indicates the type of traffic transmitted 
      over the path. There are eight possible traffic types, and the path can 
      transmit only one of them. The originating end of the connection 
      determines the type. These are arbitrary designations for traffic 
      type. The voice, data and video traffic types are defined, and five 
      other arbitrary traffic types can be defined by the network 
      administration. This attribute is used in the route selection process 
      to restrict the route to trunks that support this traffic type. The 
      supportedTrafficType trunk attribute lists all the types of traffic 
      allowed on the trunk. For example, if requiredTrafficType is 
      specified as trafficType1 then only trunks that include trafficType1 
      in supportedTrafficType, will be candidates for this connection."
::= { dclVsLCoPathDataEntry 11 }

dclVsLCoPermittedTrunkTypes OBJECT-TYPE
   SYNTAX     OCTET STRING (SIZE (1))
   ACCESS     read-only
   STATUS     mandatory
   DESCRIPTION
     "This operational attribute lists up to eight types of trunk that can be 
      used on the route. The originating end of the connection determines 
      the types. The terrestrial and satellite trunk types have been 
      defined, leaving six remaining arbitrary types that can be defined by 
      the network administration. The trunk's type is indicated in the 
      trunkType attribute of the Trunk component. When selecting a 
      route, PORS only chooses trunks whose trunkType are in the 
      permittedTrunkTypes for the path.

      Description of bits:
      terrestrial(0)
      satellite(1)
      trunkType1(2)
      trunkType2(3)
      trunkType3(4)
      trunkType4(5)
      trunkType5(6)
      trunkType6(7)"
::= { dclVsLCoPathDataEntry 12 }

dclVsLCoRequiredSecurity OBJECT-TYPE
   SYNTAX     Unsigned32 (0..7)
   ACCESS     read-only
   STATUS     mandatory
   DESCRIPTION
     "This attribute indicates the required minimum level of security of 
      the trunks on the route. Zero represents the most secure and seven 
      represents the least secure. The trunk's security is indicated by the 
      trunkSecurity attribute of the Trunk component, and has values 
      identical in range and meaning to the requiredSecurity attribute. 
      PORS ensures that any route selected does not contain a trunk 
      whose trunkSecurity attribute is numerically greater than the 
      requiredSecurity."
::= { dclVsLCoPathDataEntry 13 }

dclVsLCoRequiredCustomerParameter OBJECT-TYPE
   SYNTAX     Unsigned32 (0..7)
   ACCESS     read-only
   STATUS     mandatory
   DESCRIPTION
     "This attribute indicates the allowed customer defined parameter of 
      the trunks on the route.The originating end of the connection 
      determines the customer defined parameter. Its value, a number 
      from zero to seven, is chosen by a network administration to have a 
      meaning specific to their network, thus allowing them to customize 
      the use of their trunks. A complementary trunk attribute, 
      customerParameter, also has a value from zero to seven. The route 
      selection process does not consider trunks whose 
      customerParameter is greater than the requiredCustomerParameter 
      of the path."
::= { dclVsLCoPathDataEntry 14 }

dclVsLCoEmissionPriority OBJECT-TYPE
   SYNTAX     Unsigned32 (0..2)
   ACCESS     read-only
   STATUS     mandatory
   DESCRIPTION
     "This attribute indicates the urgency with which packets on the path 
      are emitted by the trunks on the route. The originating end of the 
      connection selects the emissionPriority. EmissionPriority of zero 
      indicates the highest emission priority, while two indicates the 
      lowest emission priority. Packets with a higher emissionPriority (or 
      numerically less) are serviced and sent out before the packets of 
      lower emissionPriority (or numerically higher)."
::= { dclVsLCoPathDataEntry 15 }

dclVsLCoDiscardPriority OBJECT-TYPE
   SYNTAX     Unsigned32 (1..3)
   ACCESS     read-only
   STATUS     mandatory
   DESCRIPTION
     "This attribute indicates the importance of the packets on the 
      path.The originating end of the connection sets discardPriority. One 
      is used for paths carrying the most important traffic, and three is 
      used for paths carrying the least important traffic. Packets with 
      lower discardPriority(numerically lower) are discarded after 
      packets with a higher discardPriority(numerically higher)."
::= { dclVsLCoPathDataEntry 16 }

dclVsLCoPathType OBJECT-TYPE
   SYNTAX     INTEGER  {
                 normal(0),
                 manual(1),
                 forced(2) }
   ACCESS     read-only
   STATUS     mandatory
   DESCRIPTION
     "This attribute indicates whether the path for this PLC was 
      determined automatically or by static provisioning. Normal 
      pathTypes are selected automatically by Route Selector.The other 
      pathTypes are both manual pathTypes where the operator must 
      specify, through provisioning, a static route termed the manualPath. 
      A manual pathType connection is nearly identical to a normal path 
      type connection with the exception that the route is pre-provisioned. 
      For a manual pathType, bandwidth reservations are respected along 
      the path exactly as in a normal path. The last type, the forced 
      pathType, is also a manual path but regardless of the bandwidth 
      available the route is granted provided the trunks are operational 
      and there are sufficient Logical Channels (LChs).
      
      The forced pathType could result in over committing the reserved 
      bandwidth allowed on a trunk. A better way to achieve the effects of 
      a forced pathType is to use a manual pathType with setupPriority = 
      0 and holdingPriority = 0. In this manner the path will reserve 
      correct bandwidth and it will bump other paths if required while not 
      being bumped itself."
::= { dclVsLCoPathDataEntry 17 }

dclVsLCoRetryCount OBJECT-TYPE
   SYNTAX     Unsigned32 (0..255)
   ACCESS     read-only
   STATUS     mandatory
   DESCRIPTION
     "This attribute is the count of the number of times the path chosen 
      during route selection could not be instantiated. This count should 
      be three or below if the network is performing adequately. A high 
      value indicates that the route selection is often performed using an 
      out-of-date view of available network bandwidth and/or topology.
      This attribute will only increase at the calling end of the connection.
      This attribute is reset each time a path reconnects and stops 
      counting when it reaches its maximum value."
::= { dclVsLCoPathDataEntry 18 }

dclVsLCoPathFailureCount OBJECT-TYPE
   SYNTAX     Unsigned32 (0..65535)
   ACCESS     read-only
   STATUS     mandatory
   DESCRIPTION
     "This attribute is the count of the number of times the path has 
      successfully connected. It is set to zero the first time the path is up. 
      If a path fails anytime after connecting this count will be 
      incremented when the path is up again. Failed route requests do not 
      count in this statistic. See retryCount above. This attribute stops 
      counting at its maximum value."
::= { dclVsLCoPathDataEntry 19 }

dclVsLCoReasonForNoRoute OBJECT-TYPE
   SYNTAX     INTEGER  {
                 none(0),
                 destinationNameTooLong(1),
                 destinationNotSpecified(2),
                 unknownDestinationName(3),
                 incorrectDestination(4),
                 incorrectDestinationEndPoint(5),
                 unknownSource(6),
                 unknownDestination(7),
                 sameNode(8),
                 routeCostTooMuch(9),
                 routesDelayTooLong(10),
                 attributesNotMet(11),
                 anError(12),
                 attributeProfileProblem(13),
                 manualPathIndexProblem(14) }
   ACCESS     read-only
   STATUS     mandatory
   DESCRIPTION
     "This attribute is the route selection's reasonForNoRoute and 
      provides a brief reason for which a route was not selected. The 
      reasons are essentially self-explanatory. Perhaps two reasons for no 
      route require some explanation. The reason 
      unknownRemoteNodeName is issued when the remote node name 
      is not in the topological database. The reason plcAttributesNotMet 
      is issued when there is no network connectivity at a level specified 
      by the PLC attributes. This reason is also issued when there is no 
      physical connectivity between two end nodes."
   DEFVAL     { none }
::= { dclVsLCoPathDataEntry 20 }

dclVsLCoLastTearDownReason OBJECT-TYPE
   SYNTAX     INTEGER  {
                 none(0),
                 normalShutDown(1),
                 insufficientTxLcOrBandwidth(2),
                 insufficientRxLcOrBandwidth(3),
                 trunkFailure(4),
                 trunkCardFailure(5),
                 operatorForced(6),
                 lostLcnClash(7),
                 networkCongestion(8),
                 trunkNotFound(9),
                 farEndNotFound(10),
                 wrongModuleReached(11),
                 farEndBusy(12),
                 callLoopedBack(13),
                 unknownReason(14),
                 farEndNotReady(15),
                 remoteNameMismatch(16),
                 serviceTypeMismatch(17),
                 reconnectFromFarEnd(18),
                 bumped(19),
                 accessCardFailure(20),
                 optimized(21),
                 overrideRemoteName(22),
                 trunkOrFarEndDidNotSupportMode(23) }
   ACCESS     read-only
   STATUS     mandatory
   DESCRIPTION
     "This attribute reflects the last tear down reason for a connection 
      (LCo). In many cases this displays the reason for a momentary 
      service interruption. This attribute applies to the last path failure 
      only. If a path is no longer up, this may give an indication to the 
      reason that the path has failed. In many cases an alarm will also be 
      generated with more specific information. The following is a brief 
      description of the reasons:
      none - This path has no information for the teardown this is typical 
      of a path provisioned with no remoteName that has not been up.
      normalShutDown - This path has gone down due to normal call 
      termination.
      insufficientTxLcOrBandwidth - At present there is either no 
      available bandwidth or logical channel numbers available on one or 
      more of the trunks for this path in the transmit direction.
      insufficientRxLcOrBandwidth - At present there is either no 
      available bandwidth or logical channel numbers available on one or 
      more of the trunks for this path in the receive direction.
      trunkFailure- A trunk on the path has failed or has gone down due 
      to a provisioning change of a critical attribute.
      trunkCardFailure- A trunk FP card has failed along the path.
      accessCardFailure- The FP on which the peer access service was 
      running has failed.
      operatorForced- The path has terminated due to the operator 
      locking a trunk along the path.
      lostLcnClash- The path has terminated because the PA's at both 
      ends of an intermediate trunk have allocated the same LC to 
      different calls. When this happens both calls must go down and then 
      try to come up again a fraction of a second later (effectively 
      ensuring that they will now be assigned different LC's). It is normal 
      to get the odd clash especially when the PA's usedLC is 
      approaching the PA's maxLC.
      networkCongestion - The path has failed due to control information 
      being lost and not recoverable.
      trunkNotFound - Occurs on a manual path usually. Check for 
      trunks not up or names provisioned incorrectly.
      farEndNotFound - The far end is not provisioned or is not up. 
      Check remote Name.
      wrongModuleReached - This may occur on a manual path. Check 
      provisioning for correct trunk and service names. For a normal 
      path, the network Topology may be changing check remoteName.
      farEndBusy - The far end has been reached but it is busy. Check 
      remoteName and remote end provisioning.
      callLoopedBack - This LCo is provisioned to call itself. Re-
      provision since this is invalid.
      unknownReason - The failure was not resolved.
      farEndNotReady - The remote end was reached but the connection 
      was refused due to the remote end not being enabled.
      remoteNameMismatch - The remote end has alarmed and rejected 
      this setup due to remoteName provisioning.
      serviceTypeMismatch - The remote Service Type does not match 
      this service type. Check provisioning.
      reconnectFromFarEnd - The remote end re-established this 
      connection. Check the remote end lastTearDownReason to 
      determine the real reason.
      bumped - Another call bumped this path from a trunk to get 
      bandwidth (or an LC) which it required to come up. This other path 
      had a higher setupPriority than this path's holdingPriority hence it 
      was allowed to steal the bandwidth (or LC) from this path.
      optimized - This call has been rerouted due to the optimization 
      feature. The call is still active this just indicates why the path 
      changed.
      trunkOrFarEndDidNotSupportMode - This call was unable to 
      complete because a mode required by the service was not supported 
      by one of the trunks the route went through or by the far end service 
      it connected to. Currently the only mode that this applies to is the 
      map/mux mode on TRUNK PA ATM component. Map mode was 
      required by the application (CES/FrAtm etc.) but was not available 
      on the TRUNK PA ATM component through which the call was 
      routed or the far end CES/FrAtm component did not specify the 
      same mode."
   DEFVAL     { none }
::= { dclVsLCoPathDataEntry 21 }

dclVsLCoPathFailureAction OBJECT-TYPE
   SYNTAX     INTEGER  {
                 disconnectConnection(0),
                 reRoutePath(1) }
   ACCESS     read-only
   STATUS     mandatory
   DESCRIPTION
     "This attribute displays whether the application is set to tolerate 
      momentary interruption of a path while a new path is selected. If 
      disconnectConnection is displayed, the application is informed as 
      soon as possible about a failure by disconnection. If the attribute 
      displays reRoutePath, the path may attempt an immediate reroute, 
      provided the failure is a recoverable failure. If rerouting fails the 
      application is informed of the failure. 
      With this option set to reRoutePath the LCo may wait up to 30 
      seconds before informing the service of complete disconnection in 
      order to allow both ends to attempt to reconnect. Note that if PLC 
      components are different at both ends only the calling end is 
      allowed to reconnect.
      
      All pathTypes respect this attribute. Also on a manualPath with 
      both ends provisioned with independent paths (at least with respect 
      to the failure) this option will have the desired effect that the path is 
      rerouted without complete disconnection at both ends"
::= { dclVsLCoPathDataEntry 22 }

dclVsLCoBumpPreference OBJECT-TYPE
   SYNTAX     INTEGER  {
                 bumpWhenNecessary(0),
                 bumpToObtainBestRoute(1) }
   ACCESS     read-only
   STATUS     mandatory
   DESCRIPTION
     "This attribute specifies when bumping will occur during route 
      selection process. Bumping may occur when necessary or always. It 
      will be necessary for a connection to bump if there is not enough 
      resources for the connection to be established and these resources 
      are occupied by a connection whose setupPriority is lower 
      (numerically higher) than the connection's setupPriority. A 
      connection may also always bump in order to obtain the best route."
::= { dclVsLCoPathDataEntry 23 }

dclVsLCoOptimization OBJECT-TYPE
   SYNTAX     INTEGER  {
                 disabled(0),
                 enabled(1) }
   ACCESS     read-only
   STATUS     mandatory
   DESCRIPTION
     "This attribute is used to specify whether this connection should 
      attempt to optimize its path when requested by the routing PORS 
      component. Every path is as optimal as it can be when it is 
      established, but as network traffic patterns and configurations 
      change this path may no longer be as optimal as it could be. The 
      PORS connection manager on a module requests circuits to 
      optimize at the optimization interval."
::= { dclVsLCoPathDataEntry 24 }

dclVsLCoPathUpDateTime OBJECT-TYPE
   SYNTAX     EnterpriseDateAndTime (SIZE (0 | 19))
   ACCESS     read-only
   STATUS     mandatory
   DESCRIPTION
     "This is the time stamp when the current path was established or 
      reestablished."
::= { dclVsLCoPathDataEntry 25 }

dclVsLCoStatsTable OBJECT-TYPE
   SYNTAX     SEQUENCE OF DclVsLCoStatsEntry
   ACCESS     not-accessible
   STATUS     mandatory
   DESCRIPTION
     "This group contains the operational statistics attributes for the path 
      oriented LCo."
::= { dclVsLCo 11 }

dclVsLCoStatsEntry OBJECT-TYPE
   SYNTAX     DclVsLCoStatsEntry
   ACCESS     not-accessible
   STATUS     mandatory
   DESCRIPTION
     "An entry in the dclVsLCoStatsTable."
   INDEX {
      dclIndex,
      dclVsIndex,
      dclVsLCoIndex }
::= { dclVsLCoStatsTable 1 }

DclVsLCoStatsEntry ::= SEQUENCE {
   dclVsLCoPktsToNetwork
      PassportCounter64,
   dclVsLCoBytesToNetwork
      PassportCounter64,
   dclVsLCoPktsFromNetwork
      PassportCounter64,
   dclVsLCoBytesFromNetwork
      PassportCounter64 }

dclVsLCoPktsToNetwork OBJECT-TYPE
   SYNTAX     PassportCounter64 
   ACCESS     read-only
   STATUS     mandatory
   DESCRIPTION
     "This attribute counts the number of packets transmitted to the 
      network over this Logical Connection."
::= { dclVsLCoStatsEntry 1 }

dclVsLCoBytesToNetwork OBJECT-TYPE
   SYNTAX     PassportCounter64 
   ACCESS     read-only
   STATUS     mandatory
   DESCRIPTION
     "This attribute counts the number of bytes sent to the network over 
      this Logical Connection."
::= { dclVsLCoStatsEntry 2 }

dclVsLCoPktsFromNetwork OBJECT-TYPE
   SYNTAX     PassportCounter64 
   ACCESS     read-only
   STATUS     mandatory
   DESCRIPTION
     "This attribute counts the number of packets received from the 
      remote LCo via the network."
::= { dclVsLCoStatsEntry 3 }

dclVsLCoBytesFromNetwork OBJECT-TYPE
   SYNTAX     PassportCounter64 
   ACCESS     read-only
   STATUS     mandatory
   DESCRIPTION
     "This attribute counts the number of bytes received from the remote 
      LCo via the network."
::= { dclVsLCoStatsEntry 4 }

dclVsLCoPathTable OBJECT-TYPE
   SYNTAX     SEQUENCE OF DclVsLCoPathEntry
   ACCESS     not-accessible
   STATUS     mandatory
   DESCRIPTION
     "This attribute contains the trunk component names over which the 
      path has been instantiated and the remote end point name 
      terminating the path."
::= { dclVsLCo 264 }

dclVsLCoPathEntry OBJECT-TYPE
   SYNTAX     DclVsLCoPathEntry
   ACCESS     not-accessible
   STATUS     mandatory
   DESCRIPTION
     "An entry in the dclVsLCoPathTable."
   INDEX {
      dclIndex,
      dclVsIndex,
      dclVsLCoIndex,
      dclVsLCoPathValue }
::= { dclVsLCoPathTable 1 }

DclVsLCoPathEntry ::= SEQUENCE {
   dclVsLCoPathValue
      AsciiString }

dclVsLCoPathValue OBJECT-TYPE
   SYNTAX     AsciiString (SIZE (0..40))
   ACCESS     read-only
   STATUS     mandatory
   DESCRIPTION
     "This variable represents both the value and the index for the
      dclVsLCoPathTable."
::= { dclVsLCoPathEntry 1 }




-- 
-- Version and Compliance statements
-- 



-- Object-Group Statement:
-- A list of all current accessible leaf objects.

-- OBJECTS { dclVsLCoPathUpDateTime,
--           dclVsLCoPktsFromNetwork,
--           dclVsFramerSilenceCells,
--           dclAlternateIdlePattern,
--           dclVsLCoRetryCount,
--           dclVsLCoEmissionPriority,
--           dclVsFramerComponentName,
--           dclVsLCoComponentName,
--           dclFramerUsageState,
--           dcmeProfileSpeechHangoverTime,
--           dclVsComponentName,
--           dcmeProfileEchoCancellation,
--           dcmeAlarmTimeInterval,
--           dclVsFramerFrmUnderRuns,
--           dclUsageState,
--           dclVsLCoBytesToNetwork,
--           dcmeProfileMaxModemFaxG711G726Rate,
--           dclVsReceivedAbBits,
--           dclVsLCoPktsToNetwork,
--           dclFramerInterfaceName,
--           dcmeProfileIngressAudioGain,
--           dclVsLCoDiscardPriority,
--           dclFramerOperationalState,
--           dcmeProfileV17EncodedAsG711G726,
--           dclActive3kHzCalls,
--           dclVsFramerVfpDebugStorageType,
--           dclOperationalState,
--           dcmeProfileRequiredSecurity,
--           dclVsFramerNegotiatedV17AsG711G726,
--           dcmePreestablishedConnections,
--           dclDnaDataNetworkAddress,
--           dcmeTrmSignalChangeInterval,
--           dcmeDLinksRowStatus,
--           dcmeProfileEgressAudioGain,
--           dclVsLCoReasonForNoRoute,
--           dclVsLCoRequiredSecurity,
--           dclVsLCoPathFailureCount,
--           dclRejected64kCalls,
--           dclVsLCoCostMetric,
--           dclVsFramerNegotiatedDtmfRegeneration,
--           dcmeProfileMinModemFaxG711G726Rate,
--           dclVsFramerModemFaxCells,
--           dcmeDLinksValue,
--           dclRejectedSpeechCalls,
--           dcmeTrmThreshold,
--           dclVsFramerVfpDebugComponentName,
--           dclVsFramerNRatesValue,
--           dclVsFramerFrmToNetworkValue,
--           dcmeProfileMaxFaxRelayRate,
--           dcmeProfileMaxVoiceBitRate,
--           dclVsLCoHoldingPriority,
--           dclTotal3kHzCalls,
--           dclVsFramerStorageType,
--           dclRemoteNpi,
--           dclVsLCoBytesFromNetwork,
--           dclVsLCoPathFailureAction,
--           dclVsFramerPcmCaptureRowStatus,
--           dclVsStorageType,
--           dclTransmittedTrmSignal,
--           dclDnaRowStatus,
--           dclVsVsType,
--           dclVsFramerAdminState,
--           dclVsLCoEnd,
--           dclVsLCoRowStatus,
--           dcmeProfileMinVoiceBitRate,
--           dclVsFramerRowStatus,
--           dclVsFramerCurrentRate,
--           dcmeProfileModemFaxSpeechDiscrim,
--           dcmeOperationalState,
--           dclVsFramerFaxRelayCells,
--           dcmeComponentName,
--           dclVsFramerNegotiatedTandemPassThrough,
--           dcmeProfileStorageType,
--           dclVsAdminState,
--           dcmeProfileComfortNoiseCap,
--           dclVsFramerTotalCells,
--           dcmeProfileInsertedOutputDelay,
--           dclVsLCoDelayMetric,
--           dclVsFramerFaxIdleCells,
--           dclActive64kCalls,
--           dclVsRowStatus,
--           dcmeProfileSetupPriority,
--           dclVsFramerNEncodingValue,
--           dclDcme,
--           dclIdlePattern,
--           dclActiveSpeechCalls,
--           dcmeProfileOptimization,
--           dclVsTransmittedAbBits,
--           dcmeProfileBumpPreference,
--           dclVsFramerUsageState,
--           dclVsFramerFrmFromNetworkValue,
--           dclInvalidTrmSignals,
--           dclVsUsageState,
--           dclRemoteDna,
--           dcmeProfileSilenceSuppressionFactor,
--           dclVsFramerFrmLostInNetwork,
--           dcmeProfileRowStatus,
--           dcmeSpeechAlarmThreshold,
--           dclVsLCoStorageType,
--           dclVsFramerInterfaceName,
--           dcmeMaxUnrestricted64kCalls,
--           dclFramerComponentName,
--           dclVsOperationalState,
--           dcmeProfileEmissionPriority,
--           dclVsFramerOperationalState,
--           dclVsFramerFrmDumped,
--           dcmeProfileModemFaxEncoding,
--           dclComponentName,
--           dclVsFramerLrcErrors,
--           dcmeCommentText,
--           dclCommentText,
--           dclTotal64kCalls,
--           dclVsLCoRequiredRxBandwidth,
--           dcmeProfileSilenceSuppression,
--           dclVsFramerMvpDebugStorageType,
--           dclDnaNumberingPlanIndicator,
--           dclVsFramerOpTptStatus,
--           dclTotalSpeechCalls,
--           dclVsLCoRequiredTxBandwidth,
--           dcmeProfileRequiredCustomerParm,
--           dclVsFramerPcmCaptureComponentName,
--           dcmeProfileComponentName,
--           dclVsLCoOverrideRemoteName,
--           dcmeProfileDiscardPriority,
--           dclVsFramerNegotiatedSilenceSuppression,
--           dcmeStorageType,
--           dclVsLCoPathValue,
--           dclVsLCoRequiredCustomerParameter,
--           dclVsFramerOpCurrentEncoding,
--           dcmeProfileFaxIdleSuppressionG711G726,
--           dclVsFramerNegotiatedFisG711G726,
--           dclVsLCoState,
--           dclVsFramerMvpDebugComponentName,
--           dcmeAudio3kHzAlarmThreshold,
--           dclVsTotalCalls,
--           dclDnaComponentName,
--           dclVsLCoLastTearDownReason,
--           dclVsFramerAudioCells,
--           dcmeAdminState,
--           dclRowStatus,
--           dclVsLCoPermittedTrunkTypes,
--           dcmeTrm64kNotAvailable,
--           dclVsLCoRoundTripDelay,
--           dcmeProfileVoiceTrafficOptimization,
--           dclVsTotalCallSeconds,
--           dcmeProfilePathAttributeToMinimize,
--           dcmeRowStatus,
--           dclVsCallType,
--           dclVsLCoOptimization,
--           dclVsLCoBumpPreference,
--           dclVsLCoRequiredTrafficType,
--           dclVsInvalidAbBits,
--           dcmeProfilePathFailureAction,
--           dclVsLCoSetupPriority,
--           dclFramerStorageType,
--           dcmeProfileRequiredTrafficType,
--           dcmeProfileHoldingPriority,
--           dcmeProfileVoiceEncoding,
--           dcmeProfileMaximumAcceptableDelay,
--           dclVsStatus,
--           dcmeProfileMaximumAcceptableCost,
--           dclStorageType,
--           dcmeUsageState,
--           dclVsFramerMvpDebugRowStatus,
--           dclVsFramerVfpDebugRowStatus,
--           dclRejected3kHzCalls,
--           dclVsFramerPcmCaptureStorageType,
--           dcmeProfilePermittedTrunkTypes,
--           dclReceivedTrmSignal,
--           dclVsLCoPathType,
--           dclFramerAdminState,
--           dcmeUnrestricted64kAlarmThreshold,
--           dclDnaStorageType,
--           dcmeProfileDtmfRegeneration,
--           dclAdminState,
--           dclFramerRowStatus,
--           dcmeTrmSpeechNotAvailable,
--           dcmeActiveDcmeLinksValue }
-- STATUS  mandatory
-- DESCRIPTION
--   "A list of all current accessible leaf objects."

dcmeGroup OBJECT IDENTIFIER ::= { dcmeMIB 1 }
dcmeGroupBE OBJECT IDENTIFIER ::= { dcmeGroup 5 }
dcmeGroupBE01 OBJECT IDENTIFIER ::= { dcmeGroupBE 2 }
dcmeGroupBE01A OBJECT IDENTIFIER ::= { dcmeGroupBE01 2 }



-- Agent-Capabilities Statement:

-- PRODUCT-RELEASE "Passport Release 7.0 Dcme."
-- STATUS          mandatory
-- DESCRIPTION     "Dcme MIB: MIB Version BE01A,
--                  Software Version BG00S4C."
-- SUPPORTS        Nortel-Magellan-Passport-DcmeMIB
--    INCLUDES     { dcmeGroupBE01A }

dcmeCapabilities OBJECT IDENTIFIER ::= { dcmeMIB 3 }
dcmeCapabilitiesBE OBJECT IDENTIFIER ::= { dcmeCapabilities 5 }
dcmeCapabilitiesBE01 OBJECT IDENTIFIER ::= { dcmeCapabilitiesBE 2 }
dcmeCapabilitiesBE01A OBJECT IDENTIFIER ::= { dcmeCapabilitiesBE01 2 }





END
