Nortel-Magellan-Passport-VnsMIB
DEFINITIONS ::= BEGIN



IMPORTS

      OBJECT-TYPE
   FROM RFC-1212

      passportMIBs
   FROM Nortel-Magellan-Passport-UsefulDefinitionsMIB

      RowPointer,
      DisplayString,
      StorageType,
      RowStatus,
      PassportCounter64,
      InterfaceIndex,
      Integer32,
      Unsigned32
   FROM Nortel-Magellan-Passport-StandardTextualConventionsMIB

      Link,
      AsciiStringIndex
   FROM Nortel-Magellan-Passport-TextualConventionsMIB

      rtgIndex,
      rtg
   FROM Nortel-Magellan-Passport-BaseRoutingMIB;




-- LAST-UPDATED   "9702280000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     Vns Enterprise MIB."

vnsMIB OBJECT IDENTIFIER ::= { passportMIBs 20 }










-- Rtg Vns/<vnsName>
-- This component is provisioned on all Passport nodes that support 
-- VNS routing and is responsible for supporting routing between 
-- Passport nodes that are part of the same logical network. Each Vns 
-- component, on a single node, supports one logical network.
-- 
-- It is recommended that the name used to identify a Vns component 
-- on a node be the same as that used for Vns components on other 
-- nodes to support the same logical network. This allows the operator 
-- to more easily see which nodes support a particular logical network. 

rtgVns OBJECT IDENTIFIER ::= { rtg 3 }



rtgVnsRowStatusTable OBJECT-TYPE
   SYNTAX     SEQUENCE OF RtgVnsRowStatusEntry
   ACCESS     not-accessible
   STATUS     mandatory
   DESCRIPTION
     "This entry controls the addition and deletion of 
      rtgVns components."
::= { rtgVns 1 }

rtgVnsRowStatusEntry OBJECT-TYPE
   SYNTAX     RtgVnsRowStatusEntry
   ACCESS     not-accessible
   STATUS     mandatory
   DESCRIPTION
     "A single entry in the table represents a single 
      rtgVns component."
   INDEX {
      rtgIndex,
      rtgVnsIndex }
::= { rtgVnsRowStatusTable 1 }

RtgVnsRowStatusEntry ::= SEQUENCE {
   rtgVnsRowStatus
      RowStatus,
   rtgVnsComponentName
      DisplayString,
   rtgVnsStorageType
      StorageType,
   rtgVnsIndex
      AsciiStringIndex }

rtgVnsRowStatus OBJECT-TYPE
   SYNTAX     RowStatus 
   ACCESS     read-write
   STATUS     mandatory
   DESCRIPTION
     "This variable is used as the basis for SNMP naming of
      rtgVns components.
      These components can be added and deleted."
::= { rtgVnsRowStatusEntry 1 }

rtgVnsComponentName OBJECT-TYPE
   SYNTAX     DisplayString 
   ACCESS     read-only
   STATUS     mandatory
   DESCRIPTION
     "This variable provides the component's string name for
      use with the ASCII Console Interface"
::= { rtgVnsRowStatusEntry 2 }

rtgVnsStorageType OBJECT-TYPE
   SYNTAX     StorageType 
   ACCESS     read-only
   STATUS     mandatory
   DESCRIPTION
     "This variable represents the storage type value for the
      rtgVns tables."
::= { rtgVnsRowStatusEntry 4 }

rtgVnsIndex OBJECT-TYPE
   SYNTAX     AsciiStringIndex (SIZE (1..12))
   ACCESS     not-accessible
   STATUS     mandatory
   DESCRIPTION
     "This variable represents the index for the rtgVns tables."
::= { rtgVnsRowStatusEntry 10 }

rtgVnsProvTable OBJECT-TYPE
   SYNTAX     SEQUENCE OF RtgVnsProvEntry
   ACCESS     not-accessible
   STATUS     mandatory
   DESCRIPTION
     "This group contains the provisioning data for the Vns component. It 
      must be set to allow the logical network to function properly."
::= { rtgVns 10 }

rtgVnsProvEntry OBJECT-TYPE
   SYNTAX     RtgVnsProvEntry
   ACCESS     not-accessible
   STATUS     mandatory
   DESCRIPTION
     "An entry in the rtgVnsProvTable."
   INDEX {
      rtgIndex,
      rtgVnsIndex }
::= { rtgVnsProvTable 1 }

RtgVnsProvEntry ::= SEQUENCE {
   rtgVnsLogicalNetworkNumber
      Unsigned32,
   rtgVnsLinkToProtocolPort
      Link,
   rtgVnsMaximumTransmissionUnit
      Unsigned32,
   rtgVnsLoadSharing
      INTEGER,
   rtgVnsDiscardPriority
      Unsigned32,
   rtgVnsIlsForwarder
      Link }

rtgVnsLogicalNetworkNumber OBJECT-TYPE
   SYNTAX     Unsigned32 (2..2047)
   ACCESS     read-write
   STATUS     mandatory
   DESCRIPTION
     "This is the Logical Network Number (LNN) for the Vns component. 
      The LNN is used to identify the logical network that the Vns 
      component supports. Vns components, on different interconnected 
      nodes, provisioned with the same LNN are part of the same logical 
      network.
      
      The maximum number of logical networks that can be supported in 
      the entire network is 2047. The maximum number of logical 
      networks, and Vns components, supported on a single node is 126. 
      Each Vns component must be provisioned with a unique LNN on a 
      single node."
::= { rtgVnsProvEntry 1 }

rtgVnsLinkToProtocolPort OBJECT-TYPE
   SYNTAX     Link 
   ACCESS     read-write
   STATUS     mandatory
   DESCRIPTION
     "This is a link to a protocol port under the VirtualRouter component 
      that uses this logical network. This link, when used, causes the 
      VirtualNetworkingSystem to support a 'broadcast media' style 
      routing model in which all reachable nodes in the logical network 
      are available for use by the VirtualRouter and its subcomponents."
::= { rtgVnsProvEntry 2 }

rtgVnsMaximumTransmissionUnit OBJECT-TYPE
   SYNTAX     Unsigned32 (2048..65535)
   ACCESS     read-write
   STATUS     mandatory
   DESCRIPTION
     "This is the maximum transmission unit (MTU), in bytes, supported 
      by the VirtualNetworkingSystem. The MTU must be less than the 
      minimum MTU provisioned on any trunk in the network that is 
      supporting the LNN of this Vns component."
   DEFVAL     { 2048 }
::= { rtgVnsProvEntry 3 }

rtgVnsLoadSharing OBJECT-TYPE
   SYNTAX     INTEGER  {
                 disabled(0),
                 enabled(1) }
   ACCESS     read-write
   STATUS     mandatory
   DESCRIPTION
     "This attribute specifies whether VNS will use the loadSharing 
      feature. If its value is disabled, VNS will send the packets from a 
      given source to a given destination over only one of the preferred 
      links in a link group. If loadSharing is enabled, VNS will send 
      packets of a data stream over all the preferred links in a link group. 
      Note that setting loadSharing to enabled may cause packets to be 
      misordered."
   DEFVAL     { disabled }
::= { rtgVnsProvEntry 4 }

rtgVnsDiscardPriority OBJECT-TYPE
   SYNTAX     Unsigned32 (0..3)
   ACCESS     read-write
   STATUS     obsolete
   DESCRIPTION
     "This attribute specifies the importance of the packets of VNS. Zero 
      (0) is used the most important traffic, and three (3) is used for the 
      least important traffic. In times of congestion, the discardPriority is 
      used by packet forwarding on the VNS to determine which packets 
      are discarded first to reduce the load. Packets with a higher 
      discardPriority (or numerically less) are discarded after packets 
      with a lower discardPriority (or numerically higher)."
   DEFVAL     { 2 }
::= { rtgVnsProvEntry 5 }

rtgVnsIlsForwarder OBJECT-TYPE
   SYNTAX     Link 
   ACCESS     read-write
   STATUS     mandatory
   DESCRIPTION
     "This attribute specifies the IlsForwarder component this VNS 
      component is using. The IlsForwarder component is used to assist 
      forwarding VNS traffic that comes in from ATM logical trunks."
::= { rtgVnsProvEntry 6 }

rtgVnsIfEntryTable OBJECT-TYPE
   SYNTAX     SEQUENCE OF RtgVnsIfEntryEntry
   ACCESS     not-accessible
   STATUS     mandatory
   DESCRIPTION
     "This group contains the provisionable attributes for the ifEntry."
::= { rtgVns 11 }

rtgVnsIfEntryEntry OBJECT-TYPE
   SYNTAX     RtgVnsIfEntryEntry
   ACCESS     not-accessible
   STATUS     mandatory
   DESCRIPTION
     "An entry in the rtgVnsIfEntryTable."
   INDEX {
      rtgIndex,
      rtgVnsIndex }
::= { rtgVnsIfEntryTable 1 }

RtgVnsIfEntryEntry ::= SEQUENCE {
   rtgVnsIfAdminStatus
      INTEGER,
   rtgVnsIfIndex
      InterfaceIndex }

rtgVnsIfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { rtgVnsIfEntryEntry 1 }

rtgVnsIfIndex OBJECT-TYPE
   SYNTAX     InterfaceIndex (1..65535)
   ACCESS     read-only
   STATUS     mandatory
   DESCRIPTION
     "This is the index for the IfEntry. Its value is automatically initialized 
      during the provisioning process."
::= { rtgVnsIfEntryEntry 2 }

rtgVnsCidDataTable OBJECT-TYPE
   SYNTAX     SEQUENCE OF RtgVnsCidDataEntry
   ACCESS     not-accessible
   STATUS     mandatory
   DESCRIPTION
     "This group contains the attribute for a component's Customer 
      Identifier (CID). Refer to the attribute description for a detailed 
      explanation of CIDs."
::= { rtgVns 12 }

rtgVnsCidDataEntry OBJECT-TYPE
   SYNTAX     RtgVnsCidDataEntry
   ACCESS     not-accessible
   STATUS     mandatory
   DESCRIPTION
     "An entry in the rtgVnsCidDataTable."
   INDEX {
      rtgIndex,
      rtgVnsIndex }
::= { rtgVnsCidDataTable 1 }

RtgVnsCidDataEntry ::= SEQUENCE {
   rtgVnsCustomerIdentifier
      Unsigned32 }

rtgVnsCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { rtgVnsCidDataEntry 1 }

rtgVnsStateTable OBJECT-TYPE
   SYNTAX     SEQUENCE OF RtgVnsStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { rtgVns 14 }

rtgVnsStateEntry OBJECT-TYPE
   SYNTAX     RtgVnsStateEntry
   ACCESS     not-accessible
   STATUS     mandatory
   DESCRIPTION
     "An entry in the rtgVnsStateTable."
   INDEX {
      rtgIndex,
      rtgVnsIndex }
::= { rtgVnsStateTable 1 }

RtgVnsStateEntry ::= SEQUENCE {
   rtgVnsAdminState
      INTEGER,
   rtgVnsOperationalState
      INTEGER,
   rtgVnsUsageState
      INTEGER }

rtgVnsAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { rtgVnsStateEntry 1 }

rtgVnsOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { rtgVnsStateEntry 2 }

rtgVnsUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { rtgVnsStateEntry 3 }

rtgVnsOperTable OBJECT-TYPE
   SYNTAX     SEQUENCE OF RtgVnsOperEntry
   ACCESS     not-accessible
   STATUS     mandatory
   DESCRIPTION
     "This group of attributes provides information about the functioning 
      of the Vns component."
::= { rtgVns 15 }

rtgVnsOperEntry OBJECT-TYPE
   SYNTAX     RtgVnsOperEntry
   ACCESS     not-accessible
   STATUS     mandatory
   DESCRIPTION
     "An entry in the rtgVnsOperTable."
   INDEX {
      rtgIndex,
      rtgVnsIndex }
::= { rtgVnsOperTable 1 }

RtgVnsOperEntry ::= SEQUENCE {
   rtgVnsReportedThroughputMetric
      Unsigned32 }

rtgVnsReportedThroughputMetric OBJECT-TYPE
   SYNTAX     Unsigned32 (0..2147483647)
   ACCESS     read-only
   STATUS     mandatory
   DESCRIPTION
     "This is the throughput metric that has been calculated and reported 
      to the VirtualRouter component for use by its routing protocol 
      subcomponents.
      
      A value of 2147483647 means infinity and implies that either 
      throughput routing is not available or supported on the logical 
      network."
::= { rtgVnsOperEntry 1 }

rtgVnsFwdStatsTable OBJECT-TYPE
   SYNTAX     SEQUENCE OF RtgVnsFwdStatsEntry
   ACCESS     not-accessible
   STATUS     mandatory
   DESCRIPTION
     "This group of attributes provides combined statistics of the traffic 
      handled by this Vns component on all LPs. They are presented in 3 
      broad classes: unicast, multicast, and total (unicast and multicast 
      combined)."
::= { rtgVns 16 }

rtgVnsFwdStatsEntry OBJECT-TYPE
   SYNTAX     RtgVnsFwdStatsEntry
   ACCESS     not-accessible
   STATUS     mandatory
   DESCRIPTION
     "An entry in the rtgVnsFwdStatsTable."
   INDEX {
      rtgIndex,
      rtgVnsIndex }
::= { rtgVnsFwdStatsTable 1 }

RtgVnsFwdStatsEntry ::= SEQUENCE {
   rtgVnsUniRxPkts
      PassportCounter64,
   rtgVnsUniRxBytes
      PassportCounter64,
   rtgVnsUniRxDiscPkts
      PassportCounter64,
   rtgVnsUniTxPkts
      PassportCounter64,
   rtgVnsUniTxBytes
      PassportCounter64,
   rtgVnsUniTxDiscPkts
      PassportCounter64,
   rtgVnsMultiRxPkts
      PassportCounter64,
   rtgVnsMultiRxBytes
      PassportCounter64,
   rtgVnsMultiRxDiscPkts
      PassportCounter64,
   rtgVnsMultiTxPkts
      PassportCounter64,
   rtgVnsMultiTxBytes
      PassportCounter64,
   rtgVnsMultiTxDiscPkts
      PassportCounter64,
   rtgVnsTotalRxPkts
      PassportCounter64,
   rtgVnsTotalRxBytes
      PassportCounter64,
   rtgVnsTotalRxDiscPkts
      PassportCounter64,
   rtgVnsTotalTxPkts
      PassportCounter64,
   rtgVnsTotalTxBytes
      PassportCounter64,
   rtgVnsTotalTxDiscPkts
      PassportCounter64 }

rtgVnsUniRxPkts OBJECT-TYPE
   SYNTAX     PassportCounter64 
   ACCESS     read-only
   STATUS     mandatory
   DESCRIPTION
     "This attribute counts the unicast packets received by this Vns 
      component. The counter wraps around to zero when the maximum 
      value is reached."
::= { rtgVnsFwdStatsEntry 1 }

rtgVnsUniRxBytes OBJECT-TYPE
   SYNTAX     PassportCounter64 
   ACCESS     read-only
   STATUS     mandatory
   DESCRIPTION
     "This attribute counts the unicast bytes received by this Vns 
      component. The counter wraps around to zero when the maximum 
      value is reached."
::= { rtgVnsFwdStatsEntry 2 }

rtgVnsUniRxDiscPkts OBJECT-TYPE
   SYNTAX     PassportCounter64 
   ACCESS     read-only
   STATUS     mandatory
   DESCRIPTION
     "This attribute counts the unicast packets received and discarded by 
      this Vns component. (For example, a received VNS packet may be 
      discarded if its Time-to-Live counter has expired.) Packets counted 
      here are not counted in uniRxPkts. The counter wraps around to 
      zero when the maximum value is reached."
::= { rtgVnsFwdStatsEntry 3 }

rtgVnsUniTxPkts OBJECT-TYPE
   SYNTAX     PassportCounter64 
   ACCESS     read-only
   STATUS     mandatory
   DESCRIPTION
     "This attribute counts the unicast packets transmitted by this Vns 
      component. The counter wraps around to zero when the maximum 
      value is reached."
::= { rtgVnsFwdStatsEntry 4 }

rtgVnsUniTxBytes OBJECT-TYPE
   SYNTAX     PassportCounter64 
   ACCESS     read-only
   STATUS     mandatory
   DESCRIPTION
     "This attribute counts the unicast bytes transmitted by this Vns 
      component. The counter wraps around to zero when the maximum 
      value is reached."
::= { rtgVnsFwdStatsEntry 5 }

rtgVnsUniTxDiscPkts OBJECT-TYPE
   SYNTAX     PassportCounter64 
   ACCESS     read-only
   STATUS     mandatory
   DESCRIPTION
     "This attribute counts the unicast packets this Vns component was 
      expected to transmit, but had to discard. (For example, VNS packets 
      may be discarded because there is no route to the given destination.) 
      Packets counted here are not counted in uniTxPkts. The counter 
      wraps around to zero when the maximum value is reached."
::= { rtgVnsFwdStatsEntry 6 }

rtgVnsMultiRxPkts OBJECT-TYPE
   SYNTAX     PassportCounter64 
   ACCESS     read-only
   STATUS     mandatory
   DESCRIPTION
     "This attribute counts the multicast packets received by this Vns 
      component. The counter wraps around to zero when the maximum 
      value is reached."
::= { rtgVnsFwdStatsEntry 7 }

rtgVnsMultiRxBytes OBJECT-TYPE
   SYNTAX     PassportCounter64 
   ACCESS     read-only
   STATUS     mandatory
   DESCRIPTION
     "This attribute counts the multicast bytes received by this Vns 
      component. The counter wraps around to zero when the maximum 
      value is reached."
::= { rtgVnsFwdStatsEntry 8 }

rtgVnsMultiRxDiscPkts OBJECT-TYPE
   SYNTAX     PassportCounter64 
   ACCESS     read-only
   STATUS     mandatory
   DESCRIPTION
     "This attribute counts the multicast packets received and discarded 
      by this Vns component. (For example, a received VNS packet may 
      be discarded if its Time-to-Live counter has expired.) Packets 
      counted here are not counted in multiRxPkts. The counter wraps 
      around to zero when the maximum value is reached."
::= { rtgVnsFwdStatsEntry 9 }

rtgVnsMultiTxPkts OBJECT-TYPE
   SYNTAX     PassportCounter64 
   ACCESS     read-only
   STATUS     mandatory
   DESCRIPTION
     "This attribute counts the multicast packets transmitted by this Vns 
      component. The counter wraps around to zero when the maximum 
      value is reached."
::= { rtgVnsFwdStatsEntry 10 }

rtgVnsMultiTxBytes OBJECT-TYPE
   SYNTAX     PassportCounter64 
   ACCESS     read-only
   STATUS     mandatory
   DESCRIPTION
     "This attribute counts the multicast bytes transmitted by this Vns 
      component. The counter wraps around to zero when the maximum 
      value is reached."
::= { rtgVnsFwdStatsEntry 11 }

rtgVnsMultiTxDiscPkts OBJECT-TYPE
   SYNTAX     PassportCounter64 
   ACCESS     read-only
   STATUS     mandatory
   DESCRIPTION
     "This attribute counts the multicast packets this Vns component was 
      expected to transmit, but had to discard. (For example, VNS packets 
      may be discarded because there is no route to the given destination.) 
      Packets counted here are not counted in multiTxPkts. The counter 
      wraps around to zero when the maximum value is reached."
::= { rtgVnsFwdStatsEntry 12 }

rtgVnsTotalRxPkts OBJECT-TYPE
   SYNTAX     PassportCounter64 
   ACCESS     read-only
   STATUS     mandatory
   DESCRIPTION
     "This attribute gives the total count of packets received by this Vns 
      component. The counter wraps around to zero when the maximum 
      value is reached."
::= { rtgVnsFwdStatsEntry 13 }

rtgVnsTotalRxBytes OBJECT-TYPE
   SYNTAX     PassportCounter64 
   ACCESS     read-only
   STATUS     mandatory
   DESCRIPTION
     "This attribute gives the total count of bytes received by this Vns 
      component. The counter wraps around to zero when the maximum 
      value is reached."
::= { rtgVnsFwdStatsEntry 14 }

rtgVnsTotalRxDiscPkts OBJECT-TYPE
   SYNTAX     PassportCounter64 
   ACCESS     read-only
   STATUS     mandatory
   DESCRIPTION
     "This attribute gives the total count of packets received and discarded 
      by this Vns component. (For example, a received VNS packet may 
      be discarded if its Time-to-Live counter has expired.) Packets 
      counted here are not counted in totalRxPkts. The counter wraps 
      around to zero when the maximum value is reached."
::= { rtgVnsFwdStatsEntry 15 }

rtgVnsTotalTxPkts OBJECT-TYPE
   SYNTAX     PassportCounter64 
   ACCESS     read-only
   STATUS     mandatory
   DESCRIPTION
     "This attribute gives the total count of packets transmitted by this 
      Vns component. The counter wraps around to zero when the 
      maximum value is reached."
::= { rtgVnsFwdStatsEntry 16 }

rtgVnsTotalTxBytes OBJECT-TYPE
   SYNTAX     PassportCounter64 
   ACCESS     read-only
   STATUS     mandatory
   DESCRIPTION
     "This attribute gives the total count of bytes transmitted by this Vns 
      component. The counter wraps around to zero when the maximum 
      value is reached."
::= { rtgVnsFwdStatsEntry 17 }

rtgVnsTotalTxDiscPkts OBJECT-TYPE
   SYNTAX     PassportCounter64 
   ACCESS     read-only
   STATUS     mandatory
   DESCRIPTION
     "This attribute gives the total count of packets this Vns component 
      was expected to transmit, but had to discard. (For example, VNS 
      packets may be discarded because there is no route to the given 
      destination.) Packets counted here are not counted in totalTxPkts. 
      The counter wraps around to zero when the maximum value is 
      reached."
::= { rtgVnsFwdStatsEntry 18 }

-- 
-- *** THIS SUBTREE CURRENTLY NOT IMPLEMENTED ***
-- 

-- Routing Vns/<vnsName> Node/<nodeId>
-- This component displays information about a node reachable in the 
-- logical network. It is used to display the metrics and neighbour link 
-- group(s) for each class of service path to a destination node.

rtgVnsNode OBJECT IDENTIFIER ::= { rtgVns 2 }



rtgVnsNodeRowStatusTable OBJECT-TYPE
   SYNTAX     SEQUENCE OF RtgVnsNodeRowStatusEntry
   ACCESS     not-accessible
   STATUS     mandatory
   DESCRIPTION
     "*** THIS TABLE CURRENTLY NOT IMPLEMENTED ***

      This entry controls the addition and deletion of 
      rtgVnsNode components."
::= { rtgVnsNode 1 }

rtgVnsNodeRowStatusEntry OBJECT-TYPE
   SYNTAX     RtgVnsNodeRowStatusEntry
   ACCESS     not-accessible
   STATUS     mandatory
   DESCRIPTION
     "A single entry in the table represents a single 
      rtgVnsNode component."
   INDEX {
      rtgIndex,
      rtgVnsIndex,
      rtgVnsNodeIndex }
::= { rtgVnsNodeRowStatusTable 1 }

RtgVnsNodeRowStatusEntry ::= SEQUENCE {
   rtgVnsNodeRowStatus
      RowStatus,
   rtgVnsNodeComponentName
      DisplayString,
   rtgVnsNodeStorageType
      StorageType,
   rtgVnsNodeIndex
      Integer32 }

rtgVnsNodeRowStatus OBJECT-TYPE
   SYNTAX     RowStatus 
   ACCESS     read-only
   STATUS     mandatory
   DESCRIPTION
     "This variable is used as the basis for SNMP naming of
      rtgVnsNode components.
      These components cannot be added nor deleted."
::= { rtgVnsNodeRowStatusEntry 1 }

rtgVnsNodeComponentName OBJECT-TYPE
   SYNTAX     DisplayString 
   ACCESS     read-only
   STATUS     mandatory
   DESCRIPTION
     "This variable provides the component's string name for
      use with the ASCII Console Interface"
::= { rtgVnsNodeRowStatusEntry 2 }

rtgVnsNodeStorageType OBJECT-TYPE
   SYNTAX     StorageType 
   ACCESS     read-only
   STATUS     mandatory
   DESCRIPTION
     "This variable represents the storage type value for the
      rtgVnsNode tables."
::= { rtgVnsNodeRowStatusEntry 4 }

rtgVnsNodeIndex OBJECT-TYPE
   SYNTAX     Integer32 (1..4095)
   ACCESS     not-accessible
   STATUS     mandatory
   DESCRIPTION
     "This variable represents the index for the rtgVnsNode tables."
::= { rtgVnsNodeRowStatusEntry 10 }

rtgVnsNodeOperTable OBJECT-TYPE
   SYNTAX     SEQUENCE OF RtgVnsNodeOperEntry
   ACCESS     not-accessible
   STATUS     mandatory
   DESCRIPTION
     "*** THIS TABLE CURRENTLY NOT IMPLEMENTED ***

      This group of attributes is maintained by the Vns component to 
      provide information about the Nodes reachable in the logical 
      network. The data in this group specifies a row in the Node 
      component."
::= { rtgVnsNode 10 }

rtgVnsNodeOperEntry OBJECT-TYPE
   SYNTAX     RtgVnsNodeOperEntry
   ACCESS     not-accessible
   STATUS     mandatory
   DESCRIPTION
     "An entry in the rtgVnsNodeOperTable."
   INDEX {
      rtgIndex,
      rtgVnsIndex,
      rtgVnsNodeIndex }
::= { rtgVnsNodeOperTable 1 }

RtgVnsNodeOperEntry ::= SEQUENCE {
   rtgVnsNodeMetric
      Unsigned32,
   rtgVnsNodeNextHopLinkGroup1
      RowPointer,
   rtgVnsNodeNextHopLinkGroup2
      RowPointer }

rtgVnsNodeMetric OBJECT-TYPE
   SYNTAX     Unsigned32 (0..2147483647)
   ACCESS     read-only
   STATUS     mandatory
   DESCRIPTION
     "The minimum metric, for the throughput Class of Service (COS), to 
      the destination Node. The metric associated with a path is computed 
      by the routing system based on the sum of the COS metrics 
      associated with the links in the path to the destination. A path with a 
      lower metric value is preferable to one with a higher value as it is 
      associated with the best COS attribute facilities. The metric 
      displayed is that of the best path(s).
      
      A metric value of 2147483647 means the Node is unreachable. A 
      value of 0 indicates that no cost is associated with the path to the 
      destination. This would be the case for the local node's Id."
::= { rtgVnsNodeOperEntry 1 }

rtgVnsNodeNextHopLinkGroup1 OBJECT-TYPE
   SYNTAX     RowPointer 
   ACCESS     read-only
   STATUS     mandatory
   DESCRIPTION
     "The first possible link group available that can be used to reach a 
      neighbour which is the next hop in the path to the destination Node 
      for the throughput Class of Service (COS). VNS traffic is routed 
      deterministically across the links in up to two link groups, when 
      available. The link groups selected are those associated with 
      minimum metric COS paths to the destination. If two link groups 
      are in use then the metric of the paths associated with each are 
      identical.
      
      If no link groups are listed then the destination is not reachable 
      (except in the case of the local node's Id).
      
      Link group instances are managed by the TransportResource 
      component. Further information about the links in the group can be 
      obtained from it."
::= { rtgVnsNodeOperEntry 2 }

rtgVnsNodeNextHopLinkGroup2 OBJECT-TYPE
   SYNTAX     RowPointer 
   ACCESS     read-only
   STATUS     mandatory
   DESCRIPTION
     "The second possible link group available that can be used to reach a 
      neighbour which is the next hop in the path to the destination Node 
      for the specified Class of Service (COS). VNS traffic is routed 
      deterministically across the links in up to two link groups, when 
      available. If only one link group is available this attribute will be 
      left blank. The link groups selected are those associated with 
      minimum metric COS paths to the destination. If two link groups 
      are in use then the metric of the paths associated with each are 
      identical.
      
      Link group instances are managed by the TransportResource 
      component. Further information about the links in the group can be 
      obtained from it."
::= { rtgVnsNodeOperEntry 3 }

-- 
-- *** THIS SUBTREE CURRENTLY NOT IMPLEMENTED ***
-- 

-- Routing Vns LogicalProcessor/<n> 
-- This component provides statistics about the traffic handled by this 
-- Vns component on the LP identified by this component instance.

rtgVnsLpStats OBJECT IDENTIFIER ::= { rtgVns 3 }



rtgVnsLpStatsRowStatusTable OBJECT-TYPE
   SYNTAX     SEQUENCE OF RtgVnsLpStatsRowStatusEntry
   ACCESS     not-accessible
   STATUS     mandatory
   DESCRIPTION
     "*** THIS TABLE CURRENTLY NOT IMPLEMENTED ***

      This entry controls the addition and deletion of 
      rtgVnsLpStats components."
::= { rtgVnsLpStats 1 }

rtgVnsLpStatsRowStatusEntry OBJECT-TYPE
   SYNTAX     RtgVnsLpStatsRowStatusEntry
   ACCESS     not-accessible
   STATUS     mandatory
   DESCRIPTION
     "A single entry in the table represents a single 
      rtgVnsLpStats component."
   INDEX {
      rtgIndex,
      rtgVnsIndex,
      rtgVnsLpStatsIndex }
::= { rtgVnsLpStatsRowStatusTable 1 }

RtgVnsLpStatsRowStatusEntry ::= SEQUENCE {
   rtgVnsLpStatsRowStatus
      RowStatus,
   rtgVnsLpStatsComponentName
      DisplayString,
   rtgVnsLpStatsStorageType
      StorageType,
   rtgVnsLpStatsIndex
      Integer32 }

rtgVnsLpStatsRowStatus OBJECT-TYPE
   SYNTAX     RowStatus 
   ACCESS     read-only
   STATUS     mandatory
   DESCRIPTION
     "This variable is used as the basis for SNMP naming of
      rtgVnsLpStats components.
      These components cannot be added nor deleted."
::= { rtgVnsLpStatsRowStatusEntry 1 }

rtgVnsLpStatsComponentName OBJECT-TYPE
   SYNTAX     DisplayString 
   ACCESS     read-only
   STATUS     mandatory
   DESCRIPTION
     "This variable provides the component's string name for
      use with the ASCII Console Interface"
::= { rtgVnsLpStatsRowStatusEntry 2 }

rtgVnsLpStatsStorageType OBJECT-TYPE
   SYNTAX     StorageType 
   ACCESS     read-only
   STATUS     mandatory
   DESCRIPTION
     "This variable represents the storage type value for the
      rtgVnsLpStats tables."
::= { rtgVnsLpStatsRowStatusEntry 4 }

rtgVnsLpStatsIndex OBJECT-TYPE
   SYNTAX     Integer32 (0..15)
   ACCESS     not-accessible
   STATUS     mandatory
   DESCRIPTION
     "This variable represents the index for the rtgVnsLpStats tables."
::= { rtgVnsLpStatsRowStatusEntry 10 }

rtgVnsLpStatsFwdStatsTable OBJECT-TYPE
   SYNTAX     SEQUENCE OF RtgVnsLpStatsFwdStatsEntry
   ACCESS     not-accessible
   STATUS     mandatory
   DESCRIPTION
     "*** THIS TABLE CURRENTLY NOT IMPLEMENTED ***

      This group of attributes provides statistics of the traffic handled by 
      this Vns component on this LP. They are presented in 3 broad 
      classes: unicast, multicast, total (unicast and multicast combined)."
::= { rtgVnsLpStats 2 }

rtgVnsLpStatsFwdStatsEntry OBJECT-TYPE
   SYNTAX     RtgVnsLpStatsFwdStatsEntry
   ACCESS     not-accessible
   STATUS     mandatory
   DESCRIPTION
     "An entry in the rtgVnsLpStatsFwdStatsTable."
   INDEX {
      rtgIndex,
      rtgVnsIndex,
      rtgVnsLpStatsIndex }
::= { rtgVnsLpStatsFwdStatsTable 1 }

RtgVnsLpStatsFwdStatsEntry ::= SEQUENCE {
   rtgVnsLpStatsUniRxPkts
      PassportCounter64,
   rtgVnsLpStatsUniRxBytes
      PassportCounter64,
   rtgVnsLpStatsUniRxDiscPkts
      PassportCounter64,
   rtgVnsLpStatsUniTxPkts
      PassportCounter64,
   rtgVnsLpStatsUniTxBytes
      PassportCounter64,
   rtgVnsLpStatsUniTxDiscPkts
      PassportCounter64,
   rtgVnsLpStatsMultiRxPkts
      PassportCounter64,
   rtgVnsLpStatsMultiRxBytes
      PassportCounter64,
   rtgVnsLpStatsMultiRxDiscPkts
      PassportCounter64,
   rtgVnsLpStatsMultiTxPkts
      PassportCounter64,
   rtgVnsLpStatsMultiTxBytes
      PassportCounter64,
   rtgVnsLpStatsMultiTxDiscPkts
      PassportCounter64,
   rtgVnsLpStatsTotalRxPkts
      PassportCounter64,
   rtgVnsLpStatsTotalRxBytes
      PassportCounter64,
   rtgVnsLpStatsTotalRxDiscPkts
      PassportCounter64,
   rtgVnsLpStatsTotalTxPkts
      PassportCounter64,
   rtgVnsLpStatsTotalTxBytes
      PassportCounter64,
   rtgVnsLpStatsTotalTxDiscPkts
      PassportCounter64 }

rtgVnsLpStatsUniRxPkts OBJECT-TYPE
   SYNTAX     PassportCounter64 
   ACCESS     read-only
   STATUS     mandatory
   DESCRIPTION
     "This attribute counts the unicast packets received by this Vns 
      component on this LP. The counter wraps around to zero when the 
      maximum value is reached."
::= { rtgVnsLpStatsFwdStatsEntry 1 }

rtgVnsLpStatsUniRxBytes OBJECT-TYPE
   SYNTAX     PassportCounter64 
   ACCESS     read-only
   STATUS     mandatory
   DESCRIPTION
     "This attribute counts the unicast bytes received by VNS packet 
      forwarding for this Vns component on this LP. The counter wraps 
      around to zero when the maximum value is reached."
::= { rtgVnsLpStatsFwdStatsEntry 2 }

rtgVnsLpStatsUniRxDiscPkts OBJECT-TYPE
   SYNTAX     PassportCounter64 
   ACCESS     read-only
   STATUS     mandatory
   DESCRIPTION
     "This attribute counts the unicast packets received and discarded by 
      this Vns component on this LP. (For example, a received VNS 
      packet may be discarded if its Time-to-Live counter has expired.) 
      Packets counted here are not counted in uniRxPkts. The counter 
      wraps around to zero when the maximum value is reached."
::= { rtgVnsLpStatsFwdStatsEntry 3 }

rtgVnsLpStatsUniTxPkts OBJECT-TYPE
   SYNTAX     PassportCounter64 
   ACCESS     read-only
   STATUS     mandatory
   DESCRIPTION
     "This attribute counts the unicast packets transmitted by this Vns 
      component on this LP. The counter wraps around to zero when the 
      maximum value is reached."
::= { rtgVnsLpStatsFwdStatsEntry 4 }

rtgVnsLpStatsUniTxBytes OBJECT-TYPE
   SYNTAX     PassportCounter64 
   ACCESS     read-only
   STATUS     mandatory
   DESCRIPTION
     "This attribute counts the unicast bytes transmitted by this Vns 
      component on this LP. The counter wraps around to zero when the 
      maximum value is reached."
::= { rtgVnsLpStatsFwdStatsEntry 5 }

rtgVnsLpStatsUniTxDiscPkts OBJECT-TYPE
   SYNTAX     PassportCounter64 
   ACCESS     read-only
   STATUS     mandatory
   DESCRIPTION
     "This attribute counts the unicast packets this Vns component was 
      expected to transmit, but had to discard on this LP. (For example, 
      VNS packets may be discarded because there is no route to the 
      given destination.) Packets counted here are not counted in 
      uniTxPkts. The counter wraps around to zero when the maximum 
      value is reached."
::= { rtgVnsLpStatsFwdStatsEntry 6 }

rtgVnsLpStatsMultiRxPkts OBJECT-TYPE
   SYNTAX     PassportCounter64 
   ACCESS     read-only
   STATUS     mandatory
   DESCRIPTION
     "This attribute counts the multicast packets received by this Vns 
      component on this LP. The counter wraps around to zero when the 
      maximum value is reached."
::= { rtgVnsLpStatsFwdStatsEntry 7 }

rtgVnsLpStatsMultiRxBytes OBJECT-TYPE
   SYNTAX     PassportCounter64 
   ACCESS     read-only
   STATUS     mandatory
   DESCRIPTION
     "This attribute counts the multicast bytes received by this Vns 
      component on this LP. The counter wraps around to zero when the 
      maximum value is reached."
::= { rtgVnsLpStatsFwdStatsEntry 8 }

rtgVnsLpStatsMultiRxDiscPkts OBJECT-TYPE
   SYNTAX     PassportCounter64 
   ACCESS     read-only
   STATUS     mandatory
   DESCRIPTION
     "This attribute counts the multicast packets received and discarded 
      by this Vns component on this LP. (For example, a received Vns 
      packet may be discarded if its Time-to-Live counter has expired.) 
      Packets counted here are not counted in multiRxPkts. The counter 
      wraps around to zero when the maximum value is reached."
::= { rtgVnsLpStatsFwdStatsEntry 9 }

rtgVnsLpStatsMultiTxPkts OBJECT-TYPE
   SYNTAX     PassportCounter64 
   ACCESS     read-only
   STATUS     mandatory
   DESCRIPTION
     "This attribute counts the multicast packets transmitted by this Vns 
      component on this LP. The counter wraps around to zero when the 
      maximum value is reached."
::= { rtgVnsLpStatsFwdStatsEntry 10 }

rtgVnsLpStatsMultiTxBytes OBJECT-TYPE
   SYNTAX     PassportCounter64 
   ACCESS     read-only
   STATUS     mandatory
   DESCRIPTION
     "This attribute counts the multicast bytes transmitted by this Vns 
      component on this LP. The counter wraps around to zero when the 
      maximum value is reached."
::= { rtgVnsLpStatsFwdStatsEntry 11 }

rtgVnsLpStatsMultiTxDiscPkts OBJECT-TYPE
   SYNTAX     PassportCounter64 
   ACCESS     read-only
   STATUS     mandatory
   DESCRIPTION
     "This attribute counts the multicast packets this Vns component was 
      expected to transmit, but had to discard. (For example, VNS packets 
      may be discarded because there is no route to the given destination.) 
      Packets counted here are not counted in multiTxPkts. The counter 
      wraps around to zero when the maximum value is reached."
::= { rtgVnsLpStatsFwdStatsEntry 12 }

rtgVnsLpStatsTotalRxPkts OBJECT-TYPE
   SYNTAX     PassportCounter64 
   ACCESS     read-only
   STATUS     mandatory
   DESCRIPTION
     "This attribute gives the total count of packets received by this Vns 
      component on this LP. The counter wraps around to zero when the 
      maximum value is reached."
::= { rtgVnsLpStatsFwdStatsEntry 13 }

rtgVnsLpStatsTotalRxBytes OBJECT-TYPE
   SYNTAX     PassportCounter64 
   ACCESS     read-only
   STATUS     mandatory
   DESCRIPTION
     "This attribute gives the total count of bytes received by this Vns 
      component on this LP. The counter wraps around to zero when the 
      maximum value is reached."
::= { rtgVnsLpStatsFwdStatsEntry 14 }

rtgVnsLpStatsTotalRxDiscPkts OBJECT-TYPE
   SYNTAX     PassportCounter64 
   ACCESS     read-only
   STATUS     mandatory
   DESCRIPTION
     "This attribute gives the total count of packets received and discarded 
      by this Vns component on this LP. (For example, a received VNS 
      packet may be discarded if its Time-to-Live counter has expired.) 
      Packets counted here are not counted in totalRxPkts. The counter 
      wraps around to zero when the maximum value is reached."
::= { rtgVnsLpStatsFwdStatsEntry 15 }

rtgVnsLpStatsTotalTxPkts OBJECT-TYPE
   SYNTAX     PassportCounter64 
   ACCESS     read-only
   STATUS     mandatory
   DESCRIPTION
     "This attribute gives the total count of packets transmitted by this 
      Vns component on this LP. The counter wraps around to zero when 
      the maximum value is reached."
::= { rtgVnsLpStatsFwdStatsEntry 16 }

rtgVnsLpStatsTotalTxBytes OBJECT-TYPE
   SYNTAX     PassportCounter64 
   ACCESS     read-only
   STATUS     mandatory
   DESCRIPTION
     "This attribute gives the total count of bytes transmitted by this Vns 
      component on this LP. The counter wraps around to zero when the 
      maximum value is reached."
::= { rtgVnsLpStatsFwdStatsEntry 17 }

rtgVnsLpStatsTotalTxDiscPkts OBJECT-TYPE
   SYNTAX     PassportCounter64 
   ACCESS     read-only
   STATUS     mandatory
   DESCRIPTION
     "This attribute gives the total count of packets this Vns component 
      was expected to transmit, but had to discard on this LP. (For 
      example, VNS packets may be discarded because there is no route 
      to the given destination.) Packets counted here are not counted in 
      totalTxPkts. The counter wraps around to zero when the maximum 
      value is reached."
::= { rtgVnsLpStatsFwdStatsEntry 18 }




-- 
-- Version and Compliance statements
-- 



-- Object-Group Statement:
-- A list of all current accessible leaf objects.

-- OBJECTS { rtgVnsMultiTxDiscPkts,
--           rtgVnsTotalTxDiscPkts,
--           rtgVnsNodeComponentName,
--           rtgVnsLpStatsTotalTxPkts,
--           rtgVnsUniRxPkts,
--           rtgVnsLpStatsMultiRxPkts,
--           rtgVnsIfIndex,
--           rtgVnsLpStatsTotalRxPkts,
--           rtgVnsLpStatsUniTxBytes,
--           rtgVnsIlsForwarder,
--           rtgVnsMultiTxPkts,
--           rtgVnsReportedThroughputMetric,
--           rtgVnsLpStatsUniTxDiscPkts,
--           rtgVnsLpStatsRowStatus,
--           rtgVnsTotalTxPkts,
--           rtgVnsStorageType,
--           rtgVnsMultiRxBytes,
--           rtgVnsMaximumTransmissionUnit,
--           rtgVnsAdminState,
--           rtgVnsTotalRxBytes,
--           rtgVnsMultiRxDiscPkts,
--           rtgVnsLpStatsComponentName,
--           rtgVnsTotalRxDiscPkts,
--           rtgVnsNodeStorageType,
--           rtgVnsLpStatsUniTxPkts,
--           rtgVnsNodeMetric,
--           rtgVnsNodeNextHopLinkGroup2,
--           rtgVnsLpStatsUniRxBytes,
--           rtgVnsMultiRxPkts,
--           rtgVnsRowStatus,
--           rtgVnsLpStatsUniRxDiscPkts,
--           rtgVnsLpStatsTotalRxDiscPkts,
--           rtgVnsTotalRxPkts,
--           rtgVnsCustomerIdentifier,
--           rtgVnsUniTxBytes,
--           rtgVnsLpStatsMultiTxBytes,
--           rtgVnsNodeNextHopLinkGroup1,
--           rtgVnsUniTxDiscPkts,
--           rtgVnsLpStatsTotalTxBytes,
--           rtgVnsNodeRowStatus,
--           rtgVnsLoadSharing,
--           rtgVnsUsageState,
--           rtgVnsLpStatsTotalTxDiscPkts,
--           rtgVnsComponentName,
--           rtgVnsLpStatsUniRxPkts,
--           rtgVnsLpStatsMultiTxDiscPkts,
--           rtgVnsUniTxPkts,
--           rtgVnsOperationalState,
--           rtgVnsLpStatsMultiTxPkts,
--           rtgVnsLogicalNetworkNumber,
--           rtgVnsUniRxBytes,
--           rtgVnsLpStatsStorageType,
--           rtgVnsLpStatsMultiRxBytes,
--           rtgVnsUniRxDiscPkts,
--           rtgVnsLpStatsTotalRxBytes,
--           rtgVnsLpStatsMultiRxDiscPkts,
--           rtgVnsIfAdminStatus,
--           rtgVnsMultiTxBytes,
--           rtgVnsLinkToProtocolPort,
--           rtgVnsTotalTxBytes }
-- STATUS  mandatory
-- DESCRIPTION
--   "A list of all current accessible leaf objects."

vnsGroup OBJECT IDENTIFIER ::= { vnsMIB 1 }
vnsGroupBD OBJECT IDENTIFIER ::= { vnsGroup 4 }
vnsGroupBD00 OBJECT IDENTIFIER ::= { vnsGroupBD 1 }
vnsGroupBD00A OBJECT IDENTIFIER ::= { vnsGroupBD00 2 }



-- Agent-Capabilities Statement:

-- PRODUCT-RELEASE "Passport Release 7.0 Vns."
-- STATUS          mandatory
-- DESCRIPTION     "Vns MIB: MIB Version BD00A,
--                  Software Version BG00S4C."
-- SUPPORTS        Nortel-Magellan-Passport-VnsMIB
--    INCLUDES     { vnsGroupBD00A }

vnsCapabilities OBJECT IDENTIFIER ::= { vnsMIB 3 }
vnsCapabilitiesBD OBJECT IDENTIFIER ::= { vnsCapabilities 4 }
vnsCapabilitiesBD00 OBJECT IDENTIFIER ::= { vnsCapabilitiesBD 1 }
vnsCapabilitiesBD00A OBJECT IDENTIFIER ::= { vnsCapabilitiesBD00 2 }





END
