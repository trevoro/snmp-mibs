ONEFS-MIB DEFINITIONS ::= BEGIN

IMPORTS
	MODULE-IDENTITY, OBJECT-TYPE, OBJECT-IDENTITY, Counter64,
	snmpModules, enterprises
		FROM SNMPv2-SMI
	TEXTUAL-CONVENTION
		FROM SNMPv2-TC
	MODULE-COMPLIANCE, OBJECT-GROUP, NOTIFICATION-GROUP
		FROM SNMPv2-CONF;

onefs MODULE-IDENTITY
	LAST-UPDATED "0201172301Z"
	ORGANIZATION "COMPANY_NAME"
	CONTACT-INFO
		"COMPANY_NAME
		 Support phone: SUPPORT_PHONE
		 Support email: SUPPORT_EMAIL
		"
	DESCRIPTION
	       "This is the enterprise number for OneFS"
	::= { enterprises 12124 }

TimeTicks64 ::=  TEXTUAL-CONVENTION
	STATUS		current
	DESCRIPTION
	       "A 64 bit value representing milliseconds from the epoch"
	SYNTAX	        Counter64 (0..18446744073709551615)

END
