-- smon2.mib
-- This MIB is used for controling SMON-2 in Lucent's INS-E devices.
-- ***********************************************************************
-- Version 2.1.4:27-Dec-1999 by ItaiZ
-- 1. The enumeration of TCP and UDP in drSmonActiveApplicationsType and 
--   drSmonActiveApplicationsSubType, were changed from TCP(4) and UDP(3)
--   to TCP(3) and UDP(4).
-- ***********************************************************************--
-- Version 2.1.3:26-Oct-1999 by ItaiZ
-- 1. drSmonEntityPlacementTable- index changed back to placment index.
--    The agent must provide entries in this table for all the 
--    index values in the range of 1..(drSmonControlMatrixRows-1)
--    Row 0 of a matrix/table is reserved for "Others" entity, and is not
--    reported in this MIB table.
-- ***********************************************************************
-- Version 2.1.2:19-Oct-1999 by ItaiZ
-- 1. drSmonEntityPlacementTable- now indexed by IP, mask.
-- ***********************************************************************
-- Version 2.1.1:18-Oct-1999!!! by ItaiZ
-- 1. Re-introduced Matrix dimensions - 
-- drSmonControlMatrixRows,drSmonControlMatrixCols
-- ***********************************************************************
-- Version 2.1.0:18-Oct-1999 by ItaiZ
-- 1. Added drSmonEntityPlacementTable reporting entity placment 
-- on H/W counter matrix/table.
-- ***********************************************************************
-- ***********************************************************************
-- Version 2.0.4:7-Oct-1999 by ItaiZ
-- 1. re-introduced drSmonControlProtocolDistStatsTimeStamp, deleted by 
-- in an earlier version.
-- ***********************************************************************
-- Version 2.0.3:5-Oct-1999 by ItaiZ
-- 1. Added VRRP to drSmonActiveApplicationsSubType
-- 2. deleted drSmonProbeCapabilities, drSmonCapabilities
-- ***********************************************************************
-- Version 2.0.2: 25-Aug-1999 by ItaiZ
-- 1. changed comment markers
-- 2. removed redundent drSmonControlMatrix items, no longer needed following
--    25-Jul-1999 P333R SMON-II Design Review 
-- ***********************************************************************
-- Version 2.0.1: 23-Aug-1999 by ItaiZ.
-- 1. Changed drActive* and drProtocol* to drSmonActiv* and drSmonProtocol*
-- 2. Fixed drActiveAplicationsTable to  { drSmonActiveApplications 1 }
-- ***********************************************************************
-- Version 2.0 : 22-Aug-1999 by ItaiZ.
-- 1. Added drSmon for distributed
--    rourting modules capable of operating in EZ2Route module
-- 2. Fixed the definition of the index clause in  xsSubnetMatrixDSEntry.
-- 3. IpAddress and BITS are now taken from SMIv2
-- ***********************************************************************
-- Version 1.0 : Long Time Ago by Someone
-- xsSmon for MMLS SMON-II phase 1
SMON2-MIB DEFINITIONS ::= BEGIN

IMPORTS

    OBJECT-TYPE, Counter32, Integer32,IpAddress,
    Gauge32, TimeTicks                            FROM SNMPv2-SMI
    RowStatus, DisplayString, TimeStamp
                                             FROM SNMPv2-TC
    ZeroBasedCounter32, LastCreateTime,
    TimeFilter, DataSource,  
    protocolDirLocalIndex, hlMatrixControlIndex  FROM RMON2-MIB
    OwnerString					 FROM RMON-MIB
    smon        	                          FROM APPLIC-MIB;

xsSmon OBJECT IDENTIFIER ::= { smon 2 } 

-- A group of the SMON tree
-- Defines the MIB objects that provide RMON-2 and SMON-2 functionality for Xswitch 
-- environments
			
-- This MIB group is written using SMIv2, as many of its constructs are imported from RMON-2


xsSmonResourceAllocation OBJECT-TYPE
SYNTAX OCTET STRING (SIZE(4))
MAX-ACCESS read-only
STATUS current
DESCRIPTION
	"This item is used to define which SMON applications are using resources at the  agent.
	  When the console performs smon application it should read this item in order to know which of the SMON applications are available in this agent. When there is a value of 0 (zero) in the relevant bit it means that the associated application is not running on the agent, When there is a value of 1 (one) in the relevant bit it means that the associated application is suported.
	D0	 -  statistics
	D1	 - history
	D2	 - alarm	
	D3	 - host 
	D4 	- hostTopN
	D5    - matrix
	D6	- filter
	D7 	- capture
	D8	- event
	D9 	- tokenRing
	D10 	- protocolDir
	D11	-protocolDist
	D12	-addressMap
	D13	-nlHost
	D14	- nlMatrix
	D15	-alHost
	D16	-alMatrix
	D17	-usrHistory
	D18	- probeConfig
	D19	-port
	D20	- portTopN
	D21	- subnet
	D22	- subnetMatrix
	D23	- vlan
	D24	- vlanMatrix
	D25	- nlHostTopN
	D26	- portHistory"
	::= { xsSmon 1}

xsHostTopN OBJECT IDENTIFIER ::= { xsSmon 2 }

xsHostTopNControlTable OBJECT-TYPE
    SYNTAX      SEQUENCE OF XsHostTopNControlEntry
    MAX-ACCESS  not-accessible
    STATUS      current
    DESCRIPTION
        "A set of parameters that control the creation of a  report of the top N network layer host 	entries according to a selected metric."
    ::= { xsHostTopN 1 }

xsHostTopNControlEntry OBJECT-TYPE
    SYNTAX      XsHostTopNControlEntry
    MAX-ACCESS  not-accessible
    STATUS      current
    DESCRIPTION
        "A conceptual row in the xsHostTopNControlTable. An example of the indexing of this table is
        xsHostTopNControlDuration.3"
    INDEX { xsHostTopNControlIndex }
    ::= { xsHostTopNControlTable 1 }

XsHostTopNControlEntry ::= SEQUENCE {
    xsHostTopNControlIndex            Integer32,
    xsHostTopNControlHostIndex      Integer32,
    xsHostTopNControlRateBase         INTEGER,
    xsHostTopNControlTimeRemaining    Integer32,
    xsHostTopNControlDuration         Integer32,
    xsHostTopNControlRequestedSize    Integer32,
    xsHostTopNControlGrantedSize      Integer32,
    xsHostTopNControlStartTime        TimeStamp,
    xsHostTopNControlOwner            OwnerString,
    xsHostTopNControlStatus           RowStatus
}

xsHostTopNControlIndex OBJECT-TYPE
    SYNTAX     Integer32 (1..65535)
    MAX-ACCESS not-accessible
    STATUS     current
    DESCRIPTION
        "An index that uniquely identifies an entry
        in the xsHostTopNControlTable.  Each such
        entry defines one top N report prepared for
        one interface."
    ::= { xsHostTopNControlEntry 1 }

xsHostTopNControlHostIndex OBJECT-TYPE
    SYNTAX     Integer32 (1..65535)
    MAX-ACCESS read-create
    STATUS     current
    DESCRIPTION
        "The nlHost table for which a top N report will be prepared on behalf of this entry.  The nlHost table is identified by the value of the hlHostControlIndex for that table - that value is used here to identify the particular table.
        This object may not be modified if the associated xsHostTopNControlStatus object is equal to active(1)."
    ::= { xsHostTopNControlEntry 2 }

xsHostTopNControlRateBase OBJECT-TYPE
    SYNTAX      INTEGER {
                    xsHostTopNInPkts(1),
		    xsHostTopNOutPkts(2),
                    xsHostTopNInOctets(3),
		    xsHostTopNOutOctets(4)
                }
    MAX-ACCESS read-create
    STATUS     current
    DESCRIPTION
        "The variable for each nlHost entry that the
        xsHostTopNEntries are sorted by. This object may not be modified if the associated
        xsHostTopNControlStatus object is equal to active(1)."
    ::= { xsHostTopNControlEntry 3 }

xsHostTopNControlTimeRemaining OBJECT-TYPE
    SYNTAX     Integer32 (0..2147483647)
    MAX-ACCESS read-create
    STATUS     current
    DESCRIPTION
 "The number of seconds left in the report currently
                  being collected.  When this object is modified by
                  the management station, a new collection is started,
                  possibly aborting a currently running report.  The
                  new value is used as the requested duration of this
                  report, which is loaded into the associated
                  xsHostTopNControlDuration object.

                  When this object is set to a non-zero value, any
                  associated xsHostTopNEntries shall be made
                  inaccessible by the monitor.  While the value of
                  this object is non-zero, it decrements by one per
                  second until it reaches zero.  During this time, all
                  associated xsHostTopNEntries shall remain
                  inaccessible.  At the time that this object
                  decrements to zero, the report is made accessible in
                  the xsHostTopNTable.  Thus, the xsHostTopN table needs
                  to be created only at the end of the collection
                  interval."
              DEFVAL { 0 }
    ::= { xsHostTopNControlEntry 4 }

xsHostTopNControlDuration OBJECT-TYPE
    SYNTAX     Integer32
 MAX-ACCESS read-only
    STATUS     current
    DESCRIPTION
        "The number of seconds that this report has collected  during the last sampling interval.
        When the associated HostTopNControlTimeRemaining object is
        set, this object shall be set by the probe to the
        same value and shall not be modified until the next time the xsHostTopNControlTimeRemaining         
        is set.
        This value shall be zero if no reports have been
        requested for this xsHostTopNControlEntry."
    ::= { xsHostTopNControlEntry 5 }

xsHostTopNControlRequestedSize OBJECT-TYPE
    SYNTAX     Integer32 (0..2147483647)
    MAX-ACCESS read-create
    STATUS     current
    DESCRIPTION
        "The maximum number of host entries requested for this report. When this object is created or 
        modified, the probe should set xsHostTopNControlGrantedSize as closely to this object as is 
        possible for the particular probe implementation and available resources."
    DEFVAL { 150 }
    ::= { xsHostTopNControlEntry 6 }

xsHostTopNControlGrantedSize OBJECT-TYPE
    SYNTAX     Integer32 (0..2147483647)
    MAX-ACCESS read-only
    STATUS     current
    DESCRIPTION
        "The maximum number of host entries in this report. When the associated 
        xsHostTopNControlRequestedSize object is
        created or modified, the probe should set this
        object as closely to the requested value as is
        possible for the particular implementation and
        available resources. The probe must not lower this  value except as a result of a set to the 
        associated  xsHostTopNControlRequestedSize object. If the value of 
        xsHostTopNControlRateBase is equal to
        xsHostTopNPkts, when the next topN report is generated, matrix entries with the highest value of 
        xsHostTopNPktRate  shall be placed in this table in decreasing order of this rate
        until there is no more room or until there are no more matrix entries. If the value of 
        xsHostTopNControlRateBase is equal to
        xsHostTopNOctets, when the next topN report   is generated, matrix entries with the highest  
        value of xsHostTopNOctetRate shall be placed in this table in decreasing order of this rate until 
        there is no more room or until there are no more matrix entries. It is an implementation-specific 
        matter how entries with the same value of xsHostTopNPktRate or xsHostTopNOctetRate are 
        sorted.  It is also an implementation-specific matter as to whether or not zero-valued entries are 
       available."
    ::= { xsHostTopNControlEntry 7 }

xsHostTopNControlStartTime OBJECT-TYPE
    SYNTAX     TimeStamp
    MAX-ACCESS read-only
    STATUS     current
    DESCRIPTION
        "The value of sysUpTime when this top N report was last started.  In other words, this is the time 
        that the associated xsHostTopNControlTimeRemaining object was  modified to start the requested 
        report or the time the report was last automatically (re)started. This object may be used by the 
        management station to determine if a report was missed or not."
    ::= { xsHostTopNControlEntry 8 }

xsHostTopNControlOwner OBJECT-TYPE
    SYNTAX     OwnerString
    MAX-ACCESS read-create
    STATUS     current
    DESCRIPTION
        "The entity that configured this entry and is
        therefore using the resources assigned to it."
    ::= { xsHostTopNControlEntry 9}

xsHostTopNControlStatus OBJECT-TYPE
    SYNTAX     RowStatus
    MAX-ACCESS read-create
    STATUS     current
    DESCRIPTION
        "The status of this xsHostTopNControlEntry.
        An entry may not exist in the active state unless all objects in the entry have an appropriate value. 
        If this object is not equal to active(1), all associated entries in the xsHostTopNTable shall be 
       deleted by the agent."
    ::= { xsHostTopNControlEntry 10 }



xsHostTopNTable OBJECT-TYPE
    SYNTAX     SEQUENCE OF XsHostTopNEntry
    MAX-ACCESS not-accessible
    STATUS     current
    DESCRIPTION
        "A set of statistics for those network layer hosts that have counted the highest number of octets or 
        packets."
    ::= { xsHostTopN 2 }

xsHostTopNEntry OBJECT-TYPE
    SYNTAX     XsHostTopNEntry
    MAX-ACCESS not-accessible
    STATUS     current
    DESCRIPTION
        "A conceptual row in the xsHostTopNTable.
        The xsHostTopNControlIndex value in the index identifies the xsHostTopNControlEntry on 
        whose behalf this entry was created.  An example of the indexing of this table is
        xsHostTopNPktRate.3.10"
    INDEX { xsHostTopNControlIndex, xsHostTopNIndex }
    ::= { xsHostTopNTable 1 }

XsHostTopNEntry ::= SEQUENCE {
    xsHostTopNIndex                 Integer32,
    xsHostTopNProtocolDirLocalIndex Integer32,
    xsHostTopNNlAddress         OCTET STRING,
    xsHostTopNRate               Gauge32
}

xsHostTopNIndex OBJECT-TYPE
    SYNTAX     Integer32 (1..65535)
    MAX-ACCESS not-accessible
    STATUS     current
    DESCRIPTION
        "An index that uniquely identifies an entry in
        the xsHostTopNTable among those in the same report. 
        This index is between 1 and N, where N is the number of entries in this report.
        If the value of xsHostTopNControlRateBase is equal to xsHostTopNInPkts, increasing values of 
       xsHostTopNIndex shall be assigned to entries with decreasing values of xsHostTopNRate until 
       index N is assigned or there are no more xsHostTopNEntries. "
    ::= { xsHostTopNEntry 1 }

xsHostTopNProtocolDirLocalIndex OBJECT-TYPE
    SYNTAX     Integer32 (1..2147483647)
    MAX-ACCESS read-only
    STATUS     current
    DESCRIPTION
        "The protocolDirLocalIndex of the network layer protocol of this entry's network address."
    ::= { xsHostTopNEntry 2 }

xsHostTopNNlAddress OBJECT-TYPE
    SYNTAX     OCTET STRING
    MAX-ACCESS read-only
    STATUS     current
    DESCRIPTION
        "The network layer address of the  host in this collection. This is represented as an octet string 
        with  specific semantics and length as identified  by the associated xsHostTopN 
        ProtocolDirLocalIndex. For example, if the protocolDirLocalIndex indicates an  encapsulation of 
        ip, this object is encoded as a length octet of 4, followed by the 4 octets of the ip address, in 
        network byte order."
    ::= { xsHostTopNEntry 3 }

xsHostTopNRate OBJECT-TYPE
    SYNTAX     Gauge32
    MAX-ACCESS read-only
    STATUS     current
    DESCRIPTION
        "The number of packets seen from the source host to the destination host during this sampling 
        interval, counted using the rules for counting the xsHostPkts object. If the value of 
        xsHostTopNControlRateBase is xsHostTopNPkts, this variable will be used to sort this  report."
    ::= { xsHostTopNEntry 4 }





-- This table is a filter used to define the hosts for which data is collected by the probe. The table 
-- contains a list of IP addresses, IPX networks, and the probe collects statistics on all hosts that were 
-- defined in this table. (This table can be  used as a  DataSource for alHostTable, nlMatrix, alMatrix, 
--xsSubnet.

xsFilter  OBJECT IDENTIFIER ::= { xsSmon 3}  -- Subtree of all xs filters


xsHostFilterTable OBJECT-TYPE
	SYNTAX SEQUENCE OF XsHostFilterEntry
	MAX-ACCESS not-accessible
	STATUS current 
	DESCRIPTION
"A list of network layer addresses hosts to be monitored through an interface by the RMON II MIB hosts group. The OID of this table is a legitimate value for the hlMatrixControlDataSource,
and for LANNET's Groups  xsSubnetControlDataSource, xsSubnetMatrixControlDataSource,"
	::= {xsFilter 1 }


xsHostFilterEntry OBJECT-TYPE
	SYNTAX XsHostFilterEntry
	MAX-ACCESS not-accessible
	STATUS current
	DESCRIPTION
"An entry in the filter table."
	INDEX { xsHostFilterIpAddress }
	::= { xsHostFilterTable 1 }

XsHostFilterEntry ::= SEQUENCE {
		xsHostFilterType		INTEGER,
		xsHostFilterIpAddress   	OCTET STRING,
		xsHostFilterIpSubnet	OCTET STRING,
		xsHostFilterIpMask	OCTET STRING,
		xsHostFilterIpxAddress	OCTET STRING,
		xsHostFilterStatus      INTEGER
		              }

xsHostFilterType OBJECT-TYPE
	SYNTAX INTEGER { 
			ipHost(1), 
			ipSubnet(2),
			ipxNet(3) 
      		         } 
	MAX-ACCESS read-write
	STATUS current 
	DESCRIPTION
"Indicates the type of the filter defined by this entry."
	::= { xsHostFilterEntry 1 }


xsHostFilterIpAddress OBJECT-TYPE
	SYNTAX OCTET STRING
	MAX-ACCESS read-write
	STATUS current 
	DESCRIPTION
"The IP address of a host monitored via  the Interface. In case the filter type is not ipHost(1), the value of this entry is not relevant and should return the null string."
	::= { xsHostFilterEntry 2 }

xsHostFilterIpSubnet OBJECT-TYPE
	SYNTAX OCTET STRING
	MAX-ACCESS read-write
	STATUS current 
	DESCRIPTION
"The address of a IP subnet monitored via  the Interface. In case the filter type is not ipSubnet(2), the value of this entry is not relevant and should return the null string."
	::= { xsHostFilterEntry 3 }

xsHostFilterIpMask OBJECT-TYPE
	SYNTAX OCTET STRING
	MAX-ACCESS read-write
	STATUS current
	DESCRIPTION
"The mask of a IP subnet monitored via  the Interface. In case the filter type is not ipSubnet(2), the value of this entry is not relevant and should return the null string."
	::= { xsHostFilterEntry 4 }

xsHostFilterIpxAddress OBJECT-TYPE
	SYNTAX OCTET STRING
	MAX-ACCESS read-write
	STATUS current 
	DESCRIPTION
"The address of a IPX  monitored via  the Interface. In case the filter type is not ipxNet(3), the value of this entry is not relevant and should return the null string."
	::= { xsHostFilterEntry 5 }


xsHostFilterStatus OBJECT-TYPE
	SYNTAX INTEGER { 
			valid(1), 
			invalid(4) 
      		         } 
	MAX-ACCESS read-write
	STATUS current 
	DESCRIPTION
"The status of this xsHostFilter entry."
	::= { xsHostFilterEntry 6 }


xsHostFilterTableClear OBJECT-TYPE
	SYNTAX INTEGER { 
			idle(1), 
			clear(2) 
      		         } 
	MAX-ACCESS read-write
	STATUS current 
	DESCRIPTION
"Setting the value of this item to clear(2) causes the 
agent to clear all entries in the HostFilterTable."
	::= {xsFilter  2 }




--Subnet Statistic group Group
--
-- Counts the amount of traffic sent from and to each network address
-- subnet discovered by the probe.
--
 xsSubnet  OBJECT IDENTIFIER  ::= {xsSmon 4 }


xsSubnetControlTable OBJECT-TYPE
    SYNTAX      SEQUENCE OF XsSubnetControlEntry
    MAX-ACCESS  not-accessible
    STATUS      current
    DESCRIPTION
        "A list of higher layer (i.e. non-MAC) Subnets\Networks table  control entries.  These entries will enable the collection of the network and application level subnets tables indexed by subnetwork addresses. Entries in the xsSubnetTable will be created on behalf of each entry in this table. Implementations are encouraged to add an entry per monitored interface upon initialization so that a default collection of subnet statistics is available."
    ::= { xsSubnet 1 }

xsSubnetControlEntry OBJECT-TYPE
    SYNTAX      XsSubnetControlEntry
    MAX-ACCESS  not-accessible
    STATUS      current
    DESCRIPTION
      "A conceptual row in the sSubnetControlTable.
        An example of the indexing of this entry is
        xsSubnetControlDataSource.1"
    INDEX { xsSubnetControlIndex }
    ::= { xsSubnetControlTable 1 }

XsSubnetControlEntry ::= SEQUENCE {
    xsSubnetControlIndex               Integer32,
    xsSubnetControlDataSource          DataSource,
    xsSubnetControlInserts           Counter32,
    xsSubnetControlDeletes           Counter32,
    xsSubnetControlMaxDesiredEntries Integer32,
    xsSubnetControlOwner               OwnerString,
    xsSubnetControlStatus              RowStatus
}

xsSubnetControlIndex OBJECT-TYPE
    SYNTAX      Integer32 (1..65535)
    MAX-ACCESS  not-accessible
    STATUS      current
    DESCRIPTION
        "An index that uniquely identifies an entry in the xsSubnetControlTable.  Each such entry defines a function that collects statistics on a particular interface and places statistics about them in the xsSubnetTable, on  behalf of this xsSubnetControlEntry."
    ::= { xsSubnetControlEntry 1 }

xsSubnetControlDataSource OBJECT-TYPE
    SYNTAX      DataSource
    MAX-ACCESS  read-create
    STATUS      current
    DESCRIPTION
        "The source of data for the associated Subnet tables. The statistics in this group reflect all packets on the local network segment attached to the identified interface.Mostly this instance will be the xsHostFilterTable. This object may not be modified if the associated xsSubnetControlStatus object is equal to active(1)."
    ::= { xsSubnetControlEntry 2 }


xsSubnetControlInserts OBJECT-TYPE
    SYNTAX     Counter32
    MAX-ACCESS read-only
    STATUS     current
    DESCRIPTION
        "The number of times an xsSubnet entry has been inserted into the xsSubnet table.  If an entry is inserted, then deleted, and then inserted, this counter will be incremented by 2. To allow for efficient implementation strategies, agents may delay updating this object for short periods of time.  For      example, an implementation strategy may allow internal  data structures to differ from those visible via SNMP for  short periods of time.  This counter may reflect the internal data structures for those short periods of time.
        Note that the table size can be determined by subtracting xsSubnetControlDeletes from xsSubnetControlInserts."
    ::= { xsSubnetControlEntry 3 }

xsSubnetControlDeletes OBJECT-TYPE
    SYNTAX     Counter32
    MAX-ACCESS read-only
    STATUS     current
    DESCRIPTION
        "The number of times an xsSubnet entry has been  deleted from the xsSubnet table (for any reason).  If an entry  is deleted, then inserted, and then deleted, this counter will  be incremented by 2. To allow for efficient implementation strategies, agents may delay updating this object for short periods of time.  For example, an implementation strategy may allow internal data structures to differ from those visible via SNMP for short periods of time.  This counter may reflect the internal  data structures for those short periods of time. Note that the table size can be determined by subtracting
        xsSubnetControlDeletes from xsSubnetControlInserts."
    ::= { xsSubnetControlEntry 4}

xsSubnetControlMaxDesiredEntries OBJECT-TYPE
    SYNTAX      Integer32 (-1..2147483647)
    MAX-ACCESS  read-create
    STATUS      current
    DESCRIPTION
        "The maximum number of entries that are desired in the xsSubnetable on behalf of this control entry. The probe will  not create more than this number of associated entries in the table, but may choose to create fewer entries in this table for any reason including the lack of resources. If this object is set to a value less than the current number of entries, enough entries are chosen in an  implementation - dependent manner and deleted so that the number  of entries in the table equals the value of this object. If this value is set to -1, the probe may create any number of entries in this table.  If the associated xsSubnetControlStatus object is equal to `active', this  object may not be modified.
This object may be used to control how resources are allocated on the probe for the various RMON functions."
    ::= { xsSubnetControlEntry 5 }

xsSubnetControlOwner OBJECT-TYPE
    SYNTAX      OwnerString
    MAX-ACCESS  read-create
    STATUS      current
    DESCRIPTION
        "The entity that configured this entry and is
        therefore using the resources assigned to it."
    ::= { xsSubnetControlEntry 6 }

xsSubnetControlStatus OBJECT-TYPE
    SYNTAX      RowStatus
    MAX-ACCESS  read-create
    STATUS      current
    DESCRIPTION
        "The status of this xsSubnetControlEntry.
        An entry may not exist in the active state unless all objects in the entry have an appropriate value. If this object is not equal to active(1), all associated entries in the nlHostTable and alHostTable shall be deleted."
::= { xsSubnetControlEntry 7 }


xsSubnetTable OBJECT-TYPE
    SYNTAX      SEQUENCE OF XsSubnetEntry
    MAX-ACCESS  not-accessible
    STATUS      current
    DESCRIPTION
        "A collection of statistics for a particular subnetwork layer address that has been discovered on an interface of this device. The probe will populate this table for all network layer protocols in the protocol directory table whose value of  protocolDirHostConfig is equal to supportedOn(3), and will delete any entries whose protocolDirEntry is deleted or has a protocolDirHostConfig value of supportedOff(2). The probe will add to this table all subnetwork addresses  that exist in the xsHostFilter."
::= { xsSubnet 2 }

xsSubnetEntry OBJECT-TYPE
    SYNTAX      XsSubnetEntry
    MAX-ACCESS  not-accessible
    STATUS      current
    DESCRIPTION
        "A conceptual row in the xsSubnetTable.
        The xsSubnetControlIndex value in the index identifies the xsSubnetControlEntry on whose behalf this entry was created. The first protocolDirLocalIndex  value in the index identifies the network layer protocol the second protocolLocalDirIndex identifies the protocol (network or application layer protocol) to be monitored on that of the xsSubnetAddress. An example of the indexing of this entry is xsSubnetOutPkts.1.783495.18.4.128.2.6.6.4.255.255.255.0.18.This Index indexes The total out IP packets  of an Ip Subnet"
    INDEX { xsSubnetControlIndex, xsSubnetTimeMark,
            protocolDirLocalIndex, xsSubnetAddress, xsSubnetMask, protocolDirLocalIndex }
    ::= { xsSubnetTable 1 }

XsSubnetEntry ::= SEQUENCE {
    xsSubnetTimeMark              TimeFilter,
    xsSubnetAddress               OCTET STRING,
    xsSubnetMask		  OCTET STRING,
    xsSubnetInPkts                ZeroBasedCounter32,
    xsSubnetOutPkts               ZeroBasedCounter32,
    xsSubnetCreateTime            LastCreateTime
}

xsSubnetTimeMark OBJECT-TYPE
    SYNTAX      TimeFilter
    MAX-ACCESS  not-accessible
    STATUS      current
    DESCRIPTION
        "A TimeFilter for this entry.  See the TimeFilter textual convention to see how this works."
    ::= { xsSubnetEntry 1 }

xsSubnetAddress OBJECT-TYPE
    SYNTAX      OCTET STRING
    MAX-ACCESS  not-accessible
    STATUS      current
    DESCRIPTION
        "The subnetwork address for this xsSubnetEntry. This is represented as an octet string with specific semantics and length as identified  by the protocolDirLocalIndex component of the index. For example, if the protocolDirLocalIndex indicates an encapsulation of ip, this object is encoded as a length octet of 4, followed by the 4 octets of the ip address, in network byte order."
    ::= { xsSubnetEntry 2 }

xsSubnetMask OBJECT-TYPE
    SYNTAX      OCTET STRING
    MAX-ACCESS  not-accessible
    STATUS      current
    DESCRIPTION
        "The subnetwork mask for this xsSubnetEntry. This is represented as an octet string with specific semantics and length as identified by the protocolDirLocalIndex component of the index. For example, if the protocolDirLocalIndex indicates an encapsulation of ip, this object is encoded as a length octet of 4, followed by the 4 octets of the ip address, in network byte order."
    ::= { xsSubnetEntry 3 }

xsSubnetInPkts OBJECT-TYPE
    SYNTAX      ZeroBasedCounter32
    MAX-ACCESS  read-only
    STATUS      current
    DESCRIPTION
        "The number of packets without errors transmitted to this subnetwork address since it was added to the xsSubnetTable. Note that this is the number of link-layer packets, so if a single  network-layer packet is fragmented into several link-layer  frames, this counter is incremented several times."
    ::= { xsSubnetEntry 4 }

xsSubnetOutPkts OBJECT-TYPE
    SYNTAX      ZeroBasedCounter32
    MAX-ACCESS  read-only
    STATUS      current
    DESCRIPTION
        "The number of packets without errors transmitted by this subnetwork address since it was added to the xsSubnetTable. Note that this is the number of link-layer packets, so if a single network-layer packet is fragmented into several link-layer frames, this counter is incremented several times."
    ::= { xsSubnetEntry 5}

xsSubnetCreateTime OBJECT-TYPE
    SYNTAX     LastCreateTime
    MAX-ACCESS read-only
    STATUS     current
    DESCRIPTION
        "The value of sysUpTime when this entry was last activated. This can be used by the management station to ensure that the entry has not been deleted and recreated between polls."
    ::= { xsSubnetEntry 6 }



--SubNetwork Layer Matrix Group
--
-- Counts the amount of traffic sent between each pair of Subnetwork
-- addresses in the xsHostFilterTable.


xsSubnetMatrixControlTable OBJECT-TYPE
    SYNTAX      SEQUENCE OF XsSubnetMatrixControlEntry
    MAX-ACCESS  not-accessible
    STATUS      current
    DESCRIPTION
        "A list of higher layer (i.e. non-MAC) matrix control entries. These entries will enable the collection of the network and application level matrix tables containing conversation
statistics indexed by pairs of subnetwork addresses. Entries in the xsSubnetMatrixSDTable and xsSubnetMatrixDSTable will be  created on behalf of each entry in this table."
    ::= { xsSubnet  3  }

xsSubnetMatrixControlEntry OBJECT-TYPE
    SYNTAX      XsSubnetMatrixControlEntry
MAX-ACCESS  not-accessible
    STATUS      current
    DESCRIPTION
        "A conceptual row in the xsSubnetMatrixControlTable. An example of indexing of this entry is
xsSubnetMatrixControDataSource.1"
    INDEX { xsSubnetMatrixControlIndex }
    ::= { xsSubnetMatrixControlTable 1 }

XsSubnetMatrixControlEntry ::= SEQUENCE {
    xsSubnetMatrixControlIndex                  Integer32,
    xsSubnetMatrixControlDataSource             DataSource,
    xsSubnetMatrixControlInserts              Counter32,
    xsSubnetMatrixControlDeletes              Counter32,
    xsSubnetMatrixControlMaxDesiredEntries    Integer32,
    xsSubnetMatrixControlOwner                  OwnerString,
    xsSubnetMatrixControlStatus                 RowStatus
}

xsSubnetMatrixControlIndex OBJECT-TYPE
    SYNTAX      Integer32 (1..65535)
    MAX-ACCESS  not-accessible
    STATUS      current
    DESCRIPTION
        "An index that uniquely identifies an entry in the xsSubnetMatrixControlTable.  Each such entry defines a function that discovers conversations on a particular interface and places statistics about them in the xsSubnetMatrixSDTable and the xsSubnetMatrixDSTable, on behalf of this xsSubnetMatrixControlEntry."
    ::= { xsSubnetMatrixControlEntry 1 }

xsSubnetMatrixControlDataSource OBJECT-TYPE
    SYNTAX      DataSource
    MAX-ACCESS  read-create
    STATUS      current
    DESCRIPTION
        "The source of the data for the associated matrix tables. The statistics in this group reflect all packets on the local network segment attached to the identified interface.Mostly this instance will be the xsHostFilterTable. This object may not be modified if the associated xsSubnetControlStatus object is equal to active(1)."
    ::= { xsSubnetMatrixControlEntry 2 }

xsSubnetMatrixControlInserts OBJECT-TYPE
    SYNTAX     Counter32
    MAX-ACCESS read-only
    STATUS     current
    DESCRIPTION
        "The number of times an subnetMatrix entry has been inserted into the subnetMatrix tables.  If an entry is inserted, then deleted, and then inserted, this counter will be incremented by 2.  The addition of a conversation into both the xsSubnetMatrixSDTable and xsSubnetMatrixDSTable shall be counted as
two insertions (even though every addition into one table must be accompanied by an insertion into the other).To allow for efficient implementation strategies, agents may delay updating this object for short periods of time.  For example, an implementation strategy may allow internal data structures to differ from those visible via SNMP for short periods of time.  This counter may reflect the internal  data structures for those short periods of time. Note that the sum of then xsSubnetMatrixSDTable and xsSubnetMatrixDSTable sizes can be determined by subtracting xsSubnetMatrixControlNlDeletes from xsSubnetMatrixControlNlInserts."
    ::= { xsSubnetMatrixControlEntry 4 }

xsSubnetMatrixControlDeletes OBJECT-TYPE
    SYNTAX     Counter32
    MAX-ACCESS read-only
    STATUS     current
    DESCRIPTION
        "The number of times an subnetMatrix entry has been deleted from the subnetMatrix tables (for any reason).  If an entry is deleted, then inserted, and then deleted, this counter will be incremented by 2.  The deletion of a conversation from both the xsSubnetMatrixSDTable and xsSubnetMatrixDSTable
shall be counted as two deletions (even though every deletion from one table must be accompanied by a deletion from the other). To allow for efficient implementation strategies, agents may  delay updating this object for short periods of time. For example, an implementation strategy may allow internal data structures to differ from those visible via SNMP for short periods of time.  This counter may reflect the internal data structures for those short periods of time. Note that the table size can be determined by subtracting xsSubnetMatrixControlNlDeletes from xsSubnetMatrixControlNlInserts."
    ::= { xsSubnetMatrixControlEntry 5 }

xsSubnetMatrixControlMaxDesiredEntries OBJECT-TYPE
    SYNTAX      Integer32 (-1..2147483647)
    MAX-ACCESS  read-create
    STATUS      current
    DESCRIPTION
        "The maximum number of entries that are desired in the  subnetMatrix tables on behalf of this control entry. The probe will not create more than this number of associated entries in the table, but may choose to create fewer entries in this table for any reason including the lack of resources. If this object is set to a value less than the current number of entries, enough entries are chosen in an implementation-dependent manner and deleted so that the number  of entries in the table equals the value of this object. If this value is set to -1, the probe may create any number of entries in this table.  If the associated xsSubnetMatrixControlStatus object is equal to `active', this object may not be modified. This object may be used to control how resources are allocated on the probe for the various RMON functions."
    ::= { xsSubnetMatrixControlEntry 6 }

xsSubnetMatrixControlOwner OBJECT-TYPE
    SYNTAX      OwnerString
    MAX-ACCESS  read-create
    STATUS      current
    DESCRIPTION
        "The entity that configured this entry and is therefore using the resources assigned to it."
    ::= { xsSubnetMatrixControlEntry 7}

xsSubnetMatrixControlStatus OBJECT-TYPE
    SYNTAX      RowStatus
    MAX-ACCESS  read-create
    STATUS      current
    DESCRIPTION
        "The status of this xsSubnetMatrixControlEntry. An entry may not exist in the active state unless all  objects in the entry have an appropriate value.
If this object is not equal to active(1), all associated entries in the xsSubnetMatrixSDTable, xsSubnetMatrixDSTable shall be deleted by the agent."
    ::= { xsSubnetMatrixControlEntry 8 }





xsSubnetMatrixSDTable OBJECT-TYPE
    SYNTAX      SEQUENCE OF XsSubnetMatrixSDEntry
    MAX-ACCESS  not-accessible
    STATUS      current
    DESCRIPTION
        "A list of traffic matrix entries which collect statistics for conversations between two network-level addresses. This table is indexed first by the source address and then by the
destination address to make it convenient to collect all conversations from a particular address. The probe will populate this table for all network layer protocols in the protocol directory table whose value of protocolDirMatrixConfig is equal to supportedOn(3), and will delete any entries whose protocolDirEntry is deleted or  has a protocolDirMatrixConfig value of supportedOff(2). The probe will add to this table all pairs of addresses  seen in all packets with no MAC errors, and will increment
        octet and packet counts in the table for all packets with no  MAC errors. Further, this table will only contain entries that have a
        corresponding entry in the 	    	   	  xsSubnetMatrixDSTable with the same
        source address and destination address."
    ::= { xsSubnet  4 }

xsSubnetMatrixSDEntry OBJECT-TYPE
    SYNTAX      XsSubnetMatrixSDEntry
    MAX-ACCESS  not-accessible
    STATUS      current
    DESCRIPTION
        "A conceptual row in the xsSubnetMatrixSDTable.
        The xsSubnetMatrixControlIndex value in the index identifies the
        xsSubnetMatrixControlEntry on whose behalf this entry was created. The first  protocolDirLocalIndex  value in the index identifies the protocol of the xsSubnetMatrixSDSourceAddress and xsSubnetMatrixSDDestAddress (network layer protocol), the second protocolDirLocalIndex. identifies the protocol to be monitored  on that subnet (network or application layer)  An example of the indexing of this table is        xsSubnetMatrixSDPkts.1.783495.18.4.128.2.6.6.4.255.255.255.0.4.128.3.6.7..4.255.255.255.0.18"
    INDEX { xsSubnetMatrixControlIndex, xsSubnetMatrixSDTimeMark,
 protocolDirLocalIndex,  
xsSubnetMatrixSDSourceAddress, xsSubnetMatrixSDSourceMask ,
xsSubnetMatrixSDDestAddress, xsSubnetMatrixSDDestMask, 
protocolDirLocalIndex   }
    ::= { xsSubnetMatrixSDTable 1 }

XsSubnetMatrixSDEntry ::= SEQUENCE {
    xsSubnetMatrixSDTimeMark              TimeFilter,
    xsSubnetMatrixSDSourceAddress         OCTET STRING,
    xsSubnetMatrixSDSourceMask         OCTET STRING,
    xsSubnetMatrixSDDestAddress           OCTET STRING,
    xsSubnetMatrixSDDestMask           OCTET STRING,
   xsSubnetMatrixSDPkts                  ZeroBasedCounter32,
    xsSubnetMatrixSDCreateTime            LastCreateTime
}

xsSubnetMatrixSDTimeMark OBJECT-TYPE
    SYNTAX      TimeFilter
    MAX-ACCESS  not-accessible
    STATUS      current
    DESCRIPTION
        "A TimeFilter for this entry.  See the TimeFilter textual convention to see how this works."
    ::= { xsSubnetMatrixSDEntry 1 }

xsSubnetMatrixSDSourceAddress OBJECT-TYPE
    SYNTAX      OCTET STRING
    MAX-ACCESS  not-accessible
    STATUS      current
    DESCRIPTION
        "The subnetwork source address for this xsSubnetMatrixSDEntry. This is represented as an octet string with  specific semantics and length as identified by the protocolDirLocalIndex component of the index. For example, if the protocolDirLocalIndex indicates an encapsulation of ip, this object is encoded as a length  octet of 4, followed by the 4 octets of the ip address, in network byte order."
    ::= { xsSubnetMatrixSDEntry 2 }

xsSubnetMatrixSDSourceMask OBJECT-TYPE
    SYNTAX      OCTET STRING
    MAX-ACCESS  not-accessible
    STATUS      current
    DESCRIPTION
        "The subnetwork source mask for this xsSubnetMatrixSDEntry. This is represented as an octet string with  specific semantics and length as identified  by the protocolDirLocalIndex component of the index.   For example, if the protocolDirLocalIndex indicates an encapsulation of ip, this object is encoded as a length octet of 4, followed by the 4 octets of the ip address, in network byte order."
    ::= { xsSubnetMatrixSDEntry 3 }

xsSubnetMatrixSDDestAddress OBJECT-TYPE
    SYNTAX      OCTET STRING
    MAX-ACCESS  not-accessible
    STATUS      current
    DESCRIPTION
        "The subnetwork destination address for this
        xsSubnetMatrixSDEntry. This is represented as an octet string with specific semantics and length as identified by the protocolDirLocalIndex component of the index. For example, if the protocolDirLocalIndex indicates an encapsulation of ip, this object is encoded as a length octet of 4, followed by the 4 octets of the ip address, in network byte order."
    ::= { xsSubnetMatrixSDEntry 4 }

xsSubnetMatrixSDDestMask OBJECT-TYPE
    SYNTAX      OCTET STRING
    MAX-ACCESS  not-accessible
    STATUS      current
    DESCRIPTION
        "The subnetwork destination mask for this xsSubnetMatrixSDEntry. This is represented as an octet string with specific semantics and length as identified by the protocolDirLocalIndex component of the index. For example, if the protocolDirLocalIndex indicates an encapsulation of ip, this object is encoded as a length octet of 4, followed by the 4 octets of the ip address, in network byte order."
    ::= { xsSubnetMatrixSDEntry 5 }

xsSubnetMatrixSDPkts OBJECT-TYPE
    SYNTAX      ZeroBasedCounter32
    MAX-ACCESS  read-only
    STATUS      current
    DESCRIPTION
        "The number of packets without errors transmitted from the  source address to the destination address since this entry was added to the xsSubnetMatrixSDTable.  Note that this is the number of  link-layer packets, so if a single network-layer packet is fragmented into several link-layer frames, this counter is incremented several times."
    ::= { xsSubnetMatrixSDEntry 6 }

xsSubnetMatrixSDCreateTime OBJECT-TYPE
    SYNTAX     LastCreateTime
    MAX-ACCESS read-only
    STATUS     current
    DESCRIPTION
        "The value of sysUpTime when this entry was last activated.  This can be used by the management station to ensure that the entry has not been deleted and recreated between polls."
    ::= { xsSubnetMatrixSDEntry 7 }


-- Traffic matrix tables from destination to source

xsSubnetMatrixDSTable OBJECT-TYPE
    SYNTAX      SEQUENCE OF XsSubnetMatrixDSEntry
    MAX-ACCESS  not-accessible
    STATUS      current
    DESCRIPTION
        "A list of traffic matrix entries which collect statistics for conversations between two subnetwork-level addresses.  This table is indexed first by the destination address and then by the source address to make it convenient to collect all conversations to a particular address. The probe will populate this table for all network layer  and application layer protocols in the protocol directory table whose value of  protocolDirMatrixConfig is equal to supportedOn(3), and will delete any entries whose protocolDirEntry is deleted or has a protocolDirMatrixConfig value of supportedOff(2). The probe will add to this table all pairs of addresses that fits the xsHostFilter. Further, this table will only contain entries that have a corresponding entry in the xsSubnetMatrixSDTable with the same source address and destination address."
    ::= { xsSubnet 5 }

xsSubnetMatrixDSEntry OBJECT-TYPE
    SYNTAX      XsSubnetMatrixDSEntry
    MAX-ACCESS  not-accessible
    STATUS      current
    DESCRIPTION
        "A conceptual row in the xsSubnetMatrixDSTable.  The hlMatrixControlIndex value in the index identifies the hlMatrixControlEntry on whose behalf this entry was created.  The protocolDirLocalIndex value in the index identifies the  network layer protocol of the xsSubnetMatrixDSSourceAddress and xsSubnetMatrixDSDestAddress.
An example of the indexing of this table is   xsSubnetMatrixDSPkts.1.783495.18.4.128.2.6.7.4.255.255.255.0.4.128.3.6.6.4.255.255.255.0.18"
    INDEX { hlMatrixControlIndex, xsSubnetMatrixDSTimeMark,
            protocolDirLocalIndex,
            xsSubnetMatrixDSDestAddress, xsSubnetMatrixDSDestMask,
	      xsSubnetMatrixDSSourceAddress, xsSubnetMatrixDSSourceMask,
            protocolDirLocalIndex }
    ::= { xsSubnetMatrixDSTable 1 }

XsSubnetMatrixDSEntry ::= SEQUENCE {
    xsSubnetMatrixDSTimeMark                 TimeFilter,
    xsSubnetMatrixDSSourceAddress            OCTET STRING,
    xsSubnetMatrixDSSourceMask            OCTET STRING,
    xsSubnetMatrixDSDestAddress              OCTET STRING,
    xsSubnetMatrixDSDestMask              OCTET STRING,
    xsSubnetMatrixDSPkts                     ZeroBasedCounter32,
    xsSubnetMatrixDSCreateTime               LastCreateTime
}

xsSubnetMatrixDSTimeMark OBJECT-TYPE
    SYNTAX      TimeFilter
    MAX-ACCESS  not-accessible
    STATUS      current
    DESCRIPTION
        "A TimeFilter for this entry.  See the TimeFilter textual convention to see how this works."
    ::= { xsSubnetMatrixDSEntry 1 }

xsSubnetMatrixDSSourceAddress OBJECT-TYPE
    SYNTAX      OCTET STRING
    MAX-ACCESS  not-accessible
    STATUS      current
    DESCRIPTION
        "The subnetwork source address for this xsSubnetMatrixDSEntry. This is represented as an octet string with specific semantics and length as identified by the protocolDirLocalIndex component of the index. For example, if the protocolDirLocalIndex indicates an encapsulation of ip, this object is encoded as a length octet of 4, followed by the 4 octets of the ip address, in network byte order."
    ::= { xsSubnetMatrixDSEntry 2 }

xsSubnetMatrixDSSourceMask OBJECT-TYPE
    SYNTAX      OCTET STRING
    MAX-ACCESS  not-accessible
    STATUS      current
    DESCRIPTION
        "The subnetwork source mask for this xsSubnetMatrixDSEntry. This is represented as an octet string with specific semantics and length as identified by the protocolDirLocalIndex component of the index. For example, if the protocolDirLocalIndex indicates an encapsulation of ip, this object is encoded as a length  octet of 4, followed by the 4 octets of the ip address, in network byte order."
    ::= { xsSubnetMatrixDSEntry 3 }

xsSubnetMatrixDSDestAddress OBJECT-TYPE
    SYNTAX      OCTET STRING
    MAX-ACCESS  not-accessible
    STATUS      current
    DESCRIPTION
        "The subnetwork destination address for this
        xsSubnetMatrixDSEntry. This is represented as an octet string with specific semantics and length as identified by the protocolDirLocalIndex component of the index. For example, if the protocolDirLocalIndex indicates an encapsulation of ip, this object is encoded as a length  octet of 4, followed by the 4 octets of the ip address,  in network byte order."
    ::= { xsSubnetMatrixDSEntry 4 }



xsSubnetMatrixDSDestMask OBJECT-TYPE
    SYNTAX      OCTET STRING
    MAX-ACCESS  not-accessible
    STATUS      current
    DESCRIPTION
        "The subnetwork destination mask for this xsSubnetMatrixDSEntry. This is represented as an octet string with  specific semantics and length as identified by the protocolDirLocalIndex component of the index. For example, if the protocolDirLocalIndex indicates an encapsulation of ip, this object is encoded as a length  octet of 4, followed by the 4 octets of the ip address, in network byte order."
    ::= { xsSubnetMatrixDSEntry 5 }

xsSubnetMatrixDSPkts OBJECT-TYPE
    SYNTAX      ZeroBasedCounter32
    MAX-ACCESS  read-only
    STATUS      current
    DESCRIPTION
        "The number of packets without errors transmitted from the  source address to the destination address since this entry was added to the xsSubnetMatrixDSTable.  Note that this is the number of link-layer packets, so if a single network-layer packet is  fragmented into several link-layer frames, this counter is incremented several times."
    ::= { xsSubnetMatrixDSEntry 6 }

xsSubnetMatrixDSCreateTime OBJECT-TYPE
    SYNTAX     LastCreateTime
    MAX-ACCESS read-only
    STATUS     current
    DESCRIPTION
        "The value of sysUpTime when this entry was last activated. This can be used by the management station to ensure that the entry has not been deleted and recreated between polls."
    ::= { xsSubnetMatrixDSEntry 7 }

-- Used for all Statistics Tables

xsNumberOfProtocols OBJECT-TYPE
        SYNTAX  Integer32 
        MAX-ACCESS read-only
        STATUS  current
        DESCRIPTION
	"This attribute contains the number of protocols in 
	the protocolDirTable."
        ::= { xsSmon 5 }
 
xsProtocolDistStatsTimeStamp OBJECT-TYPE
        SYNTAX  TimeTicks
        MAX-ACCESS read-only
        STATUS  current
        DESCRIPTION
        "This attribute contains the value of sysUpTime
        at the time protocolDistStats counters were calculated."
        ::= { xsSmon 6 }

xsNlHostTimeStamp OBJECT-TYPE
        SYNTAX  TimeTicks
        MAX-ACCESS read-only
        STATUS  current
        DESCRIPTION
        "This attribute contains the value of sysUpTime
        at the time nlHost counters were calculated."
        ::= { xsSmon 7 }

xsSubnetStatsTimeStamp OBJECT-TYPE
        SYNTAX  TimeTicks
        MAX-ACCESS read-only
        STATUS  current
        DESCRIPTION
        "This attribute contains the value of sysUpTime
        at the time xsSubnetStats counters were calculated."
        ::= { xsSmon 8 }
 
xsActiveApplications OBJECT IDENTIFIER ::= { xsSmon 9 }

xsActiveApplicationsBitMask OBJECT-TYPE
    SYNTAX  OCTET STRING (SIZE(128))
    MAX-ACCESS  read-only
    STATUS  current
    DESCRIPTION
       "The Active Applications bit mask is representing every active
       application from the first 1024 'well defined' applications. 
       Each application is represented by a single bit in the string.
       Application number 1 is represented by the first bit in the string.
       Bit value '1' means, the protocol is active.
       Bit value '0' means, the protocol is inactive.
       For example the FTP data application, assigned as number 20. 
       If the FTP application is active, then the bit number 20 will be 
       set to '1'."
::= { xsActiveApplications 1 }

xsActiveApplicationsTable OBJECT-TYPE
    SYNTAX  SEQUENCE OF XsActiveApplicationsEntry
    MAX-ACCESS  not-accessible
    STATUS  current
    DESCRIPTION
       "This table contain the 'active applications' from the 1024 
       'well defined' applications.
       For each active application, there is a global counter indicates
       the number of packets in the specific application monitored
       by the probe."
::= { xsActiveApplications 2 }

xsActiveApplicationsEntry OBJECT-TYPE
    SYNTAX  XsActiveApplicationsEntry
    MAX-ACCESS  not-accessible
    STATUS  current
    DESCRIPTION
       "The entry for the xsActiveApplicationsTable.
       For each active application, there is a global counter indicates
       the number of packets in the specific application monitored
       by the probe."
       INDEX   { xsActiveApplicationsIndex }
    ::= { xsActiveApplicationsTable  1 }

XsActiveApplicationsEntry ::=
    SEQUENCE {
        xsActiveApplicationsIndex	Integer32,
        xsActiveApplicationsPkts	Counter32
}

xsActiveApplicationsIndex OBJECT-TYPE
    SYNTAX  Integer32
    MAX-ACCESS  not-accessible
    STATUS  current
    DESCRIPTION
       "The number of the application."
    ::= { xsActiveApplicationsEntry  1 }

xsActiveApplicationsPkts OBJECT-TYPE
    SYNTAX  Counter32
    MAX-ACCESS  read-only
    STATUS  current
    DESCRIPTION
       "The number of packets of the specified application, 
       monitored by the probe."
    ::= { xsActiveApplicationsEntry  2 }

xsSmonStatus OBJECT-TYPE
    SYNTAX  INTEGER {
		operate(1),
		paused(2)
		}
    MAX-ACCESS  read-write
    STATUS  current
    DESCRIPTION
       "This item is set to value operate(1) when SMON is 
       running on the probe and paused(2) when SMON is paused.
       The status is in operate(1) value whenever there is a valid
       control or when a Console set this item to operate(1).
       The status is in paused(2) value when there is no valid control
       and the Console didnot set this item to operate(1)."
    DEFVAL {paused}
    ::= { xsSmon 10 }
-------------------------------------------------------------------
-- New Additions to the SMON2 i
-------------------------------------------------------------------
drSmon OBJECT IDENTIFIER ::= { smon 4 } 

-- A group of the proprietery SMON tree.
-- Defines the MIB objects that provide RMON-2 and SMON-2 functionality for 
-- Routing modules capable of  working in EZ2route (aka "Router-less" ) mode.
-- These modules can form a "Distributed Router", hence the name.
--Notes
--===========
--1. Device = a single management entity, distibguished by its own IP address.
--
--2. Routing modules can work in one of two modes:
--  a. Router Mode - in this mode, the routing module is considered to be a 
--	"Device", with its own IP. In this scenario, the configuration table 
--		contains a single row.
--  b. EZ2route (aka Routerless) Mode - in this mode, the routing module is 
--	registerd under the Device's Master Agent. Potentially, several
--	router modules can register their part of the table. In this scenario,
--	The moduleId (aka slot number/ group number) is used as the 
--	distribution key.
--     
--3. This MIB group is written using SMIv2, as many of its constructs are 
--     imported from RMON-2

drSmonConfiguration	OBJECT IDENTIFIER ::= { drSmon 1 }
-- A group controling the SMON2 configuration for all Routing modules in  a device.

drSmonControlTable OBJECT-TYPE
    SYNTAX      SEQUENCE OF DrSmonControlEntry
    MAX-ACCESS  not-accessible
    STATUS      current
    DESCRIPTION
        "A table configuring SMON-2 operation for each router module in a 
	device."
    ::= { drSmonConfiguration 1 }

drSmonControlEntry OBJECT-TYPE
    SYNTAX      DrSmonControlEntry
    MAX-ACCESS  not-accessible
    STATUS      current
    DESCRIPTION
        "A conceptual row in the drSmonControlTable. Configures
	the SMON-2 operation for a particular module in the device.
	The row is statically created by the agent if the module is inserted."
    INDEX { drSmonControlModuleID }
    ::= { drSmonControlTable 1 }

DrSmonControlEntry ::= SEQUENCE {
    drSmonControlModuleID        	Integer32,
    drSmonControlRowAddressAutoLearnMode	INTEGER,
    drSmonControlRoutedPackets		Counter32,
    drSmonControlProtocolDistStatsTimeStamp     TimeTicks,
    drSmonControlMatrixRows    		Integer32,
    drSmonControlMatrixCols    		Integer32
}

drSmonControlModuleID OBJECT-TYPE
SYNTAX     Integer32 (0..255)
MAX-ACCESS not-accessible
STATUS current
DESCRIPTION
	"The module group number (=slot number). Used as index."
	::= { drSmonControlEntry 1}
drSmonControlRowAddressAutoLearnMode OBJECT-TYPE
SYNTAX	INTEGER {
                    enable(1),
		    disable(2), 
		    notSupported(255)
                }
MAX-ACCESS read-write
STATUS current
DESCRIPTION
	"Controls whether the embedded SMON application populates the 
	matrix Rows with automatically-learned addresses in addition to 
	those specified in the filter table. 
	enable(1) - turns auto-learn on
	disable(2) - turns auto-learn off

	This toggle is meaningless in modes other than nl/al matrix."
	::= { drSmonControlEntry 2 }

drSmonControlRoutedPackets OBJECT-TYPE
SYNTAX     Counter32
MAX-ACCESS read-only
STATUS current
DESCRIPTION
	"The number of packets routed by the 3rd-layer forwarding hardware
	 of this module."
	::= { drSmonControlEntry 3}
drSmonControlProtocolDistStatsTimeStamp OBJECT-TYPE
        SYNTAX  TimeTicks
        MAX-ACCESS read-only
        STATUS  current
        DESCRIPTION
        "This attribute contains the value of sysUpTime
        at the time protocolDistStats counters were determined by the agent."
        ::= { drSmonControlEntry 4}
drSmonControlMatrixRows OBJECT-TYPE
SYNTAX     Integer32 (0..2147483647)
MAX-ACCESS read-only
STATUS current
DESCRIPTION
	"The number of rows in the device entity matrix/table for the current 
	counting mode. Applicable to counting mode capable of supporting one 
	or more of the following statistics:
	nlHost, nlMatrix, alHost and alMatrix. 
	For modes not supporting entity (host, subnet, or RNR group) tables/
	matrices, this counter will be 0"  
	::= { drSmonControlEntry 5}
drSmonControlMatrixCols OBJECT-TYPE
SYNTAX     Integer32 (0..2147483647)
MAX-ACCESS read-only
STATUS current
DESCRIPTION
	"The number of columns in the device entity matrix/table for the 
	current counting mode. 
	Applicable to counting mode capable of supporting one 
	or more of the following statistics:
	nlHost, nlMatrix, alHost and alMatrix. 
	For modes not supporting entity (host, subnet, or RNR group) tables/
	matrices, this counter will be 0"  
	::= { drSmonControlEntry 6}

------------------------------------------------------------------
drSmonEntityPlacementTable OBJECT-TYPE
    SYNTAX      SEQUENCE OF DrSmonEntityPlacementEntry
    MAX-ACCESS  not-accessible
    STATUS      current
    DESCRIPTION
        "A table containging a set of tables. 	Each table reports the 
	placment of entities in the counter matrix/table of a
	particular module. Entities could be IP hosts, IP subnets, or other 
	3rd layer groups specified in IP-address/SubnetMask format, for which 
	the device is capable of assigning an entry in its counter 
	matrix/table."
    ::= { drSmonConfiguration 2 }
drSmonEntityPlacementEntry OBJECT-TYPE
    SYNTAX      DrSmonEntityPlacementEntry
    MAX-ACCESS  not-accessible
    STATUS      current
    DESCRIPTION
        "A conceptual row in the drSmonEntityPlacementTable. Reports the index
	of a entity in the device's counter marix/table. 
	Reports the creator of this entity - filter table or device's internal 
	auto-learn process."     
    INDEX { drSmonEntityPlacementModuleID, drSmonEntityPlacementIndex }
    ::= { drSmonEntityPlacementTable 1 }

DrSmonEntityPlacementEntry ::= SEQUENCE {
    drSmonEntityPlacementModuleID        	Integer32,
    drSmonEntityPlacementIndex    		Integer32,
    drSmonEntityPlacementAddress    		IpAddress,
    drSmonEntityPlacementMask    		IpAddress,
    drSmonEntityPlacementType			INTEGER
}

drSmonEntityPlacementModuleID OBJECT-TYPE
SYNTAX     Integer32 (0..255)
MAX-ACCESS not-accessible
STATUS current
DESCRIPTION
	"The module group number (=slot number). Used as index."
	::= { drSmonEntityPlacementEntry 1}

drSmonEntityPlacementIndex OBJECT-TYPE
SYNTAX     Integer32 (1..2147483647)
MAX-ACCESS not-accessible
STATUS current
DESCRIPTION
	"The placment index of the particular entity. 
	The index determines the position of the entity in the counter 
	matrix/table.
	Example:
	For a matrix of A rows x B columns and index i:
	If i<A then 
		host is both on row i and column i
	else 
		host is on column i.
        The agent must provide entries in this table for all the 
        index values in the range of 1..(drSmonControlMatrixRows-1)
        Row 0 of a matrix/table is reserved for 'Others' entity, and is not
        reported in this MIB table."
	::= { drSmonEntityPlacementEntry 2}

drSmonEntityPlacementAddress OBJECT-TYPE
SYNTAX     IpAddress
MAX-ACCESS read-only
STATUS current
DESCRIPTION
	"The IP address of an entity  to explicitly monitor"
	::= { drSmonEntityPlacementEntry 3}
drSmonEntityPlacementMask OBJECT-TYPE
SYNTAX     IpAddress
MAX-ACCESS read-only
STATUS current
DESCRIPTION
	"The subnet mask of an entity. The value 
	255.255.255.255 signifies that this entity is a host."
	::= { drSmonEntityPlacementEntry 4}

drSmonEntityPlacementType OBJECT-TYPE
SYNTAX      INTEGER {
                    empty(1),
                    autoLearn(2),
                    filter(3)
                }
MAX-ACCESS read-only
STATUS current
DESCRIPTION
	"The Type of this entity:
	empty(1) - Contains no relevant information. Not yet allocated to
	a specific entity.
	autoLearn(2) -  The entity was learned by the auto-learn process of  
			the device. 
	filter(3) - The entity was created by a relevant filter entry in 
	the filter table. "
	::= { drSmonEntityPlacementEntry 5}
-- *****************************************************
drSmonProtocolDir OBJECT IDENTIFIER ::= { drSmon 2}
-- A group mirroring RMON-II protocol-dir group, in a 
-- per-module fashion. This group is supported only in EZ2route mode.
--
-- Protocol Directory Group
--
-- Lists the inventory of protocols the probe has the capability of
-- monitoring and allows the addition, deletion, and configuration of
-- entries in this list.

drSmonProtocolDirLCTable OBJECT-TYPE
    SYNTAX      SEQUENCE OF  DrSmonProtocolDirLCEntry
    MAX-ACCESS  not-accessible
    STATUS      current
    DESCRIPTION
        "A table with protocolDirLastChange per module."
    ::= { drSmonProtocolDir 1 }

drSmonProtocolDirLCEntry OBJECT-TYPE
    SYNTAX       DrSmonProtocolDirLCEntry
    MAX-ACCESS  not-accessible
    STATUS      current
    DESCRIPTION
        "A conceptual row in the drSmonProtocolDirLastChangeTable. Contains
	information for a particular module."
    INDEX { 	 drSmonProtocolDirLCModuleID }
    ::= { drSmonProtocolDirLCTable  1 }

DrSmonProtocolDirLCEntry ::= SEQUENCE {
    drSmonProtocolDirLCModuleID        	Integer32,
    drSmonProtocolDirLCLastChange           TimeStamp
    }
	 
drSmonProtocolDirLCModuleID OBJECT-TYPE
SYNTAX     Integer32 (0..255)
MAX-ACCESS not-accessible
STATUS current
DESCRIPTION
	"The module group number (=slot number). Used as index."
	::= { drSmonProtocolDirLCEntry 1}

drSmonProtocolDirLCLastChange OBJECT-TYPE
    SYNTAX      TimeStamp
    MAX-ACCESS  read-only
    STATUS      current
    DESCRIPTION
        "Same function as RFC 2021 protocolDirLastChange, 
	but for a particular module."
    ::= { drSmonProtocolDirLCEntry 2 }


drSmonProtocolDirTable OBJECT-TYPE
    SYNTAX      SEQUENCE OF DrSmonProtocolDirEntry
    MAX-ACCESS  not-accessible
    STATUS      current
    DESCRIPTION
        "This table contain a set of protocolDirTables. Each protocolDirTable 		lists the protocols that a particular  module  has the
        capability to decode and count.  There is one entry in the per-module
        table for each such protocol.  These protocols represent
        different network layer, transport layer, and higher-layer
        protocols."
    ::= { drSmonProtocolDir 2 }

drSmonProtocolDirEntry OBJECT-TYPE
    SYNTAX      DrSmonProtocolDirEntry
    MAX-ACCESS  not-accessible
    STATUS      current
    DESCRIPTION
        "A conceptual row in the drSmonProtocolDirTable. Represent a protocol to
	monitor on a particulat module. All fields except for 
	drSmonProtocolDirModuleID have the same function as in RFC 2021
	protocolDirTable.
         An example of the indexing of this entry is
         drSmonProtocolDirLocalIndex.3.8.0.0.0.1.0.0.8.0.2.0.0, which is a 
	 protocol for module 3 with the
         encoding of a length of 8, followed by 8 subids encoding the
         drSmonProtocolDirID of 1.2048, followed by a length of 2 and the
         2 subids encoding zero-valued parameters."
    INDEX { drSmonProtocolDirModuleID,drSmonProtocolDirID, drSmonProtocolDirParameters }
    ::= { drSmonProtocolDirTable  1 }

DrSmonProtocolDirEntry ::= SEQUENCE {
    drSmonProtocolDirModuleID        	Integer32,
    drSmonProtocolDirID                   OCTET STRING,
    drSmonProtocolDirParameters           OCTET STRING,
    drSmonProtocolDirLocalIndex           Integer32,
    drSmonProtocolDirDescr                DisplayString,
    drSmonProtocolDirType                 BITS,
    drSmonProtocolDirAddressMapConfig     INTEGER,
    drSmonProtocolDirHostConfig           INTEGER,
    drSmonProtocolDirMatrixConfig         INTEGER,
    drSmonProtocolDirOwner                OwnerString,
    drSmonProtocolDirStatus               RowStatus
}
drSmonProtocolDirModuleID OBJECT-TYPE
SYNTAX     Integer32 (0..255)
MAX-ACCESS not-accessible
STATUS current
DESCRIPTION
	"The module group number (=slot number). Used as index."
	::= { drSmonProtocolDirEntry 1}

drSmonProtocolDirID OBJECT-TYPE
    SYNTAX      OCTET STRING
    MAX-ACCESS  not-accessible
    STATUS      current
    DESCRIPTION
        "A unique identifier for a particular protocol.  
	same as RFC 2021, but for a particular module."
    ::= { drSmonProtocolDirEntry 2 }

drSmonProtocolDirParameters OBJECT-TYPE
    SYNTAX      OCTET STRING
    MAX-ACCESS  not-accessible
    STATUS      current
    DESCRIPTION
        "A set of parameters for the associated drSmonProtocolDirID.
	Same as RFC 2021, but for a particular module."
    ::= { drSmonProtocolDirEntry 3 }

drSmonProtocolDirLocalIndex OBJECT-TYPE


    SYNTAX      Integer32 (1..2147483647)
    MAX-ACCESS  read-only
    STATUS      current
    DESCRIPTION
        "The locally arbitrary, but unique identifier associated
        with this drSmonProtocolDir entry.
	Same as RFC 2021, but for a particular module."
    ::= { drSmonProtocolDirEntry 4 }

drSmonProtocolDirDescr OBJECT-TYPE
    SYNTAX      DisplayString (SIZE (1..64))
    MAX-ACCESS  read-create
    STATUS      current
    DESCRIPTION
        "A textual description of the protocol encapsulation.
	Same as RFC 2021, but for a particular module."
    ::= { drSmonProtocolDirEntry 5 }

drSmonProtocolDirType OBJECT-TYPE
    SYNTAX      BITS 
		{
                    extensible(0),
                    addressRecognitionCapable(1)
                }
    MAX-ACCESS  read-only
    STATUS      current
    DESCRIPTION
        "This object describes 2 attributes of this protocol
         directory entry.
	Same as RFC 2021, but for a particular module."
    ::= { drSmonProtocolDirEntry 6 }

drSmonProtocolDirAddressMapConfig OBJECT-TYPE
    SYNTAX      INTEGER {
                    notSupported(1),
                    supportedOff(2),
                    supportedOn(3)
                }
    MAX-ACCESS  read-create
    STATUS      current
    DESCRIPTION
        "This object describes and configures the probe's support for
        address mapping for this protocol.  
	Same as RFC 2021, but for a particular module."

    ::= { drSmonProtocolDirEntry 7 }

drSmonProtocolDirHostConfig OBJECT-TYPE
    SYNTAX      INTEGER {
                    notSupported(1),
                    supportedOff(2),
                    supportedOn(3)
                }
    MAX-ACCESS  read-create
    STATUS      current
    DESCRIPTION
        "This object describes and configures the probe's support for
        the network layer and application layer host tables for this
        protocol.  
	Same as RFC 2021, but for a particular module."
    ::= { drSmonProtocolDirEntry 8 }

drSmonProtocolDirMatrixConfig OBJECT-TYPE
    SYNTAX      INTEGER {
                    notSupported(1),
                    supportedOff(2),
                    supportedOn(3)
                }
    MAX-ACCESS  read-create
    STATUS      current
    DESCRIPTION
        "This object describes and configures the probe's support for
        the network layer and application layer matrix tables for this
        protocol.  
	Same as RFC 2021, but for a particular module."
    ::= { drSmonProtocolDirEntry 9 }

drSmonProtocolDirOwner OBJECT-TYPE
    SYNTAX      OwnerString
    MAX-ACCESS  read-create
    STATUS      current
    DESCRIPTION
        "The entity that configured this entry and is
        therefore using the resources assigned to it."
    ::= { drSmonProtocolDirEntry 10 }

drSmonProtocolDirStatus OBJECT-TYPE
    SYNTAX      RowStatus
    MAX-ACCESS  read-create
    STATUS      current
    DESCRIPTION
        "The status of this protocol directory entry.
	Same as RFC 2021, but for a particular module."
    ::= { drSmonProtocolDirEntry 11 }
-- *****************************************************
drSmonFilter	OBJECT IDENTIFIER ::= { drSmon 3}
-- A group controling the SMON2 filtering table(s)

drSmonFilterTable OBJECT-TYPE
    SYNTAX      SEQUENCE OF DrSmonFilterEntry
    MAX-ACCESS  not-accessible
    STATUS      current
    DESCRIPTION
        "A table containging a set of tables. Each table configure hosts and 
	subnets to explicitly monitor in a particular module. "
    ::= { drSmonFilter 1 }

drSmonFilterEntry OBJECT-TYPE
    SYNTAX      DrSmonFilterEntry
    MAX-ACCESS  not-accessible
    STATUS      current
    DESCRIPTION
        "A conceptual row in the drSmonFilterTable. Configures a host or 
	subnet to monitor in a particular module, at a particular row or 
	column. Typically, the NMS application conifgures these entries.
	"
    INDEX { drSmonFilterModuleID, drSmonFilterIndex }
    ::= { drSmonFilterTable 1 }

DrSmonFilterEntry ::= SEQUENCE {
    drSmonFilterModuleID        	Integer32,
    drSmonFilterIndex    		Integer32,
    drSmonFilterAddress    		IpAddress,
    drSmonFilterMask    		IpAddress,
    drSmonFilterStatus			RowStatus
}

drSmonFilterModuleID OBJECT-TYPE
SYNTAX     Integer32 (0..255)
MAX-ACCESS not-accessible
STATUS current
DESCRIPTION
	"The module group number (=slot number). Used as index."
	::= { drSmonFilterEntry 1}

drSmonFilterIndex OBJECT-TYPE
SYNTAX     Integer32 (1..2147483647)
MAX-ACCESS not-accessible
STATUS current
DESCRIPTION
	"The index of the particular host/subnet. The index determines the 
	position of the host/subnet in the counter matrix.
	Example:
	For a matrix of A rows x B columns and index i:
	If i<A then 
		host is both on row i and column i
	else 
		host is on column i."
	::= { drSmonFilterEntry 2}

drSmonFilterAddress OBJECT-TYPE
SYNTAX     IpAddress
MAX-ACCESS read-create
STATUS current
DESCRIPTION
	"The IP address of a host or subnet to explicitly monitor"
	::= { drSmonFilterEntry 3}
drSmonFilterMask OBJECT-TYPE
SYNTAX     IpAddress
MAX-ACCESS read-create
STATUS current
DESCRIPTION
	"The Mask of a host or subnet to explicitly monitor. The value 
	255.255.255.255 signifies that this entry is a host entry."
	::= { drSmonFilterEntry 4}

drSmonFilterStatus OBJECT-TYPE
SYNTAX     RowStatus
MAX-ACCESS read-create
STATUS current
DESCRIPTION
	"The status of the row, as per SMIv2 (RFC1903). The row is in 
	read-only mode when the status is set to active(1). Only active rows 
	are used as filters."
	::= { drSmonFilterEntry 5}
-- *****************************************************
drSmonActiveApplications OBJECT IDENTIFIER ::= { drSmon 4 }
-- This group contains information on the protocols detected by the modules
-- In the protocol distribution mode. It is similar in concept to
-- the xsActiveApplications group for the MMLS, with the following
-- differences:
-- a. Distribution accross modules
-- b. Support for both a TCP and a UDP port range, as well as other non TCP/UDP
-- protocols
drSmonActiveApplicationsTable OBJECT-TYPE
    SYNTAX  SEQUENCE OF DrSmonActiveApplicationsEntry
    MAX-ACCESS  not-accessible
    STATUS  current
    DESCRIPTION
       "This table contain the 'active applications' or protocols from all
       the protocols the modules can detect. 'Activity' is determined and
       reported by each module, in a sub-table of this table.
       The table contain entries only for 'Active' protocols.
       For each active application, there is a global counter indicates
       the number of packets in the specific application monitored
       by a module."
::= { drSmonActiveApplications 1 }

drSmonActiveApplicationsEntry OBJECT-TYPE
    SYNTAX  DrSmonActiveApplicationsEntry
    MAX-ACCESS  not-accessible
    STATUS  current
    DESCRIPTION
       "The entry for the drSmonActiveApplicationsTable.
       A set of entries exist for each module.
       For each active application,  a global counter indicates
       the number of packets in the specific application monitored
       by the module. Entries exist only for 'active' applications."
       INDEX   { drSmonActiveApplicationsModuleID,drSmonActiveApplicationsType,
       		drSmonActiveApplicationsSubType }
    ::= { drSmonActiveApplicationsTable  1 }

DrSmonActiveApplicationsEntry ::= SEQUENCE {
        drSmonActiveApplicationsModuleID	Integer32,
        drSmonActiveApplicationsType	INTEGER,
        drSmonActiveApplicationsSubType	Integer32,
        drSmonActiveApplicationsPkts	Counter32
}

drSmonActiveApplicationsModuleID OBJECT-TYPE
SYNTAX     Integer32 (0..255)
MAX-ACCESS not-accessible
STATUS current
DESCRIPTION
	"The module group number (=slot number). Used as index."
	::= { drSmonActiveApplicationsEntry  1 }

drSmonActiveApplicationsType OBJECT-TYPE
SYNTAX    INTEGER {
	ethertype(1),
	ipProtocol(2),
	udpProtocol(3),
	tcpProtocol(4)
               }
MAX-ACCESS not-accessible
STATUS current
DESCRIPTION
	"The major type of the application. Note that TCP and UDP are 
	assumed to be 
	over IP. "
	::= { drSmonActiveApplicationsEntry  2 }

drSmonActiveApplicationsSubType OBJECT-TYPE
    SYNTAX  Integer32
    MAX-ACCESS  not-accessible
    STATUS  current
    DESCRIPTION
       "The application's sub-type value depends on the value of the type:
       Type             sub-type value 
       ===========      ==============
       ethertype(1)     1 - Sum of all IP traffic
                        2 - ARP traffic
       ipProtocol(2)    1 - ICMP traffic
                        2 - OSPF traffic
                        3 - Sum of all UDP traffic
                        4 - Sum of all TCP traffic
			5 - VRRP traffic
       udpProtocol(3)     - The SubType is the UDP port number
       tcpProtocol(4)     - The SubType is the TCP port number

       "
    ::= { drSmonActiveApplicationsEntry  3 }

drSmonActiveApplicationsPkts OBJECT-TYPE
     SYNTAX  Counter32
     MAX-ACCESS  read-only
     STATUS  current
     DESCRIPTION
        "The number of packets of the specified application 
        monitored by the probe."
     ::= { drSmonActiveApplicationsEntry  4 }


END
