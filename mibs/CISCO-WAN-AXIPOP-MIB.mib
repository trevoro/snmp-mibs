-- LAST-UPDATED "200206260000Z"
CISCO-WAN-AXIPOP-MIB DEFINITIONS ::= BEGIN

IMPORTS
Counter,IpAddress,Gauge    FROM RFC1155-SMI 
OBJECT-TYPE                            FROM RFC-1212 
DisplayString                          FROM RFC1213-MIB 
atm,atmAddressRegistration,cardGeneric,axisDiagnostics,cardSpecific,
basisLines,atmLmiSignaling,ausmPortCnf,ausmChan,cesmChan,ausmPort,
circuitEmulation,frChan,frameRelay,x21,frPortCntSig,frPortCnfSig,
basisAsm,frPortCnfResPartGrp,vismChanCnfGrp,vismPort,vismChanGrp,dsx0Vism,
voice,frPortCnt,frPortCnf,frPortServiceQueGrp,frPortCnfX21PortGrp,
frPort,ausmPortCnt,virtualInterface,rpmInterface,bbIfCnf,
bbIfCnfResPartGrp, bbIfStateGrp, bbIfCnt,bbChanCnfGrp,
bbChanStateGrp, bbChanCntGrp,atmLineCnfGrp,atmLineCntGrp,rpmPort,
rpmChanGrp,par  FROM BASIS-MIB; 
AtmAddress ::= OCTET STRING (SIZE (0 .. 32))
RpmNsapAddress ::= OCTET STRING (SIZE(20))
IfNsapAddress ::= OCTET STRING (SIZE ( 20 ))
-- Important : NetPrefix :: SIZE must be either 8 or 13. Nothing else.
-- NetPrefix ::= OCTET STRING (SIZE (8 | 13))
NetPrefix ::= OCTET STRING (SIZE (8 .. 13))





-- Textual Conventions

-- All representations of ATM addresses in this MIB Module use 
-- the data type:


--  The MIB groups

atmAddressGroup   	OBJECT IDENTIFIER ::= { atmAddressRegistration 2 }


--
-- The Address Table
--
atmAddressTable OBJECT-TYPE
    SYNTAX      SEQUENCE OF AtmAddressEntry
    ACCESS      not-accessible
    STATUS      mandatory
    DESCRIPTION
              "A table implemented by the network-side of an ATM UNI port, containing
	      the ATM-layer addresses in effect on the user-side of the UNI."
    ::= { atmAddressGroup 1 }

atmAddressEntry OBJECT-TYPE
    SYNTAX      AtmAddressEntry
    ACCESS      not-accessible
    STATUS      mandatory
    DESCRIPTION
              "Information about a single ATM-layer address in effect on the user-side
	      of a UNI port."
    INDEX    { axisAtmAddressPort, axisAtmAddressAtmAddress}
    ::= { atmAddressTable 1 }

AtmAddressEntry ::= SEQUENCE {
    axisAtmAddressPort             INTEGER,
    axisAtmAddressAtmAddress       AtmAddress,
    axisAtmAddressStatus           INTEGER
}

axisAtmAddressPort  OBJECT-TYPE
    SYNTAX      INTEGER (0..2147483647)
    ACCESS      read-only
    STATUS      mandatory
    DESCRIPTION
              "A unique value which identifies this port. The value of
              0 has the special meaning of identifying the local UNI."
    ::= { atmAddressEntry 1 }

axisAtmAddressAtmAddress OBJECT-TYPE
    SYNTAX      AtmAddress
    ACCESS      read-only
    STATUS      mandatory
    DESCRIPTION
              "The ATM address which is in effect on the user-side of the ATM UNI port."
    ::= { atmAddressEntry 2 }

axisAtmAddressStatus OBJECT-TYPE
    SYNTAX      INTEGER {
                    valid(1),
                    invalid(2)
                }
    ACCESS      read-only
    STATUS      mandatory
    DESCRIPTION
              "An indication of the validity of the ATM address at
	      the user-side of the UNI port."
    ::= { atmAddressEntry 3 }









-- Textual Conventions

-- All representations of prefixes in this MIB Module use 
-- the data type:


--  The MIB groups
atmNetPrefixGroup    	OBJECT IDENTIFIER ::= { atmAddressRegistration 1 }


--  The Network Prefix Table


atmNetPrefixTable OBJECT-TYPE
    SYNTAX      SEQUENCE OF AtmNetPrefixEntry
    ACCESS      not-accessible
    STATUS      mandatory
    DESCRIPTION
              "A table implemented by the UNI Management Entity on the user-side of an
	      ATM UNI port, containing the network-prefix(es) for ATM-layer addresses
	      in effect on the user-side of the UNI."
    ::= { atmNetPrefixGroup 1 }

atmNetPrefixEntry OBJECT-TYPE
    SYNTAX      AtmNetPrefixEntry
    ACCESS      not-accessible
    STATUS      mandatory
    DESCRIPTION
              "An entry in the table, containing information about
              the ATM Prefix status."
    INDEX    { axisAtmNetPrefixPort, axisAtmNetPrefixPrefix }
    ::= { atmNetPrefixTable 1 }

AtmNetPrefixEntry ::= SEQUENCE {
    axisAtmNetPrefixPort             INTEGER,
    axisAtmNetPrefixPrefix           NetPrefix,
    axisAtmNetPrefixAdminStatus      INTEGER,
    axisAtmNetPrefixOperStatus       INTEGER
}

axisAtmNetPrefixPort OBJECT-TYPE
    SYNTAX      INTEGER (0..2147483647)
    ACCESS      read-only
    STATUS      mandatory
    DESCRIPTION
              "The unique value which identifies the ILMI port."
    ::= { atmNetPrefixEntry 1 }

axisAtmNetPrefixPrefix OBJECT-TYPE
    SYNTAX      NetPrefix
    ACCESS      read-only
    STATUS      mandatory
    DESCRIPTION
              "The network prefix for ATM addresses which is in effect
	       on the user-side of the ATM UNI port."
    ::= { atmNetPrefixEntry 2 }

axisAtmNetPrefixAdminStatus OBJECT-TYPE
    SYNTAX      INTEGER {
                    valid(1),
                    invalid(2)
                }
    ACCESS      read-write
    STATUS      mandatory
    DESCRIPTION
              "An indication of the validity of the network prefix for ATM addresses,
	      on the user-side of the UNI port."
    ::= { atmNetPrefixEntry 3 }

axisAtmNetPrefixOperStatus OBJECT-TYPE
    SYNTAX      INTEGER {
                    registering(1),
                    de-registering(2),
		    registered(3),
		    de-registered(4),
		    failRegistering(5),
		    failDe-registering(6)
                }
    ACCESS      read-only
    STATUS      mandatory
    DESCRIPTION
              "An indication of the current registration state for the prefix:
	      registering, de-registering, success, fail."
    ::= { atmNetPrefixEntry 4 }





-- ------------------------------------------------------------------
--
-- BASIS project  CARD SPECIFIC SM MIB
-- 
-- 
-- Created by Shawn K. 5/17/95 
--
-- ------------------------------------------------------------------




cardResourcePartition	OBJECT IDENTIFIER ::= {cardGeneric 9}

-- ------------------------------------------------------------------
--
--  Group "cardResourcePartition"
--  Service Module Card Resource Partition Related MIB.
--
-- ------------------------------------------------------------------
cardLcnPartitionType	OBJECT-TYPE
	SYNTAX 	INTEGER
	{
	  noPartition (1),
	  controllerBased (2),
	  portControllerBased (3)
	}
	ACCESS 	read-write
	STATUS 	mandatory
	DESCRIPTION
		"This object specified the type of partition on LCN:
		 1. noPartition -- means that all controllers compete for
		    		    the totoal (G)LCNs limited by the card

		 2. controllerBased -- means that the total number of (G)LCNs
					available to each controller is
					fixed but no reservation on each port.
					The number for each controller is 
					specified in the smCardResPartGrpTable.
					
		 3. portControllerBased -- means that a certain number of 
					(G)LCNs available on each port for each
					controller is reserved, it is 
					specified in the port resouce 
					partition table.
		 NOTE: This object has to be configured before adding any 
		       connections and once a connection is added, this object
		       cannot be changed until all of the connections are
		       deleted.
		"
	DEFVAL {noPartition}
	::= {cardResourcePartition 1}


cardResPartGrpTable	OBJECT-TYPE
	SYNTAX	SEQUENCE OF CardResPartGrpEntry
	ACCESS	not-accessible
	STATUS	mandatory
	DESCRIPTION
		"This table contains the configuration of all 
		 the resource partition(s) that are on the card level, 
		 such as (G)LCN (if the object cardLcnPartitionType is 
		 configured as controller-based, if not, there is no
		 need to configure this table since it'll be useless).
		"
	::= {cardResourcePartition 2}

cardResPartGrpEntry	OBJECT-TYPE
	SYNTAX	CardResPartGrpEntry
	ACCESS	not-accessible
	STATUS	mandatory
	DESCRIPTION
		"This is an entry for a controller
		"
	INDEX { cardResPartCtrlrNum }
	::= {cardResPartGrpTable 1}

CardResPartGrpEntry ::=
	SEQUENCE {
		cardResPartCtrlrNum		INTEGER,
		cardResPartRowStatus		INTEGER,
		cardResPartNumOfLcnAvail	INTEGER
	}

cardResPartCtrlrNum	OBJECT-TYPE
	SYNTAX	INTEGER
		{
		par (1),
		pnni (2),
		tag (3)
		}
	ACCESS	read-only
	STATUS	mandatory
	DESCRIPTION
		"This object is the index to the table
		"
	::= { cardResPartGrpEntry 1 }

cardResPartRowStatus	OBJECT-TYPE
	SYNTAX	INTEGER
		{
		add (1),
		del (2),
		mod (3)
		}
	ACCESS	read-write
	STATUS	mandatory
	DESCRIPTION
		"This object is records the status of this entry
		"
	::= {cardResPartGrpEntry 2 }

cardResPartNumOfLcnAvail	OBJECT-TYPE
	SYNTAX	INTEGER
	ACCESS	read-write
	STATUS	mandatory
	DESCRIPTION
		"This object is configured to reserve the number of 
		 (G)LCNs for one controller on a SM card, it can be used
		 on any port but the total number of connections added
		 on all of the ports for that particular controller
		 cannot exceed this number.
		"
	::= {cardResPartGrpEntry 3 }

-- ----------------------------------------------------------------------
--
-- AXIS project  ONLINE DIAGNOSTICS MIB
--
--  MIB dated  11/01/99
--  for ONLINE DIAGNOSTICS
--
-- ----------------------------------------------------------------------



onlineDiagnostics         OBJECT IDENTIFIER ::= { axisDiagnostics 3 }


diagType        OBJECT-TYPE
        SYNTAX  INTEGER {
                            post(1),
                            onlinediag(2)
                        }
        ACCESS  read-only
        STATUS  mandatory
        DESCRIPTION
                "This is used to identify the type of diagnostics.
                 When a trap is sent to report diagnostics results
                 this is used as a varbind to indicate the type of diagnostics.
                "
        ::= { onlineDiagnostics 1 }


diagResult     OBJECT-TYPE
        SYNTAX  INTEGER {
                            passed(1),
                            failed(2)
                        }
        ACCESS  read-only
        STATUS  mandatory
        DESCRIPTION
                "This is used to indicate the result of the diagnostics
                 tests in traps.
                "
        ::= { onlineDiagnostics 2 }


diagTestId     OBJECT-TYPE
        SYNTAX  INTEGER 
        ACCESS  read-only
        STATUS  mandatory
        DESCRIPTION
                "This is used to indicate the test number of the
                 diagnostics test that failed.
                "
        ::= { onlineDiagnostics 3 }

-- ----------------------------------------------------------------------
--
-- AXIS project  DIAGNOSTICS MIB
--
--  MIB dated  12/12/1996.  Rev 2.0
--  for BERT
--
-- ----------------------------------------------------------------------
 
 
 
bert                       OBJECT IDENTIFIER ::= { axisDiagnostics   1 }
 
bertControl  OBJECT-TYPE
        SYNTAX  INTEGER {
                acquireBert        (1),
                releaseBert        (2),
                cnfBert            (3),
                startBert          (4),
                modBert            (5),
                delBert            (6)
                }
        ACCESS  read-write
        STATUS  mandatory
        DESCRIPTION
             "This object controls all the SET operations on this MIB group. 
              acquireBert :  Acquire BERT resources.
              cnfBert     :  Configure the required BERT test.
              startBert   :  The configured test has to be started.
              modBert     :  Modify parameters for the ongoing BERT test.
              delBert     :  Running BERT test has to be stopped.
              The above list shows the sequence in which the SET operations 
              on this group need to be done, ideally.
	      Bert can be operated upon only with bertUserId and bertSlotNumber.
	      The default value is 0, means no action.
             " 

        ::= { bert 1 }



bertResourceStatus   OBJECT-TYPE
        SYNTAX  INTEGER {
                        free(1),
                        inUse(2),
                        cleanupPending(3)
                        }
        ACCESS  read-only
        STATUS  mandatory
        DESCRIPTION
             "All of bert resources can be used by only one user at a time.
              This gives the status of the resources.
             " 
        DEFVAL { free }

        ::= { bert 2 }



bertOwner   OBJECT-TYPE
        SYNTAX        DisplayString 
        ACCESS        read-only
        STATUS        mandatory
        DESCRIPTION
             "This refers to the user who owns the BERT resources.
              If the user is a CLI user, then this is username.
              If it is SV+, then this would be the IP address.
              For example, this value can be, 192.9.209.157 within quotes.
             "

        ::= { bert 3 }



bertUserId  OBJECT-TYPE
        SYNTAX        DisplayString 
        ACCESS        read-write
        STATUS        mandatory
        DESCRIPTION
             "This identifies the user who wants to do a SET operation
              on this group. This will be compared against bertOwner
              and access will be given only if it matches. Hence, for
              every SET request, this object should have a valid value.
              If the user is a CLI user, then this is username.
              If it is SV+, then this would be the IP address.
              For example, this value can be, 192.9.209.157 within quotes.
	      Required for bert operations.
             "

        ::= { bert 4 }



bertStatus   OBJECT-TYPE
        SYNTAX  INTEGER {
                        inactive(1),
                        bertInSync(2),
                        bertOutOfSync(3),
                        searchingDDSCommands(4),
                        farEndInLoop(5),
                        facilityInLoop(6),
                        portFacilityFifoFault(7),
                        portFacilityFifoOutOfSync(8),
                        metallicInLoop(9),
                        bertFailed(10)
                        }
        ACCESS  read-only
        STATUS  mandatory
        DESCRIPTION
             "This variable provides the status of BERT in the shelf.
             " 
        DEFVAL { inactive }

        ::= { bert 5 }



bertSlotNumber    OBJECT-TYPE
        SYNTAX  INTEGER (1..30)
        ACCESS  read-write
        STATUS  mandatory
        DESCRIPTION
             "specifies the physical slot number of the Service Module 
              which is to run BERT 
	      For MGX 8220, the range is 5-14.
	      For MGX 8850, the range is 1-6, 9-14, 17-22, 25-30.
	      Required for bert operations.

             " 

        ::= { bert 6 }

bertTestMedium  OBJECT-TYPE
        SYNTAX  INTEGER {
                        port(1),
                        line(2)
                        }
        ACCESS  read-write
        STATUS  mandatory
        DESCRIPTION
             "specifies whether the bert is to test a port or an 
              entire T1/E1 line.
	      No default value for this, it has to be set if bert is configured.
             " 

        ::= { bert 7 }



bertPort   OBJECT-TYPE
        SYNTAX  INTEGER
        ACCESS  read-write
        STATUS  mandatory
        DESCRIPTION
             "specifies the port number for BERT.
             " 

        ::= { bert 8 }




bertLine   OBJECT-TYPE
        SYNTAX  INTEGER
        ACCESS  read-write
        STATUS  mandatory
        DESCRIPTION
             "specifies the line number for BERT. If the test medium
              is port, this represents the line to which the port belongs.
             " 
        ::= { bert 9 }




bertMode   OBJECT-TYPE
        SYNTAX  INTEGER {
                        bertPatternTest(1),
                        ddsSeek(2),
                        loopback(3)
                        }
        ACCESS  read-write
        STATUS  mandatory
        DESCRIPTION
             "specifies the mode, the BERT module is to be configured for.
             " 
        ::= { bert 10 }



bertDeviceToLoop  OBJECT-TYPE
                SYNTAX  INTEGER  {
                        noLatchOCUwith1         (1),
                        noLatchOCUwitout1       (2),
                        noLatchCSU              (3),
                        noLatchDSU              (4),
                        latchDS0Drop            (5),
                        latchDS0Line            (6),
                        latchOCU                (7),
                        latchCSU                (8),
                        latchDSU                (9),
                        latchHL96               (10),
                        v54Polynomial           (11),
                        inband                  (12),
                        esf                     (13),
                        metallic                (14),
                        noDevice                (15),
                        smartJackInband         (16)
                }
                ACCESS  read-write
                STATUS  mandatory
                DESCRIPTION
                     "This shows the type of the end device and the type of the 
                      loopback used (latching/nonlatching/polynomial).
                     " 

        ::= { bert 11 }


bertDS0DPIterationCount   OBJECT-TYPE
        SYNTAX        INTEGER (1..32) 
        ACCESS        read-write
        STATUS        mandatory
        DESCRIPTION
             "The Iteration Register needs to be programmed in SRM when
              DSO drop loop option is selected in bertDeviceToLoop. The
              value to be programmed there is minus one of this object value, 
              since the register is 0 based.  DSP-OP devices can be cross 
              connected in the centeral office. By this, the user has 
              capablitiy to put any of the devices in the chain in loopback 
              mode.  This is done by repeating the latching activation 
              code in a specific manner.  The binary number in the 
              iterataion register determines how many times the first portion 
              of a latching loop activation code needs to be repeated as per 
              user request and according to the Bellcore spec.  A value of 0 
              results in no iteration and will cause the very first device in 
              chain to go into loop back.  A value of 1 will result into one 
              iteration and will cause the second device to go into loopback 
              and so on. The range of this count is 1 to 32, and it would 
              translate to a range of 0 to 31 for the iteration register.
             " 

        ::= { bert   12 }


bertPattern   OBJECT-TYPE
                SYNTAX  INTEGER {
                            allZeros (1),
                            allOnes (2),
                            alternateONeZero (3),
                            doubleOneZero (4),
                            fifteenBit (5),
                            twentyBit (6),
                            twentyBitQRSS (7),
                            twentythreeBit (8),
                            oneInEight (9),
                            threeIntwentyfour (10),
                            dds-1 (11),
                            dds-2 (12),
                            dds-3 (13),
                            dds-4 (14),
                            dds-5 (15),
                            nineBit (16),
                            elevenBit (17)
                        }
                ACCESS  read-write
                STATUS  mandatory
                DESCRIPTION
                     "This variable determines BERT pattern to be transmitted.
                     "

        ::= { bert 13 }


bertLoopback   OBJECT-TYPE
        SYNTAX  INTEGER {
                        farEndLoopback(1),
                        facilityLoopback(2),
                        metallicLoopback(3)
                        }
        ACCESS  read-write
        STATUS  mandatory
        DESCRIPTION
             "specifies the type of loopback to be (d)established.
             " 

        ::= { bert 14 }


bertLoopbackOperation   OBJECT-TYPE
        SYNTAX  INTEGER {
                        loopUp(1),
                        loopDown(2)
                        }
        ACCESS  read-write
        STATUS  mandatory
        DESCRIPTION
             "specifies the operation of loopback (up or down).
             " 

        ::= { bert 15 }

bertDS0Speed   OBJECT-TYPE
        SYNTAX INTEGER {
               speed56k (1),
               speed64k (2)
            }
        ACCESS  read-only
        STATUS  mandatory
        DESCRIPTION
             "represents the ds0 speed of the test running.
             " 

        ::= { bert 16 }


bertTimeSlots   OBJECT-TYPE
        SYNTAX  INTEGER
        ACCESS  read-only
        STATUS  mandatory
        DESCRIPTION
             "represents the number of ds0s in the test medium chosen.
             " 

        ::= { bert 17 }

bertStartTime   OBJECT-TYPE
        SYNTAX  DisplayString (SIZE (8))
        ACCESS  read-only
        STATUS  mandatory
        DESCRIPTION
             "The syntax is hh:mm:ss
              The time zone is as configured in the shelf.
             "

        ::= { bert 18 }



bertStartDate   OBJECT-TYPE
        SYNTAX  DisplayString (SIZE (10))
        ACCESS  read-only
        STATUS  mandatory
        DESCRIPTION
             "On MGX 8220, the syntax is mm/dd/yy
              On MGX 8850, the syntax is mm/dd/yyyy
             "

        ::= { bert 19 }



bertBitCount   OBJECT-TYPE
        SYNTAX  INTEGER 
        ACCESS  read-only
        STATUS  mandatory
        DESCRIPTION
             "This shows the number of bits transmitted.
             " 

        ::= { bert 20 }

bertBitErrorCount OBJECT-TYPE
        SYNTAX  INTEGER 
        ACCESS  read-only
        STATUS  mandatory
        DESCRIPTION
             "This shows the number of bits received in error.
             " 

        ::= { bert 21 }


bertErrorInjectCount OBJECT-TYPE
        SYNTAX  INTEGER 
        ACCESS  read-only
        STATUS  mandatory
        DESCRIPTION
             "This shows the number of times error was injected.
             " 

        ::= { bert 22 }

bertCleanupAction   OBJECT-TYPE
        SYNTAX  INTEGER {
                        noAction                             (1),
                        smCleanup                            (2),
                        latchDS0DropLoopdown                 (3),
                        latchDS0LineLoopdown                 (4),
                        latchOCULoopdown                     (5),
                        latchCSULoopdown                     (6),
                        latchDSULoopdown                     (7),
                        latchHL96Loopdown                    (8),
                        v54PolynomialLoopdown                (9),
                        inbandLoopdown                       (10),
                        esfLoopdown                          (11),
                        facilityLoopdown                     (12),
                        metallicLoopdown                     (13),
                        smartJackInbandLoopdown              (14)
                        }
        ACCESS  read-only
        STATUS  mandatory
        DESCRIPTION
             "When the BERT has to be stopped or aborted (due to card state 
              changes), this object would give the exact action to take. 
              The bert related changes to  the shelf, then, can be cleaned up. 
              When its value is a Loopdown, it implies smCleanup plus the 
              corresponding Loopdown. 
             "
        DEFVAL { noAction }

        ::= { bert   23 }


bertAbortReason   OBJECT-TYPE
        SYNTAX  INTEGER {
                        ascStateChange                (1),
                        smStateChange                 (2),
                        srmStateChange                (3),
                        coreCardSwitch                (4),
                        smRedundancySwitch            (5)
                        }
        ACCESS  read-only
        STATUS  mandatory
        DESCRIPTION
             "when the BERT is aborted, this object would give the 
              reason for that.
             "

        ::= { bert   24 }

-- ----------------------------------------------------------------------
--
-- This table consists of the last 20 DDS codes that were detected during 
-- DDS seek. 
-- ----------------------------------------------------------------------

-- ----------------------------------------------------------------------
--
-- If one of the indices to the table is 0, it means that there are no 
-- entries in the table. This table is a circular one and the first and
-- last indices refer to the beginning and the end of the circular list 
-- respectively. If there are more than 20 codes detected, the table
-- enrties will be overwritten to keep only the last 20 codes detected.
--
-- ----------------------------------------------------------------------


bertDDSSeekResultsTableFirstIndex   OBJECT-TYPE
        SYNTAX    INTEGER (0..20) 
        ACCESS    read-only
        STATUS    mandatory
        DESCRIPTION
             "Denotes the index of the oldest entry in the table.
              A value of zero means that there are no entries in the table.
             " 

        ::= { bert   25 }



bertDDSSeekResultsTableLastIndex   OBJECT-TYPE
        SYNTAX    INTEGER (0..20) 
        ACCESS    read-only
        STATUS    mandatory
        DESCRIPTION
             "Denotes the index of the latest entry in the table.
              A value of zero means that there are no entries in the table.
             " 

        ::= { bert   26 }


bertDDSSeekResultsTable   OBJECT-TYPE 
    SYNTAX      SEQUENCE OF  BertDDSSeekResultsTableEntry
    ACCESS      not-accessible
    STATUS      mandatory
    DESCRIPTION 
         "A list of detected DDS codes.
         "
     ::= { bert   27  }



bertDDSSeekResultsTableEntry   OBJECT-TYPE
    SYNTAX      BertDDSSeekResultsTableEntry
    ACCESS      not-accessible
    STATUS      mandatory
    DESCRIPTION
         "An entry in the detected DDS codes table.
         "
    INDEX {  bertDDSSeekResultsTableIndex   }

    ::= { bertDDSSeekResultsTable   1  }


BertDDSSeekResultsTableEntry  ::=
SEQUENCE   {
           bertDDSSeekResultsTableIndex                INTEGER,
           bertDDSCode                                INTEGER
           }           



bertDDSSeekResultsTableIndex   OBJECT-TYPE
        SYNTAX        INTEGER (1..20) 
        ACCESS        read-only
        STATUS        mandatory
        DESCRIPTION
             "Denotes the serial number of the entry in the table.
             " 

        ::= { bertDDSSeekResultsTableEntry   1 }



bertDDSCode   OBJECT-TYPE
        SYNTAX        INTEGER { 
                        abnormalStationCondition(30), -- ('1E'h),
                        block(10), -- ('0A'h),
                        channelLoopback(40), -- ('28'h),
                        dsuLoopback(44), -- ('2C'h),
                        farEndVoice(90), -- ('5A'h),
                        idle(126), -- ('7E'h),
                        loopbackEnable(86), -- ('56'h),
                        mjuAlert(114), -- ('72'h),
                        muxOutOfSync(26), -- ('1A'h),
                        ocuLoopback(42), -- ('2A'h),
                        release(120), -- ('78'h),
                        test(28), -- ('1C'h),
                        testAlert(108), -- ('6C'h),
                        transitionInProgress(58), -- ('3A'h),
                        unassignedMuxChannel(24), -- ('18'h),
                        unnamed(50) -- ('32'h)
                        }
        ACCESS        read-only
        STATUS        mandatory
        DESCRIPTION
             "Denotes the type of DDS code detected.
             " 

        ::= { bertDDSSeekResultsTableEntry   2 }



-- --------------------------------------------------------------------
--
-- This table contains the list of supported tests for each SM in
-- the shelf.
--
-- --------------------------------------------------------------------

bertSupportedTestsTable OBJECT-TYPE 
    SYNTAX      SEQUENCE OF   BertSupportedTestsTableEntry
    ACCESS      not-accessible
    STATUS      mandatory
    DESCRIPTION 
         "A list of supported tests for a given SM.
         "
    ::= { bert   28  }

bertSupportedTestsTableEntry   OBJECT-TYPE
    SYNTAX      BertSupportedTestsTableEntry
    ACCESS      not-accessible
    STATUS      mandatory
    DESCRIPTION 
         "A general supported tests entry.
         "
    INDEX { bertSupportedTestsTableIndex  }

    ::= { bertSupportedTestsTable   1  }



BertSupportedTestsTableEntry ::=
SEQUENCE {
          bertSupportedTestsTableIndex        INTEGER,    
          bertSupportFlag                     INTEGER,
          bertTestMediumMask                  INTEGER,
          bertModeMask                        INTEGER,
          bertDeviceToLoopMask                INTEGER,
          bertPatternMask                     INTEGER,
          bertLoopbackMask                    INTEGER,
          bertCardT1E1Type                    INTEGER
         }
 


bertSupportedTestsTableIndex    OBJECT-TYPE
        SYNTAX        INTEGER (1..30)
        ACCESS        read-only
        STATUS        mandatory
        DESCRIPTION
             "This index is the physical slot number of the Service 
              Module whose entry it represents in the table.
	      For MGX 8220, the range is 5-14.
	      For MGX 8850, the range is 1-6, 9-14, 17-22, 25-30. 
             " 

        ::= { bertSupportedTestsTableEntry   1 }


bertSupportFlag OBJECT-TYPE
        SYNTAX  INTEGER {
                        yes(1),
                        no(2)
                        }
        ACCESS  read-only
        STATUS  mandatory
        DESCRIPTION
             "'yes' if the table entry correctly represents the supported
              tests for the SM on the corresponding slot. 'no' if no tests
              at all are supported.
             "

        ::= { bertSupportedTestsTableEntry   2 }

bertTestMediumMask   OBJECT-TYPE
        SYNTAX  INTEGER
        ACCESS  read-only
        STATUS  mandatory
        DESCRIPTION
             "Every test medium is represented by a bit of mask. Bits 0-1 are
              valid in this integer. The meaning of the mask can be 
              understood from the example below:

                 --------------------------
                  TestMedium  |   SM        
                              | support
                 --------------------------
                    port      |    1
                    line      |    1
                 --------------------------
                 (Table contents applicable to FRSM-4T1)
                 bertTestMediumMask = 11 binary

              The column titles represent the variables bertTestMedium  
              depends on. The mask is represented in column major order.
             "

        ::= { bertSupportedTestsTableEntry   3 }

bertModeMask    OBJECT-TYPE
        SYNTAX  INTEGER
        ACCESS  read-only
        STATUS  mandatory
        DESCRIPTION
             "Every mode is represented by 2 bits of mask. Bits 0-5 are
              valid in this integer. The meaning of the mask can be 
              understood from the example below:
                -----------------------------------------------------------
                 Mode        |  SM support     | Test Medium:
                             |                 |  Multiple
                             |                 | T1 time slots
                -----------------------------------------------------------
                Pattern test |       1         |      1
                DDS seek     |       1         |      0
                Loopback     |       1         |      1
                -----------------------------------------------------------
                (Table contents applicable to FRSM-4T1)
                bertModeMask = 101111 binary
                 
              The column titles represent the variables bertMode depends on.
              The mask is represented in column major order.
             "

        ::= { bertSupportedTestsTableEntry   4 }




bertDeviceToLoopMask   OBJECT-TYPE
        SYNTAX        INTEGER
        ACCESS        read-only
        STATUS        mandatory
        DESCRIPTION
             "Every class of devices to loop is represented by 6 bits 
              of mask. Bits 0-29 are valid in this integer. The meaning 
              of the mask can be understood from the example below:

                 -----------------------------------------------------------
                           |     |         |       Test Medium
                 Class of  | SM  |   MODE  |________________________________
                 devices   |supp | Loopback|Line |multiple T1 | 64k |  56k
                           |     |         |     | time slots |     |
                 -----------------------------------------------------------
                 noLatch   |  1        0      0        0         0      1
                 latch     |  1        1      0        0         1      1
                 v54       |  1        1      0        1         1      1
                 inband/esf|  1        1      1        0         0      0
                 metallic  |  1        0      1        0         0      0
                 -----------------------------------------------------------
                 (Table contents applicable to FRSM-4T1)
                 bertDeviceToLoopMask = 001110011000100110000111011111 binary

              The column titles represent the variables bertDeviceToLoop  
              depends on. The mask is represented in column major order.
              Due to the limitation on the length of the mask, 'noDevice'
              option is not represented in this mask. But, the mask for 
              it, is assumed to be a row of ones except for a zero on 
              'MODE Loopback' column.
             "

        ::=  { bertSupportedTestsTableEntry   5 }


bertPatternMask   OBJECT-TYPE
        SYNTAX       INTEGER
        ACCESS       read-only
        STATUS       mandatory
        DESCRIPTION
             "Every class of patterns is represented by 2 bits of mask. 
              Bits 0-3 are valid in this integer. The meaning of the 
              mask can be understood from the example below:

                ----------------------------------------------
                   Class of       |   SM      | Non latching
                   patterns       | support   |device to loop
                ----------------------------------------------
                  Other patterns  |    1      |    0
                ----------------------------------------------
                     Patterns     |    1      |    1
                  power 9 and 11  |           |
                ----------------------------------------------
                (Table contents applicable to FRSM-4T1)
                bertPatternMask = 1011 binary

              The column titles represent the variables bertPattern  
              depends on. The mask is represented in column major order.
             "

        ::= { bertSupportedTestsTableEntry   6 }


bertLoopbackMask   OBJECT-TYPE
        SYNTAX        INTEGER
        ACCESS        read-only
        STATUS        mandatory
        DESCRIPTION
             "Every loopback is represented by 2 bits of mask. Bits 0-5 are
              valid in this integer. The meaning of the mask can be 
              understood from the example below:
                 ----------------------------------------------
                      Loopback     |   SM       |  Test Medium
                                   | support    |     Port
                 ----------------------------------------------
                 Far End Loopback  |     1      |    1
                 Facility Loopback |     1      |    1
                 Metallic Loopback |     1      |    0
                 ----------------------------------------------
                 (Table contents applicable to FRSM-4T1)
                 bertLoopbackMask = 011111 binary

              The column titles represent the variables bertLoopback  
              depends on. The mask is represented in column major order.
             "

        ::= { bertSupportedTestsTableEntry   7 }


bertCardT1E1Type   OBJECT-TYPE
        SYNTAX  INTEGER {
                        t1(1),
                        e1(2)
                        }
        ACCESS  read-only
        STATUS  mandatory
        DESCRIPTION
             "Specifies whether a t1 or e1 card.
             "

        ::= { bertSupportedTestsTableEntry   8 }

-- ------------------------------------------------------------------
--
-- BASIS project SRM 3T3 MIB
-- 
-- Created by Sheng Lee, modified by Jenny W.
--
-- ------------------------------------------------------------------



srm3T3CnfGrp          OBJECT IDENTIFIER ::= {cardSpecific 10}

-- ------------------------------------------------------------------
-- 
-- Group srm3T3Config 
-- This group contains DS1 mapping configuration for SRM-3T3 card. 
-- This group is card specific for SRM-3T3 card.
-- 
-- ------------------------------------------------------------------
srm3T3CnfGrpTable OBJECT-TYPE
	SYNTAX	SEQUENCE OF Srm3T3CnfGrpEntry
	ACCESS	not-accessible
	STATUS	mandatory
	DESCRIPTION
		"The SRM 3T3 configuration table, it is the
		 distribution of a T3 line.
		"
	::= { srm3T3CnfGrp 1 }

srm3T3CnfGrpEntry OBJECT-TYPE
	SYNTAX	Srm3T3CnfGrpEntry
	ACCESS	not-accessible
	STATUS	mandatory
	DESCRIPTION
		"an entry in the T3 configuration table
		"
	INDEX	{ srmT3LineNum, srmStartT1LineNum }
	::= { srm3T3CnfGrpTable 1 }

Srm3T3CnfGrpEntry ::=
	SEQUENCE {
		srmT3LineNum 
			INTEGER,
		srmStartT1LineNum 
			INTEGER,
		srmT1RowStatus 
			INTEGER,
		srmTargetSlotNum 
			INTEGER,
		srmTargetSlotLineNum 
			INTEGER
		}

srmT3LineNum   OBJECT-TYPE
    SYNTAX INTEGER (1..3)
    ACCESS read-only
    STATUS mandatory
    DESCRIPTION
    "Select T3 line number.
     There is no default value for this object."
    ::= { srm3T3CnfGrpEntry 1 }
    
srmStartT1LineNum OBJECT-TYPE
    SYNTAX INTEGER (1..28) 
    ACCESS read-only
    STATUS mandatory
    DESCRIPTION
    "The start T1 number to be affected.
     There is no default value for this object."
    ::= { srm3T3CnfGrpEntry 2 }

srmT1RowStatus OBJECT-TYPE
    SYNTAX INTEGER { 
        add(1),
        delete(2),
        modify(3)
        }
    ACCESS read-write
    STATUS mandatory
    DESCRIPTION
    "a command is used to add, delete, or modify
     one or more DS1 mapping. 
     Default value is delete."
    ::= { srm3T3CnfGrpEntry 3 }

srmTargetSlotNum OBJECT-TYPE
    SYNTAX INTEGER (1..32) 
    ACCESS read-write
    STATUS mandatory
    DESCRIPTION
    " specify the target slot number to be linked.
     There is no default value for this object.
     For MGX8850:    SRM01 services slots 1 - 6 and 9 - 14,
                     SRM02 services slots 17 - 22 and 25 - 30
     For MGX8220: SYNTAX  INTEGER (5 ..14)
     "
    ::= { srm3T3CnfGrpEntry 4 }

srmTargetSlotLineNum OBJECT-TYPE
    SYNTAX INTEGER (0..8) 
    ACCESS read-write
    STATUS mandatory
    DESCRIPTION
    "0 means not assigned.
     There is no default value for this object."
    ::= { srm3T3CnfGrpEntry 5 }
-- ------------------------------------------------------------------
--
-- BASIS project SRME MIB
-- 
-- Created by Anand G.
--
-- ------------------------------------------------------------------



srmeCnfGrp          OBJECT IDENTIFIER ::= {cardSpecific 22}

-- ------------------------------------------------------------------
-- 
-- Group srmeConfig 
-- This group contains DS1 and E1 mapping configuration for SRME card. 
-- This group is card specific for SRME card.
-- 
-- ------------------------------------------------------------------
srmeCnfGrpTable OBJECT-TYPE
	SYNTAX	SEQUENCE OF SrmeCnfGrpEntry
	ACCESS	not-accessible
	STATUS	mandatory
	DESCRIPTION
		"The SRME configuration table for bulk distribution of SRME lines.
		"
	::= { srmeCnfGrp 1 }

srmeCnfGrpEntry OBJECT-TYPE
	SYNTAX	SrmeCnfGrpEntry
	ACCESS	not-accessible
	STATUS	mandatory
	DESCRIPTION
		"an entry in the SRME Distribution configuration table
		"
	INDEX	{ srmeLineNum, srmeStartVtNum }
	::= { srmeCnfGrpTable 1 }

SrmeCnfGrpEntry ::=
	SEQUENCE {
		srmeLineNum 
			INTEGER,
		srmeStartVtNum 
			INTEGER,
		srmeRowStatus 
			INTEGER,
		srmeTargetSlotNum 
			INTEGER,
		srmeTargetSlotLineNum 
			INTEGER,
                srmeVtFramingType
                        INTEGER
		}

srmeLineNum   OBJECT-TYPE
    SYNTAX INTEGER (1..3)
    ACCESS read-only
    STATUS mandatory
    DESCRIPTION
    "Select SRME line number.
     For OC3/STM1: SYNTAX INTEGER 1
     There is no default value for this object."
    ::= { srmeCnfGrpEntry 1 }
    
srmeStartVtNum OBJECT-TYPE
    SYNTAX INTEGER (1..84) 
    ACCESS read-only
    STATUS mandatory
    DESCRIPTION
    "The start T1 or E1 number (virtual tributary) to be affected.
     For OC3  with T1 tributaries: SYNTAX INTEGER (1 .. 84)
     For STM1 with E1 tributaries: SYNTAX INTEGER (1 .. 63) 
     There is no default value for this object."
    ::= { srmeCnfGrpEntry 2 }

srmeRowStatus OBJECT-TYPE
    SYNTAX INTEGER { 
        add(1),
        delete(2),
        modify(3)
        }
    ACCESS read-write
    STATUS mandatory
    DESCRIPTION
    "Command used to add, delete, or modify
     one or more T1 or E1 mappings. Only the 
     srmeVtFramingType object can be modified once the
     distribution link is added. To modify all other
     objects, user should first delete the link and 
     add it again.

     Default value is modify."
    ::= { srmeCnfGrpEntry 3 }

srmeTargetSlotNum OBJECT-TYPE
    SYNTAX INTEGER (1..32) 
    ACCESS read-write
    STATUS mandatory
    DESCRIPTION
    " specify the target slot number to be linked.
     There is no default value for this object.
     For MGX8x50:    SRM01 services slots 1 - 6 and 9 - 14,
                     SRM02 services slots 17 - 22 and 25 - 30
     For MGX8x30:    service slots 3-6 and 10-13
     "
    ::= { srmeCnfGrpEntry 4 }

srmeTargetSlotLineNum OBJECT-TYPE
    SYNTAX INTEGER (0..8) 
    ACCESS read-write
    STATUS mandatory
    DESCRIPTION
    "Specify the target slot's line to be linked.
     0 means not assigned.
     There is no default value for this object."
    ::= { srmeCnfGrpEntry 5 }

srmeVtFramingType OBJECT-TYPE
    SYNTAX INTEGER {
        notApplicable(1),
        sf(2),
        esf(3)
        }
    ACCESS read-write
    STATUS mandatory
    DESCRIPTION
    "Specifies the Framing Type of the target slot line.
     This is applicable only if the target module is a
     T1 Service Module and byte sync mapping is used on
     SRME. Not applicable to E1 Service Modules.

     sf: Superframe or D4
     esf: Extended Superframe. 

     Default is esf if SRME lines are configured for byte-synchronous mapping.
     Else, the default is notApplicable.
    "
    ::= { srmeCnfGrpEntry 6 }

 
-- ------------------------------------------------------------------
--
-- BASIS project  LINEs  MIB .. specifically serial
--
--
-- ------------------------------------------------------------------
 
 
 
-- ----------------------------------------------------------------
--
-- Group "basisLines""
-- This group contains information on serial lines
-- Other lines like ds1 etc are in different files
-- ----------------------------------------------------------------

serialInterface         OBJECT IDENTIFIER ::= {basisLines 1}

-- ----------------------------------------------------------------
--
--
-- serial interface table                                      
--
--
-- ----------------------------------------------------------------

serialPortNumOfValidEntries   OBJECT-TYPE
    SYNTAX INTEGER
    ACCESS read-only
    STATUS mandatory
    DESCRIPTION
    "Number of rows in serialPortTable.
     This number is equal to the number of serial ports on the module.
    "
    ::= { serialInterface 2 }

serialInterfaceTable   OBJECT-TYPE
    SYNTAX  SEQUENCE OF SerialInterfaceEntry
    ACCESS  not-accessible
    STATUS  mandatory
    DESCRIPTION
        "This table represents Physical serial interfaces on the module
        "
    ::= { serialInterface 1 }

serialInterfaceEntry   OBJECT-TYPE
    SYNTAX  SerialInterfaceEntry
    ACCESS  not-accessible
    STATUS  mandatory
    DESCRIPTION
        "An entry for the serial interface
        "
    INDEX   { serialPortNum }
    ::= { serialInterfaceTable 1}
 
SerialInterfaceEntry ::=
    SEQUENCE {
        serialPortNum
            INTEGER,
        serialPortType
            INTEGER,
        serialPortEnable
            INTEGER,
         serialPortbps 
             INTEGER
    }

serialPortNum OBJECT-TYPE
    SYNTAX  INTEGER
    ACCESS  read-only
    STATUS  mandatory
    DESCRIPTION
         "serial interface number 
         port 1. is always defined as debug port
         port 2. on BSC can perform SLIP.
         "
    ::= { serialInterfaceEntry 1 }

serialPortType OBJECT-TYPE
    SYNTAX  INTEGER {
       main (1),
       debug (2)
    }
    ACCESS  read-only
    STATUS  mandatory
    DESCRIPTION
        "On the BSC board IP stack is mounted on the manager port,
         on the debug port dumb terminal can be connected
         function of the ports cannot be changed, except for enabling
         and disabling
        "
    ::= { serialInterfaceEntry 2 }


serialPortEnable OBJECT-TYPE
    SYNTAX  INTEGER {
       disable (1),
       enable  (2)
    }
    ACCESS  read-write
    STATUS  mandatory
    DESCRIPTION
        "ports can be enabled or diabled
        "
    ::= { serialInterfaceEntry 3 }

serialPortbps OBJECT-TYPE
    SYNTAX  INTEGER {
        bps9600     (1),
        bps2400     (2),
        bps19200    (3)
    }
    ACCESS  read-write
    STATUS  mandatory
    DESCRIPTION
        "baud rate of the ports, each port can be config
         different
        "
    DEFVAL { bps9600 }
    ::= { serialInterfaceEntry 4 }

-- ------------------------------------------------------------------
--
-- BASIS project  LINEs  MIB .. specifically ethernet
--
--
-- ------------------------------------------------------------------
 
 
 
-- ----------------------------------------------------------------
--
-- Group "basisLines""
-- This group contains information on ethernet lines
-- ----------------------------------------------------------------

ethernetInterface       OBJECT IDENTIFIER ::= {basisLines 2}

ethernetPhysicaAddress   OBJECT-TYPE
    SYNTAX  DisplayString (SIZE (0..8))
    ACCESS  read-only
    STATUS  mandatory
    DESCRIPTION
            "ethernet address stored in the BSC BRAM, entered by
             manfacturing.
            "
    ::= { ethernetInterface 1 }
 

-- --------------------------------------------------------------
--
-- Group "ASM"
--
-- --------------------------------------------------------------


-- --------------------------------------------------------------
-- 
-- ASM group
-- This group contains ASM Alarm table
-- 
-- --------------------------------------------------------------
asmAlarmTable OBJECT-TYPE
		SYNTAX	SEQUENCE OF AsmAlarmEntry
		ACCESS	not-accessible
		STATUS	mandatory
		DESCRIPTION
			"The ASM Alarm table. The table size is
			 given by the value of ASMNumOfValidEntries."
		::= { basisAsm 1 }

	asmAlarmEntry OBJECT-TYPE
		SYNTAX	AsmAlarmEntry
		ACCESS	not-accessible
		STATUS	mandatory
		DESCRIPTION
			"An entry in the Basis ASM Alarm Table."
		INDEX	{ asmAlarmNum }
		::= { asmAlarmTable 1 }

	AsmAlarmEntry ::=
		SEQUENCE {
			asmAlarmNum INTEGER,
			asmAlarmType INTEGER,
			asmAlarmUnitNum INTEGER,
			asmAlarmThreshold INTEGER,
			asmAlarmSeverity INTEGER,
                        asmUnitMeasurable INTEGER,
                        asmUnitMeasuredValue INTEGER,
			asmPhysicalAlarmState INTEGER,
			asmClrButton INTEGER
         		}
	asmAlarmNum OBJECT-TYPE
		SYNTAX	INTEGER
		ACCESS	read-only
		STATUS	mandatory
		DESCRIPTION
              "This object is the identifier of a ASM alarm
               entry. The Alarm is further identified by the 
               objects ASMAlarmType & ASMAlarmUnitNum."
		::= { asmAlarmEntry 1 }

	asmAlarmType OBJECT-TYPE
		SYNTAX	INTEGER {
                       alarmOther (1),
                       alarmTemperature (2),
                       alarmPSU (3),
                       alarmDCLevel (4),
                       alarmFanUnit (5)
                       }
		ACCESS	read-only
		STATUS	mandatory
		DESCRIPTION
			"The value for this object indicates the type
          of Alarm represented in the entry of ASMAlarmTable
			 indexed by ASMAlarmNum."
		::= { asmAlarmEntry 2 }

	asmAlarmUnitNum OBJECT-TYPE
		SYNTAX  INTEGER
		ACCESS  read-only
		STATUS  mandatory
		DESCRIPTION
			"This object identifies one unit among a number of
          identical units represented in ASMAlarmTable having the
          same ASMAlarmType."
		::= { asmAlarmEntry 3 }

	asmAlarmThreshold OBJECT-TYPE
		SYNTAX  INTEGER (1..2147483647)
		ACCESS  read-only
		STATUS  mandatory
		DESCRIPTION
			"This object specifies the threshold beyond which
			 the alarmable unit is said to be in an abnormal state."
		::= { asmAlarmEntry 4 }

	asmAlarmSeverity OBJECT-TYPE
		SYNTAX  INTEGER 
		              {
				        alarmMinor (1),
				        alarmMajor (2)
			           }
		ACCESS  read-only
		STATUS  mandatory
		DESCRIPTION
			"This variable specifies the severity of the alarm
          to be declared when the ASMAlarmThreshold specified is
          exceeded for the entry of ASMAlarmTable indexed by
			 ASMAlarmNum."
		::= { asmAlarmEntry 5 }

        asmUnitMeasurable OBJECT-TYPE
                SYNTAX  INTEGER
                                  {
                                  no (1),
                                  yes (2)
                                  }
                ACCESS  read-only
                STATUS  mandatory
                DESCRIPTION
                        "This object indicates if the alarm unit is measurable
                         by the AXIS shelf."  
                ::= { asmAlarmEntry 6 }

        asmUnitMeasuredValue OBJECT-TYPE
                SYNTAX  INTEGER
                ACCESS  read-only
                STATUS  mandatory
                DESCRIPTION
                        "This object gives the mesaured value of the entity
                         addressed by asmAlarmNum if it is measurable." 
                ::= { asmAlarmEntry 7 }
 
	asmPhysicalAlarmState OBJECT-TYPE
		SYNTAX  INTEGER 
		ACCESS	read-only
		STATUS  mandatory
		DESCRIPTION
                        "This object indicates the status of the ASM alarm
                         represented in this entry. It is a bitmap where a
                         set bit indicates an abnormal condition. A reset bit
                         signifies normal operation."
		::= { asmAlarmEntry 8 }

	asmClrButton OBJECT-TYPE
		SYNTAX  INTEGER {
                                asmAlarmNoAction(1),
                                asmAlarmClear(2)
                                }
      ACCESS  read-write
		STATUS  mandatory
		DESCRIPTION
			"This object when set to ASMAlarmClear causes the entry
                         in the ASMAlarmTable represented by ASMAlarmNum to be
			 cleared."
		::= { asmAlarmEntry 9 }

	asmNumOfValidEntries OBJECT-TYPE
		SYNTAX	INTEGER
		ACCESS	read-only
		STATUS	mandatory
		DESCRIPTION
			"The number of valid ASMAlarmTable entries (regardless
			 of how many are actually configured) in the table."
		::= { basisAsm 2 }

	asmShelfAlarmState OBJECT-TYPE
		SYNTAX	INTEGER
                        {
                        alarmOff(1),
                        alarmOn(2)
                        }
		ACCESS	read-only
		STATUS	mandatory
		DESCRIPTION
			"This object indicates whether any Shelf Alarm has been 
          declared in the BASIS system."
		::= { basisAsm 3 }

-- ------------------------------------------------------------------
--
-- BASIS project 
-- 
--
-- ------------------------------------------------------------------


aumClockConfig          OBJECT IDENTIFIER ::= {cardSpecific 1}
aumAddressTranslation   OBJECT IDENTIFIER ::= {cardSpecific 2}
bnmCounters             OBJECT IDENTIFIER ::= {cardSpecific 3}
bnmLineInterfaceMode    OBJECT IDENTIFIER ::= {cardSpecific 12}
-- ------------------------------------------------------------------
-- 
-- Group aumClockConfig
-- This group contains clock source for AUM card. 
-- This group is card specific for AUM card.
-- 
-- ------------------------------------------------------------------
primaryMuxClockSource   OBJECT-TYPE
    SYNTAX INTEGER {
        internalOscillator (1),
        aumInbandClock (2),
        externalClock (3)
--      clockFromTIM (4)
--      clockFromSM (5)
        }
    ACCESS read-write
    STATUS mandatory
    DESCRIPTION
    "Primary Mux Clock source for AUM card."
    ::= { aumClockConfig 1 }
    
secondaryMuxClockSource OBJECT-TYPE
    SYNTAX INTEGER {
        internalOscillator (1),
        aumInbandClock (2),
        externalClock (3)
--      clockFromTIM (4)
--      clockFromSM (5)
        }
    ACCESS read-write
    STATUS mandatory
    DESCRIPTION
    "Secondary clock source for AUM card."
    ::= { aumClockConfig 2 }

currentClock    OBJECT-TYPE
    SYNTAX INTEGER {
        primary (1),
        secondary (2),
        intOscillator(3)
        }
    ACCESS read-write
    STATUS mandatory
    DESCRIPTION
    "clock source currently selected for AUM card."
    ::= { aumClockConfig 3 }

clockSwitchState    OBJECT-TYPE
    SYNTAX INTEGER {
        noChange (1),
        clockSrcChanged (2)
        }
    ACCESS read-only
    STATUS mandatory
    DESCRIPTION
    "clock source switched."
    ::= { aumClockConfig 4 }

extClockPresent    OBJECT-TYPE
    SYNTAX INTEGER {
        clkNotPresent (1),
        clkPresent (2)
        }
    ACCESS read-only
    STATUS mandatory
    DESCRIPTION
    "Status of External T1/E1 Clock on AUM card."
    ::= { aumClockConfig 5 }

extClkSrcImpedance    OBJECT-TYPE
    SYNTAX INTEGER {
                      ohms75(1),
                      ohms100(2),
                      ohms120(3)
                   }
    ACCESS read-write
    STATUS mandatory
    DESCRIPTION
    "Impedance on external clock input for AUM card."
    ::= { aumClockConfig 6 }

extClkConnectorType   OBJECT-TYPE
    SYNTAX INTEGER {
                        db15Type(1),
                        bncType(2)
                   }
    ACCESS read-write
	 STATUS mandatory
	 DESCRIPTION
	 "This object describes the type of connector available for connecting
	  the external clock source to the AUM-LM. The T3 and E3
	cards are separate hence this field is not configurable
	for any BNM card type except bnm-155"
    ::= { aumClockConfig 7 }

-- ------------------------------------------------------------------
--
-- Group "aumAddressTranslation"
-- Has slot.LCN mapping
-- This group is card specific to AUM card.
--
-- ------------------------------------------------------------------
aumAddressTranslationTable  OBJECT-TYPE
    SYNTAX SEQUENCE OF AumAddressTranslationEntry
    ACCESS not-accessible
    STATUS mandatory
    DESCRIPTION
    "This table contains address translation parameters for AXIS connections."
    ::= { aumAddressTranslation 1 }

aumAddressTranslationEntry  OBJECT-TYPE
    SYNTAX AumAddressTranslationEntry
    ACCESS not-accessible
    STATUS mandatory
    DESCRIPTION
    "This entry exists when the connection specified by connShelfNum,
	  connSlotNum and connChanNum exists."
    INDEX  { connShelfNum,connSlotNum,connChanNum }
    ::= { aumAddressTranslationTable 1 }

AumAddressTranslationEntry ::=
    SEQUENCE {
        connShelfNum   INTEGER,
        connSlotNum    INTEGER,
        connChanNum    INTEGER,
	aumConnType       INTEGER,
	connVPINum     INTEGER
        }

connShelfNum  OBJECT-TYPE
    SYNTAX INTEGER 
    ACCESS read-only
    STATUS mandatory
    DESCRIPTION 
    "Index to shelf list on BASIS."
    ::= { aumAddressTranslationEntry 1 }
    
connSlotNum  OBJECT-TYPE
    SYNTAX INTEGER 
    ACCESS read-only
    STATUS mandatory
    DESCRIPTION 
    "Index to slot list on BASIS."
    ::= { aumAddressTranslationEntry 2 }
 
connChanNum  OBJECT-TYPE
    SYNTAX INTEGER 
    ACCESS read-only
    STATUS mandatory
    DESCRIPTION 
    "Index to channel list on BASIS."
    ::= { aumAddressTranslationEntry 3 }

aumConnType  OBJECT-TYPE
    SYNTAX INTEGER {
                    vpConnection(1),
                    vcConnection(2)
                   }
    ACCESS read-only
    STATUS mandatory
    DESCRIPTION 
    "Virtual channel connection or Virtual Path Connection"
    ::= { aumAddressTranslationEntry 4 }

connVPINum  OBJECT-TYPE
    SYNTAX INTEGER 
    ACCESS read-only
    STATUS mandatory
    DESCRIPTION 
    "Virtual channel connection or Virtual Path Connection"
    ::= { aumAddressTranslationEntry 5 }

aumAddressTranslationDeleteTable  OBJECT-TYPE
    SYNTAX SEQUENCE OF AumAddressTranslationDeleteEntry
    ACCESS not-accessible
    STATUS mandatory
    DESCRIPTION
    "This table contains address translation parameters for AXIS connections."
    ::= { aumAddressTranslation 2 }

aumAddressTranslationDeleteEntry  OBJECT-TYPE
    SYNTAX AumAddressTranslationDeleteEntry
    ACCESS not-accessible
    STATUS mandatory
    DESCRIPTION
    "This entry controls bulk deletion of connections on a given AXIS slot."
    INDEX  { delShelfNum,delSlotNum }
    ::= { aumAddressTranslationDeleteTable 1 }

AumAddressTranslationDeleteEntry ::=
    SEQUENCE {
        delShelfNum   INTEGER,
        delSlotNum    INTEGER
        }

delShelfNum  OBJECT-TYPE
    SYNTAX INTEGER 
    ACCESS read-write
    STATUS mandatory
    DESCRIPTION 
    "Index to shelf list on AXIS."
    ::= { aumAddressTranslationDeleteEntry 1 }
    
delSlotNum  OBJECT-TYPE
    SYNTAX INTEGER 
    ACCESS read-write
    STATUS mandatory
    DESCRIPTION 
    "Index to slot list on BASIS."
    ::= { aumAddressTranslationDeleteEntry 2 }

connNumOfValidEntries  OBJECT-TYPE
    SYNTAX INTEGER (0..1024)
    ACCESS read-only
    STATUS mandatory
    DESCRIPTION
    "Number of rows in aumAddressTranslationTable."
    ::= { aumAddressTranslation 3 }

-- ------------------------------------------------------------------
--
--  Group "bnmCounters"
--  ATM layer Ete, Ite & CellBus Master counters on BNM card.
--
-- ------------------------------------------------------------------

bnmPortCounterTable OBJECT-TYPE
    SYNTAX  SEQUENCE OF BnmPortCounterEntry
    ACCESS  not-accessible
    STATUS  mandatory
    DESCRIPTION
        "The counter table is for the ATM interface, initially there 
         is only one interface, but by making it a table multiple ATM interfaces
         can be accommodated later."
    ::= { bnmCounters 1 }

bnmPortCounterEntry OBJECT-TYPE
    SYNTAX  BnmPortCounterEntry
    ACCESS  not-accessible
    STATUS  mandatory
    DESCRIPTION
        " An entry for DS3 ATM counters "
    INDEX   { bnmPortCounterIndex }
    ::= { bnmPortCounterTable 1}

BnmPortCounterEntry ::=
    SEQUENCE {
          bnmPortCounterIndex       INTEGER,
          bnmPortRcvCells           Counter,
          bnmPortXmtCells           Counter,
          bnmPortCounterClrButton   INTEGER,
          bnmPortRcvCellRate        Gauge,
          bnmPortRcvUtilization     Gauge,
          bnmPortXmtCellRate        Gauge,
          bnmPortXmtUtilization     Gauge
             }

bnmPortCounterIndex   OBJECT-TYPE 
    SYNTAX  INTEGER
    ACCESS  read-only
    STATUS  mandatory
    DESCRIPTION       
        "This specifies the BNM port being referenced."
    ::= { bnmPortCounterEntry 1 }

bnmPortRcvCells   OBJECT-TYPE 
    SYNTAX  Counter
    ACCESS  read-only
    STATUS  mandatory
    DESCRIPTION       
        "The count of Received cells at the BNM port."
    ::= { bnmPortCounterEntry 2 }

bnmPortXmtCells   OBJECT-TYPE 
    SYNTAX  Counter
    ACCESS  read-only
    STATUS  mandatory
    DESCRIPTION       
        "The count of cells transmitted by the BNM port."
    ::= { bnmPortCounterEntry 3 }

bnmPortCounterClrButton   OBJECT-TYPE 
    SYNTAX  INTEGER {
	             bnmPortCounterNoAction(1),
                     bnmPortCounterClear(2)
                    }
    ACCESS  read-write
    STATUS  mandatory
    DESCRIPTION       
        "This object when set to bnmPortCounterClear causes all counters in the row
         referenced by bnmPortCounterIndex to be cleared."
    ::= { bnmPortCounterEntry 4 }

bnmPortRcvCellRate   OBJECT-TYPE
    SYNTAX  Gauge
    ACCESS  read-only
    STATUS  mandatory
    DESCRIPTION
        "The number of cells received from the BNM port (trunk) per second ."
    ::= { bnmPortCounterEntry 5 }
 
bnmPortRcvUtilization   OBJECT-TYPE
    SYNTAX  Gauge
    ACCESS  read-only
    STATUS  mandatory
    DESCRIPTION
        "The received percentage utilization of the BNM port (trunk)"
    ::= { bnmPortCounterEntry 6 }
 
bnmPortXmtCellRate   OBJECT-TYPE
    SYNTAX  Gauge
    ACCESS  read-only
    STATUS  mandatory
    DESCRIPTION
        "The number of cells transmitted to the BNM port (trunk) per second."
    ::= { bnmPortCounterEntry 7 }
 
bnmPortXmtUtilization   OBJECT-TYPE
    SYNTAX  Gauge
    ACCESS  read-only
    STATUS  mandatory
    DESCRIPTION
        "The transmitted  percentage utilization of the BNM port (trunk)"
    ::= { bnmPortCounterEntry 8 }

bnmPortCounterNumOfValidEntries   OBJECT-TYPE 
    SYNTAX  INTEGER 
    ACCESS  read-only
    STATUS  mandatory
    DESCRIPTION       
        "This object specifies the number of rows in bnmPortCounterTable."
    ::= { bnmCounters 2 }

bnmCellbusXmtCellCount      OBJECT-TYPE
    SYNTAX Counter 
    ACCESS  read-only
    STATUS  mandatory
    DESCRIPTION 
         "This objects is a count of cells transmitted by the BNM Cell Bus Master
          to the cell bus."
    ::= { bnmCounters 3 }

bnmCellbusNoAckCellCount        OBJECT-TYPE
    SYNTAX Counter 
    ACCESS  read-only
    STATUS  mandatory
    DESCRIPTION 
         "This object is a count of cells transmitted by the BNM Cell Bus Master
          to the cell bus for which no acknowledgement was received i.e the slave
          card was missing or inactive."
    ::= { bnmCounters 4 }

bnmCellbusGrantCount        OBJECT-TYPE
    SYNTAX Counter 
    ACCESS  read-only
    STATUS  mandatory
    DESCRIPTION 
         "This object is a count of receiver grants given by the BNM Cell Bus Master"
    ::= { bnmCounters 5 }

bnmEgressXmtCellCountDuringAlarm        OBJECT-TYPE
    SYNTAX Counter 
    ACCESS  read-only
    STATUS  mandatory
    DESCRIPTION 
         "This object is a count of cells transmitted by the Egress Engine to the port
i         while a T3 Alarm condition was in effect."
    ::= { bnmCounters 6 }

bnmEgressInvalidCellCount      OBJECT-TYPE
    SYNTAX Counter 
    ACCESS  read-only
    STATUS  mandatory
    DESCRIPTION 
         "This object is a count of cells with disabled channel headers, received by
          the Egress Engine on the BNM and dropped." 
    ::= { bnmCounters 7 }

bnmEgressInvalidCellHdr        OBJECT-TYPE
    SYNTAX INTEGER 
    ACCESS  read-only
    STATUS  mandatory
    DESCRIPTION 
         "This object gives the header of the first invalid cell that
          was dropped by the Egress Engine on the BNM since this object was
          last read and/or cleared." 
    ::= { bnmCounters 8 }

bnmIngressInvalidCellCount        OBJECT-TYPE
    SYNTAX Counter 
    ACCESS  read-only
    STATUS  mandatory
    DESCRIPTION 
         "This object is a count of cells from disabled channels received by the
          Ingress Engine on the BNM. This is not available in Release 1." 
    ::= { bnmCounters 9 }

bnmIngressInvalidCellHdr        OBJECT-TYPE
    SYNTAX INTEGER 
    ACCESS  read-only
    STATUS  mandatory
    DESCRIPTION 
         "This object gives the header of the first invalid cell that
          was dropped by the Ingress Engine on the BNM since this object was
          last read and/or cleared. This is not available in Release 1." 
    ::= { bnmCounters 10 }

bnmCountersClrButton        OBJECT-TYPE
    SYNTAX INTEGER {
                    bnmCountersNoAction(1),
                    bnmCountersClear   (2)
                   }
    ACCESS  read-write
    STATUS  mandatory
    DESCRIPTION 
         "This object clears the BNM counters" 
    ::= { bnmCounters 11 }

bnmLineInterfaceFormat   OBJECT-TYPE
    SYNTAX INTEGER {
        bnmSti(1),
        bnmUni(2),
        bnmNni(3)
        }
    ACCESS read-write
    STATUS mandatory
    DESCRIPTION
    "This indicates the format of the cells going out on the BNM trunk
	For T3 and E3 cards its currently fixed at STI mode. BNM-155 
	sonet cards can take on UNI or NNI options"
    ::= { bnmLineInterfaceMode 1 }

-- ------------------------------------------------------------------
--
-- BASIS project 
-- file Name: pxmclk.my
-- ------------------------------------------------------------------

        
pxmClockConfig          OBJECT IDENTIFIER ::= {cardSpecific 16}
-- ------------------------------------------------------------------
-- 
-- Group pxmClockConfig
-- This group contains clock source for PXM card. 
-- This group is card specific for PXM  card.
-- 
-- ------------------------------------------------------------------
pxmPrimaryMuxClockSource   OBJECT-TYPE
    SYNTAX INTEGER {
        pxmInbandClock1 (1),
        pxmServiceModuleClock1 (2),
        pxmTopSRMClock (3),
        pxmExternalClock (4),
        pxmInbandClock2 (5),
        pxmServiceModuleClock2 (6),
        pxmBottomSRMClock (7),
        pxmInternalOscillator (8),
        pxmExternalClock2 (9)
        }
    ACCESS read-only
    STATUS mandatory
    DESCRIPTION
    "Primary Mux Clock source for PXM card.
     For pxmInbandClock1 and pxmInbandClock2, the pxmPrimaryInbandClockSourceLineNumber
     described the Line number that the clock is derived from.
     For pxmServiceModuleClock1 and pxmServiceModuleClock2, the 
     pxmPrimarySMClockSourceSlotNumber described the SM slot number
     For pxmExternalClock and pxmExternalClock2,
     pxmPrimaryExternalClockSourcePortNumber describes the Port number from
     where the clock is derived. Also the pxmExtClockPresent and
     pxmExtClkConnectorType are used with the pxmExternalClock. And
     pxmExtClock2Present and pxmExtClk2ConnectorType are used with
     pxmExternalClock2."
    ::= { pxmClockConfig 1 }

pxmPrimaryInbandClockSourceLineNumber   OBJECT-TYPE
    SYNTAX INTEGER (0..4)
    ACCESS read-only
    STATUS mandatory
    DESCRIPTION
    "If pxmPrimaryMuxClockSource is pxmInbandClock1 (1) or pxmServiceModuleClock2 (5),
    then this entry indicates Inband Line number."
    ::= { pxmClockConfig 2 }    

pxmPrimarySMClockSourceSlotNumber   OBJECT-TYPE
    SYNTAX INTEGER (0..32)
    ACCESS read-only
    STATUS mandatory
    DESCRIPTION
    "If pxmPrimaryMuxClockSource is pxmServiceModuleClock1(2) or pxmServiceModuleClock2 (6),
    then this entry indicates SM slot number."
    ::= { pxmClockConfig 3 }    

pxmSecondaryMuxClockSource OBJECT-TYPE
    SYNTAX INTEGER {
        pxmInbandClock1 (1),
        pxmServiceModuleClock1 (2),
        pxmTopSRMClock (3),
        pxmExternalClock (4),
        pxmInbandClock2 (5),
        pxmServiceModuleClock2 (6),
        pxmBottomSRMClock (7),
        pxmInternalOscillator (8),
        pxmExternalClock2 (9)
        }
    ACCESS read-only
    STATUS mandatory
    DESCRIPTION
    "Secondary clock source for PXM card.
    For pxmInbandClock1 and pxmInbandClock2, the pxmSecondaryInbandClockSourceLineNumber
     described the Line number that the clock is derived from.
     For pxmServiceModuleClock1 and pxmServiceModuleClock2, the 
     pxmSecondarySMClockSourceSlotNumber described the SM slot number
     pxmSecondaryExternalClockSourcePortNumber describes the Port number from
     where the clock is derived. Also the pxmExtClockPresent and
     pxmExtClkConnectorType are used with the pxmExternalClock. And
     pxmExtClockPresent2 and pxmExtClkConnectorType2 are used with
     pxmExternalClock2."
    ::= { pxmClockConfig 4 }

pxmSecondaryInbandClockSourceLineNumber   OBJECT-TYPE
    SYNTAX INTEGER (0..4)
    ACCESS read-only
    STATUS mandatory
    DESCRIPTION
    "If pxmSecondaryMuxClockSource is pxmInbandClock1 (1) or pxmServiceModuleClock2 (5),
    then this entry indicates Inband Line number ."
    ::= { pxmClockConfig 5 }    

pxmSecondarySMClockSourceSlotNumber   OBJECT-TYPE
    SYNTAX INTEGER (0..32)
    ACCESS read-only
    STATUS mandatory
    DESCRIPTION
    "If pxmSecondaryMuxClockSource is pxmServiceModuleClock1(2) or pxmServiceModuleClock2 (6),
    then this entry indicates SM slot number ."
    ::= { pxmClockConfig 6 }  

pxmCurrentClock  OBJECT-TYPE
    SYNTAX INTEGER {
        primary (1),
        secondary (2),
        intOscillator(3)
        }
    ACCESS read-only
    STATUS mandatory
    DESCRIPTION
    "Clock source currently selected for PXM card.
    If the pxmCurrentClock is primary then the pxmPrimaryMuxClockSource
    described further the source of the clock.
    If the pxmCurrentClock is secondary then the pxmSecondaryMuxClockSource
    described further the source of the clock."
    ::= { pxmClockConfig 7 }

pxmPreviousClock  OBJECT-TYPE
    SYNTAX INTEGER {
        primary (1),
        secondary (2),
        intOscillator(3)
        }
    ACCESS read-only
    STATUS mandatory
    DESCRIPTION
    "Clock source Previously selected for PXM card."
    ::= { pxmClockConfig 8 }

pxmExtClockPresent    OBJECT-TYPE
    SYNTAX INTEGER {
        clkNotPresent (1),
        clkPresent (2)
        }
    ACCESS read-only
    STATUS mandatory
    DESCRIPTION
    "Status of External T1/E1 Clock on PXM card."
    ::= { pxmClockConfig 9 }

pxmExtClkSrcImpedance    OBJECT-TYPE
    SYNTAX INTEGER {
                      ohms75(1),
                      ohms100(2),
                      ohms120(3)
                   }
    ACCESS read-only
    STATUS mandatory
    DESCRIPTION
    "Impedance on external clock input for PXM card."
    ::= { pxmClockConfig 10 }

pxmExtClkConnectorType   OBJECT-TYPE
    SYNTAX INTEGER {
                        rj45Type (1),
                        smbType (2)
                   }
    ACCESS read-only
     STATUS mandatory
     DESCRIPTION
     "This object describes the type of connector available for connecting
      the external clock source to the PXM-LM."
     ::= { pxmClockConfig 11 }

pxmClkStratumLevel    OBJECT-TYPE
    SYNTAX INTEGER {
                        stratumUnknown (1),
                        stratumLevel1 (2),
                        stratumLevel2 (3),
                        stratumLevel3E (4),
                        stratumLevel3 (5),
                        stratumLevel4 (6),
                        stratumLevel4E (7)
                   }
     ACCESS read-only
     STATUS mandatory
     DESCRIPTION
     "This object describes the lowest stratum level provided by the interface
      the external clock source to the PXM-LM."
     ::= { pxmClockConfig 12 }

pxmClkErrReason          OBJECT-TYPE
    SYNTAX INTEGER {
                        goodClk (1),
                        unknownReason (2),
                        noClkSignal (3),
                        freqTooHigh (4),
                        freqTooLow (5),
                        excessiveJitter (6),
                        missingCard (7),
                        missingLogicalIf (8),
                        noClock (9)
                   }
     ACCESS read-only
     STATUS mandatory
     DESCRIPTION
     "This object gives more information about clock status (if known)."
     ::= { pxmClockConfig 13 }

pxmExtClock2Present    OBJECT-TYPE
	 SYNTAX INTEGER {
		 clkNotPresent (1),
		 clkPresent (2)
	 }
	 ACCESS read-only
	 STATUS mandatory
	 DESCRIPTION
	 "Status of External T1/E1 Clock on port 2 of UI-S3 back card of PXM card."
	 ::= { pxmClockConfig 14 }

pxmExtClk2SrcImpedance    OBJECT-TYPE
	SYNTAX INTEGER {
		 ohms75(1),
		 ohms100(2),
		 ohms120(3)
	}
	ACCESS read-only
	STATUS mandatory
	DESCRIPTION
	"Impedance on external clock input on port 2 of UI-S3 back card of PXM 
	card."
    ::= { pxmClockConfig 15 }


pxmExtClk2ConnectorType   OBJECT-TYPE
	SYNTAX INTEGER {
		 rj45Type (1),
		 smbType (2)
	}
	ACCESS read-only
	STATUS mandatory
	DESCRIPTION
	"This object describes the type of connector available for connecting
	the external clock source to the port 2 of UI-S3 back card of PXM-LM."
	::= { pxmClockConfig 16 }




-- ------------------------------------------------------------------
--
-- BASIS project  CARD SPECIFIC ASC MIB
-- 
-- 
-- Created by Jenny W. 3/22/96 
--
-- ------------------------------------------------------------------



ascFeatures              OBJECT IDENTIFIER ::= {cardSpecific 5}

-- ------------------------------------------------------------------
--
--  Group "ascFeatures"
--  ASC Module Features enabled for this card.
--  This contains all the features specific to ASC card such as
--  Redundancy.
--
-- ------------------------------------------------------------------

redundancyAllowed OBJECT-TYPE
    SYNTAX  INTEGER {
	  redNotAllowed(1),
          redAllowed(2)
	}
    ACCESS  read-only
    STATUS  mandatory
    DESCRIPTION
        "BRAM parameter indicating whether redundancy is allowed in
	this shelf.
        "
    ::= { ascFeatures 1 }


-- ------------------------------------------------------------------
--
-- BASIS project  CARD SPECIFIC ASC MIB
-- 
-- 
-- Created by Bhagvan CB 09/28/98
--
-- ------------------------------------------------------------------



coreCardCommands              OBJECT IDENTIFIER ::= {cardSpecific 20}

-- ------------------------------------------------------------------
--
--  Group "coreCardCommands"
--  Core Card Commands thru SV+
--  Commands affecting the Core Cards
--
-- ------------------------------------------------------------------

switchCoreCard OBJECT-TYPE
    SYNTAX  INTEGER {
		noAction(1),
		doswitchcc(2),
		instswitchcc(3),
		fallbackswitchcc(4)
	}
    ACCESS  read-write
    STATUS  mandatory
    DESCRIPTION
        "A SwitchCC command either to invoke switchcc or take noAction
	on the Core Card Set
        "
    ::= { coreCardCommands 1 }

--
-- ----------------------------------------------------------------------
-- BASIS Project MIB
-- 
--





ascChanStateSigLmiGrp   OBJECT IDENTIFIER ::= { atmLmiSignaling 3 }


-- ------------------------------------------------------------------------
--
-- ascChanStateSigLmi group
-- Line ATM LMI signalling Channel Status
--
-- ------------------------------------------------------------------------


ascChanStateSigLmiGrpTable	OBJECT-TYPE
	SYNTAX	SEQUENCE OF AscChanStateSigLmiGrpEntry
	ACCESS	not-accessible
	STATUS	mandatory
	DESCRIPTION
		"The ATM LMI Channel State table
		"
	::= { ascChanStateSigLmiGrp 1 }

ascChanStateSigLmiGrpEntry	OBJECT-TYPE
	SYNTAX	AscChanStateSigLmiGrpEntry
	ACCESS	not-accessible
	STATUS	mandatory
	DESCRIPTION
		" An entry for a Channel
		"
	INDEX	{ ascLmiVccLineNum, ascLmiVccVpi, ascLmiVccVci }
	::= { ascChanStateSigLmiGrpTable 1 }

AscChanStateSigLmiGrpEntry ::=
	SEQUENCE {
	   	ascLmiVccLineNum              INTEGER,
	   	ascLmiVccVpi	              INTEGER,
		ascLmiVccVci                  INTEGER, 
		ascLmiXmtAbitState            INTEGER, 
		ascLmiRcvAbitState            INTEGER
		}


ascLmiVccLineNum OBJECT-TYPE
	SYNTAX	INTEGER{
             lineNum (1)
            }
	ACCESS	read-only
	STATUS	mandatory
	DESCRIPTION		  
		"Refers to the line number
		"
	::= { ascChanStateSigLmiGrpEntry 1}

ascLmiVccVpi OBJECT-TYPE
	SYNTAX	INTEGER (5..14)
	ACCESS	read-only
	STATUS	mandatory
	DESCRIPTION		  
		"Refers to the Virtual Path Indicator
		"
	::= { ascChanStateSigLmiGrpEntry 2}

ascLmiVccVci OBJECT-TYPE
	SYNTAX	INTEGER (16..271)
	ACCESS	read-only
	STATUS	mandatory
	DESCRIPTION		  
		"Refers to the Virtual Channel Indicator
		"
	::= { ascChanStateSigLmiGrpEntry 3}
		      	   
ascLmiXmtAbitState OBJECT-TYPE
	SYNTAX	INTEGER (0..1)
    	ACCESS read-only
    	STATUS  mandatory
    	DESCRIPTION
      		"This is the transmit A bit state
		0 - A bit clear = not active
		1 - A bit set = active
		"
	::= { ascChanStateSigLmiGrpEntry 4}

ascLmiRcvAbitState OBJECT-TYPE
	SYNTAX	INTEGER (0..1)
    	ACCESS read-only
    	STATUS  mandatory
    	DESCRIPTION
      		"This is the receive A bit state
		0 - A bit clear = not active
		1 - A bit set = active
		"
	::= { ascChanStateSigLmiGrpEntry 5}



-- ------------------------------------------------------------------------
-- End of ascChanStateSigLmiGrp group definitions


--
-- ----------------------------------------------------------------------
-- BASIS Project MIB
-- 
--





ascLineCnfSigLmiGrp   	OBJECT IDENTIFIER ::= { atmLmiSignaling 1 }


-- ------------------------------------------------------------------------
--
-- ascCnfSigLMI group
-- Line configurable ATM LMI signalling parameters  
--
-- ------------------------------------------------------------------------


ascCnfSigLmiGrpTable	OBJECT-TYPE
	SYNTAX	SEQUENCE OF AscCnfSigLmiGrpEntry
	ACCESS	not-accessible
	STATUS	mandatory
	DESCRIPTION
		"The config table is for DS3 line interface
		"
	::= { ascLineCnfSigLmiGrp 1 }

ascCnfSigLmiGrpEntry	OBJECT-TYPE
	SYNTAX	AscCnfSigLmiGrpEntry
	ACCESS	not-accessible
	STATUS	mandatory
	DESCRIPTION
		" An entry for logical line
		"
	INDEX	{ ascLmiCnfLineNum }
	::= { ascCnfSigLmiGrpTable 1 }

AscCnfSigLmiGrpEntry ::=
	SEQUENCE {
	   	ascLmiCnfLineNum              INTEGER,
		ascLmiVpi                     INTEGER, 
		ascLmiVci                     INTEGER, 
		ascLmiEnabled                 INTEGER,
		ascLmiPollingEnabled          INTEGER,
		ascLmiPollingInterval         INTEGER,
		ascLmiTimerT393               INTEGER,
		ascLmiTimerT394               INTEGER,
		ascLmiMaxRetryN394 	      INTEGER,
		ascLmiMaxRetryN395	      INTEGER, 
		ascLmiOperStatus      	      INTEGER 
		}


ascLmiCnfLineNum OBJECT-TYPE
	SYNTAX	INTEGER{
               lmiCnflineNum (1)
            }
	ACCESS	read-only
	STATUS	mandatory
	DESCRIPTION		  
		"Refers to the logical line index
		"
	::= { ascCnfSigLmiGrpEntry 1}

ascLmiVpi OBJECT-TYPE
	SYNTAX	INTEGER{
               lmiVpi (3)
            }
	ACCESS	read-only
	STATUS	mandatory
	DESCRIPTION		  
		"VPI used for ATM LMI signalling 
		"
	::= { ascCnfSigLmiGrpEntry 2}
		      	   
ascLmiVci OBJECT-TYPE
	SYNTAX	INTEGER{
               lmiVci (31)
            }
	ACCESS	read-only
	STATUS	mandatory
	DESCRIPTION		  
		"VCI used for ATM LMI signalling 
		"
	::= { ascCnfSigLmiGrpEntry 3}
		      	   
ascLmiEnabled  OBJECT-TYPE
	SYNTAX	INTEGER {
		disable(1),
		atmLmiEnable(2),
		atmLmiwithExtEnable(3),
        atmLmiEnhManualRecovery(4),
        atmLmiEnhAutoRecovery(5)
		}
    ACCESS read-write
    STATUS  mandatory
    DESCRIPTION
      		"This will enable ATM LMI signalling, 
      		or ATM LMI with the Node Status Extensions
		"
	::= { ascCnfSigLmiGrpEntry 4}

ascLmiPollingEnabled  OBJECT-TYPE
	SYNTAX	INTEGER {
		disable(1),
		enable(2)
		}
    ACCESS read-write
    STATUS  mandatory
    DESCRIPTION
     		"This will enable ATM LMI polling
		"
	::= { ascCnfSigLmiGrpEntry 5}

ascLmiPollingInterval OBJECT-TYPE
	SYNTAX	INTEGER (5..30)
	ACCESS	read-write
	STATUS	mandatory
	DESCRIPTION		  
		"Status Enq Polling Interval in seconds
		Default is 10 seconds
		"
	::= { ascCnfSigLmiGrpEntry 6}

ascLmiTimerT393 OBJECT-TYPE
	SYNTAX	INTEGER (5..30)
	ACCESS	read-write
	STATUS	mandatory
	DESCRIPTION		  
		"Status Enq timeout interval in seconds
		Default is 10 seconds
		"
	::= { ascCnfSigLmiGrpEntry 7}
		      	   
ascLmiTimerT394 OBJECT-TYPE
	SYNTAX	INTEGER (5..30)
	ACCESS	read-write
	STATUS	mandatory
	DESCRIPTION		  
		"Update Status timeout interval in seconds
		Default is 10 seconds
		"
	::= { ascCnfSigLmiGrpEntry 8}
		      	   
ascLmiMaxRetryN394	OBJECT-TYPE
	SYNTAX	INTEGER (1..10)
	ACCESS read-write
    STATUS  mandatory
    DESCRIPTION
		"Status Enq maximum retry count
		Default is 3
		"
	::= { ascCnfSigLmiGrpEntry 9}

ascLmiMaxRetryN395	OBJECT-TYPE
	SYNTAX	INTEGER (1..10)
	ACCESS read-write
    STATUS  mandatory
    DESCRIPTION
		"Update Status maximum retry count
		Default is 3
		"
	::= { ascCnfSigLmiGrpEntry 10}

ascLmiOperStatus	OBJECT-TYPE
	SYNTAX	INTEGER {
		atmLmiFailed(1),
		atmLmiActive(2)
		}
	ACCESS read-only
    STATUS  mandatory
    DESCRIPTION
		"Operational status
		"
	::= { ascCnfSigLmiGrpEntry 11}


-- ------------------------------------------------------------------------
-- End of ascCnfSigLmiGrp group definitions


--
-- ----------------------------------------------------------------------
-- BASIS Project MIB
-- 
--





ascCntSigLmiGrp   	OBJECT IDENTIFIER ::= { atmLmiSignaling 2 }


-- ------------------------------------------------------------------------
--
-- ascCntSigLmi group
-- Line ATM LMI signalling counters
--
-- ------------------------------------------------------------------------


ascCntSigLmiGrpTable	OBJECT-TYPE
	SYNTAX	SEQUENCE OF AscCntSigLmiGrpEntry
	ACCESS	not-accessible
	STATUS	mandatory
	DESCRIPTION
		"The counter table is for DS3 line interface
		"
	::= { ascCntSigLmiGrp 1 }

ascCntSigLmiGrpEntry	OBJECT-TYPE
	SYNTAX	AscCntSigLmiGrpEntry
	ACCESS	not-accessible
	STATUS	mandatory
	DESCRIPTION
		" An entry for logical line
		"
	INDEX	{ ascLmiCntLineNum }
	::= { ascCntSigLmiGrpTable 1 }

AscCntSigLmiGrpEntry ::=
	SEQUENCE {
	   	ascLmiCntLineNum              INTEGER,
		ascLmiStatusTx                Counter, 
		ascLmiStatusEnqTx             Counter, 
		ascLmiStatusAckTx             Counter,
		ascLmiUpdateStatusTx          Counter,
		ascLmiStatusRx                Counter, 
		ascLmiStatusEnqRx             Counter, 
		ascLmiStatusAckRx             Counter,
		ascLmiUpdateStatusRx          Counter,
		ascLmiInvalidPduRx            Counter,
		ascLmiInvalidPduLenRx         Counter,
		ascLmiUnknownPduRx            Counter,
		ascLmiInvalidIeRx  	      Counter,
		ascLmiInvalidTransaction      Counter, 
		ascLmiTimeoutFailure          Counter, 
		ascLmiNodeStatusTx            Counter, 
		ascLmiNodeStatusAckTx         Counter,
		ascLmiNodeStatusRx            Counter, 
		ascLmiNodeStatusAckRx         Counter
		}


ascLmiCntLineNum OBJECT-TYPE
	SYNTAX	INTEGER{
              lmiCntLineNum (1)
            }
	ACCESS	read-only
	STATUS	mandatory
	DESCRIPTION		  
		"Refers to the logical line index
		"
	::= { ascCntSigLmiGrpEntry 1}

ascLmiStatusTx OBJECT-TYPE
	SYNTAX	Counter
	ACCESS	read-only
	STATUS	mandatory
	DESCRIPTION		  
		"The number of Status PDUs transmitted
		"
	::= { ascCntSigLmiGrpEntry 2}

ascLmiStatusEnqTx OBJECT-TYPE
	SYNTAX	Counter
	ACCESS	read-only
	STATUS	mandatory
	DESCRIPTION		  
		"The number of Status Enquiry PDUs transmitted
		"
	::= { ascCntSigLmiGrpEntry 3}

ascLmiStatusAckTx OBJECT-TYPE
	SYNTAX	Counter
	ACCESS	read-only
	STATUS	mandatory
	DESCRIPTION		  
		"The number of Status Ack PDUs transmitted
		"
	::= { ascCntSigLmiGrpEntry 4}

ascLmiUpdateStatusTx OBJECT-TYPE
	SYNTAX	Counter
	ACCESS	read-only
	STATUS	mandatory
	DESCRIPTION		  
		"The number of Update Status PDUs transmitted
		"
	::= { ascCntSigLmiGrpEntry 5}

ascLmiStatusRx OBJECT-TYPE
	SYNTAX	Counter
	ACCESS	read-only
	STATUS	mandatory
	DESCRIPTION		  
		"The number of Status PDUs received
		"
	::= { ascCntSigLmiGrpEntry 6}

ascLmiStatusEnqRx OBJECT-TYPE
	SYNTAX	Counter
	ACCESS	read-only
	STATUS	mandatory
	DESCRIPTION		  
		"The number of Status Enquiry PDUs received
		"
	::= { ascCntSigLmiGrpEntry 7}

ascLmiStatusAckRx OBJECT-TYPE
	SYNTAX	Counter
	ACCESS	read-only
	STATUS	mandatory
	DESCRIPTION		  
		"The number of Status Ack PDUs received
		"
	::= { ascCntSigLmiGrpEntry 8}

ascLmiUpdateStatusRx OBJECT-TYPE
	SYNTAX	Counter
	ACCESS	read-only
	STATUS	mandatory
	DESCRIPTION		  
		"The number of Update Status PDUs received
		"
	::= { ascCntSigLmiGrpEntry 9}

ascLmiInvalidPduRx OBJECT-TYPE
	SYNTAX	Counter
	ACCESS	read-only
	STATUS	mandatory
	DESCRIPTION		  
		"The number of Invalid PDUs received.
		These are PDUs with invalid SSCOP or Q.2931 header,
		or invalid Protocol Discriminator 
		"
	::= { ascCntSigLmiGrpEntry 10}

ascLmiInvalidPduLenRx OBJECT-TYPE
	SYNTAX	Counter
	ACCESS	read-only
	STATUS	mandatory
	DESCRIPTION		  
		"The number of PDUs received with invalid length.
        	ATM LMI PDU Length field plus Q.2931 Header length
        	does not equal actual message length
		"
	::= { ascCntSigLmiGrpEntry 11}

ascLmiUnknownPduRx OBJECT-TYPE
	SYNTAX	Counter
	ACCESS	read-only
	STATUS	mandatory
	DESCRIPTION		  
		"The number of PDUs with unknown Message Type received
		"
	::= { ascCntSigLmiGrpEntry 12}

ascLmiInvalidIeRx OBJECT-TYPE
	SYNTAX	Counter
	ACCESS	read-only
	STATUS	mandatory
	DESCRIPTION		  
		"The number of PDUs received with invalid Information Elements.
		This includes IEs with invalid length and missing mandatory IEs
		"
	::= { ascCntSigLmiGrpEntry 13}

ascLmiInvalidTransaction OBJECT-TYPE
	SYNTAX	Counter
	ACCESS	read-only
	STATUS	mandatory
	DESCRIPTION		  
		"The number of invalid transactions.
		The transaction number of a transmitted Update Status PDU does
		not match the transaction number of the corresponding received
		Status Ack PDU, or, 
        	the transaction number of a transmitted Status Enq PDU does
        	not match the transaction number of the corresponding received
        Status PDU.
		"
	::= { ascCntSigLmiGrpEntry 14}

ascLmiTimeoutFailure OBJECT-TYPE
	SYNTAX	Counter
	ACCESS	read-only
	STATUS	mandatory
	DESCRIPTION		  
		"The number of timeout failures
		"
	::= { ascCntSigLmiGrpEntry 15}

ascLmiNodeStatusTx OBJECT-TYPE
	SYNTAX	Counter
	ACCESS	read-only
	STATUS	mandatory
	DESCRIPTION		  
		"The number of Node Status PDUs transmitted
		"
	::= { ascCntSigLmiGrpEntry 16}

ascLmiNodeStatusAckTx OBJECT-TYPE
	SYNTAX	Counter
	ACCESS	read-only
	STATUS	mandatory
	DESCRIPTION		  
		"The number of Node Status Ack PDUs transmitted
		"
	::= { ascCntSigLmiGrpEntry 17}

ascLmiNodeStatusRx OBJECT-TYPE
	SYNTAX	Counter
	ACCESS	read-only
	STATUS	mandatory
	DESCRIPTION		  
		"The number of Node Status PDUs received
		"
	::= { ascCntSigLmiGrpEntry 18}

ascLmiNodeStatusAckRx OBJECT-TYPE
	SYNTAX	Counter
	ACCESS	read-only
	STATUS	mandatory
	DESCRIPTION		  
		"The number of Node Status Ack PDUs received
		"
	::= { ascCntSigLmiGrpEntry 19}




-- ------------------------------------------------------------------------
-- End of ascCnfSigLmiGrp group definitions






pxmFeatures    OBJECT IDENTIFIER ::= {cardSpecific 15}

-- ------------------------------------------------------------------------
-- PXM Feature Group
--
-- This contains all Platform features
-- ------------------------------------------------------------------------

vsiControllersAllowed OBJECT-TYPE
        SYNTAX  INTEGER (0..'ffffff'h)
	ACCESS	read-only
	STATUS	mandatory
	DESCRIPTION
                "This respesents bit map of the VSI Controllers
                 supported. Currently, we have 

                   BIT  0 - PAR
                   BIT  1 - PNNI
                   BIT  2 - TAG
                  
                 (e.g. A value of 1 in BIT 0 indicates the presence of PAR )

                 Remaining bits are set to 0.
                "
	::= { pxmFeatures 1 }

apsCardAttributes OBJECT-TYPE
        SYNTAX  INTEGER (0..'ff'h)
        ACCESS  read-only
        STATUS  mandatory
        DESCRIPTION
                "This respesents bit map of the APS card attributes
                 supported. Currently, we have

                   BIT  0, 1 - unused
                   BIT  2 - APS standard protocol configured
                            (1 = TRUE ; 0 = FALSE)
                   BIT  3, 4 ,5 - unused
                   BIT  6 - Card HW supports APS 1+1 on two cards
                            (1 = TRUE ; 0 = FALSE)
                   BIT  7 - Card FW supports APS (1 = TRUE ; 0 = FALSE)
 
                 Remaining bits are set to 0.
                "
        ::= { pxmFeatures 2 }

trkCACEnable  OBJECT-TYPE
        SYNTAX  INTEGER {
	 disable (1),
         enable (2)
        }
        ACCESS  read-write
        STATUS  mandatory
        DESCRIPTION
	    "This MIB variable allows one to add a new connection on 
             the feeder trunk even if it is over-subscribed.
            "
    DEFVAL { disable }

        ::= { pxmFeatures 3 }	



pxmAtmMIBObjects        OBJECT IDENTIFIER ::= { atm 16 }

--     ATM Virtual Channel (VC) Cross Connect Group

-- This group contains configuration and state
-- information of a bi-directional VC cross-connect.

-- This group is used to model a bi-directional
-- point-to-point, point-to-multipoint or
-- multipoint-to-multipoint VC cross-connects.

-- This table has read-only access and is used
-- to cross-connect the VCLs together in an ATM switch
-- or network that belong to a VC connection.
-- The pxmAtmVcCrossConnectIndex is used to associate
-- the related VCLs that are cross-connected together.


-- The step-wise procedures described for setting
-- up a VP cross-connect are also used for setting up
-- a VC cross-connect.


pxmAtmVcCrossConnectIndexNext    OBJECT-TYPE
     SYNTAX  INTEGER (0..2147483647)
     ACCESS  read-only
     STATUS  mandatory
     DESCRIPTION
      "This object contains an appropriate value to
       be used for pxmAtmVcCrossConnectIndex when creating
       entries in the pxmAtmVcCrossConnectTable.  The value
       0 indicates that no unassigned entries are
       available. To obtain the pxmAtmVpCrossConnectIndex
       value for a new entry, the manager issues a
       management protocol retrieval operation to obtain
       the current value of this object.  After each
       retrieval, the agent should modify the value to
       the next unassigned index."
     ::= { pxmAtmMIBObjects 10 }


--  The ATM VC Cross Connect Table

pxmAtmVcCrossConnectTable OBJECT-TYPE
     SYNTAX  SEQUENCE OF PxmAtmVcCrossConnectEntry
     ACCESS  not-accessible
     STATUS  mandatory
     DESCRIPTION
      "The ATM VC Cross Connect table.  A bi-
       directional VC cross-connect which
       cross-connects two end points (i.e., VCLs)
       is modeled as one entry in this table."
     ::= { pxmAtmMIBObjects 11 }


pxmAtmVcCrossConnectEntry OBJECT-TYPE
     SYNTAX  PxmAtmVcCrossConnectEntry
     ACCESS  not-accessible
     STATUS  mandatory
     DESCRIPTION
      "An entry in the ATM VC Cross Connect table.
       This entry is used to model a bi-directional ATM
       VC cross-connect cross-connecting two end points.

       Step-wise Procedures to set up a VC Cross-connect

       Once the entries in the pxmAtmVclTable are created,
       the following procedures are used
       to cross-connect the VCLs together to
       form a VCC segment.

      (1) The manager obtains a unique
          pxmAtmVcCrossConnectIndex by reading the
          pxmAtmVcCrossConnectIndexNext object.

      (2) Next, the manager creates a set of one
          or more rows in the ATM VC Cross Connect
          Table, one for each cross-connection between
          two VCLs.  Each row is indexed by the ATM
          interface port numbers and VPI/VCI values of
          the two ends of that cross-connection.
          This set of rows specifies the topology of the
          VCC cross-connect and is identified by a single
          value of pxmAtmVcCrossConnectIndex.

       Negotiated VC Cross-Connect Establishment

     (2a) The manager creates a row in this table by
          setting pxmAtmVcCrossConnectRowStatus to
          createAndWait(5).  The agent checks the
          requested topology and the mutual sanity of
          the ATM traffic parameters and
          QoS Classes, i.e., the row creation fails if:
          - the requested topology is not supported
            by the agent,
          - the traffic/QoS parameter values
            associated with the requested row are
            incompatible with those of already existing
            rows for this VC cross-connect.
          [For example, for setting up
          a point-to-point VC cross-connect, the
          ATM traffic parameters in the receive direction
          of a VCL at the low end of the cross-connect
          must equal to the traffic parameters in the
          transmit direction of the other VCL at the
          high end of the cross-connect,
          otherwise, the row creation fails.]
          The agent also checks for internal errors
          in building the cross-connect.

          The pxmAtmVcCrossConnectIndex values in the
          corresponding pxmAtmVclTable rows are filled
          in by the agent at this point.

     (2b) The manager promotes the row in the
          pxmAtmVcCrossConnectTable by setting
          pxmAtmVcCrossConnectRowStatus to active(1).  If
          this set is successful, the agent has reserved
          the resources specified by the ATM traffic
          parameter and QoS Class values
          for each direction of the VC cross-connect
          in an ATM switch or network.

      (3) The manager sets the
          pxmAtmVcCrossConnectAdminStatus to up(1)
          in all rows of this VC cross-connect to
          turn the traffic flow on.


       One-Shot VC Cross-Connect Establishment

       A VC cross-connect may also be established in
       one step by a set-request with all necessary
       parameter values and pxmAtmVcCrossConnectRowStatus
       set to createAndGo(4).

       In contrast to the negotiated VC cross-connect
       establishment which allows for detailed error
       checking i.e., set errors are explicitly linked to
       particular resource acquisition failures), the
       one-shot VC cross-connect establishment
       performs the setup on one operation but does
       not have the advantage of step-wise error
       checking.

       VC Cross-Connect Retirement

       A VC cross-connect identified by a particular
       value of pxmAtmVcCrossConnectIndex is released by:

      (1) Setting pxmAtmVcCrossConnectRowStatus of all rows
          identified by this value of
          pxmAtmVcCrossConnectIndex to destroy(6).
          The agent may release all
          associated resources, and the
          pxmAtmVcCrossConnectIndex values in the
          corresponding pxmAtmVclTable row are removed.
          Note that a situation when only a subset of
          the associated rows are deleted corresponds
          to a VC topology change.

      (2) After deletion of the appropriate
          pxmAtmVcCrossConnectEntries, the manager may
          set pxmAtmVclRowStatus to destroy(6) the
          associated VCLs.  The agent releases
          the resources and removes the associated
          rows in the pxmAtmVclTable.

       VC Cross-Connect Reconfiguration

       At the discretion of the agent, a VC
       cross-connect may be reconfigured by
       adding and/or deleting leafs to/from
       the VC topology as per the VC cross-connect
       establishment/retirement procedures.
       Reconfiguration of traffic/QoS parameter
       values requires release of the VC cross-connect
       before those parameter values may by changed
       for individual VCLs."
     INDEX { pxmAtmVcCrossConnectIndex,
           pxmAtmVcCrossConnectLowIfIndex,
           pxmAtmVcCrossConnectLowVpi,
           pxmAtmVcCrossConnectLowVci,
           pxmAtmVcCrossConnectHighIfIndex,
           pxmAtmVcCrossConnectHighVpi,
           pxmAtmVcCrossConnectHighVci }
     ::= { pxmAtmVcCrossConnectTable 1 }



PxmAtmVcCrossConnectEntry ::= SEQUENCE {
     pxmAtmVcCrossConnectIndex          INTEGER,
     pxmAtmVcCrossConnectLowIfIndex     INTEGER,
     pxmAtmVcCrossConnectLowVpi         INTEGER,
     pxmAtmVcCrossConnectLowVci         INTEGER,
     pxmAtmVcCrossConnectHighIfIndex    INTEGER,
     pxmAtmVcCrossConnectHighVpi        INTEGER,
     pxmAtmVcCrossConnectHighVci        INTEGER,
     pxmAtmVcCrossConnectAdminStatus    INTEGER,
     pxmAtmVcCrossConnectL2HOperStatus  INTEGER,
     pxmAtmVcCrossConnectH2LOperStatus  INTEGER,
     pxmAtmVcCrossConnectL2HLastChange  INTEGER,
     pxmAtmVcCrossConnectH2LLastChange  INTEGER,
     pxmAtmVcCrossConnectRowStatus      INTEGER,
     pxmAtmVcCrossConnectHighAddressType INTEGER,
     pxmAtmVcCrossConnectLowAddressType INTEGER
             }

pxmAtmVcCrossConnectIndex OBJECT-TYPE
     SYNTAX  INTEGER (1..2147483647)
     ACCESS  read-only
     STATUS  mandatory
     DESCRIPTION
      "A unique value to identify this VC cross-connect."
     ::= { pxmAtmVcCrossConnectEntry 1 }

pxmAtmVcCrossConnectLowIfIndex OBJECT-TYPE
     SYNTAX  INTEGER (1..2147483647)
     ACCESS  read-only
     STATUS  mandatory
     DESCRIPTION
      "The value of this object is equal to MIB II's
       ifIndex value of the ATM interface port for this
       VC cross-connect.  The term low implies
       that this ATM interface has the numerically lower
       ifIndex value than the other ATM interface
       identified in the same pxmAtmVcCrossConnectEntry."
     ::= { pxmAtmVcCrossConnectEntry 2 }

pxmAtmVcCrossConnectLowVpi OBJECT-TYPE
     SYNTAX  INTEGER  (0..4095)
     ACCESS  read-only
     STATUS  mandatory
     DESCRIPTION
      "The value of this object is equal to the VPI
       value at the ATM interface
       associated with the VC cross-connect that is
       identified by pxmAtmVcCrossConnectLowIfIndex.
       The VPI value cannot exceed the number
       supported by the pxmAtmInterfaceMaxVpiBits
       at the low ATM interface port."
     ::= { pxmAtmVcCrossConnectEntry 3 }

pxmAtmVcCrossConnectLowVci OBJECT-TYPE
     SYNTAX  INTEGER  (0..65535)
     ACCESS  read-only
     STATUS  mandatory
     DESCRIPTION
      "The value of this object is equal to the VCI
       value at the ATM interface
       associated with this VC cross-connect that is
       identified by pxmAtmVcCrossConnectLowIfIndex.
       The VCI value cannot exceed the number
       supported by the pxmAtmInterfaceMaxVciBits
       at the low ATM interface port."
     ::= { pxmAtmVcCrossConnectEntry 4 }

pxmAtmVcCrossConnectHighIfIndex OBJECT-TYPE
     SYNTAX  INTEGER (1..2147483647)
     ACCESS  read-only
     STATUS  mandatory
     DESCRIPTION
      "The value of this object is equal to MIB II's
       ifIndex value for the ATM interface port for
       this VC cross-connect.  The term high
       implies that this VC cross-connect
       that this ATM interface has the numerically higher
       ifIndex value than the other ATM interface
       identified in the same pxmAtmVcCrossConnectEntry."
     ::= { pxmAtmVcCrossConnectEntry 5 }

pxmAtmVcCrossConnectHighVpi OBJECT-TYPE
     SYNTAX  INTEGER   (0..4095)
     ACCESS  read-only
     STATUS  mandatory
     DESCRIPTION
      "The value of this object is equal to the VPI
       value at the ATM interface
       associated with the VC cross-connect that is
       identified by pxmAtmVcCrossConnectHighIfIndex.
       The VPI value cannot exceed
       the number supported by the pxmAtmInterfaceMaxVpiBits
       at the high ATM interface port."
     ::= { pxmAtmVcCrossConnectEntry 6 }

pxmAtmVcCrossConnectHighVci OBJECT-TYPE
     SYNTAX  INTEGER   (0..65535)
     ACCESS  read-only
     STATUS  mandatory
     DESCRIPTION
      "The value of this object is equal to the VCI
       value at the ATM interface
       associated with the VC cross-connect that is
       identified by pxmAtmVcCrossConnectHighIfIndex.
       The VCI value cannot exceed
       the number supported by the pxmAtmInterfaceMaxVciBits
       at the high ATM interface port."
     ::= { pxmAtmVcCrossConnectEntry 7 }

pxmAtmVcCrossConnectAdminStatus OBJECT-TYPE
     SYNTAX  INTEGER {
               up(1),
               down(2)
               }
     ACCESS  read-only
     STATUS  mandatory
     DESCRIPTION
      "The value of this object identifies the desired
       administrative status of this bi-directional
       VC cross-connect. The up and down states
       indicate that the traffic flow is enabled or
       disabled respectively on this VC cross-connect."
     DEFVAL { down }
     ::= { pxmAtmVcCrossConnectEntry 8 }

pxmAtmVcCrossConnectL2HOperStatus OBJECT-TYPE
     SYNTAX  INTEGER {
               up(1),
               down(2),
               unknown(3)
             }
     ACCESS  read-only
     STATUS  mandatory
     DESCRIPTION
      "The value of this object identifies the current
       operational status of the VC cross-connect
       in one direction; (i.e., from the low to
       high direction).  The up and down states indicate
       that this ATM VC cross-connect from low
       to high direction is operational or not
       operational respectively.  The unknown state
       indicates that the state of it cannot be
       determined."
     ::= { pxmAtmVcCrossConnectEntry 9 }

pxmAtmVcCrossConnectH2LOperStatus OBJECT-TYPE
     SYNTAX  INTEGER {
               up(1),
               down(2),
               unknown(3)
             }
     ACCESS  read-only
     STATUS  mandatory
     DESCRIPTION
      "The value of this object identifies the current
       operational status of the VC cross-connect
       in one direction; (i.e., from the high to
       low direction).  The up and down states indicate
       that this ATM VC cross-connect from high
       to low direction is operational or not
       operational respectively.  The unknown state
       indicates that the state of it cannot be
       determined."
     ::= { pxmAtmVcCrossConnectEntry 10 }

pxmAtmVcCrossConnectL2HLastChange OBJECT-TYPE
     SYNTAX  INTEGER
     ACCESS  read-only
     STATUS  mandatory
     DESCRIPTION
      "The value of MIB II's sysUpTime object
       at the time this VC cross-connect entered
       its current operational state in low to high
       direction.  If the current state was
       entered prior to the last re-initialization of the
       agent, then this object contains a zero value."
     ::= { pxmAtmVcCrossConnectEntry 11 }

pxmAtmVcCrossConnectH2LLastChange OBJECT-TYPE
     SYNTAX  INTEGER
     ACCESS  read-only
     STATUS  mandatory
     DESCRIPTION
      "The value of MIB II's sysUpTime object
       at the time this VC cross-connect entered
       its current operational state in high to low
       direction.  If the current state was
       entered prior to the last re-initialization of the
       agent, then this object contains a zero value."
     ::= { pxmAtmVcCrossConnectEntry 12 }

pxmAtmVcCrossConnectRowStatus OBJECT-TYPE
     SYNTAX  INTEGER

     ACCESS  read-only
     STATUS  mandatory
     DESCRIPTION
      "The status of this entry in the
       pxmAtmVcCrossConnectTable.  This object is used to
       create a new cross-connect for cross-connecting
       VCLs which are created using the pxmAtmVclTable
       or to change or delete existing cross-connect.
       This object must be initially set to
       `createAndWait' or `createAndGo'.  This object
       cannot be set to `active' unless the following
       columnar object exists in this row:
       pxmAtmVcCrossConnectAdminStatus.
       To turn on a VC cross-connect,
       the pxmAtmVcCrossConnectAdminStatus
       is set to `up'."
     ::= { pxmAtmVcCrossConnectEntry 13 }

  pxmAtmVcCrossConnectHighAddressType OBJECT-TYPE
     SYNTAX  INTEGER {
               atmUni(1),
               atmNni(2),
               frameRelay(3)
             }
     ACCESS  read-only
     STATUS  mandatory
     DESCRIPTION
      "The value of this object identifies the address type of the
       interface associated with the VC cross-connect that is 
       identified by pxmAtmVcCrossConnectHighIfIndex. If the address
       type is pxmAtmUni, the first 4 bits of the VPI field is the
       GFCI and the remaing 12 bits of the VPI field is the VPI. If
       the address type is pxmAtmNni, the whole 16 bits of the VPI
       is the VPI. If the address type is the frameRelay, the 
       combination of the VPI field and the VCI field are the DLCI."
      ::= { pxmAtmVcCrossConnectEntry 14 }

  pxmAtmVcCrossConnectLowAddressType OBJECT-TYPE
     SYNTAX  INTEGER {
               atmUni(1),
               atmNni(2),
               frameRelay(3)
             }
     ACCESS  read-only
     STATUS  mandatory
     DESCRIPTION
      "The value of this object identifies the address type of the
       interface associated with the VC cross-connect that is 
       identified by pxmAtmVcCrossConnectLowIfIndex. If the address
       type is pxmAtmUni, the first 4 bits of the VPI field is the
       GFCI and the remaing 12 bits of the VPI field is the VPI. If
       the address type is pxmAtmNni, the whole 16 bits of the VPI
       is the VPI. If the address type is the frameRelay, the 
       combination of the VPI field and the VCI field are the DLCI."
	
      ::= { pxmAtmVcCrossConnectEntry 15}


 
-- atm              OBJECT IDENTIFIER ::= { basisServices 2 }
-- atmLines   		OBJECT IDENTIFIER ::= { atm 5 }
-- atmLineCnfGrp    OBJECT IDENTIFIER ::= { atmLines 1 }
 
-- --------------------------------------------------------------------
--
-- ATM LINE COUNTS Group
--
-- --------------------------------------------------------------------
 
atmLineCnfTable OBJECT-TYPE
    SYNTAX  SEQUENCE OF AtmLineCnfEntry
    ACCESS  not-accessible
    STATUS  mandatory
    DESCRIPTION "
        The ATM Line config table is for the physical interface.
        There will an entry for each of the physical line.
    "
    ::= { atmLineCnfGrp 1 }

atmLineCnfEntry OBJECT-TYPE
    SYNTAX  AtmLineCnfEntry
    ACCESS  not-accessible
    STATUS  mandatory
    DESCRIPTION "
        An entry for the physical interface. 
    "
    INDEX   { atmLineCnfNum }
    ::= { atmLineCnfTable 1 }
 
AtmLineCnfEntry ::=
    SEQUENCE {
		atmLineCnfNum
			INTEGER,
		atmLineInterfaceFormat
			INTEGER
	}

atmLineCnfNum OBJECT-TYPE
	SYNTAX  INTEGER (1..4)
	ACCESS  read-only
	STATUS  mandatory
	DESCRIPTION "
		Refers to the phsical line number, PXM port will have a maximum of
		4 lines.
	"
	::= { atmLineCnfEntry 1}

atmLineInterfaceFormat   OBJECT-TYPE
    SYNTAX INTEGER {
        other(1),
        atmUni(2),
        atmNni(3)
        }
    ACCESS read-write
    STATUS mandatory
    DESCRIPTION "
		This indicates the format of the cells going out on the 
		physical interface
	"
	DEFVAL { atmUni }
    ::= { atmLineCnfEntry 2 }


-- --------------------------------------------------------------------
-- End of atmLineCnfGrp
-- --------------------------------------------------------------------

 
-- atm              OBJECT IDENTIFIER ::= { basisServices 2 }
-- atmLines   		OBJECT IDENTIFIER ::= { atm 7 }
-- atmLineCntGrp  OBJECT IDENTIFIER ::= { atmLines 2 }
 
-- --------------------------------------------------------------------
--
-- ATM LINE COUNTS Group
--
-- --------------------------------------------------------------------
 
atmLineCntTable OBJECT-TYPE
    SYNTAX  SEQUENCE OF AtmLineCntEntry
    ACCESS  not-accessible
    STATUS  mandatory
    DESCRIPTION "
        The ATM Line count table is for the physical interface.
        There will an entry for each of the physical line.
    "
    ::= { atmLineCntGrp 1 }

atmLineCntEntry OBJECT-TYPE
    SYNTAX  AtmLineCntEntry
    ACCESS  not-accessible
    STATUS  mandatory
    DESCRIPTION "
        An entry for the physical interface. 
		These are counts which are collected on a physical line basis.
    "
    INDEX   { atmLineNum }
    ::= { atmLineCntTable 1 }
 
AtmLineCntEntry ::=
    SEQUENCE {
		atmLineNum
			INTEGER,
		atmLineTotalRcvCells
			Counter,
		atmLineTotalXmtCells
			Counter,
		atmLineRcvHecErrorCells
			Counter,
		atmLineCntClrButton
			INTEGER

	}

atmLineNum OBJECT-TYPE
	SYNTAX  INTEGER (1..4)
	ACCESS  read-only
	STATUS  mandatory
	DESCRIPTION "
		Refers to the phsical line number, PXM port will have a maximum of
		4 lines.
	"
	::= { atmLineCntEntry 1}

atmLineTotalRcvCells OBJECT-TYPE
	SYNTAX  Counter
	ACCESS  read-only
	STATUS  mandatory
	DESCRIPTION "
		The number of cells received in Ingress direction.
	"
	::= { atmLineCntEntry 2 }

atmLineTotalXmtCells OBJECT-TYPE
	SYNTAX  Counter
	ACCESS  read-only
	STATUS  mandatory
	DESCRIPTION "
		The number of cells transmitted in the egress direction
	"
	::= { atmLineCntEntry 3 }

atmLineRcvHecErrorCells  OBJECT-TYPE
	SYNTAX  Counter
	ACCESS  read-only
	STATUS  mandatory
	DESCRIPTION "
		Number of cells with HEC error
	"
	::= { atmLineCntEntry 4 }

atmLineCntClrButton OBJECT-TYPE
	SYNTAX  INTEGER {
		noAction (1),
		resetCounters (2)
	}
	ACCESS  read-write
	STATUS  mandatory
	DESCRIPTION "
		writing a value of 2 resets all the counters
	"
	::= { atmLineCntEntry 5 }


-- --------------------------------------------------------------------
-- End of atmLineCntGrp
-- --------------------------------------------------------------------

 
-- atm              OBJECT IDENTIFIER ::= { basisServices 2 }
-- bbInterface      OBJECT IDENTIFIER ::= { atm 6 }
-- bbIfCnf          OBJECT IDENTIFIER ::= { bbInterface 1 }
bbIfCnfPortGrp      OBJECT IDENTIFIER ::= { bbIfCnf 1}
 
-- --------------------------------------------------------------------
--
--
--      BROADBAND INTERFACE  CONFIG Group
--
--
-- --------------------------------------------------------------------
 
 
bbIfCnfPortGrpTable OBJECT-TYPE
    SYNTAX  SEQUENCE OF BbIfCnfPortGrpEntry
    ACCESS  not-accessible
    STATUS  mandatory
    DESCRIPTION "
        The Broadband Interface config table is for logical interface.
        There will an entry for each of the logical partition of the 
        physical line.
    "
    ::= { bbIfCnfPortGrp 1 }

bbIfCnfPortGrpEntry OBJECT-TYPE
    SYNTAX  BbIfCnfPortGrpEntry
    ACCESS  not-accessible
    STATUS  mandatory
    DESCRIPTION "
        An entry for the logical interface. The interface may be further
        be configured to be used as a virtual trunk OR as a UNI Port.
    "
    INDEX   { bbIfNum }
    ::= { bbIfCnfPortGrpTable  1 }

BbIfCnfPortGrpEntry ::=
    SEQUENCE {
        bbIfNum
            INTEGER,
        bbIfRowStatus
            INTEGER,
        bbIfAdmin
            INTEGER,
        bbIfLineNum
            INTEGER,
        bbIfIngrPctBandwidth
            INTEGER,
        bbIfEgrPctBandwidth 
            INTEGER,
        bbIfMinVpi 
            INTEGER,
        bbIfMaxVpi
            INTEGER,
        bbIfSpeed
            INTEGER,
        bbIfMaxCellRatePct
            INTEGER
    }

bbIfNum OBJECT-TYPE
    SYNTAX  INTEGER (1..32)
    ACCESS  read-only
    STATUS  mandatory
    DESCRIPTION "
        This is logical interface number within a physical line num.
        In MGX PXM card, a physical port can have a maximum of 32 logical
        interfaces. 
    "
    ::= { bbIfCnfPortGrpEntry 1}
 
bbIfRowStatus  OBJECT-TYPE
    SYNTAX  INTEGER {
        add (1),
        del (2),
        mod (3)
    }
    ACCESS read-write
    STATUS  mandatory
    DESCRIPTION "
        This variable enables or disables the logical interface.
        1 - enable
        2 - disable
        3 - modify
    "
    ::= { bbIfCnfPortGrpEntry 2 }

bbIfAdmin OBJECT-TYPE
    SYNTAX  INTEGER {
        up (1),
        down (2),
        writeOnly (3)
    }
    ACCESS read-write
    STATUS  mandatory
    DESCRIPTION "
        This variable enables or disables the logical interface.
        1 - up
        2 - down
        3 - writeOnly
    "
    ::= { bbIfCnfPortGrpEntry 3 }

bbIfLineNum OBJECT-TYPE
    SYNTAX  INTEGER (1..4)
    ACCESS read-write
    STATUS  mandatory
    DESCRIPTION "
        The line number associated with the logical interface. 
        For PXM, there  is currently 4 physical lines.
    "
    ::= { bbIfCnfPortGrpEntry 4 }

bbIfIngrPctBandwidth OBJECT-TYPE
    SYNTAX  INTEGER ( 0..100 )
    ACCESS  read-write
    STATUS  mandatory
    DESCRIPTION "
        The percentage of aggregate physical line bandwidth, available for
        this broadband interface - Ingress. Default is 0 %
    "
    DEFVAL { 0 }
    ::= { bbIfCnfPortGrpEntry  5 }

bbIfEgrPctBandwidth OBJECT-TYPE
    SYNTAX  INTEGER ( 0..100 )
    ACCESS  read-write
    STATUS  mandatory
    DESCRIPTION "
        The percentage of aggregate physical line bandwidth, available for
        this broadband interface - Egress . Default is 0 %
    "
    DEFVAL { 0 }
    ::= { bbIfCnfPortGrpEntry  6 }

bbIfMinVpi OBJECT-TYPE
    SYNTAX  INTEGER ( 0..4095 )
    ACCESS  read-write
    STATUS  mandatory
    DESCRIPTION "
        The lower limit of VPI range to be reserved for this logical interface.
    "
    ::= { bbIfCnfPortGrpEntry  7 }
 
 
bbIfMaxVpi OBJECT-TYPE
    SYNTAX  INTEGER ( 0..4095 )
    ACCESS  read-write
    STATUS  mandatory
    DESCRIPTION "
        The upper limit of VPI range to be reserved for this logical interface.

        For virtual trunks, bbIfMinVpi and bbIfMaxVpi should be the same.
    "
    ::= { bbIfCnfPortGrpEntry  8 }

bbIfSpeed  OBJECT-TYPE
    SYNTAX  INTEGER
    ACCESS  read-only
    STATUS  mandatory
    DESCRIPTION "
        The speed of the port in cells per second
    "
    ::= { bbIfCnfPortGrpEntry 9 }

bbIfMaxCellRatePct  OBJECT-TYPE
    SYNTAX  INTEGER ( 0..100 )
    ACCESS  read-write
    STATUS  mandatory
    DESCRIPTION "
        The maximum cell rate allowed for the port in terms of percentage.
        Must be greater than or equal to bbIfIngrPctBandwidth.
        The default is 100 percent.
    "
    ::= { bbIfCnfPortGrpEntry 10 }

-- Scalars in the bbIfCnfPortGrp
 
nextBbIfNumAvailable    OBJECT-TYPE
    SYNTAX  INTEGER(1..32)
    ACCESS  read-only
    STATUS  mandatory
    DESCRIPTION "
		Indicates the next logical broadband interface  number that is available
    "
    ::= { bbIfCnfPortGrp 2 }

  
-- --------------------------------------------------------------
-- End of bbIfCnfPortGrp
-- --------------------------------------------------------------

 
-- atm                  OBJECT IDENTIFIER ::= { basisServices 2 }
-- bbInterface          OBJECT IDENTIFIER ::= { atm 7 }
-- bbIfCnfResPartGrp    OBJECT IDENTIFIER ::= { bbInterface 2 }
 
-- --------------------------------------------------------------------
--
--
--      BROADBAND INTERFACE  CONFIG Group
--
--
-- --------------------------------------------------------------------

bbIfCnfRscPartGrpTable  OBJECT-TYPE
    SYNTAX  SEQUENCE OF BbIfCnfRscPartGrpEntry
    ACCESS  not-accessible
    STATUS  mandatory
    DESCRIPTION "
        The config table is for logical port interface
        There can be 32 entries for PXM card in MGX.
    "
    ::= { bbIfCnfResPartGrp 1 }

bbIfCnfRscPartGrpEntry  OBJECT-TYPE
    SYNTAX  BbIfCnfRscPartGrpEntry
    ACCESS  not-accessible
    STATUS  mandatory
    DESCRIPTION " 
        An entry for a logical interface
    "
    INDEX   { bbRscPartIfNum, bbRscPartCtrlrNum }
    ::= { bbIfCnfRscPartGrpTable 1 }
 
BbIfCnfRscPartGrpEntry ::=
    SEQUENCE {
        bbRscPartIfNum
            INTEGER,
        bbRscPartCtrlrNum
            INTEGER,

        bbIfRscPrtRowStatus
            INTEGER,
        bbIfRscPrtInUse
            INTEGER,

        bbIfRscPrtIngrPctBandwidth
            INTEGER,
        bbIfRscPrtEgrPctBandwidth
            INTEGER,

        bbIfRscPrtVpiLow
            INTEGER,
        bbIfRscPrtVpiHigh
            INTEGER,
        bbIfRscPrtVciLow
            INTEGER,
        bbIfRscPrtVciHigh
            INTEGER,
        bbIfRscPrtVpidLow
            INTEGER,
        bbIfRscPrtVpidHigh
            INTEGER,
        bbIfRscPrtMaxChans
            INTEGER,
        bbIfRscPartCtrlrID
            INTEGER

    }
 
 
bbRscPartIfNum OBJECT-TYPE
    SYNTAX  INTEGER (1..32)
    ACCESS  read-only
    STATUS  mandatory
    DESCRIPTION "
        This is logical interface number.
    "
    ::= { bbIfCnfRscPartGrpEntry 1}

bbRscPartCtrlrNum OBJECT-TYPE
	SYNTAX  INTEGER {
		par (1),
		pnni (2),
		tag (3)
	}
    ACCESS  read-only
    STATUS  mandatory
    DESCRIPTION "
        This is index for controller using the  interface .

        1 - PAR
        2 - PNNI
        3 - TAG
    "
    ::= { bbIfCnfRscPartGrpEntry 2}

bbIfRscPrtRowStatus OBJECT-TYPE
    SYNTAX  INTEGER {
        add (1),
        del (2),
        mod (3)
    }
    ACCESS  read-write
    STATUS  mandatory
    DESCRIPTION "
        This will add, delete or modify the partition.
        1 ==> ADD
        2 ==> DELETE
        3 ==> MODIFY
    "
    DEFVAL { del }
    ::= { bbIfCnfRscPartGrpEntry 3}


bbIfRscPrtInUse OBJECT-TYPE
    SYNTAX  INTEGER {
        inUse(1),
        notInUse(2)
    }
    ACCESS  read-write
    STATUS  mandatory
    DESCRIPTION "
        Setting this object to 1 indicates that the resources
        (LCN/Local VPID/VCI/VPI) have been partitioned and INS,
        network ctrlrs.,SV+ are currently using this information. The resource
        partition information can be changed after setting this
        variable to 2.
        The default value is 2 (NotInUse).
    "
    DEFVAL { notInUse }
    ::= { bbIfCnfRscPartGrpEntry 4 }

bbIfRscPrtIngrPctBandwidth OBJECT-TYPE
    SYNTAX  INTEGER (0..100)
    ACCESS  read-write
    STATUS  mandatory
    DESCRIPTION "
        The percentage of logical interface bandwidth ( bbIfIngrPctBandwidth ),
        available for UNI channels.
    "
    DEFVAL { 0 }
    ::= { bbIfCnfRscPartGrpEntry 5 }

bbIfRscPrtEgrPctBandwidth OBJECT-TYPE
    SYNTAX  INTEGER (0..100)
    ACCESS  read-write
    STATUS  mandatory
    DESCRIPTION "
        The percentage of logical interface bandwidth ( bbIfIngrPctBandwidth ),
        available for UNI channels.
    "
    DEFVAL { 0 }
    ::= { bbIfCnfRscPartGrpEntry 6 }


bbIfRscPrtVpiLow OBJECT-TYPE
    SYNTAX  INTEGER (0..4095)
    ACCESS  read-write
    STATUS  mandatory
    DESCRIPTION "
        The beginning of the VPI range reserved for this partition.
    "
    ::= { bbIfCnfRscPartGrpEntry 7 }
 
bbIfRscPrtVpiHigh OBJECT-TYPE
    SYNTAX  INTEGER (0..4095)
    ACCESS  read-write
    STATUS  mandatory
    DESCRIPTION "
        The end of the VPI range reserved for this partition.
    "
    ::= { bbIfCnfRscPartGrpEntry 8 }

bbIfRscPrtVciLow OBJECT-TYPE
    SYNTAX  INTEGER (0..'ffff'h)
    ACCESS  read-write
    STATUS  mandatory
    DESCRIPTION "
        The beginning of the VCI range reserved for this partition.
        This field is only valid for logical interfaces configured with
        a single VPI.
    "
    ::= { bbIfCnfRscPartGrpEntry 9 }
 
bbIfRscPrtVciHigh OBJECT-TYPE
    SYNTAX  INTEGER (0..'ffff'h)
    ACCESS  read-write
    STATUS  mandatory
    DESCRIPTION "
        The end of the VCI range reserved for this partition.
        This field is only valid for logical interfaces configured with      
        a single VPI.
    "
    ::= { bbIfCnfRscPartGrpEntry 10 }
 
                                                                 
bbIfRscPrtVpidLow OBJECT-TYPE
    SYNTAX  INTEGER (1..100)
    ACCESS  read-write
    STATUS  mandatory
    DESCRIPTION "
        The beginning of the VPID range reserved for partition.
        Used for VP conn.s
    "
    ::= { bbIfCnfRscPartGrpEntry 11 }
 
bbIfRscPrtVpidHigh OBJECT-TYPE
    SYNTAX  INTEGER (1..100)
    ACCESS  read-write
    STATUS  mandatory
    DESCRIPTION "
        The end of the VPID range reserved for partition.
        Used for VP conn.s
    "
    ::= { bbIfCnfRscPartGrpEntry 12 }

bbIfRscPrtMaxChans OBJECT-TYPE
    SYNTAX  INTEGER (0..32767)
    ACCESS  read-write
    STATUS  mandatory
    DESCRIPTION " 
        This represents no. of channels that are available to the 
        controller.
    "
    ::= { bbIfCnfRscPartGrpEntry 13 }
 
bbIfRscPartCtrlrID OBJECT-TYPE
    SYNTAX  INTEGER (0..255)
    ACCESS  read-write
    STATUS  mandatory
    DESCRIPTION "
        This is the controller identifier for resource patition.
        The default value is set for PNNI controller.
    "
    ::= { bbIfCnfRscPartGrpEntry 14 }

-- --------------------------------------------------------------
-- End of bbIfCnfRscPartGrp
-- --------------------------------------------------------------



-- atm                  OBJECT IDENTIFIER ::= { basisServices 2 }
-- bbInterface          OBJECT IDENTIFIER ::= { atm 7 }
-- bbIfCnf              OBJECT IDENTIFIER ::= { bbInterface 1 }

bbIfCnfSigILMIGrp       OBJECT IDENTIFIER ::= { bbIfCnf 2}

-- ------------------------------------------------------------------------
--
-- bbIfCnfSigILMI group
-- Port configurable signalling parameters, when the logical interface is
-- used as a UNI port
--
-- ------------------------------------------------------------------------

bbIfCnfSigILMIGrpTable    OBJECT-TYPE
    SYNTAX    SEQUENCE OF BbIfCnfSigILMIGrpEntry
    ACCESS    not-accessible
    STATUS    mandatory
    DESCRIPTION
        "The config table is for upto 32 logical port interfaces.
        "
    ::= { bbIfCnfSigILMIGrp 1 }

bbIfCnfSigILMIGrpEntry    OBJECT-TYPE
    SYNTAX    BbIfCnfSigILMIGrpEntry
    ACCESS    not-accessible
    STATUS    mandatory
    DESCRIPTION " 
        An entry for a boradband  interface used as a UNI port. 
        In MGX PXM card, a physical port can have a maximum of 32 logical
        interfaces. 
    "
    INDEX    { bbIfSigPortNum }
    ::= { bbIfCnfSigILMIGrpTable 1 }

BbIfCnfSigILMIGrpEntry ::=
    SEQUENCE {
        bbIfSigPortNum                   
            INTEGER,
        bbIfIlmiEnable
            INTEGER,
        bbIfSignallingProtocolType    
            INTEGER, 
        bbIfSignallingVpi                 
            INTEGER, 
        bbIfSignallingVci                 
            INTEGER, 
        bbIfAddrPrefix                    
            NetPrefix,
        bbIfCustomerId                    
            INTEGER,
        bbIfProtocolRevNo                 
            INTEGER,
        bbIfIlmiTrapEnable                
            INTEGER,
        bbIfMinTrapInterval               
            INTEGER,
        bbIfKeepAlivePollingEnable        
            INTEGER,
        bbIfErrorThresholdN491            
            INTEGER,
        bbIfEventThresholdN492            
            INTEGER,
        bbIfPollingIntervalT491           
            INTEGER,
        bbIfMinEnquiryIntervalT493          
            INTEGER,
        bbIfAddrRegEnable                   
            INTEGER
    }


bbIfSigPortNum OBJECT-TYPE
    SYNTAX    INTEGER (1..32)
    ACCESS    read-only
    STATUS    mandatory
    DESCRIPTION    "
        Refers to the logical interface index on the PXM card in MGX node. 
    "
    ::= { bbIfCnfSigILMIGrpEntry 1}

bbIfIlmiEnable OBJECT-TYPE
    SYNTAX  INTEGER {
        disable (1),
        enable  (2)
    }
    ACCESS read-write
    STATUS  mandatory
    DESCRIPTION "
        The logical interface is a generic entity, it can be used as either
        a virtual trunk, or user port with UNI support. 

        This variable is provided to enable/disable ILMI.

        ILMI should only be enabled on 'user ports' and not on 'virtual trunks'
            1 - disable
            2 - enable
    "
    DEFVAL { disable }
    ::= { bbIfCnfSigILMIGrpEntry 2}

bbIfSignallingProtocolType  OBJECT-TYPE
    SYNTAX    INTEGER {
        other(1),
        noSignalling(2),
        iLMI(3)
    }
    ACCESS read-write
    STATUS  mandatory
    DESCRIPTION "
        This will set the signalling protocol
         1 - other
         2 - noSignalling
         3 - ILMI
    "
    ::= { bbIfCnfSigILMIGrpEntry 3}

bbIfSignallingVpi   OBJECT-TYPE
    SYNTAX    INTEGER (0..4095 )
    ACCESS    read-write
    STATUS    mandatory
    DESCRIPTION "
        Indicates the VPI on which signalling cells arrive.
    "
    ::= { bbIfCnfSigILMIGrpEntry 4}

bbIfSignallingVci   OBJECT-TYPE
    SYNTAX    INTEGER (0..'ffff'h )
    ACCESS    read-write
    STATUS    mandatory
    DESCRIPTION "
        Indicates the VCI on which signalling cells arrive.
    "
    ::= { bbIfCnfSigILMIGrpEntry 5}

bbIfAddrPrefix    OBJECT-TYPE
    SYNTAX    NetPrefix   -- from ILMI MIB
    ACCESS    read-write
    STATUS    mandatory
    DESCRIPTION "
        Network Prefix for the ATM address
    "
    ::= { bbIfCnfSigILMIGrpEntry 6}

bbIfCustomerId    OBJECT-TYPE
    SYNTAX    INTEGER
    ACCESS    read-write
    STATUS    mandatory
    DESCRIPTION "
        For the INS as a read/write variable
    "
    ::= { bbIfCnfSigILMIGrpEntry 7}
                     
bbIfProtocolRevNo    OBJECT-TYPE
    SYNTAX    INTEGER
    ACCESS    read-write
    STATUS    mandatory
    DESCRIPTION "
        For the INS as a read/write variable.
    "
    ::= { bbIfCnfSigILMIGrpEntry 8}
                     

bbIfIlmiTrapEnable OBJECT-TYPE
    SYNTAX    INTEGER {
        disable (1),
        enable (2)
    } 
    ACCESS    read-write
    STATUS    mandatory
    DESCRIPTION "
        Enable/disable ILMI Trap sending
    "
    ::= { bbIfCnfSigILMIGrpEntry 9}
                     
bbIfMinTrapInterval    OBJECT-TYPE
    SYNTAX    INTEGER (1..10)
    ACCESS    read-write
    STATUS    mandatory
    DESCRIPTION "
        Number of seconds between traps.
    "
    ::= { bbIfCnfSigILMIGrpEntry 10}
                     
bbIfKeepAlivePollingEnable    OBJECT-TYPE
    SYNTAX    INTEGER {
        disable (1),
        enable (2)
    } 
    ACCESS    read-write
    STATUS    mandatory
    DESCRIPTION "
        Enable/disable Keep Alive Polling
    "
    ::= { bbIfCnfSigILMIGrpEntry 11}
                     
bbIfErrorThresholdN491    OBJECT-TYPE
    SYNTAX    INTEGER (1..10)
    ACCESS    read-write
    STATUS    mandatory
    DESCRIPTION "
        Error Threshold (N491) value
    "
    ::= { bbIfCnfSigILMIGrpEntry 12}
                     
bbIfEventThresholdN492    OBJECT-TYPE
    SYNTAX    INTEGER (1..10)
    ACCESS    read-write
    STATUS    mandatory
    DESCRIPTION "
        Event Threshold (N492) value
    "
    ::= { bbIfCnfSigILMIGrpEntry 13}
                     
bbIfPollingIntervalT491    OBJECT-TYPE
    SYNTAX    INTEGER {
        v1(5),
        v2(10),
        v3(15),
        v4(20),
        v5(25),
        v6(30),
        v7(35),
        v8(40),
        v9(45),
        v10(50),
        v11(55),
        v12(60)
        }
    ACCESS    read-write
    STATUS    mandatory
    DESCRIPTION "
        Polling Interval (T491) value
    "
    ::= { bbIfCnfSigILMIGrpEntry 14}
                     
bbIfMinEnquiryIntervalT493    OBJECT-TYPE
    SYNTAX    INTEGER (1..20)
    ACCESS    read-write
    STATUS    mandatory
    DESCRIPTION "
        Minimum Enquiry Interval (T493)
    "
    ::= { bbIfCnfSigILMIGrpEntry 15}
                     
bbIfAddrRegEnable OBJECT-TYPE
    SYNTAX  INTEGER {
        disable (1),
        enable (2)
    }
    ACCESS  read-write
    STATUS  mandatory
    DESCRIPTION "
        Enable/disable ILMI Address Registration
    "
    DEFVAL { disable }
    ::= { bbIfCnfSigILMIGrpEntry 16}
   

-- ------------------------------------------------------------------------
-- End of bbIfCnfSigILMIGrp 
-- ------------------------------------------------------------------------
 
 
-- atm              OBJECT IDENTIFIER ::= { basisServices 2 }
-- bbInterface      OBJECT IDENTIFIER ::= { atm 7 }
-- bbIfCnt          OBJECT IDENTIFIER ::= { bbInterface 4 }
bbIfCntGrp      OBJECT IDENTIFIER ::= { bbIfCnt 1}
 
-- --------------------------------------------------------------------
--
--
--      BROADBAND INTERFACE  COUNT Group
--
--
-- --------------------------------------------------------------------
 
 
bbIfCntGrpTable OBJECT-TYPE
    SYNTAX  SEQUENCE OF BbIfCntGrpEntry
    ACCESS  not-accessible
    STATUS  mandatory
    DESCRIPTION "
        The Broadband Interface Count table is for logical interface.
        There will an entry for each of the logical partition of the
        physical line.
    "
    ::= { bbIfCntGrp 1 }
 
bbIfCntGrpEntry OBJECT-TYPE
    SYNTAX  BbIfCntGrpEntry
    ACCESS  not-accessible
    STATUS  mandatory
    DESCRIPTION " 
		An entry for logical interface.
	"
    INDEX   { bbCntIfNum }
    ::= { bbIfCntGrpTable 1 }
 
BbIfCntGrpEntry ::=
    SEQUENCE {
		bbCntIfNum
			INTEGER,
		bbIfTotalCells
			Counter,

-- Ingress direction
		bbIfRcvValidOAMCells
			Counter,
		bbIfRcvRmCells
			Counter,
		bbIfRcvClp0Cells
			Counter,
		bbIfRcvClp1Cells
			Counter,
		bbIfRcvClp0DiscCells
			Counter,
		bbIfRcvClp1DiscCells
			Counter,

		bbIfXmtOAMCells
			Counter,
		bbIfXmtRmCells
			Counter,
		bbIfXmtClp0Cells
			Counter,
		bbIfXmtClp1Cells
			Counter,

		bbIfCntClrButton
		   INTEGER

	}


bbCntIfNum OBJECT-TYPE
	SYNTAX  INTEGER (1..32)
	ACCESS  read-only
	STATUS  mandatory
	DESCRIPTION "
		Refers to the logical interface index on the PXM card in MGX node. 
	"
	::= { bbIfCntGrpEntry 1}

bbIfTotalCells OBJECT-TYPE
	SYNTAX  Counter 
	ACCESS  read-only
	STATUS  mandatory
	DESCRIPTION "
		Total number of cells (VC plus Qbin) that belong to this Interface.
		This maps on to the virtual interface of QE.
	"
	::= { bbIfCntGrpEntry 2  }

bbIfRcvValidOAMCells OBJECT-TYPE
	SYNTAX  Counter
	ACCESS  read-only
	STATUS  mandatory
	DESCRIPTION "
		Total number of OAM cell received.
	"
	::= { bbIfCntGrpEntry 3 }

bbIfRcvRmCells OBJECT-TYPE
	SYNTAX  Counter
	ACCESS  read-only
	STATUS  mandatory
	DESCRIPTION "
		Total number of RM cells Received.
	"
	::= { bbIfCntGrpEntry 4 }

bbIfRcvClp0Cells OBJECT-TYPE
	SYNTAX  Counter
	ACCESS  read-only
	STATUS  mandatory
	DESCRIPTION "
		Total number of CLP-0 cells Received.
	"
	::= { bbIfCntGrpEntry 5 }
 
bbIfRcvClp1Cells OBJECT-TYPE
	SYNTAX  Counter
	ACCESS  read-only
	STATUS  mandatory
	DESCRIPTION "
		Total number of CLP-1 cells Received.
	"
	::= { bbIfCntGrpEntry 6 }
 
bbIfRcvClp0DiscCells OBJECT-TYPE
	SYNTAX  Counter
	ACCESS  read-only
	STATUS  mandatory
	DESCRIPTION "
		Total number of CLP-0 cells discarded at Ingress.
	"
	::= { bbIfCntGrpEntry 7 }

bbIfRcvClp1DiscCells OBJECT-TYPE
	SYNTAX  Counter
	ACCESS  read-only
	STATUS  mandatory
	DESCRIPTION "
		Total number of CLP-1 cells discarded at Ingress.
	"
	::= { bbIfCntGrpEntry 8 }

bbIfXmtOAMCells OBJECT-TYPE
	SYNTAX  Counter
	ACCESS  read-only
	STATUS  mandatory
	DESCRIPTION "
		Total number of OAM cells transmitted.
	"
	::= { bbIfCntGrpEntry 9 }
 
bbIfXmtRmCells OBJECT-TYPE
	SYNTAX  Counter
	ACCESS  read-only
	STATUS  mandatory
	DESCRIPTION "
		Total number of RM cells transmitted.
	"
	::= { bbIfCntGrpEntry 10 }
 
bbIfXmtClp0Cells  OBJECT-TYPE
	SYNTAX  Counter
	ACCESS  read-only
	STATUS  mandatory
	DESCRIPTION "
		Total number of CLP-0 cells transmitted.
	"
	::= { bbIfCntGrpEntry 11 }
 
bbIfXmtClp1Cells OBJECT-TYPE
	SYNTAX  Counter
	ACCESS  read-only
	STATUS  mandatory
	DESCRIPTION "
		Total number of CLP-1 cells transmitted.
	"
	::= { bbIfCntGrpEntry 12 }
 
bbIfCntClrButton OBJECT-TYPE
    SYNTAX  INTEGER {
		noAction (1),
		resetCounters (2)
	}
    ACCESS  read-write
    STATUS  mandatory
    DESCRIPTION "
		Writing a value of 2 resets all the counters
	"
    ::= { bbIfCntGrpEntry 13 }

 
-- --------------------------------------------------------------------
-- End of bbIfCntGrp
-- --------------------------------------------------------------------
 
 
 
-- atm                  OBJECT IDENTIFIER ::= { basisServices 2 }
-- bbInterface          OBJECT IDENTIFIER ::= { atm 7 }
-- bbIfCnt              OBJECT IDENTIFIER ::= { bbInterface 4 }
 
bbIfCntSigILMIGrp       OBJECT IDENTIFIER ::= { bbIfCnt 2}
 
-- ------------------------------------------------------------------------
--
-- bbIfCntSigILMI group
-- ILMI and signalling counts, when the logical interface is
-- used as a UNI port
--
-- ------------------------------------------------------------------------

bbIfCntSigILMIGrpTable OBJECT-TYPE
	SYNTAX  SEQUENCE OF BbIfCntSigILMIGrpEntry
	ACCESS  not-accessible
	STATUS  mandatory
	DESCRIPTION "
        The counter table is for upto 32 logical port interfaces.
	"
	::= { bbIfCntSigILMIGrp 1 }


bbIfCntSigILMIGrpEntry      OBJECT-TYPE
	SYNTAX  BbIfCntSigILMIGrpEntry
	ACCESS  not-accessible
	STATUS  mandatory
	DESCRIPTION " 
        An entry for a boradband  interface used as a UNI port.
        In MGX PXM card, a physical port can have a maximum of 32 logical
        interfaces.
	"
	INDEX  { sigCntBbIfNum }
    ::= { bbIfCntSigILMIGrpTable 1 }
 
BbIfCntSigILMIGrpEntry ::=
	SEQUENCE {
		sigCntBbIfNum 
			INTEGER,
        bbIfSnmpPduReceived
            Counter,
        bbIfGetRequestReceived
            Counter,
        bbIfGetNextRequestReceived
            Counter,
        bbIfSetRequestReceived
            Counter,
        bbIfTrapReceived
            Counter,
        bbIfGetResponseReceived
            Counter,
        bbIfGetResponseTransmitted
            Counter,
        bbIfGetRequestTransmitted
            Counter,
        bbIfTrapTransmitted
            Counter,
        bbIfInvalidPDUReceived
            Counter,
        bbIfAsn1ParseError
            Counter,
        bbIfNoSuchNameError
            Counter,
        bbIfTooBigError
            Counter,
-- Clear Button
        bbIfSigCntClrButton
            INTEGER
	}

sigCntBbIfNum OBJECT-TYPE
    SYNTAX  INTEGER (1..32)
    ACCESS  read-only
    STATUS  mandatory
    DESCRIPTION "
        Refers to the logical interface index on the PXM card in MGX node.
    "
    ::= { bbIfCntSigILMIGrpEntry 1}

bbIfSnmpPduReceived OBJECT-TYPE
	SYNTAX  Counter
	ACCESS  read-only
	STATUS  mandatory
	DESCRIPTION "
		The number of snmp packets received on this logical interface.
	"
	::= { bbIfCntSigILMIGrpEntry 2 }

bbIfGetRequestReceived  OBJECT-TYPE
	SYNTAX  Counter
	ACCESS  read-only
	STATUS  mandatory
	DESCRIPTION "
		The number of get request messages received
	"
	::= { bbIfCntSigILMIGrpEntry 3 }

bbIfGetNextRequestReceived  OBJECT-TYPE
	SYNTAX  Counter
	ACCESS  read-only
	STATUS  mandatory
	DESCRIPTION "
		The number of get-next messages received
	"
	::= { bbIfCntSigILMIGrpEntry 4 }

bbIfSetRequestReceived  OBJECT-TYPE
	SYNTAX  Counter
	ACCESS  read-only
	STATUS  mandatory
	DESCRIPTION "
		The number of set messages received
	"
	::= { bbIfCntSigILMIGrpEntry 5 }

bbIfTrapReceived  OBJECT-TYPE
	SYNTAX  Counter
	ACCESS  read-only
	STATUS  mandatory
	DESCRIPTION "
		The number of traps received
	"
	::= { bbIfCntSigILMIGrpEntry 6 }

bbIfGetResponseReceived OBJECT-TYPE
	SYNTAX  Counter
	ACCESS  read-only
	STATUS  mandatory
	DESCRIPTION "
		The number of Keep Alive response messages received
	"
	::= { bbIfCntSigILMIGrpEntry 7 }

bbIfGetResponseTransmitted  OBJECT-TYPE
	SYNTAX  Counter
	ACCESS  read-only
	STATUS  mandatory
	DESCRIPTION "
		The number of response messages transmitted
	"
	::= { bbIfCntSigILMIGrpEntry 8 }

bbIfGetRequestTransmitted   OBJECT-TYPE
	SYNTAX  Counter
	ACCESS  read-only
	STATUS  mandatory
	DESCRIPTION "
		The number of Keep Alive get request messages transmitted
	"
	::= { bbIfCntSigILMIGrpEntry 9 }

bbIfTrapTransmitted     OBJECT-TYPE
	SYNTAX  Counter
	ACCESS  read-only
	STATUS  mandatory
	DESCRIPTION "
		The number of trap messages transmitted
	"
	::= { bbIfCntSigILMIGrpEntry 10 }

bbIfInvalidPDUReceived  OBJECT-TYPE
	SYNTAX  Counter
	ACCESS  read-only
	STATUS  mandatory
	DESCRIPTION "
		The number of invalid PDUs received
	"
	::= { bbIfCntSigILMIGrpEntry 11 }

bbIfAsn1ParseError      OBJECT-TYPE
	SYNTAX  Counter
	ACCESS  read-only
	STATUS  mandatory
	DESCRIPTION "
		The number of parse errors on ASN.1
	"
	::= { bbIfCntSigILMIGrpEntry 12 }

bbIfNoSuchNameError     OBJECT-TYPE
	SYNTAX  Counter
	ACCESS  read-only
	STATUS  mandatory
	DESCRIPTION "
		The number of errors for name not present
	"
	::= { bbIfCntSigILMIGrpEntry 13 }

bbIfTooBigError     OBJECT-TYPE
	SYNTAX  Counter
	ACCESS  read-only
	STATUS  mandatory
	DESCRIPTION "
		The number of messages received with len > 484
	"
	::= { bbIfCntSigILMIGrpEntry 14 }

bbIfSigCntClrButton OBJECT-TYPE
    SYNTAX  INTEGER {
		noAction (1),
		resetCounters (2)
    }
    ACCESS  read-write
    STATUS  mandatory
    DESCRIPTION "
		Writing a value of 2 resets all the counters
	"
    ::= { bbIfCntSigILMIGrpEntry 15 }
 
 
-- --------------------------------------------------------------------
-- End of bbIfCntSigILMIGrp
-- --------------------------------------------------------------------

 
-- atm                  OBJECT IDENTIFIER ::= { basisServices 2 }
-- bbInterface          OBJECT IDENTIFIER ::= { atm 7 }
-- bbIfStateGrp         OBJECT IDENTIFIER ::= { bbInterface 3 }
 
-- --------------------------------------------------------------------
--
--
--      BROADBAND INTERFACE  STATE Group
--
--
-- --------------------------------------------------------------------
 
bbIfStateGrpTable   OBJECT-TYPE
	SYNTAX  SEQUENCE OF BbIfStateGrpEntry
	ACCESS  not-accessible
	STATUS  mandatory
	DESCRIPTION "
		The state table for the logical  interface
		there can be  32 entries for the PXM card in MGX.
	"
	::= { bbIfStateGrp 1 }
 
bbIfStateGrpEntry   OBJECT-TYPE
	SYNTAX  BbIfStateGrpEntry
	ACCESS  not-accessible
	STATUS  mandatory
	DESCRIPTION " 
		An entry for logical interface.  
		In MGX PXM card, a physical port can have a maximum of 32 logical
		interfaces. 
	"
	INDEX   { bbStateIfNum }
    ::= { bbIfStateGrpTable 1 }

BbIfStateGrpEntry ::=
	SEQUENCE {
		bbStateIfNum 
			INTEGER,
		bbIfState
			INTEGER,
		bbIfOversubscribed
			INTEGER,
		bbIfIngrPercentUtil
			INTEGER,
		bbIfEgrPercentUtil
			INTEGER
	}

bbStateIfNum        OBJECT-TYPE
	SYNTAX  INTEGER (1..32) 
	ACCESS  read-only
	STATUS  mandatory
	DESCRIPTION "
        This is logical interface number within a physical line num.
        In MGX PXM card, a physical port can have a maximum of 32 logical
        interfaces.
	"
	::= { bbIfStateGrpEntry 1}

bbIfState  OBJECT-TYPE
	SYNTAX  INTEGER {
		notConfigured (1),
		active (2),
		linefailure (4),
		signallingfailure (5),
		inactive (6),
		lineinloopback ( 7 )

	}
	ACCESS  read-only
	STATUS  mandatory
	DESCRIPTION "
		This variable indicates the status of the logical interface.

		The following are not supported for the logical interface.

--      remoteloopback (3),
--      outofcelldelineation (6),
--      localloopback (7)

	"
	::= { bbIfStateGrpEntry 2 }
 
bbIfOversubscribed  OBJECT-TYPE
	SYNTAX  INTEGER {
		false (1),
		true (2)
	}
	ACCESS  read-only
	STATUS  mandatory
	DESCRIPTION "
		This variable indicates the whether the logical interface is 
		over subscribed or not.
	"
	::= { bbIfStateGrpEntry 3 }

bbIfIngrPercentUtil OBJECT-TYPE
	SYNTAX  INTEGER (0..1000)  
	ACCESS  read-only 
	STATUS  mandatory  
	DESCRIPTION "
		Percentage Utilization of the interface in the Ingress direction.
	" 
	::= { bbIfStateGrpEntry  4 }


bbIfEgrPercentUtil OBJECT-TYPE
	SYNTAX  INTEGER (0..1000)  
	ACCESS  read-only 
	STATUS  mandatory  
	DESCRIPTION "
		Percentage Utilization of the interface in the Egress direction.
	" 
	::= { bbIfStateGrpEntry  5 }


-- ------------------------------------------------------------------
-- End of bbIfStateGrp
-- ------------------------------------------------------------------

 
-- atm              OBJECT IDENTIFIER ::= { basisServices 2 }
-- bbChan           OBJECT IDENTIFIER ::= { atm 7 }
-- bbChanCnfGrp     OBJECT IDENTIFIER ::= { bbChan     1 }
 


-- --------------------------------------------------------------------
--
--
--      BROADBAND CHANNEL  CONFIG Group
--
--
-- --------------------------------------------------------------------
 
 
bbChanCnfGrpTable OBJECT-TYPE
    SYNTAX  SEQUENCE OF BbChanCnfGrpEntry
    ACCESS  not-accessible
    STATUS  mandatory
    DESCRIPTION "
        The Broadband Channel config table is for a channel on logical 
        interface.  There will an entry for each of the channel added on the
        logical partition of the physical line.
    "
    ::= { bbChanCnfGrp 1 }
 
bbChanCnfGrpEntry OBJECT-TYPE
    SYNTAX  BbChanCnfGrpEntry
    ACCESS  not-accessible
    STATUS  mandatory
    DESCRIPTION " 
        The config table is for logical channel.
    "
    INDEX   { bbChanCnfNum }
    ::= { bbChanCnfGrpTable  1 }
 
BbChanCnfGrpEntry ::=
    SEQUENCE {

    bbChanCnfNum                   INTEGER,
    bbChanRowStatus                INTEGER,
    bbChanConnType                 INTEGER,
    bbChanServiceType              INTEGER,
    bbChanConnDesc                 DisplayString,
    bbChanSvcFlag                  INTEGER,
    bbChanSvcConnId                INTEGER,

-- 
-- connection endpoint parameters, 'e'
--
    bbChanIfNum                    INTEGER,
    bbChanVpi                      INTEGER,
    bbChanVci                      INTEGER,

--
-- These are needed if the connection is from a PXM user port
-- and policing is enabled. These apply to connection on PXM 
-- lines confiured as user port only.
--
-- PCR/CDVT is used for GCRA1 and
-- SCR/MBS is used for GCRA2

-- UpcEnable
--         UpcPCR
--         UpcCDVT
--
--         UpcSCRPolicing
--             for CBR conns.
--                 UpcPCR0
--                 UpcCDVT0
--             for non CBR conns.
--                 UpcSCR
--                 UpcMBS
--
-- Note that all these parameters are clp = 0+1 stream
--
    bbChanUpcEnable                INTEGER,
    bbChanUpcPCR                   INTEGER,
    bbChanUpcCDVT                  INTEGER,

    bbChanUpcSCR                   INTEGER,
    bbChanUpcMBS                   INTEGER,

    bbChanGcra1Action              INTEGER,
    bbChanGcra2Action              INTEGER,
    bbChanUpcSCRPolicing           INTEGER,
-- 
-- below defines the per-connection based threshold
-- 
    bbChanEfciThreshold            INTEGER,
    bbChanDiscardOption            INTEGER,
    bbChanFrmDiscardThreshold      INTEGER,
    bbChanClpHiThreshold           INTEGER,
    bbChanClpLoThreshold           INTEGER,
    bbChanCongstUpdateCode         INTEGER,
    bbChanMaxCellMemThreshold      INTEGER,


-- CAC parameters
    bbChanIngrPercentUtil          INTEGER,
    bbChanEgrPercentUtil           INTEGER,
    bbChanEgrSrvRate               INTEGER,
    bbChanOvrSubOvrRide            INTEGER,

--
-- connection parameters, 'x'
-- 
    bbChanLocalVpi                 INTEGER,
    bbChanLocalVci                 INTEGER,
    bbChanLocalNsapAddr            IfNsapAddress,

--
-- connection parameters, 'y'
-- 
    bbChanRemoteVpi                INTEGER,
    bbChanRemoteVci                INTEGER,
    bbChanRemoteNsapAddr           IfNsapAddress,

--
-- connection parameters, 'p'
-- 
    bbChanMaster                   INTEGER,
    bbChanRtePriority              INTEGER,
    bbChanMaxCost                  INTEGER,
    bbChanRestrictTrkType          INTEGER,

--
-- for testcon/testdelay 
--
    bbChanTestType                 INTEGER,
    bbChanTestState                INTEGER,
    bbChanTestResult               INTEGER,

-- Variable to support OAM Segment Loopback towards CPE
    bbChanTestTypeCPESide          INTEGER,
    bbChanTestStateCPESide         INTEGER,

-- Connection parameters, used by PXM

    bbConnVpcFlag                  INTEGER,
    bbConnServiceType              INTEGER,
    bbConnPCR                      INTEGER,
    bbConnSCR                      INTEGER,
    bbConnPercentUtil              INTEGER,
    bbRemoteConnPCR                INTEGER,
    bbRemoteConnSCR                INTEGER,
    bbRemoteConnPercentUtil        INTEGER,
    bbChanUpcMCR                   INTEGER
    }

bbChanCnfNum OBJECT-TYPE
    SYNTAX  INTEGER (16..4111)
    ACCESS  read-only
    STATUS  mandatory
    DESCRIPTION "
        This identifies a channel on the PXM logical interface, used as 
        PXM port.
    "
    ::= { bbChanCnfGrpEntry 1 }

bbChanRowStatus OBJECT-TYPE
    SYNTAX  INTEGER  {
        add(1),
        delete(2),
        modify(3)
    }
    ACCESS  read-write
    STATUS  mandatory
    DESCRIPTION "
        This will add, delete or modify the channel
        1 ==> ADD
        2 ==> DELETE
        3 ==> MODIFY
    "
    ::= { bbChanCnfGrpEntry 2 }

bbChanConnType OBJECT-TYPE
    SYNTAX  INTEGER  {
           vpc(1),
           vcc(2)
    }
    ACCESS  read-write
    STATUS  mandatory
    DESCRIPTION "
        This specifies the connection type
        1 ==> Virtual Path Connection
        2 ==> Virtual Channel Connection
    "
    ::= { bbChanCnfGrpEntry 3 }

bbChanServiceType OBJECT-TYPE
    SYNTAX  INTEGER  {
        cbr(1),
        vbr(2),
        abr(3),
        ubr(4),
        vbr-rt(5)
    }
    ACCESS  read-write
    STATUS  mandatory
    DESCRIPTION "
        This specifies the service type
        1 ==> Constant Bit Rate
        2 ==> Variable Bit Rate
        3 ==> Available Bit Rate
        4 ==> Unspecified Bit Rate
        5 ==> Variable Bit Rate - Real Time
    "
    ::= { bbChanCnfGrpEntry 4 }

bbChanConnDesc    OBJECT-TYPE
    SYNTAX  DisplayString (SIZE (0..20))
    ACCESS read-write
    STATUS  mandatory
    DESCRIPTION "
        A string that has been defined to give a
        descriptive name to the connection
    "
    ::= { bbChanCnfGrpEntry 5 }
 
bbChanSvcFlag     OBJECT-TYPE
    SYNTAX  INTEGER {
        svc  (1),
        pvc  (2),
        spvc (3)
    }
    ACCESS read-write
    STATUS  mandatory
    DESCRIPTION "
        This specifies the connection type
        1 ==> SVC connection
        2 ==> PVC connection, used by PAR
        3 ==> Soft PVC connection, used by PNNI
    "
    ::= { bbChanCnfGrpEntry 6 }

bbChanSvcConnId   OBJECT-TYPE
    SYNTAX  INTEGER
    ACCESS read-write
    STATUS  mandatory
    DESCRIPTION "
        This connection ID is for future use Currently not supported.
    "
    ::= { bbChanCnfGrpEntry 7 }

--
-- connection endpoint parameters, 'e'
--

bbChanIfNum OBJECT-TYPE
    SYNTAX  INTEGER (1..32)
    ACCESS  read-write
    STATUS  mandatory
    DESCRIPTION " 
        Channel's logical Interface from which traffic of the connection
        will be received.
    "
    ::= { bbChanCnfGrpEntry 8}

bbChanVpi OBJECT-TYPE
    SYNTAX  INTEGER (0..4095)
    ACCESS  read-write
    STATUS  mandatory
    DESCRIPTION "
        VPI for the connection.
    "
    ::= { bbChanCnfGrpEntry 9}

bbChanVci OBJECT-TYPE
    SYNTAX  INTEGER (0..'ffff'h)
    ACCESS  read-write
    STATUS  mandatory
    DESCRIPTION "
        VCI for the connection.
    "
    ::= { bbChanCnfGrpEntry 10}

--
-- UPC parameters
-- 

bbChanUpcEnable OBJECT-TYPE
    SYNTAX  INTEGER {
        disable (1),
        enable (2)
    }
    ACCESS read-write
    STATUS  mandatory
    DESCRIPTION "
        enables/disables UPC for Ingress cells
    "
    DEFVAL { enable }
    ::= { bbChanCnfGrpEntry 11}

bbChanUpcPCR OBJECT-TYPE
    SYNTAX  INTEGER (50..1412832)
    ACCESS read-write
    STATUS  mandatory
    DESCRIPTION "
         PCR(0+1), Peak Cell Rate, specifies an upper bound on
         rate at which traffic can be submitted on an ATM
         connection. This object applies to the First Leaky
         Bucket for leaving cells with Cell Loss Priority of 0 or 1.
         . Units: cells per second.
         . Applicable connection types:
           UBR, CBR, VBR, ABR
         . Default: 50
         . Ranges:
           T3  : 50-96000
           E3  : 50-80000
           OC3 : 50-353208
           OC12: 50-1412832

    "
    ::= { bbChanCnfGrpEntry 12}
 
bbChanUpcCDVT OBJECT-TYPE
    SYNTAX  INTEGER (1..5000000)     
    ACCESS read-write
    STATUS  mandatory
    DESCRIPTION "
        Compliant Cell Delay Variation. Also known as
        CDVT(0+1), Cell Delay Variation Tolerance, which
        specifies the maximum time period for accumulated
        violations of cell-arrival time parameters. This object
        applies to the First Leaky bucket for cells with Cell
        Loss Priority of 0 or 1.
            . Units: microseconds.
            . Applicable connection types:
               UBR, CBR, VBR, ABR
            . Default:
               CBR:    10000
               Others: 250000
    "
    ::= { bbChanCnfGrpEntry 13}

bbChanUpcSCR OBJECT-TYPE
    SYNTAX  INTEGER (1..1412832)
    ACCESS read-write
    STATUS  mandatory
    DESCRIPTION "
         SCR, Sustainable Cell Rate, is an upper bound on the
         conforming average rate of an ATM connection, over
         time scales which are long relative to those for which
         the PCR is defined. Enforcement of this bound by the UPC
         could allow the network to allocate sufficient resources,
         but less than thos based on the PCR, and still ensure
         that the performance objectives (e.g., Cell Loss Ratio)
         can be achieved.
         . Units: cell per second.
         . Applicable connection types:
           . VBR, ABR
         . Ranges:
             T3  :  50-96000
             E3  :  50-80000
             OC3 :  50-353208
             OC12:  50-1412832
         . Default: 50

    "
    ::= { bbChanCnfGrpEntry 14}

bbChanUpcMBS OBJECT-TYPE
    SYNTAX  INTEGER (1..5000000)
    ACCESS  read-write
    STATUS  mandatory
    DESCRIPTION "
        Maximum Burst Size (MBS). Also known as Compliant Burst Size (CBS).
            . Units: cells
            . Applicable connection types:
                . VBR, ABR
            . Default: 1000
            . Range  : 1-5000000
    "
    ::= { bbChanCnfGrpEntry 15}

 
bbChanGcra1Action OBJECT-TYPE
    SYNTAX  INTEGER {
        noAction(1),
        tagCells(2),
        tagAndDiscard(3),
        discardAllNonComformCells(4)
    }
    ACCESS  read-write
    STATUS  mandatory
    DESCRIPTION "
        GCRA1 Action.
        1 = No Action
        2 = Tag Untagged cells
        3 = Tag untagged cells and discard tagged cells
        4 = Discard all (0+1) non-comforming cells
    "
    DEFVAL { discardAllNonComformCells }
    ::= { bbChanCnfGrpEntry 16 }

bbChanGcra2Action OBJECT-TYPE
    SYNTAX  INTEGER {
        noAction(1),
        tagCells(2),
        tagAndDiscard(3),
        discardAllNonComformCells(4)
    }
    ACCESS  read-write
    STATUS  mandatory
    DESCRIPTION "
        GCRA2 Action.
        1 = No Action
        2 = Tag Untagged cells
        3 = Tag untagged cells and discard tagged cells
        4 = Discard all (0+1) non-comforming cells
    "
    DEFVAL { discardAllNonComformCells }
    ::= { bbChanCnfGrpEntry 17 }

bbChanUpcSCRPolicing OBJECT-TYPE
    SYNTAX  INTEGER {
        clp0 (1),
        clp0and1 (2),
        off (3)
    }
    ACCESS  read-write
    STATUS  mandatory
    DESCRIPTION "
        Selects SCR policing for CLP = 0 or all cells
    "
    ::= { bbChanCnfGrpEntry 18}

bbChanEfciThreshold OBJECT-TYPE
    SYNTAX  INTEGER (0..491520)
    ACCESS  read-write
    STATUS  mandatory
    DESCRIPTION "
        Threshold above which EFCI bit is to be set.
        Default Value  is 3/4 of max cell count.
    "
	DEFVAL { 196608 }
    ::= { bbChanCnfGrpEntry 19 }

bbChanDiscardOption OBJECT-TYPE
    SYNTAX  INTEGER {
        clpHysteresis(1),
        frameDiscard(2)
    }
    ACCESS  read-write
    STATUS  mandatory
    DESCRIPTION "
        Enable Frame Discard or CLP Hysteresis.
    "
    DEFVAL { clpHysteresis }
    ::= { bbChanCnfGrpEntry 20 }

bbChanFrmDiscardThreshold OBJECT-TYPE
    SYNTAX  INTEGER (0..491520)
    ACCESS  read-write
    STATUS  mandatory
    DESCRIPTION "
        Ingress Frame Discard Threshold.
        Valid only when Ingress Frame Discard option is selected.

        Default Value : TBD
    "
    ::= { bbChanCnfGrpEntry 21 }

bbChanClpHiThreshold OBJECT-TYPE
    SYNTAX  INTEGER (0..491520)
    ACCESS  read-write
    STATUS  mandatory
    DESCRIPTION "
        Ingress CLP High Threshold.

		Default is 3/4 of max cell count.
    "
	DEFVAL { 196608 }
    ::= { bbChanCnfGrpEntry 22 }

bbChanClpLoThreshold OBJECT-TYPE
    SYNTAX  INTEGER (0..491520)
    ACCESS  read-write
    STATUS  mandatory
    DESCRIPTION "
        Ingress CLP Low Threshold. Valid only when
        Ingress CLP Hysteresis option is selected.

        Default Value is 1/2 of max cell count.

    "
	DEFVAL { 131072 }
    ::= { bbChanCnfGrpEntry 23 }

bbChanCongstUpdateCode OBJECT-TYPE
    SYNTAX  INTEGER  {
        dontUpdate(1),
        setCiBit(2),
        setEfciBit(3),
        clearEfciBit(4)
    }
    ACCESS  read-write
    STATUS  mandatory
    DESCRIPTION "
        Ingress Channel Congestion Update Code.
        Default Value : TBD
    "
    ::= { bbChanCnfGrpEntry 24 }

bbChanMaxCellMemThreshold OBJECT-TYPE
    SYNTAX  INTEGER (0..512000)
    ACCESS  read-write
    STATUS  mandatory
    DESCRIPTION "
        Maximum number of cells of that connection in
        the memory.
		
		Assuming Total Cell Memory is 512K cells, this is defaulted to
		half of total size.

    "
	DEFVAL { 262144 }
    ::= { bbChanCnfGrpEntry 25 }


-- CAC parameters

bbChanIngrPercentUtil OBJECT-TYPE
    SYNTAX  INTEGER (0..100)
    ACCESS read-write
    STATUS  mandatory
    DESCRIPTION "
        Percentage Utilization of the IngrService Rate. This is used
        for connection admission control.
        Default Value : TBD
    "
    ::= { bbChanCnfGrpEntry 26}


bbChanEgrPercentUtil OBJECT-TYPE
    SYNTAX  INTEGER (0..100)
    ACCESS  read-write
    STATUS  mandatory
    DESCRIPTION "
        Percentage Utilization of the EgrService Rate.
        This is used for egress bandwidth calculation and 
        connection admission control.
        Default Value : TBD
    "
    ::= { bbChanCnfGrpEntry 27 }

bbChanEgrSrvRate OBJECT-TYPE
    SYNTAX  INTEGER (1..1412832)
    ACCESS read-write
    STATUS  mandatory
    DESCRIPTION "
        Egress service rate - This is used for egress bandwidth calculation
        and for connection admission control. The actual value
        depends on the speed of the logical interface
    "
    ::= { bbChanCnfGrpEntry 28 }

bbChanOvrSubOvrRide OBJECT-TYPE
    SYNTAX  INTEGER {
            disable (1),
            enable (2)
    }
    ACCESS read-write
    STATUS  mandatory
    DESCRIPTION "
        Channel Over Subscrive Override
        This MIB variable allows one to add a new connection on a port
        even if it is over subscribed.
    "
    DEFVAL { disable }
    ::= { bbChanCnfGrpEntry 29 }
 
--
-- connection parameters, 'x'
--

bbChanLocalVpi OBJECT-TYPE
    SYNTAX  INTEGER (0..4095)
    ACCESS  read-only
    STATUS  mandatory
    DESCRIPTION "
        The VPI value for this channel
    "
    ::= { bbChanCnfGrpEntry 30 }

bbChanLocalVci OBJECT-TYPE
    SYNTAX  INTEGER (0..'ffff'h)
    ACCESS  read-only
    STATUS  mandatory
    DESCRIPTION "
        The VCI value for this channel
    "
    ::= { bbChanCnfGrpEntry 31 }

bbChanLocalNsapAddr OBJECT-TYPE
    SYNTAX  IfNsapAddress
    ACCESS  read-write
    STATUS  mandatory
    DESCRIPTION " 
        The Near End NSAP Address  value for this channel.
    "
    ::= { bbChanCnfGrpEntry 32 }

--
-- connection parameters, 'y'
--
bbChanRemoteVpi OBJECT-TYPE
    SYNTAX  INTEGER (0..4095)
    ACCESS  read-write
    STATUS  mandatory
    DESCRIPTION "
        The VPI value for this channel
    "
    ::= { bbChanCnfGrpEntry 33 }

bbChanRemoteVci OBJECT-TYPE
    SYNTAX  INTEGER (0..'ffff'h)
    ACCESS  read-write
    STATUS  mandatory
    DESCRIPTION "
        The VCI value for this channel
    "
    ::= { bbChanCnfGrpEntry 34 }

bbChanRemoteNsapAddr OBJECT-TYPE
    SYNTAX  IfNsapAddress
    ACCESS  read-write
    STATUS  mandatory
    DESCRIPTION "
        The Far End NSAP Address  value for this channel.
    "
    ::= { bbChanCnfGrpEntry 35 }

--
-- connection parameters, 'p'
--

bbChanMaster OBJECT-TYPE
    SYNTAX  INTEGER {
        master (1),
        slave  (2),
        unknown (3)

    }
    ACCESS  read-write
    STATUS  mandatory
    DESCRIPTION "
        This is used by the PXM switch platform module, to determine if this
        endpoint ia master or slave.
    "
    ::= { bbChanCnfGrpEntry 36 }

bbChanRtePriority OBJECT-TYPE
    SYNTAX  INTEGER (1..15)
    ACCESS  read-write
    STATUS  mandatory
    DESCRIPTION "
        This is also known as class of service, it is used by 
        PXM to determine how important this connection is when
        selecting connections to route.
    "
    DEFVAL { 1 }
    ::= { bbChanCnfGrpEntry 37 }

bbChanMaxCost OBJECT-TYPE
    SYNTAX  INTEGER (1..65535)
    ACCESS  read-write
    STATUS  mandatory
    DESCRIPTION "
        Maximum allowed cost. It is related to Cost Based Routing.
        This is used by PXM so that it won't choose a path with a
        cost greater than this configured level.
    "
    DEFVAL { 255 }
    ::= { bbChanCnfGrpEntry 38 }

bbChanRestrictTrkType OBJECT-TYPE
    SYNTAX  INTEGER {
        noRestriction   (1),
        terrestrialTrunk (2),
        satelliteTrunk   (3)
    }
    ACCESS  read-write
    STATUS  mandatory
    DESCRIPTION "
        Restricted trunk type for routind, used by PXM. It
        specifies that the connection either cannot be routed over satellite
        trunks or terrestrial trunks, or it can be on any type of trunk.
    "
    DEFVAL { noRestriction }
    ::= { bbChanCnfGrpEntry 39 }

--
-- for testcon/testdelay
--
bbChanTestType OBJECT-TYPE
    SYNTAX  INTEGER {
        testcon(1),
        testdelay(2),
        notest(3)
    }
    ACCESS read-write
    STATUS  mandatory
    DESCRIPTION "

     The chanTestType starts testing the continuity or delay of a connection.
     It sends specific cell patterns toward the network and the terminating
     end of this connection has to be an AXIS or ASI of a BPX in order for
     this test to be working.
     The receiving node would loop back when it receives these
     cells. The test should be done in about couple of seconds. The testcon
     tests the continuity of the connection and testdelay uses the same
     test except that it measures for delay through the network.
     To test the delay follow this procedure:
        a- set chanTestType to testdelay
        b- read chanTestState till it is Pass or Fail
        c- Read chanTestResult for the delay if it is Pass

    *Note that the chanTestType would go back to notest when the
        test is completed
     To test the continuity follow this procedure:
        a- set chanTestType to testcon
        b- read chanTestState till it is Pass or Fail
        *Note that the chanTestType would go back to notest when the
         test is completed
     You CAN NOT select 2 tests back to back, you have selcelt one and wait
     the result and then start the other one.
     SYNTAX
     When you select testdelay

     This is the type of the test
     1 = Test Continuity
     2 = Test Delay
     3 = No Test

     tstconseg is performed on the port side, i.e, towards the CPE
    "
    DEFVAL { notest }
    ::= { bbChanCnfGrpEntry 40 }

bbChanTestState OBJECT-TYPE
    SYNTAX  INTEGER {
        passed(1),
        failed(2),
        inprogress(3),
        notinprogress(4)
    }
    ACCESS read-only
    STATUS  mandatory
    DESCRIPTION "
        This shows the state of the test
        When you add a connection then the chanTestState becomes notinprogress
        and when you select any test, it would go to inprogress state and after
        it completes the test, it will go to failed or passed state.
        1 = Passed
        2 = Failed
        3 = In Progress
        4 = Not In Progress
    "
    ::= { bbChanCnfGrpEntry 41 }

bbChanTestResult OBJECT-TYPE
    SYNTAX  INTEGER (1..65535)
    ACCESS read-only
    STATUS  mandatory
    DESCRIPTION "
        This is round trip delay in milliseconds.
        When you select testdelay option for the chanTestType, the result of
        the test that is measured in milliseconds can be read in chanTestResult.
    "
    ::= { bbChanCnfGrpEntry 42 }

-- CPE side OAM segment loopback
 
bbChanTestTypeCPESide     OBJECT-TYPE
    SYNTAX  INTEGER {
        testconseg(1),
        notest(2)
    }
    ACCESS read-write
    STATUS  mandatory
    DESCRIPTION "

        The default is notest.

        The chanTestType starts testing the segment continuity of a connection.
        It sends OAM Segment loopback cell towards port side (CPE)
        The CPE would loop back the cell
        To test the continuity follow this procedure:
        a- set chanTestTypeCPEside to testconseg
        b- read chanTestState till it is Pass or Fail

        *Note that the chanTestType would go back to notest when the
         test is completed

        SYNTAX
        When you select testdelay

         This is the type of the test
         1 = Test Continuity
         2 = No Test
    "
    DEFVAL { notest }
    ::= { bbChanCnfGrpEntry 43}

bbChanTestStateCPESide    OBJECT-TYPE
    SYNTAX  INTEGER {
        passed(1),
        failed(2),
        inprogress(3),
        notinprogress(4)
    }
    ACCESS read-only
    STATUS  mandatory
    DESCRIPTION "
        This shows the state of the test
        When you add a connection then the chanTestState becomes notinprogress
        and when you select any test, it would go to inprogress state and after
        it completes the test, it will go to failed or passed state.
        1 = Passed
        2 = Failed
        3 = In Progress
        4 = Not In Progress
    "
    ::= { bbChanCnfGrpEntry 44}


bbConnVpcFlag OBJECT-TYPE
    SYNTAX INTEGER {
        vpc (1),
        vcc (2)
    }
    ACCESS read-write
    STATUS mandatory
    DESCRIPTION " 
        This represents the connection type, used for PXM to
        identify VPC/VCC
    "
    ::= { bbChanCnfGrpEntry 45 }
 
bbConnServiceType OBJECT-TYPE
    SYNTAX INTEGER{
        cbr    (1),
        vbr    (2),
        ubr    (4),
        abrstd (6),
	vbrrt  (8)
    }
    ACCESS read-write
    STATUS mandatory
    DESCRIPTION "
        This specifies the service type
          1 ==> Constant Bit Rate
          2 ==> Variable Bit Rate
          4 ==> Unspecified Bit Rate
          6 ==> Available Bit Rate ( standard )
          8 ==> Variable Bit Rate - Real-Time

        Note that this is used by PXM card,
        Also to make it compatible with existing AUSM MIB definition,
        value 3 is not used.
        
        foresight ABR is not supported in PXM , i.e Virtual Service Module
    "
    ::= { bbChanCnfGrpEntry 46 }
 
bbConnPCR OBJECT-TYPE
    SYNTAX INTEGER
    ACCESS read-write
    STATUS mandatory
    DESCRIPTION " 
        Peak cell rate, could be derived from the end point parameter
    "
    ::= { bbChanCnfGrpEntry 47 }
 
bbConnSCR OBJECT-TYPE
    SYNTAX INTEGER
    ACCESS read-write
    STATUS mandatory
    DESCRIPTION " 
        Sustained cell rate, could be derived from the end point parameter
    "
    ::= { bbChanCnfGrpEntry 48 }
 
bbConnPercentUtil OBJECT-TYPE
    SYNTAX INTEGER ( 0..100 )
    ACCESS read-write
    STATUS mandatory
    DESCRIPTION "
        This is the expected long-term utilization of the
        channel by this end-point.
    "
	DEFVAL {100}
    ::= {bbChanCnfGrpEntry 49 }

bbRemoteConnPCR OBJECT-TYPE
    SYNTAX INTEGER
    ACCESS read-write
    STATUS mandatory
    DESCRIPTION " 
		Peak cell rate of the other end, if not set, will be
        set to the same as local end PCR (bbChanUpcPCR). However,
        note that if the PCRs for both local and remote end
        are set to the different value (i.e., asymmetric conn),
        then this should be set differently from local end PCR.
    "
    ::= { bbChanCnfGrpEntry 50 }
 
bbRemoteConnSCR OBJECT-TYPE
    SYNTAX INTEGER
    ACCESS read-write
    STATUS mandatory
    DESCRIPTION " 
		Sustained cell rate of the other end, if not set, will be
        set to the same as local end SCR (bbChanUpcSCR). However,
        note that if the PCRs for both local and remote end
        are set to the different value (i.e., asymmetric conn),
        then this should be set differently from local end SCR.
    "
    ::= { bbChanCnfGrpEntry 51 }
 
bbRemoteConnPercentUtil OBJECT-TYPE
    SYNTAX INTEGER ( 0..100 )
    ACCESS read-write
    STATUS mandatory
    DESCRIPTION "
		This is the expected long-term utilization of the
        channel by this end-point. If this is not specified in
        the connection setup request, it'll be defaulted to
        100 percent
    "
	DEFVAL {100}
    ::= {bbChanCnfGrpEntry 52 }

bbChanUpcMCR OBJECT-TYPE
    SYNTAX  INTEGER (1..1412832)
    ACCESS read-write
    STATUS  mandatory
    DESCRIPTION "
         SCR, Sustainable Cell Rate, is an upper bound on the
         conforming average rate of an ATM connection, over
         time scales which are long relative to those for which
         the PCR is defined. Enforcement of this bound by the UPC
         could allow the network to allocate sufficient resources,
         but less than thos based on the PCR, and still ensure
         that the performance objectives (e.g., Cell Loss Ratio)
         can be achieved.
         . Units: cell per second.
         . Applicable connection types:
           . ABR
         . Ranges:
             T3  :  50-96000
             E3  :  50-80000
             OC3 :  50-353208
             OC12:  50-1412832
         . Default: 50
 
    "
    ::= { bbChanCnfGrpEntry 53}
 
-- ---------------------------------------------------------------------

--
--  Next available channel
--
 
bbChanNumNextAvailable OBJECT-TYPE
    SYNTAX  INTEGER (16..4111)
    ACCESS  read-only
    STATUS  mandatory
    DESCRIPTION "
        This variable contains the next unused channel number of the possible
        4096 . This number can be used in channel config table.
        ChanNumNextAvailable gets updated whenever this number is used to
        create a new logical channel. Value 0 for this variable indicates that
        no more channels are available. 
    "
    ::= { bbChanCnfGrp 2 }
 
-- NextAvailable local  VPID

bbChanVpIdNextAvailable OBJECT-TYPE
    SYNTAX  INTEGER (1..4095)
    ACCESS  read-only
    STATUS  mandatory
    DESCRIPTION "

        This in only valid for a Service Module, will NOT be used in PXM.

        This variable contains the next unused local VPId of the possible
        1 to 4095. This number can be used in channel config table. It gets
        updated if the number is used to create a new vp connection. 

        The max. no. of VP conn.s is limited to the VPI range configured
        for this logical interface.
        Value of 0 for this variable indicates that no more vp connections 
        are available
    "
    ::= { bbChanCnfGrp 3 }
 

-- --------------------------------------------------------------------
-- End of bbChanCnfGrp
-- --------------------------------------------------------------------

 
-- atm              OBJECT IDENTIFIER ::= { basisServices 2 }
-- bbChan	        OBJECT IDENTIFIER ::= { atm 7 }
-- bbChanCntGrp     OBJECT IDENTIFIER ::= { bbChan	 3 }
 
-- --------------------------------------------------------------------
--
--
--      BROADBAND CHANNEL  COUNT Group
--
--
-- --------------------------------------------------------------------
 
 
bbChanCntGrpTable OBJECT-TYPE
    SYNTAX  SEQUENCE OF BbChanCntGrpEntry
    ACCESS  not-accessible
    STATUS  mandatory
    DESCRIPTION "
        The Broadband Channel count table is for a channel on virtual
        interface or a physical line.  There will an entry for each 
        of the channel added on the logical partition of the physical line.
    "
    ::= { bbChanCntGrp 1 }
 
bbChanCntGrpEntry OBJECT-TYPE
    SYNTAX  BbChanCntGrpEntry
    ACCESS  not-accessible
    STATUS  mandatory
    DESCRIPTION "
        The count table is for logical channel.
        The available number of channels on the broadband interface 
        on the PXM card is restricted to 4K.
 
        The PXM card has 2 Queue Engines ( QE0 and QE1).
    "
    INDEX   { bbChanCntNum }
    ::= { bbChanCntGrpTable  1 }
 
BbChanCntGrpEntry ::=
    SEQUENCE {
--
-- index. Mapping from this index to VI/VPI/VCI to 
-- glcn is required.
-- 
		bbChanCntNum 								INTEGER,

--
-- 4 ingress counts from RCMP
-- Also available from RCMP are PM counts and queue depth. These are 
-- not included here.
--
        bbChanRcvClp0Cells 							Counter,
        bbChanRcvClp1Cells 							Counter,
        bbChanNonConformCellsAtGcra1Policer         Counter,
        bbChanNonConformCellsAtGcra2Policer         Counter,

--
-- additional 4 ingress counts are from QE
--
        bbChanRcvEOFCells							Counter,
        bbChanDscdClp0Cells							Counter,
        bbChanDscdClp1Cells							Counter,
        bbChanRcvCellsSent							Counter,

--
-- 4 egress counts are from QE
--
--
		bbChanXmtClp0Cells                      Counter,
		bbChanXmtClp1Cells                       Counter,
        bbChanDscdClpZeroCellsToPort                Counter,
        bbChanDscdClpOneCellsToPort                 Counter,
        bbChanCntClrButton			                INTEGER

    }

bbChanCntNum OBJECT-TYPE
	SYNTAX  INTEGER (16..4111)
	ACCESS  read-only
	STATUS  mandatory
	DESCRIPTION "
		Channel  number. 
	"
	::= { bbChanCntGrpEntry 1 }

bbChanRcvClp0Cells OBJECT-TYPE
	SYNTAX  Counter
	ACCESS  read-only
	STATUS  mandatory
	DESCRIPTION "
		CLP_0 Cells Received From Port Count.
	"
	::= { bbChanCntGrpEntry 2 }

bbChanRcvClp1Cells OBJECT-TYPE
	SYNTAX  Counter
	ACCESS  read-only
	STATUS  mandatory
	DESCRIPTION "
		CLP_1 Cells Received From Port Count.
	"
	::= { bbChanCntGrpEntry 3 }

bbChanNonConformCellsAtGcra1Policer OBJECT-TYPE
	SYNTAX  Counter
	ACCESS  read-only
	STATUS  mandatory
	DESCRIPTION "
		Non-Conforming Cells Received at Ingress GCRA1 Policer Count.
	"
	::= { bbChanCntGrpEntry 4 }

bbChanNonConformCellsAtGcra2Policer OBJECT-TYPE
	SYNTAX  Counter
	ACCESS  read-only
	STATUS  mandatory
	DESCRIPTION "
		Non-Conforming Cells Received at Ingress GCRA2 Policer Count.
	"
	::= { bbChanCntGrpEntry 5 }

bbChanRcvEOFCells OBJECT-TYPE
	SYNTAX  Counter
	ACCESS  read-only
	STATUS  mandatory
	DESCRIPTION "
		Number of cells received from PXM port with EOF set.
	"
	::= { bbChanCntGrpEntry 6 }

bbChanDscdClp0Cells OBJECT-TYPE
	SYNTAX  Counter
	ACCESS  read-only
	STATUS  mandatory
    DESCRIPTION "
		Number of discarded clp = 0 cells received from PXM port.  
	"
	::= { bbChanCntGrpEntry 7 }

bbChanDscdClp1Cells OBJECT-TYPE
	SYNTAX  Counter
	ACCESS  read-only
	STATUS  mandatory
	DESCRIPTION "
		Number of discarded clp = 1 cells received from PXM port.  
	"
	::= { bbChanCntGrpEntry 8 }

bbChanRcvCellsSent OBJECT-TYPE
	 SYNTAX  Counter
	 ACCESS  read-only
	 STATUS  mandatory
	 DESCRIPTION "
		Number of cells received from port and  sent out of the Queue Engine. 
	 "
	::= { bbChanCntGrpEntry 9 }

bbChanXmtClp0Cells OBJECT-TYPE
	SYNTAX  Counter
	ACCESS  read-only
	STATUS  mandatory
	DESCRIPTION "
		Number of cells with EFCI clear transmitted to PXM port.
	"
	::= { bbChanCntGrpEntry 10 }

bbChanXmtClp1Cells OBJECT-TYPE
	SYNTAX  Counter
	ACCESS  read-only
	STATUS  mandatory
	DESCRIPTION "
		Number of cells with EFCI set transmitted to PXM port.
	"
	::= { bbChanCntGrpEntry 11 }

bbChanDscdClpZeroCellsToPort OBJECT-TYPE
	SYNTAX  Counter
	ACCESS  read-only
	STATUS  mandatory
	DESCRIPTION "
		Number of discard CLP = 0 cells before transmitted to PXM port.
	"
	::= { bbChanCntGrpEntry 12 }

bbChanDscdClpOneCellsToPort OBJECT-TYPE
	SYNTAX  Counter
	ACCESS  read-only
	STATUS  mandatory
	DESCRIPTION "
		Number of discard CLP = 1 cells before transmitted to PXM port.
	"
	::= { bbChanCntGrpEntry 13 }

bbChanCntClrButton OBJECT-TYPE
    SYNTAX  INTEGER {
        noAction (1),
        resetCounters (2)
    }
    ACCESS  read-write
    STATUS  mandatory
    DESCRIPTION "
        Writing a value of 2 resets all the counters
    "
	::= { bbChanCntGrpEntry 14 }


-- --------------------------------------------------------------------
-- End of bbChanCntGrp
-- --------------------------------------------------------------------

 
-- atm              OBJECT IDENTIFIER ::= { basisServices 2 }
-- bbChan	        OBJECT IDENTIFIER ::= { atm 7 }
-- bbChanStateGrp   OBJECT IDENTIFIER ::= { bbChan	 2 }
 
-- --------------------------------------------------------------------
--
--
--      BROADBAND CHANNEL  State Group
--
--
-- --------------------------------------------------------------------
 
 
bbChanStateGrpTable OBJECT-TYPE
    SYNTAX  SEQUENCE OF BbChanStateGrpEntry
    ACCESS  not-accessible
    STATUS  mandatory
    DESCRIPTION "
        The Broadband Channel state table is for a channel on logical
        interface.  There will an entry for each of the channel added on the
        logical partition of the physical line.
    "
    ::= { bbChanStateGrp 1 }
 
bbChanStateGrpEntry OBJECT-TYPE
    SYNTAX  BbChanStateGrpEntry
    ACCESS  not-accessible
    STATUS  mandatory
    DESCRIPTION "
        The state table is for logical channel.
        The available number of channels on the broadband interface (user ports)
        on the PXM card is restricted to 4K.
 
        The PXM card has 2 Queue Engines ( QE0 and QE1).
        Current calculations allow 31954 GLCNs on QE0, and 31748 GLCNs on QE1.
    "
    INDEX   { bbChanStateNum }
    ::= { bbChanStateGrpTable  1 }
 
BbChanStateGrpEntry ::=
    SEQUENCE {
        bbChanStateNum
            INTEGER,

		bbChanState
			INTEGER,
        bbChanEgrXmtState
            INTEGER,
        bbChanIngrRcvState
            INTEGER
	}


bbChanStateNum OBJECT-TYPE
    SYNTAX  INTEGER (16..4111)
    ACCESS  read-only
    STATUS  mandatory
    DESCRIPTION "
		Refers to the logical channel number
	"
    ::= { bbChanStateGrpEntry 1}

bbChanState OBJECT-TYPE
    SYNTAX  INTEGER {
        notconfigured (1),
        normal(2),
        alarm(3)
    }
    ACCESS  read-only
    STATUS  mandatory
    DESCRIPTION "
		This variable indicates the state of the VC (channel).
	"
    ::= { bbChanStateGrpEntry 2}
 
bbChanEgrXmtState OBJECT-TYPE
    SYNTAX INTEGER {
        other(1),
        normal(2),
        sendingAis (3),
        sendingFerf (4)
	}
    ACCESS read-only
    STATUS mandatory
    DESCRIPTION "
		Indicates the status of port transmit(Egress)
	"
    ::= { bbChanStateGrpEntry 3}
 
bbChanIngrRcvState OBJECT-TYPE
    SYNTAX INTEGER {
        other(1),
        normal(2),
        receivingAis (3),
        receivingFerf (4),
        alarm(5)
	}
    ACCESS read-only
    STATUS mandatory
    DESCRIPTION "
		indicates the status of port receive(Ingress)
	"
    ::= { bbChanStateGrpEntry 4}
 
 
-- ------------------------------------------------------------------------
-- End of bbChanStateGrp group definitions
-- ------------------------------------------------------------------------
 



-- virtualInterface       OBJECT IDENTIFIER ::= { atm 8 }


virtualInterfaceCnf       OBJECT IDENTIFIER ::= { virtualInterface 1 }

-- ---------------------------------------------------------------------
--
-- Port Virtual Interface Group
--
-- ---------------------------------------------------------------------

vrtlIntrConfigTable OBJECT-TYPE
	  SYNTAX  SEQUENCE OF VrtlIntrConfigEntry
	  ACCESS  not-accessible
	  STATUS  mandatory
	  DESCRIPTION
		 " Virtual Interface Configuration Table
		 "
	   ::= { virtualInterfaceCnf 1 }

vrtlIntrConfigEntry OBJECT-TYPE
	  SYNTAX VrtlIntrConfigEntry
	  ACCESS  not-accessible
	  STATUS  mandatory
	  DESCRIPTION
		 "An entry in the Virtual Interface configuration Table
		 "
	   INDEX {configVrtlIntrNum}
	   ::= { vrtlIntrConfigTable 1 }
		 
VrtlIntrConfigEntry ::=
	  SEQUENCE {
		   configVrtlIntrNum	        INTEGER,
		   vrtlIntrPortNum              INTEGER,
		   vrtlIntrState              	INTEGER,
		   vrtlIntrMaxQueMem            INTEGER,
		   vrtlIntrMinCellRate          INTEGER,
		   vrtlIntrMaxCellRate          INTEGER,
		   vrtlIntrCurrConfigPaths		INTEGER
	  } 
		 

configVrtlIntrNum OBJECT-TYPE
	  SYNTAX  INTEGER (1..32)
	  ACCESS  read-only
	  STATUS  mandatory
	  DESCRIPTION
		 " Virtual Interface Number. There are totaly
		   32 Virtual Interfaces on the card (egress).
		 "
	  ::= { vrtlIntrConfigEntry 1 }
		 
vrtlIntrPortNum OBJECT-TYPE
	  SYNTAX  INTEGER (0..4)
	  ACCESS  read-write
	  STATUS  mandatory   
	  DESCRIPTION
		 " Port number which will be connected to the
		   Virtual Interface. Value zero meens that this
		   virtual interface is not connected to any port.
		 "
	  ::= { vrtlIntrConfigEntry 2 }

vrtlIntrState OBJECT-TYPE
	SYNTAX  INTEGER {
		down(1),
		up(2)
	}
	ACCESS  read-write
	STATUS  mandatory  
	DESCRIPTION "
		Virtual Interface State.
	"
	::= { vrtlIntrConfigEntry 3 }

vrtlIntrMaxQueMem OBJECT-TYPE 
	SYNTAX  INTEGER (1..8)
	ACCESS  read-write
	STATUS  mandatory    
	DESCRIPTION " 
		Virtual Interface's Max queue memory.
		1 = 4Kcells
		2 = 8Kcells
		3 = 16Kcells
		4 = 32Kcells
		5 = 64Kcells
		6 = 128Kcells
		7 = 256Kcells
		8 = 512Kcells
	"
	::= { vrtlIntrConfigEntry 4 }

vrtlIntrMinCellRate OBJECT-TYPE 
	SYNTAX  INTEGER (103384..353208)
	ACCESS  read-write
	STATUS  mandatory    
	DESCRIPTION "
		Virtual Interface's minimum cell rate.
		The default value: 
		for OC12 port is 1412832 cells/sec 
		for OC3  port is  353208 cells/sec 
		for T3   port is   96000 cells/sec
		for E3   port is   80000 cells/sec
	"
	::= { vrtlIntrConfigEntry 5 }

vrtlIntrMaxCellRate OBJECT-TYPE  
	SYNTAX  INTEGER (103384..353208)
	ACCESS  read-write 
	STATUS  mandatory     
	DESCRIPTION " 
		Virtual Interface's maximum cell rate.
		The default value:
		for OC12 port is 1412832 cells/sec 
		for OC3  port is  353208 cells/sec 
		for T3   port is   96000 cells/sec
		for E3   port is   80000 cells/sec
	" 
	::= { vrtlIntrConfigEntry 6 } 


vrtlIntrCurrConfigPaths OBJECT-TYPE
	SYNTAX  INTEGER 
	ACCESS  read-only
	STATUS  mandatory     
	DESCRIPTION " 
		This is not a configurable parameter.

		This gives the count of paths currently configured on this VI.
	" 
	::= { vrtlIntrConfigEntry 7 } 


-- --------------------------------------------------------------
-- End of port_virtual_int_cnfg
-- --------------------------------------------------------------



-- virtualInterface        OBJECT IDENTIFIER ::= { atm 8 }

virtualInterfaceCnt        OBJECT IDENTIFIER ::= { virtualInterface 2 }

-- --------------------------------------------------------------------
--
-- Port Virtual Interface Counters Group
--
-- --------------------------------------------------------------------


vrtlIntrCounterTable OBJECT-TYPE
	  SYNTAX  SEQUENCE OF VrtlIntrCounterEntry
	  ACCESS  not-accessible
	  STATUS  mandatory
	  DESCRIPTION
		 "Virtual Interface Counters Table.
		 "
	   ::= { virtualInterfaceCnt 1 }

vrtlIntrCounterEntry OBJECT-TYPE
	  SYNTAX VrtlIntrCounterEntry
	  ACCESS  not-accessible
	  STATUS  mandatory
	  DESCRIPTION
		 "An entry in the Virtual Interface Counter Table.
		 "
	   INDEX {countVrtlIntrNum}
	   ::= { vrtlIntrCounterTable 1 }

VrtlIntrCounterEntry ::=
	  SEQUENCE {
		   countVrtlIntrNum                         INTEGER,
		   vrtlIntrTotalCellCnt                     Counter,
		   vrtlIntrTotalQbinCellCnt                 Counter,
		   vrtlIntrRxdValidOAMCellCnt               Counter,
		   vrtlIntrRxdRmCellCnt                     Counter,
		   vrtlIntrRxdClpUntaggedCellCnt            Counter,
		   vrtlIntrRxdClpTaggedCellCnt              Counter,
		   vrtlIntrRxdClpUntaggedDiscardedCellCnt   Counter,
		   vrtlIntrRxdClpTaggedDiscardedCellCnt     Counter,
		   vrtlIntrXmtdOAMCellCnt                   Counter,
		   vrtlIntrXmtdRmCellCnt                    Counter,
		   vrtlIntrXmtdClpUntaggedCellCnt           Counter,
		   vrtlIntrXmtdClpTaggedCellCnt             Counter
	  }  


countVrtlIntrNum OBJECT-TYPE
	SYNTAX  INTEGER (1..32)
	ACCESS  read-only
	STATUS  mandatory
	DESCRIPTION "
		Virtual Interface Number.
	"
	::= { vrtlIntrCounterEntry 1 }

vrtlIntrTotalCellCnt OBJECT-TYPE
	SYNTAX  Counter
	ACCESS  read-only
	STATUS  mandatory
	DESCRIPTION " 
		Total number of cells (VC plus Qbin) that belong to 
		this Virtual Interface. 
	"
	::= { vrtlIntrCounterEntry 2 }
		 
vrtlIntrTotalQbinCellCnt OBJECT-TYPE
	SYNTAX  Counter
	ACCESS  read-only
	STATUS  mandatory   
	DESCRIPTION " 
		Total number of cells in the Qbin belonging 
		to this Virtual Interface.
	"
	::= { vrtlIntrCounterEntry 3 }

vrtlIntrRxdValidOAMCellCnt OBJECT-TYPE
	  SYNTAX  Counter
	  ACCESS  read-only
	  STATUS  mandatory
	  DESCRIPTION
		 "Total number of OAM cell received.
		 "
	  ::= { vrtlIntrCounterEntry 4 }
		 
vrtlIntrRxdRmCellCnt OBJECT-TYPE
	  SYNTAX  Counter
	  ACCESS  read-only
	  STATUS  mandatory
	  DESCRIPTION
		 "Total number of RM cells Received.
		 "
	  ::= { vrtlIntrCounterEntry 5 }
		 
vrtlIntrRxdClpUntaggedCellCnt OBJECT-TYPE
	  SYNTAX  Counter
	  ACCESS  read-only
	  STATUS  mandatory
	  DESCRIPTION
		 "Total number of CLP-0 cells Received.
		 "
	  ::= { vrtlIntrCounterEntry 6 }

vrtlIntrRxdClpTaggedCellCnt OBJECT-TYPE
	  SYNTAX  Counter
	  ACCESS  read-only
	  STATUS  mandatory
	  DESCRIPTION
		 "Total number of CLP-1 cells Received.
		 "
	  ::= { vrtlIntrCounterEntry 7 }
		 
vrtlIntrRxdClpUntaggedDiscardedCellCnt OBJECT-TYPE
	  SYNTAX  Counter
	  ACCESS  read-only
	  STATUS  mandatory
	  DESCRIPTION
		 "Total number of CLP-0 cells discarded at Ingress.
		 "
	  ::= { vrtlIntrCounterEntry 8 }
		 
vrtlIntrRxdClpTaggedDiscardedCellCnt OBJECT-TYPE
	  SYNTAX  Counter
	  ACCESS  read-only
	  STATUS  mandatory
	  DESCRIPTION
		 "Total number of CLP-1 cells discarded at Ingress.
		 "
	  ::= { vrtlIntrCounterEntry 9 }
		 
vrtlIntrXmtdOAMCellCnt OBJECT-TYPE
	  SYNTAX  Counter
	  ACCESS  read-only
	  STATUS  mandatory
	  DESCRIPTION
		 "Total number of OAM cells transmitted.
		 "
	  ::= { vrtlIntrCounterEntry 10 }
		 
vrtlIntrXmtdRmCellCnt OBJECT-TYPE
	  SYNTAX  Counter
	  ACCESS  read-only
	  STATUS  mandatory
	  DESCRIPTION
		 "Total number of RM cells transmitted.
		 "
	  ::= { vrtlIntrCounterEntry 11 }
		 
vrtlIntrXmtdClpUntaggedCellCnt OBJECT-TYPE
	  SYNTAX  Counter
	  ACCESS  read-only
	  STATUS  mandatory
	  DESCRIPTION
		 "Total number of CLP-0 cells transmitted.
		 "
	  ::= { vrtlIntrCounterEntry 12 }
		 
vrtlIntrXmtdClpTaggedCellCnt OBJECT-TYPE
	  SYNTAX  Counter
	  ACCESS  read-only
	  STATUS  mandatory
	  DESCRIPTION
		 "Total number of CLP-1 cells transmitted.
		 "
	  ::= { vrtlIntrCounterEntry 13 }
		 




-- virtualInterface     OBJECT IDENTIFIER ::= { atm 8 }

virtualInterfaceQbinCnf        OBJECT IDENTIFIER ::= { virtualInterface 3 }

-- --------------------------------------------------------------------
--
-- Port Virtual Interface Qbin Configuration Group
--
-- --------------------------------------------------------------------

vrtlIntrQbinConfigTable OBJECT-TYPE
	  SYNTAX  SEQUENCE OF VrtlIntrQbinConfigEntry
	  ACCESS  not-accessible
	  STATUS  mandatory
	  DESCRIPTION
		 "Virtual Interface QBin Configuration Table.
		 "
	   ::= { virtualInterfaceQbinCnf 1 }

vrtlIntrQbinConfigEntry OBJECT-TYPE
	  SYNTAX VrtlIntrQbinConfigEntry
	  ACCESS  not-accessible
	  STATUS  mandatory
	  DESCRIPTION
		 "An entry in the Virtual Interface Qbin Config Table.
		 "
	   INDEX {queConfigVrtlIntrNum, queConfigVrtlIntrQbinNum}
	   ::= { vrtlIntrQbinConfigTable 1 }

VrtlIntrQbinConfigEntry ::=
	  SEQUENCE {
		   queConfigVrtlIntrNum             		INTEGER,
		   queConfigVrtlIntrQbinNum  	      		INTEGER,
		   vrtlIntrQbinState            			INTEGER,
		   vrtlIntrQbinPri              			INTEGER,
		   vrtlIntrQbinRate             			INTEGER,
		   vrtlIntrQbinDiscardSelection 			INTEGER,
		   vrtlIntrQbinMaxThreshold 				INTEGER,
		   vrtlIntrQbinClpHiThreshold 				INTEGER,
		   vrtlIntrQbinClpLoThreshold 				INTEGER,
		   vrtlIntrQbinFrameDiscardThreshold 		INTEGER,
		   vrtlIntrQbinEfciThreshold     			INTEGER
	  }  


queConfigVrtlIntrNum OBJECT-TYPE
	  SYNTAX  INTEGER (1..32)
	  ACCESS  read-only
	  STATUS  mandatory
	  DESCRIPTION
		 " Virtual Interface Number.
		 "
	  ::= { vrtlIntrQbinConfigEntry 1 }

queConfigVrtlIntrQbinNum OBJECT-TYPE 
	  SYNTAX  INTEGER (1..16) 
	  ACCESS  read-only
	  STATUS  mandatory  
	  DESCRIPTION
		 " Virtual Interface Qbin Number. There are totaly 16  Qbin
		   per Virtual Interface.
		 "
	  ::= { vrtlIntrQbinConfigEntry 2 }

vrtlIntrQbinState OBJECT-TYPE 
	  SYNTAX  INTEGER {
	  down(1),
	  up(2)
	  }
	  ACCESS  read-write
	  STATUS  mandatory  
	  DESCRIPTION
		 " Virtual Interface QBIN state. 
		 "
	  ::= { vrtlIntrQbinConfigEntry 3 }

vrtlIntrQbinPri OBJECT-TYPE  
	  SYNTAX  INTEGER (1..16)
	  ACCESS  read-write
	  STATUS  mandatory    
	  DESCRIPTION 
		 " This indicates the priority of the QBIN service 
		   within the Virtual Interface.
		 "
	  ::= { vrtlIntrQbinConfigEntry 4 }

vrtlIntrQbinRate OBJECT-TYPE  
	  SYNTAX  INTEGER (0..353208)
	  ACCESS  read-write 
	  STATUS  mandatory     
	  DESCRIPTION  
		 " The rate at which cells in the QBIN are serviced.
		   Max Cell rate for OC3 interface is 353208 cell/sec.
		 " 
	  ::= { vrtlIntrQbinConfigEntry 5 } 

vrtlIntrQbinDiscardSelection OBJECT-TYPE  
	  SYNTAX  INTEGER {
		  clpHysteresis(1),
		  frameDiscard(3) 
	  } 
	  ACCESS  read-write
	  STATUS  mandatory    
	  DESCRIPTION 
		 " Virtual Interface QBin Congestion control option.
		 "
	  DEFVAL { clpHysteresis }
	  ::= { vrtlIntrQbinConfigEntry 6 }

vrtlIntrQbinMaxThreshold OBJECT-TYPE   
	  SYNTAX  INTEGER (0..512000)
	  ACCESS  read-write    
	  STATUS  mandatory      
	  DESCRIPTION   
		 "Max cells that can be queued in the QBIN.
		  The Get value will be different from the Set 
		  value because of FW internal round up.
		 "  
	  ::= { vrtlIntrQbinConfigEntry 7 }  

vrtlIntrQbinClpHiThreshold OBJECT-TYPE
	  SYNTAX  INTEGER (0..512000)
	  ACCESS  read-write
	  STATUS  mandatory
	  DESCRIPTION
		 "The threshold above which the tagged cells 
		  will be dropped.
		  The Get value will be different from the Set 
		  value because of FW internal round up.
		 "
	  ::= { vrtlIntrQbinConfigEntry 8 }

vrtlIntrQbinClpLoThreshold OBJECT-TYPE
	  SYNTAX  INTEGER (0..512000) 
	  ACCESS  read-write   
	  STATUS  mandatory    
	  DESCRIPTION 
		 "Valid only if congestion control is set to 
		  CLP hysterises. The threshold upto which the 
		  dropping of the tagged cells should continue once 
		  it has crossed CLP HI threshold.
		  The Get value will be different from the Set 
		  value because of FW internal round up.
		 " 
	  ::= { vrtlIntrQbinConfigEntry 9 } 

vrtlIntrQbinFrameDiscardThreshold OBJECT-TYPE 
	  SYNTAX  INTEGER (0..512000)  
	  ACCESS  read-write    
	  STATUS  mandatory       
	  DESCRIPTION  
		 "Valid only if congestion control is set to 
		  Frame Discard. It is the threshold after which 
		  the QE will start discarding the entire frame 
		  if one or more cells of the frame is discarded..
		  The Get value will be different from the Set 
		  value because of FW internal round up.
		 "  
	  ::= { vrtlIntrQbinConfigEntry 10 } 

vrtlIntrQbinEfciThreshold OBJECT-TYPE
	  SYNTAX  INTEGER (0..512000) 
	  ACCESS  read-write   
	  STATUS  mandatory    
	  DESCRIPTION 
		 "The threshold above which the EFCI bits of 
		  the cell is set.
		  The Get value will be different from the Set 
		  value because of FW internal round up.
		 " 
	  ::= { vrtlIntrQbinConfigEntry 11 } 




-- virtualInterface          OBJECT IDENTIFIER ::= { atm 8 }

virtualInterfaceQbinCnt      OBJECT IDENTIFIER ::= { virtualInterface 4 }

-- --------------------------------------------------------------------
--
-- Port Virtual Interface Qbin Counters Group
--
-- --------------------------------------------------------------------

vrtlIntrQbinCounterTable OBJECT-TYPE
	  SYNTAX  SEQUENCE OF VrtlIntrQbinCounterEntry
	  ACCESS  not-accessible
	  STATUS  mandatory
	  DESCRIPTION
		 "Virtual Interface QBin Counter Table.
		 "
	   ::= { virtualInterfaceQbinCnt 1 }

vrtlIntrQbinCounterEntry OBJECT-TYPE
	  SYNTAX VrtlIntrQbinCounterEntry
	  ACCESS  not-accessible
	  STATUS  mandatory
	  DESCRIPTION
		 "An entry in the Virtual Interface Qbin Counter Table.
		 "
	   INDEX {queConuterVrtlIntrNum, queCounterVrtlIntrQbinNum}
	   ::= { vrtlIntrQbinCounterTable 1 }

VrtlIntrQbinCounterEntry ::=
	  SEQUENCE {
		   queConuterVrtlIntrNum                      INTEGER,
		   queCounterVrtlIntrQbinNum                  INTEGER,
		   vrtlIntrQbinCurrentCellCnt             Counter,
		   vrtlIntrQbinRxdCellCnt                 Counter,
		   vrtlIntrQbinTxdCellCnt                 Counter,
		   vrtlIntrQbinDiscardedCellCnt           Counter
	  }


queConuterVrtlIntrNum OBJECT-TYPE
	  SYNTAX  INTEGER (1..32)
	  ACCESS  read-only
	  STATUS  mandatory
	  DESCRIPTION
		 " Virtual Interface Number.
		 "
	  ::= { vrtlIntrQbinCounterEntry 1 }

queCounterVrtlIntrQbinNum OBJECT-TYPE
	  SYNTAX  INTEGER (1..16)
	  ACCESS  read-only
	  STATUS  mandatory
	  DESCRIPTION
		 " Virtual Interface Qbin Number. There are totaly 16  Qbin
		   per Virtual Interface.
		 "
	  ::= { vrtlIntrQbinCounterEntry 2 }

vrtlIntrQbinCurrentCellCnt OBJECT-TYPE 
	  SYNTAX  Counter
	  ACCESS  read-only
	  STATUS  mandatory    
	  DESCRIPTION 
		 " Total number of cells currently in the Qbin.
		 " 
	  ::= { vrtlIntrQbinCounterEntry 3 } 

vrtlIntrQbinRxdCellCnt OBJECT-TYPE  
	  SYNTAX  Counter
	  ACCESS  read-only
	  STATUS  mandatory    
	  DESCRIPTION 
		 " Total number of cells arrived to the QBIN.
		 "  
	  ::= { vrtlIntrQbinCounterEntry 4 }  

vrtlIntrQbinTxdCellCnt OBJECT-TYPE  
	  SYNTAX  Counter
	  ACCESS  read-only 
	  STATUS  mandatory     
	  DESCRIPTION  
		 " Total number of cells departured from QBIN.
		 "   
	  ::= { vrtlIntrQbinCounterEntry 5 }   

vrtlIntrQbinDiscardedCellCnt OBJECT-TYPE   
	SYNTAX  Counter
	ACCESS  read-only  
	STATUS  mandatory      
	DESCRIPTION   
		" Total number of arrivals to QBIN which were discarded.
		"    
	::= { vrtlIntrQbinCounterEntry 6 }    


------------------------------------------------------------
--
-- RPM CHAN TABLE
--
------------------------------------------------------------




-- rpmChan		OBJECT IDENTIFIER ::= { atm 10 }
-- rpmChanGrp	OBJECT IDENTIFIER ::= { rpmChan 1 }



rpmChanGrpTable OBJECT-TYPE
    SYNTAX  SEQUENCE OF RpmChanGrpEntry
    ACCESS  not-accessible
    STATUS  mandatory
    DESCRIPTION
	"
		The RPM channel table. 
	" 
	::= { rpmChanGrp 1 }

rpmChanGrpEntry OBJECT-TYPE
    SYNTAX  RpmChanGrpEntry
    ACCESS  not-accessible
    STATUS  mandatory
    DESCRIPTION 
	"
		An entry for logical channel.
    "
    INDEX   { rpmChanSlotNum, rpmChanNum }
    ::= { rpmChanGrpTable 1 }

RpmChanGrpEntry ::=
	SEQUENCE {
	
	rpmChanSlotNum					INTEGER,
	rpmChanInterface				INTEGER,
	rpmChanNum						INTEGER,
	rpmChanRowStatus				INTEGER,
	rpmChanVcd						INTEGER,
	rpmChanVpi						INTEGER,
	rpmChanVci						INTEGER,

	rpmChanSubInterface				INTEGER,
	rpmChanLocalVpi					INTEGER,
	rpmChanLocalVci					INTEGER,
	rpmChanLocalNsap				RpmNsapAddress,
	
	rpmChanRemoteVpi				INTEGER,
	rpmChanRemoteVci				INTEGER,
	rpmChanRemoteNsap				RpmNsapAddress,

	rpmChanType  					INTEGER,
	rpmChanConnType					INTEGER,
	rpmChanServiceType				INTEGER,

	rpmChanMastership				INTEGER,
	rpmChanRtePriority				INTEGER,
	rpmChanMaxCost					INTEGER,
	rpmChanRestrictTrkType			INTEGER,

	rpmChanPCR						INTEGER,
	rpmChanRemotePCR				INTEGER,
	rpmChanMCR						INTEGER,
	rpmChanRemoteMCR				INTEGER,
	rpmChanPercentUtil				INTEGER,
	rpmChanRemotePercentUtil		INTEGER,
	
	rpmChanMidLow					INTEGER,
	rpmChanMidHigh					INTEGER,
	rpmChanBurstSize				INTEGER,
	rpmChanEncapType				INTEGER,
	rpmChanInArpFreq				INTEGER,
	rpmChanOAMloopback				INTEGER,
	rpmChanState					INTEGER,
	rpmChanVirtualTemplate				INTEGER,
	rpmChanAbrRDF					INTEGER,
	rpmChanAbrRIF					INTEGER
	}

rpmChanSlotNum	OBJECT-TYPE
	SYNTAX 	INTEGER  (1..30)
	ACCESS	read-only
	STATUS  mandatory
	DESCRIPTION
	"
		Specifies the slot number of the RPM card.
	"
	::= { rpmChanGrpEntry 1 }

rpmChanInterface OBJECT-TYPE
	SYNTAX 	INTEGER
	ACCESS	read-only
	STATUS  mandatory
	DESCRIPTION
	"
        This is the RPM's backplane interface.
        Currently there is only one interface.
	"
	::= { rpmChanGrpEntry 2 }

rpmChanNum OBJECT-TYPE
	SYNTAX 	INTEGER (16..4095)
	ACCESS	read-only
	STATUS  mandatory
	DESCRIPTION
	"
		This is the LCN. A unique number which identifies a
		connection. LCN maps VPI and VCI.
		For VCC, VCI range is 1..3825, and LCN range is 16..3840. 
		LCN = VCI + 16.
		For VPC, VPI range is 1..255 and LCN range is 3841..4095. 
		LCN = VPI + 3840.
	"
	::= { rpmChanGrpEntry 3 }

rpmChanRowStatus  OBJECT-TYPE
    SYNTAX  INTEGER {
        add(1),
        del(2),
        mod(3)
        }
    ACCESS read-only
    STATUS  mandatory
    DESCRIPTION
	"
		This indicates the status of this channel.
		1 ==> ADD
		2 ==> DELETE
		3 ==> MODIFY
	"
	::= { rpmChanGrpEntry 4 }

rpmChanVcd OBJECT-TYPE
	SYNTAX 	INTEGER (0..4095)
	ACCESS	read-only
	STATUS  mandatory
	DESCRIPTION
	"
		Virtual Circuit Descriptor. A unique number which identifies a
		connection.
	"
	::= { rpmChanGrpEntry 5 }

rpmChanVpi OBJECT-TYPE
	SYNTAX 	INTEGER (0..255)
	ACCESS	read-only
	STATUS  mandatory
	DESCRIPTION
	"
		The VPI value for this channel.
		For VPC, VPI range is 1..255 and LCN range is 3841..4095. 
		LCN = VPI + 3840
	"
	::= { rpmChanGrpEntry 6 }

rpmChanVci OBJECT-TYPE
	SYNTAX 	INTEGER (0..65535)
	ACCESS	read-only
	STATUS  mandatory
	DESCRIPTION
	"
		The VCI value for this channel.
		For VCC, VCI range is 1..3825, and LCN range is 16..3840. 
		LCN = VCI + 16.
	"
	::= { rpmChanGrpEntry 7 }

rpmChanSubInterface OBJECT-TYPE
	SYNTAX 	INTEGER  
	ACCESS	read-only
	STATUS  mandatory
	DESCRIPTION
	"
		This is the RPM's backplane sub-interface.
		(SNMP doent support index value 0)
		sub-interface starts from 1. The sub-interface 
		0 in CLI will be 1 here. So sub-interface
		is incremented by 1. 
	"
	::= { rpmChanGrpEntry 8 }

rpmChanLocalVpi OBJECT-TYPE
	SYNTAX 	INTEGER (0..255)
	ACCESS	read-only
	STATUS  mandatory
	DESCRIPTION
	"
		This VPI together with the local VCI and NSAP represents the
		local end point in this connection. The VPI value is zero if it
		is a VCC conn. type.
	"
	::= { rpmChanGrpEntry 9 }

rpmChanLocalVci OBJECT-TYPE
	SYNTAX 	INTEGER (0..65535)
	ACCESS	read-only
	STATUS  mandatory
	DESCRIPTION
	"
		This VCI together with the local VPI and NSAP represents the
		local end point in this connection.
	"
	::= { rpmChanGrpEntry 10 }
	
rpmChanLocalNsap OBJECT-TYPE
	SYNTAX 	RpmNsapAddress
	ACCESS	read-only
	STATUS  mandatory
	DESCRIPTION
	"
	 The Near End NSAP Address  value for this channel.
	 This NSAP is 20 bytes binary, among these 20 bytes: 13 bytes
	 as node name, 2 bytes for Cisco ID, 1 byte rsvd, 3 bytes for
	 logical interface: slot (1 byte) and port number (2 bytes),
	 the last byte is for SEL

	 Of the 13 bytes for the node name, only the first 8 bytes are
         used. If the node name is n (0 < n < 8) bytes long, the node
         name must be left justified ( Bytes 1 to n contain the node name
         and bytes (n+1) to 8 must be 0 ). Bytes 9-13 must be always 0.
	"
	::= { rpmChanGrpEntry 11 }

rpmChanRemoteVpi OBJECT-TYPE
	SYNTAX 	INTEGER (0..255)
	ACCESS	read-only
	STATUS  mandatory
	DESCRIPTION
	"
		This VPI together with the remote VCI and NSAP represents the
		remote end point in this connection.
	"
	::= { rpmChanGrpEntry 12 }

rpmChanRemoteVci OBJECT-TYPE
	SYNTAX 	INTEGER (0..65535)
	ACCESS	read-only
	STATUS  mandatory
	DESCRIPTION
	"
		This VCI together with the remote VPI and NSAP represents the
		remote end point in this connection.
	"
	::= { rpmChanGrpEntry 13 }

rpmChanRemoteNsap OBJECT-TYPE
	SYNTAX 	RpmNsapAddress
	ACCESS	read-only
	STATUS  mandatory
	DESCRIPTION
	"
		The Far End NSAP Address  value for this channel.
		This NSAP is 20 bytes binary, among these 20 bytes: 13 bytes
		as prefix, 2 bytes for Cisco ID, 1 byte rsvd, 3 bytes for
		logical interface: slot (1 byte) and port number (2 bytes),
		the last byte is for SEL
	"
	::= { rpmChanGrpEntry 14 }

rpmChanType OBJECT-TYPE
	SYNTAX 	INTEGER {
           svc(1),
           pvc(2),
           spvc(3)
    }
	ACCESS	read-only
	STATUS  mandatory
	DESCRIPTION
	"
		This specifies the connection type
		1 ==> SVC
		2 ==> PVC
		3 ==> Soft PVC
		Currently only PVC is supported.
	"
	::= { rpmChanGrpEntry 15 }

rpmChanConnType OBJECT-TYPE
	SYNTAX 	INTEGER {
           vpc(1),
           vcc(2)
    }
	ACCESS	read-only
	STATUS  mandatory
	DESCRIPTION
	"
		This specifies the connection type
		1 ==> Virtual Path Connection
		2 ==> Virtual Channel Connection
	"
	::= { rpmChanGrpEntry 16 }

rpmChanServiceType OBJECT-TYPE
	SYNTAX 	INTEGER {
        cbr(1),
        vbr(2),
        ubr(4),
		atfr(5),
		abrstd(6),
		abrfst(7)
    }
	ACCESS	read-only
	STATUS  mandatory
	DESCRIPTION
	"
		This specifies the service type
		1 ==> Constant Bit Rate
		2 ==> Variable Bit Rate
		4 ==> Unspecified Bit Rate
		5 ==> ATM frame relay
		6 ==> standard ABR
		7 ==> foresight ABR
		Only VBR,standard ABR and UBR are supported in phase I.
	"
	::= { rpmChanGrpEntry 17 }

rpmChanMastership OBJECT-TYPE
	SYNTAX 	INTEGER {
        master (1),
        slave  (2),
		unknown (3)
    }
	ACCESS	read-only
	STATUS  mandatory
	DESCRIPTION
	"
		This specifies which end of the connection is the master.
		This is used by PXM to determine if this end point is
		master or slave. Only in AXIS shelf, 'unknown' is always used.
		For consistency it was added here.
	"
	::= { rpmChanGrpEntry 18 }

rpmChanRtePriority OBJECT-TYPE
	SYNTAX 	INTEGER (1..15)
	ACCESS	read-only
	STATUS  mandatory
	DESCRIPTION
	"
		This is also known as class of service, it is used by
		PXM to determine how important this connection is when
		selecting connections to route.
	"
	::= { rpmChanGrpEntry 19 }

rpmChanMaxCost OBJECT-TYPE
	SYNTAX 	INTEGER (1..65535)
	ACCESS	read-only
	STATUS  mandatory
	DESCRIPTION
	"
		Maximum allowed cost. It is related to Cost Based Routing.
		This is used by PXM so that it won't choose a path with a
		cost greater than this configured level.
	"
	::= { rpmChanGrpEntry 20 }

rpmChanRestrictTrkType OBJECT-TYPE
	SYNTAX 	INTEGER {
        noRestriction   (1),
        terrestrialTrunk (2),
        satelliteTrunk   (3)
    }
	ACCESS	read-only
	STATUS  mandatory
	DESCRIPTION
	"
		Restricted trunk type for routing, used by PXM. It
		specifies that the connection either cannot be routed over satellite
		trunks or terrestrial trunks, or it can be on any type of trunk.
	"
	::= { rpmChanGrpEntry 21 }

rpmChanPCR OBJECT-TYPE
	SYNTAX 	INTEGER  (0..353208)
	ACCESS	read-only
	STATUS  mandatory
	DESCRIPTION
	"
		Peak cell rate.(in cells per sec.)
	"
	::= { rpmChanGrpEntry 22 }

rpmChanRemotePCR OBJECT-TYPE
	SYNTAX 	INTEGER (0..353208)
	ACCESS	read-only
	STATUS  mandatory
	DESCRIPTION
	"
		Peak cell rate of the other end, if not set, will be
		set to the same as local end PCR.
	"
	::= { rpmChanGrpEntry 23 }

rpmChanMCR OBJECT-TYPE
	SYNTAX 	INTEGER  (0..353208)
	ACCESS	read-only
	STATUS  mandatory
	DESCRIPTION
	"
		Minimum cell rate.(in cells per sec.)
	"
	::= { rpmChanGrpEntry 24 }

rpmChanRemoteMCR OBJECT-TYPE
	SYNTAX 	INTEGER (0..353208)
	ACCESS	read-only
	STATUS  mandatory
	DESCRIPTION
	"
		Minimum cell rate of the other end, if not set, will be
		set to the same as local end MCR.
	"
	::= { rpmChanGrpEntry 25 }

rpmChanPercentUtil OBJECT-TYPE
	SYNTAX 	INTEGER ( 0..100 )
	ACCESS	read-only
	STATUS  mandatory
	DESCRIPTION
	"
		This is the expected long-term utilization of the
    	channel by this end-point.
	"
	::= { rpmChanGrpEntry 26 }

rpmChanRemotePercentUtil OBJECT-TYPE
	SYNTAX 	INTEGER ( 0..100 )
	ACCESS	read-only
	STATUS  mandatory
	DESCRIPTION
	"
		This is the expected long-term utilization of the
		channel by the other end-point. If this is not specified in
		the connection setup request, it'll be set to be the same
		as the local end.
	"
	::= { rpmChanGrpEntry 27 }


rpmChanEncapType OBJECT-TYPE
	SYNTAX 	INTEGER {
		aal5snap(1),
		aal34smds(2),
		aal5nlpid(3),
		qsaal(4),
		ilmi(5),
		aal5muxXNS(6),
		aal5muxIP(7),
		aal5muxVINES(8),
		aal5muxDECNET(9),
		aal5muxNOVELL1(10),
		ppp(11),
		unknown(12)
	} 
	ACCESS	read-only
	STATUS  mandatory
	DESCRIPTION
	"
		ATM adaptation layer (AAL) and Encapsulation type.
		aal5snap - LLC/SNAP precedes the protocol datagram.
		aal34smds - Encapsulation for SMDS network.
		aal5nlpid - Encapsulation that allows ATM interfaces  to
		            interoperate with HSSI.
		qsaal - signaling type PVC used  for setting up or 
		        tearing down SVCs.
		ilmi - used to set up communication with ILMI.
		aal5mux[protocol] - a MUX-type Virtual circuit.
		ppp - PPP over ATM.
		The Encapsulation types aal34smds, qsaal and ilmi 
        are not supported.
	"
	::= { rpmChanGrpEntry 28 }

rpmChanMidLow OBJECT-TYPE
	SYNTAX 	INTEGER (0..1023)
	ACCESS	read-only
	STATUS  mandatory
	DESCRIPTION
	"
		Starting Message Identifier Number for this PVC.
	"
	::= { rpmChanGrpEntry 29 }

rpmChanMidHigh OBJECT-TYPE
	SYNTAX 	INTEGER (0..1023)
	ACCESS	read-only
	STATUS  mandatory
	DESCRIPTION
	"
		Ending Message Identifier Number for this PVC.
	"
	::= { rpmChanGrpEntry 30 }

rpmChanBurstSize OBJECT-TYPE
	SYNTAX 	INTEGER (0..65535)
	ACCESS	read-only
	STATUS  mandatory
	DESCRIPTION
	"
		The Maximum number of ATM cells the virtual circuit can 
		transmit.
	"
	::= { rpmChanGrpEntry 31 }

rpmChanInArpFreq OBJECT-TYPE
	SYNTAX 	INTEGER (0..60)
	ACCESS	read-only
	STATUS  mandatory
	DESCRIPTION
	"
		Specifies how often (in minutes) Inverse ARP datagrams 
		will be sent on this virtual circuit.
	"
	::= { rpmChanGrpEntry 32 }

rpmChanOAMloopback OBJECT-TYPE
	SYNTAX 	INTEGER (0..600) 
	ACCESS	read-only
	STATUS  mandatory
	DESCRIPTION
	"
		Specifies how often (in seconds) to generate an OAM F5 
		loopback cell from this virtual circuit.
	"
	::= { rpmChanGrpEntry 33 }

rpmChanState  OBJECT-TYPE
    SYNTAX  INTEGER {
        notConfigured(1),
        active(2),
        failed(3)
        }
    ACCESS read-only
    STATUS  mandatory
    DESCRIPTION
	"
		This indicates the status of this channel.
		1 ==> notConfigured
		2 ==> active
		3 ==> failed.
		Currently 'failed' state is not supported.
		When the channel is not added, the state is 
		notConfigured.
	"
	::= { rpmChanGrpEntry 34 }

rpmChanVirtualTemplate OBJECT-TYPE
	SYNTAX  INTEGER
	ACCESS read-only
	STATUS  mandatory
	DESCRIPTION
	"
		Specifies the Virtual Template used for CISCO PPP.
		If it is not using Virtual Template then this value
		is 0. 
	"
	::= { rpmChanGrpEntry 35 }

rpmChanAbrRDF	OBJECT-TYPE
	SYNTAX  INTEGER 
	ACCESS read-only
	STATUS  mandatory
	DESCRIPTION
	"This is valid only for ABR Service Type.
	 Rate Decrease Factor: Controls the rate decrease which occurs
	 when backward RM-cells with CI=1 are received. Larger values
	 lead to faster rate decrease.
	 Reference - ATM Forum Traffic Management Specification
	 Version 4.0 Section 5.10.2"
	::= { rpmChanGrpEntry 36 }

rpmChanAbrRIF	OBJECT-TYPE
	SYNTAX  INTEGER 
	ACCESS read-only
	STATUS  mandatory
	DESCRIPTION
	"This is valid only for ABR Service Type.
	 Rate Increase Factor: Controls the rate increase which occurs
	 when a backward RM-cell is received with CI=0 and NI=0. Larger 
	 values lead to faster rate increase.
	 Reference - ATM Forum Traffic Management Specification
	 Version 4.0 Section 5.10.2"
	::= { rpmChanGrpEntry 37 }

------------------------------------------------------------
--
-- RPM CHAN TABLE END
--
------------------------------------------------------------
------------------------------------------------------------
--
-- RPM PORT TABLE
--
------------------------------------------------------------



-- rpmInterface OBJECT IDENTIFIER ::= { atm 9 }
-- rpmPort		 OBJECT IDENTIFIER ::= { rpmInterface 1 }


rpmPortTable OBJECT-TYPE
    SYNTAX  SEQUENCE OF RpmPortEntry
    ACCESS  not-accessible
    STATUS  mandatory
    DESCRIPTION
	" 
		List of RPM backplane sub-interfaces.
	"
    ::= { rpmPort 1 }

rpmPortEntry OBJECT-TYPE
    SYNTAX  RpmPortEntry 
    ACCESS  not-accessible
    STATUS  mandatory
    DESCRIPTION
	" 
		An entry for the RPM backplane sub interface.
		Each entry contains RPM's backplane sub interface number,
		its IP address and ATM address.
	"
    INDEX   { rpmPortSlotNum, rpmPortSubInterface}
    ::= { rpmPortTable 1 }

RpmPortEntry ::=
	SEQUENCE {
		rpmPortSlotNum
			INTEGER,
		rpmPortInterface
			INTEGER,
		rpmPortSubInterface
			INTEGER,
		rpmPortRowStatus
			INTEGER,
		rpmPortIpAddress
			IpAddress,
		rpmPortSubNetMask
			IpAddress,
		rpmPortState
			INTEGER
	}

rpmPortSlotNum	OBJECT-TYPE
	SYNTAX 	INTEGER  (1..30)
	ACCESS	read-only
	STATUS  mandatory
	DESCRIPTION
	"
		Specifies the slot number of the RPM card.
	"
	::= { rpmPortEntry 1 }

rpmPortInterface	OBJECT-TYPE
    SYNTAX  INTEGER 
    ACCESS  read-only
    STATUS  mandatory
    DESCRIPTION
	" 
        This is the RPM's backplane interface.
        Currently there is only one interface.
	"
    ::= { rpmPortEntry 2 }

rpmPortSubInterface	OBJECT-TYPE
    SYNTAX  INTEGER 
    ACCESS  read-only
    STATUS  mandatory
    DESCRIPTION
	" 
		It identifies a sub-interface.
		(SNMP doent support index value 0)
		sub-interface starts from 1. The sub-interface 
		0 in CLI will be 1 here. So sub-interface
		is incremented by 1. 
	"
    ::= { rpmPortEntry 3 }

rpmPortRowStatus  OBJECT-TYPE
    SYNTAX  INTEGER {
        add(1),
        del(2),
        mod(3)
        }
    ACCESS read-only
    STATUS  mandatory
    DESCRIPTION
	"
		This indicates the status of this sub-interface.
		1 ==> ADD
		2 ==> DELETE
		3 ==> MODIFY
	"
	::= { rpmPortEntry 4 }


rpmPortIpAddress	OBJECT-TYPE
	SYNTAX	IpAddress
	ACCESS	read-only 
	STATUS  mandatory
	DESCRIPTION
	" 
		IP address of the sub-interface.
	"
    ::= { rpmPortEntry 5 }

rpmPortSubNetMask	OBJECT-TYPE
	SYNTAX 	IpAddress 
	ACCESS  read-only
	STATUS  mandatory
	DESCRIPTION
	" 
		SUB-NETMASK of the sub-interface.
	"
    ::= { rpmPortEntry 6 }

rpmPortState  OBJECT-TYPE
    SYNTAX  INTEGER {
        notConfigured(1),
        active(2),
        failed(3)
        }
    ACCESS read-only
    STATUS  mandatory
    DESCRIPTION
	"
		This indicates the state of this sub-interface.
		1 ==> notConfigured
		2 ==> active
		3 ==> failed.
		Currently 'failed' state is not supported.
	"
	::= { rpmPortEntry 7 }


------------------------------------------------------------
--
-- END RPM PORT TABLE
--
------------------------------------------------------------
------------------------------------------------------------
--
-- RPM PORT RESOURCE PARTITION TABLE
--
------------------------------------------------------------

 
rpmIfCnfResPart  OBJECT IDENTIFIER ::= { rpmInterface 2 }

rpmIfCnfRscPartTable  OBJECT-TYPE
    SYNTAX  SEQUENCE OF RpmIfCnfRscPartEntry
    ACCESS  not-accessible
    STATUS  mandatory
    DESCRIPTION "
        The table is for RPM interface resource partition.
    "
    ::= { rpmIfCnfResPart 1 }

rpmIfCnfRscPartEntry  OBJECT-TYPE
    SYNTAX  RpmIfCnfRscPartEntry
    ACCESS  not-accessible
    STATUS  mandatory
    DESCRIPTION " 
        An entry for a logical interface
    "
    INDEX   { rpmIfRscSlotNum, rpmIfRscPartIfNum, rpmIfRscPartCtrlrNum }
    ::= { rpmIfCnfRscPartTable 1 }
 
RpmIfCnfRscPartEntry ::=
    SEQUENCE {
		rpmIfRscSlotNum
			INTEGER,
        rpmIfRscPartIfNum
            INTEGER,
        rpmIfRscPartCtrlrNum
            INTEGER,

        rpmIfRscPrtRowStatus
            INTEGER,

        rpmIfRscPrtIngrPctBandwidth
            INTEGER,
        rpmIfRscPrtEgrPctBandwidth
            INTEGER,

        rpmIfRscPrtVpiLow
            INTEGER,
        rpmIfRscPrtVpiHigh
            INTEGER,
        rpmIfRscPrtVciLow
            INTEGER,
        rpmIfRscPrtVciHigh
            INTEGER,
        rpmIfRscPrtMaxChans
            INTEGER
    }
 
rpmIfRscSlotNum OBJECT-TYPE
    SYNTAX  INTEGER  (1..30)
    ACCESS  read-only
    STATUS  mandatory
    DESCRIPTION "
        Specifies the slot number of the RPM card.
    "
    ::= { rpmIfCnfRscPartEntry 1}
 
rpmIfRscPartIfNum OBJECT-TYPE
    SYNTAX  INTEGER 
    ACCESS  read-only
    STATUS  mandatory
    DESCRIPTION "
        This is backplane interface number.
        Currently there is only one interface.
    "
    ::= { rpmIfCnfRscPartEntry 2}

rpmIfRscPartCtrlrNum OBJECT-TYPE
	SYNTAX  INTEGER {
		par (1),
		pnni (2),
		tag (3)
	}
    ACCESS  read-only
    STATUS  mandatory
    DESCRIPTION "
        This is index for controller using the  interface .

        1 - PAR
        2 - PNNI
        3 - TAG
    "
    ::= { rpmIfCnfRscPartEntry 3}

rpmIfRscPrtRowStatus OBJECT-TYPE
    SYNTAX  INTEGER {
        add (1),
        del (2),
        mod (3)
    }
    ACCESS  read-only
    STATUS  mandatory
    DESCRIPTION "
        This will add, delete or modify the partition.
        1 ==> ADD
        2 ==> DELETE
        3 ==> MODIFY
    "
    DEFVAL { del }
    ::= { rpmIfCnfRscPartEntry 4}


rpmIfRscPrtIngrPctBandwidth OBJECT-TYPE
    SYNTAX  INTEGER (0..100)
    ACCESS  read-only
    STATUS  mandatory
    DESCRIPTION "
        The percentage of logical interface bandwidth.
    "
    DEFVAL { 0 }
    ::= { rpmIfCnfRscPartEntry 5 }

rpmIfRscPrtEgrPctBandwidth OBJECT-TYPE
    SYNTAX  INTEGER (0..100)
    ACCESS  read-only
    STATUS  mandatory
    DESCRIPTION "
        The percentage of logical interface bandwidth.
    "
    DEFVAL { 0 }
    ::= { rpmIfCnfRscPartEntry 6 }


rpmIfRscPrtVpiLow OBJECT-TYPE
    SYNTAX  INTEGER (0..255)
    ACCESS  read-only
    STATUS  mandatory
    DESCRIPTION "
        The beginning of the VPI range reserved for this partition.
    "
    ::= { rpmIfCnfRscPartEntry 7 }
 
rpmIfRscPrtVpiHigh OBJECT-TYPE
    SYNTAX  INTEGER (0..255)
    ACCESS  read-only
    STATUS  mandatory
    DESCRIPTION "
        The end of the VPI range reserved for this partition.
    "
    ::= { rpmIfCnfRscPartEntry 8 }

rpmIfRscPrtVciLow OBJECT-TYPE
    SYNTAX  INTEGER (0..65535)
    ACCESS  read-only
    STATUS  mandatory
    DESCRIPTION "
        The beginning of the VCI range reserved for this partition.
        This field is only valid for logical interfaces configured with
        a single VPI.
    "
    ::= { rpmIfCnfRscPartEntry 9 }
 
rpmIfRscPrtVciHigh OBJECT-TYPE
    SYNTAX  INTEGER (0..65535)
    ACCESS  read-only
    STATUS  mandatory
    DESCRIPTION "
        The end of the VCI range reserved for this partition.
        This field is only valid for logical interfaces configured with      
        a single VPI.
    "
    ::= { rpmIfCnfRscPartEntry 10 }
 
                                                                 
rpmIfRscPrtMaxChans OBJECT-TYPE
    SYNTAX  INTEGER (0..4047)
    ACCESS  read-only
    STATUS  mandatory
    DESCRIPTION " 
        This represents no. of channels that are available to the 
        controller.
    "
    ::= { rpmIfCnfRscPartEntry 11 }
 

------------------------------------------------------------
--
-- RPM PORT RESOURCE PARTITION TABLE
--
------------------------------------------------------------
--
----------------------------------------------------------------------------
-- PAR MIB
-- -------------------------------------------------------------------------

-- -------------------------------------------------------------------------
--   PAR Self Node Group
-- -------------------------------------------------------------------------




parSelfNode	OBJECT IDENTIFIER ::= { par 1 }
parInterfaces	OBJECT IDENTIFIER ::= { par 2 }
parConnection	OBJECT IDENTIFIER ::= { par 3 }
parNetworkClock	OBJECT IDENTIFIER ::= { par 4 }
parConfigParms	OBJECT IDENTIFIER ::= { par 5 }

--  Boolean Values 
	TruthValue  ::= INTEGER { true (1), false (2) }

parSnNodeId	OBJECT-TYPE
	SYNTAX	INTEGER(1..223)
	ACCESS	read-write
	STATUS	mandatory
	DESCRIPTION
		" This object specifies the node number of the node. When the network manager tries to modify the value of this object, a message is sent node state machine which propagates this information and the value gets modified only if the new node number is successfully propagated. The node number uniquely identifies a routing node in a network.
	"
	DEFVAL  { 1 }
	::= { parSelfNode 1}


parSnNodeIP	OBJECT-TYPE
	SYNTAX	IpAddress
	ACCESS	read-write
	STATUS	mandatory
	DESCRIPTION "
	This object specifies the IP address for routing node and is used 
	for communication with SV+.
	"
	::= { parSelfNode 2}


parSnNodeName	OBJECT-TYPE
	SYNTAX	DisplayString (SIZE (0..8))
	ACCESS	read-write
	STATUS	mandatory
	DESCRIPTION
	"
        This object specifies the name of the node and is unique among 
	all the nodes in the network. Whenever the name of the node is 
	changed, AutoRoute has to propagate the information to the other 
	nodes in the network. It also specifies the name of a PAR Feeder
        node.
        "
	::= { parSelfNode 3}


parSnRevision	OBJECT-TYPE
	SYNTAX  DisplayString	
	ACCESS	read-only
	STATUS	mandatory
	DESCRIPTION
	"This object specifies the primary revision of the PAR running 
	on the node.
	Format: cc.c.cc 
	Where: c = one ascii character"

	::= { parSelfNode 4}


parSnNodeAlarmStatus	OBJECT-TYPE
	SYNTAX	INTEGER {
	clear (1),
	minor (2),
	major (3),
	unreach (4)
	}
	ACCESS	read-only
	STATUS	mandatory

	DESCRIPTION
	"This object specifies the type of alarm on the node.
	If there is no alarm the value of this object is none(1).
	If there is a minor alarm the value of this object is min(2)
	If there is a major alarm the value of this object is maj(3).
	If the node is unreachable the value of this object is unreach(4)."

	::= { parSelfNode 5}


parSnNumberOfTrunks	OBJECT-TYPE
	SYNTAX	INTEGER (0..255)
	ACCESS	read-only
	STATUS	mandatory
	DESCRIPTION
	"This object specifies the number of trunks attached to the node."
	::= { parSelfNode 6}

-- parInterfaces

parIfTable	OBJECT-TYPE
	SYNTAX	SEQUENCE OF ParIfEntry
	ACCESS	not-accessible
	STATUS	mandatory
	DESCRIPTION
	"Table of all logical interfaces supported by PAR"
	::= { parInterfaces 1}


parIfEntry	OBJECT-TYPE
	SYNTAX	ParIfEntry
	ACCESS	not-accessible
	STATUS	mandatory
	DESCRIPTION	
	"Entries for logical interfaces."
	INDEX	{ parIfLogicalInterface }
	::=	{ parIfTable 1}



ParIfEntry ::=
	SEQUENCE {
		parIfLogicalInterface	INTEGER,
		parIfType		INTEGER,
		parIfOperStatus		INTEGER,
		parIfTxBw		INTEGER,
		parIfRxBw		INTEGER,
		parIfMaxConn		INTEGER,
		parIfHiAddrMin		INTEGER,
		parIfHiAddrMax		INTEGER,
		parIfLoAddrMin		INTEGER,
		parIfLoAddrMax		INTEGER
}


parIfLogicalInterface	OBJECT-TYPE
	SYNTAX	INTEGER
	ACCESS  read-only
        STATUS	mandatory
	DESCRIPTION
	"This object specifies the logical interface number 
	assigned by Platform Software"
	::= { parIfEntry 1}


parIfType	OBJECT-TYPE
	SYNTAX	INTEGER {
		userport (1),
		routingtrunk (2),
		feedertrunk (3),
        clkport(4),
        virtualtrunk(5)
		}
	ACCESS	read-write
	STATUS	mandatory
	DESCRIPTION
	"Specifies the type of interface - uni, nni or clock. uni(1) interface 
	is for user ports and trunks may be either nni or uni. Default 
	type of the interface is uni(1) and it can be configured to 
	nni(2) provided there are no connections on the port.
	Type of interface can be changed from nni(2) to uni(1) if the 
	trunk is not added. clock type interface is one which is used derive the
        clock."
	DEFVAL {userport }
	::= { parIfEntry 2}


parIfOperStatus OBJECT-TYPE
	SYNTAX	INTEGER {
		up (1),
		added (2),
		failed (3),
		added-failed (4)
	}
	ACCESS	read-only
	STATUS	mandatory
	DESCRIPTION
	"This object specifies the operation status of the interface.
	For interfaces of type uni(1) the status is either up(1) or 
	failed(3) as reported by platform.
	For interfaces of type nni(2) the status is either of up(1), 
	added(2), failed(3) or added-failed(4).
	Status up(1) indicates that the interface is configured as 
	trunk but the trunk is not added.
	Status failed(3) indicates that the interface is configured as 
	trunk, the trunk is not added and platform indicates an alarm 
	on the interface.
	Status added(2) indicates that the interface is configured as 
	trunk and the trunk is added.
	Status added-failed(4) indicates that the interface is configured 
	as trunk, the trunk is added and there is an alarm on the trunk. 
	This alarm could be generated by PAR or reported by Platform."
	::= { parIfEntry 3}


parIfTxBw	OBJECT-TYPE
	SYNTAX	INTEGER
	ACCESS	read-only
	STATUS	mandatory
	DESCRIPTION
	"This object specifies the transmit bandwidth for the interface 
	in units of cells per second."
	::= { parIfEntry 4}

parIfRxBw	OBJECT-TYPE
	SYNTAX	INTEGER
	ACCESS	read-only
	STATUS	mandatory
	DESCRIPTION
	"This object specifies the receive bandwidth for the interface
	in units of cells per second."
	::= { parIfEntry 5}


parIfMaxConn	OBJECT-TYPE
	SYNTAX	INTEGER
	ACCESS	read-only
	STATUS	mandatory
	DESCRIPTION
	"This object specifies the maximum number of connections that 
	can be configured over the interface."
	::= { parIfEntry 6}


parIfHiAddrMin	OBJECT-TYPE
	SYNTAX	INTEGER
	ACCESS	read-only
	STATUS	mandatory
	DESCRIPTION
	"This object specifies the minimum VPI that PAR can use for 
	configuring connection in the interface."
	::= { parIfEntry 7}


parIfHiAddrMax	OBJECT-TYPE
	SYNTAX	INTEGER
	ACCESS	read-only
	STATUS	mandatory
	DESCRIPTION
	"This object specifies the maximum VPI that PAR can use for 
	configuring connection in the interface."
	::= { parIfEntry 8}


parIfLoAddrMin	OBJECT-TYPE
	SYNTAX	INTEGER
	ACCESS	read-only
	STATUS	mandatory
	DESCRIPTION
	"This object specifies the minimum VCI that PAR can use for 
	configuring connection in the interface."
	::= { parIfEntry 9}


parIfLoAddrMax	OBJECT-TYPE
	SYNTAX	INTEGER
	ACCESS	read-only
	STATUS	mandatory
	DESCRIPTION
	"This object specifies the maximum VCI that PAR can use for 
	configuring connection in the interface."
	::= { parIfEntry 10}


parTrkTable	OBJECT-TYPE
	SYNTAX	SEQUENCE OF ParTrkEntry
	ACCESS	not-accessible
	STATUS	mandatory
	DESCRIPTION
	"Trunk parameters"
	::= { parInterfaces 2}

parTrkEntry	OBJECT-TYPE
	SYNTAX	ParTrkEntry
	ACCESS	not-accessible
	STATUS	mandatory
	DESCRIPTION
	"Entries for logical interfaces configured as trunks (parIfType nni)."
	INDEX { parIfLogicalInterface }
	::= { parTrkTable 1}


ParTrkEntry ::=

	SEQUENCE {
	parTrkId	INTEGER,
	parTrkStatReserve INTEGER,
	parTrkCnfgCcRestrict TruthValue,
	parTrkCnfgLineType INTEGER,
	parTrkCnfgPassSync TruthValue,
	parTrkCnfgDerouteDelay INTEGER,
	parTrkCnfgTrafficClassFst TruthValue,
	parTrkCnfgTrafficClassFr TruthValue,
	parTrkCnfgTrafficClassNts TruthValue,
	parTrkCnfgTrafficClassTs TruthValue,
	parTrkCnfgTrafficClassVoice TruthValue,
	parTrkCnfgTrafficClassCbr TruthValue,
	parTrkCnfgTrafficClassVbr TruthValue,
	parTrkCnfgTrafficClassAbr TruthValue,
	parTrkCnfgAdminStatus INTEGER,
	parTrkCnfgRoutingCost INTEGER,
	parTrkCnfgVpcConids INTEGER,
	parTrkCnfgVccConids INTEGER,
	parTrkLocalSlotNumber INTEGER,
	parTrkLocalPortNumber INTEGER,
	parTrkLocalVTrunkId INTEGER,
	parTrkRemoteNodeId INTEGER,
	parTrkRemoteTrunkId INTEGER,
	parTrkRemoteSlotNumber INTEGER,
	parTrkRemotePortNumber INTEGER,
	parTrkRemoteVTrunkId INTEGER,
	parTrkRemoteNodeIP IpAddress,
	parTrkRemoteNodeType INTEGER,
	parTrkRemoteNodeName DisplayString,
	parTrkAlarmStatus INTEGER,
	parTrkAlarmType INTEGER,
	parTrkLineLoad INTEGER,
	parTrkBwCapacity INTEGER
}



parTrkId	OBJECT-TYPE
	SYNTAX	INTEGER
	ACCESS	read-only
	STATUS	mandatory
	DESCRIPTION
	"This object specifies the logical trunk number associated 
	with the trunk at the local node."
	::= { parTrkEntry 1}


parTrkStatReserve	OBJECT-TYPE
	SYNTAX	INTEGER
	ACCESS	read-write
	STATUS	mandatory
--			(cells per second)
	DESCRIPTION
	"Specifies the bandwidth reserved as Statistical Reserve on 
	the trunk in units of cells per second.
	This object cannot take a value beyond the bandwidth capacity 
	of the trunk."
	DEFVAL  { 1000}  
	::= { parTrkEntry 2}


parTrkCnfgCcRestrict	OBJECT-TYPE
	SYNTAX	TruthValue
	ACCESS	read-write
	STATUS	mandatory
	DESCRIPTION
	"This object specifies the operators preference for routing 
	control plane traffic on the interface.
	If the object is set to False, then the interface may be chosen 
	for control plane traffic. If it is True, then the interface is 
	not chosen, unless there is no other trunk with parIfOperStatus 
	added(2), in which case it is chosen regardless of the value of 
	this object."
	DEFVAL	{ false }
	::= { parTrkEntry 3}



parTrkCnfgLineType	OBJECT-TYPE
	SYNTAX	INTEGER {
		terrestrial (1),
		satellite   (2)
	}
	ACCESS	read-write
	STATUS	mandatory
	DESCRIPTION
	"This object specifies the type of interface terrestrial 
	or satellite. The interfaces configured as terrestrial(1) 
	are preferred over those configured as satellite(2) for 
	routing control plane traffic.
	This information is also used for connections for which 
	routing restrictions are specified."
	DEFVAL  { terrestrial }
	::= { parTrkEntry 4}


parTrkCnfgPassSync	OBJECT-TYPE
	SYNTAX	TruthValue
	ACCESS	read-write
	STATUS	mandatory
	DESCRIPTION
	"This object specifies whether the trunk can be used to pass 
	clock sync.
	If the value of this object is True, clock can be synchronized 
	through the trunk; otherwise not."
	DEFVAL  { true}
	::= { parTrkEntry 5}



parTrkCnfgDerouteDelay OBJECT-TYPE
	SYNTAX INTEGER
	ACCESS read-write
	STATUS mandatory
	DESCRIPTION
	"This object specifies the value of deroute delay timer in seconds."
	DEFVAL { 0 }
	::= { parTrkEntry 6}


parTrkCnfgTrafficClassFst OBJECT-TYPE
	SYNTAX TruthValue
	ACCESS read-write
	STATUS mandatory
	DESCRIPTION
	"This object indicates whether Foresight traffic can be routed 
	over the trunk. If the value is True it can be rerouted otherwise 
	not."
	DEFVAL { true }
	::= { parTrkEntry 7}



parTrkCnfgTrafficClassFr OBJECT-TYPE
	SYNTAX TruthValue
	ACCESS read-write
	STATUS mandatory
	DESCRIPTION
	"This object indicates whether Frame Relay traffic can be 
	routed over the trunk. If the value is True it can be rerouted 
	otherwise not."
	DEFVAL { true }
	::= { parTrkEntry 8}


parTrkCnfgTrafficClassNts OBJECT-TYPE
	SYNTAX TruthValue
	ACCESS read-write
	STATUS mandatory
	DESCRIPTION
	"This object indicates whether Non-Time Stamped traffic can 
	be routed over the trunk. If the value is True it can be 
	rerouted otherwise not."
	DEFVAL { true }
	::= { parTrkEntry 9}


parTrkCnfgTrafficClassTs OBJECT-TYPE
	SYNTAX TruthValue
	ACCESS read-write
	STATUS mandatory
	DESCRIPTION
	"This object indicates whether Time Stamped traffic can be 
	routed over the trunk. If the value is True it can be rerouted 
	otherwise not."
	DEFVAL { true }
	::= { parTrkEntry 10}



parTrkCnfgTrafficClassVoice OBJECT-TYPE
	SYNTAX TruthValue
	ACCESS read-write
	STATUS mandatory
	DESCRIPTION
	"This object indicates whether Voice traffic can be routed 
	over the trunk. If the value is True it can be rerouted 
	otherwise not."
	DEFVAL { true }
	::= { parTrkEntry 11}



parTrkCnfgTrafficClassCbr OBJECT-TYPE
	SYNTAX TruthValue
	ACCESS read-write
	STATUS mandatory
	DESCRIPTION
	"This object indicates whether Constant Bit Rate traffic can 
	be routed over the trunk. If the value is True it can be 
	rerouted otherwise not."
	DEFVAL { true }
	::= { parTrkEntry 12}



parTrkCnfgTrafficClassVbr OBJECT-TYPE
	SYNTAX TruthValue
	ACCESS read-write
	STATUS mandatory
	DESCRIPTION
	"This object indicates whether Variable Bit Rate traffic can 
	be routed over the trunk. If the value is True it can be 
	rerouted otherwise not."
	DEFVAL { true }
	::= { parTrkEntry 13}
 


parTrkCnfgTrafficClassAbr OBJECT-TYPE
	SYNTAX TruthValue
	ACCESS read-write
	STATUS mandatory
	DESCRIPTION
	"This object indicates whether Available Bit Rate traffic 
	can be routed over the trunk. If the value is True it can 
	be rerouted otherwise not."
	DEFVAL { true }
	::= { parTrkEntry 14}



parTrkCnfgAdminStatus OBJECT-TYPE
	SYNTAX INTEGER {
		add (1),
		delete (2)
	}
	ACCESS read-write
	STATUS mandatory
	DESCRIPTION
	"This object can be used to add or delete the trunk. The value 
	of this object can be set to add(1) only if the parIfOperStatus 
	is up. The value can be set to delete if parIfOperStatus is 
	added or added-failed"
	DEFVAL { delete }
	::= { parTrkEntry 15}

parTrkCnfgRoutingCost OBJECT-TYPE
	SYNTAX INTEGER(1..15)
	ACCESS read-write
	STATUS mandatory
	DESCRIPTION
	"This object specifies the cost associated with the trunk 
	for the purpose of routing the connections. This object has 
	significance if cost based routing feature is enabled. 
	(parCmParmsCostBased)"
	DEFVAL { 7 }
	::= { parTrkEntry 16}


parTrkCnfgVccConids OBJECT-TYPE
	SYNTAX INTEGER
	ACCESS read-write
	STATUS mandatory
	DESCRIPTION 
	"The max number of routing resource available on the trunk for 
	VCC connections."
	::= { parTrkEntry 17}





parTrkCnfgVpcConids OBJECT-TYPE
	SYNTAX INTEGER
	ACCESS read-write
	STATUS mandatory
	DESCRIPTION
	"The max number of routing resource available on the trunk for 
	VPC connections"
	::= { parTrkEntry 18}


parTrkLocalSlotNumber OBJECT-TYPE
	SYNTAX INTEGER
	ACCESS read-only
	STATUS mandatory
	DESCRIPTION 
	"This object specifies the slot number of the interface card 
	associated with the trunk at the local node."
	::= { parTrkEntry 19}


parTrkLocalPortNumber OBJECT-TYPE
	SYNTAX INTEGER
	ACCESS read-only
	STATUS mandatory
	DESCRIPTION
	"This object specifies the port number of the interface card 
	associated with the trunk at the local node."
	::= { parTrkEntry 20}


parTrkLocalVTrunkId OBJECT-TYPE
	SYNTAX INTEGER (1..255)
	ACCESS read-only
	STATUS mandatory
	DESCRIPTION
	"This object specifies the Virtual trunk of the interface card 
	associated with the trunk at the local node. The value of this 
	object is between 1 and 254, inclusive for a virtual trunk and 
	255 for a physical trunk."
	::= { parTrkEntry 21}


parTrkRemoteNodeId OBJECT-TYPE
	SYNTAX INTEGER (1..223)
	ACCESS read-only
	STATUS mandatory
	DESCRIPTION 
	"This object specifies the node number of the node attached to 
	the remote end of the trunk."
	::= { parTrkEntry 22}


parTrkRemoteTrunkId OBJECT-TYPE
	SYNTAX INTEGER (1..255)
	ACCESS read-only
	STATUS mandatory
	DESCRIPTION 
	"This object specifies the logical trunk number at the node on 
	the remote end of the trunk."
	::= { parTrkEntry 23}



parTrkRemoteSlotNumber OBJECT-TYPE
	SYNTAX INTEGER
	ACCESS read-only
	STATUS mandatory
	DESCRIPTION
	"This object specifies the slot number of the interface card 
	to which the trunk is attached on the remote node."
	::= { parTrkEntry 24}




parTrkRemotePortNumber OBJECT-TYPE
	SYNTAX INTEGER
	ACCESS read-only
	STATUS mandatory
	DESCRIPTION
	"This object specifies the port number of the interface card 
	to which the trunk is attached on the remote node."
	::= { parTrkEntry 25}


parTrkRemoteVTrunkId OBJECT-TYPE
	SYNTAX INTEGER (1..255)
	ACCESS read-only
	STATUS mandatory
	DESCRIPTION 
	"This object specifies the Virtual trunk of the interface card 
	associated with the trunk at the remote node. The value of this 
	object is between 1 and 254, inclusive for a virtual trunk and 
	255 for a physical trunk."
	::= { parTrkEntry 26}


parTrkRemoteNodeIP OBJECT-TYPE
	SYNTAX IpAddress
	ACCESS read-only
	STATUS mandatory
	DESCRIPTION "This object specifies the IP address for the 
	Remote node, used for communication with NMS"
	::= { parTrkEntry 27}


parTrkRemoteNodeType OBJECT-TYPE
	SYNTAX INTEGER{
		ipx (1),
		igx (2),
		bpx (3),
		par (4),
		unknown (5)
		}
	ACCESS read-only
	STATUS mandatory
	DESCRIPTION
	"Specifies the type of the node."
	::= { parTrkEntry 28}


parTrkRemoteNodeName OBJECT-TYPE
	SYNTAX DisplayString
	ACCESS read-only
	STATUS mandatory
	DESCRIPTION
	"This object specifies the name of the remote node and is unique 
	among all the nodes in the network."
	::= { parTrkEntry 29}



parTrkAlarmStatus OBJECT-TYPE
	SYNTAX INTEGER {
	clear (1),
	minor (2),
	major (3)
	}
	ACCESS read-only
	STATUS mandatory
	DESCRIPTION
	"This object specifies the severity of the alarm on the trunk.
	If there is no alarm the value of this object is none(1).
	If there is a minor alarm the value of this object is min(2).
	If there is a major alarm on the trunk the value of this object 
	is maj(3)."
	::= { parTrkEntry 30}


parTrkAlarmType OBJECT-TYPE
	SYNTAX INTEGER{
	rsrcunavail (1),
	commfail (2),
	unknown (3),
    failed (4),
    looped (5)}
	ACCESS read-only
	STATUS mandatory
	DESCRIPTION 
	"This object specifies the type of alarm on the trunk. The value 
	of this object has no significance if parTrunkAlarmStatus 
	indicates no alarm.
	resources unavailable (1) indicates that the platform has not 
	provided the resources required to make this interface into 
	a trunk.
	communication failure (2) indicates that message exchange 
	between neighboring nodes on this trunk has failed.
	unknown (3) indicates that the alarm type is unknown to PAR, 
	for example if the platform has declared the interface in alarm 
	due to some physical problem with the interface."
	::= { parTrkEntry 31}




parTrkBwCapacity OBJECT-TYPE
	SYNTAX INTEGER
	ACCESS read-only
	STATUS mandatory
	DESCRIPTION
	"Specifies the bandwidth capacity of the trunk."
	::= { parTrkEntry 32}


parTrkLineLoad OBJECT-TYPE
	SYNTAX INTEGER
	ACCESS read-only
	STATUS mandatory
	DESCRIPTION
	"Specifies the bandwidth used by the connections routed over the trunk."
	::= { parTrkEntry 33}




parTrkLoadTable OBJECT-TYPE
	SYNTAX SEQUENCE OF ParTrkLoadEntry
	ACCESS not-accessible
	STATUS mandatory
	DESCRIPTION 
	"Trunk Load Information"
	::= { parInterfaces 3}

parTrkLoadEntry OBJECT-TYPE
	SYNTAX ParTrkLoadEntry
	ACCESS not-accessible
	STATUS mandatory
	DESCRIPTION
	"Load info for logical interfaces configured as trunks (parIfType nni)."
	INDEX { parIfLogicalInterface }
	::= { parTrkLoadTable 1}



ParTrkLoadEntry ::=
	SEQUENCE {
		parTrkLoadXmtUsedCbr	INTEGER,
		parTrkLoadRcvUsedCbr	INTEGER,
		parTrkLoadXmtUsedVbr	INTEGER,
		parTrkLoadRcvUsedVbr	INTEGER,
		parTrkLoadXmtUsedAbr	INTEGER,
		parTrkLoadRcvUsedAbr	INTEGER,
		parTrkLoadXmtUsedNts	INTEGER,
		parTrkLoadRcvUsedNts	INTEGER,
		parTrkLoadXmtUsedTs	INTEGER,
		parTrkLoadRcvUsedTs	INTEGER,
		parTrkLoadXmtUsedVoice	INTEGER,
		parTrkLoadRcvUsedVoice	INTEGER,
		parTrkLoadXmtUsedBdataA	INTEGER,
		parTrkLoadRcvUsedBdataA	INTEGER,
		parTrkLoadXmtUsedBdataB	INTEGER,
		parTrkLoadRcvUsedBdataB	INTEGER,
		parTrkLoadVccConidsUsed	INTEGER,
		parTrkLoadVpcConidsUsed	INTEGER
	}




parTrkLoadXmtUsedCbr OBJECT-TYPE
	SYNTAX INTEGER
	ACCESS read-only
	STATUS mandatory
	DESCRIPTION
	"This object specifies the used bandwidth in the transmit 
	direction for CBR traffic."
	::= { parTrkLoadEntry 1}


parTrkLoadRcvUsedCbr OBJECT-TYPE
	SYNTAX INTEGER
	ACCESS read-only
	STATUS mandatory
	DESCRIPTION
	"This object specifies the used bandwidth in the receive 
	direction for CBR traffic"
	::= { parTrkLoadEntry 2}


parTrkLoadXmtUsedVbr OBJECT-TYPE
	SYNTAX INTEGER
	ACCESS read-only
	STATUS mandatory
	DESCRIPTION
	"This object specifies the used bandwidth in the transmit 
	direction for VBR."
	::= { parTrkLoadEntry 3}


parTrkLoadRcvUsedVbr OBJECT-TYPE
	SYNTAX INTEGER
	ACCESS read-only
	STATUS mandatory
	DESCRIPTION
	"This object specifies the used bandwidth in the receive 
	direction for VBR."
	::= { parTrkLoadEntry 4}



parTrkLoadXmtUsedAbr OBJECT-TYPE
	SYNTAX INTEGER
	ACCESS read-only
	STATUS mandatory
	DESCRIPTION
	"This object specifies the used bandwidth in the transmit 
	direction for ABR."
	::= { parTrkLoadEntry 5}



parTrkLoadRcvUsedAbr OBJECT-TYPE
	SYNTAX INTEGER
	ACCESS read-only
	STATUS mandatory
	DESCRIPTION 
	"This object specifies the used bandwidth in the receive 
	direction for ABR."
	::= { parTrkLoadEntry 6}


parTrkLoadXmtUsedNts OBJECT-TYPE
	SYNTAX INTEGER
	ACCESS read-only
	STATUS mandatory
	DESCRIPTION
	"This object specifies the used bandwidth in the transmit 
	direction for Non-Time Stamped."
	::= { parTrkLoadEntry 7}
	


parTrkLoadRcvUsedNts OBJECT-TYPE
	SYNTAX INTEGER
	ACCESS read-only
	STATUS mandatory
	DESCRIPTION
	"This object specifies the used bandwidth in the receive 
	direction for Non-Time Stamped."
	::= { parTrkLoadEntry 8}




parTrkLoadXmtUsedTs OBJECT-TYPE
	SYNTAX INTEGER
	ACCESS read-only
	STATUS mandatory
	DESCRIPTION
	"This object specifies the used bandwidth in the transmit 
	direction for Time-Stamped."
	::= { parTrkLoadEntry 9}
	


parTrkLoadRcvUsedTs OBJECT-TYPE
	SYNTAX INTEGER
	ACCESS read-only
	STATUS mandatory
	DESCRIPTION
	"This object specifies the used bandwidth in the receive 
	direction for Time-Stamped."
	::= { parTrkLoadEntry 10}



parTrkLoadXmtUsedVoice OBJECT-TYPE
	SYNTAX INTEGER
	ACCESS read-only
	STATUS mandatory
	DESCRIPTION
	"This object specifies the used bandwidth in the transmit 
	direction for Voice."
	::= { parTrkLoadEntry 11}



parTrkLoadRcvUsedVoice OBJECT-TYPE
	SYNTAX INTEGER
	ACCESS read-only
	STATUS mandatory
	DESCRIPTION
	"This object specifies the used bandwidth in the receive 
	direction for Voice."
	::= { parTrkLoadEntry 12}
	


parTrkLoadXmtUsedBdataA OBJECT-TYPE
	SYNTAX INTEGER
	ACCESS read-only
	STATUS mandatory
	DESCRIPTION "This object specifies the used bandwidth in the 
	transmit direction for Busty Data A."
	::= { parTrkLoadEntry 13}



parTrkLoadRcvUsedBdataA OBJECT-TYPE
	SYNTAX INTEGER
	ACCESS read-only
	STATUS mandatory
	DESCRIPTION "This object specifies the used bandwidth in the 
	receive direction for Bursty Data A."
	::= { parTrkLoadEntry 14}



parTrkLoadXmtUsedBdataB OBJECT-TYPE
	SYNTAX INTEGER
	ACCESS read-only
	STATUS mandatory
	DESCRIPTION
	"This object specifies the used bandwidth in the transmit 
	direction for Bursty Data B."
	::= { parTrkLoadEntry 15}



parTrkLoadRcvUsedBdataB OBJECT-TYPE
	SYNTAX INTEGER
	ACCESS read-only
	STATUS mandatory
	DESCRIPTION
	"This object specifies the used bandwidth in the receive 
	direction for Bursty Data B."
	::= { parTrkLoadEntry 16}
	

parTrkLoadVccConidsUsed	OBJECT-TYPE
	SYNTAX INTEGER
	ACCESS read-only
	STATUS mandatory
	DESCRIPTION
	"This object specifies the number of conids used for VCCs
	(not used) on the trunk."
	::= { parTrkLoadEntry 17}


parTrkLoadVpcConidsUsed	OBJECT-TYPE
	SYNTAX INTEGER
	ACCESS read-only
	STATUS mandatory
	DESCRIPTION
	"This object specifies the number of conids Used for VPCs
	(not used) on the trunk."
	::= { parTrkLoadEntry 19}


-- parConnection

parConnectionTable OBJECT-TYPE
	SYNTAX SEQUENCE OF ParConnectionEntry
	ACCESS not-accessible
	STATUS mandatory
	DESCRIPTION
	"Connections Mastered or slaved by the node."
	::= { parConnection 1}


parConnectionEntry OBJECT-TYPE
	SYNTAX ParConnectionEntry
	ACCESS not-accessible
	STATUS mandatory
	DESCRIPTION
	"Entries for connections mastered or slaved by the node."
	INDEX { parConnLocalSlot, parConnLocalPort, parConnLocalVpi, parConnLocalVci }
	::= { parConnectionTable 1}


ParConnectionEntry ::=
SEQUENCE {
	parConnLocalSlot	INTEGER,
	parConnLocalPort	INTEGER,
	parConnLocalVpi		INTEGER,
	parConnLocalVci		INTEGER,
        parConnMasterShip       TruthValue,
	parConnLocalVcIndx	INTEGER,
        parConnLocalEndpt       DisplayString,
	parConnRemoteNodeName	DisplayString,
	parConnRemoteSlot	INTEGER,
	parConnRemotePort	INTEGER,
	parConnRemoteVpi	INTEGER,
	parConnRemoteVci	INTEGER,
	parConnRemoteVcIndx	INTEGER,
        parConnRemoteEndpt      DisplayString,
	parConnOperStatus	INTEGER,
	parConnAdminStatus	INTEGER,
	parConnRoute		DisplayString,
        parPrefRoute            DisplayString,
        parConnFailRsn          INTEGER,
        parRrtFailRsn           DisplayString,
	parConnRstrTyp		INTEGER,
	parConnRstrZcs		TruthValue,
        parConnCos              INTEGER
}


parConnLocalSlot OBJECT-TYPE
	SYNTAX INTEGER
	ACCESS read-only
	STATUS mandatory
	DESCRIPTION
	"This object specifies the slot number part of the local 
	endpoint connection address."
	::= { parConnectionEntry 1}


parConnLocalPort OBJECT-TYPE
	SYNTAX INTEGER
	ACCESS read-only
	STATUS mandatory
	DESCRIPTION
	"This object specifies the port number part of the local 
	endpoint connection address."
	::= { parConnectionEntry 2}


parConnLocalVpi OBJECT-TYPE
	SYNTAX INTEGER
	ACCESS read-only
	STATUS mandatory
	DESCRIPTION 
	"This object specifies the Virtual Path Identifier part of 
	the local endpoint connection address."
	::= { parConnectionEntry 3}


parConnLocalVci OBJECT-TYPE
	SYNTAX INTEGER
	ACCESS read-only
	STATUS mandatory
	DESCRIPTION
	"This object specifies the Virtual Channel Identifier part 
	of the local endpoint connection address."
	::= { parConnectionEntry 4}


parConnMasterShip OBJECT-TYPE
	SYNTAX TruthValue
	ACCESS read-only
	STATUS mandatory
	DESCRIPTION
        "This object specifies whether this end of the connection is the master
         or the slave of the connection."
	::= { parConnectionEntry 5}


parConnLocalVcIndx OBJECT-TYPE
	SYNTAX INTEGER
	ACCESS read-only
	STATUS mandatory
	DESCRIPTION 
	"This object specifies the Virtual Connection Index at this 
	node. It is used by Network Management to correlate this end 
	of the connection with the remote end."
	::= { parConnectionEntry 6}

parConnLocalEndpt OBJECT-TYPE
        SYNTAX DisplayString
        ACCESS read-only
        STATUS mandatory
        DESCRIPTION
        "This object specifies the actual physical connection endpoint
         at the local node."
        ::= { parConnectionEntry 7}

parConnRemoteNodeName OBJECT-TYPE
	SYNTAX DisplayString
	ACCESS read-only
	STATUS mandatory
	DESCRIPTION
	"This object specifies the node name of the remote endpoint. 
	For a intra-switch connection or feeder connection this object 
	would specify the self node name."
	::= { parConnectionEntry 8}


parConnRemoteSlot OBJECT-TYPE
	SYNTAX INTEGER
	ACCESS 	read-only
	STATUS mandatory
	DESCRIPTION
	"This object specifies the slot number part of the remote 
	endpoint connection address."
	::= { parConnectionEntry 9}


parConnRemotePort OBJECT-TYPE
	SYNTAX INTEGER
	ACCESS read-only
	STATUS mandatory
	DESCRIPTION
	"This object specifies the port number part of the remote 
	endpoint connection address."
	::= { parConnectionEntry 10}


parConnRemoteVpi OBJECT-TYPE
	SYNTAX INTEGER
	ACCESS read-only
	STATUS mandatory
	DESCRIPTION
	"This object specifies the VPI part of the remote endpoint 
	connection address."
	::= { parConnectionEntry 11}


parConnRemoteVci OBJECT-TYPE
	SYNTAX INTEGER 
	ACCESS read-only
	STATUS mandatory
	DESCRIPTION
	"This object specifies the VCI part of the remote endpoint 
	connection address."
	::= { parConnectionEntry 12}



parConnRemoteVcIndx OBJECT-TYPE
	SYNTAX INTEGER
	ACCESS read-only
	STATUS mandatory
	DESCRIPTION
	"This object specifies the Virtual Connection Index at the 
	remote node. It is used by Network Management to correlate 
	this end of the connection with the remote end.."
	::= { parConnectionEntry 13}



parConnOperStatus OBJECT-TYPE
        SYNTAX INTEGER {
	routed (1),
	unrouted (2),
        lmifail(3),
	unknown (4)
	}
	ACCESS read-only
	STATUS mandatory
	DESCRIPTION
	"This object specifies the status of connection as known and
         determined by PAR. The status shall be OK if there is an abit
         alarm on the connection."
	::= { parConnectionEntry 14}


parConnAdminStatus OBJECT-TYPE
	SYNTAX INTEGER {
	down    (1),
	up      (2),
	reroute (3)
	}
	ACCESS read-write
	STATUS mandatory
	DESCRIPTION
	"This object is used by the operator to reroute or down/up 
	a connection. The value of this object is up when the 
	connection is created. If the value of the object is set to 
	down(1) the connection is derouted (if it is routed) and 
	parConnOperStatus object is set to not routed.
	If the value of the object is up (2) and it is set to reroute(3) 
	the connection is derouted and attempt is made to reroute the 
	connection. If the value of the object is down (1) and the it 
	is set to reroute (3), no action is performed and the object's 
	value does not changes. If the value of object is down(1) and 
	is set to up(2), an attempt is made to reroute the connection."
	DEFVAL { up }
	::= { parConnectionEntry 15}

parConnRoute OBJECT-TYPE
	SYNTAX DisplayString
	ACCESS read-only
	STATUS mandatory
	DESCRIPTION
	"This object specifies the current path on which the connection 
	is routed. A value of this object is valid only if 
	parConnOperStatus is routed. Null string specifies that the 
	connection is not routed.
	Format: Nodename {Trk--Trk Nodename}
	Where: Nodename = up to 8 characters, Trk = slot.port.vtrk, 
	slot = 1 or 2 characters, port = 1 or two characters, and 
	vtrk = 1 or two characters and is optional. The portion of 
	the format shown in braces {like this} can be repeated up to 
	10 times."
	::= { parConnectionEntry 16}

parConnRemoteEndpt OBJECT-TYPE
        SYNTAX DisplayString
        ACCESS read-only
        STATUS mandatory
        DESCRIPTION
        "This object specifies the actual physical connection endpoint at 
         the remote end of the connection. It shall be known only if the 
         connection is a local(DAX) connection."
        ::= { parConnectionEntry 17}


parPrefRoute OBJECT-TYPE
	SYNTAX DisplayString
	ACCESS read-write
	STATUS mandatory
	DESCRIPTION
	"This object specifies the preferred path for the connection.
        Null string specifies that the connection does not have a 
        preferred route.
	Format: Nodename {Trk--Trk Nodename}
	Where: Nodename = up to 8 characters, Trk = slot.port.vtrk, 
	slot = 1 or 2 characters, port = 1 or two characters, and 
	vtrk = 1 or two characters and is optional. The portion of 
	the format shown in braces {like this} can be repeated up to 
	10 times."
	::= { parConnectionEntry 18}


parConnFailRsn OBJECT-TYPE
        SYNTAX INTEGER {
            down(1),
            hwalm(2),
            abitalm(3),
            lmifail(4),
            rrtfail(5),
            incomplete(6)
        }
        ACCESS read-only
	STATUS mandatory 
        DESCRIPTION
        "This object specifies a reason code for the failure of the connection."
        ::= {parConnectionEntry 19}
 

parRrtFailRsn OBJECT-TYPE
	SYNTAX DisplayString
	ACCESS read-only
	STATUS mandatory
	DESCRIPTION
	"This object specifies the Reason of failure of a connection
	to route."
	::= {parConnectionEntry 20}

parConnRstrTyp OBJECT-TYPE
	SYNTAX INTEGER {
	norestrict(1),
	terrestrict(2),
	satrestrict(3),
	undefrestrict(4)
	}
	ACCESS read-only
	STATUS mandatory
	DESCRIPTION
	"This object specifies the Route restriction of a connection.
	The possible values are no restriction, terrestrial line 
	restriction or sattelite line restriction."
	::= {parConnectionEntry 21}
	
parConnRstrZcs OBJECT-TYPE
	SYNTAX TruthValue
	ACCESS read-only
	STATUS mandatory
	DESCRIPTION
	"This object specifies whether ZCS lines should be avoided 
	or not. The possible values are no restriction, terrestrial line 
	restriction or sattelite line restriction."
	::= {parConnectionEntry 22}

parConnCos OBJECT-TYPE
	SYNTAX INTEGER (0..15)
	ACCESS read-only
	STATUS mandatory
	DESCRIPTION
	"This object specifies the COS for the connection."
	::= {parConnectionEntry 23}

-- parNetworkClock

parClockTable OBJECT-TYPE
	SYNTAX SEQUENCE OF ParClockEntry
	ACCESS not-accessible
	STATUS mandatory
	DESCRIPTION
	"Table of clock sources available to PAR"
	::=
{ parNetworkClock 1}

parClockEntry OBJECT-TYPE
	SYNTAX ParClockEntry
	ACCESS not-accessible
	STATUS mandatory
	DESCRIPTION "Each entry represent a clock source iavailable to PAR"
	INDEX { parClockIndex }
	::= { parClockTable 1}

ParClockEntry ::= SEQUENCE {
	parClockIndex INTEGER,
	parClockType INTEGER,
        parClockCurSource TruthValue,
	parClockSource INTEGER,
	parClockSourceId INTEGER,
        parClockPath   DisplayString}
	
parClockIndex OBJECT-TYPE
	SYNTAX INTEGER
	ACCESS read-only
	STATUS mandatory
	DESCRIPTION
	"This clock index is assigned by PAR. This object is used 
	to index into parClockTable"
	::= { parClockEntry 1}

parClockType OBJECT-TYPE
	SYNTAX INTEGER{
		primary (1),
		secondary (2),
		tertiary (3),
                null (4)
	}
	ACCESS read-write
	STATUS mandatory
	DESCRIPTION
	"Specifies the type of clock - Primary, Secondary, Tertiary"
	::= { parClockEntry 2}
	
parClockSource OBJECT-TYPE
	SYNTAX INTEGER{
	internal (1),
	interface (2),
	external (3)}
	ACCESS read-only
	STATUS mandatory
	DESCRIPTION
	"Specifies source of the clock - Internal, Interface, External"
	DEFVAL { internal }
	::= { parClockEntry 3}

parClockCurSource OBJECT-TYPE
        SYNTAX TruthValue
        ACCESS read-only
        STATUS mandatory
        DESCRIPTION
        "Specifies whether clock source is a current clock source or not. The 
         value is true if the cloock source is current and false otherwise"
        DEFVAL {false}
        ::= { parClockEntry 4}

parClockSourceId OBJECT-TYPE
	SYNTAX INTEGER 
	ACCESS read-write
	STATUS mandatory
	DESCRIPTION
	"Specifies identification of the clock - for example - if 
	clock source is `Interface' then this field will carry 
	logical interface number"
	::= { parClockEntry 5}

parClockPath OBJECT-TYPE
        SYNTAX DisplayString
        ACCESS read-only
        STATUS mandatory
        DESCRIPTION
        "Describes the path used for clock synchronization"
        ::= { parClockEntry 6}

-- parConfigParms

parVsiConfigParms	OBJECT	IDENTIFIER	::= { parConfigParms 1 }
parCmParms		OBJECT	IDENTIFIER	::= { parConfigParms 2 }
parMnUpdt		OBJECT	IDENTIFIER	::= { parConfigParms 3 }
parSwFunc		OBJECT	IDENTIFIER	::= { parConfigParms 4 }
parOnOff		OBJECT	IDENTIFIER	::= { parConfigParms 5 }
parSysParms		OBJECT	IDENTIFIER	::= { parConfigParms 6 }
parNetworkingParms	OBJECT	IDENTIFIER	::= { parConfigParms 7 }


parCmParmsMaxRoutingBundle OBJECT-TYPE
	SYNTAX INTEGER
	ACCESS read-write
	STATUS mandatory
	DESCRIPTION
	"This object specifies the maximum number of connections that 
	can be routed in one routing cycle."
	DEFVAL { 24 }
	::= { parCmParms 1}

parCmParmsRerouteTimer OBJECT-TYPE
	SYNTAX INTEGER
	ACCESS read-write
	STATUS mandatory
	DESCRIPTION
	"This object specifies the minimum time after which a connection 
	is routed once it has been successfully routed."
	DEFVAL { 0 }
	::= { parCmParms 2}

parCmParmsResetTimer OBJECT-TYPE
	SYNTAX TruthValue
	ACCESS read-write
	STATUS mandatory
	DESCRIPTION
	"This object specifies whether the reroute timer should be reset 
	if the path for routed connection failed.
	If the value of the object is True the timer is reset on detecting 
	path fail."
	DEFVAL { true }
	::= { parCmParms 3}

parCmParmsDnUpPerPass OBJECT-TYPE
	SYNTAX INTEGER
	ACCESS read-write
	STATUS mandatory
	DESCRIPTION
	"This object specifies the maximum number of connections that are 
	upped or down in one schedule of down connection state machine."
	DEFVAL { 50 }
	::= { parCmParms 4}

parCmParmsDnUpTimer OBJECT-TYPE
	SYNTAX INTEGER
	ACCESS read-write
	STATUS mandatory
	DESCRIPTION
	"This object specifies the minimum time interval (in milliseconds) 
	between two schedules of the down connection state machine."
	DEFVAL { 30000 }
	::= { parCmParms 5}

parCmParmsRrtErrsPerCycle OBJECT-TYPE
	SYNTAX INTEGER
	ACCESS read-write
	STATUS mandatory
	DESCRIPTION
	"This object specifies the threshold for number of failures to 
	route a connection before it is moved into the wait group.
	If the value of this object is 0 the feature is disabled."
	DEFVAL { 50 }
	::= { parCmParms 6}

parCmParmsRrtCycleInterval OBJECT-TYPE
	SYNTAX INTEGER
	ACCESS read-write
	STATUS mandatory
	DESCRIPTION
	"This object specifies the time (in minutes) for which no 
	attempt is made to route a connection in the wait group."
	DEFVAL { 5 }
	::= { parCmParms 7}

parCmParmsMaxRrtCycles OBJECT-TYPE
	SYNTAX INTEGER
	ACCESS read-write
	STATUS mandatory
	DESCRIPTION
	"This object specifies the number of times a connection is 
	added to the wait group before declaring it unroutable."
	DEFVAL { 10 }
	::= { parCmParms 8}

parCmParmsRrtPauseTime OBJECT-TYPE
	SYNTAX INTEGER
	ACCESS read-write
	STATUS mandatory
	DESCRIPTION
	"This object specifies the time interval (in milliseconds) 
	between two routing cycles."
	DEFVAL { 0 }
	::= { parCmParms 9}

parCmParmsMaxUpdates OBJECT-TYPE
	SYNTAX INTEGER
	ACCESS read-write
	STATUS mandatory
	DESCRIPTION
	"This object specifies the maximum number of connection 
	management updates that are sent by the node in schedule.."
	DEFVAL { 10 }
	::= { parCmParms 10}

parCmParmsRerouteGroups OBJECT-TYPE
	SYNTAX INTEGER
	ACCESS read-write
	STATUS mandatory
	DESCRIPTION
	"This object specifies the total number of reroute groups."
	DEFVAL { 50 }
	::= { parCmParms 11}

parCmParmsMinRrGroupSize OBJECT-TYPE
	SYNTAX INTEGER
	ACCESS read-write
	STATUS mandatory
	DESCRIPTION
	"This object specifies the minimum size of reroute group in 
	Cell Load Units."
	DEFVAL { 0 }
	::= { parCmParms 12}

parCmParmsRrGroupInc OBJECT-TYPE
	SYNTAX INTEGER
	ACCESS 	read-write
	STATUS mandatory
	DESCRIPTION
	"This object specifies the increment of reroute group size 
	(in Cell Load Units) between adjacent groups."
	DEFVAL { 100 }
	::= { parCmParms 13}

parCmParmsCostBased OBJECT-TYPE
	SYNTAX TruthValue
	ACCESS read-write
	STATUS mandatory
	DESCRIPTION
	"This object can be configured to enable or disable cost 
	based routing feature. If the value of this object is True 
	the feature is enabled else it is disabled."
	DEFVAL { false }
	::= { parCmParms 14}

parCmParmsUseCache OBJECT-TYPE
	SYNTAX TruthValue
	ACCESS read-write
	STATUS mandatory
	DESCRIPTION
	"This object can be configured to enable or disable hop 
	based route selection from using cache of precomputed routes. 
	If the value of this object is True the feature is enabled 
	else it is disabled."
	DEFVAL { false }
	::= { parCmParms 15}
	
parCmParmsUseDelay OBJECT-TYPE
	SYNTAX TruthValue
	ACCESS read-write
	STATUS mandatory
	DESCRIPTION
	"This object can be configured to enable or disable cost 
	based route selection from considering end-to-end delay 
	associated with the routes. If the value of this object 
	is True the delay would be considered otherwise daley would 
	not be considered during routing of connection."
	DEFVAL { false }
	::= { parCmParms 16}

parCmParmMaxViaCons OBJECT-TYPE
	SYNTAX INTEGER (1..80000)
	ACCESS read-write
	STATUS mandatory
	DESCRIPTION
	"This object specifies the maximum number of via user connections 
	that can be routed through the node."
	DEFVAL { 50000 }
	::= { parCmParms 17}

parMnUpdtInterval OBJECT-TYPE
	SYNTAX INTEGER
	ACCESS read-write
	STATUS mandatory
	DESCRIPTION
	" This object specifies the timer interval (in seconds) for 
	the mandatory update state machine."
	DEFVAL { 15 }
	::= { parMnUpdt 1}

parMnUpdtNodesPerInt OBJECT-TYPE
	SYNTAX INTEGER
	ACCESS read-write
	STATUS mandatory
	DESCRIPTION
	"This object specifies the maximum number of nodes to which 
	mandatory updates can be sent per interval."
	DEFVAL { 20 }
	::= { parMnUpdt 2}

parMnUpdtBatchSend OBJECT-TYPE
	SYNTAX TruthValue
	ACCESS read-write
	STATUS mandatory
	DESCRIPTION 
	"This object specifies whether mandatory updates to any node 
	are sent one at a time or all in one go. If the value of this 
	object is True, all mandatory updates are sent to the node 
	simultaneously. If the value of this object is False, mandatory 
	updates are sent one at a time."
	DEFVAL { true }
	::= { parMnUpdt 3}

parSwFuncAbrVsvd OBJECT-TYPE
	SYNTAX TruthValue
	ACCESS read-write
	STATUS mandatory
	DESCRIPTION
	"This object enables/disables the ABR standard with VSVD. 
	The feature is enabled if the value of the object is True."
	DEFVAL { false }
	::= { parSwFunc 1}

parSwFuncNodeType OBJECT-TYPE
	SYNTAX INTEGER {
	routing (1),
	feeder (2)
	}
	ACCESS read-write
	STATUS mandatory
	DESCRIPTION
	"This object specifies whether the node is a routing node or 
	a feeder node. To configure the node from a routing(1) node 
	to feeder(2) node the node should be part of a single node network.
	To configure the node from feeder node to routing node, there 
	should be no feeder trunk attached to the node."
	DEFVAL { routing }
	::= { parSwFunc 2}

parOnOffBackgroundUpdt OBJECT-TYPE
	SYNTAX TruthValue
	ACCESS read-write
	STATUS mandatory
	DESCRIPTION 
	"This object can be used to enable or disable Background updates.
	If the value of the object is True Background updates are enabled; 
	otherwise they are disabled."
	DEFVAL { false }
	::= { parOnOff 1}

parOnOffDynamicBwAlloc OBJECT-TYPE
	SYNTAX TruthValue
	ACCESS read-write
	STATUS mandatory
	DESCRIPTION 
	"This object can be used to enable or disable Bandwidth state 
	machine. If the value of the object is True Bandwidth state 
	machine is enabled; otherwise it is disabled."
	DEFVAL { true }
	::= { parOnOff 2}

parOnOffCmUpdts OBJECT-TYPE
	SYNTAX TruthValue
	ACCESS read-write
	STATUS mandatory
	DESCRIPTION
	"This object can be used to enable or disable Connection 
	management updates. If the value of the object is True 
	Connection management updates are enabled; otherwise they 
	are disabled."
	DEFVAL { true }
	::= { parOnOff 3}

parOnOffRouting OBJECT-TYPE
	SYNTAX TruthValue
	ACCESS read-write
	STATUS mandatory
	DESCRIPTION 
	"This object can be used to enable or disable connection 
	routing. If the value of the object is True routing is enabled; 
	otherwise it is disabled."
	DEFVAL { true }
	::= { parOnOff 4}

parOnOffCommFailTest OBJECT-TYPE
	SYNTAX TruthValue
	ACCESS read-write
	STATUS mandatory
	DESCRIPTION
	"This object can be used to enable or disable Comm Fail Test.
	If the value of the object is True Comm Fail test is enabled; 
	otherwise it is disabled."
	DEFVAL { true }
	::= { parOnOff 5}

parOnOffDrtDelay OBJECT-TYPE
	SYNTAX TruthValue
	ACCESS read-write
	STATUS mandatory
	DESCRIPTION
	"This object can be used to enable or disable Deroute Delay feature.
	If the value of the object is True Derote delay feature is 
	enabled; otherwise it is disabled."
	DEFVAL { true }
	::= { parOnOff 6}

parOnOffRenumRec OBJECT-TYPE
	SYNTAX TruthValue
	ACCESS read-write
	STATUS mandatory
	DESCRIPTION
	"This object can be used to enable or disable Renumber 
	recovery feature. If the value of the object is True renumber 
	recovery feature is enabled; otherwise it is disabled."
	DEFVAL { false }
	::= { parOnOff 7}


parOnOffCommBreak OBJECT-TYPE
	SYNTAX TruthValue
	ACCESS read-write
	STATUS mandatory
	DESCRIPTION
	"This object can be used to enable or disable Comm Break Test.
	If the value of the object is True Comm Break Test feature is 
	enabled; otherwise it is disabled."
	DEFVAL { false }
	::= { parOnOff 8}


parSysParmsTsPacketAge OBJECT-TYPE
	SYNTAX INTEGER(1..64) 
	ACCESS read-write
	STATUS mandatory
	DESCRIPTION
	"Time Stamped packets older than this value (in milliseconds) 
	are discarded. This is a network wide parameter."
	DEFVAL { 64 }
	::= { parSysParms 1}

parSysParmsConnFail OBJECT-TYPE
	SYNTAX TruthValue
	ACCESS read-write
	STATUS mandatory
	DESCRIPTION
	"This object specifies whether the connections to a node 
	should be failed when comm fail is declared with the node.
	If the value of this object is True the connection will be 
	failed. This is a network wide parameter."
	DEFVAL {false}
	::= { parSysParms 2}

parSysParmsVcPollRate OBJECT-TYPE
	SYNTAX INTEGER
	ACCESS read-only
	STATUS mandatory
	DESCRIPTION 
	"This object specifies the rate at which VC statistics are 
	to be polled. This is a network wide parameter.
	For Portable AutoRoute statistic collections would be done by 
	platform software."
	::= { parSysParms 3}

parSysParmsMaxVDelay OBJECT-TYPE
	SYNTAX INTEGER
	ACCESS read-only
	STATUS mandatory
	DESCRIPTION "This object specifies the maximum delay for 
	voice connection with VAD enabled in milli-seconds. This is 
	a network wide parameter."
	::= { parSysParms 4}

parSysParmsMaxCDelay OBJECT-TYPE
	SYNTAX INTEGER
	ACCESS read-only
	STATUS mandatory
	DESCRIPTION 
	"This object specifies the maximum delay for ADPCM compressed 
	voice connection with VAD enabled in milli-seconds. This is 
	a network wide parameter."
	::= { parSysParms 5}

parSysParmsMaxDDelay OBJECT-TYPE
	SYNTAX INTEGER
	ACCESS read-only
	STATUS mandatory
	DESCRIPTION
	"This object specifies the maximum delay for data connection 
	in milli-seconds. This is a network wide parameter."
	::= { parSysParms 6}

parSysParmsMaxADelay OBJECT-TYPE
	SYNTAX INTEGER
	ACCESS read-only
	STATUS mandatory
	DESCRIPTION 
	"This object specifies the maximum delay for ADPCM compressed 
	voice connection in milli-seconds. This is a network wide parameter."
	::= { parSysParms 7}

parSysParmsMaxHsdDelay OBJECT-TYPE
	SYNTAX INTEGER
	ACCESS read-only
	STATUS mandatory
	DESCRIPTION 
	"This object specifies the maximum delay for High Speed data 
	connection in milli-seconds. This is a network wide parameter."
	::= { parSysParms 8}

parSysParmsDeEnable OBJECT-TYPE
	SYNTAX TruthValue
	ACCESS read-only
	STATUS 	mandatory
	DESCRIPTION
	"This object specifies whether DE bit of Frame Relay frames 
	can be modified. DE bit can be modified if the value of this 
	object is True. This is a network wide parameter."
	::= { parSysParms 9}

parSysParmsFrStandard OBJECT-TYPE
	SYNTAX TruthValue
	ACCESS read-only
	STATUS mandatory
	DESCRIPTION
	"This object specifies whether standard Frame Relay parameters, 
	Be and Bc, are to be used. If the value of this object is True, 
	standard parameters are used. This is a network wide parameter."
	::= { parSysParms 10}


parSysParmsDrtDelay OBJECT-TYPE
	SYNTAX TruthValue
	ACCESS read-write
	STATUS mandatory
	DESCRIPTION
	"This object specifies whether Deroute Delay feature is enabled.
	If the value of this object is True, the feature is enabled. 
	This is a network wide parameter."
	DEFVAL { true }
	::= { parSysParms 11}

parSysParmsInvLogAlarmThres OBJECT-TYPE
	SYNTAX INTEGER 
	ACCESS read-only
	STATUS mandatory
	DESCRIPTION
	"This object specifies the threshold for invalid login attempts 
	before triggering an alarm. If the value of this object is zero, 
	this feature is disabled. This is a network wide parameter."
        DEFVAL { 0 }
	::= { parSysParms 12}
	
parSysParmsMaxCdpVDelay OBJECT-TYPE
	SYNTAX INTEGER
	ACCESS read-only
	STATUS mandatory
	DESCRIPTION
	"This object specifies the maximum network delay for CDP to CDP 
	voice connection with VAD enabled in milli-seconds. This is a 
	network wide parameter."
	::= { parSysParms 13}

parSysParmsMaxCdpCDelay OBJECT-TYPE
	SYNTAX INTEGER
	ACCESS read-only
	STATUS mandatory
	DESCRIPTION
	"This object specifies the maximum network delay for CDP to CDP 
	ADPCM compressed voice connection with VAD enabled in milli-seconds. 
	This is a network wide parameter."
	::= { parSysParms 14}

parSysParmsMaxCdpDDelay OBJECT-TYPE
	SYNTAX INTEGER
	ACCESS read-only
	STATUS mandatory
	DESCRIPTION 
	"This object specifies the maximum network delay for CDP to CDP 
	data connection in milli-seconds. This is a network wide parameter."
	::= { parSysParms 15}

parSysParmsMaxCdpADelay OBJECT-TYPE
	SYNTAX INTEGER
	ACCESS read-only
	STATUS mandatory
	DESCRIPTION
	"This object specifies the maximum network delay for CDP to CDP 
	ADPCM compressed voice connection in milli-seconds. This is a 
	network wide parameter."
	::= { parSysParms 16}

parSysParmsMaxCdpHsdDelay OBJECT-TYPE
	SYNTAX INTEGER
	ACCESS read-only
	STATUS mandatory
	DESCRIPTION
	"This object specifies the maximum network delay for CDP to CDP 
	High Speed data connection in milli-seconds. This is a network 
	wide parameter."
	::= { parSysParms 17}

parSysParmsMaxIpcdpVDelay OBJECT-TYPE
	SYNTAX INTEGER
	ACCESS read-only
	STATUS mandatory
	DESCRIPTION
	"This object specifies the maximum local delay for CDP to CDP voice connection with VAD enabled in milli-seconds. This is a network wide parameter."
	::= { parSysParms 18}

parSysParmsMaxIpcdpCDelay OBJECT-TYPE
	SYNTAX INTEGER
	ACCESS read-only
	STATUS mandatory
	DESCRIPTION
	"This object specifies the maximum local delay for CDP to CDP ADPCM compressed voice connection with VAD enabled in milli-seconds. This is a network wide parameter."
	::= { parSysParms 19}

parSysParmsMaxIpcdpDDelay OBJECT-TYPE
	SYNTAX INTEGER
	ACCESS read-only
	STATUS mandatory
	DESCRIPTION
	"This object specifies the maximum local delay for CDP to CDP data connection in milli-seconds. This is a network wide parameter."
	::= { parSysParms 20}

parSysParmsMaxIpcdpADelay OBJECT-TYPE
	SYNTAX INTEGER
	ACCESS read-only
	STATUS mandatory
	DESCRIPTION
	"This object specifies the maximum local delay for CDP to CDP ADPCM compressed voice connection in milli-seconds. This is a network wide parameter."
	::= { parSysParms 21}

parSysParmsMaxIpcdpHsdDelay OBJECT-TYPE
	SYNTAX INTEGER
	ACCESS read-only
	STATUS mandatory
	DESCRIPTION
	"This object specifies the maximum local delay for CDP to CDP High Speed data connection in milli-seconds. This is a network wide parameter."
	::= { parSysParms 22}

parSysParmsMaxIphsdDelay OBJECT-TYPE
	SYNTAX INTEGER
	ACCESS read-only
	STATUS mandatory
	DESCRIPTION
	"This object specifies the maximum local delay for High Speed data connection in milli-seconds. This is a network wide parameter."
	::= { parSysParms 23}

parSysParmsFpdDeJitter OBJECT-TYPE
	SYNTAX INTEGER
	ACCESS read-only
	STATUS mandatory
	DESCRIPTION
	"This object specifies the jitter delay for Fast Pad. This is a network wide parameter."
	::= { parSysParms 24}

parNetParmCondInitialStgr OBJECT-TYPE
	SYNTAX INTEGER
	ACCESS read-write
	STATUS mandatory
	DESCRIPTION
	"This object specifies the initial pause time 
	(in milliseconds) per new node added on addition of node(s) 
	in the network before initiating conditional updates."
	DEFVAL { 5000 }
	::= { parNetworkingParms 1}

parNetParmCondPerNodeInterval OBJECT-TYPE
	SYNTAX INTEGER
	ACCESS read-write
	STATUS mandatory
	DESCRIPTION 
	"This object specifies the minimum interval (in milliseconds) 
	between sending of conditional updates to any two nodes."
	DEFVAL {30000}
	::= { parNetworkingParms 2}

parNetParmCbDelay OBJECT-TYPE
	SYNTAX INTEGER
	ACCESS read-write
	STATUS mandatory
	DESCRIPTION
	"This object specifies the minimum interval (in milliseconds) 
	between initiating comm break tests between any two nodes."
	DEFVAL { 30000 }
	::= { parNetworkingParms 3}
	

parNetParmCbOffset OBJECT-TYPE
	SYNTAX INTEGER
	ACCESS read-write
	STATUS mandatory
	DESCRIPTION
	"TBD."
	DEFVAL { 10 }
	::= { parNetworkingParms 4}
	
parNetParmMsgTimeout OBJECT-TYPE
	SYNTAX INTEGER
	ACCESS read-write
	STATUS mandatory
	DESCRIPTION 
	"This object specifies the timeout (in milliseconds) for 
	acknowledgment for control plane message sent to another node."
	DEFVAL { 1700 }
	::= { parNetworkingParms 5}

parNetParmMsgMaxTimeout OBJECT-TYPE
	SYNTAX INTEGER
	ACCESS read-write
	STATUS mandatory
	DESCRIPTION
	"This object specifies the maximum number of times a network 
	handler timeout waiting for acknowledgment for control plane 
	message sent to another node reachable through all terrestrial trunks."
	DEFVAL { 7 }
	::= { parNetworkingParms 6}
	
parNetParmMsgMaxTimeoutSat OBJECT-TYPE
	SYNTAX INTEGER
	ACCESS read-write
	STATUS mandatory
	DESCRIPTION
	"This object specifies the maximum number of times a network 
	handler timeout waiting for acknowledgment for control plane 
	message sent to another node reachable through all satellite trunks."
	DEFVAL { 6 }
	::= { parNetworkingParms 7}

parNetParmBlindMaxTimeout OBJECT-TYPE
	SYNTAX INTEGER
	ACCESS read-write
	STATUS mandatory
	DESCRIPTION 
	"This object specifies the maximum number of times a network 
	handler timeout waiting for acknowledgment for control plane 
	blind message sent to another node."
	DEFVAL { 4 }
	::= { parNetworkingParms 8}

parNetParmCbMaxTimeout OBJECT-TYPE
	SYNTAX INTEGER
	ACCESS read-write
	STATUS mandatory
	DESCRIPTION
	"This object specifies the maximum number of times a network 
	handler timeout waiting for acknowledgment for comm break test 
	message sent to another node."
	DEFVAL { 5 }
	::= { parNetworkingParms 9}

parNetParmCfTestInterval OBJECT-TYPE
	SYNTAX INTEGER
	ACCESS read-write
	STATUS mandatory
	DESCRIPTION
	"This object specifies the minimum time interval between the 
	comm fail tests for a trunk."
	DEFVAL { 10000 }
	::= { parNetworkingParms 10}

parNetParmCfTestMultiplier OBJECT-TYPE

	SYNTAX INTEGER 
	ACCESS 	read-write
	STATUS mandatory
	DESCRIPTION 
	"This object specifies the multiplier for the comm fail test 
	interval for good trunks, that is, trunks not in comm fail."
	DEFVAL { 3 }
	::= { parNetworkingParms 11}

parNetParmNetwWindowSz OBJECT-TYPE
	SYNTAX INTEGER
	ACCESS read-write
	STATUS mandatory
	DESCRIPTION 
	"This object specifies the window size for the network handler 
	for messages to any node. That is, the number of messages that 
	the network handler can send simultaneous to a node without 
	receiving the acknowledgment for them."
	DEFVAL { 1 }
	::= { parNetworkingParms 12}

parNetParmNetwLetWait OBJECT-TYPE
	SYNTAX INTEGER
	ACCESS read-write
	STATUS mandatory
	DESCRIPTION 
	"This object specifies the maximum interval (in milliseconds) 
	network handler waits for the letter (message) from the 
	processes running on its nodes before checking the received cells."
	DEFVAL { 50 }
	::= { parNetworkingParms 13}

parNetParmCfDelay OBJECT-TYPE
	SYNTAX INTEGER
	ACCESS read-write
	STATUS mandatory
	DESCRIPTION
	"TBD (in milliseconds)."
	DEFVAL { 60 }
	::= { parNetworkingParms 14}


parNetParmHighTxRate OBJECT-TYPE
	SYNTAX INTEGER
	ACCESS read-write
	STATUS mandatory
	DESCRIPTION
	"This object specifies the rate (in fast packets per second) 
	at which the network handler sends control plane message cells 
	to high performance nodes (High performance node are BPX and MGX)."
	DEFVAL { 2500 }
	::= { parNetworkingParms 15}

parNetParmLowTxRate OBJECT-TYPE
	SYNTAX INTEGER
	ACCESS read-write
	STATUS mandatory
	DESCRIPTION
	"This object specifies the rate (in fast packets per second) at 
	which the network handler sends control plane message cells to 
	low capacity nodes (Low capacity node are IPX and IGX)."
	DEFVAL { 500 }
	::= { parNetworkingParms 16}

parNetParmMaxNodeBlks OBJECT-TYPE
	SYNTAX INTEGER
	ACCESS read-write
	STATUS mandatory
	DESCRIPTION
	"This object specifies the maximum number of blocks, of size 
	256 bytes, that should be queued up for transmission to a node."
	DEFVAL { 3000 }
	::= { parNetworkingParms 17}

parNetParmTopoMsgSegSz OBJECT-TYPE
	SYNTAX INTEGER
	ACCESS read-write
	STATUS mandatory
	DESCRIPTION
	"This object specifies the maximum size (in bytes) of the 
	segment into which the topology message, sent during network 
	join, is divided."
	DEFVAL { 3570 }
	::= { parNetworkingParms 18}
-- ---------------------------------------------------------------------
--
-- Specific to cards in AXIS that support IMA functionality
-- At present only IMATM and AUSM-8p cards use this functionality
--
-- ---------------------------------------------------------------------


-- atm                  OBJECT IDENTIFIER ::= { basisServices 2 }
-- ausmPort             OBJECT IDENTIFIER ::= { atm 1 }
-- ausmPortCnf           OBJECT IDENTIFIER ::= { ausmPort 1 }
ausmPortCnfPortImaGrp   OBJECT IDENTIFIER ::= { ausmPortCnf 4 }
ausmPortImaGrpRestart   OBJECT IDENTIFIER ::= { ausmPortCnf 7 }

-- --------------------------------------------------------------------
--
--
--        IMA PORT CONFIG Group
--
--
-- --------------------------------------------------------------------


ausmPortCnfPortImaGrpTable    OBJECT-TYPE
    SYNTAX    SEQUENCE OF AusmPortCnfPortImaGrpEntry
    ACCESS    not-accessible
    STATUS    mandatory
    DESCRIPTION
        "The config table is for the IMA port (IMA group).
         There are 8 entries in all.
        "
    ::= { ausmPortCnfPortImaGrp 1 }


ausmPortCnfPortImaGrpEntry    OBJECT-TYPE
    SYNTAX    AusmPortCnfPortImaGrpEntry
    ACCESS    not-accessible
    STATUS    mandatory
    DESCRIPTION
        " An entry for every IMA port (total of 8 entries)
        "
    INDEX    { imaPortNum }
    ::= { ausmPortCnfPortImaGrpTable 1 }

AusmPortCnfPortImaGrpEntry ::=
    SEQUENCE {
        imaPortNum     
            INTEGER,
        imaPortEnable
            INTEGER,
		imaPortSpeed
			INTEGER,
		numLinksInImaGrp
			INTEGER,
		listOfLinksInImaGrp
			DisplayString,
		lcpCellsPeriodicity
			INTEGER,
		lcpDelayTolerance
			INTEGER,
		readPtrWrPtrDiff
			INTEGER,
		numRedundantLinks
			INTEGER,
		maxTolerableDiffDelay
			INTEGER,
		imaPortType
			INTEGER,
		axisImaGroupTxAvailCellRate
			INTEGER,
		axisImaGroupSymmetry
			INTEGER,	
		axisImaGroupMinNumRxLinks
			INTEGER,
		axisImaGroupNeTxClkMode
			INTEGER,	
		axisImaGroupAlphaValue
			INTEGER,
		axisImaGroupBetaValue
			INTEGER,
		axisImaGroupGammaValue
			INTEGER,
		axisImaGroupNumRxCfgLnks
			INTEGER,
		axisImaGroupTestLinkIfIndex
			INTEGER,
		axisImaGroupTestPattern
			INTEGER,
		axisImaGroupTestProcStatus
			INTEGER,
		axisImaGroupIntegrationUpTime
			INTEGER,
		axisImaGroupIntegrationDownTime
			INTEGER,
		axisImaGroupMinNumTxLinks
			INTEGER,
		axisImaGroupRxImaId
			INTEGER

    }

imaPortNum    OBJECT-TYPE
    SYNTAX    INTEGER (1..8) 
    ACCESS    read-only
    STATUS    mandatory
    DESCRIPTION
        "This is the logical port number.
        "
    ::= { ausmPortCnfPortImaGrpEntry 1}

imaPortEnable  OBJECT-TYPE        
    SYNTAX    INTEGER {
        delport(1),
        addport(2),
		addlinks(3),
		dellinks(4),
		modify(5)
        }
    ACCESS read-write
    STATUS  mandatory
    DESCRIPTION
        "This variable enables, disables or modifies the configuration of
		 the port
        1 - delport  (Disables the entire IMA group)
        2 - addport  (Enables the IMA group)
		3 - addlinks (Adds links to an existing IMA group)
		4 - dellinks (Deletes links from an existing IMA group)
		5 - modify   (Modifies parameters in an existing IMA group)

		An IMA group is synonymous with an IMA port.
		To configure an IMA port, the different lines in the IMA port
		should be enabled and then the IMA port should be added using
		the enumeration 'addport'.
		To delete an IMA port, the enumeration 'delport' should be used.
		To increase the bandwidth of an IMA group, the enumeration
		'addlinks' should be used.
		To decrease the bandwidth of an IMA group, the enumeration
		'dellinks' should be used.
		'modify' is used to change parameters other than links in the IMA
		 group
        "
	DEFVAL	{delport}
    ::= { ausmPortCnfPortImaGrpEntry 2 }

imaPortSpeed  OBJECT-TYPE
    SYNTAX  INTEGER (0..38328)
    ACCESS read-only
    STATUS  mandatory
    DESCRIPTION
    "The speed of the port in cells per second. This depends
	 on the nuber of links in the IMA group and the configuration of
	 the physical interface on each link (eg: T1, Normal E1, Clear E1 etc).
    "
    ::= { ausmPortCnfPortImaGrpEntry 3 }

numLinksInImaGrp OBJECT-TYPE
    SYNTAX  INTEGER (1..8)
    ACCESS read-only
    STATUS  mandatory
    DESCRIPTION
    "The number of links configured in the IMA group
     This is same as axisImaGroupNumTxCfgLnks in Forum Compliant Ima
    "
    ::= { ausmPortCnfPortImaGrpEntry 4 }

listOfLinksInImaGrp OBJECT-TYPE
    SYNTAX  DisplayString (SIZE (1..15))
    ACCESS read-write
    STATUS  mandatory
    DESCRIPTION
    "The list of links in the IMA group delimited by dots
    "
    ::= { ausmPortCnfPortImaGrpEntry 5 }

lcpCellsPeriodicity	OBJECT-TYPE
    SYNTAX  INTEGER (32..128)
    ACCESS read-only
    STATUS  mandatory
    DESCRIPTION
    "Period at wich LCP cells of the IMA protocol can be transmitted.
	 A value of 32 indicates that after 32 cells, one LCP cell is
	 transmitted on that link of the IMA group. Currently, the only
	 value supported is 128
     This has same meaning as axisImaGroupTxFrameLength in Forum
	 Compliant Ima. 
    "
	DEFVAL	{128}
    ::= { ausmPortCnfPortImaGrpEntry 6 }

lcpDelayTolerance	OBJECT-TYPE
    SYNTAX  INTEGER (1..1)
    ACCESS read-only
    STATUS  mandatory
    DESCRIPTION
    "The number of IMA frames for which an LCP cell on any link can
	 be missed before the IMA state machine should remove the link
	 from the IMA group. At present, this is hard-coded to 1 and is
	 not programmable.
	 Not supported in Forum Compliant Ima 
    "
	DEFVAL	{1}
    ::= { ausmPortCnfPortImaGrpEntry 7 }

readPtrWrPtrDiff	OBJECT-TYPE
    SYNTAX  INTEGER (4..12)
    ACCESS read-write
    STATUS  mandatory
    DESCRIPTION
    "The difference between the read and write pointer of a link in
	 the common cell buffer. A lower value reduces the latency in the
	 common cell buffer but also increases the probability of an IMA
	 group being stalled for a cell-time due to a slower link in the
	 IMA group
	 Not supported in Forum Compliant Ima.
    "
	DEFVAL	{4}
    ::= { ausmPortCnfPortImaGrpEntry 8 }

numRedundantLinks	OBJECT-TYPE
    SYNTAX  INTEGER (0..7)
    ACCESS read-write
    STATUS  mandatory
    DESCRIPTION
    "The degree of resiliency in the IMA group. This indicates the number
	 of links the system can lose from this IMA group without bringing it
	 down. By default, the system can tolerate {configured #links - 1}
	 to go down.
	 Not supported in Forum Compliant Ima.
    "
    ::= { ausmPortCnfPortImaGrpEntry 9 }

maxTolerableDiffDelay	OBJECT-TYPE
	SYNTAX	INTEGER (0..275)
	ACCESS	read-write
	STATUS	mandatory
	DESCRIPTION
	"This indicates the maximum tolerable differential delay in milliseconds
	 between the various links in the IMA group. The default value is
	 variable and depends on the type of card with IMA feature:
	 For AUSM-8p:
	 200 milliseconds for an IMA group consisting of E1 lines
	 275 milliseconds for an IMA group consisting of T1 lines.
	 For IMATM:
	 50 milliseconds for an IMA group consisting of either T1/E1 lines.
	 This is same as axisImaGroupDiffDelayMax of Forum Compliant Ima.
	"
	::= { ausmPortCnfPortImaGrpEntry 10 }

imaPortType	OBJECT-TYPE
	SYNTAX	INTEGER {
		uni(1),
		nni(2),
		sti(3),
		vpTrkUni (4)
	}
	ACCESS	read-write
	STATUS	mandatory
	DESCRIPTION
	"This indicates whether the port is to be configured for UNI/NNI/STI
	 mode. STI mode is supported only in the case of IMATM.
	 vpTrkUni should be used only in IMATM when virtual trunks are
	 passing through IMATM (i.e. the cell format is UNI but ForeSight
	 information is carried in the lower 16 bits)
	"
	::= { ausmPortCnfPortImaGrpEntry 11 }

axisImaGroupTxAvailCellRate  OBJECT-TYPE
    SYNTAX INTEGER(0..38330)
    ACCESS read-only
    STATUS  mandatory
    DESCRIPTION
    "The current cell rate(truncated value in cells per second) provided by 
    the IMA group in the transmit direction, considering all the transmit 
    links in the Active state.

	The generic formula for the link rate with N links active is :

	N * link Rate * (M-1)/M * (2048/2049), where M is the Ima Frame length.
	
	Suppose M = 128, then following are the link rates :

    In case of T1,for 8 lines the value is 28728 cells/sec.
	
    In case of Normal E1(for 8 Lines), the value is 35920 cells/sec.
	
    In case of Clear E1(for 8 Lines),the value is 38312 cells/sec.
    "
    ::= { ausmPortCnfPortImaGrpEntry 12}

axisImaGroupSymmetry  OBJECT-TYPE
	SYNTAX  INTEGER {
	  symmetricOperation(1),
	  asymmetricOperation(2),
	  asymmetriConfiguration(3) }
	ACCESS	read-write
	STATUS	mandatory
	DESCRIPTION
	"Symmetry of the IMA group.
	 AsymmetricOperation,AsymmetricConfiguration are not supported.
	"
	DEFVAL	{symmetricOperation}
	::= { ausmPortCnfPortImaGrpEntry 13}

axisImaGroupMinNumRxLinks OBJECT-TYPE
	SYNTAX	INTEGER(1..8)
	ACCESS	read-write
	STATUS	mandatory
	DESCRIPTION
	"Minimum number of receive links required to be active for the IMA
	 group to be in the Up state.At present since only symmetric 
	configuration is supported,this should be equal to 
	axisImaGroupMinNumTxLinks.
	"	
	::= { ausmPortCnfPortImaGrpEntry 14}

axisImaGroupNeTxClkMode OBJECT-TYPE
	SYNTAX  INTEGER  {
		ctc(1),
		itc(2) }
	ACCESS	read-write
	STATUS	mandatory
	DESCRIPTION
	"Transmit clocking mode used by the near-end IMA group.
	 ITC is not available in ausm8(B). Only default value (ctc) is supported.
	"
	DEFVAL { ctc }
	::= { ausmPortCnfPortImaGrpEntry 15}

axisImaGroupAlphaValue  OBJECT-TYPE
	SYNTAX	INTEGER (1..2)
	ACCESS	read-only
	STATUS	mandatory
	DESCRIPTION
	"This indicates the 'alpha' value used  to  specify  the number of
	 consecutive  invalid  ICP cells to be detected before moving to the 
	 IMA HUNT state.
	 Only default values are supported.
	"
	DEFVAL { 2 }
	::= { ausmPortCnfPortImaGrpEntry 16}

axisImaGroupBetaValue  OBJECT-TYPE
	SYNTAX	INTEGER (1..5)
	ACCESS	read-only
	STATUS	mandatory
	DESCRIPTION
	"This indicates the 'beta'value used to specify the number of 
	consecutive errored ICP cells to be detected before moving to the IMA 
	HUNT state.
	 Only default values are supported.
	"
	DEFVAL { 2 }
	::= { ausmPortCnfPortImaGrpEntry 17}

axisImaGroupGammaValue  OBJECT-TYPE
	SYNTAX	INTEGER (1..5)
	ACCESS	read-only
	STATUS	mandatory
	DESCRIPTION
	"This indicates the 'gamma' value used to specify the number of 
	 consecutive valid ICP cells to be detected before moving to the IMA
	 SYNC state from the PRESYNC state.
	 Only default values are supported.
	"
	DEFVAL	{ 1 }	
	::= { ausmPortCnfPortImaGrpEntry 18}

axisImaGroupNumRxCfgLnks OBJECT-TYPE
	SYNTAX	INTEGER
	ACCESS	read-only
	STATUS	mandatory
	DESCRIPTION
	"The Number of links that are configured to receive in this IMA
	 Group.
	"
    ::= { ausmPortCnfPortImaGrpEntry 19}



-- Test pattern procedure control objects.

axisImaGroupTestLinkIfIndex  OBJECT-TYPE
	SYNTAX	INTEGER	
	ACCESS	read-write
	STATUS	mandatory
	DESCRIPTION
	"This object is used to designate an interface as the test link.
	 A value of -1 specifies that the implementation may choose the
	 test link. In this case ,the implementation may also choose the 
	 value of axisImaGroupTestPattern.
	"
	DEFVAL { -1 }
	::= { ausmPortCnfPortImaGrpEntry 20}

axisImaGroupTestPattern  OBJECT-TYPE 
	SYNTAX	INTEGER
	ACCESS	read-write
	STATUS	mandatory
	DESCRIPTION
	"The value of this object is used to specify the test pattern in an 
	 IMA group loopback operation. A value in the range 0 to 255 designates
	 a specific pattern. A value of -1 specifies that the implementation may 
	 choose the value. In this case,the implementation may also choose the 
	 value of 'axisImaGroupTestLinkIfIndex.
	"
	DEFVAL	{ -1 }

	::= { ausmPortCnfPortImaGrpEntry 21}

axisImaGroupTestProcStatus OBJECT-TYPE
	SYNTAX 	INTEGER	{
		disabled(1),
		operating(2),
		linkfail(3) }
	ACCESS	read-write
	STATUS	mandatory
	DESCRIPTION	
	"This object is used to enable or disable the Test Pattern Proceudre,and 
	 to note whether at least one link failed the test.
	 The test is started by setting operating(2) status.If any link should
	 fail the test ,the IMA will set the status to linkfail(3).The linkfail(3)
	 state will persist until either the disabled(1) state is set or until no
	 instance of imaLinkTestProcStatus has the value linkfail(3).
	
	 Only the values disabled(1) and operating(2) may be written. 
	 Writing the opersting(2) value will not cause clearing of the 
	 linkfail(3) state.
	"
	DEFVAL	{ disabled }
	::= { ausmPortCnfPortImaGrpEntry 22}

axisImaGroupIntegrationUpTime OBJECT-TYPE
	SYNTAX	INTEGER	 (100..100000)
	ACCESS	read-write
	STATUS	mandatory
	DESCRIPTION
	"	
	Integration UP time for alarm integration.Persisting checking time to
	enter a failure alarm condition,in case of LIF,LODS,RFI-IMA fault 
	failure alarms.
	Time in Milli Seconds.
	"
	DEFVAL {2500}
	::= { ausmPortCnfPortImaGrpEntry 23}
	
axisImaGroupIntegrationDownTime	OBJECT-TYPE
	SYNTAX 	INTEGER	 (100..400000)
	ACCESS	read-write
	STATUS	mandatory
	DESCRIPTION	
	"
	Integration DOWN time for alarm integration.Persisting clearing time to
	exit the LIF,LODS,RFI-IMA failure alarm conditions.
	Time in Milli seconds.
	"
	DEFVAL {10000}
	::= { ausmPortCnfPortImaGrpEntry 24}


axisImaGroupMinNumTxLinks  OBJECT-TYPE
	SYNTAX	INTEGER(1..8)
	ACCESS	read-write
	STATUS	mandatory
	DESCRIPTION
	"Minimum number of transmit links required to be active for the IMA
	 group to be in the Up state.Eventhough the range is 1..8,this value
	 should be <= maximum number of configured links in IMA group. 
	"	
	::= { ausmPortCnfPortImaGrpEntry 25}

axisImaGroupRxImaId  OBJECT-TYPE
	SYNTAX	INTEGER(0..255)
	ACCESS	read-only
	STATUS	mandatory
	DESCRIPTION
	"The Ima id used by the far end.
	"	
	::= { ausmPortCnfPortImaGrpEntry 26}


-- Scalars in the ausmPortCnfPortImaGrp

nextPortNumAvailable	OBJECT-TYPE
	SYNTAX	INTEGER(1..8)
	ACCESS	read-only
	STATUS	mandatory
	DESCRIPTION
	"Indicates the next logical port number (i.e. either ATM T1/E1 UNI
	 or IMA port) that is available
	"
	::= { ausmPortCnfPortImaGrp 2 }

-- --------------------------------------------------------------
-- End of ausmPortCnfPortImaGrp

-- --------------------------------------------------------------------
--
--
--        IMA PORT RESTART Group
--
--
-- --------------------------------------------------------------------


ausmPortImaGrpRestartTable    OBJECT-TYPE
    SYNTAX    SEQUENCE OF AusmPortImaGrpRestartEntry
    ACCESS    not-accessible
    STATUS    mandatory
    DESCRIPTION
        "The restart table is for the IMA port (IMA group).
         There are 8 entries in all.
        "
    ::= { ausmPortImaGrpRestart 1 }


ausmPortImaGrpRestartEntry    OBJECT-TYPE
    SYNTAX    AusmPortImaGrpRestartEntry
    ACCESS    not-accessible
    STATUS    mandatory
    DESCRIPTION
        " An entry for every IMA port (total of 8 entries)
        "
    INDEX    { axisImaGroupimaPortNum }
    ::= { ausmPortImaGrpRestartTable 1 }

AusmPortImaGrpRestartEntry ::=
    SEQUENCE {
        axisImaGroupimaPortNum     
            INTEGER,
		axisImaGroupRestartImaGrp
			INTEGER
    }

axisImaGroupimaPortNum    OBJECT-TYPE
    SYNTAX    INTEGER (1..8) 
    ACCESS    read-only
    STATUS    mandatory
    DESCRIPTION
        "This is the logical port number.
        "
    ::= { ausmPortImaGrpRestartEntry 1}

axisImaGroupRestartImaGrp OBJECT-TYPE
	SYNTAX	INTEGER {
		noAction(1),
		persistent(2),
		dorelearn(3)
	}
	ACCESS	read-write
	STATUS	mandatory
	DESCRIPTION
	"This variable restarts the Ima grp. We have the option of
	 relearning the Ima id or retaining the stored ID.
	"
	::= { ausmPortImaGrpRestartEntry 2}


-- --------------------------------------------------------------
-- End of ausmPortImaGrpRestart

-- atm               OBJECT IDENTIFIER ::= { basisServices 2 }
-- ausmPort           OBJECT IDENTIFIER ::= { atm 1 }
-- ausmPortCnt        OBJECT IDENTIFIER ::= { ausmPort 3 }
ausmPortCntPortImaGrp OBJECT IDENTIFIER ::= { ausmPortCnt 3}

-- --------------------------------------------------------------------
--
--
--        AUSM-8p/IMATM PER IMA GROUP, IMA COUNTER Group
--
--
-- --------------------------------------------------------------------


ausmPortCntPortImaGrpTable    OBJECT-TYPE
    SYNTAX    SEQUENCE OF AusmPortCntPortImaGrpEntry
    ACCESS    not-accessible
    STATUS    mandatory
    DESCRIPTION
        "The counter table is for the IMA groups (8 possible entries)
        "
    ::= { ausmPortCntPortImaGrp 1 }


ausmPortCntPortImaGrpEntry    OBJECT-TYPE
    SYNTAX    AusmPortCntPortImaGrpEntry
    ACCESS    not-accessible
    STATUS    mandatory
    DESCRIPTION
        " An entry for the IMA group
        "
    INDEX    { imaCntPortNum }
    ::= { ausmPortCntPortImaGrpTable 1 }

AusmPortCntPortImaGrpEntry ::=
    SEQUENCE {
        imaCntPortNum
            INTEGER,
		rcvAcpCells
			Counter,
		rcvAcpErrCells
			Counter,
		xmtAcpCells
			Counter,
		xmtAcpCellsMissed
			Counter,
		imaGrpRcvHecErrCount
			Counter,
		imaGrpRcvHecErrSecCount
			Counter,
		imaGrpRcvHecErrSESecCount
			Counter,
        imaCntClrButton
            INTEGER,
		axisImaGroupRunningSecs
			INTEGER,
		axisImaGroupUnavailSecs
			INTEGER ,
		axisImaGroupNeNumFailures 
			INTEGER ,
		axisImaGroupFeNumFailures
			INTEGER 
    }

imaCntPortNum    OBJECT-TYPE
    SYNTAX  INTEGER (1..8) 
    ACCESS  read-only
    STATUS  mandatory
    DESCRIPTION
        "This is the logical port number.
		 This object does not have any default value.
        "
    ::= { ausmPortCntPortImaGrpEntry 1}

rcvAcpCells	OBJECT-TYPE
	SYNTAX	Counter
    ACCESS  read-only
    STATUS  mandatory
    DESCRIPTION
        "This is the number of ICP cells received.
		 This object does not have any default value.
        "
    ::= { ausmPortCntPortImaGrpEntry 2}

rcvAcpErrCells	OBJECT-TYPE
	SYNTAX	Counter
    ACCESS  read-only
    STATUS  mandatory
    DESCRIPTION
        "This is the number of errored ICP cells on this IMA
		 group.
		 This object does not have any default value.
        "
    ::= { ausmPortCntPortImaGrpEntry 3}

xmtAcpCells	OBJECT-TYPE
	SYNTAX	Counter
    ACCESS  read-only
    STATUS  mandatory
    DESCRIPTION
        "This is the number of ACP cells transmitted on this IMA group.
		 This object does not have any default value.
	 	Not supported in Forum Compliant Ima.
        "
    ::= { ausmPortCntPortImaGrpEntry 4}

xmtAcpCellsMissed	OBJECT-TYPE
	SYNTAX	Counter
    ACCESS  read-only
    STATUS  mandatory
    DESCRIPTION
        "This is the number of ACP cells that could not be transmitted on
		 this IMA group due to lack of resources (buffers).
		 This object does not have any default value.
	 	Not supported in Forum Compliant Ima.
        "
    ::= { ausmPortCntPortImaGrpEntry 5}

imaGrpRcvHecErrCount	OBJECT-TYPE
	SYNTAX	Counter
    ACCESS  read-only
    STATUS  mandatory
    DESCRIPTION
        "This is the number of HEC errored cells received on all the links
		 currently in the IMA group
		 This object does not have any default value.
        "
    ::= { ausmPortCntPortImaGrpEntry 6}

imaGrpRcvHecErrSecCount	OBJECT-TYPE
	SYNTAX	Counter
    ACCESS  read-only
    STATUS  mandatory
    DESCRIPTION
        "This is the number of HEC errored seconds for the IMA group--
		 that is the number of seconds in which at least one link in the
		 IMA group experienced a HEC error
		 This object does not have any default value.
        "
    ::= { ausmPortCntPortImaGrpEntry 7}

imaGrpRcvHecErrSESecCount	OBJECT-TYPE
	SYNTAX	Counter
    ACCESS  read-only
    STATUS  mandatory
    DESCRIPTION
        "This is the number of severely errored seconds received on all the
		 links currently in the IMA group. A severely errored second
		 for an IMA group is defined if the following condn is true:
		 if (sigma (number of HEC errors of all links in IMA group) >
			 (HEC_SE_COUNT * nlinks)) where HEC_SE_COUNT is defined as 10
		 This object does not have any default value.
        "
    ::= { ausmPortCntPortImaGrpEntry 8}

-- Clear Button
imaCntClrButton    OBJECT-TYPE
    SYNTAX  INTEGER {
    noAction (1),
    resetCounters (2)
    }
    ACCESS  read-write
    STATUS  mandatory
    DESCRIPTION
        "writing a value of 2 resets all the counters
		 This object does not have any default value.
        "
    ::= { ausmPortCntPortImaGrpEntry 9 }

axisImaGroupRunningSecs	OBJECT-TYPE
	SYNTAX	INTEGER 
	ACCESS	read-only
	STATUS	mandatory	
	DESCRIPTION
		"The amount of time(in seconds) since this IMA group has been 
		 in opeartion(UP or DOWN.)
		"
    ::= { ausmPortCntPortImaGrpEntry 10 }

axisImaGroupUnavailSecs	OBJECT-TYPE
	SYNTAX	INTEGER 
	ACCESS	read-only	
	STATUS	mandatory
	DESCRIPTION
		"Count of one second intervals where IMA group traffic state
		 machine is down.
		"
    ::= { ausmPortCntPortImaGrpEntry 11 }

axisImaGroupNeNumFailures	OBJECT-TYPE
	SYNTAX	INTEGER 
	ACCESS	read-only	
	STATUS	mandatory
	DESCRIPTION
		"The number of times a near-end group failure(Config-abort,
		 Insufficient-Links) has been reported since power-up or reboot.
		"
    ::= { ausmPortCntPortImaGrpEntry 12 }

axisImaGroupFeNumFailures	OBJECT-TYPE
	SYNTAX	INTEGER 
	ACCESS	read-only	
	STATUS	mandatory
	DESCRIPTION
		"The number of times a far-end group failure(config-abort-FE,
		Insufficient-links-FE,Blocked-FE) has been reported since power-up
		or reboot.
		"
    ::= { ausmPortCntPortImaGrpEntry 13 }
 


-- --------------------------------------------------------------------
-- End of ausmPortCntPortImaGrp

-- atm             OBJECT IDENTIFIER ::= { basisServices 2 }
-- ausmPort         OBJECT IDENTIFIER ::= { atm 1 }
ausmPortStateImaGrp OBJECT IDENTIFIER ::= { ausmPort 4 }

-- --------------------------------------------------------------------
--
--
--        IMA Group STATE Group
--
--
-- --------------------------------------------------------------------


ausmPortStateImaGrpTable    OBJECT-TYPE
    SYNTAX    SEQUENCE OF AusmPortStateImaGrpEntry
    ACCESS    not-accessible
    STATUS    mandatory
    DESCRIPTION
        "The state table for the IMA port interface:
         there are 8 entries for the 8 (maximum possible) IMA groups
        "
    ::= { ausmPortStateImaGrp 1 }


ausmPortStateImaGrpEntry    OBJECT-TYPE
    SYNTAX    AusmPortStateImaGrpEntry
    ACCESS    not-accessible
    STATUS    mandatory
    DESCRIPTION
        " An entry for every IMA group
        "
    INDEX    { imaStatePortNum }
    ::= { ausmPortStateImaGrpTable 1 }

AusmPortStateImaGrpEntry ::=
    SEQUENCE {
        imaStatePortNum     
            INTEGER,
		imaPortState
			INTEGER,
		numLinksPresentInImaGroup
			INTEGER,
		listLinksPresentInImaGroup
			DisplayString,
		remoteImaId
			INTEGER,
		locImaId
			INTEGER,
		imaArbitrationWinner
			INTEGER,
		imaObsDiffDelay
            INTEGER,
		imaPortOversubscribed
			INTEGER,
		imaPortIngrPercentUtil
			INTEGER,
		imaPortEgrPercentUtil
			INTEGER,
		axisImaGroupRxAvailCellRate
			INTEGER,
		axisImaGroupFeState
			INTEGER,
		axisImaGroupFailureStatus
			INTEGER,
		axisImaGroupFeTxClkMode
			INTEGER,
		axisImaGroupTxTimingRefLink	
			INTEGER,
		axisImaGroupRxTimingRefLink
			INTEGER,
		axisImaGroupLastChange
			OCTET STRING,		
		axisImaGroupRxFrameLength
			INTEGER,
		axisImaGroupLeastDelayLink
			INTEGER,
		axisImaGroupNumRxActLnks
			INTEGER,
		axisImaGroupNeState
			INTEGER
    }

imaStatePortNum     OBJECT-TYPE
    SYNTAX    INTEGER (1..8) 
    ACCESS    read-only
    STATUS    mandatory
    DESCRIPTION
        "This is the logical port number
			This object does not have any default value
        "
    ::= { ausmPortStateImaGrpEntry 1}

imaPortState	OBJECT-TYPE
	SYNTAX	INTEGER {
		unconfigured (1),
		active (2),
		bandwidthChanged (3),
		failedDueToAcpTimeout (4),
		failedDueToMajorAlmonImaGrp (5),
		failedDueToImaSigFailure (6),
		failedDueToBadDiffDelay (7),
		failedDueToArbConflict (8),
		receivingLoamAis(9),
		receivingLoamRdi(10),
		failedDueToIlmiSignalling(20)
	}
	ACCESS	read-only
	STATUS	mandatory
	DESCRIPTION
		"Indicates the state of the IMA port. The following error
		 conditions are currently reported:
		 1 - Unconfigured state
		 2 - Active state
		 3 - Bandwidth changed due to addition/deletion of links. The
		     addition/deletion can be triggered by either end
		 4 - FailedDueToACPTimeout (indicates that a timeout occurred due
			 to non-arrival of an ACP cell)
		 5 - FailedDueToMajorAlarmOnIMAGroup (issued when the bandwidth
			 of an IMA group falls below a certain threshold due to loss
			 of links from an IMA group)
		 6 - FailedDueToImaSigFailure (this indicates configuration
			 mismatch or non-arrival of LCP cells during set up of
			 an IMA group)
		 7 - FailedDueToBadDiffDelay (indicates that the differential
			 delay exceeded the maximum threshold)
		 8 - FailedDueToArbConflict (indicates that the IMA-ID could
			 not be resolved between the 2 ends of the IMA pipe)
		 9 - Receiving Local OAM AIS from peer IMA node (valid only for
			 network modules)
		 10- Receiving LOAM RDI from peer IMA node (valud only for
			 network modules)
		 20- Failed due to ILMI signalling failure
		 This object does not have any default value
		"
    ::= { ausmPortStateImaGrpEntry 2}

numLinksPresentInImaGroup	OBJECT-TYPE
	SYNTAX	INTEGER(0..8)
	ACCESS	read-only
	STATUS	mandatory
	DESCRIPTION
		"Indicates the number of links that are currently present in
		 the IMA group.
		 This object does not have any default value
		 Same as axisImaGroupNumTxActLnks in Forum Compliant Ima.
		"
    ::= { ausmPortStateImaGrpEntry 3}

listLinksPresentInImaGroup	OBJECT-TYPE
	SYNTAX	DisplayString (SIZE (1..15))
	ACCESS	read-only
	STATUS	mandatory
	DESCRIPTION
		"Indicates the list of links currently present in the IMA
		 group. Different links in the IMA group are delimited by
		 dots. The position of each link in the displayed string indicates
		 the relative order of the links in the round-robin (multiplexing
		 order)
		 This object does not have any default value
		"
    ::= { ausmPortStateImaGrpEntry 4}
	

remoteImaId	OBJECT-TYPE
	SYNTAX	INTEGER(1..255)
	ACCESS	read-only
	STATUS	mandatory
	DESCRIPTION
		"Indicates the IMA-ID in use at the remote end when sending
		 LCP/ACP cells.
         Same as axisImaGroupRxImaId in Forum Compliant Ima .
		 This object does not have any default value
		"
    ::= { ausmPortStateImaGrpEntry 5}

locImaId	OBJECT-TYPE
	SYNTAX	INTEGER(1..255)
	ACCESS	read-only
	STATUS	mandatory
	DESCRIPTION
		"Indicates the IMA-ID in use at the local end when sending
		 LCP/ACP cells.
		 This is same as axisImaGroupTxImaId in Forum Compliant Ima
		 This object does not have any default value
		"
    ::= { ausmPortStateImaGrpEntry 6}

imaArbitrationWinner	OBJECT-TYPE
	SYNTAX	INTEGER	{
		isUnknown (1),
		isWinner (2),
		isLoser (3)
	}
	ACCESS	read-only
	STATUS	mandatory
	DESCRIPTION
		"Result of arbitration between the two ends of the IMA pipe.
		This object does not have any default value
		Retaining for the backward compatibility.
		Not supported in Forum Compliant Ima.
		"
    ::= { ausmPortStateImaGrpEntry 7}

imaObsDiffDelay	OBJECT-TYPE
	SYNTAX	INTEGER
	ACCESS	read-only
	STATUS	mandatory
	DESCRIPTION
		"The observed differential delay in milliseconds between the
		 different physical links in the IMA group
	 	This object does not have any default value
         Same as axisImaGroupDiffDelayMaxObs in Forum Compliant Ima.
		"
    ::= { ausmPortStateImaGrpEntry 8}

imaPortOversubscribed OBJECT-TYPE
	SYNTAX	INTEGER {
		false (1),
		true (2)
		}
	ACCESS	read-only
	STATUS	mandatory
	DESCRIPTION
		"This variable indicates whether the port is over-subscribed or
		  not
		  This object does not have any default value
		"
    ::= { ausmPortStateImaGrpEntry 9}

imaPortIngrPercentUtil OBJECT-TYPE
	SYNTAX	INTEGER (0..1000)
	ACCESS	read-only
	STATUS	mandatory
	DESCRIPTION
		"Percent Utilization of the IMA Port in the Ingress direction
		This object does not have any default value
		"
    ::= { ausmPortStateImaGrpEntry 10}

imaPortEgrPercentUtil OBJECT-TYPE
	SYNTAX	INTEGER (0..1000)
	ACCESS	read-only
	STATUS	mandatory
	DESCRIPTION
		"Percent Utilization of the IMA Port in the Egress direction
		 This object does not have any default value
		"
    ::= { ausmPortStateImaGrpEntry 11}

axisImaGroupRxAvailCellRate	OBJECT-TYPE
	SYNTAX	INTEGER 
	ACCESS	read-only
	STATUS	mandatory
	DESCRIPTION
		"The current cell-rate (truncated value in cells per second)
		 provided by this IMA group in the receive direction,considering
		 all the receive links in the active state.
		"
    ::= { ausmPortStateImaGrpEntry 12}

axisImaGroupFeState	OBJECT-TYPE
	SYNTAX  INTEGER {
		notConfigured(1),
		startUp(2),
		startUpAck(3),
		configAbortUnsupportedM(4),
		configAbortIncompatibleSymmetry(5),
		configAbortOther(6),
		insufficientLinks(7),
		blocked(8),
		operational(9) }
	ACCESS	read-only
	STATUS	mandatory
	DESCRIPTION
		"The current operational state of the far-end IMA group state
	 	 machine
		
		1) notConfigured : The Group doesn't exist.This is the GSM 
				   initial state.
		2) startUp	 : On UM configuring the IMA group,GSM comes to
				   this state. 
		3) startUpAck  	 : On getting the Start-up-ack from FE(this info
				   from received ICP cell. i.e. FE accepting the 			  	   proposed group parameters by this END.), 
				   GSM goes to this state.
		4) configAbortUnsupportedM : This state is entered when FE is 
						not accepting the parameter M.
		5) configAbortIncompatibleSymmetry : When Group symmetry is not
			supported by the FE,this group is entered.
		6) configAbortOther : If any of the other group parameters are
			not supported by the FE,then this state is entered.
		7) insufficientLinks : On getting one of the following events 
			from FE, when GSM is in startUpAck state,GSM moves to 
			insufficientLinks state.
			evens : 1) Start-up-ack 2) insufficient links
				3) Blocked or operational
		8) blocked : For to maintenance purpose,if group is blcoked
			(inhibited by UM),GSM goes to this state. 
		9) operational : When the group has sufficient links in both Tx 			and Rx directions GSM goes to this state.
		"
    ::= { ausmPortStateImaGrpEntry 13}

axisImaGroupFailureStatus	OBJECT-TYPE
	SYNTAX  INTEGER {
		noFailure(1),   
		startUpNe(2),
		startUpFe(3),
		invalidMValueNe(4),
		invalidMValueFe(5),
		failedAssymetricNe(6),
		failedAssymetricFe(7),
		insufficientLinksNe(8),
		insufficientLinksFe(9),
		blockedNe(10),
		blockedFe(11),
		otherFailure(12) }
	ACCESS	read-only
	STATUS	mandatory
	DESCRIPTION
		"The current failure status of the IMA group(the reason why
		 the GTSM is in the DOWN state.
		1) noFailure	: The group is UP. 
		2) startUpNe	: When the NE GSM is in startUp state.
		3) startUpFe	: When the FE GSM is in startUp state.
		4) invalidMValueNe : If FE doesn't support M value this end 
		5) invalidMValueFe : When the FE M value is not supported by NE.
		6) failedAssymetricNe : If FE doesn't support Assymetric 
			operation of the NE.
		7) failedAssymetricFe : When the FE assymetry is not supported 
			by the NE.
		8) insufficientLinksNe: When the NE is in insufficient links 
							state
		9) insufficientLinksFe: If the FE is in insufficient links 
				state and if that message is conveyed to this
				end by ICP cell. 
		10) blockedNe	: If the GSM is in blocked state.
		11) blockedFe	: If the FE is in blocked state.
		12) otherFailure: Start-up-ack and others.
		"
    ::= { ausmPortStateImaGrpEntry 14}

axisImaGroupFeTxClkMode	OBJECT-TYPE
	SYNTAX	INTEGER {
		ctc(1),
		itc(2) }
	ACCESS	read-only
	STATUS	mandatory
	DESCRIPTION
		"Transmit clocking mode used by the far-end IMA group."
    ::= { ausmPortStateImaGrpEntry 15}

axisImaGroupTxTimingRefLink  OBJECT-TYPE
	SYNTAX	INTEGER	
	ACCESS	read-only
	STATUS	mandatory
	DESCRIPTION
	"The IfIndex of the transmit timing reference link to be used by the
	 near-end for IMA data cell clock recovery from the ATM layer.
	"
    ::= { ausmPortStateImaGrpEntry 16}

axisImaGroupRxTimingRefLink	OBJECT-TYPE
	SYNTAX	INTEGER	
	ACCESS	read-only
	STATUS	mandatory
	DESCRIPTION
	"The IfIndex of the receive timing reference link to be used by 
	 the near-end for IMA data cell clock recovery toward the ATM layer.
	"
    ::= { ausmPortStateImaGrpEntry 17}

axisImaGroupLastChange	OBJECT-TYPE
	SYNTAX	OCTET STRING( SIZE (11) )	
	ACCESS	read-only
	STATUS	mandatory		
	DESCRIPTION
		"The time-of-day the IMA group last changed operational state(
		 i.e. value of axisImaGroupNeState changed.)

			SPLAY-HINT 2d-1d-1d,1d:1d:1d.1d,1a1d:1d 

			field  octets  contents 		range
			-----  ------  -------- 		-----
			1      1-2   year      			0..65536
			2       3    month     			1..12
			3       4    day       			1..31
			4       5    hour      			0..23
			5       6    minutes   			0..59
			6       7    seconds   			0..60
				(use 60 for leap-second)
			7       8    deci-seconds 		0..9
			8       9    direction from UTC	 	'+' / '-'
			9       10    hours from UTC     	0..11
			10      11    minutes from UTC  	0..59

			 For example, Tuesday May 26, 1992 at 1:30:15 PM
 			EDT would be displayed as: 
			1992-5-26,13:30:15.0,-4:0
			Note that if only local time is known,then,timezone information
			(fields 8- 10) is not present.
			This variable is not supported anymore in forum Ima.
	     "
    ::= { ausmPortStateImaGrpEntry 18}

axisImaGroupRxFrameLength	OBJECT-TYPE
	SYNTAX	INTEGER {
		m32(32),
		m64(64),
		m128(128),
		m256(256) }
	ACCESS	read-only
	STATUS	mandatory
	DESCRIPTION
		"Value of IMA frame length as received from remote IMA function.
		"
    ::= { ausmPortStateImaGrpEntry 19}


axisImaGroupLeastDelayLink	OBJECT-TYPE
	SYNTAX 	INTEGER	
	ACCESS 	read-only
	STATUS 	mandatory
	DESCRIPTION
		"The IfIndex of the link configured in the IMA group which has 
		 the smallest link propagation delay. This value has meaning only
		 if at least 1 link has been configured in IMA group.
		"
    ::= { ausmPortStateImaGrpEntry 20}


axisImaGroupNumRxActLnks	OBJECT-TYPE
	SYNTAX	INTEGER 
	ACCESS 	read-only
	STATUS	mandatory
	DESCRIPTION
		"The number of links which are configured to receive and are 
		 currently Active in this IMA group.
		"
    ::= { ausmPortStateImaGrpEntry 21}

axisImaGroupNeState OBJECT-TYPE
	SYNTAX  INTEGER {
		notConfigured(1),
		startUp(2),
		startUpAck(3),
		configAbortUnsupportedM(4),
		configAbortIncompatibleSymmetry(5),
		configAbortOther(6),
		insufficientLinks(7),
		blocked(8),
		operational(9) }
	ACCESS	read-only
	STATUS	mandatory
	DESCRIPTION
		"The current operational state of the near-end IMA group state
		machine.

		1) notConfigured : The Group doesn't exist.This is the GSM 
				   initial state.
		2) startUp	 : On UM configuring the IMA group,GSM comes to
				   this state. 
		3) startUpAck  	 : On getting the Start-up-ack from FE(this info
				   from received ICP cell. i.e. FE accepting the 			  	   proposed group parameters by this END.), 
				   GSM goes to this state.
		4) configAbortUnsupportedM : This state is entered when FE is 
						not accepting the parameter M.
		5) configAbortIncompatibleSymmetry : When Group symmetry is not
			supported by the FE,this group is entered.
		6) configAbortOther : If any of the other group parameters are
			not supported by the FE,then this state is entered.
		7) insufficientLinks : On getting one of the following events 
			from FE, when GSM is in startUpAck state,GSM moves to 
			insufficientLinks state.
			evens : 1) Start-up-ack 2) insufficient links
				3) Blocked or operational
		8) blocked : For to maintenance purpose,if group is blcoked
			(inhibited by UM),GSM goes to this state. 
		9) operational : When the group has sufficient links in both Tx 			and Rx directions GSM goes to this state.
		"
    ::= { ausmPortStateImaGrpEntry 22}

-- Scalara in the ausmPortStateImaGrp 

axisImaGroupNumber OBJECT-TYPE
	SYNTAX	INTEGER 
	ACCESS  read-only
	STATUS	mandatory
	DESCRIPTION
		"The number of IMA groups configured with the lines."	
    ::= { ausmPortStateImaGrp 2 }


-- ------------------------------------------------------------------
-- End of ausmPortStateGrp

-- ------------------------------------------------------------------
--
-- BASIS project  CARD SPECIFIC MIB
-- Specific only to IMATM card
--
-- author: anandar 01.31.1996
--
-- ------------------------------------------------------------------



imatmClkCfgGrp             OBJECT IDENTIFIER ::= { cardSpecific 8 }
 


-- ------------------------------------------------------------------
--
-- Group "imatmClkCfgGrp"
-- This group contains information which is specific to the IMATM clock
-- configuration.
--
-- ------------------------------------------------------------------

primaryClockSource OBJECT-TYPE
    SYNTAX INTEGER {
		liu-rclk0	(1),
		liu-rclk1	(2),
		liu-rclk2	(3),
		liu-rclk3	(4),
		liu-rclk4	(5),
		liu-rclk5	(6),
		liu-rclk6	(7),
		liu-rclk7	(8),
		dsx3	    (9),
		bp8clk		(10)
	}
    ACCESS read-write
    STATUS mandatory
    DESCRIPTION
        "Primary reference for the clock source. Each of these codes are
		 to be interpreted as follows:
			liu-rclk0: Recovered clock from physical line 0
			liu-rclk1: Recovered clock from physical line 1
			liu-rclk2: Recovered clock from physical line 2
			liu-rclk3: Recovered clock from physical line 3
			liu-rclk4: Recovered clock from physical line 4
			liu-rclk5: Recovered clock from physical line 5
			liu-rclk6: Recovered clock from physical line 6
			liu-rclk7: Recovered clock from physical line 7
			dsx3: Recovered clock from the T3/E3 line
			bp8clk: Back-plane 8 KHz clock
        "
	DEFVAL {bp8clk}
    ::= { imatmClkCfgGrp 1 }

secondaryClockSource OBJECT-TYPE
    SYNTAX INTEGER {
		liu-rclk0	(1),
		liu-rclk1	(2),
		liu-rclk2	(3),
		liu-rclk3	(4),
		liu-rclk4	(5),
		liu-rclk5	(6),
		liu-rclk6	(7),
		liu-rclk7	(8),
		dsx3	    (9),
		bp8clk		(10),
		none		(11)
	}
    ACCESS read-write
    STATUS mandatory
    DESCRIPTION
        "Secondary reference for the clock source. Each of these codes are
		 to be interpreted as follows:
			liu-rclk0: Recovered clock from physical line 0
			liu-rclk1: Recovered clock from physical line 1
			liu-rclk2: Recovered clock from physical line 2
			liu-rclk3: Recovered clock from physical line 3
			liu-rclk4: Recovered clock from physical line 4
			liu-rclk5: Recovered clock from physical line 5
			liu-rclk6: Recovered clock from physical line 6
			liu-rclk7: Recovered clock from physical line 7
			dsx3: Recovered clock from the T3/E3 line
			bp8clk: Back-plane 8 KHz clock
			none  : No secondary clock is configured
        "
	DEFVAL {none}
    ::= { imatmClkCfgGrp 2 }

currentClockSource OBJECT-TYPE
    SYNTAX INTEGER {
       primary     (1),
       secondary   (2),
	   internal    (3)
    }
    ACCESS read-write
    STATUS mandatory
    DESCRIPTION
        "This object holds the current source for the clock
        "
    DEFVAL { primary }
    ::= { imatmClkCfgGrp 3 }


-- ------------------------------------------------------------------
--
-- BASIS project  CARD SPECIFIC MIB
-- Specific only to IMATM card
-- 
-- author: anandar 01.31.1996
--
-- ------------------------------------------------------------------



imatmDsx3CntrsGrp             OBJECT IDENTIFIER ::= { cardSpecific 9 }
 


-- ------------------------------------------------------------------
--
-- Group "imatmDsx3CntrsGrp"
-- This group contains information related to dsx3 counters
--
-- ------------------------------------------------------------------

imatmDsx3PortCntrsGrpTable OBJECT-TYPE
    SYNTAX SEQUENCE OF ImatmDsx3PortCntrsEntry
    ACCESS not-accessible
    STATUS mandatory
    DESCRIPTION
        "The dsx3 port counters table is for the DS3 port in IMATM.
		 At present there is only one entry (corresponding to the
		 single DS3 port available). This structure has been made a
		 table for flexibility (although there is only one entry in
		 the table at present)
		"
    ::= { imatmDsx3CntrsGrp 1 }

imatmDsx3PortCntrsEntry	OBJECT-TYPE
	SYNTAX	ImatmDsx3PortCntrsEntry
	ACCESS	not-accessible
	STATUS  mandatory
	DESCRIPTION
		"An entry for each T3 port (total of only one entry at present)
		"
	INDEX {imatmDsx3PortIndex}
	::= { imatmDsx3PortCntrsGrpTable 1 }

ImatmDsx3PortCntrsEntry ::=
	SEQUENCE {
		imatmDsx3PortIndex
			INTEGER,
		imatmDsx3PortRcvCells
			Counter,
		imatmDsx3PortXmtCells
			Counter,
		imatmPortRcvInvCells
			Counter,
		imatmPortCntrClrButton
			INTEGER,
		imatmDsx3PortLastMismatchVpiVci
			INTEGER,
		imatmPortImaCtrlMatchCells
			Counter
		}

imatmDsx3PortIndex OBJECT-TYPE
	SYNTAX	INTEGER (1..1)
	ACCESS  read-only
	STATUS  mandatory
	DESCRIPTION
		"Index to the dsx3 port number
		"
	::= { imatmDsx3PortCntrsEntry 1}

imatmDsx3PortRcvCells OBJECT-TYPE
	SYNTAX	Counter
	ACCESS  read-only
	STATUS  mandatory
	DESCRIPTION
		"Number of cells received on the DS3 port
		"
	::= { imatmDsx3PortCntrsEntry 2}

imatmDsx3PortXmtCells OBJECT-TYPE
	SYNTAX	Counter
	ACCESS  read-only
	STATUS  mandatory
	DESCRIPTION
		"Number of cells transmitted on the DS3 port
		"
	::= { imatmDsx3PortCntrsEntry 3}

imatmPortRcvInvCells OBJECT-TYPE
	SYNTAX	Counter
	ACCESS  read-only
	STATUS  mandatory
	DESCRIPTION
		"Number of invalid cells received on the DS3 port
		"
	::= { imatmDsx3PortCntrsEntry 4}

imatmPortCntrClrButton OBJECT-TYPE
	SYNTAX	INTEGER {
		noaction (1),
		clear (2)
	}
	ACCESS	read-write
	STATUS	mandatory
	DESCRIPTION
		"This variable is used to clear all the counters
		 maintained by the card for this DS3 port
		"
	::= { imatmDsx3PortCntrsEntry 5}

imatmDsx3PortLastMismatchVpiVci OBJECT-TYPE
	SYNTAX	INTEGER
	ACCESS	read-only
	STATUS	mandatory
	DESCRIPTION
		"This variable denotes the last mismatch VPI/VCI value that
		 was received over the DS3 interface.
		"
	::= { imatmDsx3PortCntrsEntry 6}

imatmPortImaCtrlMatchCells OBJECT-TYPE
	SYNTAX	Counter
	ACCESS	read-only
	STATUS	mandatory
	DESCRIPTION
		"This variable is used to count the number of cells from the
		 DS3 interface that were discarded due to match with IMA
		 Control header
		"
	::= { imatmDsx3PortCntrsEntry 7}

--  -------------------------------------------------------------------------
--
-- Copyright (C) 1995, StrataCom Inc., 1400, Parkmoor Ave, San Jose, CA 95126
--
-- This module is an original, unpublished work and is the intellectual property
-- of StrataCom Inc., and may not be divulged, copied or used in any form
-- whatsoever without the express written permission of StrataCom Inc.
--  -------------------------------------------------------------------------
-- 
--
--  MODULE NAME:
--		AIMNM
--
--  FILE : 
--		cardSpecAIMNMDsx3cnfg.my	
--
--  AUTHORS:
--		rodesai
--
--  CREATION DATE:
--		03/31/97
--
--
--  NOTES:
--		Created to add a configurable HEC correction enable/disble. Specific
--	to AIMNM only.
--
--  MODIFICATION HISTORY:
--		History maintained by clearcase.
--
-- ------------------------------------------------------------------
--
-- BASIS project  CARD SPECIFIC MIB
-- Specific only to IMATM card
--
-- ------------------------------------------------------------------

 
 
   dsx3CardSpecCnfgGrp OBJECT IDENTIFIER ::= { cardSpecific 14 }

-- ------------------------------------------------------------------
--
-- Group "imatmDsx3CardSpecCnfgGrp"
-- This group contains information which is specific to the IMATM dsx3
-- configuration. Right now there in only one element in it.
--
-- ------------------------------------------------------------------

imatmDsx3CardSpecConfigGrpTable 	OBJECT-TYPE
	SYNTAX SEQUENCE OF ImatmDsx3CardSpecConfigEntry
	ACCESS not-accessible
	STATUS mandatory
	DESCRIPTION
		"The dsx3 Card spec Config group table will contain all the 
		configuration variable for DSX3. Right now there is only one 
		configurable parameter in this group. Moreover this structure has
		been made a table for flexibility (although there is only one entry
		in the table at present). 
		"
	::= { dsx3CardSpecCnfgGrp 1}

imatmDsx3CardSpecConfigEntry	OBJECT-TYPE
	SYNTAX	ImatmDsx3CardSpecConfigEntry
	ACCESS	not-accessible
	STATUS	mandatory
	DESCRIPTION
	"Each entry gives the config parameters for the given port."
	INDEX	{ imatmdsx3PortIndex}
	::=	{ imatmDsx3CardSpecConfigGrpTable 1}

ImatmDsx3CardSpecConfigEntry	::=
	SEQUENCE {
		imatmdsx3PortIndex				
			INTEGER,
		imatmDsx3SingleBitErrCorrEnable	
			INTEGER
	}

imatmdsx3PortIndex OBJECT-TYPE
    SYNTAX  INTEGER (1..1)
    ACCESS  read-only
    STATUS  mandatory
    DESCRIPTION
        "Index to the dsx3 port number
        "
    ::= { imatmDsx3CardSpecConfigEntry 1}

imatmDsx3SingleBitErrCorrEnable		OBJECT-TYPE
	SYNTAX INTEGER	{
		disable(1),
		enable(2)
	}
	ACCESS	read-write
	STATUS	mandatory
	DESCRIPTION
		"This variable refers to dsx3 HEC correction enabled/disabled
		default is disable."
	DEFVAL	{disable}
	::= { imatmDsx3CardSpecConfigEntry 2}
-- ------------------------------------------------------------------
-- End of dsx3CardSpecConfigGrp group definitions
-- ------------------------------------------------------------------

-- ------------------------------------------------------------------
--
-- BASIS project  CARD SPECIFIC MIB
-- Specific only to IMATM card
-- 
-- author: anandar 08.09.1996
--
-- ------------------------------------------------------------------



imatmVpTrkGrp             OBJECT IDENTIFIER ::= { cardSpecific 13 }
imatmVpTrkMapGrp          OBJECT IDENTIFIER ::= { imatmVpTrkGrp 1 }
 


-- ------------------------------------------------------------------
--
-- Group "aumnmVpTrkMapGrp"
-- This group contains information on which VP ranges should be mapped
-- to which trunk
--
-- ------------------------------------------------------------------

imatmVpTrkMapGrpTable OBJECT-TYPE
    SYNTAX SEQUENCE OF ImatmVpTrkMapGrpTableEntry
    ACCESS not-accessible
    STATUS mandatory
    DESCRIPTION
        "The imatmVpTrkMapGrpTable entry contains the information for
         mapping VPI ranges to different trunks in IMATM.
        "
    ::= { imatmVpTrkMapGrp 1 }
 
imatmVpTrkMapGrpTableEntry OBJECT-TYPE
    SYNTAX  ImatmVpTrkMapGrpTableEntry
    ACCESS  not-accessible
	STATUS	mandatory
	DESCRIPTION
		"An entry for each VPI range
		"
	INDEX {imatmRangeNum}
	::= { imatmVpTrkMapGrpTable 1 }


ImatmVpTrkMapGrpTableEntry ::=
	SEQUENCE {
		imatmRangeNum
			INTEGER,
		imatmTrkNum
			INTEGER,
		imatmTrkMinVp
			INTEGER,
		imatmTrkMaxVp
			INTEGER,
		imatmTrkOpType
			INTEGER
		}


imatmRangeNum OBJECT-TYPE
	SYNTAX	INTEGER (1..128)
	ACCESS  read-only
	STATUS  mandatory
	DESCRIPTION
		"An index to the VpTrkTbl
		"
	::= { imatmVpTrkMapGrpTableEntry 1}

imatmTrkNum OBJECT-TYPE
	SYNTAX	INTEGER (1..8)
	ACCESS  read-write
	STATUS  mandatory
	DESCRIPTION
		"This variable refers to the trunk number on the IMATM card. The
         trunk number is the same as logical port number.
		"
	::= { imatmVpTrkMapGrpTableEntry 2}

imatmTrkMinVp OBJECT-TYPE
	SYNTAX	INTEGER (0..4095)
	ACCESS  read-write
	STATUS  mandatory
	DESCRIPTION
		"This variable refers to the minimum VPI value to be configured
         in the range of VPIs that are to be mapped to an IMATM trunk.
		"
	::= { imatmVpTrkMapGrpTableEntry 3}

imatmTrkMaxVp OBJECT-TYPE
	SYNTAX	INTEGER (0..4095)
	ACCESS  read-write
	STATUS  mandatory
	DESCRIPTION
		"This variable refers to the maximum VPI value to be configured
         in the range of VPIs that are to be mapped to an IMATM trunk.
		 It should be necessarily greater than or equal to the value of
         imatmTrkMinVp.
		"
	::= { imatmVpTrkMapGrpTableEntry 4}

imatmTrkOpType OBJECT-TYPE
	SYNTAX	INTEGER {
		disable(1),
		enable(2),
		modify(3)
	}
	ACCESS  read-write
	STATUS  mandatory
	DESCRIPTION
		"This variable refers to the operation type for the VPI range
		 in question.
		 'disable' deletes an existing row from the table
		 'enable'  adds a new row to the table
		 'modify'  modifies the attributes of an existing row to the
				   table
		"
	::= { imatmVpTrkMapGrpTableEntry 5}

--
-- scalars
--

nextRangeNumAvail	OBJECT-TYPE
	SYNTAX	INTEGER(1..128)
	ACCESS	read-only
	STATUS	mandatory
	DESCRIPTION
		"This variable indicates the next range number to be used as the
		 index for the VpTrkTbl.
		"
    ::= { imatmVpTrkMapGrp 2 }

-- ------------------------------------------------------------------
-- End of imatmVpTrkMapGrp group definitions
-- ------------------------------------------------------------------


-- ------------------------------------------------------------------
-- Begin description for imatmVpTrkClrGrp group definitions
-- Specific only to IMATM card
-- ------------------------------------------------------------------
-- ------------------------------------------------------------------
--
-- This group (imatmVpTrkClrGrp) is created to enable deletion of all
-- rows corresponding to a particular trunk
--
-- ------------------------------------------------------------------

imatmVpTrkClrGrp          OBJECT IDENTIFIER ::= { imatmVpTrkGrp 2 }

imatmVpTrkClrGrpTable OBJECT-TYPE
    SYNTAX SEQUENCE OF ImatmVpTrkClrGrpEntry
    ACCESS not-accessible
    STATUS mandatory
    DESCRIPTION
        "This table is for each trunk in IMATM and is used if the user
         wishes to remove all VPI ranges for an IMATM trunk.
		"
    ::= { imatmVpTrkClrGrp 1 }

imatmVpTrkClrGrpEntry	OBJECT-TYPE
	SYNTAX	ImatmVpTrkClrGrpEntry
	ACCESS	not-accessible
	STATUS  mandatory
	DESCRIPTION
		"An entry for each IMATM trunk
		"
	INDEX {imatmClrVpTrkNum}
	::= { imatmVpTrkClrGrpTable 1 }

ImatmVpTrkClrGrpEntry ::=
	SEQUENCE {
		imatmClrVpTrkNum
			INTEGER,
		imatmClrVpTrkButton
			INTEGER
		}

imatmClrVpTrkNum OBJECT-TYPE
	SYNTAX	INTEGER(1..8)
	ACCESS	read-only
	STATUS	mandatory
	DESCRIPTION
		"This variable is used to identify the IMATM trunk number on
         which the 'Clear Map Table' operation needs to be done.
		"
	::= { imatmVpTrkClrGrpEntry 1}

imatmClrVpTrkButton OBJECT-TYPE
	SYNTAX	INTEGER {
		noaction (1),
		clear (2)
	}
	ACCESS	read-write
	STATUS	mandatory
	DESCRIPTION
		"This variable implements the 'Clear Map Table' for a specified
		 IMATM trunk.
		"
	::= { imatmVpTrkClrGrpEntry 2}


-- ----------------------------------------------------------------------
-- End of imatmVpTrkGrp group definitions

-- ------------------------------------------------------------------
--
-- BASIS project  CARD SPECIFIC MIB
-- Specific only to IMATM card
--
--
-- ------------------------------------------------------------------



imaAutoRestartFeature             OBJECT IDENTIFIER ::= { cardSpecific 21 }

-- ------------------------------------------------------------------
--
-- Group "imaAutoRestartFeature"
-- enable/disable feature thru SV+
--
-- ------------------------------------------------------------------

imaAutoRestart  OBJECT-TYPE
    SYNTAX INTEGER {
        disabled     (1),
        enabled      (2)
    }
    ACCESS read-write
    STATUS mandatory
    DESCRIPTION
        "
            This object allows the user to enable/disable the IMA
            group auto-restart feature on IMA capable cards. The
            effect of this object is card-wide. 
            A value of 1 disables the feature.
            A value of 2 enables  the feature.
        "
    DEFVAL {disabled}
    ::= { imaAutoRestartFeature 1}



commonChannel    OBJECT IDENTIFIER ::= { cardGeneric 7}

-- --------------------------------------------------------------------
--
--
--        COMMON CHANNEL Group
--
--
-- --------------------------------------------------------------------


commonChanTable    OBJECT-TYPE
    SYNTAX    SEQUENCE OF CommonChanTableEntry
    ACCESS    not-accessible
    STATUS    mandatory
    DESCRIPTION
        "The common port table is for the common ports."
    ::= { commonChannel 1 }


commonChanTableEntry    OBJECT-TYPE
    SYNTAX    CommonChanTableEntry
    ACCESS    not-accessible
    STATUS    mandatory
    DESCRIPTION
        " An entry for every common port group.
        "
    INDEX    { commonChanNum }
    ::= { commonChanTable 1 }

CommonChanTableEntry ::=
    SEQUENCE {
        commonChanNum     
           INTEGER,
		commonConnType
			INTEGER,
   		commonChanStatus
   	        INTEGER,
		commonAlarmState
			INTEGER,
		commonChanPortNum
			INTEGER,
		commonChanServiceType
			INTEGER,
		commonChanIngrXmtState
			INTEGER,
		commonChanIngrRcvState
			INTEGER,
		commonChanEgrXmtState
			INTEGER,
		commonChanEgrRcvState
			INTEGER,
		commonConnParm1
			DisplayString,
		commonConnParm2
			DisplayString
    }

commonChanNum    OBJECT-TYPE
    SYNTAX    INTEGER (16..1015)
    ACCESS    read-only
    STATUS    mandatory
    DESCRIPTION
        "This is the index to the channel number.
        "
    ::= { commonChanTableEntry 1}

commonConnType    OBJECT-TYPE
    SYNTAX    INTEGER {
			vpc(1),
			vcc(2)
			}
    ACCESS    read-only
    STATUS    mandatory
    DESCRIPTION
      "This specifies the connection type
          1 ==> Virtual Path Connection
          2 ==> Virtual Channel Connection
      "
    ::= { commonChanTableEntry 2}

commonChanStatus  OBJECT-TYPE        
    SYNTAX    INTEGER {
        notconfigured (1),
        normal(2),
        alarm(3)
    }
    ACCESS read-only
    STATUS  mandatory
    DESCRIPTION
        "This variable indicates the state of the VC (channel)(
        "
	DEFVAL {notconfigured}
    ::= { commonChanTableEntry 3 }

commonAlarmState OBJECT-TYPE
    SYNTAX    INTEGER
    ACCESS    read-only
    STATUS    mandatory
    DESCRIPTION
        "This is the alarm state of the port.
        "
    ::= { commonChanTableEntry 4}

commonChanPortNum OBJECT-TYPE
    SYNTAX    INTEGER(1..8)
    ACCESS read-only
    STATUS  mandatory
    DESCRIPTION
        "This variable indicates the port number associated with the
         channel
        "
    ::= { commonChanTableEntry 5 }

commonChanServiceType OBJECT-TYPE
    SYNTAX  INTEGER {
		cbr(1),
		vbr(2),
		abr(3)
    }
    ACCESS read-only
    STATUS  mandatory
    DESCRIPTION
      "This specifies the service type
          1 ==> Constant Bit Rate
          2 ==> Variable Bit Rate
          3 ==> Associated Bit Rate
      "
    ::= { commonChanTableEntry 6 }

commonChanIngrXmtState  OBJECT-TYPE
    SYNTAX INTEGER {
        other(1),
        normal(2),
        receivingAis (3),
        receivingFerf (4)
    }
    ACCESS read-only
    STATUS  mandatory
    DESCRIPTION
		"This variable indicates the transmit state of the VC (channel)
		 on the CellBus side (Ingress)
        "
        ::= { commonChanTableEntry 7 }
 
commonChanIngrRcvState  OBJECT-TYPE
    SYNTAX INTEGER {
        other(1),
        normal(2),
        receivingAis (3),
        receivingFerf (4),
		alarm(5)
    }
    ACCESS read-only
    STATUS  mandatory
    DESCRIPTION
		"This variable indicates the status of port receive (Ingress)
        "
        ::= { commonChanTableEntry 8 }
 
commonChanEgrXmtState OBJECT-TYPE
    SYNTAX INTEGER {
        other(1),
        normal(2),
        sendingAis (3),
        sendingFerf (4)
        }
    ACCESS read-only
    STATUS mandatory
    DESCRIPTION
        "indicates the status of port transmit(Egress)
        "
        ::= { commonChanTableEntry  9 }
 
commonChanEgrRcvState OBJECT-TYPE
    SYNTAX INTEGER {
        other(1),
        normal(2),
        sendingAis (3),
        sendingFerf (4),
		alarm(5)
        }
    ACCESS read-only
    STATUS mandatory
    DESCRIPTION
        "Indicates the receiving state of the VC (channel) on the Cellbus
         side (Egress)
        "
        ::= { commonChanTableEntry  10 }
 
commonConnParm1 OBJECT-TYPE
    SYNTAX  DisplayString
    ACCESS read-only
        STATUS  mandatory
        DESCRIPTION
        "Connection paramter 1
        "
        ::= { commonChanTableEntry 11 }

commonConnParm2 OBJECT-TYPE
    SYNTAX  DisplayString
    ACCESS read-only
        STATUS  mandatory
        DESCRIPTION
        "Connection paramter 2
        "
        ::= { commonChanTableEntry 12 }

-- --------------------------------------------------------------
-- End of commonChanTableEntry



commonPort    OBJECT IDENTIFIER ::= { cardGeneric 6}

-- --------------------------------------------------------------------
--
--
--        COMMON PORT Group
--
--
-- --------------------------------------------------------------------


commonPortTable    OBJECT-TYPE
    SYNTAX    SEQUENCE OF CommonPortTableEntry
    ACCESS    not-accessible
    STATUS    mandatory
    DESCRIPTION
        "The common port table is for the common ports."
    ::= { commonPort 1 }


commonPortTableEntry    OBJECT-TYPE
    SYNTAX    CommonPortTableEntry
    ACCESS    not-accessible
    STATUS    mandatory
    DESCRIPTION
        " An entry for every common port group.
        "
    INDEX    { commonPortNum }
    ::= { commonPortTable 1 }

CommonPortTableEntry ::=
    SEQUENCE {
        commonPortNum     
           INTEGER,
		commonPortType
			INTEGER,
   		commonPortStatus
   	        INTEGER,
		commonPortSpeed
			INTEGER,
		commonPortAlarmState
			INTEGER,
		commonPortSignallingProtocolType
			INTEGER,
		commonPortSignallingState
			INTEGER,
		commonPortAssocLines
			DisplayString,
		commonPortAssocChannels
			DisplayString
    }

commonPortNum    OBJECT-TYPE
    SYNTAX    INTEGER (1..8) 
    ACCESS    read-only
    STATUS    mandatory
    DESCRIPTION
        "This is the index to the port number.
        "
    ::= { commonPortTableEntry 1}

commonPortType    OBJECT-TYPE
    SYNTAX    INTEGER {
			framerelayport(1),
			atmport(2),
			imaport(3)
			}
    ACCESS    read-only
    STATUS    mandatory
    DESCRIPTION
        "This is the type of the port.
		  1 - Frame Relay Port.
		  2 - ATM Port.
		  3 - IMA Port.
        "
	DEFVAL	{atmport}
    ::= { commonPortTableEntry 2}

commonPortStatus  OBJECT-TYPE        
    SYNTAX    INTEGER {
        disable(1),
        enable(2)
        }
    ACCESS read-only
    STATUS  mandatory
    DESCRIPTION
        "This variable enables or disables the port
        1 - disable
        2 - enable
        "
	 DEFVAL {disable}	
    ::= { commonPortTableEntry 3 }

commonPortSpeed    OBJECT-TYPE
    SYNTAX    INTEGER (0..37360)
    ACCESS    read-only
    STATUS    mandatory
    DESCRIPTION
        "This is the speed of the port in cells per second.
        "
    ::= { commonPortTableEntry 4}

commonPortAlarmState  OBJECT-TYPE        
    SYNTAX    INTEGER {
        inalarm(1),
        outofalarm(2)
        }
    ACCESS read-only
    STATUS  mandatory
    DESCRIPTION
        "This variable states the alarm status of the port
        1 - port in alarm
        2 - port out of alarm
        "
    ::= { commonPortTableEntry 5 }

commonPortSignallingProtocolType  OBJECT-TYPE
    SYNTAX  INTEGER {
        tbd(1)
        }
    ACCESS read-only
        STATUS  mandatory
        DESCRIPTION
		"This variable indicates the signalling protocol type of the port. 
		 This field is TBD. It is unused in IMATM/AUSM.
         "
        ::= { commonPortTableEntry 6 }

commonPortSignallingState  OBJECT-TYPE
    SYNTAX  INTEGER {
        tbd(1)
        }
    ACCESS read-only
        STATUS  mandatory
        DESCRIPTION
		"This variable indicates the signalling state of the port. 
         "
        ::= { commonPortTableEntry 7 }
 
commonPortAssocLines  OBJECT-TYPE
    SYNTAX  DisplayString
    ACCESS read-only
        STATUS  mandatory
        DESCRIPTION
        "This variable indicates the list of physical lines in the port
		delimited by dots.
        "
        ::= { commonPortTableEntry  8 }
 
commonPortAssocChannels  OBJECT-TYPE
    SYNTAX  DisplayString
    ACCESS read-only
        STATUS  mandatory
        DESCRIPTION
        "The variable indicates the list of channels that are used in the 
		ds1 frame.
        "
        ::= { commonPortTableEntry 9 }


-- --------------------------------------------------------------
-- End of commonPortTableEntry

--
-- ----------------------------------------------------------------------
-- BASIS Project MIB
-- 
-- Initial revision 
-- 2/22/95, updated Ravi Bhat
--





-- atm                  OBJECT IDENTIFIER ::= { basisServices 2 }
--ausmChan                OBJECT IDENTIFIER ::= { atm 2 }
ausmChanCnfGrp          OBJECT IDENTIFIER ::= { ausmChan 1 }


-- ------------------------------------------------------------------------
--
-- ausmChannelConfig group
-- Channel configurable parameters  (VC)
--
-- ------------------------------------------------------------------------


ausmChanCnfGrpTable	OBJECT-TYPE
	SYNTAX	SEQUENCE OF AusmChanCnfGrpEntry
	ACCESS	not-accessible
	STATUS	mandatory
	DESCRIPTION
		"The config table is for logical channel interface
		 there are 1000 entries for the 8 logical ports in AUSM (8-port)
         and 256 entries for the 4 logical ports in AUSM (4-port card).
         In AUSM (4-port card), a logical port is same as a physical
         port.
		"
	::= { ausmChanCnfGrp 1 }

ausmChanCnfGrpEntry	OBJECT-TYPE
	SYNTAX	AusmChanCnfGrpEntry
	ACCESS	not-accessible
	STATUS	mandatory
	DESCRIPTION
		" An entry for logical channel
		"
	INDEX	{ ausmChanNum }
	::= { ausmChanCnfGrpTable 1 }

AusmChanCnfGrpEntry ::=
	SEQUENCE {
	   	ausmChanNum		INTEGER,
		ausmChanRowStatus      	INTEGER, 
		chanConnType		INTEGER, -- VP or VC connection
		chanServiceType		INTEGER, -- CBR or VBR 
		chanConnDesc		DisplayString,
		chanSvcFlag		INTEGER, -- 1-SVC,2-non-SVC
		chanSvcConnId		INTEGER, -- Future Use
		ausmChanPortNum         INTEGER, 
		chanVpi		        INTEGER,
		chanVci		        INTEGER,
		chanEgrQSelect	      	INTEGER,
		ingrQDepth	      	INTEGER,
		ingrQCLPThreshHigh	INTEGER,
		ingrQCLPThreshLow	INTEGER,
		ingrQCLPState		INTEGER,
		ingrQEfciThresh		INTEGER,
-- UPC parameters
		ingrUpcEnable		INTEGER, -- 1-Disable, 2-Enable
		ingrUpcPCR01		INTEGER, -- Used only by UPC
		ingrUpcCIR		INTEGER, -- AKA SCR
		ingrUpcCCDV		INTEGER, -- for CBR traffic
		ingrUpcCBS		INTEGER,
		ingrUpcIBS		INTEGER,
		ingrUpcMFS		INTEGER,
		ingrUpcSCRPolicing	INTEGER, -- 1-CLP0, 2-CLP0+1
		ingrUpcPCR0		INTEGER,
		ingrUpcCDVT0		INTEGER,
		ingrUpcCLPTagEnable	INTEGER,
		ingrUpcFGCRAEnable	INTEGER,
-- Foresight parameters
		foresightEnable		INTEGER,
		foresightMIR		INTEGER,
		foresightPIR		INTEGER,
		foresightQIR		INTEGER,
-- Release 2 additions (directly from FRSM)
		ausmChanLocRmtLpbkState	INTEGER,
		ausmChanTestType	INTEGER,
		ausmChanTestState	INTEGER,
		ausmChanRTDResult	INTEGER,
-- Variable to support OAM Segment Loopback towards CPE
		ausmChanTestTypeCPESide	    INTEGER,
		ausmChanTestStateCPESide	INTEGER,
-- CAC parameters (IngrPcr will be derived from foresightPIR )
		ausmChanIngrPercentUtil	INTEGER,
		ausmChanEgrPercentUtil  INTEGER,
		ausmChanEgrSrvRate      INTEGER,
		ausmChanOvrSubOvrRide   INTEGER,
-- VP connection parameter
		ausmChanLocalVpId	INTEGER,
-- New addition will not be supported in 8.2
		ausmChanRMEnable	INTEGER,
-- Parameters for Early/Partial packet Discard Threshold
		ausmIngrDiscardOption INTEGER,
		ausmIngrFrDiscardThreshold INTEGER,
		ausmCDRNumber INTEGER,
-- Connection parameters, used by PXM
		ausmLocalVpi		INTEGER,
		ausmLocalVci		INTEGER,
		ausmLocalNSAP		OCTET STRING,
		ausmRemoteVpi		INTEGER,
		ausmRemoteVci		INTEGER,
		ausmRemoteNSAP		OCTET STRING,
		ausmMastership		INTEGER,
		ausmVpcFlag		INTEGER,
		ausmConnServiceType	INTEGER,
		ausmRoutingPriority	INTEGER,
		ausmMaxCost		INTEGER,
		ausmRestrictTrunkType 	INTEGER,
		ausmConnPCR		INTEGER,
		ausmConnMCR		INTEGER,
		ausmConnPercentUtil	INTEGER,
		ausmConnRemotePCR   INTEGER,
		ausmConnRemoteMCR   INTEGER,
		ausmConnRemotePercentUtil INTEGER,
		ausmConnForeSightEnable   INTEGER,
		ausmConnFGCRAEnable       INTEGER,
		ausmChanReroute           INTEGER,
		ausmConnSCR               INTEGER,
        ausmConnRemoteSCR         INTEGER,
		ausmConnMBS		          INTEGER,
		ausmConnRemoteMBS 	      INTEGER,
        ausmConnTemplateId        INTEGER,
        ausmConnAdminStatus       INTEGER
}


ausmChanNum OBJECT-TYPE
	SYNTAX	INTEGER (16..1015)
	ACCESS	read-only
	STATUS	mandatory
	DESCRIPTION		  
		"Refers to the virtual connection index. In AUSM (4-port card),
         valid range is from 16..271.
		"
	::= { ausmChanCnfGrpEntry 1}

ausmChanRowStatus  OBJECT-TYPE
	SYNTAX	INTEGER {
		add(1),
		del(2),
		mod(3),
-- added outOfService for Release2.2
		outOfService(4)
		}
	ACCESS read-write
	STATUS  mandatory
	DESCRIPTION
	  "This will add, delete or modify the channel
     	  1 ==> ADD
      	  2 ==> DELETE
      	  3 ==> MODIFY
	  Setting this object to outOfService takes the channel
	  out of service or brings the channel 'down'. The channel
	  can be brought 'up' again by setting the object to mod
		"
        DEFVAL { del }
   	::= { ausmChanCnfGrpEntry 2 }

chanConnType	OBJECT-TYPE	
	SYNTAX	INTEGER {
		vpc(1),
		vcc(2)
		}
	ACCESS read-write
	STATUS  mandatory
	DESCRIPTION
	  "This specifies the connection type 
     	  1 ==> Virtual Path Connection
      	  2 ==> Virtual Channel Connection
	  "
        DEFVAL { vcc }
   	::= { ausmChanCnfGrpEntry 3 }

chanServiceType	OBJECT-TYPE
	SYNTAX	INTEGER {
		cbr(1),
		vbr(2),
		abr (3),
		ubr(4),
		rtvbr(5)
		}
	ACCESS read-write
	STATUS  mandatory
	DESCRIPTION
	  "This specifies the service type 
     	  1 ==> Constant Bit Rate
      	  2 ==> Variable Bit Rate
          3 ==> Available Bit Rate
	  4 ==> Unspecified Bit Rate
	  5 ==> Real-Time Variable Bit Rate
	  "
        DEFVAL { cbr }
   	::= { ausmChanCnfGrpEntry 4 }

chanConnDesc	OBJECT-TYPE
	SYNTAX	DisplayString (SIZE (0..20))
	ACCESS read-write
	STATUS  mandatory
	DESCRIPTION
	  "A string that has been defined to give a 
	   descriptive name to the connection
	  "
   	::= { ausmChanCnfGrpEntry 5 }


chanSvcFlag	OBJECT-TYPE
	SYNTAX	INTEGER {
		svc(1),
		pvc(2),
		spvc(3),
		par(4),
		pnni(5),
		tag(6)
		}
	ACCESS read-write
	STATUS  mandatory
	DESCRIPTION
	  "This specifies the connection type 
      1 ==> SVC connection
      2 ==> PVC connection
	  3 ==> SPVC connection
	  4 ==> connection added by PAR
	  5 ==> connection added by PNNI
	  6 ==> connection added by TAG
	  "
   	::= { ausmChanCnfGrpEntry 6 }

chanSvcConnId	OBJECT-TYPE
	SYNTAX	INTEGER 
	ACCESS read-write
	STATUS  mandatory
	DESCRIPTION
	  "This connection ID is for future use
     	   Currently not supported
	  "
   	::= { ausmChanCnfGrpEntry 7 }

ausmChanPortNum OBJECT-TYPE
	SYNTAX	INTEGER (1..8)
	ACCESS	read-write
	STATUS	mandatory
	DESCRIPTION		  
		"Refers to the logical port on the board to which
		 logical channel is associated. In AUSM (4-port card), a
         logical port is same as a physical port.
		"
	::= { ausmChanCnfGrpEntry	8}

chanVpi 	OBJECT-TYPE
	SYNTAX	INTEGER (0..'ff'h)
	ACCESS	read-write
	STATUS	mandatory
	DESCRIPTION		  
		"The VPI value for this channel 
		"
        DEFVAL { 0 }
	::= { ausmChanCnfGrpEntry	9}

chanVci 	OBJECT-TYPE
	SYNTAX	INTEGER (0..'ffff'h)
	ACCESS	read-write
	STATUS	mandatory
	DESCRIPTION		  
		"The VCI value for this channel 
		"
        DEFVAL { 0 }
	::= { ausmChanCnfGrpEntry	10}

chanEgrQSelect OBJECT-TYPE
	SYNTAX	INTEGER (1..16)
	ACCESS	read-write
	STATUS	mandatory
	DESCRIPTION		  
		"Selects one out of the 16 possible queues
		Each queue may have a different service algorithm
		"
        DEFVAL { 1 }
	::= { ausmChanCnfGrpEntry	11}

ingrQDepth	OBJECT-TYPE
	SYNTAX	INTEGER (1..16000)
	ACCESS read-write
        STATUS  mandatory
        DESCRIPTION
        "This variable sets the max depth for queue, before
		 it starts dropping the cells. In AUSM (4-port card), the
         valid range is from 1..8000.
		"
        DEFVAL { 1000 }
        ::= { ausmChanCnfGrpEntry 12}

ingrQCLPThreshHigh	OBJECT-TYPE
	SYNTAX	INTEGER (1..16000)
	ACCESS read-write
        STATUS  mandatory
        DESCRIPTION
        "This variable sets the higher threshold for
		 dropping CLP set cells in the ingress direction. In AUSM
         (4-port card), the valid range is from 1..8000.This value
		 should be less than or equal to ingrQDepth.
         Default value depends on the ingrQDepth.
		"
        ::= { ausmChanCnfGrpEntry 13}

ingrQCLPThreshLow	OBJECT-TYPE
	SYNTAX	INTEGER (1..16000)
	ACCESS read-write
        STATUS  mandatory
        DESCRIPTION
        "This variable sets the lower threshold for dropping CLP set
         cells in the ingress direction. In AUSM (4-port card), the
         valid range is from 1..8000.This value should be less than
		 or equal to ingrQCLPThreshHigh.
         Default value depends on the ingrQDepth.
		"
        ::= { ausmChanCnfGrpEntry 14}

ingrQCLPState	OBJECT-TYPE
	SYNTAX	INTEGER {
		low (1),
		high (2)
		} 
	ACCESS read-only
        STATUS  mandatory
        DESCRIPTION
                "This variable indicates the CLP state for
		the channel
		"
        ::= { ausmChanCnfGrpEntry 15}

ingrQEfciThresh	OBJECT-TYPE
	SYNTAX	INTEGER (1..16000)
	ACCESS read-write
        STATUS  mandatory
        DESCRIPTION
        "This variable sets the efci threshold value for setting efci bit
         in the ingress direction. In AUSM (4-port card), the
         valid range is from 1..8000.This value should be less than
		 or equal to ingrQDepth.
		"
        DEFVAL { 1000 }
        ::= { ausmChanCnfGrpEntry 16}

-- UPC parameters
-- The values for CBS,IBS,MFS,AR are to be decided (TBD)

ingrUpcEnable		OBJECT-TYPE
	SYNTAX	INTEGER {
		disable (1),
		enable (2)
		} 
	ACCESS read-write
        STATUS  mandatory
        DESCRIPTION
                "enables/disables UPC for Ingress cells
		"
        DEFVAL { enable }
        ::= { ausmChanCnfGrpEntry 17}


ingrUpcPCR01              OBJECT-TYPE
	SYNTAX	INTEGER (10..38328)
	ACCESS read-write
        STATUS  mandatory
        DESCRIPTION
        "Peak Cell Rate for CLP [0+1] cells. The actual value
         depends on the speed of the logical port (which can be
         a T1, E1 (normal), E1 (clear), IMA T1, IMA E1 (normal) or
         IMA E1 (clear) port. Note that the IMA port's speed is
         variable and depends on the number of links in the port. In
         AUSM (4-port), maximum value is 4830.
		"
        ::= { ausmChanCnfGrpEntry 18}

ingrUpcCIR              OBJECT-TYPE
	SYNTAX	INTEGER (10..38328)
	ACCESS read-write
        STATUS  mandatory
        DESCRIPTION
        "Complaint Information Rate. The actual value
         depends on the speed of the logical port (which can be
         a T1, E1 (normal), E1 (clear), IMA T1, IMA E1 (normal) or
         IMA E1 (clear) port. Note that the IMA port's speed is
         variable and depends on the number of links in the port. In
         AUSM (4-port), maximum value is 4830.
		"
        ::= { ausmChanCnfGrpEntry 19}

ingrUpcCCDV              OBJECT-TYPE
	SYNTAX	INTEGER (1..250000)	-- in microseconds
	ACCESS read-write
        STATUS  mandatory
        DESCRIPTION
               	"Complaint Cell Delay Variation for all cells
		"
        DEFVAL { 10000 }
        ::= { ausmChanCnfGrpEntry 20}

ingrUpcCBS              OBJECT-TYPE
	SYNTAX	INTEGER (1..5000)
	ACCESS read-write
        STATUS  mandatory
        DESCRIPTION
               	"Complaint Burst Size
                 The unit of this parameter is in terms of number of cells.
                 CBS is applicable only for VBR and ABR connections.

                 In MGX switches, release 3.0.0.0 and above,
                 the default value is 1024
		"
        DEFVAL { 1000 }
        ::= { ausmChanCnfGrpEntry 21}

ingrUpcIBS              OBJECT-TYPE
	SYNTAX	INTEGER (1..4830)
	ACCESS read-write
        STATUS  mandatory
        DESCRIPTION
               	"Initial Burst Size.
		 The Burst size allowed for a connection that has been
		 idle for some time. The unit of this parameter is in
		 terms of number of cells.
		 IBS is applicable only for VBR and ABR connections.
                 IBS value should be less than CBS for VBR and ABR connections.
		 IBS value will be ignored for other service types.
		"
        DEFVAL { 1 }
        ::= { ausmChanCnfGrpEntry 22}

ingrUpcMFS              OBJECT-TYPE
	SYNTAX	INTEGER (0..200)
	ACCESS read-write
        STATUS  mandatory
        DESCRIPTION
               	"Maximum Frame Size
		"
        ::= { ausmChanCnfGrpEntry 23}

ingrUpcSCRPolicing	OBJECT-TYPE
	SYNTAX	INTEGER {
		clp0 (1),
		clp0and1 (2),
		off (3)
		} 
	ACCESS read-write
        STATUS  mandatory
        DESCRIPTION
                "selects SCR policing for CLP = 0 or all cells
		"
        DEFVAL { clp0 }
        ::= { ausmChanCnfGrpEntry 24}

ingrUpcPCR0		OBJECT-TYPE
	SYNTAX	INTEGER (10..38328)
	ACCESS read-write
        STATUS  mandatory
        DESCRIPTION
        "Peak Cell Rate for CLP=0 cells. The actual value
         depends on the speed of the logical port (which can be
         a T1, E1 (normal), E1 (clear), IMA T1, IMA E1 (normal) or
         IMA E1 (clear) port. Note that the IMA port's speed is
         variable and depends on the number of links in the port. In
         AUSM (4-port), maximum value is 4830.
		"
        ::= { ausmChanCnfGrpEntry 25}

ingrUpcCDVT0		OBJECT-TYPE
	SYNTAX	INTEGER (1..250000)	-- in microseconds
	ACCESS read-write
        STATUS  mandatory
        DESCRIPTION
               	"Complaint Cell Delay Variation for CLP=0 cells
		"
        ::= { ausmChanCnfGrpEntry 26}


ingrUpcCLPTagEnable     OBJECT-TYPE
	SYNTAX	INTEGER {
		disable (1),
		enable (2)
		} 
	ACCESS read-write
        STATUS  mandatory
        DESCRIPTION
                "enables/disables CLP tagging for Ingress cells
		"
        DEFVAL { enable }
        ::= { ausmChanCnfGrpEntry 27}

ingrUpcFGCRAEnable     OBJECT-TYPE
	SYNTAX	INTEGER {
		disable (1),
		enable (2)
		} 
	ACCESS read-write
        STATUS  mandatory
        DESCRIPTION
                "enables/disables Frame based GCRA
		"
        DEFVAL { disable }
        ::= { ausmChanCnfGrpEntry 28}


-- Foresight parameters
-- The different values for Foresight parameters are TBD

foresightEnable         OBJECT-TYPE
	SYNTAX	INTEGER {
		disable (1),
		enable (2)
		} 
	ACCESS read-write
        STATUS  mandatory
        DESCRIPTION
                "enables/disables Foresight
		"
        DEFVAL { disable }
        ::= { ausmChanCnfGrpEntry 29}

foresightMIR            OBJECT-TYPE
	SYNTAX	INTEGER (1..38328)
	ACCESS read-write
        STATUS  mandatory
        DESCRIPTION
        "Minimum Information Rate. The actual value
         depends on the speed of the logical port (which can be
         a T1, E1 (normal), E1 (clear), IMA T1, IMA E1 (normal) or
         IMA E1 (clear) port. Note that the IMA port's speed is
         variable and depends on the number of links in the port. In
         AUSM (4-port), maximum value is 4830.
		"
        ::= { ausmChanCnfGrpEntry 30}

foresightPIR            OBJECT-TYPE
	SYNTAX	INTEGER (10..38328)
	ACCESS read-write
        STATUS  mandatory
        DESCRIPTION
        "Peak Information Rate. The actual value
         depends on the speed of the logical port (which can be
         a T1, E1 (normal), E1 (clear), IMA T1, IMA E1 (normal) or
         IMA E1 (clear) port. Note that the IMA port's speed is
         variable and depends on the number of links in the port. In
         AUSM (4-port), maximum value is 4830.
		"
        ::= { ausmChanCnfGrpEntry 31}

foresightQIR            OBJECT-TYPE
	SYNTAX	INTEGER (1..38328)
	ACCESS read-write
        STATUS  mandatory
        DESCRIPTION
        "Quiescent Information Rate. The actual value
         depends on the speed of the logical port (which can be
         a T1, E1 (normal), E1 (clear), IMA T1, IMA E1 (normal) or
         IMA E1 (clear) port. Note that the IMA port's speed is
         variable and depends on the number of links in the port. In
         AUSM (4-port), maximum value is 4830.
		"
        ::= { ausmChanCnfGrpEntry 32}

ausmChanLocRmtLpbkState	OBJECT-TYPE  
	SYNTAX  INTEGER {
		enable(1), 
		disable(2) 
	}
	ACCESS read-write 
	STATUS  mandatory  
	DESCRIPTION    
        "The default is disable.
	 This variable enables or disables the remote loopback for each
	 channel.
	 When you enable this option on a connection (channel) then all the
	 cells that are coming from the network side would be looped back
	 toward the network and all the frames coming from the user side
	 would be dropped.
	 This channel remote loopback has nothing to do with the chanTestType
	 option, each one does a different function. 
	 For example, the channel remote loopback is used for looping the data
	 toward the network and if this connection is terminated on an IPX
	 then they can put a test equipment and measure some of the 
	 characteristics of the network.
	1 = enable
	2 = disable
        " 
        DEFVAL { disable }
        ::= { ausmChanCnfGrpEntry 33}

 
ausmChanTestType 		OBJECT-TYPE  
	SYNTAX  INTEGER {
		testcon(1),
		testdelay(2),
		notest(3)
	}
	ACCESS read-write 
	STATUS  mandatory  
	DESCRIPTION    
        "The default is notest.
	 The chanTestType starts testing the continuity or delay of a connection.
	 It sends specific cell patterns toward the network and the terminating
	 end of this connection has to be an AXIS or ASI of a BPX in order for 
	 this test to be working. 
	 The receiving node would loop back when it receives these
	 cells. The test should be done in about couple of seconds. The testcon
	 tests the continuity of the connection and testdelay uses the same
	 test except that it measures for delay through the network. 
	 To test the delay follow this procedure:
		a- set chanTestType to testdelay
		b- read chanTestState till it is Pass or Fail 
		c- Read chanRTDResult for the delay if it is Pass
		*Note that the chanTestType would go back to notest when the
		 test is completed 
	 To test the continuity follow this procedure:
		a- set chanTestType to testcon
		b- read chanTestState till it is Pass or Fail 
		*Note that the chanTestType would go back to notest when the
		 test is completed 
	 You CAN NOT select 2 tests back to back, you have selcelt one and wait 
	 the result and then start the other one.
    SYNTAX  
	 When you select testdelay 
	 
	 This is the type of the test
	 1 = Test Continuity
	 2 = Test Delay
	 3 = No Test
        " 
        DEFVAL { notest }
        ::= { ausmChanCnfGrpEntry 34}
 
ausmChanTestState 		OBJECT-TYPE  
	SYNTAX  INTEGER {
		passed(1),
		failed(2),
		inprogress(3),
		notinprogress(4)
	} 
	ACCESS read-only 
	STATUS  mandatory  
	DESCRIPTION    
        "This shows the state of the test
	 When you add a connection then the chanTestState becomes notinprogress
	 and when you select any test, it would go to inprogress state and after
	 it completes the test, it will go to failed or passed state.
	 1 = Passed
	 2 = Failed
	 3 = In Progress 
	 4 = Not In Progress
        " 
        DEFVAL { notinprogress }
        ::= { ausmChanCnfGrpEntry 35}

ausmChanRTDResult 		OBJECT-TYPE  
	SYNTAX  INTEGER (1..65535)  
	ACCESS read-only 
	STATUS  mandatory  
	DESCRIPTION    
        "This is round trip delay in milliseconds.
	 When you select testdelay option for the chanTestType, the result of
	 the test that is measured in milliseconds can be read in chanRTDResult.
        " 
        ::= { ausmChanCnfGrpEntry 36}

-- CPE side OAM segment loopback
 
ausmChanTestTypeCPESide		OBJECT-TYPE  
	SYNTAX  INTEGER {
		testconseg(1),
		notest(2)
	}
	ACCESS read-write 
	STATUS  mandatory  
	DESCRIPTION    
        "The default is notest.
	 The chanTestType starts testing the segment continuity of a connection.
	 It sends OAM Segment loopback cell towards port side (CPE)
	 The CPE would loop back the cell
	 To test the continuity follow this procedure:
		a- set chanTestTypeCPEside to testconseg
		b- read chanTestState till it is Pass or Fail 
		*Note that the chanTestType would go back to notest when the
		 test is completed 
    SYNTAX  
	 When you select testdelay 
	 
	 This is the type of the test
	 1 = Test Continuity
	 2 = No Test
        " 
        ::= { ausmChanCnfGrpEntry 37}
 
ausmChanTestStateCPESide 	OBJECT-TYPE  
	SYNTAX  INTEGER {
		passed(1),
		failed(2),
		inprogress(3),
		notinprogress(4)
	} 
	ACCESS read-only 
	STATUS  mandatory  
	DESCRIPTION    
        "This shows the state of the test
	 When you add a connection then the chanTestState becomes notinprogress
	 and when you select any test, it would go to inprogress state and after
	 it completes the test, it will go to failed or passed state.
	 1 = Passed
	 2 = Failed
	 3 = In Progress 
	 4 = Not In Progress
        " 
        ::= { ausmChanCnfGrpEntry 38}


ausmChanIngrPercentUtil		OBJECT-TYPE
	SYNTAX  INTEGER (1..127)  
	ACCESS read-write 
	STATUS  mandatory  
	DESCRIPTION    
		"Percentage Utilization of the IngrService Rate. This is used
		 for connection admission control.
		" 
	DEFVAL { 100 }
        ::= { ausmChanCnfGrpEntry 39}


ausmChanEgrPercentUtil		OBJECT-TYPE
	SYNTAX  INTEGER (1..127)  
	ACCESS read-write 
	STATUS  mandatory  
	DESCRIPTION    
		"Percentage Utilization of the EgrService Rate. This is used for
		 egress bandwidth calculation and connection admission control.
		" 
	DEFVAL { 100 }
        ::= { ausmChanCnfGrpEntry 40}


ausmChanEgrSrvRate	OBJECT-TYPE
	SYNTAX  INTEGER (1..38328)  
	ACCESS read-write 
	STATUS  mandatory  
	DESCRIPTION    
		" Egress service rate - This is used for egress bandwidth calculation
		  and for connection admission control. The actual value
          depends on the speed of the logical port (which can be
          a T1, E1 (normal), E1 (clear), IMA T1, IMA E1 (normal) or
          IMA E1 (clear) port. Note that the IMA port's speed is
          variable and depends on the number of links in the port. In
          AUSM (4-port), maximum value is 4830.
		" 
        ::= { ausmChanCnfGrpEntry 41}


ausmChanOvrSubOvrRide	OBJECT-TYPE
 	SYNTAX  INTEGER {
	        disable (1),
    	  	enable (2)
       		 }
	ACCESS read-write 
	STATUS  mandatory  
	DESCRIPTION    
		"This MIB variable allows one to add a new connection on a port
		 even if it is over subscribed.
		" 
        DEFVAL { enable }
        ::= { ausmChanCnfGrpEntry 42}
 
ausmChanLocalVpId	OBJECT-TYPE
	SYNTAX  INTEGER (1..340)  
	ACCESS read-write 
	STATUS  mandatory  
	DESCRIPTION    
		" Every VP connection will have a unique local VpId  between
		  1 to 340. This is sent to ASC at the time of vp connection
		  setup. This number along with the slot number will form a
		  number which is unique across the shelf. This will be set
		  only at the time adding the connection.	
          This range varies dpending on the BNM interface.
          For STI 1..100
          For UNI 1..20
          For NNI 1..340
          In case of AUSM-4P maximum localVpId can be only 1..255
		" 
        ::= { ausmChanCnfGrpEntry 43}

ausmChanRMEnable		OBJECT-TYPE
	SYNTAX	INTEGER {
		disable (1),
		enable (2)
		} 
	ACCESS read-write
    STATUS  mandatory
    DESCRIPTION
        "enables/disables sending Resource Mangement Cells
		"
        ::= { ausmChanCnfGrpEntry 44}

ausmIngrDiscardOption	OBJECT-TYPE	
	SYNTAX	INTEGER {
		clpHysterisis (1),
		frameDiscard (2)
		}
	ACCESS read-write
	STATUS  mandatory
	DESCRIPTION
		"This variable specifies whether Frame based Discard is to be
		 enabled or CLP Threshold is to be used for determining the
		 criterion for dropping cells. FrameDiscard enables the EPD/PPD
		 features
		"
	DEFVAL {clpHysterisis}
   	::= { ausmChanCnfGrpEntry 45 }

ausmIngrFrDiscardThreshold OBJECT-TYPE	
	SYNTAX	INTEGER (0..16000)
	ACCESS read-write
	STATUS  mandatory
	DESCRIPTION
		"This variable specifies the Ingress Frame Discard Threshold.
		 Valid only when Ingress Frame Discard option is selected. By
		 default, the value of this variable would be the peak queue
		 depth of the queue. The value of this variable should be less
		 than the peak queue depth that is configured for the queue
		"
   	::= { ausmChanCnfGrpEntry 46 }

ausmCDRNumber OBJECT-TYPE
	SYNTAX INTEGER 
	ACCESS read-write
	STATUS mandatory
	DESCRIPTION
		"This is the key to correlate cell/frame counts, start/end record.
		"
	::= { ausmChanCnfGrpEntry 47}


ausmLocalVpi OBJECT-TYPE
	SYNTAX 	INTEGER (0..65535)
	ACCESS	read-only
	STATUS	mandatory
	DESCRIPTION
		"This VPI has different meaning with the end point VPI (CPE),
		 it can be same with the end point VPI but not necessary,
		 it represents the local end point VPI, this object is
		 read only, therefore, SM is responsible to assign a value 
		 to it.
		"
	::= { ausmChanCnfGrpEntry 48 }

ausmLocalVci OBJECT-TYPE
	SYNTAX 	INTEGER (0..65535)
	ACCESS	read-only
	STATUS	mandatory
	DESCRIPTION
		"This VCI has different meaning with the end point VCI (CPE),
		 it can be same with the end point VPI but not necessary
		 it represents the local end point VCI, this object is
		 read only, therefore, SM is responsible to assign a value 
		 to it.
		"
	::= { ausmChanCnfGrpEntry 49 }

ausmLocalNSAP OBJECT-TYPE
	SYNTAX	OCTET STRING (SIZE(0..20))
	ACCESS	read-write
	STATUS	mandatory
	DESCRIPTION
		"This NSAP is 20 bytes binary, among these 20 bytes: 13 bytes
		 as prefix, 2 bytes for Cisco ID, 2 bytes rsvd, 2 bytes for
		 slot (5 bits) and port number (11 bits), and 1 byte for SEL"
	::= { ausmChanCnfGrpEntry 50 }

ausmRemoteVpi OBJECT-TYPE
	SYNTAX 	INTEGER (0..65535)
	ACCESS	read-write
	STATUS	mandatory
	DESCRIPTION
		"This VPI has different with the remote end point VPI (CPE),
		 this is similar to a connection ID and it can be same
		 with the remote end point VPI but not necessary"
	::= { ausmChanCnfGrpEntry 51 }

ausmRemoteVci OBJECT-TYPE
	SYNTAX 	INTEGER (0..65535)
	ACCESS	read-write
	STATUS	mandatory
	DESCRIPTION
		"This VCI has different with the remote end point VCI (CPE),
		 this is similar to a connection ID and it can be same
		 with the remote end point VPI but not necessary"
	::= { ausmChanCnfGrpEntry 52 }

ausmRemoteNSAP OBJECT-TYPE
	SYNTAX	OCTET STRING (SIZE(0..20))
	ACCESS	read-write
	STATUS	mandatory
	DESCRIPTION
		"This NSAP is 20bytes binary, among these 20 bytes: 13 bytes
		 as prefix, 2 bytes for Cisco ID, 2 bytes rsvd, 2 bytes for
		 slot (5 bits) and port number (11 bits), and 1 byte for SEL"
	::= { ausmChanCnfGrpEntry 53 }

ausmMastership OBJECT-TYPE
	SYNTAX INTEGER {
		master (1),
		slave (2),
		unknown (3)
	}
	ACCESS read-write
	STATUS mandatory
	DESCRIPTION
		" This is used by PXM to determine if this end point is 
		  master or slave. In AXIS shelf, unknown is always used,
		  but in MGX shelf, if unknown is set, PXM will fail
		  the set request.
		"
        DEFVAL { slave }
	::= { ausmChanCnfGrpEntry 54 }

ausmVpcFlag OBJECT-TYPE
	SYNTAX INTEGER {
		vpc (1),
		vcc (2)
	}
	ACCESS read-write
	STATUS mandatory
	DESCRIPTION
		" This represents the connection type, used for PXM to
		  identify VPC/VCC
		"
        DEFVAL { vcc }
	::= { ausmChanCnfGrpEntry 55 }

ausmConnServiceType OBJECT-TYPE
	SYNTAX INTEGER{
		cbr    (1),
		vbr    (2),
		ubr    (4),
		atfr   (5),
		abrstd (6),
		abrfst (7),
		rtvbr  (8),
		cbr1   (21),
		vbr1rt (22),
		vbr2rt (23),
		vbr3rt (24),
		vbr1nrt(25),
		vbr2nrt(26),
		vbr3nrt(27),
		ubr1   (28),
		ubr2   (29),
		stdabr (30),
		cbr2   (31),
		cbr3   (32)
	}
	ACCESS read-write
	STATUS mandatory
	DESCRIPTION
		  "This specifies the service type 
     		  1 ==> Constant Bit Rate
	      	  2 ==> Variable Bit Rate
        	  3 ==> Not used
		  4 ==> Unspecified Bit Rate
		  5 ==> ATM frame relay
		  6 ==> standard ABR
		  7 ==> foresight ABR
		  8 ==> Real-Time Variable Bit Rate
		Note that this is used by PXM card, FRSM doesn't need to set it
		Also to make it compatible with existing AUSM MIB definition,
		value 3 is not used.

	The following types are being added for PNNI support.
        and are based on UNI 4.0
        cbr1   (21) - CBR.1
        vbr1rt (22) - Real time VBR.1
        vbr2rt (23) - Real time VBR.2
        vbr3rt (24) - Real time VBR.3
        vbr1nrt(25) - Non Real time VBR.1
        vbr2nrt(26) - Non Real time VBR.2
        vbr3nrt(27) - Non Real time VBR.3
        ubr1   (28) - UBR.1
        ubr2   (29) - UBR.2
        stdabr (30) - TM 4.0 compliant standard ABR
        cbr2   (31) - CBR.2
        cbr3   (32) - CBR.3
		"
        DEFVAL { cbr }
	::= { ausmChanCnfGrpEntry 56 }
		
ausmRoutingPriority OBJECT-TYPE
	SYNTAX  INTEGER (1..15)
	ACCESS	read-write
	STATUS 	mandatory
	DESCRIPTION
		" This is also known as class of service, it is used by
		  PXM to determine how important this connection is when 
		  selecting connections to route
		"
        DEFVAL { 1 }
	::= { ausmChanCnfGrpEntry 57 }
	
ausmMaxCost OBJECT-TYPE
        SYNTAX  INTEGER (1..2147483647)
        ACCESS  read-write
        STATUS  mandatory
        DESCRIPTION
                " Maximum allowed cost. It is related to Cost Based Routing.
                  This is used by PXM so that it won't choose a path with
                  a cost greater than this configured level.
          When used with PAR controller the valid range is 1..65535 and the
          default value is 255.
          When used with PNNI controller the valid range is 1..2147483647 and
          the default value is 2147483647.
                "
        ::= { ausmChanCnfGrpEntry 58 }

ausmRestrictTrunkType OBJECT-TYPE
	SYNTAX	INTEGER {
		noresriction (1),
		terrestrialTrunk (2),
		sateliteTrunk (3)
	}
	ACCESS	read-write
	STATUS	mandatory
	DESCRIPTION
		" Restricted trunk type for routing, used by PXM. It 
		  specifies that the connection either cannot be routed over
		  satelite trunks, or terrestrial trunks, or it can be on
		  any type of trunk.
		"
        DEFVAL { noresriction }
	::= { ausmChanCnfGrpEntry 59 }
 
ausmConnPCR OBJECT-TYPE
	SYNTAX INTEGER (10..38328)
	ACCESS read-write
	STATUS mandatory
	DESCRIPTION
		" Peak cell rate, if not set in MGX, will be derived
		  from the end point parameter
		"
	::= { ausmChanCnfGrpEntry 60 }

ausmConnMCR OBJECT-TYPE
	SYNTAX INTEGER (10..38328)
	ACCESS read-write
	STATUS mandatory
	DESCRIPTION
		" Minimum cell rate, if not set in MGX, will be derived
		  from the end point parameter
		"
	::= { ausmChanCnfGrpEntry 61 }

ausmConnPercentUtil OBJECT-TYPE
	SYNTAX INTEGER  (0..100)
	ACCESS read-write
	STATUS mandatory
	DESCRIPTION
		"This is the expected long-term utilization of the
		 channel by theis end-point."
        DEFVAL { 100 }
	::= {ausmChanCnfGrpEntry 62 }

ausmConnRemotePCR OBJECT-TYPE
	SYNTAX INTEGER (10..38328)
	ACCESS read-write
	STATUS mandatory
	DESCRIPTION
		" Peak cell rate of the other end, if not set in MGX, will be 
		  derived from the end point parameter
		"
	::= { ausmChanCnfGrpEntry 63 }

ausmConnRemoteMCR OBJECT-TYPE
	SYNTAX INTEGER (10..38328)
	ACCESS read-write
	STATUS mandatory
	DESCRIPTION
		" Minimum cell rate of the other end, if not set in MGX, will be 
		  derived from the end point parameter
		"
	::= { ausmChanCnfGrpEntry 64 }

ausmConnRemotePercentUtil OBJECT-TYPE
	SYNTAX INTEGER  (0..100)
	ACCESS read-write
	STATUS mandatory
	DESCRIPTION
		"This is the expected long-term utilization of the
		 channel by the other end-point."

        DEFVAL { 100 }
	::= {ausmChanCnfGrpEntry 65 }

ausmConnForeSightEnable OBJECT-TYPE
	SYNTAX INTEGER {
	enable(1),
	disable(2)
	}
	ACCESS read-write
	STATUS mandatory
	DESCRIPTION
		"This object is used by the controller(PAR/PNNI/TAG) to set up
		 the Qbin for the connection"

        DEFVAL { disable }
	::= {ausmChanCnfGrpEntry 66 }

ausmConnFGCRAEnable OBJECT-TYPE
	SYNTAX INTEGER {
	enable(1),
	disable(2)
	}
	ACCESS read-write
	STATUS mandatory
	DESCRIPTION
		"enables/disables Frame based GCRA (early packet discard).
		 "
    DEFVAL {disable}
	::= {ausmChanCnfGrpEntry 67 }

ausmChanReroute    OBJECT-TYPE
    SYNTAX INTEGER {
           true (1),
           false (2) 
    }
    ACCESS read-write
    STATUS mandatory
    DESCRIPTION
       " This is used by the administrator to trigger the re-routing
         of the connection. The rerouting takes effect, when this object
         is set to true(1). When set to false (2), no action is taken.
         A get on this object always returns false (2).
         This object is not applicable to MGX Release 1.x.
       "
    DEFVAL {false}
    ::= { ausmChanCnfGrpEntry 68 }

ausmConnSCR OBJECT-TYPE
    SYNTAX INTEGER (10..38328)
    ACCESS read-write
    STATUS mandatory
    DESCRIPTION
        " Sustained cell rate, Used for VBR connections setup with PNNI
        controller.
        "
    ::= { ausmChanCnfGrpEntry 69 }

ausmConnRemoteSCR OBJECT-TYPE
    SYNTAX INTEGER (10..38328)
    ACCESS read-write
    STATUS mandatory
    DESCRIPTION
        " Sustained cell rate of the other end,  Used for VBR connections
        setup with PNNI controller.
        "
    ::= { ausmChanCnfGrpEntry 70 }

ausmConnMBS OBJECT-TYPE
    SYNTAX INTEGER (1..5000)
    ACCESS read-write
    STATUS mandatory
    DESCRIPTION
        " Maximum burst size,  Used for VBR connections
        setup with PNNI controller.

        In MGX switches, release 3.0.0.0 and above,
        the default value is 1024
        "
    ::= { ausmChanCnfGrpEntry 71 }

ausmConnRemoteMBS OBJECT-TYPE
    SYNTAX INTEGER (1..5000000)
    ACCESS read-write
    STATUS mandatory
    DESCRIPTION
        " Maximum burst size at the remote end of the connection,
        Used for VBR connections setup with PNNI controller.

        "
    ::= { ausmChanCnfGrpEntry 72 }


ausmConnTemplateId OBJECT-TYPE
    SYNTAX INTEGER (1..17)
    ACCESS read-write
    STATUS mandatory
    DESCRIPTION
        "This object specifies the template identifier for the connection
         template associated with this connection.
         The valid range for templates is 1..16.
         A value of 17 indicates no template is associated with this
         connection"

    DEFVAL {17}
    ::= { ausmChanCnfGrpEntry 73 }

ausmConnAdminStatus OBJECT-TYPE
    SYNTAX INTEGER {
        up(1),
        down(2)
    }
    ACCESS read-write
    STATUS mandatory
    DESCRIPTION
        "This object specifies channel admin status.
         This object is not applicable to MGX Release 1.x.
         "

    DEFVAL {down}
    ::= { ausmChanCnfGrpEntry 74 }

--
--	Next available channel
--

ausmChanNumNextAvailable 	OBJECT-TYPE
	SYNTAX	INTEGER (16..1015) 
	ACCESS	read-only 
	STATUS	mandatory
	DESCRIPTION
		"This variable contains the next unused channel number of the possible
		 1000. This number can be used in channel config table.
		 ChanNumNextAvailable gets updated whenever this number is used to
		 create a new logical channel. Value 0 for this variable indicates that
		 no more channels are available. In AUSM (4-port card), the maximum
         number of values for this variable is 256 (i.e. 16 ..271).
		"
	::= { ausmChanCnfGrp 2 }

--NextAvailable local  VPID

ausmChanVpIdNextAvailable 	OBJECT-TYPE
	SYNTAX	INTEGER (1..100)
	ACCESS	read-only
	STATUS	mandatory
	DESCRIPTION
		"This variable contains the next unused local VPId of the possible
		 1 to 100. This number can be used in channel config table. It gets
		 updated if the number is used to create a new vp connection. There
		 can max 100 vp connections per slot. Value of 0 for this variable
		 indicates that no more vp connections are available. 
		"
	::= { ausmChanCnfGrp 3 }



-- ------------------------------------------------------------------------
-- End of ausmChanCnf group definitions


-- ----------------------------------------------------------------------
-- ausmStdABRCnfGrp.my
--
-- MIB for Standard ABR in AUSM
-- ----------------------------------------------------------------------





-- ausmChanCnfGrp          OBJECT IDENTIFIER ::= { ausmChan 1} 
		
-- ----------------------------------------------------------------------
-- AUSM Standard ABR Configuration Group
--
-- ausmStdABRCnfGrp definitions
-- Channel configurable parameters
--
-- ----------------------------------------------------------------------

ausmStdABRCnfGrpTable	OBJECT-TYPE
    SYNTAX  SEQUENCE OF AusmStdABRCnfGrpEntry
    ACCESS	not-accessible
    STATUS	mandatory
    DESCRIPTION
        "The ABR config table is for logical channel interface
         there are 1000 entries for the 8 logical ports in AUSM
         (8-port).
	"
    ::= { ausmChanCnfGrp 4 }


ausmStdABRCnfGrpEntry OBJECT-TYPE
    SYNTAX  AusmStdABRCnfGrpEntry
    ACCESS  not-accessible
    STATUS  mandatory
    DESCRIPTION
        " An entry for logical channel
        "
    INDEX   { ausmStdABRCnfChanNum }
    ::= { ausmStdABRCnfGrpTable 1 }


AusmStdABRCnfGrpEntry ::=
    SEQUENCE {
        ausmStdABRCnfChanNum	INTEGER,
        ausmStdABRType		INTEGER,
        ausmStdABRTBE		INTEGER,
        ausmStdABRFRTT		INTEGER,
        ausmStdABRRDF		INTEGER,
        ausmStdABRRIF		INTEGER,
        ausmStdABRNrm		INTEGER,
        ausmStdABRTrm		INTEGER,
        ausmStdABRCDF		INTEGER,
        ausmStdABRADTF		INTEGER,
        ausmStdABRICR           INTEGER,
        ausmStdABRMCR           INTEGER,
        ausmStdABRPCR           INTEGER
    }   
	
ausmStdABRCnfChanNum	OBJECT-TYPE
    SYNTAX  INTEGER (16..1015)
    ACCESS  read-only
    STATUS  mandatory
    DESCRIPTION
        "Refers to the virtual connection index.
        "
    ::= { ausmStdABRCnfGrpEntry 1}

ausmStdABRType         OBJECT-TYPE
    SYNTAX  INTEGER {
    	switchBehaviour (1),
	srcDestBehaviour (2)
    } 
    ACCESS  read-write
    STATUS  mandatory
    DESCRIPTION
 	"StdabrType of value 1 indicates a TM4.0 switch behaving 
	 connection (Transparent connection) which assumes that RM cells
 	 will be received from a TM4.0 compliant CPE. Value 2 indicates 
 	 a TM4.0 source destination behaving connection (Terminating 
	 connection)  which generates RM cells by itself. 
	"
    ::= { ausmStdABRCnfGrpEntry 2 }

ausmStdABRTBE            OBJECT-TYPE
    SYNTAX  INTEGER (0..16777215)
    ACCESS  read-write
    STATUS  mandatory
    DESCRIPTION
    	"Transient Buffer Exposure. The unit is number of cells. 
    	"
    DEFVAL {16777215}
    ::= { ausmStdABRCnfGrpEntry 3 }

ausmStdABRFRTT           OBJECT-TYPE
    SYNTAX  INTEGER (0..16700)
    ACCESS  read-write
    STATUS  mandatory
    DESCRIPTION
     	"Fixed Round-Trip Time. The unit is milliseconds. Value 0 
     	 signifies that FRTT value is not available. 
     	"
    DEFVAL {0}
    ::= { ausmStdABRCnfGrpEntry 4 }


ausmStdABRRDF            OBJECT-TYPE
    SYNTAX  INTEGER (1..32768)
    ACCESS  read-write
    STATUS  mandatory
    DESCRIPTION
    	"Rate Decrease Factor. This unitless value has to be inversed
    	 to arrive at the actual value. The valid values possible are
    	 only powers of 2; i.e.  1, 2, 4, 8 .....  32768 . The SNMP 
    	 agent has to verify this compliance. 
    	"
    DEFVAL {16}
    ::= { ausmStdABRCnfGrpEntry 5 }

ausmStdABRRIF            OBJECT-TYPE
    SYNTAX  INTEGER (1..32768)
    ACCESS  read-write
    STATUS  mandatory
    DESCRIPTION
    	"Rate Increase Factor.  This unitless value has to be inversed
    	 to arrive at  the actual value. The valid values possible are
    	 are only powers of 2; i.e.  1, 2, 4, 8 .....  32768 . The SNMP
    	 agent has to verify this compliance.
    	"
    DEFVAL {64}
    ::= { ausmStdABRCnfGrpEntry 6 }

ausmStdABRNrm            OBJECT-TYPE
    SYNTAX  INTEGER (2..256)
    ACCESS  read-write
    STATUS  mandatory
    DESCRIPTION
    	"Maximum number of cells a source may send for each forward RM
    	 cell. The valid values possible     are only powers of 2 starting
    	 from 2 ; i.e.  2, 4, 8 .....  256. The SNMP agent has to verify 
    	 this compliance. 
    	"
    DEFVAL {64}
    ::= { ausmStdABRCnfGrpEntry 7 }

ausmStdABRTrm            OBJECT-TYPE
    SYNTAX  INTEGER (3..255)
    ACCESS  read-write
    STATUS  mandatory
    DESCRIPTION
    	"Upper bound on the time between forward RM cells for an active
    	 source. The unit is in milliseconds. 
    	"
    DEFVAL {255}
    ::= { ausmStdABRCnfGrpEntry 8 }

ausmStdABRCDF            OBJECT-TYPE
    SYNTAX  INTEGER (0..64)
    ACCESS  read-write
    STATUS  mandatory
    DESCRIPTION
    	"Cutoff Decrease Factor. This unitless value has to be inversed 
    	 to arrive at the actual value. The valid values possible are 0
    	 and only powers of 2; i.e.  1, 2, 4, 8, 16, 32, 64 . The SNMP 
    	 agent has to verify this compliance. 
    	"
    DEFVAL {16}
    ::= { ausmStdABRCnfGrpEntry 9 }

ausmStdABRADTF           OBJECT-TYPE
    SYNTAX  INTEGER (10..10230)
    ACCESS  read-write
    STATUS  mandatory
    DESCRIPTION
    	"ACR Decrease Time Factor. Unit of this value is milliseconds. 
    	 Granularity allowed is 10 milli seconds. The SNMP agent has to 
    	 verify this compliance. 
    	"
    DEFVAL {500}
    ::= { ausmStdABRCnfGrpEntry 10 }

ausmStdABRICR            OBJECT-TYPE
    SYNTAX  INTEGER (10..38328)
    ACCESS  read-write
    STATUS  mandatory
    DESCRIPTION
     	"Initial cell Rate. The actual value depends on the speed of the
     	 logical port (which can be a T1, E1 (normal), E1 (clear), IMA T1,
     	 IMA T1, IMA E1 (normal) or IMA E1 (clear) port. Note that the
     	 IMA port's speed is variable and depends on the number of
     	 links in the port. 
     	"
     DEFVAL {10}
    ::= { ausmStdABRCnfGrpEntry 11 }

ausmStdABRMCR            OBJECT-TYPE
    SYNTAX  INTEGER (10..38328)
    ACCESS  read-write
    STATUS  mandatory
    DESCRIPTION
       	"Minimum cell Rate. The actual value depends on the speed of the
       	 logical port (which can be a T1, E1 (normal), E1 (clear), IMA T1
       	 IMA E1 (normal) or IMA E1 (clear) port. Note that the IMA port's
       	 speed is  variable and depends on the  number of links in the port.
         Please note that the MCR value will include bandwidth occupied
         by Data cells as well as all in-rate RM cells.
       	"
    DEFVAL {10}
    ::= { ausmStdABRCnfGrpEntry 12 }

ausmStdABRPCR            OBJECT-TYPE
    SYNTAX  INTEGER (10..38328)
    ACCESS  read-write
    STATUS  mandatory
    DESCRIPTION
        "Peak cell Rate. The actual value depends on the speed of the
         logical port (which can be a T1, E1 (normal), E1 (clear), IMA T1
         IMA E1 (normal) or IMA E1 (clear) port. Note that the IMA port's
         speed is  variable and depends on the  number of links in the port.
         Please note that the PCR value will include bandwidth occupied
         by Data cells as well as all in-rate RM cells.
        "
    DEFVAL {10}
    ::= { ausmStdABRCnfGrpEntry 13 }



-- ------------------------------------------------------------------------
-- End of ausmStdABRCnf group definitions

--
-- ----------------------------------------------------------------------
-- BASIS Project MIB
-- 
--






-- atm                  OBJECT IDENTIFIER ::= { basisServices 2 }
--ausmChan                OBJECT IDENTIFIER ::= { atm 2 }
ausmChanCntGrp          OBJECT IDENTIFIER ::= { ausmChan 3 }


-- ------------------------------------------------------------------------
--
-- ausmChannelCounters group
-- Channel OR VC COUNTERS 
--
-- ------------------------------------------------------------------------


ausmChanCntGrpTable	OBJECT-TYPE
	SYNTAX	SEQUENCE OF AusmChanCntGrpEntry
	ACCESS	not-accessible
	STATUS	mandatory
	DESCRIPTION
		"The config table is for logical channel interface
		 there are 1000 entries for 8 logical ports. In AUSM (4-port
         card), a logical port is synonymous with a physical port and
         the number of supported entries in this table is 256.
		"
	::= { ausmChanCntGrp 1 }


ausmChanCntGrpEntry	OBJECT-TYPE
	SYNTAX	AusmChanCntGrpEntry
	ACCESS	not-accessible
	STATUS	mandatory
	DESCRIPTION
		" An entry for logical channel
		"
	INDEX	{ ausmCntChanNum }
	::= { ausmChanCntGrpTable 1}

AusmChanCntGrpEntry ::=
	SEQUENCE {
		ausmCntChanNum 	
			INTEGER,
		chanSecInService
			Counter,
		chanCongestMinutes
			Counter,
		chanIngrPeakQDepth
			INTEGER,
-- Ingress Receive  
		chanIngrRcvCells	
			Counter,
		chanIngrClpSetRcvCells
			Counter,
		chanIngrEfciSetRcvCells
			Counter,
		chanIngrQfullDiscardCells
			Counter,
		chanIngrClpSetDiscardCells
			Counter,
		chanIngrUpcClpSetCells
			Counter,
-- Ingress Transmit
		chanIngrXmtCells
			Counter,
		chanShelfAlarmDiscardCells
			Counter,
-- Reset counters
		ausmChanClrButton
			INTEGER,
		chanEpdDiscCells
			Counter,
		chanPpdDiscCells
			Counter,

-- Percentage Utilization Counters
        chanIngrRcvCellRate
            Gauge,
        chanIngrRcvUtilization
            Gauge,
        chanIngrXmtCellRate
            Gauge,
        chanIngrXmtUtilization
            Gauge,
        chanEgrRcvCellRate
            Gauge,
        chanEgrRcvUtilization
            Gauge,
        chanIngrXmtAAL5Frames
            Counter,
        chanIngrEfciSetXmtCells
            Counter,
        chanEgrPortQfullDiscardCells
            Counter,
        chanEgrPortQClpThresDiscardCells
            Counter,
        chanTxFifoFullCnt
            Counter,
        chanIngrCurrQDepth
            INTEGER

}

ausmCntChanNum OBJECT-TYPE
	SYNTAX	INTEGER (16..1015)
	ACCESS	read-only
	STATUS	mandatory
	DESCRIPTION		  
		"Refers to the logical channel number. In AUSM (4-port card),
         the permissible range is from 16..271.
		"
	::= { ausmChanCntGrpEntry 1}

chanSecInService	OBJECT-TYPE
	SYNTAX	Counter
	ACCESS	read-only
	STATUS	mandatory
	DESCRIPTION		  
		"The number of seconds channel is in service
		"
	::= { ausmChanCntGrpEntry	2 }

chanCongestMinutes	OBJECT-TYPE
	SYNTAX	Counter
	ACCESS	read-only
	STATUS	mandatory
	DESCRIPTION		  
		"The number of minutes for which congestion was
		 experienced
		"
	::= { ausmChanCntGrpEntry	3 }

chanIngrPeakQDepth		OBJECT-TYPE
	SYNTAX	INTEGER (0..'ffff'h)
	ACCESS	read-only
	STATUS	mandatory
	DESCRIPTION		  
		"Peak queue depth on the ingress direction
		"
	::= { ausmChanCntGrpEntry	4 }

-- Ingress Receive  

chanIngrRcvCells	OBJECT-TYPE
	SYNTAX	Counter
	ACCESS	read-only
	STATUS	mandatory
	DESCRIPTION		  
		"The number of cells received in the Ingress direction
		"
	::= { ausmChanCntGrpEntry	5 }

chanIngrClpSetRcvCells	OBJECT-TYPE
	SYNTAX	Counter
	ACCESS	read-only
	STATUS	mandatory
	DESCRIPTION		  
		"The number of CLP set cells received in Ingress direction
		"
	::= { ausmChanCntGrpEntry	6 }

chanIngrEfciSetRcvCells	OBJECT-TYPE
	SYNTAX	Counter
	ACCESS	read-only
	STATUS	mandatory
	DESCRIPTION		  
		"The number of EFCI set cells received in Ingress direction
		"
	::= { ausmChanCntGrpEntry	7 }

chanIngrQfullDiscardCells	OBJECT-TYPE
	SYNTAX	Counter
	ACCESS	read-only
	STATUS	mandatory
	DESCRIPTION		  
		"The number of cells discarded due to ingress Q full
		"
	::= { ausmChanCntGrpEntry	8 }

chanIngrClpSetDiscardCells	OBJECT-TYPE
	SYNTAX	Counter
	ACCESS	read-only
	STATUS	mandatory
	DESCRIPTION		  
		"The number of CLP set cells discarded in Ingress direction
		"
	::= { ausmChanCntGrpEntry	9 }

chanIngrUpcClpSetCells	OBJECT-TYPE
	SYNTAX	Counter
	ACCESS	read-only
	STATUS	mandatory
	DESCRIPTION		  
		"The number of cells for which CLP was set by UPC
		"
	::= { ausmChanCntGrpEntry	10 }


-- Ingress Transmit

chanIngrXmtCells	OBJECT-TYPE
	SYNTAX	Counter
	ACCESS	read-only
	STATUS	mandatory
	DESCRIPTION		  
		"The number of cells transmitted to the cellbus
		"
	::= { ausmChanCntGrpEntry	11 }

chanShelfAlarmDiscardCells	OBJECT-TYPE
	SYNTAX	Counter
	ACCESS	read-only
	STATUS	mandatory
	DESCRIPTION		  
		"The number of cells discarded due to Shelf Alarm
		"
	::= { ausmChanCntGrpEntry	12 }


ausmChanClrButton OBJECT-TYPE
               SYNTAX  INTEGER {
                        noAction (1),
                        resetCounters (2)
                        }
                ACCESS  read-write
                STATUS  mandatory
                DESCRIPTION
                        "writing a value of 2 resets all the counters
                        "
	::= { ausmChanCntGrpEntry	13 }
 
chanEpdDiscCells	OBJECT-TYPE
	SYNTAX	Counter
	ACCESS	read-only
	STATUS	mandatory
	DESCRIPTION		  
		"The number of cells discarded due to EPD (Early Packet Discard)
		 condition
		"
	::= { ausmChanCntGrpEntry	14 }

chanPpdDiscCells	OBJECT-TYPE
	SYNTAX	Counter
	ACCESS	read-only
	STATUS	mandatory
	DESCRIPTION		  
		"The number of cells discarded due to PPD (Partial Packet Discard)
		 condition
		"
	::= { ausmChanCntGrpEntry	15 }

chanIngrRcvCellRate OBJECT-TYPE
    SYNTAX  Gauge
    ACCESS  read-only
    STATUS  mandatory
    DESCRIPTION
        "The number of cells received per second from the port. Statistics
         collected before UPC and ingress qeueing. The maximum value is
         5000 because clear E1 rate is 4830.
        "
    ::= { ausmChanCntGrpEntry   16 }
 
chanIngrRcvUtilization  OBJECT-TYPE
    SYNTAX  Gauge
    ACCESS  read-only
    STATUS  mandatory
    DESCRIPTION
        "The percentage utilization of the reserved bandwidth (PCR). Statistics
         collected before UPC and ingress queueing. The maximum value is 200
         because a connection can oversubcribe.
        "
    ::= { ausmChanCntGrpEntry   17 }
 
chanIngrXmtCellRate OBJECT-TYPE
    SYNTAX  Gauge
    ACCESS  read-only
    STATUS  mandatory
    DESCRIPTION
        "The number of cells transmitted per second to the network. Statistics
         collected after UPC and ingress qeueing.
        "
    ::= { ausmChanCntGrpEntry   18 }
 
chanIngrXmtUtilization  OBJECT-TYPE
    SYNTAX  Gauge
    ACCESS  read-only
    STATUS  mandatory
    DESCRIPTION
        "The percentage utilization of the reserved bandwidth (PCR). Statistics
         collected after UPC and ingress queueing.
        "
    ::= { ausmChanCntGrpEntry   19 }

chanEgrRcvCellRate  OBJECT-TYPE
    SYNTAX  Gauge
    ACCESS  read-only
    STATUS  mandatory
    DESCRIPTION
        "The number of cells received per second from the network. Statistics
         collected before egress qeueing.
        "
    ::= { ausmChanCntGrpEntry   20 }
 
chanEgrRcvUtilization   OBJECT-TYPE
    SYNTAX  Gauge
    ACCESS  read-only
    STATUS  mandatory
    DESCRIPTION
        "The percentage utilization of the reserved bandwidth (PCR). Statistics
         collected before egress queueing.
        "
    ::= { ausmChanCntGrpEntry   21 }
 
chanIngrXmtAAL5Frames OBJECT-TYPE
    SYNTAX  Counter
    ACCESS  read-only
    STATUS  mandatory
    DESCRIPTION
        "This statistics provides a count of the  number of AAL5 Frames that are
         sent to the network
        "
    ::= { ausmChanCntGrpEntry   22 }
 
chanIngrEfciSetXmtCells OBJECT-TYPE
    SYNTAX  Counter
    ACCESS  read-only
    STATUS  mandatory
    DESCRIPTION
        "This statistics provides a count of the number of EFCI set cells
         that are transmitted to the network. This statistis is collected
         after the policing and queueing.
        "
    ::= { ausmChanCntGrpEntry   23 }
 
chanEgrPortQfullDiscardCells OBJECT-TYPE
    SYNTAX  Counter
    ACCESS  read-only
    STATUS  mandatory
    DESCRIPTION
        "This statistics provides a count of the  number of cells discarded
         because of Egress Port Queue full. This count is displayed for the
         queue corresponding to port and the service type to which this channel
         belongs.
 
        "
    ::= { ausmChanCntGrpEntry   24 }

chanEgrPortQClpThresDiscardCells OBJECT-TYPE
    SYNTAX  Counter
    ACCESS  read-only
    STATUS  mandatory
    DESCRIPTION
        "This statistics provides a count of the  number of cells discarded
         because of Egress Port Queue CLP Threshold exceed. This count is
         displayed for the queue corresponding to port and the service type to
         which this channel belongs.
        "
    ::= { ausmChanCntGrpEntry   25 }
 
chanTxFifoFullCnt OBJECT-TYPE
    SYNTAX  Counter
    ACCESS  read-only
    STATUS  mandatory
    DESCRIPTION
        "This statistics provides a count of the  number of times the AUSM
         card tried to send a cell, but was unable to send because the
         Transmit FIFO was full. Note that this is NOT a count of the number
         of cells dropped. This statistics is per card statistics.
        "
    ::= { ausmChanCntGrpEntry   26 }

chanIngrCurrQDepth      OBJECT-TYPE
    SYNTAX  INTEGER (0..'ffff'h)
    ACCESS  read-only
    STATUS  mandatory
    DESCRIPTION
        "Current queue depth on the ingress direction
        "
   ::= { ausmChanCntGrpEntry   27 }


-- ------------------------------------------------------------------------
-- End of ausmChanCnt group definitions


--
-- ----------------------------------------------------------------------
-- BASIS Project MIB
-- 
--





-- atm                  OBJECT IDENTIFIER ::= { basisServices 2 }
--ausmChan                OBJECT IDENTIFIER ::= { atm 2 }
ausmChanStateGrp        OBJECT IDENTIFIER ::= { ausmChan 2 }


-- ------------------------------------------------------------------------
--
-- Group ausmChannelState
-- Contains status information for channels
--
-- ------------------------------------------------------------------------


ausmChanStateGrpTable OBJECT-TYPE
	SYNTAX  SEQUENCE OF AusmChanStateGrpEntry
	ACCESS  not-accessible
	STATUS  mandatory
	DESCRIPTION
		"Table of transmit/receive states of channels.
		"
	::= { ausmChanStateGrp 1 }

ausmChanStateGrpEntry OBJECT-TYPE
	SYNTAX AusmChanStateGrpEntry
	ACCESS not-accessible
	STATUS mandatory
	DESCRIPTION
		"An entry for AusmChannelStateGrpEntry.
		"
	INDEX	{ ausmStateChanNum }
	::= { ausmChanStateGrpTable 1 }

AusmChanStateGrpEntry ::=
	SEQUENCE {
		ausmStateChanNum
         		INTEGER,
		ausmChanState
         		INTEGER,
		chanEgrXmtState
			INTEGER,
		chanIngrRcvState
			INTEGER,
		chanIngrXmtState
			INTEGER,
		chanEgrRcvState
			INTEGER,
        ausmChanStatusBitMap
            INTEGER
		}

ausmStateChanNum OBJECT-TYPE
	SYNTAX	INTEGER (16..1015)
	ACCESS	read-only
	STATUS	mandatory
	DESCRIPTION		  
		"Refers to the logical channel number. In AUSM (4-port card),
         the permissible range is from 16..271.
		"
	::= { ausmChanStateGrpEntry 1}

ausmChanState OBJECT-TYPE
	SYNTAX  INTEGER {
		notconfigured (1),
		normal(2),
		alarm(3),
        failed(4)

	}
	ACCESS  read-only
	STATUS  mandatory
	DESCRIPTION
		"This variable indicates the state of the
		 VC (channel)
         failed(4) is added to distinguish between alarm (when the connection
         segment is not actually broken) and failed(when the segment is actually
         broken). This is applicable only to the PNNI environment.
		"
	::= { ausmChanStateGrpEntry 2}
 
chanEgrXmtState	OBJECT-TYPE
	SYNTAX INTEGER {
		other(1),
		normal(2),
		sendingAis (3),
		sendingFerf (4)
		}
	ACCESS read-only
	STATUS mandatory
	DESCRIPTION
		"indicates the status of port transmit(Egress)
		"
	::= { ausmChanStateGrpEntry 3}

chanIngrRcvState 	OBJECT-TYPE
	SYNTAX INTEGER {
		other(1),
		normal(2),
		receivingAis (3),
		receivingFerf (4),
		alarm(5)
		}
	ACCESS read-only
	STATUS mandatory
	DESCRIPTION
		"indicates the status of port receive(Ingress)
		"
	::= { ausmChanStateGrpEntry 4}

chanIngrXmtState	 OBJECT-TYPE
	SYNTAX  INTEGER {
		other (1),
		normal(2),
		sendingAis(3),
		sendingFerf (4)
	}
	ACCESS  read-only
	STATUS  mandatory
	DESCRIPTION
		"This variable indicates the transmit state of the
		 VC (channel) on the Cellbus side (Ingress)
		 1 - other
		 2- normal
		 3 - sendingAIS
		 4 - sendingFerf
		"
	::= { ausmChanStateGrpEntry 5}
 
chanEgrRcvState		OBJECT-TYPE
	SYNTAX  INTEGER {
		other (1),
		normal(2),
		receivingAis(3),
		receivingFerf(4),
		alarm (5)
	}
	ACCESS  read-only
	STATUS  mandatory
	DESCRIPTION
		"This variable indicates the receiving state of the
		 VC (channel) on the Cellbus side (Egress)
		 1 - other
		 2- normal
		 3 - receivingAIS
		 4 - receivingFERF
		"
	::= { ausmChanStateGrpEntry 6}

ausmChanStatusBitMap OBJECT-TYPE
    SYNTAX  INTEGER (0..'ff'h)
    ACCESS  read-only
    STATUS  mandatory
    DESCRIPTION

        "This variable indicates the consolidated bit map of the channel alarm
        state.

        Individual bit positions are as defined below.

        Bit position   Fail/Alarm     Reason
        ------------   ----------     ------
            0           Alarm      port side AIS/RDI Rx
            1           Alarm      n/w side AIS/RDI Rx
            2           Fail       Conditioned(A bit from n/w)
            3           Alarm      Reserved         
            4           Fail       Reserved            
            5           Fail       Reserved            
            6           Alarm      Reserved            
            7           Alarm      Reserved

            Fail bitmap mask : 0x34
            Alarm bitmap mask: 0xCB

            This object is not applicable to MGX Release 1.x.
        "
    ::= { ausmChanStateGrpEntry 7}


-- ------------------------------------------------------------------------
-- End of ausmChanState group definitions


--
-- ----------------------------------------------------------------------
-- BASIS Project MIB
-- 
--


-- atm                OBJECT IDENTIFIER ::= { basisServices 2 }
ausmEndPointMapGrp    OBJECT IDENTIFIER ::= { atm 3 }


-- ------------------------------------------------------------------------
--
-- ausmEndPointMap group
--
-- This MIB Grp. is used in 3 products of Axis,MGX. They are
-- Ausm-4p , Ausm-8p, PXM (MGX).
--
-- So the Range of values for portNum, Vpi, Vci need to be checked
-- appropriately in the SNMP Agent code.
--
-- ------------------------------------------------------------------------


ausmEndPointMapGrpTable    OBJECT-TYPE
    SYNTAX    SEQUENCE OF AusmEndPointMapGrpEntry
    ACCESS    not-accessible
    STATUS    mandatory
    DESCRIPTION "
         For Ausm-4p      There are  255 entries 
         For Ausm-8p      There are 1000 entries 
         For PXM (MGX) There are 4096 entries 

         Port Num and VpiVci will uniquely identify a row.
    "
    ::= { ausmEndPointMapGrp 1 }

ausmEndPointMapGrpEntry    OBJECT-TYPE
    SYNTAX    AusmEndPointMapGrpEntry
    ACCESS    not-accessible
    STATUS    mandatory
    DESCRIPTION
        " An entry in the table
        "
    INDEX    { ausmEndPortNum, endVpi, endVci }
    ::= { ausmEndPointMapGrpTable 1 }

AusmEndPointMapGrpEntry ::=
    SEQUENCE {
        ausmEndPortNum        INTEGER,
        endVpi                INTEGER,
        endVci                INTEGER,
        ausmEndChanNum         INTEGER,
        endChanType            INTEGER
    }

ausmEndPortNum     OBJECT-TYPE
    SYNTAX  INTEGER (1..32)
    ACCESS  read-only
    STATUS  mandatory
    DESCRIPTION "
        Refers to the logical port on the board. In AUSM (4-port card),
        a logical port is synonymous with a physical port.

        In PXM, a port refers to the Logical Broadband Interface.
        Refer bbIfCnfPortGrp.my for more information.
    "
    ::= { ausmEndPointMapGrpEntry 1 }
 
endVpi         OBJECT-TYPE
    SYNTAX  INTEGER (0..4095)
    ACCESS  read-only
    STATUS  mandatory
    DESCRIPTION
        "The VPI value for the connection
    "
    ::= { ausmEndPointMapGrpEntry 2 }
 
endVci         OBJECT-TYPE
    SYNTAX  INTEGER (0..'ffff'h)
    ACCESS  read-only
    STATUS  mandatory
    DESCRIPTION
        "The VCI value for the connection
    "
    ::= { ausmEndPointMapGrpEntry 3 }
 
ausmEndChanNum     OBJECT-TYPE
    SYNTAX    INTEGER (16..4111)
    ACCESS    read-only
    STATUS    mandatory
    DESCRIPTION          
        "Refers to the logical connection for this port and VpiVci.

         In AUSM (4-port card), the permissible range is 16..271
         In AUSM (8-port card), the permissible range is 16..1015

         In PXM (MGX )     , the permissible range is 16..4111
    "
    ::= { ausmEndPointMapGrpEntry 4}

endChanType    OBJECT-TYPE
    SYNTAX    INTEGER {
        vpc (1),
        vcc (2)
    }
    ACCESS    read-only
    STATUS    mandatory
    DESCRIPTION          
        "Refers to the type of the connection for this Port and VpiVci 
    "
    ::= { ausmEndPointMapGrpEntry 5}



-- ------------------------------------------------------------------------
-- End of ausmEndPointMap group definitions
-- ------------------------------------------------------------------------

-- atm                  OBJECT IDENTIFIER ::= { basisServices 2 }
--ausmPort       		OBJECT IDENTIFIER ::= { atm 1 }
--ausmPortCnf		OBJECT IDENTIFIER ::= { ausmPort 1 }
ausmPortCnfPortGrp	OBJECT IDENTIFIER ::= { ausmPortCnf 1}

-- --------------------------------------------------------------------
--
--
--		AUSM PORT CONFIG Group
--
--
-- --------------------------------------------------------------------


ausmPortCnfPortGrpTable	OBJECT-TYPE
	SYNTAX	SEQUENCE OF AusmPortCnfPortGrpEntry
	ACCESS	not-accessible
	STATUS	mandatory
	DESCRIPTION
		"The config table is for logical port interface
		 there are 8 entries for either T1 or E1
		"
	::= { ausmPortCnfPortGrp 1 }


ausmPortCnfPortGrpEntry	OBJECT-TYPE
	SYNTAX	AusmPortCnfPortGrpEntry
	ACCESS	not-accessible
	STATUS	mandatory
	DESCRIPTION
		" An entry for logical port.  In AUSM (4-port card), a logical port
          is same as a physical port.
		"
	INDEX	{ ausmPortNum }
    ::= { ausmPortCnfPortGrpTable 1 }

AusmPortCnfPortGrpEntry ::=
	SEQUENCE {
		ausmPortNum 	
			INTEGER,
   		portEnable
         	INTEGER,
		ausmPortType
			INTEGER,	
		ausmPortIfType
			INTEGER,	
		ausmPortSpeed
			INTEGER,
		ausmLineNum
			INTEGER
		}

ausmPortNum	OBJECT-TYPE
	SYNTAX	INTEGER (1..8) 
	ACCESS	read-only
	STATUS	mandatory
	DESCRIPTION
		"This is logical port number. In AUSM (4-port card), a logical port
          is same as a physical port.
		"
	::= { ausmPortCnfPortGrpEntry 1}

portEnable  OBJECT-TYPE		
	SYNTAX	INTEGER {
		disable(1),
		enable(2)
		}
	ACCESS read-write
        STATUS  mandatory
        DESCRIPTION
        "This variable enables or disables the port
		1 - disable
		2 - enable
        "
        ::= { ausmPortCnfPortGrpEntry 2 }

ausmPortType  OBJECT-TYPE		
	SYNTAX	INTEGER {
		uni(1),
		nni(2),
		sti(3),
		vpTrkUni (4)
		}
	ACCESS read-write
        STATUS  mandatory
        DESCRIPTION
        "This variable  
		indicates whether UNI/NNI/STI interface
        STI mode is supported only in IMATM.
		vpTrkUni should be used only in IMATM when virtual trunks are
		passing through IMATM (i.e. the cell format is UNI but ForeSight
		information is carried in the lower 16 bits)
        "
        ::= { ausmPortCnfPortGrpEntry 3 }

ausmPortIfType  OBJECT-TYPE		
	SYNTAX	INTEGER {
		unknown(1),
		t1(2),
		e1(3)
		}
	ACCESS read-only
        STATUS  mandatory
        DESCRIPTION
        "This variable indicates the type of interface
        "
        ::= { ausmPortCnfPortGrpEntry 4 }

ausmPortSpeed  OBJECT-TYPE		
	SYNTAX	INTEGER 
	ACCESS read-only
        STATUS  mandatory
        DESCRIPTION
        "The speed of the port in cells per second 
        "
        ::= { ausmPortCnfPortGrpEntry 5 }

ausmLineNum  OBJECT-TYPE		
	SYNTAX	INTEGER 
	ACCESS read-write
        STATUS  mandatory
        DESCRIPTION
        "The line number associated with the logical port. For AUSM (4 port),
		 the line number is same as the logical port. In AUSM-8p, these two
		 can be different
        "
        ::= { ausmPortCnfPortGrpEntry 6 }


-- --------------------------------------------------------------
-- End of ausmPortCnfPortGrp
-- 
-- BASIS Project MIB
--


-- atm                  OBJECT IDENTIFIER ::= { basisServices 2 }
-- ausmPort             OBJECT IDENTIFIER ::= { atm 1 }
-- ausmPortCnf          OBJECT IDENTIFIER ::= { ausmPort 1 }
ausmPortCnfResPartGrp   OBJECT IDENTIFIER ::= { ausmPortCnf 5}
ausmPortDelSvcsGrp      OBJECT IDENTIFIER ::= { ausmPortCnf 6}

-- --------------------------------------------------------------------
--
--
--        AUSM PORT RESOURCE PARTITION Group
--
--
-- --------------------------------------------------------------------

ausmPortCnfResPartGrpTable    OBJECT-TYPE
    SYNTAX    SEQUENCE OF AusmPortCnfResPartGrpEntry
    ACCESS    not-accessible
    STATUS    mandatory
    DESCRIPTION
        "The config table is for logical port interface
         there are 4/8 entries for either T1 or E1 or AIMUX
         ports

         For PXM (MGX), there are 32 entries.
        "
    ::= { ausmPortCnfResPartGrp 1 }


ausmPortCnfResPartGrpEntry    OBJECT-TYPE
    SYNTAX    AusmPortCnfResPartGrpEntry
    ACCESS    not-accessible
    STATUS    mandatory
    DESCRIPTION
        " An entry for logical port
        "
    INDEX    { ausmResPartPortNum }
    ::= { ausmPortCnfResPartGrpTable 1 }

AusmPortCnfResPartGrpEntry ::=
    SEQUENCE {
        ausmResPartPortNum     
            INTEGER,
        ausmPortSvcInUse
            INTEGER,
        ausmPortSvcShareLcnVpid
            INTEGER,
        ausmPortSvcLcnLow
            INTEGER,
        ausmPortSvcLcnHigh
            INTEGER,
        ausmPortSvcVpidLow
            INTEGER,
        ausmPortSvcVpidHigh
            INTEGER,
        ausmPortSvcVciLow
            INTEGER,
        ausmPortSvcVciHigh
            INTEGER,
        ausmPortSvcVpiLow
            INTEGER,
        ausmPortSvcVpiHigh
            INTEGER,
        ausmPortIngrSvcBandW
            INTEGER,
        ausmPortEgrSvcBandW
            INTEGER
    }

ausmResPartPortNum    OBJECT-TYPE
    SYNTAX    INTEGER (1..32) 
    ACCESS    read-only
    STATUS    mandatory
    DESCRIPTION "
        This is logical port number

        In PXM, a port refers to the Logical Broadband Interface.
        Refer bbIfCnfPortGrp.my for more information.

    "
    ::= { ausmPortCnfResPartGrpEntry 1}

ausmPortSvcInUse OBJECT-TYPE        
    SYNTAX    INTEGER {
        inUse(1),
        notInUse(2)
    }
    ACCESS  read-write
    STATUS  mandatory
    DESCRIPTION "
        Setting this object to 1 indicates that the resources
        (LCN/Local VPID/VCI/VPI) have been partitioned and INS
        and SV+ are currently using this information. The resource
        partition information can be changed after setting this
        variable to 2.
        The default value is 2 (NotInUse).
    "
    ::= { ausmPortCnfResPartGrpEntry 2 }

ausmPortSvcShareLcnVpid OBJECT-TYPE        
    SYNTAX    INTEGER {
        portBased (1),
        cardBased (2)
    } 
    ACCESS  read-only
    STATUS  mandatory
    DESCRIPTION
        "Indicates whether or not the LCN and VPid address spaces
         are shared across all the ports.
         Default value is 2 (cardBased).
    "
    DEFVAL {cardBased}
    ::= { ausmPortCnfResPartGrpEntry 3 }

ausmPortSvcLcnLow OBJECT-TYPE        
    SYNTAX    INTEGER (16..4111)
    ACCESS  read-write
    STATUS  mandatory
    DESCRIPTION
        "The beginning of the LCN range reserved for SVCs.
         Both the LCN low and high values apply to all ports
         when the 'atmPortSvcShareLcnVpid' object is set to
         2 (CardBased). When they are changed for one port the
         change is applicable/propagated to all ports.
    "
    ::= { ausmPortCnfResPartGrpEntry 4 }

ausmPortSvcLcnHigh OBJECT-TYPE        
    SYNTAX    INTEGER (16..4111)
    ACCESS  read-write
    STATUS  mandatory
    DESCRIPTION
        "The end of the LCN range reserved for SVCs.
        "
    ::= { ausmPortCnfResPartGrpEntry 5 }

ausmPortSvcVpidLow OBJECT-TYPE        
    SYNTAX    INTEGER (1..100)
    ACCESS  read-write
    STATUS  mandatory
    DESCRIPTION
        "The beginning of the VPID range reserved for SVCs.
         Both the VPID low and high values apply to all ports
         when the 'atmPortSvcShareLcnVpid' object is set to
         2 (CardBased). When they are changed for one port the
         change is applicable/propagated to all ports.
    "
    ::= { ausmPortCnfResPartGrpEntry 6 }

ausmPortSvcVpidHigh OBJECT-TYPE        
    SYNTAX    INTEGER (1..100)
    ACCESS  read-write
    STATUS  mandatory
    DESCRIPTION
        "The end of the VPID range reserved for SVCs.
        "
    ::= { ausmPortCnfResPartGrpEntry 7 }

ausmPortSvcVciLow OBJECT-TYPE        
    SYNTAX    INTEGER (0..'ffff'h)
    ACCESS  read-write
    STATUS  mandatory
    DESCRIPTION
        "The beginning of the VCI range reserved for SVCs.
         For VPI connections the valid VCI values are 0 - 4095
        "
    ::= { ausmPortCnfResPartGrpEntry 8 }

ausmPortSvcVciHigh OBJECT-TYPE        
    SYNTAX    INTEGER (0..'ffff'h)
    ACCESS  read-write
    STATUS  mandatory
    DESCRIPTION
        "The end of the VCI range reserved for SVCs.
         For VPI connections the valid VCI values are 0 -4095
        "
    ::= { ausmPortCnfResPartGrpEntry 9 }

ausmPortSvcVpiLow OBJECT-TYPE        
    SYNTAX    INTEGER (0..4095)
    ACCESS  read-write
    STATUS  mandatory
    DESCRIPTION
        "The beginning of the VCI range reserved for SVCs.
        "
    ::= { ausmPortCnfResPartGrpEntry 10 }

ausmPortSvcVpiHigh OBJECT-TYPE        
    SYNTAX    INTEGER (0..4095)
    ACCESS  read-write
    STATUS  mandatory
    DESCRIPTION
        "The end of the VPI range reserved for SVCs.
        "
    ::= { ausmPortCnfResPartGrpEntry 11 }

ausmPortIngrSvcBandW        OBJECT-TYPE
    SYNTAX  INTEGER (0..100)
    ACCESS  read-write
    STATUS  mandatory
    DESCRIPTION
        "This represents Ingress Bandwidth reserved for SVC
        "
    ::= { ausmPortCnfResPartGrpEntry 12 }
 
ausmPortEgrSvcBandW OBJECT-TYPE
    SYNTAX  INTEGER (0..100)
    ACCESS  read-write
    STATUS  mandatory
    DESCRIPTION
        "This represents Egress Bandwidth reserved for SVC
        "
    ::= { ausmPortCnfResPartGrpEntry 13 }

-- --------------------------------------------------------------
-- End of ausmPortCnfPortGrp
-- --------------------------------------------------------------

-- --------------------------------------------------------------------
--
--
--        AUSM PORT DELETE SVC connections Group
--
--
-- --------------------------------------------------------------------


ausmPortDelSvcsGrpTable    OBJECT-TYPE
    SYNTAX    SEQUENCE OF AusmPortDelSvcsGrpEntry
    ACCESS    not-accessible
    STATUS    mandatory
    DESCRIPTION
        "The table is for logical port interface
         there are 4/8 entries for either T1 or E1 or AIMUX
         ports

         For PXM (MGX), there are 32 entries.
        "
    ::= { ausmPortDelSvcsGrp 1 }


ausmPortDelSvcsGrpEntry    OBJECT-TYPE
    SYNTAX    AusmPortDelSvcsGrpEntry
    ACCESS    not-accessible
    STATUS    mandatory
    DESCRIPTION
        " An entry for logical port
        "
    INDEX    { ausmDelSvcsPortNum }
    ::= { ausmPortDelSvcsGrpTable 1 }

AusmPortDelSvcsGrpEntry ::=
    SEQUENCE {
        ausmDelSvcsPortNum     
            INTEGER,
        ausmPortDeleteSvcs
            INTEGER
    }

ausmDelSvcsPortNum    OBJECT-TYPE
    SYNTAX    INTEGER (1..32) 
    ACCESS    read-only
    STATUS    mandatory
    DESCRIPTION
        "This is logical port number

         In PXM, a port refers to the Logical Broadband Interface.
         Refer bbIfCnfPortGrp.my for more information.

        "
    ::= { ausmPortDelSvcsGrpEntry 1}

ausmPortDeleteSvcs OBJECT-TYPE        
    SYNTAX    INTEGER {
        delete(1),
        other(2)
    }
    ACCESS  read-write
    STATUS  mandatory
    DESCRIPTION
        "Setting this object to 1 indicates that all the SVC
         connections on the given port has to be deleted
        "
    ::= { ausmPortDelSvcsGrpEntry 2 }

-- --------------------------------------------------------------
-- End of ausmPortDelSvcsGrp
-- --------------------------------------------------------------
 

-- atm                  OBJECT IDENTIFIER ::= { basisServices 2 }
-- ausmPort       		OBJECT IDENTIFIER ::= { atm 1 }
-- ausmPortCnf		OBJECT IDENTIFIER ::= { ausmPort 1 }
ausmPortCnfServiceQueGrp	OBJECT IDENTIFIER ::= { ausmPortCnf 2}

-- --------------------------------------------------------------------
--
--
--		AUSM PORT CONFIG Egress Queue Group
--
--
-- --------------------------------------------------------------------


ausmPortCnfServiceQueGrpTable	OBJECT-TYPE
	SYNTAX	SEQUENCE OF AusmPortCnfServiceQueGrpEntry
	ACCESS	not-accessible
	STATUS	mandatory
	DESCRIPTION
		"In AUSM (4port): the Service queue table has 64 entries,
		 16 each for every port, in addition there are 4 queues for 
		 OAM/ILMI traffic
		 In AUSM (8-port), the Service queue table has 128 entries,
		 16 each for every port, in addition there are 8 queues for 
		 OAM/ILMI traffic
		"
	::= { ausmPortCnfServiceQueGrp 1 }


ausmPortCnfServiceQueGrpEntry	OBJECT-TYPE
	SYNTAX	AusmPortCnfServiceQueGrpEntry
	ACCESS	not-accessible
	STATUS	mandatory
	DESCRIPTION
		" An entry for a single queue
		"
	INDEX	{ servicePortNum,egrQIndex }
    ::= { ausmPortCnfServiceQueGrpTable 1 }

AusmPortCnfServiceQueGrpEntry ::=
	SEQUENCE {
		egrQIndex 
			INTEGER,
      	servicePortNum
         	INTEGER,
		egrQBinState
			INTEGER,
		egrQServiceSequence
			INTEGER,
		egrQDepthMax
			INTEGER,
		egrQCLPThreshHigh
			INTEGER,
		egrQCLPThreshLow
			INTEGER,
		egrQEfciThresh
			INTEGER,
		egrQAlgorithm
			INTEGER,
		egrMaxBwInc
			INTEGER,
		egrMinBwInc
			INTEGER,
		egrQCLPState
			INTEGER,
-- Egress counters 
		egrQfullDiscardCells
			Counter,
		egrQClpSetDiscardCells
			Counter
		}

egrQIndex	OBJECT-TYPE
		SYNTAX	INTEGER (1..16) 
		ACCESS	read-only
		STATUS	mandatory
		DESCRIPTION
		"Egress queue number. In AUSM (4 port), only range from 1..12
		 is permissible
		"
		::= { ausmPortCnfServiceQueGrpEntry 1}

servicePortNum	OBJECT-TYPE
		SYNTAX	INTEGER (1..8)
		ACCESS	read-only
		STATUS	mandatory
		DESCRIPTION
		"Logical port number to which egress queue is associated.
         In AUSM (4-port card), a logical port is same as a physical
         port.
         This is read only and queue mapping is as follows
		1-16	port no 1
		17-32	port no 2
		33-48	port no 3
		49-64	port no 4

		For AUSM 8-port card, the following queue mapping is used
		in addition to the above:
		65-80	port no 5
		81-96	port no 6
		97-112	port no 7
		113-128	port no 8
		"
		::= { ausmPortCnfServiceQueGrpEntry 2}

egrQBinState	OBJECT-TYPE
		SYNTAX	INTEGER
		{
 			disable (1),
 			enable (2) 
 		}
		ACCESS	read-write
		STATUS	mandatory
		DESCRIPTION
		"Egress queue state 
		"
		::= { ausmPortCnfServiceQueGrpEntry 3}

egrQServiceSequence	OBJECT-TYPE
		SYNTAX	INTEGER (1..16) 
		ACCESS	read-write
		STATUS	mandatory
		DESCRIPTION
		"Egress queue number sequence in the priority list. In AUSM
		 (4 port), range from only 1..12 is permissible
		"
		::= { ausmPortCnfServiceQueGrpEntry 4}

egrQDepthMax	OBJECT-TYPE		
		SYNTAX	INTEGER (1..16000)
		ACCESS read-write
      	 	STATUS  mandatory
        	DESCRIPTION
		"The maximum depth of the egress queue. In AUSM (4 port),
		 range from only 1..8000 is permissible
		"
        	::= { ausmPortCnfServiceQueGrpEntry 5 }

egrQCLPThreshHigh	OBJECT-TYPE		
		SYNTAX	INTEGER (1..16000)
		ACCESS read-write
      	 	STATUS  mandatory
        	DESCRIPTION
		"High CLP threshold of the egress queue. In AUSM (4 port),
         range from only 1..8000 is permissible.This value should
		 be less than or equal to egrQDepthMax.
		"
        	::= { ausmPortCnfServiceQueGrpEntry 6 }

egrQCLPThreshLow	OBJECT-TYPE		
		SYNTAX	INTEGER (1..16000)
		ACCESS read-write
      	 	STATUS  mandatory
        	DESCRIPTION
		"Low CLP threshold of the egress queue. In AUSM (4 port),
         range from only 1..8000 is permissible. This value should
		 be less than or equal to egrQCLPThreshHigh.
		"
        	::= { ausmPortCnfServiceQueGrpEntry 7 }

egrQEfciThresh	OBJECT-TYPE		
		SYNTAX	INTEGER (1..16000)
		ACCESS read-write
      	 	STATUS  mandatory
        	DESCRIPTION
		"Threshold of the egress queue for EFCI. In AUSM (4 port),
         range from only 1..8000 is permissible.This value should
		 be less than or equal to egrQDepthMax.
		"
        	::= { ausmPortCnfServiceQueGrpEntry 8 }

egrQAlgorithm	OBJECT-TYPE		
		SYNTAX	INTEGER (1..'ff'h) 
		ACCESS read-write
      	 	STATUS  mandatory
        	DESCRIPTION
		"The algorithm number for the Egress queue
		 1-5 are valid values
		 'ff'h is disable	
		"
        	::= { ausmPortCnfServiceQueGrpEntry 9 }

egrMaxBwInc	OBJECT-TYPE		
		SYNTAX	INTEGER (1..512) 
		ACCESS read-write
      	 	STATUS  mandatory
        	DESCRIPTION
		"The increment for the Maximum carry for the queue. In
         AUSM (8 port), range from only 1..511 is permissible
		"
        	::= { ausmPortCnfServiceQueGrpEntry 10 }

egrMinBwInc	OBJECT-TYPE		
		SYNTAX	INTEGER (1..512)
		ACCESS read-write
      	 	STATUS  mandatory
        	DESCRIPTION
		"The increment for the minimum carry for the queue. In
         AUSM (8 port), range from only 1..511 is permissible
		"
        	::= { ausmPortCnfServiceQueGrpEntry 11 }
egrQCLPState	OBJECT-TYPE		
 		SYNTAX	INTEGER 
		{
 			clplow (1),
 			clphigh (2) 
 		}
		ACCESS read-only
      	 	STATUS  mandatory
        	DESCRIPTION
 		"this variable indicates the CLP state for the queue
 		"
        	::= { ausmPortCnfServiceQueGrpEntry 12 }

-- Egress counters

egrQfullDiscardCells	OBJECT-TYPE
		SYNTAX	Counter
		ACCESS	read-only
		STATUS	mandatory
		DESCRIPTION		  
			"The number of cells discarded due to Egress Q full
			"
        	::= { ausmPortCnfServiceQueGrpEntry 13 }

egrQClpSetDiscardCells	OBJECT-TYPE
		SYNTAX	Counter
		ACCESS	read-only
		STATUS	mandatory
		DESCRIPTION		  
			"The number of CLP set cells discarded in Egress direction 
			"
        	::= { ausmPortCnfServiceQueGrpEntry 14 }


-- ------------------------------------------------------------
-- End of ausmPortCnfServiceQueGrp
--
-- ----------------------------------------------------------------------
-- BASIS Project MIB
-- 
--





-- Important Note : NetPrefix must only be of SIZE 8 or 13.


-- atm                  OBJECT IDENTIFIER ::= { basisServices 2 }
--ausmPort       		OBJECT IDENTIFIER ::= { atm 1 }
--ausmPortCnf		OBJECT IDENTIFIER ::= { ausmPort 1 }
ausmPortCnfSig		OBJECT IDENTIFIER ::= { ausmPortCnf 3}
ausmPortCnfSigILMIGrp	OBJECT IDENTIFIER ::= { ausmPortCnfSig 1}


-- ------------------------------------------------------------------------
--
-- ausmPortCnfSig group
-- Port configurable signalling parameters  
--
-- ------------------------------------------------------------------------


ausmPortCnfSigILMIGrpTable	OBJECT-TYPE
	SYNTAX	SEQUENCE OF AusmPortCnfSigILMIGrpEntry
	ACCESS	not-accessible
	STATUS	mandatory
	DESCRIPTION
		"The config table is for upto 8 logical port interfaces 
		"
	::= { ausmPortCnfSigILMIGrp 1 }

ausmPortCnfSigILMIGrpEntry	OBJECT-TYPE
	SYNTAX	AusmPortCnfSigILMIGrpEntry
	ACCESS	not-accessible
	STATUS	mandatory
	DESCRIPTION
		" An entry for a logical port. In AUSM (4-port card), a logical
          port is same as a physical port.
		"
	INDEX	{ sigPortNum }
	::= { ausmPortCnfSigILMIGrpTable 1 }

AusmPortCnfSigILMIGrpEntry ::=
	SEQUENCE {
	   	sigPortNum 	              INTEGER,
		ausmSignallingProtocolType    INTEGER, 
		signallingVpi                 INTEGER, 
		signallingVci                 INTEGER, 
		addrPrefix                    NetPrefix,
		customerId                    INTEGER,
		protocolRevNo                 INTEGER,
		iLMITrapEnable                INTEGER,
		minTrapInterval               INTEGER,
		keepAlivePollingEnable        INTEGER,
		errorThresholdN491            INTEGER,
		eventThresholdN492            INTEGER,
		pollingIntervalT491           INTEGER,
		minEnquiryIntervalT493	      INTEGER,
		addrRegEnable         	      INTEGER
		}


sigPortNum OBJECT-TYPE
	SYNTAX	INTEGER (1..8)
	ACCESS	read-only
	STATUS	mandatory
	DESCRIPTION		  
		"Refers to the logical port index. In AUSM (4-port card), a
         logical port is same as a physical port.
		"
	::= { ausmPortCnfSigILMIGrpEntry 1}

ausmSignallingProtocolType  OBJECT-TYPE
	SYNTAX	INTEGER {
		other(1),
		noSignalling(2),
		iLMI(3)
		}
	ACCESS read-write
	STATUS  mandatory
        DESCRIPTION
            "This will set the signalling protocol
	     1 - other
	     2 - noSignalling
	     3 - ILMI
	    "
	::= { ausmPortCnfSigILMIGrpEntry 2}

signallingVpi   OBJECT-TYPE
	SYNTAX	INTEGER (0..'ffffff'h )
	ACCESS	read-write
	STATUS	mandatory
	DESCRIPTION		  
		"indicates the VPI on which signalling cells 
		 arrive
		"
	::= { ausmPortCnfSigILMIGrpEntry 3}

signallingVci   OBJECT-TYPE
	SYNTAX	INTEGER (0..'ffffff'h )
	ACCESS	read-write
	STATUS	mandatory
	DESCRIPTION		  
		"indicates the VCI on which signalling cells 
		 arrive
		"
	::= { ausmPortCnfSigILMIGrpEntry 4}

addrPrefix      OBJECT-TYPE
	SYNTAX	NetPrefix   -- from ILMI MIB
	ACCESS	read-write
	STATUS	mandatory
	DESCRIPTION		  
		"Network Prefix for the ATM address
		"
	::= { ausmPortCnfSigILMIGrpEntry 5}

customerId	OBJECT-TYPE
	SYNTAX	INTEGER
	ACCESS	read-write
	STATUS	mandatory
	DESCRIPTION 
		"for the INS as a read/write variable
		"
	::= { ausmPortCnfSigILMIGrpEntry 6}
		      	   
protocolRevNo	OBJECT-TYPE
	SYNTAX	INTEGER
	ACCESS	read-write
	STATUS	mandatory
	DESCRIPTION 
		"for the INS as a read/write variable
		"
	::= { ausmPortCnfSigILMIGrpEntry 7}
		      	   

iLMITrapEnable OBJECT-TYPE
	SYNTAX	INTEGER {
		disable (1),
		enable (2)
		} 
	ACCESS	read-write
	STATUS	mandatory
	DESCRIPTION		  
		"Enable/disable ILMI Trap sending
		"
	::= { ausmPortCnfSigILMIGrpEntry 8}
		      	   
minTrapInterval	OBJECT-TYPE
	SYNTAX	INTEGER (1..10)
	ACCESS	read-write
	STATUS	mandatory
	DESCRIPTION 
		"number of seconds between traps
		"
	::= { ausmPortCnfSigILMIGrpEntry 9}
		      	   
keepAlivePollingEnable	OBJECT-TYPE
	SYNTAX	INTEGER {
		disable (1),
		enable (2)
		} 
	ACCESS	read-write
	STATUS	mandatory
	DESCRIPTION		  
		"Enable/disable Keep Alive Polling
		"
	::= { ausmPortCnfSigILMIGrpEntry 10}
		      	   
errorThresholdN491	OBJECT-TYPE
	SYNTAX	INTEGER (1..10)
	ACCESS	read-write
	STATUS	mandatory
	DESCRIPTION 
		"Error Threshold (N491) value
		"
	::= { ausmPortCnfSigILMIGrpEntry 11}
		      	   
eventThresholdN492	OBJECT-TYPE
	SYNTAX	INTEGER (1..10)
	ACCESS	read-write
	STATUS	mandatory
	DESCRIPTION 
		"Event Threshold (N492) value
		"
	::= { ausmPortCnfSigILMIGrpEntry 12}
		      	   
pollingIntervalT491	OBJECT-TYPE
	SYNTAX	INTEGER {
		v1(5),
		v2(10),
		v3(15),
		v4(20),
		v5(25),
		v6(30),
		v7(35),
		v8(40),
		v9(45),
		v10(50),
		v11(55),
		v12(60)
		}
	ACCESS	read-write
	STATUS	mandatory
	DESCRIPTION 
		"Polling Interval (T491) value
		"
	::= { ausmPortCnfSigILMIGrpEntry 13}
		      	   
minEnquiryIntervalT493	OBJECT-TYPE
	SYNTAX	INTEGER (1..20)
	ACCESS	read-write
	STATUS	mandatory
	DESCRIPTION 
		"Minimum Enquiry Interval (T493)
		"
	::= { ausmPortCnfSigILMIGrpEntry 14}
		      	   
addrRegEnable OBJECT-TYPE
    SYNTAX  INTEGER {
        disable (1),
        enable (2)
        }
    ACCESS  read-write
    STATUS  mandatory
    DESCRIPTION
        "Enable/disable ILMI Address Registration
        "
    ::= { ausmPortCnfSigILMIGrpEntry 15}
   

-- ------------------------------------------------------------------------
-- End of ausmPortCnfSigILMIGrp group definitions



-- atm                  OBJECT IDENTIFIER ::= { basisServices 2 }
--ausmPort       		OBJECT IDENTIFIER ::= { atm 1 }
--ausmPortCnt		OBJECT IDENTIFIER ::= { ausmPort 3 }
ausmPortCntPortGrp	OBJECT IDENTIFIER ::= { ausmPortCnt 1}

-- --------------------------------------------------------------------
--
--
--		AUSM PORT COUNTER Group
--
--
-- --------------------------------------------------------------------


ausmPortCntPortGrpTable	OBJECT-TYPE
	SYNTAX	SEQUENCE OF AusmPortCntPortGrpEntry
	ACCESS	not-accessible
	STATUS	mandatory
	DESCRIPTION
		"The config table is for logical port interface
		 there are 8 entries for either T1 or E1
		"
	::= { ausmPortCntPortGrp 1 }


ausmPortCntPortGrpEntry	OBJECT-TYPE
	SYNTAX	AusmPortCntPortGrpEntry
	ACCESS	not-accessible
	STATUS	mandatory
	DESCRIPTION
		" An entry for logical port
		"
	INDEX	{ ausmCntPortNum }
    ::= { ausmPortCntPortGrpTable 1 }

AusmPortCntPortGrpEntry ::=
	SEQUENCE {
		ausmCntPortNum 	
			INTEGER,
-- Ingress direction
		ingrRcvCells
			Counter,
		ingrGfcErrCells
			Counter,
		ingrVpiVciErrCells
			Counter,
		ingrLastUnknVpiVci
			INTEGER,
-- Egress direction
		egrXmtCells
			Counter,
		egrPortAlarmDiscardCells
			Counter,
		egrXmtClpSetCells
			Counter,
		egrXmtEfciSetCells
			Counter,
-- OAM 
		portXmtAisCells
			Counter,
		portXmtSgmtLpbkCells
			Counter,
		portRcvAisCells
			Counter,
		portRcvFerfCells
			Counter,
		portRcvSgmtLpbkCells
			Counter,
		portRcvCrcErrOAMCells
			Counter,
-- Clear Button
		ausmPortClrButton
			INTEGER,
-- New Counters
         ingrRcvClpSetCells
            Counter,
         ingrXmtCells
            Counter,
         egrRcvCells
            Counter,
         ingrRcvCellRate
            Gauge,
         ingrRcvUtilization
            Gauge,
         egrXmtCellRate
            Gauge,
         egrXmtUtilization
            Gauge,
         egrRcvCellRate
            Gauge,
         egrRcvUtilization
            Gauge,
         totalIngrQfulldiscardCells
            Counter,
         txFifoFullCnt
            Counter,
         totalIngrClpSetDiscardCells
            Counter
		}

ausmCntPortNum	OBJECT-TYPE
	SYNTAX	INTEGER (1..8)
	ACCESS	read-only
	STATUS	mandatory
	DESCRIPTION
		"This is the logical port number. In AUSM (4-port card), a
         logical port is same as a physical port.
		"
	::= { ausmPortCntPortGrpEntry 1}


-- Ingress direction
ingrRcvCells	OBJECT-TYPE
        SYNTAX  Counter
        ACCESS  read-only
        STATUS  mandatory
        DESCRIPTION              
                "The number of cells received in Ingress direction
                "
        ::= { ausmPortCntPortGrpEntry 2 }
 

ingrGfcErrCells	OBJECT-TYPE
        SYNTAX  Counter
        ACCESS  read-only
        STATUS  mandatory
        DESCRIPTION              
                "The number of cells received in Ingress direction
		 with non zero-GFC
                "
        ::= { ausmPortCntPortGrpEntry 3 }
 
ingrVpiVciErrCells	OBJECT-TYPE
        SYNTAX  Counter
        ACCESS  read-only
        STATUS  mandatory
        DESCRIPTION              
                "The number of cells received in Ingress direction
		 with unknown VpiVci 
                "
        ::= { ausmPortCntPortGrpEntry 4 }
 
ingrLastUnknVpiVci	OBJECT-TYPE
        SYNTAX  INTEGER (0..'ffffff'h)
        ACCESS  read-only
        STATUS  mandatory
        DESCRIPTION              
                "The last unknown Vpi Vci value
                "
        ::= { ausmPortCntPortGrpEntry 5 }
 
-- Egress direction

egrXmtCells	OBJECT-TYPE
        SYNTAX  Counter
        ACCESS  read-only
        STATUS  mandatory
        DESCRIPTION              
                "The number of cells transmitted in the egress direction
                "
        ::= { ausmPortCntPortGrpEntry 6 }
 
egrPortAlarmDiscardCells	OBJECT-TYPE
        SYNTAX  Counter
        ACCESS  read-only
        STATUS  mandatory
        DESCRIPTION              
                "The number of cells discarded due to port alarm
                "
        ::= { ausmPortCntPortGrpEntry 7 }
 
egrXmtClpSetCells	OBJECT-TYPE
        SYNTAX  Counter
        ACCESS  read-only
        STATUS  mandatory
        DESCRIPTION              
                "The number of cells transmitted in Egress direction
		 with CLP bit set
                "
        ::= { ausmPortCntPortGrpEntry 8 }
 
egrXmtEfciSetCells	OBJECT-TYPE
        SYNTAX  Counter
        ACCESS  read-only
        STATUS  mandatory
        DESCRIPTION              
                "The number of cells transmitted in Egress direction
		 with EFCI bit set
                "
        ::= { ausmPortCntPortGrpEntry 9 }
 
-- OAM

portXmtAisCells	OBJECT-TYPE
        SYNTAX  Counter
        ACCESS  read-only
        STATUS  mandatory
        DESCRIPTION              
                "The number of AIS cells transmitted towards port
                "
        ::= { ausmPortCntPortGrpEntry 10 }
 
portXmtSgmtLpbkCells	OBJECT-TYPE
        SYNTAX  Counter
        ACCESS  read-only
        STATUS  mandatory
        DESCRIPTION              
                "The number of Segment Loopback  cells transmitted 
		 towards port
                "
        ::= { ausmPortCntPortGrpEntry 11 }
 
portRcvAisCells	OBJECT-TYPE
        SYNTAX  Counter
        ACCESS  read-only
        STATUS  mandatory
        DESCRIPTION              
                "The number of AIS cells received in Ingress direction
                "
        ::= { ausmPortCntPortGrpEntry 12 }
 
portRcvFerfCells	OBJECT-TYPE
        SYNTAX  Counter
        ACCESS  read-only
        STATUS  mandatory
        DESCRIPTION              
                "The number of FERF cells received in Ingress direction
                "
        ::= { ausmPortCntPortGrpEntry 13 }
 
portRcvSgmtLpbkCells	OBJECT-TYPE
        SYNTAX  Counter
        ACCESS  read-only
        STATUS  mandatory
        DESCRIPTION              
                "The number of Segment Loopback cells received in 
		 Ingress direction
                "
        ::= { ausmPortCntPortGrpEntry 14 }
 
portRcvCrcErrOAMCells	OBJECT-TYPE
        SYNTAX  Counter
        ACCESS  read-only
        STATUS  mandatory
        DESCRIPTION              
                "The number of OAM cells received in Ingress direction
		 with CRC error
                "
        ::= { ausmPortCntPortGrpEntry 15 }
 
-- Clear Button
ausmPortClrButton	OBJECT-TYPE
	SYNTAX  INTEGER {
	noAction (1),
	resetCounters (2)
	}
	ACCESS  read-write
	STATUS  mandatory
	DESCRIPTION
		"writing a value of 2 resets all the counters
		"
	::= { ausmPortCntPortGrpEntry 16 }
 
ingrRcvClpSetCells  OBJECT-TYPE
        SYNTAX  Counter
        ACCESS  read-only
        STATUS  mandatory
        DESCRIPTION
                "The number of cells received from the port which had
                 the CLP bit in the ATM cell header equal to 1.
                "
        ::= { ausmPortCntPortGrpEntry 17 }
 
ingrXmtCells    OBJECT-TYPE
        SYNTAX  Counter
        ACCESS  read-only
        STATUS  mandatory
        DESCRIPTION
                "The number of cells out of the received cells from the port
                 that were sent to the network. This count is taken after
                 policing and ingress queueing.
                "
        ::= { ausmPortCntPortGrpEntry 18 }
 
egrRcvCells OBJECT-TYPE
        SYNTAX  Counter
        ACCESS  read-only
        STATUS  mandatory
        DESCRIPTION
                "The number of cells received from the network
                 in the egress direction
                "
        ::= { ausmPortCntPortGrpEntry 19 }
 
ingrRcvCellRate OBJECT-TYPE
        SYNTAX  Gauge
        ACCESS  read-only
        STATUS  mandatory
        DESCRIPTION
                "The number of cells received per second from the port
                 in the ingress direction. Maximum value is 5000 because
                 because clear E1 rate is 4830.
                "
        ::= { ausmPortCntPortGrpEntry 20 }
 
ingrRcvUtilization  OBJECT-TYPE
        SYNTAX  Gauge
        ACCESS  read-only
        STATUS  mandatory
        DESCRIPTION
                "The percentage utilization of the port speed
                 in the ingress direction.
                "
        ::= { ausmPortCntPortGrpEntry 21 }

egrXmtCellRate  OBJECT-TYPE
        SYNTAX  Gauge
        ACCESS  read-only
        STATUS  mandatory
        DESCRIPTION
                "The number of cells received transmitted to the port
                 in the egress direction.
                "
        ::= { ausmPortCntPortGrpEntry 22 }
 
egrXmtUtilization   OBJECT-TYPE
        SYNTAX  Gauge
        ACCESS  read-only
        STATUS  mandatory
        DESCRIPTION
                "The percentage utilization of the port speed
                 in the egress direction.
                "
        ::= { ausmPortCntPortGrpEntry 23 }
 
egrRcvCellRate  OBJECT-TYPE
        SYNTAX  Gauge
        ACCESS  read-only
        STATUS  mandatory
        DESCRIPTION
                "The number of cells received per second from the network
                 in the egress receive direction.
                "
        ::= { ausmPortCntPortGrpEntry 24 }
 
egrRcvUtilization   OBJECT-TYPE
        SYNTAX  Gauge
        ACCESS  read-only
        STATUS  mandatory
        DESCRIPTION
                "The percentage utilization of the port speed
                 in the egress receive direction.
                "
        ::= { ausmPortCntPortGrpEntry 25 }

totalIngrQfulldiscardCells  OBJECT-TYPE
        SYNTAX  Counter
        ACCESS  read-only
        STATUS  mandatory
        DESCRIPTION
                "The total number of cells dropped on all the channels
                 on this port because the the ingress Q was full. Adds
                 up all the IngressQfull discard per channel statistics
                 for all the channels in the port.
                "
        ::= { ausmPortCntPortGrpEntry 26 }
 
txFifoFullCnt OBJECT-TYPE
    SYNTAX  Counter
    ACCESS  read-only
    STATUS  mandatory
    DESCRIPTION
        "This statistics provides a count of the  number of times the AUSM
         card tried to send a cell, but was unable to send because the
         Transmit FIFO was full. Note that this is NOT a count of the number
         of cells dropped. This statistics is per card statistics. This
         counter is duplicated in channel count group to help monitoring.
        "
    ::= { ausmPortCntPortGrpEntry   27 }
 
totalIngrClpSetDiscardCells OBJECT-TYPE
        SYNTAX  Counter
        ACCESS  read-only
        STATUS  mandatory
        DESCRIPTION
                "The total number of cells with CLP=1 dropped on all the
                 channels on this port because of either PCR Exceeded,
                 SCR exceeded (with CLP tagging disabled) or CLP Hysteris.
                 Adds up all the IngressClpSet discard per channel statistics
                 for all the channels in the port.
                "
        ::= { ausmPortCntPortGrpEntry 28 }


-- --------------------------------------------------------------------
-- End of ausmPortCntPortGrp

-- atm                  OBJECT IDENTIFIER ::= { basisServices 2 }
-- ausmPort    		OBJECT IDENTIFIER ::= { atm 1 }
-- ausmPortCnt		OBJECT IDENTIFIER ::= { ausmPort 3 }
ausmPortCntSig          OBJECT IDENTIFIER ::= { ausmPortCnt 2}
ausmPortCntSigILMIGrp   OBJECT IDENTIFIER ::= { ausmPortCntSig 1}

-- --------------------------------------------------------------------
--
--
--		AUSM PORT SIGNALLING COUNTER Group
--
--
-- --------------------------------------------------------------------


ausmPortCntSigILMIGrpTable	OBJECT-TYPE
	SYNTAX	SEQUENCE OF AusmPortCntSigILMIGrpEntry
	ACCESS	not-accessible
	STATUS	mandatory
	DESCRIPTION
		"The config table is for physical port interface
		 there are 8 entries for either T1 or E1 or IMA
		"
	::= { ausmPortCntSigILMIGrp 1 }


ausmPortCntSigILMIGrpEntry	OBJECT-TYPE
	SYNTAX	AusmPortCntSigILMIGrpEntry
	ACCESS	not-accessible
	STATUS	mandatory
	DESCRIPTION
		" An entry for logical port. In AUSM (4-port card), a logical port
          is same as a physical port.
		"
	INDEX	{ sigCntPortNum }
    ::= { ausmPortCntSigILMIGrpTable 1 }

AusmPortCntSigILMIGrpEntry ::=
	SEQUENCE {
		sigCntPortNum 	
			INTEGER,
		snmpPduReceived
			Counter,
		getRequestReceived
			Counter,
		getNextRequestReceived
			Counter,
		setRequestReceived
			Counter,
		trapReceived
			Counter,
		getResponseReceived
			Counter,
		getResponseTransmitted
			Counter,
		getRequestTransmitted
			Counter,
		trapTransmitted
			Counter,
		invalidPDUReceived
			Counter,
		asn1ParseError
			Counter,
		noSuchNameError
			Counter,
		tooBigError
			Counter,
-- Clear Button
		portSigClrButton
			INTEGER
		}

sigCntPortNum	OBJECT-TYPE
	SYNTAX	INTEGER (1..8) 
	ACCESS	read-only
	STATUS	mandatory
	DESCRIPTION
		"This is the logical port number.
		"
	::= { ausmPortCntSigILMIGrpEntry 1}


snmpPduReceived		OBJECT-TYPE
        SYNTAX  Counter
        ACCESS  read-only
        STATUS  mandatory
        DESCRIPTION              
                "The number of snmp packets received
                "
        ::= { ausmPortCntSigILMIGrpEntry 2 }
 
getRequestReceived	OBJECT-TYPE
        SYNTAX  Counter
        ACCESS  read-only
        STATUS  mandatory
        DESCRIPTION              
                "The number of get request messages received
                "
        ::= { ausmPortCntSigILMIGrpEntry 3 }
 
getNextRequestReceived	OBJECT-TYPE
        SYNTAX  Counter
        ACCESS  read-only
        STATUS  mandatory
        DESCRIPTION              
                "The number of get-next messages received
                "
        ::= { ausmPortCntSigILMIGrpEntry 4 }
 
setRequestReceived	OBJECT-TYPE
        SYNTAX  Counter
        ACCESS  read-only
        STATUS  mandatory
        DESCRIPTION              
                "The number of set messages received
                "
        ::= { ausmPortCntSigILMIGrpEntry 5 }
 
trapReceived		OBJECT-TYPE
        SYNTAX  Counter
        ACCESS  read-only
        STATUS  mandatory
        DESCRIPTION              
                "The number of traps received
                "
        ::= { ausmPortCntSigILMIGrpEntry 6 }
 
getResponseReceived	OBJECT-TYPE
        SYNTAX  Counter
        ACCESS  read-only
        STATUS  mandatory
        DESCRIPTION              
                "The number of Keep Alive response messages received
                "
        ::= { ausmPortCntSigILMIGrpEntry 7 }
 
getResponseTransmitted	OBJECT-TYPE
        SYNTAX  Counter
        ACCESS  read-only
        STATUS  mandatory
        DESCRIPTION              
                "The number of response messages transmitted 
                "
        ::= { ausmPortCntSigILMIGrpEntry 8 }
 
getRequestTransmitted	OBJECT-TYPE
        SYNTAX  Counter
        ACCESS  read-only
        STATUS  mandatory
        DESCRIPTION              
                "The number of Keep Alive get request messages transmitted
                "
        ::= { ausmPortCntSigILMIGrpEntry 9 }
 
trapTransmitted		OBJECT-TYPE
        SYNTAX  Counter
        ACCESS  read-only
        STATUS  mandatory
        DESCRIPTION              
                "The number of trap messages transmitted
                "
        ::= { ausmPortCntSigILMIGrpEntry 10 }
 
invalidPDUReceived	OBJECT-TYPE
        SYNTAX  Counter
        ACCESS  read-only
        STATUS  mandatory
        DESCRIPTION              
                "The number of invalid PDUs received
                "
        ::= { ausmPortCntSigILMIGrpEntry 11 }
 
asn1ParseError		OBJECT-TYPE
        SYNTAX  Counter
        ACCESS  read-only
        STATUS  mandatory
        DESCRIPTION              
                "The number of parse errors on ASN.1
                "
        ::= { ausmPortCntSigILMIGrpEntry 12 }
 
noSuchNameError		OBJECT-TYPE
        SYNTAX  Counter
        ACCESS  read-only
        STATUS  mandatory
        DESCRIPTION              
                "The number of errors for name not present
                "
        ::= { ausmPortCntSigILMIGrpEntry 13 }
 
tooBigError		OBJECT-TYPE
        SYNTAX  Counter
        ACCESS  read-only
        STATUS  mandatory
        DESCRIPTION              
                "The number of messages received with len > 484
                "
        ::= { ausmPortCntSigILMIGrpEntry 14 }
 

-- Clear Button
portSigClrButton	OBJECT-TYPE
	SYNTAX  INTEGER {
	noAction (1),
	resetCounters (2)
	}
	ACCESS  read-write
	STATUS  mandatory
	DESCRIPTION
		"writing a value of 2 resets all the counters
		"
	::= { ausmPortCntSigILMIGrpEntry 15 }
 


-- --------------------------------------------------------------------
-- End of ausmPortCntSigILMIGrp

-- atm                  OBJECT IDENTIFIER ::= { basisServices 2 }
--ausmPort       		OBJECT IDENTIFIER ::= { atm 1 }
ausmPortStateGrp	OBJECT IDENTIFIER ::= { ausmPort 2 }

-- --------------------------------------------------------------------
--
--
--		AUSM PORT STATE Group
--
--
-- --------------------------------------------------------------------


ausmPortStateGrpTable	OBJECT-TYPE
	SYNTAX	SEQUENCE OF AusmPortStateGrpEntry
	ACCESS	not-accessible
	STATUS	mandatory
	DESCRIPTION
		"The state table for the port interface
		 there are 8 entries for either T1 or E1 or IMA.
		"
	::= { ausmPortStateGrp 1 }


ausmPortStateGrpEntry	OBJECT-TYPE
	SYNTAX	AusmPortStateGrpEntry
	ACCESS	not-accessible
	STATUS	mandatory
	DESCRIPTION
		" An entry for logical port.  In AUSM (4-port card), a logical port
          is same as a physical port.
		"
	INDEX	{ ausmStatePortNum }
    ::= { ausmPortStateGrpTable 1 }

AusmPortStateGrpEntry ::=
	SEQUENCE {
		ausmStatePortNum 	
				INTEGER,
      	ausmPortState
         		INTEGER,
      	ausmPortOversubscribed
         		INTEGER,
		ausmPortIngrPercentUtil
				INTEGER,
		ausmPortEgrPercentUtil
				INTEGER
		}

ausmStatePortNum 	OBJECT-TYPE
	SYNTAX	INTEGER (1..8) 
	ACCESS	read-only
	STATUS	mandatory
	DESCRIPTION
		"This is logical port number. In AUSM (4-port card), a logical port
         is same as a physical port.
		"
	::= { ausmPortStateGrpEntry 1}

ausmPortState  OBJECT-TYPE		
	SYNTAX	INTEGER {
		notConfigured (1),
		active (2),
		remoteloopback (3),
		linefailure (4),
		signallingfailure (5),
		outofcelldelineation (6),
		localloopback (7)
		}
	ACCESS read-only
        STATUS  mandatory
        DESCRIPTION
        "This variable indicates the status of the port
        "
        ::= { ausmPortStateGrpEntry 2 }

ausmPortOversubscribed  OBJECT-TYPE		
	SYNTAX	INTEGER {
		false (1),
		true (2)
		}
	ACCESS read-only
        STATUS  mandatory
        DESCRIPTION
        "This variable indicates the whether the port is 
		over subscribed or not
        "
        ::= { ausmPortStateGrpEntry 3 }

ausmPortIngrPercentUtil		OBJECT-TYPE
	SYNTAX  INTEGER (0..1000)  
	ACCESS read-only 
	STATUS  mandatory  
	DESCRIPTION    
		"Percentage Utilization of the Port in the Ingress
		 direction.
		" 
        ::= { ausmPortStateGrpEntry  4 }


ausmPortEgrPercentUtil		OBJECT-TYPE
	SYNTAX  INTEGER (0..1000)  
	ACCESS read-only 
	STATUS  mandatory  
	DESCRIPTION    
		"Percentage Utilization of the Port in the Egress
		 direction.
		" 
        ::= { ausmPortStateGrpEntry  5 }


-- ------------------------------------------------------------------
-- End of ausmPortStateGrp

ausmPortInterfaceGrp	OBJECT IDENTIFIER ::= { ausmPort 5 }

-- --------------------------------------------------------------------
--
--
--		AUSM PORT INTERFACE Group
--
--
-- --------------------------------------------------------------------

ausmInterfaceConfTable	OBJECT-TYPE
	SYNTAX         SEQUENCE OF AusmInterfaceConfEntry
	ACCESS         not-accessible
	STATUS         mandatory
	DESCRIPTION
		"This table contains ATM local interface
		 configuration parameters, one entry per ATM (ausm)
		 interface port.
		"
	::= { ausmPortInterfaceGrp 1 }

ausmInterfaceConfEntry    OBJECT-TYPE
	SYNTAX         AusmInterfaceConfEntry
	ACCESS         not-accessible
	STATUS         mandatory
	DESCRIPTION
		"This list contains ATM interface configuration
		 parameters and state variables and is indexed
		 by ausmInterfacePortNum values of ATM interfaces.
		"
	INDEX { ausmInterfacePortNum }
	::= { ausmInterfaceConfTable  1}

AusmInterfaceConfEntry ::=
	SEQUENCE {
	ausmInterfacePortNum INTEGER,
	ausmInterfaceMyNeighborIpAddress IpAddress
}

ausmInterfacePortNum 	OBJECT-TYPE
	SYNTAX	INTEGER (1..8) 
	ACCESS	read-only
	STATUS	mandatory
	DESCRIPTION
		"This is logical port number. In AUSM, a logical port
		 is same as a physical port.
		"
	::= { ausmInterfaceConfEntry 1}

ausmInterfaceMyNeighborIpAddress OBJECT-TYPE
	SYNTAX         IpAddress
	ACCESS         read-only
	STATUS         mandatory
	DESCRIPTION
		"The IP address of the neighbor system connected to
		 the  far end of this interface, to which a Network
		 Management Station can send SNMP messages, as IP
		 datagrams sent to UDP port 161, in order to access
		 network management information concerning the
		 operation of that system.  Note that the value
		 of this object may be obtained in different ways,
		 e.g., by manual configuration, or through ILMI
		 interaction with the neighbor system.
		"
	::= { ausmInterfaceConfEntry 2 }


-- ------------------------------------------------------------------
-- End of ausmPortInterfaceGrp
--
-- ----------------------------------------------------------------------
-- BASIS Project MIB
-- 
-- Initial revision 
-- updated by Jayakumar for CESM-8P 3/23/97
-- updated by Durai for CESM-T3E3   2/26/1998



--circuitEmulation        OBJECT IDENTIFIER ::= { basisServices 3 }
--cesmChan                OBJECT IDENTIFIER ::= { circuitEmulation 2 }  
cesmChanCnfGrp          OBJECT IDENTIFIER ::= { cesmChan 1 }


-- ------------------------------------------------------------------------
--
-- cesmChannelConfig group
-- Channel configurable parameters  
--
-- ------------------------------------------------------------------------


cesmChanCnfGrpTable    OBJECT-TYPE
    SYNTAX    SEQUENCE OF CesmChanCnfGrpEntry
    ACCESS    not-accessible
    STATUS    mandatory
    DESCRIPTION
        "The config table is for logical channel interface
         there are 4 entries for 4 DS1s in case of CESM-4P
         in case of CESM-8P it can  have 263 entries.
	 For CESM-T3/E3 , this will have only one entry.
        "
    ::= { cesmChanCnfGrp 1 }

cesmChanCnfGrpEntry    OBJECT-TYPE
    SYNTAX    CesmChanCnfGrpEntry
    ACCESS    not-accessible
    STATUS    mandatory
    DESCRIPTION
        " An entry for logical channel
        "
    INDEX    { cesCnfChanNum }
    ::= { cesmChanCnfGrpTable 1 }

CesmChanCnfGrpEntry ::=
    SEQUENCE {
       cesCnfChanNum                  INTEGER,
       cesChanRowStatus               INTEGER, 
       cesMapPortNum                  INTEGER,
       cesMapVpi                      INTEGER,
       cesMapVci                      INTEGER, 
       cesCBRService                  INTEGER,
       cesCBRClockMode                INTEGER,
       cesCas                         INTEGER,
       cesPartialFill                 INTEGER,
       cesBufMaxSize                  INTEGER,
       cesCDVRxT                      INTEGER,
       cesCellLossIntegrationPeriod   INTEGER,
       cesChanLocRmtLpbkState         INTEGER,
       cesChanTestType                INTEGER,
       cesChanTestState               INTEGER,
       cesChanRTDResult               INTEGER,
       cesChanPortNum                 INTEGER,
       cesChanConnType                INTEGER,
       cesChanStrauSciNum             INTEGER,
       cesChanIdleDetEnable           INTEGER,
       cesChanIdleSignalCode          INTEGER,
       cesChanIdleCodeIntgnPeriod     INTEGER,
       cesChanOnhookCode              INTEGER,
       cesChanConditionedData         INTEGER,
       cesmChanExtTrgIdleSupp         INTEGER,
       cesmChanConditionedSigCode     INTEGER,
-- Connection parameters, used by PXM
                cesLocalVpi              INTEGER,
                cesLocalVci              INTEGER,
                cesLocalNSAP             OCTET STRING,
                cesRemoteVpi             INTEGER,
                cesRemoteVci             INTEGER,
                cesRemoteNSAP            OCTET STRING,
                cesMastership            INTEGER,
                cesVpcFlag               INTEGER,
                cesConnServiceType       INTEGER,
                cesRoutingPriority       INTEGER,
                cesMaxCost               INTEGER,
                cesRestrictTrunkType     INTEGER,
                cesConnPCR               INTEGER,
                cesConnMCR               INTEGER,
                cesConnPercentUtil       INTEGER,
                cesmConnRemotePCR   	 INTEGER,
                cesmConnRemoteMCR   	 INTEGER,
                cesmConnRemotePercentUtil INTEGER,
                cesmConnForeSightEnable   INTEGER,
                cesmConnFGCRAEnable       INTEGER,
                cesmChanReroute           INTEGER,
                cesmConnAdminStatus	      INTEGER

      }


cesCnfChanNum OBJECT-TYPE
    SYNTAX    INTEGER (16..279)
    ACCESS    read-only
    STATUS    mandatory
    DESCRIPTION          
        "Refers to the virtual connection no. In case of 
         CESM-4P the range is 16..19 (only for 4 entries).
         for CESM-8t1 we can have 192 and for CESM-8e1 we 
         can have 248 channels. For CESM-T3/E3  we can have only one
         connection.
         For CESM-T1/E1/T3/E3, channel number starts from 35
         in Release2.2
        "
    ::= { cesmChanCnfGrpEntry 1}

cesChanRowStatus  OBJECT-TYPE
    SYNTAX    INTEGER {
        add(1),
        del(2),
        mod(3),
-- added outOfService for Release2.2
        outOfService(4)
        }
    ACCESS read-write
    STATUS  mandatory
    DESCRIPTION
      "This indicates the channel status
           1 ==> ADD
           2 ==> DELETE
           3 ==> MODIFY
	   4 ==> Setting this object to outOfService takes the channel
	  	 out of service or brings the channel 'down'. The channel
		 can be brought 'up' again by setting the object to mod.
      "
       ::= { cesmChanCnfGrpEntry 2 }

cesMapPortNum    OBJECT-TYPE    
    SYNTAX    INTEGER (1..8)
    ACCESS read-only
    STATUS  mandatory
    DESCRIPTION
      "In case of CESM-4P this variable  specifies the port number
       to which this channel is associated.  Mappings are as -
       Port 1 - channel 16, 2-17, 3-18, 4-19 (it can take value from 1..4)
       In CESM-8 this variable gives mapping between logical channel
       and physical line number. 
       In case of CESM-8P instead of this cesChanPortNum will be used
       to have the mapping between Channel and logical Port. In case of
       CESM-T3 it can be 1..1 
      "
       ::= { cesmChanCnfGrpEntry 3 }

cesMapVpi    OBJECT-TYPE
    SYNTAX    INTEGER (5..14)
    ACCESS read-only
    STATUS  mandatory
    DESCRIPTION
      "The value of this object is equal to the VPI used for the emulated
       circuit represented by this connection. In MGX8220( formerly AXIS)
       Implementaion slot number of the card  will be used for this.
      "
       ::= { cesmChanCnfGrpEntry 4 }

cesMapVci OBJECT-TYPE
    SYNTAX    INTEGER (16..279)
    ACCESS    read-only
    STATUS    mandatory
    DESCRIPTION          
        "This specifies VCI for emulated circuit represented by this VC.
         Our Implementation cesCnfChanNum will be used for this.
         In case of CESM-4P valid range is 16..19.
         In case of CESM-8P valid range is 32..279.
         In case of CESM-T3/E3 valid value is 32.

        "
    ::= { cesmChanCnfGrpEntry    5}

cesCBRService     OBJECT-TYPE
    SYNTAX    INTEGER {
        unstructured (1),
        structured (2)
        } 
    
    ACCESS    read-only
    STATUS    mandatory
    DESCRIPTION          
        "This specifies data type supported by the CBR service
         Only Unstructured mode is supported in CESM-4P
         CESM-8P supports both structured and  unstructured mode for
         T1/E1 and supports only unstructured mode in case of T3/E3.
         In CESM-T3 only unstructured is supported.
        "
    DEFVAL { unstructured }
    ::= { cesmChanCnfGrpEntry    6}

cesCBRClockMode    OBJECT-TYPE
    SYNTAX    INTEGER {
        synchronous (1),
        srts (2),
        adaptive (3)
        } 
    ACCESS    read-write
    STATUS    mandatory
    DESCRIPTION          
        "This specifies clocking mode of the CBR service
         Only synchronous mode is supported in CESM-4P
         Structured mode is always synchronous. CESM -T3
         will support only  synchronous.
        "
    DEFVAL { synchronous } 
    ::= { cesmChanCnfGrpEntry    7}

cesCas OBJECT-TYPE
    SYNTAX    INTEGER {
        basic (1),
        e1Cas (2),
        ds1SfCas (3),
        ds1EsfCas (4),
        ccs (5),
        conditionedE1Cas (6),
        basicNoPointer (7),
        ds1SfCasMF (8),
        ds1EsfCasMF (9)
        }
    ACCESS    read-write
    STATUS    mandatory
    DESCRIPTION          
        "Specifies if CAS  bits are carried by the service.
         This also selects which AAL1 format should be used.
         Only basic mode is supported for unstructured connections
         Only basic mode is supported in CESM-4P and CESM-T3E3 . 
         If type is ccs then this particular VC is carrying 
         Signaling information. ccs option is not supported in CESM-8T1E1.
         In CESM-8T1/E1 all channels on a line should have the same value.
         basicNoPointer should be used for adding 1x64 basic connections
         without an AAL1 pointer ( CES-IS 2.0 compliance ).
         when cesCas = basic, for 1x64 connections, cells will be generated 
         with a AAL1 pointer.Similarly while receiving, pointer will be
         expected in the incoming cells.
         ds1SfCasMF and ds1EsfCasMF should be used when line level 
         multiframe sync to be enabled.
        "
    DEFVAL { basic }  
    ::= { cesmChanCnfGrpEntry    8}

cesPartialFill    OBJECT-TYPE
    SYNTAX    INTEGER (0..47)
    ACCESS read-write
    STATUS  mandatory
    DESCRIPTION
       "Specifies the number of user octets per cell, if partial
        cell fill is used. 47 means partial fill disabled.
        Partial fill is not supported in CESM-4P
        Ranges for partial fill are:
        T1 struct     25 - 47
        T1 unstruct   33 - 47
        E1 struct     20 - 47
        E1 unstruct   33 - 47

        and 

        partial fill for any channel should always exceed the number
        of time slots assigned to that channel.

       "
     DEFVAL { 47 } 
     ::= { cesmChanCnfGrpEntry 9}

cesBufMaxSize    OBJECT-TYPE
    SYNTAX    INTEGER (0..65535)
    ACCESS read-write
    STATUS  mandatory
    DESCRIPTION
       "Specifies the maximum size in octets of egress buffer.
        CESM - 4P:
        Should be at least 0.6*CDVRxT for a T1 line and 
        0.7 * CDVRxT for a E1 line.  0 can be specified to internally
        compute the value

		Defaults for CESM-8T1E1 and CESM-T3E3
        -------------------------------------

        Default value of cesBufMaxSize is 0.

        Maximum value  for CESM-8T1E1 and CESM-T3E3
        -------------------------------------------

		For T1 UDT and E1 UDT : 16224 bytes
		For T1 SDT            : 384 * N  bytes
		For E1 SDT            : 417 * N  bytes
		For T3 UDT and E3 UDT : 16224 bytes

		where N is the number of timeslots assigned in Nx64
        connection. For T1-UDT  and E1 UDT use N = 32 .

        Minimum value  for CESM-8T1E1 and CESM-T3E3
        -------------------------------------------

	    In CESM-8T1/E1 and CESM-T3E3  this object ( unit in bytes ) should be at 
        least the greater of
        
        (1) CDVT in frames * 2 * N

        (2) ( CDVT in frames +  number of frames in two cells ) * N

		where N is the number of timeslots assigned in Nx64
        connection. For T1-UDT and E1-UDT use N = 32.
        "
--DEFVAL { ? } 
        ::= { cesmChanCnfGrpEntry 10}

cesCDVRxT    OBJECT-TYPE
    SYNTAX    INTEGER (125..65535)
    ACCESS read-write
    STATUS  mandatory
    DESCRIPTION
        "
        Specifies maximum cell arrival jitter that the reassembly 
        process will tolerate.
        In case of CESM-8P it should be in increment of 125 micro secs and
        Max limit are as follows. T1 = 24 ms  E1 = 26 ms T3 = 1.447 ms 
        and E3 = 1.884 ms.
        Default values in CESM-8T1/E1 and CESM-T3/E3.:
        For  T1 and E1 , 1000 microsecs.
        For  T3 and E3 , 1000 microsecs.

        "
--DEFVAL ?
        ::= { cesmChanCnfGrpEntry 11}

cesCellLossIntegrationPeriod    OBJECT-TYPE
    SYNTAX    INTEGER (1000..65535)
    ACCESS read-write
        STATUS  mandatory
        DESCRIPTION
        "Specifies the cell loss integration period in milliseconds
        "
--  DEFVAL
        ::= { cesmChanCnfGrpEntry 12}


cesChanLocRmtLpbkState    OBJECT-TYPE
    SYNTAX  INTEGER {
    enable(1), 
    disable(2) 
    }
    ACCESS read-write 
    STATUS  mandatory  
    DESCRIPTION    
        "Loopback on cellbus in egress direction.
        " 
        DEFVAL { disable }
        ::= { cesmChanCnfGrpEntry 13}
 
cesChanTestType         OBJECT-TYPE  
    SYNTAX  INTEGER {
      testcon(1),
      testdelay(2),
      notest(3),
	  testconsti(4),
	  testdelaysti(5)
    }     
    ACCESS read-write 
    STATUS  mandatory  
    DESCRIPTION    
        "This is the type of the test
        1 = Test Continuity
        2 = Test Delay
        3 = no test is initated 
		4 = test continuity with sti cell format
		5 = test delay with sti cell format
        " 
     DEFVAL { notest}  
     ::= { cesmChanCnfGrpEntry 14}
 
cesChanTestState         OBJECT-TYPE  
    SYNTAX  INTEGER  {
		 passed(1),
         failed(2),
         inprogress(3),
         notinprogress(4)
      }
 
    ACCESS read-only 
    STATUS  mandatory  
    DESCRIPTION    
        "This shows the state of the test
        1 = Passed
        2 = Failed
        3 = In Progress 
        4 = Not In Progress
        " 
        ::= { cesmChanCnfGrpEntry 15}

cesChanRTDResult         OBJECT-TYPE  
    SYNTAX  INTEGER (1..65535)  
    ACCESS read-only 
    STATUS  mandatory  
    DESCRIPTION    
        "This is round trip delay in milliseconds
        " 
        ::= { cesmChanCnfGrpEntry 16}

cesChanPortNum         OBJECT-TYPE
    SYNTAX  INTEGER (1..248)  
    ACCESS read-write 
    STATUS  mandatory  
    DESCRIPTION    
        " This indicates to which logical port this connection 
          belongs. Applicable on CESM-8T1/E1 or CESM-T3/E3.
          1.. 248 for E1
          1.. 192 for T1
          1.. 1 for T3
           Only applicable to CESM-8P
        " 
        ::= { cesmChanCnfGrpEntry 17}

cesChanConnType         OBJECT-TYPE  
    SYNTAX  INTEGER {
      pvc(1),
      svc(2),
      spvc(3)
    }     
    ACCESS read-write 
    STATUS  mandatory  
    DESCRIPTION    
        "This indicates the type of connection.
         1 = PVC
         2 = SVC
         3 ==> SPVC connection

         Only applicable to CESM-8P and CESM-T3/E3.
        "
     DEFVAL { pvc }
     ::= { cesmChanCnfGrpEntry 18}

cesChanStrauSciNum         OBJECT-TYPE  
    SYNTAX  INTEGER {
         nonStrauChannel(1),
      	 sci1(2),
      	 sci2(3),
      	 sci3(4),
      	 sci4(5)
    }     
    ACCESS read-write 
    STATUS  mandatory  
    DESCRIPTION    
        "This indicates the type of connection.
         1 = Normal Channel (nonStrauChannel(0) )
         2 = SCI 1 i.e bit 1 & 2
         3 = SCI 2 i.e bit 3 & 4
         4 = SCI 3 i.e bit 5 & 6
         5 = SCI 4 i.e bit 7 & 8
         Currently not supported in CESM-8  
	 Not applicable for CESM-4 and CESM-T3/E3
        "
     DEFVAL { nonStrauChannel }
     ::= { cesmChanCnfGrpEntry 19}

cesChanIdleDetEnable          OBJECT-TYPE  
    SYNTAX  INTEGER {
      disable(1),
      enableOnhookDet(2),
      enableIdlePatternDet(3)
    }     
    ACCESS read-write 
    STATUS  mandatory  
    DESCRIPTION    
        "This indicates the type of Idle detection enabled
         1 = Idle code detection is disabled.
         2 = This will enable Idle detection whenver it detects
             Onhook in ABCD bits. Onhook code is configurable
             using cesChanOnhookCode. Applicable in
             structured mode.
         3 = This will enable payload Idle code detection.
             Idle pattern is configurable through cesChanIdleSignalCode
             variable.
             Only applicable to CESM-8T1/E1 and non strau channels
             This will be supported in future release
	     
         "
         DEFVAL { disable }
     ::= { cesmChanCnfGrpEntry 20}

cesChanIdleSignalCode         OBJECT-TYPE  
    SYNTAX  INTEGER (0..255)  
    ACCESS read-write 
    STATUS  mandatory  
    DESCRIPTION    
         "When cesChanIdleDetEnable = enableIdlePatternDet
          3. This object will carry value 0..0xff and this will 
          indicate Idle  pattern in DS0 time slots.
         Only applicable to CESM-8P and not supported in this release.
         " 
      ::= { cesmChanCnfGrpEntry 21}
cesChanIdleCodeIntgnPeriod         OBJECT-TYPE  
    SYNTAX  INTEGER (0..100)  
    ACCESS read-write 
    STATUS  mandatory  
    DESCRIPTION    
       " This variable indicates the Integration period in seconds
         whenever  cesChanIdleDetEnable = enableIdlePatternDet
         Only applicable to CESM-8P and not supported in this release.
       " 
         
      ::= { cesmChanCnfGrpEntry 22}

cesChanOnhookCode         OBJECT-TYPE
    SYNTAX  INTEGER (0..15)
    ACCESS read-write
    STATUS  mandatory
    DESCRIPTION
        " When cesChanIdleDetEnable = enableOnhookDet
         1. This will carry value 0..3 for framing mode SF.
         2. This will carry value 0..15 for framing mode ESF/e1Cas.
	 Only applicable for CESM-8T1/E1
       "
      ::= { cesmChanCnfGrpEntry 23}

cesChanConditionedData         OBJECT-TYPE
    SYNTAX  INTEGER (0..255)
    ACCESS read-write
    STATUS  mandatory
    DESCRIPTION
        " This byte will indicate Idle data to be sent
          towards the line whenever channels goes
          in to Underrun
	 Only applicable for CESM-8T1/E1
       "
      DEFVAL { 255 }
      ::= { cesmChanCnfGrpEntry 24}


cesmChanExtTrgIdleSupp          OBJECT-TYPE
    SYNTAX  INTEGER {
      disablesuppression(1),
      enableSuppresion(2)
    }
    ACCESS read-write
    STATUS  mandatory
    DESCRIPTION
        "Using this variable we can initiate Idle suppression on the
         connection. This can be set by external signalling device.
         Only applicable to CESM-8T1/E1.
        "
    DEFVAL { disablesuppression }
    ::=  { cesmChanCnfGrpEntry 25 }

cesmChanConditionedSigCode          OBJECT-TYPE
    SYNTAX  INTEGER (0..255)
    ACCESS read-write
    STATUS  mandatory
    DESCRIPTION
        " This byte will indicate Signal code to be sent
          sent towards the line whenever channels goes
          in to Underrun
         Only applicable to CESM-8T1/E1
       "
      DEFVAL { 255 }
      ::= { cesmChanCnfGrpEntry 26}


cesLocalVpi OBJECT-TYPE
	SYNTAX 	INTEGER (0..65535)
	ACCESS	read-only
	STATUS	mandatory
	DESCRIPTION
		"This VPI together with the local VCI and NSAP represents the
		 local end point in this connection, this object is read only,
		 therefore it'll be assigned by SM to 0.
		"
	::= { cesmChanCnfGrpEntry 27 }

cesLocalVci OBJECT-TYPE
	SYNTAX 	INTEGER (0..65535)
	ACCESS	read-only
	STATUS	mandatory
	DESCRIPTION
		"This VCI together with the local VPI and NSAP represents the
		 local end point in this connection, this object is read only,
		 therefore it'll be assigned by SM to 0.
		"
	::= { cesmChanCnfGrpEntry 28 }

cesLocalNSAP OBJECT-TYPE
	SYNTAX	OCTET STRING (SIZE(0..20))
	ACCESS	read-write
	STATUS	mandatory
	DESCRIPTION
		"This NSAP is 20 bytes binary, among these 20 bytes: 13 bytes
		 as prefix, 2 bytes for Cisco ID, 1 byte rsvd, 3 bytes for
		 logical interface: slot (1 byte) and port number (2 bytes), 
		 the last byte is for SEL"
	::= { cesmChanCnfGrpEntry 29 }

cesRemoteVpi OBJECT-TYPE
	SYNTAX 	INTEGER (0..65535)
	ACCESS	read-write
	STATUS	mandatory
	DESCRIPTION
		"This VPI together with the remote VCI and NSAP represents the
		 remote end point in this connection.
		 The value should be 0 for a DACS connection in MGX"
	::= { cesmChanCnfGrpEntry 30 }

cesRemoteVci OBJECT-TYPE
	SYNTAX 	INTEGER (0..65535)
	ACCESS	read-write
	STATUS	mandatory
	DESCRIPTION
		"This VCI together with the remote VPI and NSAP represents the
		 remote end point in this connection. 
		 The value should be 0 for a DACS connection in MGX"
	::= { cesmChanCnfGrpEntry 31 }

cesRemoteNSAP OBJECT-TYPE
	SYNTAX	OCTET STRING (SIZE(0..20))
	ACCESS	read-write
	STATUS	mandatory
	DESCRIPTION
		"This NSAP is 20 bytes binary, among these 20 bytes: 13 bytes
		 as prefix, 2 bytes for Cisco ID, 1 byte rsvd, 3 bytes for
		 logical interface: slot (1 byte) and port number (2 bytes), 
		 the last byte is for SEL"
	::= { cesmChanCnfGrpEntry 32 }

cesMastership OBJECT-TYPE
	SYNTAX INTEGER {
		master (1),
		slave  (2),
		unkown (3)
	}
	ACCESS read-write
	STATUS mandatory
	DESCRIPTION
		  " This is used by PXM to determine if this end point is 
		  master or slave, a new type unknown is added to identify
		  the SM in MGX8220(formerly AXIS) shelf and the SM in MGX shelf. 
                  In MGX8220 shelf, user can still use addchan to add a channel without
		  specifying X/Y/P parameters. But in MGX shelf, if the
		  user uses addchan without X/Y/P set (based on this object
		  being set to type 3 unknown), SPM on PXM will reject
		  the request. It must be supplied in connection setup request
		"	
	::= { cesmChanCnfGrpEntry 33 }

cesVpcFlag OBJECT-TYPE
        SYNTAX INTEGER {
                vpc (1),
                vcc (2)
        }
        ACCESS read-write
        STATUS mandatory
        DESCRIPTION
		" This represents the connection type, used for PXM to
		  identify VPC/VCC but CESM card doesn't use it
		  always set to vcc for CESM card
                "
        DEFVAL { vcc }
        ::= { cesmChanCnfGrpEntry 34 }
 
cesConnServiceType OBJECT-TYPE
	SYNTAX INTEGER{
		cbr    (1),
		vbr    (2),
		ubr    (4),
		atfr   (5),
		abrstd (6),
		abrfst (7),
		cbr1   (21),
		vbr1rt (22),
        	vbr2rt (23),
        	vbr3rt (24),
        	vbr1nrt(25),
        	vbr2nrt(26),
        	vbr3nrt(27),
        	ubr1   (28),
        	ubr2   (29),
        	stdabr (30),
        	cbr2   (31),
        	cbr3   (32)

	}
	ACCESS read-write
	STATUS mandatory
	DESCRIPTION
		    "This specifies the service type 
     		  1 ==> Constant Bit Rate
	      	  2 ==> Variable Bit Rate
        	  3 ==> Not used
		  4 ==> Unspecified Bit Rate
		  5 ==> ATM frame relay
		  6 ==> standard ABR
		  7 ==> foresight ABR
		Note that this is used by PXM card, SV+ doesn't need to set it,
		if not set in the connection setup request, it'll be defaulted
		to CBR type for CESM.
		Also to make it compatible with existing AUSM MIB definition,
		value 3 is not used.

        	The following types are being added for PNNI support
        	and are based on UNI 4.0.
        	cbr1   (21) - CBR.1
        	vbr1rt (22) - Real time VBR.1
        	vbr2rt (23) - Real time VBR.2
        	vbr3rt (24) - Real time VBR.3
        	vbr1nrt(25) - Non Real time VBR.1
        	vbr2nrt(26) - Non Real time VBR.2
        	vbr3nrt(27) - Non Real time VBR.3
        	ubr1   (28) - UBR.1
        	ubr2   (29) - UBR.2
        	stdabr (30) - TM 4.0 compliant standard ABR
        	cbr2   (31) - CBR.2
        	cbr3   (32) - CBR.3

		Note that for CESM, the only valid connection type for PNNI
		support is cbr1(21). Other enumerations have been added
		for the sake of consistency across Narrow-Band service 
		modules.

		"
	::= { cesmChanCnfGrpEntry 35 }
		
cesRoutingPriority OBJECT-TYPE
	SYNTAX  INTEGER (1..15)
	ACCESS	read-write
	STATUS 	mandatory
	DESCRIPTION
		" This is used by PXM to determine how important 
                  this connection is when selecting connections to route
		"
	::= { cesmChanCnfGrpEntry 36 }
	
cesMaxCost OBJECT-TYPE
	SYNTAX	INTEGER (1..2147483647)
	ACCESS	read-write
	STATUS	mandatory
	DESCRIPTION
		" Maximum allowed cost. It is related to Cost Based Routing.
		  This is used by PXM so that it won't choose a path with
		  a cost greater than this configured level. This is not
		  necessary to be provided in the connection setup request,
		  if not provided, the default value 255 will be used.
		  When used with PAR controller the valid range is 1..65535 and
		  the default value is 255.
		  When used with PNNI controller the valid range is 1..2147483647
		  and the default value is 2147483647.
		" 

	::= { cesmChanCnfGrpEntry 37 }

cesRestrictTrunkType OBJECT-TYPE
	SYNTAX	INTEGER {
		noresriction (1),
		terrestrialTrunk (2),
		sateliteTrunk (3)
	}
	ACCESS	read-write
	STATUS	mandatory
	DESCRIPTION
        	" Restricted trunk type for routing, used by PXM. It 
		  specifies that the connection either cannot be routed over
		  satelite trunks, or terrestrial trunks, or it can be on
		  any type of trunk. It is not necessary to be provide in
		  the connection setup request, the default value is 
		  noresriction(1).
		"
	::= { cesmChanCnfGrpEntry 38 }
 
cesConnPCR OBJECT-TYPE
	SYNTAX INTEGER 
	ACCESS read-write
	STATUS mandatory
	DESCRIPTION
		" Peak cell rate,if not provided in the connection setup
                  request,it will be computed as follows,
                  For CESM-8T1/E1 -  N * 64 Kbps , where N = Number of timeslots assigned
                                                   to this channel.

		  For CESM-T3, the value is 44736 Kbps
		  For CESM-E3, the value is 34368 Kbps.
		"
	::= { cesmChanCnfGrpEntry 39 }

cesConnMCR OBJECT-TYPE
	SYNTAX INTEGER 
	ACCESS read-write
	STATUS mandatory
	DESCRIPTION
		" Minimum cell rate,if not provided in the connection setup
                  request,it will be computed as follows,
                  For CESM-8T1/E1 -  N * 64 Kbps , where N = Number of timeslots assigned
                                                   to this channel.
 
                  For CESM-T3, the value is 44736 Kbps
                  For CESM-E3, the value is 34368 Kbps.
		"
	::= { cesmChanCnfGrpEntry 40 }

cesConnPercentUtil OBJECT-TYPE
	SYNTAX INTEGER  (0..100)
	ACCESS read-write
	STATUS mandatory
	DESCRIPTION
		"This is the expected long-term utilization of the
		 channel by theis end-point.
		 For CESM-8T1/E1/T3/E3 , the value is 100%"
	::= {cesmChanCnfGrpEntry 41 }


cesmConnRemotePCR OBJECT-TYPE
	SYNTAX INTEGER 
	ACCESS read-write
	STATUS mandatory
	DESCRIPTION
		" Peak cell rate of the other end, if not set in MGX, will be 
		  derived from the end point parameter
		"
	::= { cesmChanCnfGrpEntry 42 }

cesmConnRemoteMCR OBJECT-TYPE
	SYNTAX INTEGER 
	ACCESS read-write
	STATUS mandatory
	DESCRIPTION
		" Minimum cell rate of the other end, if not set in MGX, will be 
		  derived from the end point parameter
		"
	::= { cesmChanCnfGrpEntry 43 }

cesmConnRemotePercentUtil OBJECT-TYPE
	SYNTAX INTEGER  (0..100)
	ACCESS read-write
	STATUS mandatory
	DESCRIPTION
		"This is the expected long-term utilization of the
		 channel by the other end-point."

	::= {cesmChanCnfGrpEntry 44 }

cesmConnForeSightEnable OBJECT-TYPE
	SYNTAX INTEGER {
	enable(1),
	disable(2)
	}
	ACCESS read-write
	STATUS mandatory
	DESCRIPTION
		"This object is used by the controller(PAR/PNNI/TAG) to set up
		 the Qbin for the connection. 
		 This is notapplicable to CESM-8T1/E1/T3/E3. "

	::= {cesmChanCnfGrpEntry 45 }

cesmConnFGCRAEnable OBJECT-TYPE
	SYNTAX INTEGER {
	enable(1),
	disable(2)
	}
	ACCESS read-write
	STATUS mandatory
	DESCRIPTION
		"enables/disables Frame based GCRA (early packet discard). 
		 This is not applicable to CESM-8T1/E1/T3/E3."
    DEFVAL {disable}
	::= {cesmChanCnfGrpEntry 46 }

cesmChanReroute OBJECT-TYPE
    SYNTAX INTEGER {
           true(1),
           false(2)
    }
    ACCESS read-write
    STATUS mandatory
    DESCRIPTION
        "This is used by the administrator to trigger the re-routing
         of the connection. The rerouting takes effect, when this object
         is set to true(1). When set to false (2), no action is taken.
         A get on this object always returns false (2).
         This object is not applicable to MGX Release 1.x.
        "
    DEFVAL {false}
    ::= {cesmChanCnfGrpEntry 47 }    

cesmConnAdminStatus OBJECT-TYPE
    SYNTAX INTEGER {
        up(1),
        down(2)
    }
    ACCESS read-write
    STATUS mandatory
    DESCRIPTION
        "This object specifies channel admin status.
         This object is not applicable to MGX Release 1.x.
        "

    DEFVAL {down}
    ::= { cesmChanCnfGrpEntry 48 }


cesmChanNumNextAvailable    OBJECT-TYPE
    SYNTAX  INTEGER (0..279)
    ACCESS  read-only
    STATUS  mandatory
    DESCRIPTION
        "This variable contains the next unused channel number of the possible
         248. This number can be used in channel config table.
         cesChanNumNextAvailable gets updated whenever this number is used to
         create a new logical channel. Value 0 for this variable indicates that
         no more channels are available. In CESM 8-port card), the maximum
         number of values for this variable is 248 (i.e. 32 ..279).
         Only applicable to CESM-8T1/E1/T3/E3.
        "
    ::= { cesmChanCnfGrp 2 }


-- ------------------------------------------------------------------------
-- End of cesmChanCnf group definitions


--
-- ----------------------------------------------------------------------
-- BASIS Project MIB
-- 
--






--circuitEmulation        OBJECT IDENTIFIER ::= { basisServices 3 }
--cesmChan                OBJECT IDENTIFIER ::= { circuitEmulation 2 }
cesmChanCntGrp          OBJECT IDENTIFIER ::= { cesmChan 2 }


-- ------------------------------------------------------------------------
--
-- Group cesmChannelStatus
-- Contains status information for channels
--
-- ------------------------------------------------------------------------


-- ------------------------------------------------------------------------
--
-- cesmChannelCounters group
-- Channel OR VC COUNTERS 
--
-- ------------------------------------------------------------------------


cesmChanCntGrpTable	OBJECT-TYPE
	SYNTAX	SEQUENCE OF CesmChanCntGrpEntry
	ACCESS	not-accessible
	STATUS	mandatory
	DESCRIPTION
		"The config table is for logical channel interface
		 there are 4 entries for 4 DS1s in case of CESM-4P
         In case of CESM-8P it can have 352 entries.
		"
	::= { cesmChanCntGrp 1 }


cesmChanCntGrpEntry	OBJECT-TYPE
	SYNTAX	CesmChanCntGrpEntry
	ACCESS	not-accessible
	STATUS	mandatory
	DESCRIPTION
		" An entry for logical channel
		"
	INDEX	{ cesCntChanNum }
	::= { cesmChanCntGrpTable 1}

CesmChanCntGrpEntry ::=
	SEQUENCE {
		cesCntChanNum 	
			INTEGER,
		cesChanState
			INTEGER,
		cesXmtATMState
			INTEGER,
		cesRcvATMState
			INTEGER,
		cesCellLossStatus
			INTEGER,
		cesReassCells
			Counter,
		cesGenCells
			Counter,
		cesHdrErrors	
			Counter,
		cesPointerReframes
			Counter,
		cesLostCells
			Counter,
		cesBufUnderflows
			Counter,
		cesBufOverflows
			Counter,
		cesIngrDiscardedBytes
			Counter,
		cesUflowInsCells
			Counter,
		cesOflowDropBytes
			Counter,
		cesCellSeqMismatchCnt
			Counter,
-- Reset counters
		counterClrButton
			INTEGER,
        cesChanSecUptime
           Counter,
        cesChanSignalingStatus
            INTEGER,
        cesChanStatusBitMap
            INTEGER
}

cesCntChanNum OBJECT-TYPE
	SYNTAX	INTEGER (16..279)
	ACCESS	read-only
	STATUS	mandatory
	DESCRIPTION		  
		"Refers to the channel Number
		16 - 19 for CESM-4P
		32 - 279 for CESM-8t1e1
		32 for CESM-T3/E3
		"
	::= { cesmChanCntGrpEntry 1}

cesChanState OBJECT-TYPE
	SYNTAX  INTEGER {
				notConfigured(1),
				okay(2),
				alarm(3),
                failed(4)
				}
	ACCESS  read-only
	STATUS  mandatory
	DESCRIPTION
		"
        This variable indicates the connection status
        failed(4) is added to distinguish between alarm (when the connection
        segment is not actually broken) and failed(when the segment is actually
        broken). This is applicable only to the PNNI environment.
		"
	::= { cesmChanCntGrpEntry 2}


cesXmtATMState OBJECT-TYPE
	SYNTAX  INTEGER {
				other (1),
				normal (2),
				sendingAIS (3),
				sendingFERF (4)
				}
	ACCESS  read-only
	STATUS  mandatory
	DESCRIPTION
		"
		  This variable indicates the transmit state of channel
		  on the ATM side (towards the network).
		"
	::= { cesmChanCntGrpEntry 3}

cesRcvATMState OBJECT-TYPE
	SYNTAX  INTEGER {
				other (1),
				normal (2),
				receivingAIS (3),
				receivingFERF (4)
				}
	ACCESS  read-only
	STATUS  mandatory
	DESCRIPTION
		"
		  This variable indicates the receive state of channel
		  on the ATM side (from the network).
		"
	::= { cesmChanCntGrpEntry 4}
			
cesCellLossStatus	OBJECT-TYPE
	SYNTAX	INTEGER {
           noLoss (1),
           loss  (2)
           }
	ACCESS	read-only
	STATUS	mandatory
	DESCRIPTION		  
		"When cells are lost for the CellLossIntegrationPeriod the value
         is set to loss ( 2). when cells are no longer lost, the value is
         set to noLoss(1).
		"
	::= { cesmChanCntGrpEntry	5 }

cesReassCells	OBJECT-TYPE
	SYNTAX	Counter
	ACCESS	read-only
	STATUS	mandatory
	DESCRIPTION		  
		"The number of cells played out to T1/E1/T3E3 interface. It
         excludes cells that were discarded for any reason.
		"
	::= { cesmChanCntGrpEntry	6 }

cesGenCells		OBJECT-TYPE
	SYNTAX	Counter 
	ACCESS	read-only
	STATUS	mandatory
	DESCRIPTION		  
		"The number of cells generated from T1/E1/T3E3 interface  and
         sent towards network.
		"
	::= { cesmChanCntGrpEntry	7 }


cesHdrErrors	OBJECT-TYPE
	SYNTAX	Counter
	ACCESS	read-only
	STATUS	mandatory
	DESCRIPTION		  
		"The number of AAL-1 header errors detected and possibly 
         corrected. Header errors include correctable and uncor-
         rectable CRC, plus bad parity.
		"
	::= { cesmChanCntGrpEntry	8 }

cesPointerReframes	OBJECT-TYPE
	SYNTAX	Counter
	ACCESS	read-only
	STATUS	mandatory
	DESCRIPTION		  
		"The number of events in which the AAL1 reassembler found
         that an SDT pointer is not where it is expected and the 
         and the pointer must be reacquired. Not supported in
         cesm8P due limitation in AAL1 SAR.
	 Not applicable for CESM-4T1/E1 and CESM-T3/E3
		"
	::= { cesmChanCntGrpEntry	9 }

cesLostCells	OBJECT-TYPE
	SYNTAX	Counter
	ACCESS	read-only
	STATUS	mandatory
	DESCRIPTION		  
		"The number of cells lost in egress direction due to
		 AAL 1 header errors and missing cells.
		"
	::= { cesmChanCntGrpEntry	10 }

cesBufUnderflows	OBJECT-TYPE
	SYNTAX	Counter
	ACCESS	read-only
	STATUS	mandatory
	DESCRIPTION		  
		"The number of buffer underflows in Egress direction
         Not supported in cesm8P due limitation in AAL1 SAR.
		"
	::= { cesmChanCntGrpEntry	11 }

cesBufOverflows	OBJECT-TYPE
	SYNTAX	Counter
	ACCESS	read-only
	STATUS	mandatory
	DESCRIPTION		  
		"The number of buffer overflows in Egress direction
         Not supported in cesm8P due limitation in AAL1 SAR.
		"
	::= { cesmChanCntGrpEntry	12 }


cesIngrDiscardedBytes	OBJECT-TYPE
	SYNTAX	Counter
	ACCESS	read-only
	STATUS	mandatory
	DESCRIPTION		  
		"The number of bytes discarded due to shelf alarm in ingress 
         direction from port data. Not supported in CESM-8P.
		"
	::= { cesmChanCntGrpEntry	13 }

cesUflowInsCells	OBJECT-TYPE
	SYNTAX	Counter
	ACCESS	read-only
	STATUS	mandatory
	DESCRIPTION
		"The Number of All 1's cells inserted in case of Egress Buffer
		  Underflow
          Not supported in CESM-8P. 
		 "
	::= { cesmChanCntGrpEntry	14 }

cesOflowDropBytes	OBJECT-TYPE
	SYNTAX	Counter
	ACCESS	read-only
	STATUS	mandatory
	DESCRIPTION
		"The Number of bytes discarded in Egress direction because of
		 Egress buffer overflow
         Not supported in CESM-8P.
		 "
	::= { cesmChanCntGrpEntry	15 }


cesCellSeqMismatchCnt	OBJECT-TYPE
	SYNTAX	Counter
	ACCESS	read-only
	STATUS	mandatory
	DESCRIPTION
		"The Number of times SAR received a valid out of sequence AAL-1
		  cell from CellBus.
		 "
	::= { cesmChanCntGrpEntry	16 }

counterClrButton OBJECT-TYPE
               SYNTAX  INTEGER {
                        noAction (1),
                        resetCounters (2)
                        }
                ACCESS  read-write
                STATUS  mandatory
                DESCRIPTION
                        "writing a value of 2 resets all the counters
                        "
	::= { cesmChanCntGrpEntry	17 }

cesChanSecUptime	OBJECT-TYPE
	SYNTAX	Counter
	ACCESS	read-only
	STATUS	mandatory
	DESCRIPTION
		"The Number of seconds channel is in service
		 only applicable for CESM-8P
		 "
	::= { cesmChanCntGrpEntry	18 }


cesChanSignalingStatus OBJECT-TYPE
	SYNTAX  INTEGER {
			off-hook(1),
		    on-hook(2)
	     	}
	ACCESS  read-only
	STATUS  mandatory
	DESCRIPTION
		"
        This variable indicates the connection signalling status
        Connection will be in Idle suppression mode if it in on-hook.
        Not applicable for T3E3 and CESM-4P.
		"
	::= { cesmChanCntGrpEntry 19}

cesChanStatusBitMap OBJECT-TYPE
    SYNTAX  INTEGER (0..'ff'h)
    ACCESS  read-only
    STATUS  mandatory
    DESCRIPTION

        "This variable indicates the consolidated bit map of the channel alarm
        state.

        Individual bit positions are as defined below.

        Bit position   Fail/Alarm     Reason
        ------------   ----------     ------
            0           Alarm       Reserved
            1           Alarm       n/w side AIS/RDI Rx
            2           Fail        Conditioned(A bit from n/w)
            3           Alarm       Reserved         
            4           Fail        Reserved            
            5           Fail        Reserved            
            6           Alarm       Reserved            
            7           Alarm       Cell loss alarm

            Fail bitmap mask : 0x34
            Alarm bitmap mask: 0xCB

            This object is not applicable to MGX Release 1.x.
        "

    ::= { cesmChanCntGrpEntry 20}


-- ------------------------------------------------------------------------
-- End of cesmChanCnt group definitions


-- ----------------------------------------------------------------------
-- BASIS Project MIB
-- 
-- Initial revision  by Jayakumar for CESM-8P 3/23/97
-- 



--circuitEmulation        OBJECT IDENTIFIER ::= { basisServices 3 }
cesmPort                  OBJECT IDENTIFIER ::= { circuitEmulation 1 }  
cesmPortCnfGrp            OBJECT IDENTIFIER ::= { cesmPort 1 }


-- ------------------------------------------------------------------------
--
-- cesmPortConfig group
-- Port configurable parameters  
--
-- ------------------------------------------------------------------------


cesmPortCnfGrpTable	OBJECT-TYPE
	SYNTAX	SEQUENCE OF CesmPortCnfGrpEntry
	ACCESS	not-accessible
	STATUS	mandatory
	DESCRIPTION
		"The config table is for logical port interface
		 there are 192 entries for 8 DS1s or 248 entries for 8 E1s
		"
	::= { cesmPortCnfGrp 1 }


cesmPortCnfGrpEntry	OBJECT-TYPE
	SYNTAX	CesmPortCnfGrpEntry
	ACCESS	not-accessible
	STATUS	mandatory
	DESCRIPTION
		" An entry for logical port
		"
	INDEX	{ cesPortNum }
    ::= { cesmPortCnfGrpTable 1 }

CesmPortCnfGrpEntry ::=
	SEQUENCE {
		cesPortNum 	
			INTEGER,
   		cesPortRowStatus
         		INTEGER,
		cesPortLineNum 	
			INTEGER,
		cesPortType
               		INTEGER,
		cesPortDs0ConfigBitMap	 	
			INTEGER,
      	cesPortNumOfDs0Slot
        		INTEGER,
      	cesPortNumOfSCIPerDS0  
          		INTEGER,
        cesPortSpeed
     			INTEGER,
		cesPortState
		        INTEGER,
		cesPortBERTEnable
		        INTEGER
	
		}

cesPortNum	OBJECT-TYPE
	SYNTAX	INTEGER (1..248) 
	ACCESS	read-only
	STATUS	mandatory
	DESCRIPTION
		"This is logical port number.
		 If we have T1 card then the maximum port number is 192
		 and if we have E1 card the maximum port number can be 248
         for T3 only one port is supported.
		"
	::= { cesmPortCnfGrpEntry 1}


cesPortRowStatus  OBJECT-TYPE		
	SYNTAX	INTEGER {
		add(1),
		del(2),
		mod(3)
		}
	ACCESS read-write
        STATUS  mandatory
        DESCRIPTION
        "This variable enables or modifies the port
		1- add
		2 - del
		3 - mod
        "
        ::= { cesmPortCnfGrpEntry 2 }

cesPortLineNum	OBJECT-TYPE
	SYNTAX	INTEGER (1..8) 
	ACCESS	read-write
	STATUS	mandatory
	DESCRIPTION
		"This represents the line number to which this port is associated.
         For T3 only one line is supported.
		"
	::= { cesmPortCnfGrpEntry 3}

cesPortType	OBJECT-TYPE
	SYNTAX	INTEGER {
            structured(1),
            unstructured(2),
            framingOnVcDisconnect(3),
            strau(4)
            }
	ACCESS	read-write
	STATUS	mandatory
	DESCRIPTION
		"This represents port type whether it is carrying  subrate circuits
         strau. If it is strau port then it can have only one DS0 time slot.
         In case of unstructured all the time slots will be allocated to that.
         Strau ports are not supported in CESM-8T1/E1 or CESM-T3E3.
         framingOnVcDisconnect is similar to unstructured port 
         during normal operation. In case of channel failure, line data will
         be looped back towards line.
         CESM-T3E3 card will support only unstructured mode.
		"
	 ::= { cesmPortCnfGrpEntry 4 }

cesPortDs0ConfigBitMap	OBJECT-TYPE
	SYNTAX	INTEGER (0..'ffffff'h) 
	ACCESS	read-write
	STATUS	mandatory
	DESCRIPTION
		"This respesents bit map of DS0s for a line which
		 are used to form this logical port. Bit 0
		 represents DS0-1.
          
		"
	::= { cesmPortCnfGrpEntry 5 }

cesPortNumOfDs0Slot 	OBJECT-TYPE
	SYNTAX	INTEGER (1..32) 
	ACCESS	read-write
	STATUS	mandatory
	DESCRIPTION
		"This represents  number of DS0 time slots configured to this
         Port. If the port type is strau then this can not have
         more than 1 DS0 time slot.
		"
	::= { cesmPortCnfGrpEntry 6}

cesPortNumOfSCIPerDS0 	OBJECT-TYPE
	SYNTAX	INTEGER (1..8) 
	ACCESS	read-write
	STATUS	mandatory
	DESCRIPTION
		"This is applicable only to the Strau Port.
         represents  number of subcircuit in the DS0 time slot.
         8 = there are 8 no .of 8kbps links  (1 bit)
         4 = there are 4 no .of 16kbps links (2 bit)
         2 = there are 2 no .of 32kbps links (4 bit)
         Currently not supported in CESM-8
		"
    DEFVAL { 4 }
	::= { cesmPortCnfGrpEntry 7}

cesPortSpeed       OBJECT-TYPE
        SYNTAX  INTEGER (0..44736)
    	ACCESS      read-only
        STATUS  mandatory
        DESCRIPTION
                "Configured speed of port in kbps
                 Max speed for T1 = 1544
                 Max speed for E1 = 2038
                 Max speed for T3 = 44736
                 Max spped for E3 = 34368
                "
        ::= { cesmPortCnfGrpEntry 8 }

cesPortState OBJECT-TYPE
        SYNTAX  INTEGER {
                notConfigured(1),
                active(2),
                remoteLoopback(3),
                failedDueToLine(4),
                failedDueToSignalling(5),
                inactive(6),
                inBert(7),
                farEndRemoteLoopback(8)
        }
        ACCESS  read-only
        STATUS  mandatory
        DESCRIPTION
                "This variable indicates the state of the
                 logical port
                "
        DEFVAL { notConfigured }
        ::= { cesmPortCnfGrpEntry 9 }
 


cesPortBERTEnable	   OBJECT-TYPE
        SYNTAX  INTEGER {
                        disable(1),
                        enable(2)
                        }
    ACCESS  read-write
    STATUS  mandatory
    DESCRIPTION
                "This variable enables BERT
                 This object is not supported in CESM-T3E3.
                 "
	DEFVAL { disable }
        ::= { cesmPortCnfGrpEntry 10 }
 

	

--
--	Next available port
--

cesPortNextAvailable 	OBJECT-TYPE
	SYNTAX	INTEGER (0..248) 
	ACCESS	read-only
	STATUS	mandatory
	DESCRIPTION
		"This variable contains the next UNUSED logical port number
		 of the possible 32 DS0s * n ports.  
		 This number can be used in channel config table, the 
		 cesportNextAvailable gets updated if the number gets
		 used to create a logical port.  
		 A '0' indicates that no more ports are available.
		"
	::= { cesmPortCnfGrp 2 }

--- This will indicate the DS0 slots used by the ports
--- that belongs the particular line.
	


cesPortsUsedLine1 	OBJECT-TYPE
	SYNTAX	INTEGER (0..'ffffff'h) 
	ACCESS	read-only
	STATUS	mandatory
	DESCRIPTION
		"Each bits set represents a DS0 that is used by all the
		 logical ports defined so far for that DS1, the most significant
		 byte is invalid for DS1
		 This is for line 1
		"
	::= { cesmPortCnfGrp 3 }

cesPortsUsedLine2 	OBJECT-TYPE
	SYNTAX	INTEGER (0..'ffffff'h) 
	ACCESS	read-only
	STATUS	mandatory
	DESCRIPTION
		"Each bits set represents a DS0 that is used by all the
		 logical ports defined so far for that DS1, the most significant
		 byte is invalid for DS1
		 This is for line 2
		"
	::= { cesmPortCnfGrp 4 }

cesPortsUsedLine3 	OBJECT-TYPE
	SYNTAX	INTEGER (0..'ffffff'h) 
	ACCESS	read-only
	STATUS	mandatory
	DESCRIPTION
		"Each bits set represents a DS0 that is used by all the
		 logical ports defined so far for that DS1, the most significant
		 byte is invalid for DS1
		 This is for line 3
		"
	::= { cesmPortCnfGrp 5 }

cesPortsUsedLine4 	OBJECT-TYPE
	SYNTAX	INTEGER (0..'ffffff'h) 
	ACCESS	read-only
	STATUS	mandatory
	DESCRIPTION
		"Each bits set represents a DS0 that is used by all the
		 logical ports defined so far for that DS1, the most significant
		 byte is invalid for DS1
		 This is for line 4
		"
	::= { cesmPortCnfGrp 6 }

cesPortsUsedLine5 	OBJECT-TYPE
	SYNTAX	INTEGER (0..'ffffff'h) 
	ACCESS	read-only
	STATUS	mandatory
	DESCRIPTION
		"Each bits set represents a DS0 that is used by all the
		 logical ports defined so far for that DS1, the most significant
		 byte is invalid for DS1
		 This is for line 5
		"
	::= { cesmPortCnfGrp 7 }

cesPortsUsedLine6 	OBJECT-TYPE
	SYNTAX	INTEGER (0..'ffffff'h) 
	ACCESS	read-only
	STATUS	mandatory
	DESCRIPTION
		"Each bits set represents a DS0 that is used by all the
		 logical ports defined so far for that DS1, the most significant
		 byte is invalid for DS1
		 This is for line 6
		"
	::= { cesmPortCnfGrp 8 }

cesPortsUsedLine7 	OBJECT-TYPE
	SYNTAX	INTEGER (0..'ffffff'h) 
	ACCESS	read-only
	STATUS	mandatory
	DESCRIPTION
		"Each bits set represents a DS0 that is used by all the
		 logical ports defined so far for that DS1, the most significant
		 byte is invalid for DS1
		 This is for line 7
		"
	::= { cesmPortCnfGrp 9 }

cesPortsUsedLine8 	OBJECT-TYPE
	SYNTAX	INTEGER (0..'ffffff'h) 
	ACCESS	read-only
	STATUS	mandatory
	DESCRIPTION
		"Each bits set represents a DS0 that is used by all the
		 logical ports defined so far for that DS1, the most significant
		 byte is invalid for DS1
		 This is for line 8
		"
	::= { cesmPortCnfGrp 10 }

--


--circuitEmulation        OBJECT IDENTIFIER ::= { basisServices 3 }
--cesmPort                  OBJECT IDENTIFIER ::= { circuitEmulation 1 }  
cesmPortCnfResPartGrp            OBJECT IDENTIFIER ::= { cesmPort 2 }

-- --------------------------------------------------------------------
--
--
--              LOGICAL PORT CONFIG Resource Partition Group
--
--
-- --------------------------------------------------------------------

cesmPortCnfResPartGrpTable	OBJECT-TYPE
	SYNTAX  SEQUENCE OF CesmPortCnfResPartGrpEntry
	ACCESS  not-accessible
	STATUS  mandatory
	DESCRIPTION
		"This table contains the configuration of port resource 
		 partition
		 This is applicable for MGX8820(formerly AXIS) Rel. 5 and MGX.
		"
	::= {cesmPortCnfResPartGrp 1}

cesmPortCnfResPartGrpEntry		OBJECT-TYPE
	SYNTAX  CesmPortCnfResPartGrpEntry
	ACCESS  not-accessible
	STATUS  mandatory
	DESCRIPTION
		"An entry for logical port
		"
	INDEX  { cesmResPartPortNum, cesmResPartCtrlrNum }
	::= { cesmPortCnfResPartGrpTable 1 }

CesmPortCnfResPartGrpEntry ::=
	SEQUENCE {
		cesmResPartPortNum	INTEGER,
		cesmResPartCtrlrNum	INTEGER,
		cesmResPartRowStatus	INTEGER,
		cesmResPartNumOfLcnAvail	INTEGER,
		cesmResPartLcnLow	INTEGER,
		cesmResPartLcnHigh	INTEGER,
		cesmResPartIngrPctBW	INTEGER,
		cesmResPartEgrPctBW	INTEGER,
		cesmResPartCtrlrID  INTEGER
	}

cesmResPartPortNum	OBJECT-TYPE
        SYNTAX  INTEGER (1..248)
        ACCESS  read-only
        STATUS  mandatory
        DESCRIPTION
                "This is the logical port number, the index to this table.
	 	 If we have T1 card then the maximum port number is 192
		 and if we have E1 card the maximum port number can be 248.
                 CESM-T3/E3 supports only one port.
                "
        ::= { cesmPortCnfResPartGrpEntry 1 }

cesmResPartCtrlrNum OBJECT-TYPE
        SYNTAX  INTEGER {
		par (1),
		pnni(2),
		tag (3)
	}
        ACCESS  read-only
        STATUS  mandatory
        DESCRIPTION
                "This is index for controller using the port
                "
        ::= { cesmPortCnfResPartGrpEntry 2 }

cesmResPartRowStatus OBJECT-TYPE
        SYNTAX  INTEGER {
		add (1),
		del (2),
		mod (3)
	}
        ACCESS  read-write
        STATUS  mandatory
        DESCRIPTION
                " This will add, delete or modify the partition.
		1 ==> ADD
        	2 ==> DELETE
        	3 ==> MODIFY
		"
        ::= { cesmPortCnfResPartGrpEntry 3 }

cesmResPartNumOfLcnAvail OBJECT-TYPE
        SYNTAX  INTEGER (0..248)
        ACCESS  read-write
        STATUS  mandatory
        DESCRIPTION
                " This represents number of LCNs available for this
		  controller and this port.
		  In CESM-T3/E3 and 8-T1/E1,this value is 1.
                "
        ::= { cesmPortCnfResPartGrpEntry 4 }

cesmResPartLcnLow OBJECT-TYPE
        SYNTAX  INTEGER (1..248)
        ACCESS  read-write
        STATUS  mandatory
        DESCRIPTION
                "This represents low end of reserved LCN
		 In CESM-8T1/E1 and T3/E3, this refers to the
                 logical port.
                "
        ::= { cesmPortCnfResPartGrpEntry 5 }

cesmResPartLcnHigh OBJECT-TYPE
        SYNTAX  INTEGER (1..248)
        ACCESS  read-write
        STATUS  mandatory
        DESCRIPTION
                "This represents high end of reserved LCN
		 In CESM-8T1/E1 and T3/E3, this refers to the
                 logical port.
                "
        ::= { cesmPortCnfResPartGrpEntry 6 }

cesmResPartIngrPctBW OBJECT-TYPE
        SYNTAX  INTEGER (0..100)
        ACCESS  read-write
        STATUS  mandatory
        DESCRIPTION
                "The percentage of total ingress bandwidth reserved.
                 In CESM-8T1/E1 and T3/E3, as
                 there is only one LCN per port and it could be
                 used by only one controller,this value is
                 100% for that controller.
                "
        ::= { cesmPortCnfResPartGrpEntry 7 }

cesmResPartEgrPctBW OBJECT-TYPE
        SYNTAX  INTEGER (0..100)
        ACCESS  read-write
        STATUS  mandatory
        DESCRIPTION
                "The percentage of total egress bandwidth reserved 
                 In CESM-8T1/E1 and T3/E3, as
                 there is only one LCN per port and it could be
                 used by only one controller,this value is
                 100% for that controller.
                "
        ::= { cesmPortCnfResPartGrpEntry 8 }

cesmResPartCtrlrID OBJECT-TYPE
        SYNTAX INTEGER(1..255)
        ACCESS read-write
        STATUS mandatory
        DESCRIPTION
                "This is the controller identifier for the  resource patition.
                 The  default value is set for PNNI controller.
                "
        DEFVAL { 2 }

        ::= { cesmPortCnfResPartGrpEntry 9 }

-- ----------------------------------------------------------------------
-- BASIS Project MIB
-- 
-- Initial revision  by Jayakumar for CESM-8P 3/23/97
-- 


--circuitEmulation        OBJECT IDENTIFIER ::= { basisServices 3 }
cesmEndPtMapGrp        OBJECT IDENTIFIER ::= { circuitEmulation 3 }  

-- ------------------------------------------------------------------------
--
-- Group cesmEndpoint Map group
--
-- ------------------------------------------------------------------------


cesmEndPtMapGrpTable OBJECT-TYPE
	SYNTAX  SEQUENCE OF CesmEndPtMapGrpEntry
	ACCESS  not-accessible
	STATUS  mandatory
	DESCRIPTION
		"There are 248 entries and port num will uniquely 
                 identify a row.

		 For CESM-8T1/E1 , only 248 ports are possible.
		 For CESM-T3/E3, only one port is possible.
		"
	::= { cesmEndPtMapGrp 1 }

cesmEndPtMapGrpEntry OBJECT-TYPE
	SYNTAX CesmEndPtMapGrpEntry
	ACCESS not-accessible
	STATUS mandatory
	DESCRIPTION
		"An entry for cesmEndPtMapGrpEntry.
		"
	INDEX	{ cesEndPortNum }
	::= { cesmEndPtMapGrpTable 1 }

CesmEndPtMapGrpEntry ::=
	SEQUENCE {
		cesEndPortNum
         		INTEGER,
		cesEndChanNum
			INTEGER,
		cesEndLineNum
			INTEGER
		}

cesEndPortNum OBJECT-TYPE
	SYNTAX	INTEGER (1..248)
	ACCESS	read-only
	STATUS	mandatory
	DESCRIPTION		  
		"Refers to the logical port index
		 CESM-8E1 supports 248 ports.
		 CESM-8T1 supports 192 ports.
		 CESM-T3/E3 supports only one port.
		"
	::= { cesmEndPtMapGrpEntry 1}

cesEndChanNum OBJECT-TYPE
	SYNTAX INTEGER (32..279)
	ACCESS read-only
	STATUS mandatory
	DESCRIPTION
		"Logical connection number for above cesEndPortNum
		"
	::= { cesmEndPtMapGrpEntry 2}

cesEndLineNum OBJECT-TYPE
	SYNTAX INTEGER (1..8)
	ACCESS read-only
	STATUS mandatory
	DESCRIPTION
		"Refers to the physical line index
         In case T3 only one line will be supported.
		"
	::= { cesmEndPtMapGrpEntry 3}


-- ------------------------------------------------------------------------
-- End of cesmEndPtMap group definitions


--
-- ----------------------------------------------------------------------
-- BASIS Project MIB
-- 
--






-- frChan     		OBJECT IDENTIFIER ::= { frameRelay 2 }
frChanCnfGrp		OBJECT IDENTIFIER ::= { frChan 1 }


-- ------------------------------------------------------------------------
--
-- frChannelConfig group
-- Channel configurable parameters  (VC)
--
-- ------------------------------------------------------------------------


frChanCnfGrpTable	OBJECT-TYPE
	SYNTAX	SEQUENCE OF FrChanCnfGrpEntry
	ACCESS	not-accessible
	STATUS	mandatory
	DESCRIPTION
		"The config table is for logical channel interface
		 (upto 4000 entries). The actual number of entries
		 supported by a card depends on the type of card.
		 eg: FRSM-4T1/E1 supports 256 entries
		     FRSM-8T1/E1 supports 1000 entries
		     FRSM-T3/E3/HS2/HS2B-HSSI/T3B/E3B supports 2000 entries
		     FRSM-2CT3/HS2B-12IN1 supports 4000 entries
		     FRSM12 supports 16000 entries
		"
	::= { frChanCnfGrp 1 }

frChanCnfGrpEntry	OBJECT-TYPE
	SYNTAX	FrChanCnfGrpEntry
	ACCESS	not-accessible
	STATUS	mandatory
	DESCRIPTION
		" An entry for logical channel
		"
	INDEX	{ chanNum }
	::= { frChanCnfGrpTable 1 }

FrChanCnfGrpEntry ::=
	SEQUENCE {
	   	chanNum			INTEGER,
		chanRowStatus          	INTEGER, 
		chanPortNum             INTEGER, 
		dLCI		        INTEGER,
		egressQSelect	      	INTEGER,
		ingressQDepth	      	INTEGER,
		ingressQDEThresh   	INTEGER,
		ingressQECNThresh	INTEGER,
		egressQDepth	      	INTEGER,
		egressQDEThresh	   	INTEGER,
		egressQECNThresh	INTEGER,
        	deTaggingEnable     	INTEGER,
        	cir                 	INTEGER,
        	bc                  	INTEGER,
        	be                  	INTEGER,
        	ibs                 	INTEGER,
        	foreSightEnable     	INTEGER,
        	qir                 	INTEGER,
        	mir                 	INTEGER,
        	pir                 	INTEGER,
        	chanLocRmtLpbkState	INTEGER,
        	chanTestType            INTEGER,
        	chanTestState           INTEGER,
        	chanRTDResult           INTEGER,
		chanType	INTEGER,
		chanFECNconfig	INTEGER,
		chanDEtoCLPmap	INTEGER,
		chanCLPtoDEmap	INTEGER,
-- CAC parameters (IngrPcr will be derived from foresightPIR )
		chanIngrPercentUtil	INTEGER,
		chanEgrPercentUtil  INTEGER,
		chanEgrSrvRate      INTEGER,
		chanOvrSubOvrRide   INTEGER,
		chanFrConnType	INTEGER,
		frCDRNumber	INTEGER,
-- Connection parameters, used by PXM
		frLocalVpi		INTEGER,
		frLocalVci		INTEGER,
		frLocalNSAP		OCTET STRING,
		frRemoteVpi		INTEGER,
		frRemoteVci		INTEGER,
		frRemoteNSAP		OCTET STRING,
		frMastership		INTEGER,
		frVpcFlag		INTEGER,
		frConnServiceType	INTEGER,
		frRoutingPriority	INTEGER,
		frMaxCost		INTEGER,
		frRestrictTrunkType 	INTEGER,
		frConnPCR		INTEGER,
		frConnRemotePCR		INTEGER,
		frConnMCR		INTEGER,
		frConnRemoteMCR		INTEGER,
		frConnPercentUtil	INTEGER,
		frConnRemotePercentUtil	INTEGER,
		frConnForeSightEnable	INTEGER,
		frConnFGCRAEnable	INTEGER,
-- Channel service type used by FRSM-VHS
		chanServType    INTEGER,
-- adding the sar service rate fields to meet sprint req.
		chanServiceRateOverride		INTEGER,
		chanServiceRate				INTEGER,
		zeroCirConEir				INTEGER,
		chanReroute           INTEGER,
		frConnSCR             INTEGER,
		frConnRemoteSCR       INTEGER,
		frConnTemplateId      INTEGER,
		frConnAdminStatus     INTEGER,
-- added for FRSM12 card
		frChanCnfChangeCount    Counter,
		frChanCnfIgnoreIncomingDE  INTEGER,
		frChanOamCCEnable     INTEGER,
		frChanStatsEnable     INTEGER,
		frChanLocalLpbkEnable INTEGER,
		frChanUpcEnable       INTEGER,
		frChanSlaveType      INTEGER,
-- applicable for all FRSM cards
		frConnRemoteMBS      INTEGER
	    
}


chanNum OBJECT-TYPE
	SYNTAX	INTEGER
	ACCESS	read-only
	STATUS	mandatory
	DESCRIPTION		  
		"Refers to the virtual connection index
		 Note that the actual range of the index
		 supported by a card depends on the type of card.
		 eg: FRSM-4T1/E1 supports a range from 16..271 (256 entries)
		     FRSM-8T1/E1 supports a range from 16..1015 (1000 entries)
		     FRSM-T3/E3/HS2/HS2B-HSSI/T3B/E3B supports a range from
		     16..2015 (2000 entries)
		     FRSM-2CT3/HS2B-12IN1 supports a range from 16..4015 (4000 entries)
		     For FRSM12 Card:
		     Byte 3 = Chassis Number, Byte 2 = Slot Number,
		     Byte 1 & 0 = channel Number.
		     Lower two bytes range from 16..16015 (16000 entries)
		"
	::= { frChanCnfGrpEntry 1}

chanRowStatus  OBJECT-TYPE
	SYNTAX	INTEGER {
		add(1),
		del(2),
		mod(3),
-- added outOfService for Release2.2
                outOfService(4)

		}
	ACCESS read-write
   STATUS  mandatory
   DESCRIPTION
      "This will add, delete or modify the channel
       1 ==> ADD
       2 ==> DELETE
       3 ==> MODIFY
       Setting this object to outOfService takes the channel
       out of service or brings the channel 'down'. The channel
       can be brought 'up' again by setting the object to mod
		"
   	::= { frChanCnfGrpEntry 2 }

chanPortNum OBJECT-TYPE
	SYNTAX	INTEGER
	ACCESS	read-write
	STATUS	mandatory
	DESCRIPTION		  
		"Refers to the logical ports that are possible
		 on this card, the user must set this variable
		 For FRSM12 Card:
		 This object contains the port's ifIndex value.
		"
	::= { frChanCnfGrpEntry	3}

dLCI OBJECT-TYPE
	SYNTAX	INTEGER (0..8388607)
	ACCESS	read-write
	STATUS	mandatory
	DESCRIPTION		  
		"This variable is the DLCI number of the channel. 
		 The user has to set this variable. 
		 All the connections on the same port should have 
		 a unique DLCI number. 
		 Note that if we are adding a channel to a port that
		 has LMI signalling enabled, then we can not use DLCI
		 number 0(ANNEX A & D) and 1023(STRATA LMI). 
		 For FRSM12 Card:
		 For FR header length of 2-bytes, DLCI range is (0 .. 1023) and
			0, 1007, 1023 DLCIs cannot be used.
		 For FR header length of 4-bytes, DLCI range is (0 .. 8388607) and
			0, 8257535 DLCIs cannot be used.

		"
	::= { frChanCnfGrpEntry	4}

egressQSelect OBJECT-TYPE
	SYNTAX	INTEGER {
		highPriority(1),
		lowPriority(2),
		notSupported(3)
		}
	ACCESS	read-write
	STATUS	mandatory
	DESCRIPTION		  
		"Selects one out of two possible port queues.
		 The default port queue number is 1 which is the high 
		 pririty queue.
		1 = High priority queue 
		2 = Low priority queue 
		3 = Indicates that this entry is not used (eg: in FRSM-VHS,
		    chanServType indicates the channel service type and
		    would determine the queue to which the channel gets mapped)
		For FRSM12 Card:
		This object is used to select between the two ATM-COS queues
		in the egress direction.
		"
	DEFVAL { lowPriority }
	::= { frChanCnfGrpEntry	5}

ingressQDepth	OBJECT-TYPE
	SYNTAX	INTEGER (4510..'1fffff'h)
	ACCESS read-write
        STATUS  mandatory
        DESCRIPTION
        "This variable sets the max depth for queue, before
         it starts dropping the cells. It is defined in
         terms of number of bytes.
         In all cards except the FRSM-VHS card, the range is
         limited to (4510..'ffff'h).

         ingressQDepth should be greater than ingressQECNThresh
         and ingressQDEThresh

         For FRSM12 Card: Not Supported
        "
	DEFVAL { 65535 }
        ::= { frChanCnfGrpEntry 6}

ingressQECNThresh	OBJECT-TYPE
	SYNTAX	INTEGER (0..'1fffff'h)
	ACCESS read-write
        STATUS  mandatory
        DESCRIPTION
        "This variable sets the max depth for queue, before
		 it  starts flow control. It is defined in terms of
		 number of bytes.
		 In all cards except the FRSM-VHS card, the range is
		 limited to (0..'ffff'h).

		 For FRSM12 Card: Not Supported
		"
	DEFVAL { 6553 }
        ::= { frChanCnfGrpEntry 7}

ingressQDEThresh	OBJECT-TYPE
	SYNTAX	INTEGER (0..'1fffff'h)
	ACCESS read-write
        STATUS  mandatory
        DESCRIPTION
        "This variable sets the max depth for queue, before
		 they become discard eligible. It is defined in terms of 
		 number of bytes.
		 In all cards except the FRSM-VHS card, the range is
		 limited to (0..'ffff'h).

		 For FRSM12 Card: Not Supported
		"
	DEFVAL { 32767 }
        ::= { frChanCnfGrpEntry 8}

egressQDepth	OBJECT-TYPE
	SYNTAX	INTEGER (0..'1fffff'h)
	ACCESS read-write
        STATUS  mandatory
        DESCRIPTION
        "This variable sets the max depth for queue, before
		 it  starts dropping the cells. It is defined in terms of 
		 number of bytes.
		 In all cards except the FRSM-VHS card, the range is
		 limited to (0..'ffff'h).

		 egressQDepth should be greater than egressQDEThresh 
		 and egressQECNThresh

		 For FRSM12 Card: Not Supported
		"
	DEFVAL { 65535 }
        ::= { frChanCnfGrpEntry 9}

egressQDEThresh	OBJECT-TYPE
	SYNTAX	INTEGER (0..'1fffff'h)
	ACCESS read-write
        STATUS  mandatory
        DESCRIPTION
        "This variable sets the max depth for queue, before
		 they become discard eligible. It is defined in terms of 
		 number of bytes.
		 In all cards except the FRSM-VHS card, the range is
		 limited to (0..'ffff'h).

		 For FRSM12 Card: Not Supported
		"
	DEFVAL { 32767 }
        ::= { frChanCnfGrpEntry 10}

egressQECNThresh        OBJECT-TYPE
        SYNTAX  INTEGER (0..'1fffff'h)
        ACCESS read-write
        STATUS  mandatory
        DESCRIPTION
        "This variable sets the max depth for queue, before
         it  starts flow control. It is defined in terms of 
		 number of bytes.
		 In all cards except the FRSM-VHS card, the range is
		 limited to (0..'ffff'h).

		 For FRSM12 Card: Not Supported
        "
	DEFVAL { 6553 }
        ::= { frChanCnfGrpEntry 11}

-- Shawn K. 5/17/95 added
deTaggingEnable OBJECT-TYPE
    SYNTAX  INTEGER {
	enable(1),
	disable(2)
	} 
    ACCESS read-write
    STATUS  mandatory
    DESCRIPTION
    "The default value is 2.
	 This variable enables DE tagging in the ingress direction only.
	 enable = 1
	 disable = 2
	 For FRSM12 Card:
	 When this object is disabled, the ingress policer will never
	 set the DE bit to 1 in the Frame Relay frames even if 
	 the incoming frame exceeds the Bc bucket.
        "
	DEFVAL { disable }
        ::= { frChanCnfGrpEntry 12}
 
cir OBJECT-TYPE
    SYNTAX  INTEGER (0..52000000)
    ACCESS read-write
    STATUS  mandatory
    DESCRIPTION
         "The default value is 2400
	  cir defines committed information rate
	  cir is in bits per second
	  Maximum value for cir for an E1 card is 2048000 and
	  for a T1 card is 1536000.
	  cir has to be less than or equal to the port speed.
	  Maximum value for cir for an E3 card is 34368000, for
	  a T3 card is 44736000m, and for HSSI it is 52000000.
	  Note that for FRSM-2CT3 card, the peak value of
	  permissible CIR is 1536000.
	  Maximum value for FRSM-HS2B-12IN1 is 10240000
	  Any value from 1 to 2399 will be rounded off to 2400.
	  For FRSM12 Card:
	  The range is 0-44736000 bps for T3, and
	  The range is 0-34368000 bps for E3.
	  cir can be 0 only for chanServType of uBR.
        "
	DEFVAL { 2400 }
        ::= { frChanCnfGrpEntry 13}
         
bc OBJECT-TYPE
    SYNTAX  INTEGER (0..2097151)
    ACCESS read-write
    STATUS  mandatory
    DESCRIPTION
        "The default value is 5100
	 bc defines burst committed.  bc is in bytes.
	 bc can not be 0 when cir is not 0.
	 bc has to be 0 if cir is 0.
	 The peak value for bc in FRSM-VHS cards is (2^21 -1),
	 i.e. 2097151 and for all other cards, it is 65535.
	 For FRSM-VHS cards, the relation between CIR and Bc should 
	 be such that Tc is always less than 512 seconds. 
	 For FRSM12 Card: 
	 The range is 0-2097151
        "
	DEFVAL { 5100 }
        ::= { frChanCnfGrpEntry 14}
         
be OBJECT-TYPE
    SYNTAX  INTEGER (0..2097151)
    ACCESS read-write
    STATUS  mandatory
    DESCRIPTION
        "The default value is 5100 be defines the burst excess.
     	     be can not be 0 when cir is 0.  be is in bytes.
	     The peak value for be in FRSM-VHS cards is (2^21 -1),
		 i.e. 2097151 and for all other cards, it is 65535.
		 For FRSM-VHS cards, setting the value of 2091751 will 
		 cause the policing to be disabled.
		 For FRSM12 Card: 
		 The range is 0-2097151
		"
	DEFVAL { 5100 }
        ::= { frChanCnfGrpEntry 15}
         
ibs OBJECT-TYPE
    SYNTAX  INTEGER (0..2097151)
    ACCESS read-write
    STATUS  mandatory
    DESCRIPTION
        "The default value is 100
	 ibs should be less or equal to bc when cir is greater
	 than 0. ibs has to be 0 when cir is 0.
	 The peak value for ibs in FRSM-VHS cards is (2^21 -1),
	 i.e. 2097151 and for all other cards, it is 65535.

	 For FRSM12 Card: Not Supported
        "
	DEFVAL { 100 }
        ::= { frChanCnfGrpEntry 16}
         
foreSightEnable OBJECT-TYPE
    SYNTAX  INTEGER {
	enable(1),
	disable(2)
	}
    ACCESS read-write
    STATUS  mandatory
    DESCRIPTION
        "The default value is 2
	  This variable sets foreSight option
	  Note that when you enable foresight option then you can
	  modify qir, mir and pir, otherwise you CAN NOT change
	  these values if you are disabling foresight or if foresight
	  option is already disabled.
	  The RATE CONTROL FEATURE has to be ON in order to enable 
	  foresight and also modify its parameter. 
	  enable = 1
	  disable = 2

	 For FRSM12 Card: Not Supported
        "
	DEFVAL { disable }
        ::= { frChanCnfGrpEntry 17}
 
qir OBJECT-TYPE
    SYNTAX  INTEGER (160..6400000)
    ACCESS read-write
    STATUS  mandatory
    DESCRIPTION
        "The dafault is 160
	 qir is defined in fastpackets/sec and it defines
	 quiescent information rate for Foresight.  1 cell/sec
	 is equal to 16 fastpackets/sec.
	 Following information about cps is for reference only: 
	 The peak value for qir in FRSM-VHS cards is 285714 cps and
	 for all other cards, it is 10000 cps.
	 For FRSM-VHS cards, cell will be the ATM cell (48 byte payload).

	 For FRSM12 Card: Not Supported
        "
	DEFVAL { 160 }
        ::= { frChanCnfGrpEntry 18}
 
mir OBJECT-TYPE
    SYNTAX  INTEGER (160..6400000)
    ACCESS read-write
    STATUS  mandatory
    DESCRIPTION
        "The dafault is 160
	 mir is defined in fastpackets/sec and it defines
	 minimum information rate for Foresight.  1 cell/sec 
	 is equal to 16 fastpackets/sec.
	 Following information about cps is for reference only: 
	 The peak value for qir in FRSM-VHS cards is 285714 cps and
	 for all other cards, it is 10000 cps.
	 For FRSM-VHS cards, cell will be the ATM cell (48 byte payload).

	 For FRSM12 Card: Not Supported
        "
	DEFVAL { 160 }
        ::= { frChanCnfGrpEntry 19}
         
pir OBJECT-TYPE
    SYNTAX  INTEGER (160..6400000)
    ACCESS read-write
    STATUS  mandatory
    DESCRIPTION
        "The dafault is 160
	 pir is defined in fastpackets/sec and it defines
	 peak information rate for Foresight.  1 cell/sec
	 is equal to 16 fastpackets/sec.
	 Following information about cps is for reference only: 
	 The peak value for qir in FRSM-VHS cards is 285714 cps and
	 for all other cards, it is 10000 cps.
	 For FRSM-VHS cards, cell will be the ATM cell (48 byte payload).

	 For FRSM12 Card: Not Supported
        "
	DEFVAL { 160 }
        ::= { frChanCnfGrpEntry 20}


chanLocRmtLpbkState OBJECT-TYPE 
    SYNTAX  INTEGER {
	enable(1), 
	disable(2) 
	}
    ACCESS read-write 
    STATUS  mandatory 
    DESCRIPTION 
        "The default is disable.
	 This variable enables or disables the remote loopback for each
	 channel.
	 When you enable this option on a connection (channel) then all the
	 cells that are coming from the network side would be looped back
	 toward the network and all the frames coming from the user side
	 would be dropped.
	 This channel remote loopback has nothing to do with the chanTestType
	 option, each one does a different function. 
	 For example, the channel remote loopback is used for looping the data
	 toward the network and if this connection is terminated on an IPX
	 then they can put a test equipment and measure some of the 
	 characteristics of the network.
	1 = enable
	2 = disable

	 For FRSM12 Card: Not Supported
        " 
	DEFVAL { disable }
        ::= { frChanCnfGrpEntry 21} 

chanTestType OBJECT-TYPE  
    SYNTAX  INTEGER {
    	testcon(1),
	testdelay(2),
	notest(3)
	}
    ACCESS read-write 
    STATUS  mandatory  
    DESCRIPTION    
        "The default is notest.
	 The chanTestType starts testing the continuity or delay of a connection.
	 It sends specific cell patterns toward the network and the terminating
	 end of this connection has to be an AXIS or ASI of a BPX in order for 
	 this test to be working. 
	 The receiving node would loop back when it receives these
	 cells. The test should be done in about couple of seconds. The testcon
	 tests the continuity of the connection and testdelay uses the same
	 test except that it measures for delay through the network. 
	 To test the delay follow this procedure:
		a- set chanTestType to testdelay
		b- read chanTestState till it is Pass or Fail 
		c- Read chanRTDResult for the delay if it is Pass
		*Note that the chanTestType would go back to notest when the
		 test is completed 
	 To test the continuity follow this procedure:
		a- set chanTestType to testcon
		b- read chanTestState till it is Pass or Fail 
		*Note that the chanTestType would go back to notest when the
		 test is completed 
	 You CAN NOT select 2 tests back to back, you have selcelt one and wait 
	 the result and then start the other one.
    SYNTAX  
	 When you select testdelay 
	 
	 This is the type of the test
	 1 = Test Continuity
	 2 = Test Delay
	 3 = No Test
        " 
	DEFVAL { notest }
        ::= { frChanCnfGrpEntry 22}  
 
chanTestState OBJECT-TYPE  
    SYNTAX  INTEGER {
	passed(1),
	failed(2),
	inprogress(3),
	notinprogress(4)
	} 
    ACCESS read-only 
    STATUS  mandatory  
    DESCRIPTION    
        "This shows the state of the test
	 When you add a connection then the chanTestState becomes notinprogress
	 and when you select any test, it would go to inprogress state and after
	 it completes the test, it will go to failed or passed state.
	 1 = Passed
	 2 = Failed
	 3 = In Progress 
	 4 = Not In Progress
        " 
	DEFVAL { notinprogress }
        ::= { frChanCnfGrpEntry 23}  
 
chanRTDResult OBJECT-TYPE  
    SYNTAX  INTEGER (1..65535)  
    ACCESS read-only 
    STATUS  mandatory  
    DESCRIPTION    
        "This is round trip delay in milliseconds.
	 When you select testdelay option for the chanTestType, the result of
	 the test that is measured in milliseconds can be read in chanRTDResult.
        " 
	DEFVAL { 65535 }
        ::= { frChanCnfGrpEntry 24}  
 
chanType	OBJECT-TYPE
	SYNTAX	INTEGER {
		frNIW(1),
		frSIW-transparent(2),
		frSIW-translate(3),
		frFUNI(4),
		frForward(5),
		frNIWReplace(6)
		}
	ACCESS read-write
        STATUS  mandatory
        DESCRIPTION
                "sets channel type
                 Type 1 is frame-relay network interworking (NIW-unicast)
                 type 2 is service interworking with out any SDU translation
                 type 3 is service interworking with SDU translation
                 type 4 is frame-relay UNI, currently mode-1a which is ALL5
                 type 5 is frame forwarding
                 types 1,2,3 and 5 are supported as explained above 
                 type 4 (frame-relay UNI) is NOT supported
                 type 6 is also supported. It  means frame-relay Network
                 Interworking with DLCI in FRSSCS-PDU always set to 1022
                 For FRSM12 Card: frFUNI is not supported.
                "
        ::= { frChanCnfGrpEntry 25 }

chanFECNconfig	OBJECT-TYPE
	SYNTAX	INTEGER {
		mapEFCI(1),
		setEFCIzero(2)
		}
	ACCESS read-write
        STATUS  mandatory
        DESCRIPTION
                "sets FECN config mapEFCI valid only for SIW 
                 The FECN bits in frame-relay are mapped to EFCI bit in the ATM
                 cells.
		"
        ::= { frChanCnfGrpEntry 26 }

chanDEtoCLPmap	OBJECT-TYPE
	SYNTAX	INTEGER {
		mapCLP(1),
		setCLPzero(2),
		setCLPone(3) 
		}
	ACCESS read-write
        STATUS  mandatory
        DESCRIPTION
                "sets mapping of CLP bit 
                 The DE bit is mapped to CLP bit in ATM cell
                 in Case 2 and 3, the DE bit is ignored and CLP bit
                 is set to a constant value
                 For FRSM12 Card:
                 Should not be mapCLP for chanType of frForward.
		"
        ::= { frChanCnfGrpEntry 27 }

chanCLPtoDEmap	OBJECT-TYPE
	SYNTAX	INTEGER {
		mapDE(1),
		setDEzero(2),
		setDEone(3),
		ignoreCLP(4) 
		}
	ACCESS read-write
        STATUS  mandatory
        DESCRIPTION
                "sets mapping of DE bit 1,2,3 valid for SIW
                 1,4 valid for NIW
                 The CLP bit is mapped to DE bit in frame-relay
                 in the Case of 2 and 3, the CLP bit is ignored and DE bit
                 is set to a constant value
                 ignoreCLP ignores CLP bit and DE bit remains as received.
                 For FRSM12 Card:
                 Should be ignoreCLP for chanType of frForward.
                 Should not be setDEzero/setDEone for chanType of frNIW 
                    and frNIWReplace.
                 Should not be ignoreCLP for chanType of frSIW-transparent
                    and frSIW-translate.
		"
        ::= { frChanCnfGrpEntry 28 }

chanIngrPercentUtil	OBJECT-TYPE
	SYNTAX	INTEGER (1..100)	
	ACCESS	read-write
	STATUS	mandatory
        DESCRIPTION
				"the channel ingress utilized percentage
				"
	DEFVAL { 100 }
        ::= { frChanCnfGrpEntry 29 }


chanEgrPercentUtil  OBJECT-TYPE
	SYNTAX	INTEGER (1..100)	
	ACCESS	read-write
	STATUS	mandatory
        DESCRIPTION
				"the channel egress utilized percentage
				"
	DEFVAL { 100 }
        ::= { frChanCnfGrpEntry 30 }

chanEgrSrvRate  OBJECT-TYPE
    	SYNTAX  INTEGER (2400..52000000)
	ACCESS	read-write
	STATUS	mandatory
    DESCRIPTION
	"The channel egress cir.
	 Maximum value for chanEgrSrvRate for an E1 card is 2048000 and
	 for a T1 card is 1536000.
	 chanEgrSrvRate has to be less than or equal to the port speed.
	 Maximum value for chanEgrSrvRate for an E3 card is 34368000, for
	 a T3 card is 44736000m, and for HSSI it is 52000000.
	 Note that for FRSM-2CT3 card, the peak value of
	 permissible chanEgrSrvRate is 1536000.
	 For FRSM12 Card:
	 This object is used only for CAC and the range will be same
	 as the range for cir object. The Maximum value is 44736000m.
	"
	DEFVAL { 2400 }
        ::= { frChanCnfGrpEntry 31 }


chanOvrSubOvrRide   OBJECT-TYPE
 	SYNTAX  INTEGER {
	        disable (1),
    	    	enable (2)
       		 }
	ACCESS read-write 
	STATUS  mandatory  
	DESCRIPTION    
		"This MIB variable allows one to add a new connection on a port
		 even if it is over subscribed.

		 For FRSM12 Card: Not Supported
		" 
	DEFVAL { disable }
        ::= { frChanCnfGrpEntry 32 }

chanFrConnType	OBJECT-TYPE
	SYNTAX	INTEGER {
		pvc(1),
		svc(2),
		spvc(3),
		par(4),
		pnni(5),
		tag(6)
		}
	ACCESS read-write
        STATUS  mandatory
        DESCRIPTION
                "channel connection type
		 1 for pvc
		 2 for svc
		 3 for spvc
		 4 par (only for trunk connection)
		 5 pnni (only for trunk connection)
		 6 tag (only for trunk connection)

		 For FRSM12 Card: Not Supported
		"
	DEFVAL { pvc }
        ::= { frChanCnfGrpEntry 33 }

-- Added by Jerry Shiao on 1/16/97

frCDRNumber OBJECT-TYPE
	SYNTAX INTEGER 
	ACCESS read-write
	STATUS mandatory
	DESCRIPTION
		"This is the key to correlate cell/frame counts, start/end record.

		 For FRSM12 Card: Not Supported
		"
	::= { frChanCnfGrpEntry 34 }


frLocalVpi OBJECT-TYPE
	SYNTAX 	INTEGER (0..65535)
	ACCESS	read-only
	STATUS	mandatory
	DESCRIPTION
		"This VPI together with the local VCI and NSAP represents the
		 local end point in this connection, this object is read only,
		 therefore it'll be assigned by SM to 0.
		"
	::= { frChanCnfGrpEntry 35 }

frLocalVci OBJECT-TYPE
	SYNTAX 	INTEGER (0..65535)
	ACCESS	read-only
	STATUS	mandatory
	DESCRIPTION
		"This VCI together with the local VPI and NSAP represents the
		 local end point in this connection, this object is read only,
		 therefore it'll be assigned by SM to be equal to DLCI.
		"
	::= { frChanCnfGrpEntry 36 }

frLocalNSAP OBJECT-TYPE
	SYNTAX	OCTET STRING (SIZE(0..20))
	ACCESS	read-write
	STATUS	mandatory
	DESCRIPTION
		"This NSAP is 20 bytes binary, among these 20 bytes: 13 bytes
		 as prefix, 2 bytes for Cisco ID, 1 byte rsvd, 3 bytes for
		 logical interface: slot (1 byte) and port number (2 bytes), 
		 the last byte is for SEL
		 For FRSM12 Card:
		 This object will have the NSAP format as required by the
		 PNNI controller
		"
	::= { frChanCnfGrpEntry 37 }

frRemoteVpi OBJECT-TYPE
	SYNTAX 	INTEGER (0..65535)
	ACCESS	read-write
	STATUS	mandatory
	DESCRIPTION
		"This VPI together with the remote VCI and NSAP represents the
		 remote end point in this connection
		"
	::= { frChanCnfGrpEntry 38 }

frRemoteVci OBJECT-TYPE
	SYNTAX 	INTEGER (0..65535)
	ACCESS	read-write
	STATUS	mandatory
	DESCRIPTION
		"This VCI together with the remote VPI and NSAP represents the
		 remote end point in this connection
		"
	::= { frChanCnfGrpEntry 39 }

frRemoteNSAP OBJECT-TYPE
	SYNTAX	OCTET STRING (SIZE(0..20))
	ACCESS	read-write
	STATUS	mandatory
	DESCRIPTION
		"This NSAP is 20 bytes binary, among these 20 bytes: 13 bytes
		 as prefix, 2 bytes for Cisco ID, 1 byte rsvd, 3 bytes for
		 logical interface: slot (1 byte) and port number (2 bytes), 
		 the last byte is for SEL"
	::= { frChanCnfGrpEntry 40 }

frMastership OBJECT-TYPE
	SYNTAX INTEGER {
		master (1),
		slave (2),
		unknown (3)
	}
	ACCESS read-write
	STATUS mandatory
	DESCRIPTION
		" This is used by PXM to determine if this end point is 
		  master or slave, a new type unknown is added to identify
		  the SM in AXIS shelf and the SM in MGX shelf. In AXIS
		  shelf, user can still use addchan to add a channel without
		  specifying X/Y/P parameters. But in MGX shelf, if the
		  user uses addchan without X/Y/P set (based on this object
		  being set to type 3 unknown), SPM on PXM will reject
		  the request. It must be supplied in connection setup request.
		  In the feeder mode, this is always set to master.
		"
	::= { frChanCnfGrpEntry 41 }

frVpcFlag OBJECT-TYPE
	SYNTAX INTEGER {
		vpc (1),
		vcc (2)
	}
	ACCESS read-write
	STATUS mandatory
	DESCRIPTION
		" This represents the connection type, used for PXM to
		  identify VPC/VCC but FRSM card doesn't use it
		  always set to vcc for FRSM card
		  For FRSM12 Card:
		  This object is used by the PNNI controller and is 
		  always set to VCC
		"
	DEFVAL { vcc }
	::= { frChanCnfGrpEntry 42 }

frConnServiceType OBJECT-TYPE
	SYNTAX INTEGER{
		cbr    (1),
		vbr    (2),
		notUsed (3),
		ubr    (4),
		atfr   (5),
		abrstd (6),
		abrfst (7),
		vbrrt  (8),
        cbr1   (21),
        vbr1rt (22),
        vbr2rt (23),
        vbr3rt (24),
        vbr1nrt(25),
        vbr2nrt(26),
        vbr3nrt(27),
        ubr1   (28),
        ubr2   (29),
        stdabr (30),
        cbr2   (31),
        cbr3   (32)


	}
	ACCESS read-write
	STATUS mandatory
	DESCRIPTION
		  "This specifies the service type 
     		  1 ==> Constant Bit Rate
	      	  2 ==> Variable Bit Rate
        	  3 ==> Not used
		  4 ==> Unspecified Bit Rate
		  5 ==> ATM frame relay
		  6 ==> standard ABR
		  7 ==> foresight ABR
		Note that this is used by PXM card, SV+ doesn't need to set it,
		if not set in the connection setup request, it'll be defaulted
		to ATFR type for FRSM.
		Also to make it compatible with existing AUSM MIB definition,
		value 3 is not used.

        The following types are being added for PNNI support.
        and are based on UNI 4.0
        cbr1   (21) - CBR.1
        vbr1rt (22) - Real time VBR.1
        vbr2rt (23) - Real time VBR.2
        vbr3rt (24) - Real time VBR.3
        vbr1nrt(25) - Non Real time VBR.1
        vbr2nrt(26) - Non Real time VBR.2
        vbr3nrt(27) - Non Real time VBR.3
        ubr1   (28) - UBR.1
        ubr2   (29) - UBR.2
        stdabr (30) - TM 4.0 compliant standard ABR
        cbr2   (31) - CBR.2
        cbr3   (32) - CBR.3

        For FRSM12 Card:
        Not Supported. Derived from chanServType.
		"
	DEFVAL {atfr}
	::= { frChanCnfGrpEntry 43 }
		
frRoutingPriority OBJECT-TYPE
	SYNTAX  INTEGER (1..15)
	ACCESS	read-write
	STATUS 	mandatory
	DESCRIPTION
		" This is used by PXM to determine how important this 
		  connection is when selecting connections to route
		"
	DEFVAL {1}
	::= { frChanCnfGrpEntry 44 }
	
frMaxCost OBJECT-TYPE
	SYNTAX	INTEGER (1..2147483647)
	ACCESS	read-write
	STATUS	mandatory
	DESCRIPTION
		" Maximum allowed cost. It is related to Cost Based Routing.
		  This is used by PXM so that it won't choose a path with
		  a cost greater than this configured level. This is not
		  necessary to be provided in the connection setup request,
		  if not provided, the default value 255 will be used.
          When used with PAR controller the valid range is 1..65535 and the
          default value is 255.
          When used with PNNI controller the valid range is 1..2147483647 and
          the default value is 2147483647.

		"
	::= { frChanCnfGrpEntry 45 }

frRestrictTrunkType OBJECT-TYPE
	SYNTAX	INTEGER {
		norestriction (1),
		terrestrialTrunk (2),
		sateliteTrunk (3)
	}
	ACCESS	read-write
	STATUS	mandatory
	DESCRIPTION
		" Restricted trunk type for routing, used by PXM. It 
		  specifies that the connection either cannot be routed over
		  satelite trunks, or terrestrial trunks, or it can be on
		  any type of trunk. It is not necessary to be provide in
		  the connection setup request, the default value is 
		  norestriction(1).

		  For FRSM12 Card: Not Supported
		"
	DEFVAL {norestriction}
	::= { frChanCnfGrpEntry 46 }
 
frConnPCR OBJECT-TYPE
	SYNTAX INTEGER 
	ACCESS read-write
	STATUS mandatory
	DESCRIPTION
		" Peak cell rate, if not provided in the connection setup
		  request, it'll be derived from pir.
		  For FRSM12 Card:
		  Default value is (1.44 * CIR)
		"
	::= { frChanCnfGrpEntry 47 }

frConnRemotePCR OBJECT-TYPE
	SYNTAX INTEGER 
	ACCESS read-write
	STATUS mandatory
	DESCRIPTION
		" Peak cell rate of the other end, if not set, will be
		  set to the same as local end PCR (frConnPCR). However,
		  note that if the CIRs for both local and remote end
		  are set to the different value (i.e., asymmetric conn), 
		  then this should be set differently from local end PCR.
		  For FRSM12 Card:
		  Default value is frConnPCR
		"
	::= { frChanCnfGrpEntry 48 }

frConnMCR OBJECT-TYPE
	SYNTAX INTEGER 
	ACCESS read-write
	STATUS mandatory
	DESCRIPTION
		" Minimum cell rate, if not provided in the connection setup
		  request, it'll be derived from mir.
		  For FRSM12 Card:
		  Default value is frConnPCR
		"
	::= { frChanCnfGrpEntry 49 }

frConnRemoteMCR OBJECT-TYPE
	SYNTAX INTEGER 
	ACCESS read-write
	STATUS mandatory
	DESCRIPTION
		" Minimum cell rate of the other end, if not set, will be
		  set to the same as local end MCR (frConnMCR). However,
		  note that if the CIRs for both local and remote end
		  are set to the different value (i.e., asymmetric conn),
		  then this should be set differently from local end MCR.
		  For FRSM12 Card:
		  Default value is frConnMCR
		"
	::= { frChanCnfGrpEntry 50 }

frConnPercentUtil OBJECT-TYPE
	SYNTAX INTEGER  (0..100)
	ACCESS read-write
	STATUS mandatory
	DESCRIPTION
		"This is the expected long-term utilization of the
		 channel by this end-point. If this is not specified in
		 the connection setup request, it'll be defaulted to
		 100 percent

		 For FRSM12 Card: Not Supported
		"
	DEFVAL {100}
	::= {frChanCnfGrpEntry 51 }

frConnRemotePercentUtil OBJECT-TYPE
	SYNTAX INTEGER  (0..100)
	ACCESS read-write
	STATUS mandatory
	DESCRIPTION
		"This is the expected long-term utilization of the
		 channel by the other end-point. If this is not specified in
		 the connection setup request, it'll be set to be the same
		 as the local end frConnPercentUtil value assuming that the
		 connection is symmetric. In a asymmetric connection, this
		 object is supposed to be set.

		 For FRSM12 Card: Not Supported
		"
	::= { frChanCnfGrpEntry 52 }

frConnForeSightEnable OBJECT-TYPE
    	SYNTAX  INTEGER {
		enable(1),
		disable(2)
		}
	ACCESS read-write
	STATUS mandatory
	DESCRIPTION
		"
		This object is used by the controller(PAR/PNNI/TAG) to
		set up the Qbin for the connection, if this is not set,
		it'll be defaulted by SM to the same as foreSightEnable
		in the end point parameters. 

		 For FRSM12 Card: Not Supported
		"
	::= { frChanCnfGrpEntry 53 }

frConnFGCRAEnable     OBJECT-TYPE
        SYNTAX  INTEGER {
                enable (1),
                disable (2)
                }
        ACCESS read-write
        STATUS  mandatory
        DESCRIPTION
                "enables/disables Frame based GCRA (early packet discard).

                 For FRSM12 Card: Not Supported
                "
	DEFVAL {disable}
        ::= { frChanCnfGrpEntry 54}
 
chanServType OBJECT-TYPE
	SYNTAX INTEGER{
		highpriority(1),
		rtVBR(2),
		nrtVBR(3),
		aBR(4),
		uBR(5),
		queue6(6),
		queue7(7),
		queue8(8),
		stdABR(9)

		}
	ACCESS read-write
	STATUS mandatory
	DESCRIPTION
		"This indicates the class of the connection
		1-High priority (typically CBR connections)
		2- real-time VBR
		3- non-real time VBR
		4- Available Bit Rate
		5- Unspecified Bit Rate
		9- Standard ABR
		There are 8 queues actually but only 4 are currently being used
		(the 4 queues are for CBR, VBR-rt, <VBR-nrt and ABR>, UBR traffic).
		This object is currently suuported only in FRSM-VHS and FRSM-8T1E1.
		For FRSM-8T1E1, a 0 indicates that the connections are of old model
		type where chanServType object is unused.
		Note that chanServType is not modifiable after a channel has been
		enabled
		For FRSM12 Card:
		The types aBR, queue6, queue7, queue8 are not supported
		"
        ::= { frChanCnfGrpEntry 55 }


chanServiceRateOverride	OBJECT-TYPE
	SYNTAX INTEGER{
		enable(1),
		disable(2)
		}
	ACCESS read-write
	STATUS mandatory
	DESCRIPTION
		"This variable sets the SAR IR programming option.
		Foresight and chanServiceRateOverride are mutually exclusive.
		
		For FRSM12 Card: Not Supported
		"
	
	DEFVAL	{disable}


        ::= { frChanCnfGrpEntry 56 }

chanServiceRate	OBJECT-TYPE
	SYNTAX INTEGER	(160..6400000)
	ACCESS	read-write
	STATUS	mandatory
	DESCRIPTION
			"This is the rate to which IR can be set to when 
		chanServiceRateOverride is set to enabled. If chanServiceRateOverride
		is disabled then this object does not have any significance.
		For FRSM-8P, this is defined in fastpackets/sec.
		For FRSM-VHS, this is defined in atm cells per second.
		For VHS the range in cells per second will be 10 to 400000 cps.
		
		For FRSM12 Card: Not Supported
		"

        ::= { frChanCnfGrpEntry 57 }

zeroCirConEir OBJECT-TYPE
	SYNTAX  INTEGER (0..52000000)
	ACCESS read-write
	STATUS  mandatory
	DESCRIPTION
			"zeroCirConEir defines EIR value for '0' CIR connection. 
		If zeroCirConEir is '0', EIR is set to port speed. If zeroCirConEir 
		is non-zero value, EIR is set to value of this object, and this value 
		is used for policing in ingress direction. 
		This object is valid only for a zero cir connection.
		zeroCirConEir has to be less than or equal to the port speed."

	DEFVAL {0}

		::= { frChanCnfGrpEntry 58}
chanReroute    OBJECT-TYPE
    SYNTAX INTEGER {
         true(1),
             false(2)
    }
    ACCESS read-write
    STATUS mandatory
    DESCRIPTION
       " This is used by the administrator to trigger the re-routing
         of the connection. The rerouting takes effect, when this object
         is set to true(1). When set to false (2), no action is taken.
         A get on this object always returns false (2).
         This object is not applicable to MGX Release 1.x.
       "
    DEFVAL {false}
    ::= { frChanCnfGrpEntry 59 }

frConnSCR OBJECT-TYPE
    SYNTAX INTEGER
    ACCESS read-write
    STATUS mandatory
    DESCRIPTION
        " Sustained cell rate, Used for VBR connections setup with PNNI
          controller.
          For FRSM12 Card: Default value is frConnPCR
          This object is not applicable to MGX Release 1.x
        "
    ::= { frChanCnfGrpEntry 60 }

frConnRemoteSCR OBJECT-TYPE
    SYNTAX INTEGER
    ACCESS read-write
    STATUS mandatory
    DESCRIPTION
        " Sustained cell rate of the other end,  Used for VBR connections
          setup with PNNI controller.
          For FRSM12 Card: Default value is frConnSCR
          This object is not applicable to MGX Release 1.x
        "
    ::= { frChanCnfGrpEntry 61 }

frConnTemplateId OBJECT-TYPE
    SYNTAX INTEGER (1..17)
    ACCESS read-write
    STATUS mandatory
    DESCRIPTION
        "This object specifies the template identifier for the connection
         template associated with this connection.
         The valid range for templates is 1..16.
         A value of 17 indicates no template is associated with this
         connection
         For FRSM12 Card: Not Supported
         This object is not applicable to MGX Release 1.x
        "
    DEFVAL {17}
    ::= { frChanCnfGrpEntry 62 }

frConnAdminStatus OBJECT-TYPE
    SYNTAX INTEGER {
        up(1),
        down(2)
    }
    ACCESS read-write
    STATUS mandatory
    DESCRIPTION
        "This object specifies channel admin status. 
         This object is not applicable to MGX Release 1.x.
         "
    DEFVAL {down}
    ::= { frChanCnfGrpEntry 63 }

-- added for FRSM12
frChanCnfChangeCount  OBJECT-TYPE
    SYNTAX	Counter
	ACCESS	read-only
	STATUS	mandatory
	DESCRIPTION
            "
        This object is added only for FRSM12 card.

        This counter tracks the number of configuration changes
		that happen on a channel. The  counter is
		associated only with the end point  and NOT with the
		connection itself.

		This counter is used by the NMS to determine if a connection
		configuration had been modified and requires an upload.
		This functionality is conventionally achieved by time 
		stamping using a time-of-day clock. However, in switches
		where time-of-day clock is not available, the following
		scheme is used:

		The upload counter is incremented, when:

		* assignment of connection to an end point channel. This
		  happens when a connection is added and assigned this 
		  channel number.
		* de-assignment of connection from a channel number. This
		  happens when a connection is deleted and the 
		  end point  resource is released.
		* When there is a configuration change done to the connection
		  that is associated with this end point channel number.

		In a new system, an unutilised resouce (channel number)
		has a counter value of zero. When a connection is added to
		this channel end point, the counter is incremented. And is
		incremented for any of the above operations. When a connection
		is deleted the value of this counter is incremented and
		preserved till a new connection gets associated with this
		channel end point.
        
        This object is not applicable to MGX Release 1.x."
            ::= { frChanCnfGrpEntry 64 }

-- added for FRSM12
frChanCnfIgnoreIncomingDE OBJECT-TYPE
	SYNTAX	INTEGER {
		enable (1),
		disable (2)
		}
	ACCESS	read-write
	STATUS	mandatory
	DESCRIPTION	
		"  
         This object is added for FRSM12 card.

         When this object is enabled, the incoming frames with 
         DE(Discard Eligible) bit set to 1 are counted in the 
         Bc bucket instead of Be bucket
 
         This object is not applicable to MGX Release 1.x.
        "
        ::= { frChanCnfGrpEntry 65 }

-- FRSM12   Following Object is needed if channel Status Objects in MIB 
-- "cardSpecificSM.my" on FRSM12 due to scalability issues, OAMCC per PVC 
-- will be done as this is handled by HW (ATLAS). The OAM LoopBack as 
-- on FRSM, will not be supported. FRSM12 will loop back incoming OAM loopback
-- cells originating from FRSM. But the test cannot be initiated 
-- on FRSM12 (No HW support, will be too much CPU burning for 16K Conns.) 
-- Instead of the FRSM TRAP "50311", "trapGenFrChanAlarm (50393)
-- will be used when OAM CC detects Chan Failure. 

-- added for FRSM12
frChanOamCCEnable OBJECT-TYPE
	SYNTAX	INTEGER {
		enable (1),
		disable (2)
		}
	ACCESS	read-write
	STATUS	mandatory
	DESCRIPTION	
        "
        This object is added for FRSM12 card.

		This object serves to enable or disable continuity check(CC)
		on a connection endpoint. When continuity check is enabled 
		on an endpoint, the endpoint anticipates OAM CC cells from its
		peer endpoint. OAM CC cells are sent when the peer endpoint
		does not have traffic cells to send. If the connection is
		idle and this endpoint has not received OAM CC cells for a 
		period of 3.5 +/- 0.5 seconds, it declares continuity failure.

		This object serves to administratively control the CC feature.
		Typical implementations (of this feature) may choose to ignore
		this control or impose other conditions to actually enable CC 
		cell flow. However, if this object is set to false(2), then this 
		feature should be disabled
    
        This object is not applicable to MGX Release 1.x.
        "
	DEFVAL { disable } 
        ::= { frChanCnfGrpEntry 66 }

-- added for FRSM12
frChanStatsEnable  OBJECT-TYPE
	SYNTAX	INTEGER {
		enable (1),
		disable (2)
		}
	ACCESS	read-write
	STATUS	mandatory
    DESCRIPTION
        "
        This object is added for FRSM12 card.

        Limits imposed by software or hardware implementations
        could restrict the amount of statistical data that can be
        maintained in a physical entity (like a service module card).
        Hence there could be a need to restrict statistics collection
        to a smaller subset.

        This object serves the purpose of enabling/disabling statistics
        collection on a per connection basis. In implementations which
        do not have such limitations, this object can be set to enable(1)
        for all connections
 
        This object is not applicable to MGX Release 1.x.
        "
    DEFVAL { disable }
    ::= { frChanCnfGrpEntry 67 }

-- added for FRSM12
frChanLocalLpbkEnable  OBJECT-TYPE
	SYNTAX	INTEGER {
		enable (1),
		disable (2)
		}
	ACCESS	read-write
	STATUS	mandatory
    DESCRIPTION
        "
        This object is added for FRSM12 card.

        This object when enabled adds a channel-level loopback
        towards the port side.  If the connection is in loopback,
        Connection MIB (FrChanCnfGrpEntry) variables cannot be modified.

        This object is not applicable to MGX Release 1.x.
        "
    DEFVAL { disable }
    ::= { frChanCnfGrpEntry 68 }

-- added for FRSM12
frChanUpcEnable  OBJECT-TYPE
	SYNTAX	INTEGER {
		enable (1),
		disable (2)
		}
	ACCESS	read-write
	STATUS	mandatory
    DESCRIPTION
        "
        This object is added for FRSM12 card.

        This object when disabled, disables Frame Relay policing.

        This object is not applicable to MGX Release 1.x.
        "
    DEFVAL { enable }
    ::= { frChanCnfGrpEntry 69 }

-- added for FRSM12
frChanSlaveType OBJECT-TYPE
    SYNTAX  INTEGER {
        persistentSlave (1),
        nonPersistentSlave (2)
        }
    ACCESS  read-write
    STATUS  mandatory
    DESCRIPTION
        "
        This object is added for FRSM12 card.
        This object indicates whether a master endpoint has a persistent
        slave or not. A connection with a master and a non-persistent
        slave is considered a single-ended SPVC.

        This object is only meaningful when 'frMastership'
        contains the value of 'master(1)'. And this variable 
        must be used with 'frMastership' to decide
        if a connection is single-ended or not.

        This object is not applicable to MGX Release 1.x.
        "
    DEFVAL { persistentSlave }
    ::= { frChanCnfGrpEntry 70 }


frConnRemoteMBS OBJECT-TYPE
    SYNTAX INTEGER (1..5000000)
    ACCESS read-write
	STATUS mandatory
    DESCRIPTION
        "Remote Maximum Burst Size in terms of number of cells.
         This object should be set by the user in cases when
         the remote end of the connection is an ATM end-point
         where the Local MBS can be explicitly specified. In such
         cases, this element should be set to be equal to the
         remote end-point's local MBS.

         This object is not applicable to MGX Release 1.x.
         "
    DEFVAL {1024}
    ::= { frChanCnfGrpEntry 71 }


--
--	Next available channel
--

chanNumNextAvailable 	OBJECT-TYPE
	SYNTAX	INTEGER (16..4015) 
	ACCESS	read-only
	STATUS	mandatory
	DESCRIPTION
		"This variable contains the next UNUSED channel number
		 of the possible 4000 (ranging from 16 to 4015).
		 This number can be used in channel config table, the 
		 ChanNumNextAvailable gets updated if the number gets
		 used to create a logical channel.  
		 A '0' indicates that no more channels are available.

		 For FRSM12 Card: Not Supported
		"
	::= { frChanCnfGrp 2 }



--
-- ----------------------------------------------------------------------
-- BASIS Project MIB
-- 
--






-- frChan     		OBJECT IDENTIFIER ::= { frameRelay 2 }
-- frChanCnfGrp		OBJECT IDENTIFIER ::= { frChan 1 }


-- ------------------------------------------------------------------------
--
-- frstdABRConfig group
-- Channel configurable parameters  (VC)
--
-- ------------------------------------------------------------------------
--

frstdABRCnfGrpTable	OBJECT-TYPE
	SYNTAX	SEQUENCE OF FrstdABRCnfGrpEntry
	ACCESS	not-accessible
	STATUS	mandatory
	DESCRIPTION
		"The ABR config table is for logical channel interface
		 (upto 4000 entries). The actual number of entries
		 supported by a card depends on the type of card.
		 eg: FRSM-4T1/E1 supports 256 entries
		     FRSM-8T1/E1 supports 1000 entries
		     FRSM-T3/E3/HS2/T3B/E3B/HS2B-HSSI supports 2000 entries
		     FRSM-2CT3/HS2B-12IN1 supports 4000 entries
		     FRSM12 supports 16000 entries
		"
	::= { frChanCnfGrp 3 }
	

frstdABRCnfGrpEntry		OBJECT-TYPE
	SYNTAX	FrstdABRCnfGrpEntry
	ACCESS	not-accessible
	STATUS	mandatory
	DESCRIPTION
		" An entry for logical channel
		"
	INDEX	{ frstdABRcnfChanNum }
	::= { frstdABRCnfGrpTable 1 }

FrstdABRCnfGrpEntry ::=
    SEQUENCE {
		frstdABRcnfChanNum	INTEGER,
		frstdABRTBE			INTEGER,
		frstdABRFRTT 		INTEGER,
		frstdABRRDF			INTEGER,
		frstdABRRIF			INTEGER,
		frstdABRNrm			INTEGER,
		frstdABRTrm			INTEGER,
		frstdABRCDF			INTEGER,
		frstdABRADTF		INTEGER,
		frstdABRICR			INTEGER,
		frstdABRMCR			INTEGER,
		frstdABRPCR 		INTEGER
}

frstdABRcnfChanNum OBJECT-TYPE
	SYNTAX INTEGER
	ACCESS read-only
	STATUS mandatory
	DESCRIPTION
		"Refers to the virtual connection index
		 Note that the actual range of the index
		 supported by a card depends on the type of card.
		 eg: FRSM-4T1/E1 supports a range from 16..271 (256 entries)
		     FRSM-8T1/E1 supports a range from 16..1015 (1000 entries)
		     FRSM-T3/E3/HS2/T3B/E3B/HS2B-HSSI supports a range from
		     16..2015 (2000 entries)
		     FRSM-2CT3/HS2B-12IN1 supports a range from 16..4015 (4000 entries)
		     For FRSM12 Card:
		     Byte 3 = Chassis Number, Byte 2 = Slot Number,
		     Byte 1 & 0 = channel Number.
		     Lower two bytes range from 16..16015 (16000 entries)
		"
	::= { frstdABRCnfGrpEntry 1}

frstdABRTBE OBJECT-TYPE
    SYNTAX INTEGER (0..16777215)
    ACCESS read-write
    STATUS mandatory
    DESCRIPTION
        "Transient Buffer Exposure. The unit is number of cells."
    DEFVAL  {16777215}

	::= { frstdABRCnfGrpEntry 2}

frstdABRFRTT OBJECT-TYPE
    SYNTAX INTEGER  (0..16700)
    ACCESS  read-write
    STATUS  mandatory
    DESCRIPTION
        "Fixed Round-Trip Time. The unit is milliseconds. Value 0 signifies
        that FRTT is not available."
    DEFVAL {0}
        ::= { frstdABRCnfGrpEntry 3 }

frstdABRRDF OBJECT-TYPE
    SYNTAX INTEGER  (1..32768)
    ACCESS  read-write
    STATUS  mandatory
    DESCRIPTION
        "Rate Decrease Factor. This unitless value has to be inverted to
        arrive at the actual value. The valid values possible are only powers
        of 2; i.e. 1, 2, 4, 8 ..... 32768. The SNMP agent has to verify this
        compliance."
    DEFVAL {16}
        ::= { frstdABRCnfGrpEntry 4 }

frstdABRRIF OBJECT-TYPE
    SYNTAX INTEGER  (1..32768)
    ACCESS  read-write
    STATUS  mandatory
    DESCRIPTION
        "Rate Increase Factor. This unitless value has to be inverted to
        arrive at the actual value. The valid values possible are only powers
        of 2; i.e. 1, 2, 4, 8 ..... 32768. The SNMP agent has to verify this
        compliance."
    DEFVAL {64}
        ::= { frstdABRCnfGrpEntry 5 }

frstdABRNrm OBJECT-TYPE
    SYNTAX INTEGER  (2..256)
    ACCESS  read-write
    STATUS  mandatory
    DESCRIPTION
        "Maximum number of cells a source may send for each forward RM cell.
        The valid values possible are only powers of 2 starting from 2; 
		i.e. 2, 4, 8 ..... 256. The SNMP agent has to verify this compliance."
    DEFVAL {64}
        ::= { frstdABRCnfGrpEntry 6 }

frstdABRTrm OBJECT-TYPE
    SYNTAX INTEGER  (3..255)
    ACCESS  read-write
    STATUS  mandatory
    DESCRIPTION
        "Upper bound on the time between forward RM cells for an active source.
         The unit is in milliseconds."
    DEFVAL {255}
        ::= { frstdABRCnfGrpEntry 7 }

frstdABRCDF OBJECT-TYPE
    SYNTAX INTEGER  (0..64)
    ACCESS  read-write
    STATUS  mandatory
    DESCRIPTION
        "Cutoff Decrease Factor. This unitless value has to be inverted
        to arrive at the actual value. The valid values possible are 0
        and only powers of 2; i.e., 1, 2, 4, 8, 16, 32, 64. The SNMP agent
        has to verify this compliance."
    DEFVAL {16}
        ::= { frstdABRCnfGrpEntry 8 }

frstdABRADTF OBJECT-TYPE
    SYNTAX INTEGER  (10..10230)
    ACCESS  read-write
    STATUS  mandatory
    DESCRIPTION
        "ACR DecreaseTime Factor. Unit of this value is milliseconds.
        Granularity allowed is 10 milli seconds. The SNMP agent has to
        verify this compliance."
    DEFVAL {500}

        ::= { frstdABRCnfGrpEntry 9 }
		 
frstdABRICR OBJECT-TYPE
    SYNTAX INTEGER  (10..400000)
    ACCESS  read-write
    STATUS mandatory
    DESCRIPTION
        "  Initial Cell Rate is the rate at which the source 
        should send initially and after an idle period. This 
		includes the bandwidth allocated for both data cells 
		as well as all in-rate RM cells.
        Unit is cells/sec. The Range will be 10 to 400000.
		."
    DEFVAL {10}
        ::= { frstdABRCnfGrpEntry 10 }

frstdABRMCR OBJECT-TYPE
    SYNTAX INTEGER  (10..400000)
    ACCESS  read-write
    STATUS mandatory
    DESCRIPTION
        "  Minimum Cell Rate is the rate at which the source 
        is allowed to send. This includes the bandwidth allocated
		for both data cells as well as all in-rate RM cells. 
		Unit is cells/sec.  The Range will be 10 to 400000.
		."
    DEFVAL {10}
        ::= { frstdABRCnfGrpEntry 11 }

frstdABRPCR OBJECT-TYPE
    SYNTAX INTEGER  (10..400000)
    ACCESS read-write
    STATUS mandatory
    DESCRIPTION
        "  Peak Cell Rate is the rate at which the source
        is allowed to send. This includes the bandwidth allocated
		for both data cells as well as all in-rate RM cells. 
		Unit is cells/sec.  The Range will be 10 to 400000.
        "
    DEFVAL {10}
        ::= { frstdABRCnfGrpEntry 12 }



--
-- ----------------------------------------------------------------------
-- BASIS Project MIB
-- 
--





-- frChan     	OBJECT IDENTIFIER ::= { frameRelay 2 }
frChanCntGrp	OBJECT IDENTIFIER ::= { frChan 3 }


-- ------------------------------------------------------------------------
--
-- Group frChannelStatus
-- Contains status information for channels
--
-- ------------------------------------------------------------------------


-- ------------------------------------------------------------------------
--
-- frChannelCounters group
-- Channel OR VC COUNTERS 
--
-- ------------------------------------------------------------------------


frChanCntGrpTable	OBJECT-TYPE
	SYNTAX	SEQUENCE OF FrChanCntGrpEntry
	ACCESS	not-accessible
	STATUS	mandatory
	DESCRIPTION
		"The config table is for logical channel interface
		 there are upto 4000 entries.
		"
	::= { frChanCntGrp 1 }


frChanCntGrpEntry	OBJECT-TYPE
	SYNTAX	FrChanCntGrpEntry
	ACCESS	not-accessible
	STATUS	mandatory
	DESCRIPTION
		" An entry for logical channel
		"
	INDEX	{ cntChanNum }
	::= { frChanCntGrpTable 1}

FrChanCntGrpEntry ::=
	SEQUENCE {
		cntChanNum 	
			INTEGER,
-- Rcv Counters
		rcvFrames		
			Counter,
		rcvBytes	
			Counter,
		rcvFramesDE		
			Counter,
		rcvBytesDE		
			Counter,
		rcvFramesDiscard	
			Counter,
		rcvBytesDiscard	
			Counter,
-- Discarded due to 
		rcvFramesDiscShelfAlarm	
			Counter,
		rcvFramesDiscXceedQDepth
			Counter,
		rcvBytesDiscXceedQDepth
			Counter,
		rcvFramesDiscXceedDEThresh
			Counter,
-- Rcv Congestion
		rcvFramesFECN
			Counter,
		rcvFramesBECN
			Counter,
		rcvFramesTaggedFECN
			Counter,
		rcvFramesTaggedBECN
			Counter,
		rcvFramesTaggedDE
			Counter,
		rcvBytesTaggedDE
			Counter,
		rcvKbpsAIR
			INTEGER,
-- Xmt Counters
		xmtFrames		
			Counter,
		xmtBytes	
			Counter,
		xmtFramesFECN
			Counter,
		xmtFramesBECN
			Counter,
		xmtFramesDE		
			Counter,
		xmtBytesDE		
			Counter,
		xmtFramesDiscard	
			Counter,
		xmtBytesDiscard	
			Counter,
		xmtFramesDiscXceedQDepth
			Counter,
		xmtBytesDiscXceedQDepth
			Counter,
		xmtFramesDiscXceedDEThresh
			Counter,
		xmtFramesDiscPhyLayerFail
			Counter,
		xmtFramesDiscCRCError
			Counter,
		xmtFramesDiscReassmFail
			Counter,
		xmtFramesDiscSrcAbort
			Counter,
		xmtFramesDuringLMIAlarm
			Counter,
		xmtBytesDuringLMIAlarm
			Counter,
		xmtFramesTaggedFECN
			Counter,
		xmtFramesTaggedBECN
			Counter,
		xmtKbpsAIR
			INTEGER,
		chanClrButton
         INTEGER,
      chanSecUpTime
         Counter,
      rcvFramesDiscUPC
         Counter,
      xmtBytesTaggedDE
         Counter,
      xmtFramesTaggedDE
         Counter,
      xmtFramesInvalidCPIs
         Counter,
      xmtFramesLengthViolations
         Counter,
      xmtFramesOversizedSDUs
         Counter,
      xmtFramesUnknownProtocols
         Counter,
      rcvFramesUnknownProtocols
			Counter
}

cntChanNum OBJECT-TYPE
	SYNTAX	INTEGER
	ACCESS	read-only
	STATUS	mandatory
	DESCRIPTION		  
		"Refers to the virtual connection index
		 Note that the actual range of the index
		 supported by a card depends on the type of card.
		 eg: FRSM-4T1/E1 supports a range from 16..271 (256 entries)
		     FRSM-8T1/E1 supports a range from 16..1015 (1000 entries)
		     FRSM-T3/E3/HS2 supports a range from 16..2015 (2000 entries)
		     FRSM-2CT3 supports a range from 16..4015 (4000 entries)
		     FRSM12 supports a range from 16..16015 (16000 entries)
		     For FRSM12 Card: Byte 3 = Chassis Number, Byte 2 = Slot Number,
		     Byte 1 & 0 = channel Number
		"
	::= { frChanCntGrpEntry 1}

rcvFrames OBJECT-TYPE
	SYNTAX	Counter
	ACCESS	read-only
	STATUS	mandatory
	DESCRIPTION		  
		"The number of frames Received on the ingress
		"
	::= { frChanCntGrpEntry	2 }

rcvBytes OBJECT-TYPE
	SYNTAX	Counter
	ACCESS	read-only
	STATUS	mandatory
	DESCRIPTION		  
		"The number of bytes Received on the ingress
		"
	::= { frChanCntGrpEntry	3 }

rcvFramesDE OBJECT-TYPE
	SYNTAX	Counter
	ACCESS	read-only
	STATUS	mandatory
	DESCRIPTION		  
		"The number of DE frames Received on the ingress
		"
	::= { frChanCntGrpEntry	4 }

rcvBytesDE OBJECT-TYPE
	SYNTAX	Counter
	ACCESS	read-only
	STATUS	mandatory
	DESCRIPTION		  
		"The number of DE bytes Received on the ingress
		"
	::= { frChanCntGrpEntry	5 }

rcvFramesDiscard OBJECT-TYPE
	SYNTAX	Counter
	ACCESS	read-only
	STATUS	mandatory
	DESCRIPTION		  
		"The number of frames discarded on the ingress
		"
	::= { frChanCntGrpEntry	6 }

rcvBytesDiscard OBJECT-TYPE
	SYNTAX	Counter
	ACCESS	read-only
	STATUS	mandatory
	DESCRIPTION		  
		"The number of bytes discarded on the ingress
		"
	::= { frChanCntGrpEntry	7 }

rcvFramesDiscShelfAlarm OBJECT-TYPE
	SYNTAX	Counter
	ACCESS	read-only
	STATUS	mandatory
	DESCRIPTION		  
		"The number of frames discarded on the ingress
		 due to shelf alarm

		 For FRSM12 Card: Not Supported
		"
	::= { frChanCntGrpEntry	8 }

rcvFramesDiscXceedQDepth OBJECT-TYPE
	SYNTAX	Counter
	ACCESS	read-only
	STATUS	mandatory
	DESCRIPTION		  
		"The number of frames discarded on the ingress
		 due to exceeded queue depth
		"
	::= { frChanCntGrpEntry	9 }

rcvBytesDiscXceedQDepth OBJECT-TYPE
	SYNTAX	Counter
	ACCESS	read-only
	STATUS	mandatory
	DESCRIPTION		  
		"The number of bytes discarded on the ingress
		 due to exceeded queue depth
		"
	::= { frChanCntGrpEntry	10 }

rcvFramesDiscXceedDEThresh OBJECT-TYPE
	SYNTAX	Counter
	ACCESS	read-only
	STATUS	mandatory
	DESCRIPTION		  
		"The number of frames discarded on the ingress
		 due to exceeded DE Threshold
		"
	::= { frChanCntGrpEntry	11 }

rcvFramesFECN OBJECT-TYPE
	SYNTAX	Counter
	ACCESS	read-only
	STATUS	mandatory
	DESCRIPTION		  
		"The number of frames received with
		 FECN bit already set
		"
	::= { frChanCntGrpEntry	12 }

rcvFramesBECN OBJECT-TYPE
	SYNTAX	Counter
	ACCESS	read-only
	STATUS	mandatory
	DESCRIPTION		  
		"The number of frames received with
		 BECN bit already set
		"
	::= { frChanCntGrpEntry	13 }

rcvFramesTaggedFECN OBJECT-TYPE
	SYNTAX	Counter
	ACCESS	read-only
	STATUS	mandatory
	DESCRIPTION		  
		"The number of frames received that were
		 tagged with FECN bit
		"
	::= { frChanCntGrpEntry	14 }

rcvFramesTaggedBECN OBJECT-TYPE
	SYNTAX	Counter
	ACCESS	read-only
	STATUS	mandatory
	DESCRIPTION		  
		"The number of frames received that were
		 tagged with BECN bit
		"
	::= { frChanCntGrpEntry	15 }

rcvFramesTaggedDE OBJECT-TYPE
	SYNTAX	Counter
	ACCESS	read-only
	STATUS	mandatory
	DESCRIPTION		  
		"The number of frames received that were
		 tagged with DE bit
		"
	::= { frChanCntGrpEntry	16 }

rcvBytesTaggedDE OBJECT-TYPE
	SYNTAX	Counter
	ACCESS	read-only
	STATUS	mandatory
	DESCRIPTION		  
		"The number of bytes received that were
		 tagged with DE bit
		"
	::= { frChanCntGrpEntry	17 }


rcvKbpsAIR OBJECT-TYPE
	SYNTAX	INTEGER
	ACCESS	read-only
	STATUS	mandatory
	DESCRIPTION		  
		"Received Average Information Rate in KBPS
		"
	::= { frChanCntGrpEntry	18 }

xmtFrames OBJECT-TYPE
	SYNTAX	Counter
	ACCESS	read-only
	STATUS	mandatory
	DESCRIPTION		  
		"The number of frames transmitted
		"
	::= { frChanCntGrpEntry	19 }

xmtBytes OBJECT-TYPE
	SYNTAX	Counter
	ACCESS	read-only
	STATUS	mandatory
	DESCRIPTION		  
		"The number of bytes transmitted
		"
	::= { frChanCntGrpEntry	20 }

xmtFramesFECN OBJECT-TYPE
	SYNTAX	Counter
	ACCESS	read-only
	STATUS	mandatory
	DESCRIPTION		  
		"The number of frames transmitted with FECN bit already set
		"
	::= { frChanCntGrpEntry	21 }

xmtFramesBECN OBJECT-TYPE
	SYNTAX	Counter
	ACCESS	read-only
	STATUS	mandatory
	DESCRIPTION		  
		"The number of frames transmitted with BECN bit already set
		"
	::= { frChanCntGrpEntry	22 }

xmtFramesDE OBJECT-TYPE
	SYNTAX	Counter
	ACCESS	read-only
	STATUS	mandatory
	DESCRIPTION		  
		"The number of DE frames transmitted
		"
	::= { frChanCntGrpEntry	23 }

xmtBytesDE OBJECT-TYPE
	SYNTAX	Counter
	ACCESS	read-only
	STATUS	mandatory
	DESCRIPTION		  
		"The number of DE bytes transmitted
		"
	::= { frChanCntGrpEntry	24 }

xmtFramesDiscard OBJECT-TYPE
	SYNTAX	Counter
	ACCESS	read-only
	STATUS	mandatory
	DESCRIPTION		  
		"The number of frames discarded on the eggress
		"
	::= { frChanCntGrpEntry	25 }

xmtBytesDiscard OBJECT-TYPE
	SYNTAX	Counter
	ACCESS	read-only
	STATUS	mandatory
	DESCRIPTION		  
		"The number of bytes discarded on the egress

		For FRSM12 Card: Not Supported
		"
	::= { frChanCntGrpEntry	26 }

xmtFramesDiscXceedQDepth OBJECT-TYPE
	SYNTAX	Counter
	ACCESS	read-only
	STATUS	mandatory
	DESCRIPTION		  
		"The number of frames discarded on the egress
		 due to exceeded queue depth

		For FRSM12 Card: Not Supported
		"
	::= { frChanCntGrpEntry	27 }

xmtBytesDiscXceedQDepth OBJECT-TYPE
	SYNTAX	Counter
	ACCESS	read-only
	STATUS	mandatory
	DESCRIPTION		  
		"The number of bytes discarded on the egress
		 due to exceeded queue depth

		For FRSM12 Card: Not Supported
		"
	::= { frChanCntGrpEntry	28 }

xmtFramesDiscXceedDEThresh OBJECT-TYPE
	SYNTAX	Counter
	ACCESS	read-only
	STATUS	mandatory
	DESCRIPTION		  
		"The number of frames discarded on the egress
		 due to exceeded DE Threshold

		For FRSM12 Card: Not Supported
		"
	::= { frChanCntGrpEntry	29 }

xmtFramesDiscPhyLayerFail OBJECT-TYPE
	SYNTAX	Counter
	ACCESS	read-only
	STATUS	mandatory
	DESCRIPTION		  
		"The number of frames discarded on the egress
		 due to physical layer failure
		"
	::= { frChanCntGrpEntry	30 }

xmtFramesDiscCRCError OBJECT-TYPE
	SYNTAX	Counter
	ACCESS	read-only
	STATUS	mandatory
	DESCRIPTION		  
		"The number of frames discarded on the egress
		 due to CRC Error
		"
	::= { frChanCntGrpEntry	31 }

xmtFramesDiscReassmFail OBJECT-TYPE
	SYNTAX	Counter
	ACCESS	read-only
	STATUS	mandatory
	DESCRIPTION		  
		"The number of frames discarded on the egress
		 due to reassembly failure

		For FRSM12 Card: Not Supported
		"
	::= { frChanCntGrpEntry	32 }

xmtFramesDiscSrcAbort OBJECT-TYPE
	SYNTAX	Counter
	ACCESS	read-only
	STATUS	mandatory
	DESCRIPTION		  
		"The number of frames discarded on the egress
		 due to source abort
		"
	::= { frChanCntGrpEntry	33 }

xmtFramesDuringLMIAlarm OBJECT-TYPE
	SYNTAX	Counter
	ACCESS	read-only
	STATUS	mandatory
	DESCRIPTION		  
		"The number of frames transmitted during
		 LMI logical port alarm
		"
	::= { frChanCntGrpEntry	34 }

xmtBytesDuringLMIAlarm OBJECT-TYPE
	SYNTAX	Counter
	ACCESS	read-only
	STATUS	mandatory
	DESCRIPTION		  
		"The number of bytes transmitted during
		 LMI logical port alarm
		"
	::= { frChanCntGrpEntry	35 }

xmtFramesTaggedFECN OBJECT-TYPE
	SYNTAX	Counter
	ACCESS	read-only
	STATUS	mandatory
	DESCRIPTION		  
		"The number of frames transmitted that were
		 tagged with FECN bit
		"
	::= { frChanCntGrpEntry	36 }

xmtFramesTaggedBECN OBJECT-TYPE
	SYNTAX	Counter
	ACCESS	read-only
	STATUS	mandatory
	DESCRIPTION		  
		"The number of frames transmitted that were
		 tagged with BECN bit
		"
	::= { frChanCntGrpEntry	37 }

xmtKbpsAIR OBJECT-TYPE
	SYNTAX	INTEGER
	ACCESS	read-only
	STATUS	mandatory
	DESCRIPTION		  
		"Transmitted Average Information Rate in KBPS
		"
	::= { frChanCntGrpEntry	38 }

chanClrButton OBJECT-TYPE
	SYNTAX	INTEGER {
               noaction (1),
               clear (2)
        }
	ACCESS	read-write
	STATUS	mandatory
	DESCRIPTION		  
		"Channel clear button. Clears Channel Counters.
		"
	::= { frChanCntGrpEntry 39 }

 
xmtFramesTaggedDE OBJECT-TYPE
   SYNTAX   Counter
   ACCESS   read-only
   STATUS   mandatory
   DESCRIPTION
      "The number of frames transmitted which have been DE tagged
       at the far end ingress in excess of CIR
      "
   ::= { frChanCntGrpEntry 40 }
 
xmtBytesTaggedDE OBJECT-TYPE
   SYNTAX   Counter
   ACCESS   read-only
   STATUS   mandatory
   DESCRIPTION
      "The number of bytes transmitted which have been DE tagged
       at the far end ingress in excess of CIR
      "
   ::= { frChanCntGrpEntry 41 }
 
rcvFramesDiscUPC OBJECT-TYPE
   SYNTAX   Counter
   ACCESS   read-only
   STATUS   mandatory
   DESCRIPTION
      "The number of frames discarded at ingress
       due to the UPC measurement in excess of CIR+EIR
      "
   ::= { frChanCntGrpEntry 42 }
 
chanSecUpTime OBJECT-TYPE
   SYNTAX   Counter
   ACCESS   read-only
   STATUS   mandatory
   DESCRIPTION
      "The time in seconds the PVC stay in service
      "
   ::= { frChanCntGrpEntry 43 }
 

xmtFramesInvalidCPIs OBJECT-TYPE
   SYNTAX   Counter
   ACCESS   read-only
   STATUS   mandatory
   DESCRIPTION   
      "Number of frames transmitted with invalid CPI header.
       currently valid is 0
      "
   ::= { frChanCntGrpEntry 44 }
 
xmtFramesLengthViolations OBJECT-TYPE
   SYNTAX   Counter
   ACCESS   read-only
   STATUS   mandatory
   DESCRIPTION
      "The number of frames discarded due to violation of length in
       the egress direction.
      "
   ::= { frChanCntGrpEntry 45 }
 
xmtFramesOversizedSDUs OBJECT-TYPE
   SYNTAX   Counter
   ACCESS   read-only
   STATUS   mandatory
   DESCRIPTION
      "The number of frames discarded because the size is beyond 
       the max in the egress direction
      "
   ::= { frChanCntGrpEntry 46 }
 
xmtFramesUnknownProtocols OBJECT-TYPE
   SYNTAX   Counter
   ACCESS   read-only
   STATUS   mandatory
   DESCRIPTION
      "The number of frames discarded for Unknown protocol in
       the egress direction. Used only in SIW for PDUs that
       are dropped.
      "
   ::= { frChanCntGrpEntry 47 }
 
rcvFramesUnknownProtocols OBJECT-TYPE
   SYNTAX   Counter
   ACCESS   read-only
   STATUS   mandatory
   DESCRIPTION
      "Number of frames discarded for Unknown protocol in the 
       ingress direction. Used only in SIW for PDUs that 
       are dropped
      "
   ::= { frChanCntGrpEntry 48 }



--
-- ----------------------------------------------------------------------
-- BASIS Project MIB
-- 
--





-- frChan     	OBJECT IDENTIFIER ::= { frameRelay 2 }
frChanStateGrp 	OBJECT IDENTIFIER ::= { frChan 2 }

-- ------------------------------------------------------------------------
--
-- Group frChannelState
-- Contains status information for channels
--
-- ------------------------------------------------------------------------


frChanStateGrpTable OBJECT-TYPE
	SYNTAX  SEQUENCE OF FrChanStateGrpEntry
	ACCESS  not-accessible
	STATUS  mandatory
	DESCRIPTION
		"Table of transmit/receive states of channels.
		"
	::= { frChanStateGrp 1 }

frChanStateGrpEntry OBJECT-TYPE
	SYNTAX FrChanStateGrpEntry
	ACCESS not-accessible
	STATUS mandatory
	DESCRIPTION
		"An entry for FrChannelStateGrpEntry.
		"
	INDEX	{ stateChanNum }
	::= { frChanStateGrpTable 1 }

FrChanStateGrpEntry ::=
	SEQUENCE {
		stateChanNum
         		INTEGER,
		chanState
         		INTEGER,
		xmtAbitState
			INTEGER,
		rcvAbitState
			INTEGER,
		xmtATMState
			INTEGER,
		rcvATMState
			INTEGER,
		chanStatusBitMap
            INTEGER
		}

stateChanNum OBJECT-TYPE
	SYNTAX	INTEGER
	ACCESS	read-only
	STATUS	mandatory
	DESCRIPTION		  
		"Refers to the virtual connection index
		 Note that the actual range of the index
		 supported by a card depends on the type of card.
		 eg: FRSM-4T1/E1 supports a range from 16..271 (256 entries)
		     FRSM-8T1/E1 supports a range from 16..1015 (1000 entries)
		     FRSM-T3/E3/HS2 supports a range from 16..2015 (2000 entries)
		     FRSM-2CT3 supports a range from 16..4015 (4000 entries)
		     For FRSM12 Card:
		     Byte 3 = Chassis Number, Byte 2 = Slot Number,
		     Byte 1 & 0 = channel Number.
		     Lower two bytes range from 16..16015 (16000 entries)
		"
	::= { frChanStateGrpEntry 1}

chanState OBJECT-TYPE
	SYNTAX  INTEGER {
		notConfigured(1),
		okay(2),
		alarm(3),
        failed(4)
	}
	ACCESS  read-only
	STATUS  mandatory
	DESCRIPTION
		"This variable indicates the LMI state of the
		 VC (channel)
         failed(4) is added to distinguish between alarm (when the connection
         in the PNNI n/w is not actually broken) and failed (when the connection
         in the PNNI n/w is actually broken). This is applicable only to the 
         PNNI environment.
		"
	::= { frChanStateGrpEntry 2}
 
xmtAbitState OBJECT-TYPE
	SYNTAX INTEGER { 
		off(1),
		sendingAequal1(2),
		sendingAequal0(3)
	}
	ACCESS read-only
	STATUS mandatory
	DESCRIPTION
		"The A bit transmit state
		 1 - LMI off 
		 2 - LMI on and connection is O.K. 
		 3 - LMI on and connection has failed 
		"
	::= { frChanStateGrpEntry 3}

rcvAbitState OBJECT-TYPE
	SYNTAX INTEGER {
		off(1),
		rcvingAequal1(2),
		rcvingAequal0(3)
	}
	ACCESS read-only
	STATUS mandatory
	DESCRIPTION
		"The A bit receive state
		 1 - LMI off 
		 2 - LMI on and connection is O.K. 
		 3 - LMI on and connection has failed 
		"
	::= { frChanStateGrpEntry 4}

xmtATMState OBJECT-TYPE
	SYNTAX  INTEGER {
		notSending(1),
		sendingAIS(2),
		sendingFERF(3)
	}
	ACCESS  read-only
	STATUS  mandatory
	DESCRIPTION
		"This variable indicates the transmit state of the
		 VC (channel) on the ATM side
		 1 - Not sending any state 
		 2 - Sending AIS OAM state 
		 3 - Sending FERF OAM state 
		"
	::= { frChanStateGrpEntry 5}
 
rcvATMState OBJECT-TYPE
	SYNTAX  INTEGER {
		notRcving(1),
		rcvingAIS(2),
		rcvingFERF(3)
	}
	ACCESS  read-only
	STATUS  mandatory
	DESCRIPTION
		"This variable indicates the receiving state of the
		 VC (channel) on the ATM side
		 1 - Not receiving any state 
		 2 - Receiving AIS OAM
		 3 - Receiving FERF OAM 
		"
	::= { frChanStateGrpEntry 6}

chanStatusBitMap OBJECT-TYPE
    SYNTAX  INTEGER (0..'ff'h)
    ACCESS  read-only
    STATUS  mandatory
    DESCRIPTION
        "This variable indicates the consolidated bit map of the channel alarm
        state.

        Individual bit positions are as defined below.

        Bit position   Fail/Alarm     Reason
        ------------   ----------     ------
            0           Alarm         Reserved
            1           Alarm         n/w side AIS/RDI Rx
            2           Fail          Conditioned(A bit from n/w)
            3           Alarm         Reserved         
            4           Fail          CC failed/RAS failed
            5           Fail          Mismatch
            6           Alarm         ingress A bit (LMI)
            7           Alarm         Reserved

            Fail bitmap mask : 0x34
            Alarm bitmap mask: 0xCB

            This object is not applicable to MGX Release 1.x.
        "

    ::= { frChanStateGrpEntry 7}


-- ------------------------------------------------------------------------
-- End of frChanState group definitions


--
-- ----------------------------------------------------------------------
-- BASIS Project MIB
-- 
--





frEndPtMapGrp  	OBJECT IDENTIFIER ::= { frameRelay 3 }

-- ------------------------------------------------------------------------
--
-- Group frChannelState
-- Contains status information for channels
--
-- ------------------------------------------------------------------------


frEndPtMapGrpTable OBJECT-TYPE
	SYNTAX  SEQUENCE OF FrEndPtMapGrpEntry
	ACCESS  not-accessible
	STATUS  mandatory
	DESCRIPTION
		"Table of transmit/receive states of channels.
		"
	::= { frEndPtMapGrp 1 }

frEndPtMapGrpEntry OBJECT-TYPE
	SYNTAX FrEndPtMapGrpEntry
	ACCESS not-accessible
	STATUS mandatory
	DESCRIPTION
		"An entry for FrEndPtMapGrpEntry.
		"
	INDEX	{ endPortNum, endDLCI }
	::= { frEndPtMapGrpTable 1 }

FrEndPtMapGrpEntry ::=
	SEQUENCE {
		endPortNum
         		INTEGER,
		endDLCI
         		INTEGER,
		endChanNum
			INTEGER,
		endLineNum
			INTEGER
		}

endPortNum OBJECT-TYPE
	SYNTAX	INTEGER
	ACCESS	read-only
	STATUS	mandatory
	DESCRIPTION		  
		"Refers to the logical port index
		 For FRSM12 card:
		 The ifIndex of the port's corresponding row in ifTable.
		 Byte  3 = Chassis Number, Byte 2 = Slot Number,
		 Byte 1 & 0 = Encoded unique number for Port.
		"
	::= { frEndPtMapGrpEntry 1}

endDLCI OBJECT-TYPE
	SYNTAX  INTEGER (0..8388607)
	ACCESS  read-only
	STATUS  mandatory
	DESCRIPTION
		"Refers to the DLCI index
		"
	::= { frEndPtMapGrpEntry 2}
 
endChanNum OBJECT-TYPE
	SYNTAX INTEGER
	ACCESS read-only
	STATUS mandatory
	DESCRIPTION
		"Logical connection number
		 0 if port.dlci is a multicast group
		 Note that the actual range of endChanNum
		 supported by a card depends on the type of card.
		 eg: FRSM-4T1/E1 supports a range from 16..271 (256 entries)
		     FRSM-8T1/E1 supports a range from 16..1015 (1000 entries)
		     FRSM-T3/E3/HS2 supports a range from 16..2015 (2000 entries)
		     FRSM-2CT3 supports a range from 16..4015 (4000 entries)
		     For FRSM12 Card:
		     Byte 3 = Chassis Number, Byte 2 = Slot Number,
		     Byte 1 & 0 = channel Number.
		     Lower two bytes range from 16..16015 (16000 entries)
		"
	::= { frEndPtMapGrpEntry 3}

endLineNum OBJECT-TYPE
	SYNTAX INTEGER
	ACCESS read-only
	STATUS mandatory
	DESCRIPTION
		"Refers to the physical line index.
		 Note that the actual range of endLineNum
		 supported by a card depends on the type of card.
		 eg: FRSM-4T1/E1 supports a range from 1..4 (4 entries)
		     FRSM-8T1/E1 supports a range from 1..8 (8 entries)
		     FRSM-T3/E3/HS2 supports a range from 1..2 (2 entries)
		     FRSM-2CT3 supports a range from 1..56 (56 entries)
		     For FRSM12 Card:
		     The ifIndex of the physical line on which this channel
		     is provisioned.
		"
	::= { frEndPtMapGrpEntry 4}


-- ------------------------------------------------------------------------
-- End of frEndPtMap group definitions




-- frPort        		OBJECT IDENTIFIER ::= { frameRelay 1 }
-- frPortCnf		OBJECT IDENTIFIER ::= { frPort 1 }
frPortCnfPortGrp  	OBJECT IDENTIFIER ::= { frPortCnf 1 }

-- --------------------------------------------------------------------
--
--
--		LOGICAL PORT CONFIG Group
--
--
-- --------------------------------------------------------------------


frPortCnfPortGrpTable	OBJECT-TYPE
	SYNTAX	SEQUENCE OF FrPortCnfPortGrpEntry
	ACCESS	not-accessible
	STATUS	mandatory
	DESCRIPTION
		"The config table is for logical port interface.
		 In FRSM-VHS, there are upto 256 entries for FRSM-2CT3
		 card and 2 entries for FRSM-T3/E3/HS2/T3B/E3B/HS2B-HSSI 
		 cards and 8 entries for FRSM-HS2B-12IN1 card.
		 For other cards, there are upto 192 entries (for 8 DS1s)
		 and upto 248 entries (for 8 E1s).
		 For FRSM12 cards:
		 There are upto 12 entries.  When a new row is added to this
		 table, the corresponding row is created in ifTable.
		"
	::= { frPortCnfPortGrp 1 }


frPortCnfPortGrpEntry	OBJECT-TYPE
	SYNTAX	FrPortCnfPortGrpEntry
	ACCESS	not-accessible
	STATUS	mandatory
	DESCRIPTION
		" An entry for logical port
		"
	INDEX	{ portNum }
    ::= { frPortCnfPortGrpTable 1 }

FrPortCnfPortGrpEntry ::=
	SEQUENCE {
		portNum 	
			INTEGER,
		portLineNum 	
			INTEGER,
      	portRowStatus
         	INTEGER,
		portDs0ConfigBitMap	 	
			INTEGER,
      	portDs0Speed
         	INTEGER,
      	portFlagsBetweenFrames
         	INTEGER,
      	portEqueueServiceRatio
         	INTEGER,
        portSpeed
            INTEGER,
        portAdmin
            INTEGER,
        portType
            INTEGER,
        portSvcStatus
            INTEGER,
        portSvcInUse
            INTEGER,
        portSvcShareLcn
            INTEGER,
        portSvcLcnLow
            INTEGER,
        portSvcLcnHigh
            INTEGER,
        portSvcDlciLow
            INTEGER,
        portSvcDlciHigh
            INTEGER,
	    portDeleteSvcs
	       INTEGER,
	    portIngrSvcBandW
	       INTEGER,
	    portEgrSvcBandW
	       INTEGER,
		portBERTEnable
			INTEGER,
--FRSM_VHS This new entry (portEnhancedSIW) is added for FRSM_VHS.
			portEnhancedSIW
			INTEGER,
			portM32EgrQueueThresh
			   INTEGER,
			--These entries are added for FRSM12
			portHeaderLen
			   INTEGER,
			portFrameChkSumType
			   INTEGER,
			portFileId
			   INTEGER,
			portOverSubEnable
			   INTEGER
		}

portNum	OBJECT-TYPE
	SYNTAX	INTEGER
	ACCESS	read-only
	STATUS	mandatory
	DESCRIPTION
		"This is logical port number.
		 If we have T1 card then the maximum port number is 192
		 and if we have E1 card the maximum port number can be 248.
		 For FRSM-2CT3 card, the maximum port number is 256 and
		 for unchannelized FRSM-VHS cards (FRSM-T3/E3/HS2/T3B/E3B/HS2B-HSSI),
		 the maximum port number is 2
		 For FRSM-HS2B-12IN1 card, the maximum port number is 8
		 For FRSM12 card:
		 The ifIndex of the port's corresponding row in ifTable.
		 Byte  3 = Chassis Number, Byte 2 = Slot Number,
		 Byte 1 & 0 = Encoded unique number for Port.
		"
	::= { frPortCnfPortGrpEntry 1}

portLineNum	OBJECT-TYPE
	SYNTAX	INTEGER
	ACCESS	read-write
	STATUS	mandatory
	DESCRIPTION
		"This represents the line number
		 For FRSM12 card:
		 The ifIndex of the physical line on which this port
		 is provisioned.
		"
	::= { frPortCnfPortGrpEntry 2}

portRowStatus  OBJECT-TYPE		
	SYNTAX	INTEGER {
		add(1),
		del(2),
		mod(3)
		}
	ACCESS read-write
        STATUS  mandatory
        DESCRIPTION
        "This variable enables or modifies the port
		1- add
		2 - del
		3 - mod
		 For FRSM12 card:
		 For Snmp GET operations, only mod is returned.
        "
        ::= { frPortCnfPortGrpEntry 3 }

portDs0ConfigBitMap	OBJECT-TYPE
	SYNTAX	INTEGER (0..'ffffff'h) 
	ACCESS	read-write
	STATUS	mandatory
	DESCRIPTION
		"This respesents bit map of DS0s for a line which
		 are used to form this logical port. Bit 0
		 represents DS0-1.
		 This entry is not used for unchannelized FRSM-VHS/FRSM12 cards.
		 For these cases, this field carries a value of 'ffffff'h
		 always.
		"
	::= { frPortCnfPortGrpEntry 4 }

portDs0Speed	OBJECT-TYPE
	SYNTAX	INTEGER {
            speed56k(1),
            speed64k(2),
			unUsed(3)
            }
	ACCESS	read-write
	STATUS	mandatory
	DESCRIPTION
		"This represents port speed of 64 or 56
            	 1 - speed56k
            	 2 - speed64k
				 3 - unUsed.
		 This field is not used for unchannelised FRSM-VHS (FRSM-2T3/
		 FRSM-2E3/FRSM-HS2/FRSM-T3B/FRSM-E3B/FRSM-HS2B) cards; in such 
		 cards, the portDs0Speed field carries a value of 'unUsed' always.
		 For FRSM12 card:
		 This is set to 3 - unUsed.
		"
	DEFVAL { speed64k }
	::= { frPortCnfPortGrpEntry 5 }

portFlagsBetweenFrames	OBJECT-TYPE
	SYNTAX	INTEGER (1..10) 
	ACCESS	read-write
	STATUS	mandatory
	DESCRIPTION
		"Number of flags transmitted between FR frames
		 For FRSM12 card:
		 Only the values 1 to 8 are supported. The mapping is as follows:
		   MIB object value      No. of HDLC flags inserted
		          1                        1
		          2                        2
		          3                        4
		          4                        8
		          5                       16
		          6                       32
		          7                       64
		          8                      128
		"
	DEFVAL { 1 }
	::= { frPortCnfPortGrpEntry 6 }

portEqueueServiceRatio	OBJECT-TYPE
	SYNTAX	INTEGER (0..15) 
	ACCESS	read-write
	STATUS	mandatory
	DESCRIPTION
		"Number of times queue 1 is serviced 
		 for every time queue 2 is serviced.
		 The value 0 is supported only by FRSM-VHS.
		
		 FRSM-VHS supports two different egress queue
         servicing algorithms depending on the Egress
         Qos Feature.

         if EgrQosFeature is ENABLED, Weighted Fair
         queueing algorithm will be used to select
         one queue out of 4 data queues and this
         object will be set to a default value of
         0 in this case and this value cannot be
         modified by user.

         In case of EgrQosFeature being DISABLED,
         this object will be set to a default value
         of 1 and can be configured to user desired
         value. This value will be used to decide
         number of times High priority queue has
         to be serviced for every time low priority
         queue is serviced.
         For FRSM12 card:
         There is only one scheme of egress scheduling of COS queues
         within ports, which uses only two COS queues for user data.
         The scheduling scheme uses a pre-defined ratio to schedule
         these COS queues on a given port. This object will be
         used to decide number of times High priority queue
         has to be serviced for every time low priority queue
         is serviced.
        "

	DEFVAL { 1 }
	::= { frPortCnfPortGrpEntry 7 }

portSpeed       OBJECT-TYPE
        SYNTAX  INTEGER
    ACCESS      read-only
        STATUS  mandatory
        DESCRIPTION
                "Configured speed of port in kbps
                "
        ::= { frPortCnfPortGrpEntry 8 }

portAdmin       OBJECT-TYPE
        SYNTAX  INTEGER {
                 up(1),
                 down(2),
                 write-Only(3)
                }
        ACCESS read-write
        STATUS  mandatory
        DESCRIPTION
                " used to up and down the port 
                 For FRSM12 card:
                 This variable will be equivalent to ifAdminStatus of
                 of ifTable.  The write-only is not used.
                "
        ::= { frPortCnfPortGrpEntry 9 }

portType	OBJECT-TYPE
	SYNTAX	INTEGER {
            frame-relay(1),
            frFUNI(2),
	    frame-forward(3)
            }
	ACCESS	read-write
	STATUS	mandatory
	DESCRIPTION
		"This represents port type
		 For FRSM12 card:
		 frFUNI not Applicable. For frame-relay the ifType is
		 frameRelayService(44) and for frame-forward it is
		 frForward(158).
		"
	DEFVAL { frame-relay }
	::= { frPortCnfPortGrpEntry 10 }



portSvcStatus	OBJECT-TYPE
	SYNTAX	INTEGER {
            disable(1),
            enable(2)
            }
	ACCESS	read-write
	STATUS	mandatory
	DESCRIPTION
		"This represents SVC status

		 For FRSM12 card: Not Supported
		"
	::= { frPortCnfPortGrpEntry 11 }

portSvcInUse	OBJECT-TYPE
	SYNTAX	INTEGER {
            not-use(1),
            in-use(2)
            }
	ACCESS	read-write
	STATUS	mandatory
	DESCRIPTION
		"This represents port svc in use

		 For FRSM12 card: Not Supported
		"
	::= { frPortCnfPortGrpEntry 12 }

portSvcShareLcn	OBJECT-TYPE
	SYNTAX	INTEGER {
            port-based(1),
            card-based(2)
            }
	ACCESS	read-only
	STATUS	mandatory
	DESCRIPTION
		"This represents port type

		 For FRSM12 card: Not Supported
		"
	::= { frPortCnfPortGrpEntry 13 }

portSvcLcnLow	OBJECT-TYPE
	SYNTAX	INTEGER (16..4015)
	ACCESS	read-only
	STATUS	mandatory
	DESCRIPTION
		"This represents low end of reserved LCN for svc

		 For FRSM12 card: Not Supported
		"
	::= { frPortCnfPortGrpEntry 14 }

portSvcLcnHigh	OBJECT-TYPE
	SYNTAX	INTEGER (16..4015)
	ACCESS	read-only
	STATUS	mandatory
	DESCRIPTION
		"This represents high end of reserved LCN for svc

		 For FRSM12 card: Not Supported
		"
	::= { frPortCnfPortGrpEntry 15 }

portSvcDlciLow	OBJECT-TYPE
	SYNTAX	INTEGER (0..1023)
	ACCESS	read-only
	STATUS	mandatory
	DESCRIPTION
		"This represents low end of reserved DLCI for svc

		 For FRSM12 card: Not Supported
		"
	::= { frPortCnfPortGrpEntry 16 }

portSvcDlciHigh	OBJECT-TYPE
	SYNTAX	INTEGER (0..1023)
	ACCESS	read-only
	STATUS	mandatory
	DESCRIPTION
		"This represents high end of reserved DLCI for svc

		 For FRSM12 card: Not Supported
		"
	::= { frPortCnfPortGrpEntry 17 }


portDeleteSvcs OBJECT-TYPE		
	SYNTAX	INTEGER {
		delete(1),
		other(2)
		}
	ACCESS  read-write
        STATUS  mandatory
        DESCRIPTION
		"Setting this object to 1 indicates that all the SVC
		 connections on the given port has to be deleted

		 For FRSM12 card: Not Supported
		"
	::= { frPortCnfPortGrpEntry 18 }

portIngrSvcBandW	OBJECT-TYPE
	SYNTAX	INTEGER
	ACCESS	read-only
	STATUS	mandatory
	DESCRIPTION
		"This represents Ingress Bandwidth reserve for SVC

		 For FRSM12 card: Not Supported
		"
	::= { frPortCnfPortGrpEntry 19 }

portEgrSvcBandW	OBJECT-TYPE
	SYNTAX	INTEGER
	ACCESS	read-only
	STATUS	mandatory
	DESCRIPTION
		"This represents Egress Bandwidth reserve for SVC

		 For FRSM12 card: Not Supported
		"
	::= { frPortCnfPortGrpEntry 20 }

portBERTEnable OBJECT-TYPE
	SYNTAX	INTEGER {
			disable(1),
			enable(2)
			}
	ACCESS  read-write
    STATUS  mandatory
    DESCRIPTION
		"This variable enables BERT

		 For FRSM12 card: Not Supported
		" 
	DEFVAL { disable }
	::= { frPortCnfPortGrpEntry 21 }

portEnhancedSIW OBJECT-TYPE
	SYNTAX	INTEGER {
			disable(1),
			enable(2)
			}
	ACCESS  read-write
    STATUS  mandatory
    DESCRIPTION
		"This variable enables/disables enhanced SIW feature. Enabling
		 this permits support for SIW translation of Appletalk. This
		 feature is currently supported only in the FRSM-VHS card.

		 For FRSM12 card: Not Supported
		 This object is not required in FRSM12 since Appletalk is
		 supported by default in FRF.8.1 and FRSM12 supports FRF.8.1
		" 
    DEFVAL {disable}
	::= { frPortCnfPortGrpEntry 22 }

portM32EgrQueueThresh OBJECT-TYPE
    SYNTAX  INTEGER (1..6000)
    ACCESS  read-write
    STATUS  mandatory
    DESCRIPTION
        "This represents the M32 logical port Egress Queue threshold in bytes.
         Frames will not be queued until the number of bytes in the queue is
         less than the threshold. The default value is 6000. Using a very low
         value could under utilize the logical port.
         This is supported in FRSM 8t1e1 and FRSM 4t1e1 Service Modules only.

         For FRSM12 card: Not Supported
        "
    DEFVAL { 6000 }
    ::= { frPortCnfPortGrpEntry 23 }

portHeaderLen OBJECT-TYPE 
    SYNTAX  INTEGER { 
        twoOctets(1), 
        fourOctets(2) 
            } 
    ACCESS  read-write 
    STATUS  mandatory 
    DESCRIPTION 
            "
             This object is added for FRSM12.

             The value of this object identifies the Q.922 
             Address field length and DLCI length for this 
             UNI/NNI logical port. 

			This object is not applicable to MGX Release 1.x.
            " 
	DEFVAL { twoOctets }
    ::= { frPortCnfPortGrpEntry 24 } 

portFrameChkSumType  OBJECT-TYPE 
    SYNTAX  INTEGER { 
        crc16(1), 
        crc32(2) 
            } 
    ACCESS  read-write 
    STATUS  mandatory 
    DESCRIPTION 
            "
             This object is added for FRSM12.

             The value of this object identifies the CRC Length
             in the HDLC Packet. Applicable for FrameForwarding
             ports only.

            This object is not applicable to MGX Release 1.x.
            " 
	DEFVAL { crc16 }
    ::= { frPortCnfPortGrpEntry 25 } 


portFileId OBJECT-TYPE
    SYNTAX  INTEGER 
    ACCESS  read-write
    STATUS  mandatory
    DESCRIPTION
        "The ID of the SCT file that holds module specific configuration
         parameters for this FR virtual interface.
 
         This object is not applicable to MGX Release 1.x."
        DEFVAL { 0 }
    ::= { frPortCnfPortGrpEntry 26 }


portOverSubEnable OBJECT-TYPE
    SYNTAX  INTEGER { 
        enable(1), 
        disable(2) 
            } 
    ACCESS  read-write 
    STATUS  mandatory 
    DESCRIPTION 
            "
             This object is added for FRSM12.

             When this object is enabled the port will be allowed
             to be over subscribed. 
 
             This object is not applicable to MGX Release 1.x.
            " 
	DEFVAL { disable }
    ::= { frPortCnfPortGrpEntry 27 } 



--	PORT usage scalars
--  These scalars are not used in FRSM-VHS and FRSM12

portsUsedLine1 	OBJECT-TYPE
	SYNTAX	INTEGER (0..'ffffff'h) 
	ACCESS	read-only
	STATUS	mandatory
	DESCRIPTION
		"Each bits set represents a DS0 that is used by all the
		 logical ports defined so far for that DS1, the most significant
		 byte is invalid for DS1
		 This is for line 1
		"
	::= { frPortCnfPortGrp 2 }

portsUsedLine2 	OBJECT-TYPE
	SYNTAX	INTEGER (0..'ffffff'h) 
	ACCESS	read-only
	STATUS	mandatory
	DESCRIPTION
		"Each bits set represents a DS0 that is used by all the
		 logical ports defined so far for that DS1, the most significant
		 byte is invalid for DS1
		 This is for line 2
		"
	::= { frPortCnfPortGrp 3 }

portsUsedLine3 	OBJECT-TYPE
	SYNTAX	INTEGER (0..'ffffff'h) 
	ACCESS	read-only
	STATUS	mandatory
	DESCRIPTION
		"Each bits set represents a DS0 that is used by all the
		 logical ports defined so far for that DS1, the most significant
		 byte is invalid for DS1
		 This is for line 3
		"
	::= { frPortCnfPortGrp 4 }

portsUsedLine4 	OBJECT-TYPE
	SYNTAX	INTEGER (0..'ffffff'h) 
	ACCESS	read-only
	STATUS	mandatory
	DESCRIPTION
		"Each bits set represents a DS0 that is used by all the
		 logical ports defined so far for that DS1, the most significant
		 byte is invalid for DS1
		 This is for line 4
		"
	::= { frPortCnfPortGrp 5 }

portsUsedLine5 	OBJECT-TYPE
	SYNTAX	INTEGER (0..'ffffff'h) 
	ACCESS	read-only
	STATUS	mandatory
	DESCRIPTION
		"Each bits set represents a DS0 that is used by all the
		 logical ports defined so far for that DS1, the most significant
		 byte is invalid for DS1
		 This is for line 5
		"
	::= { frPortCnfPortGrp 7 }

portsUsedLine6 	OBJECT-TYPE
	SYNTAX	INTEGER (0..'ffffff'h) 
	ACCESS	read-only
	STATUS	mandatory
	DESCRIPTION
		"Each bits set represents a DS0 that is used by all the
		 logical ports defined so far for that DS1, the most significant
		 byte is invalid for DS1
		 This is for line 6
		"
	::= { frPortCnfPortGrp 8 }

portsUsedLine7 	OBJECT-TYPE
	SYNTAX	INTEGER (0..'ffffff'h) 
	ACCESS	read-only
	STATUS	mandatory
	DESCRIPTION
		"Each bits set represents a DS0 that is used by all the
		 logical ports defined so far for that DS1, the most significant
		 byte is invalid for DS1
		 This is for line 7
		"
	::= { frPortCnfPortGrp 9 }

portsUsedLine8 	OBJECT-TYPE
	SYNTAX	INTEGER (0..'ffffff'h) 
	ACCESS	read-only
	STATUS	mandatory
	DESCRIPTION
		"Each bits set represents a DS0 that is used by all the
		 logical ports defined so far for that DS1, the most significant
		 byte is invalid for DS1
		 This is for line 8
		"
	::= { frPortCnfPortGrp 10 }

--
--	Next available port
--

portNextAvailable 	OBJECT-TYPE
	SYNTAX	INTEGER (0..256) 
	ACCESS	read-only
	STATUS	mandatory
	DESCRIPTION
		"This variable contains the next UNUSED logical port number.
		 This number can be used in channel config table, the 
		 portNextAvailable gets updated if the number gets
		 used to create a logical port.  
		 A '0' indicates that no more ports are available.

		 For FRSM12 Card: Not Supported
		"
	::= { frPortCnfPortGrp 6 }



--
-- This file is specific to FRSM-VHS only at present
-- FRSM_VHS      PORT usage Table
--



frPortsUsedLineGrpTable         OBJECT-TYPE
        SYNTAX  SEQUENCE OF FrPortsUsedLineGrpEntry
        ACCESS  not-accessible
        STATUS  mandatory
        DESCRIPTION
         "Contains a sequence of entries for each DS1 line.
          each entry gives the number of DS0 slots being used
		  added for FRSM_VHS"
        ::= { frPortCnfPortGrp 11 }

frPortsUsedLineGrpEntry         OBJECT-TYPE
        SYNTAX  FrPortsUsedLineGrpEntry
        ACCESS  not-accessible
        STATUS  mandatory
        DESCRIPTION
         "One entry per DS1"
        INDEX   { frPortsUsedLineIndex }
        ::= { frPortsUsedLineGrpTable 1 }

FrPortsUsedLineGrpEntry ::=
        SEQUENCE {
            frPortsUsedLineIndex
                INTEGER,
            frPortsUsedLine
                INTEGER
        }

frPortsUsedLineIndex    OBJECT-TYPE
        SYNTAX  INTEGER(1..56)
        ACCESS  read-only
        STATUS  mandatory
        DESCRIPTION
             "This is the Index to the table containing the portsUsedLine
              for the 56 DS1s"
        ::= { frPortsUsedLineGrpEntry 1 }


frPortsUsedLine   OBJECT-TYPE
        SYNTAX  INTEGER (0..'ffffff'h)
        ACCESS  read-only
        STATUS  mandatory
        DESCRIPTION
        "Each bits set represents a DS0 that is used by all the
         logical ports defined so far for that DS1, the most significant
         byte is invalid for DS1
        "
        ::= { frPortsUsedLineGrpEntry 2 }

--
-- ----------------------------------------------------------------------
-- BASIS Project MIB
-- 
--






-- frPort        		OBJECT IDENTIFIER ::= { frameRelay 1 }
-- frPortCnf		OBJECT IDENTIFIER ::= { frPort 1 }
-- frPortCnfSig  		OBJECT IDENTIFIER ::= { frPortCnf 2 }
frPortCnfSigCLLMGrp   	OBJECT IDENTIFIER ::= { frPortCnfSig 2 }


-- ------------------------------------------------------------------------
--
-- frPortCnfSigCLLM group
-- Port configurable signalling parameters  
--
-- ------------------------------------------------------------------------


frPortCnfSigCLLMGrpTable	OBJECT-TYPE
	SYNTAX	SEQUENCE OF FrPortCnfSigCLLMGrpEntry
	ACCESS	not-accessible
	STATUS	mandatory
	DESCRIPTION
		"The config table is for logical port interface
		"
	::= { frPortCnfSigCLLMGrp 1 }

frPortCnfSigCLLMGrpEntry	OBJECT-TYPE
	SYNTAX	FrPortCnfSigCLLMGrpEntry
	ACCESS	not-accessible
	STATUS	mandatory
	DESCRIPTION
		" An entry for logical port
		"
	INDEX	{ cllmCnfPortNum }
	::= { frPortCnfSigCLLMGrpTable 1 }

FrPortCnfSigCLLMGrpEntry ::=
	SEQUENCE {
	   	cllmCnfPortNum 	              INTEGER,
		cllmEnable                    INTEGER, 
		xmtCLLMStatusTimer            INTEGER, 
		rcvCLLMStatusTimer            INTEGER
		}


cllmCnfPortNum OBJECT-TYPE
	SYNTAX	INTEGER
	ACCESS	read-only
	STATUS	mandatory
	DESCRIPTION		  
		"Refers to the logical port index
		 For FRSM12 card:
		 The ifIndex of the port's corresponding row in ifTable.
		 Byte  3 = Chassis Number, Byte 2 = Slot Number,
		 Byte 1 & 0 = Encoded unique number for Port.
		"
	::= { frPortCnfSigCLLMGrpEntry 1}

cllmEnable OBJECT-TYPE
	SYNTAX	INTEGER {
		disable(1),
		enable(2)
		}
	ACCESS read-write
   	STATUS  mandatory
   	DESCRIPTION
      		"This will enable CLLM
		1 - disabled
		2 - enabled
		CLLM is not applicable for frame forwarding ports
		"
	DEFVAL { disable }
	::= { frPortCnfSigCLLMGrpEntry 2}

xmtCLLMStatusTimer OBJECT-TYPE
	SYNTAX	INTEGER (40..5000)
	ACCESS	read-write
	STATUS	mandatory
	DESCRIPTION		  
		"Interval in milliseconds for CLLM to send CLLM updates 
		 CLLM parameters are not applicable for frame forwarding ports
		"
	DEFVAL { 40 }
	::= { frPortCnfSigCLLMGrpEntry 3}
		      	   
rcvCLLMStatusTimer OBJECT-TYPE
	SYNTAX	INTEGER {
              rcvCLLMTimerValue (1000)
            }
	ACCESS	read-only
	STATUS	mandatory
	DESCRIPTION		  
		"Timeout value for receiving CLLM updates 
		 CLLM parameters are not applicable for frame forwarding ports
		"
	DEFVAL { rcvCLLMTimerValue }
	::= { frPortCnfSigCLLMGrpEntry 4}



-- ------------------------------------------------------------------------
-- End of frPortCnfSigCLLMGrp group definitions


--
-- ----------------------------------------------------------------------
-- BASIS Project MIB
-- 
--






-- frPort        		OBJECT IDENTIFIER ::= { frameRelay 1 }
-- frPortCnf		OBJECT IDENTIFIER ::= { frPort 1 }
-- frPortCnfSig  		OBJECT IDENTIFIER ::= { frPortCnf 2 }
frPortCnfSigLMIGrp   	OBJECT IDENTIFIER ::= { frPortCnfSig 1 }


-- ------------------------------------------------------------------------
--
-- frPortCnfSigLMI group
-- Port configurable signalling parameters  
--
-- ------------------------------------------------------------------------


frPortCnfSigLMIGrpTable	OBJECT-TYPE
	SYNTAX	SEQUENCE OF FrPortCnfSigLMIGrpEntry
	ACCESS	not-accessible
	STATUS	mandatory
	DESCRIPTION
		"The config table is for logical port interface
		 there are upto 248 entries (8 E1s) and 192 entries (8 T1s).
		 In FRSM-VHS, there are a total of 256 entries.
		 In FRSM12, there are 12 entries.
		"
	::= { frPortCnfSigLMIGrp 1 }

frPortCnfSigLMIGrpEntry	OBJECT-TYPE
	SYNTAX	FrPortCnfSigLMIGrpEntry
	ACCESS	not-accessible
	STATUS	mandatory
	DESCRIPTION
		" An entry for logical port
		"
	INDEX	{ lmiCnfPortNum }
	::= { frPortCnfSigLMIGrpTable 1 }

FrPortCnfSigLMIGrpEntry ::=
	SEQUENCE {
	   	lmiCnfPortNum 	              INTEGER,
		signallingProtocolType        INTEGER, 
		asynchronousUpdates           INTEGER, 
		t391LinkIntegrityTimer        INTEGER,
		t392PollingVerificationTimer  INTEGER,
		n391FullStatusPollingCounter  INTEGER,
		n392ErrorThreshold            INTEGER,
		n393MonitoredEventCount       INTEGER,
		enhancedLmi                   INTEGER,
		portFRF1Dot2Support           INTEGER
		}


lmiCnfPortNum OBJECT-TYPE
	SYNTAX	INTEGER
	ACCESS	read-only
	STATUS	mandatory
	DESCRIPTION		  
		"Refers to the logical port index
		 For FRSM12 card:
		 The ifIndex of the port's corresponding row in ifTable.
		 Byte  3 = Chassis Number, Byte 2 = Slot Number,
		 Byte 1 & 0 = Encoded unique number for Port.
		"
	::= { frPortCnfSigLMIGrpEntry 1}

signallingProtocolType  OBJECT-TYPE
	SYNTAX	INTEGER {
		other(1),
		noSignalling(2),
		strataLMI(3),
		annexAUNI(4),
		annexDUNI(5),
		annexANNI(6),
		annexDNNI(7)
		}
	ACCESS read-write
   STATUS  mandatory
   DESCRIPTION
      "This will set the signalling protocol
	1 - other
	2 - noSignalling
	3 - strataLMI
	4 - annexAUNI
	5 - annexDUNI
	6 - annexANNI
	7 - annexDNNI
	Only noSignalling is applicable to 
	frame forwarding ports
    For FRSM12: strataLMI is not supported for portHeaderLen of fourOctets.
	"
	DEFVAL { noSignalling }
	::= { frPortCnfSigLMIGrpEntry 2}

asynchronousUpdates OBJECT-TYPE
	SYNTAX	INTEGER {
            disable(1),
            enable(2),
	    fsenable(3),
	    updfsenable(4)
            }
	ACCESS	read-write
	STATUS	mandatory
	DESCRIPTION		  
		"disable     - disable Asynchronous Status Updates & Unsolicited Full Status
		 enable      - enable Asynchronous Status Updates
		 fsenable    - enable Unsolicited Full Status
		 updfsenable - enable Asynchronous Status Updates & Unsolicited Full Status
		 The signalling parameters are not applicable for
		 the frame forwarding port.
		"
	DEFVAL { disable }
	::= { frPortCnfSigLMIGrpEntry 3}

t391LinkIntegrityTimer OBJECT-TYPE
	SYNTAX	INTEGER (5..30)
	ACCESS	read-write
	STATUS	mandatory
	DESCRIPTION		  
		"Interval in seconds for NNI to do status polling 
		 The signalling parameters are not applicable for
		 the frame forwarding port.
		"
	DEFVAL { 10 }
	::= { frPortCnfSigLMIGrpEntry 4}
		      	   
t392PollingVerificationTimer OBJECT-TYPE
	SYNTAX	INTEGER (5..30)
	ACCESS	read-write
	STATUS	mandatory
	DESCRIPTION		  
		"Interval in seconds for UNI to expect status polling 
		 The signalling parameters are not applicable for
		 the frame forwarding port.
		"
	DEFVAL { 15 }
	::= { frPortCnfSigLMIGrpEntry 5}

n391FullStatusPollingCounter	OBJECT-TYPE
	SYNTAX	INTEGER (1..255)
	ACCESS read-write
   STATUS  mandatory
   DESCRIPTION
      "Number of UNI/NNI Polling cycles
       The signalling parameters are not applicable for
       the frame forwarding port.
		"
	DEFVAL { 6 }
	::= { frPortCnfSigLMIGrpEntry 6}

n392ErrorThreshold	OBJECT-TYPE
	SYNTAX	INTEGER (1..10)
	ACCESS read-write
   STATUS  mandatory
   DESCRIPTION
      "UNI/NNI Error Threshold
       The signalling parameters are not applicable for
       the frame forwarding port.
		"
	DEFVAL { 3 }
	::= { frPortCnfSigLMIGrpEntry 7}

n393MonitoredEventCount	OBJECT-TYPE
	SYNTAX	INTEGER (1..10)
	ACCESS read-write
   STATUS  mandatory
   DESCRIPTION
      "UNI/NNI Events, always greater than n392
       The signalling parameters are not applicable for
       the frame forwarding port.
		"
	DEFVAL { 4 }
	::= { frPortCnfSigLMIGrpEntry 8}

enhancedLmi OBJECT-TYPE
	SYNTAX	INTEGER {
            disable(1),
            enable(2)
            }
	ACCESS	read-write
	STATUS	mandatory
	DESCRIPTION		  
		"This object defines if enhanced LMI is enabled on a 
		 logical port.
		 The signalling parameters are not applicable for
		 the frame forwarding port.
		"
	DEFVAL { disable }
	::= { frPortCnfSigLMIGrpEntry 9}

portFRF1Dot2Support OBJECT-TYPE
    SYNTAX  INTEGER {
            enable(1),
            disable(2)
            }
    ACCESS  read-write
    STATUS  mandatory
    DESCRIPTION
        "
         This object is added for FRSM12.

         This variable enables/disables FRF 1.2 feature.

	     This object is not applicable to MGX Release 1.x	
        "
    DEFVAL { disable }
    ::= { frPortCnfSigLMIGrpEntry 10}


-- ------------------------------------------------------------------------
-- End of frPortCnfSigLMIGrp group definitions


--
-- ----------------------------------------------------------------------
-- BASIS Project MIB
-- 
--






-- frPort        		OBJECT IDENTIFIER ::= { frameRelay 1 }
-- frPortCnt		OBJECT IDENTIFIER ::= { frPort 2 }
frPortCntPortGrp        OBJECT IDENTIFIER ::= { frPortCnt 1 }


-- ------------------------------------------------------------------------
--
-- frPortCounters group
-- Channel OR VC COUNTERS 
--
-- ------------------------------------------------------------------------


frPortCntPortGrpTable	OBJECT-TYPE
	SYNTAX	SEQUENCE OF FrPortCntPortGrpEntry
	ACCESS	not-accessible
	STATUS	mandatory
	DESCRIPTION
		"The config table is for logical port interface
		 there are upto 248 entries (for 8 E1s) or 192 
		 (for 8 T1s). In FRSM-VHS, there is support for
		 upto 256 entries.
		"
	::= { frPortCntPortGrp 1 }


frPortCntPortGrpEntry	OBJECT-TYPE
	SYNTAX	FrPortCntPortGrpEntry
	ACCESS	not-accessible
	STATUS	mandatory
	DESCRIPTION
		" An entry for logical port
		"
	INDEX	{ cntPortNum }
	::= { frPortCntPortGrpTable 1}

FrPortCntPortGrpEntry ::=
	SEQUENCE {
		cntPortNum 	
			INTEGER,
-- Rcv Counters
		rcvPortFrames		
			Counter,
		rcvPortBytes		
			Counter,
		rcvPortFramesDE		
			Counter,
		rcvPortFramesFECN
			Counter,
		rcvPortFramesBECN
			Counter,
-- Discarded due to 
		rcvFramesDiscCRCError	
			Counter,
		rcvFramesDiscAlignmentError
			Counter,
		rcvFramesDiscIllegalLen
			Counter,
		rcvFramesDiscIllegalHeader
			Counter,
		rcvFramesAbort
			Counter,
		rcvFramesUnknownDLCI
			Counter,
		rcvLastUnknownDLCI
			INTEGER,
-- Rcv Congestion
		rcvPortFramesTaggedFECN
			Counter,
		rcvPortFramesTaggedBECN
			Counter,
		rcvPortFramesTaggedDE
			Counter,
		rcvPortFramesDiscXceedDEThresh
			Counter,
		rcvPortKbpsAIR
			INTEGER,
		rcvBufNotAvailable
			Counter,
-- Xmt Counters
		xmtPortFrames		
			Counter,
		xmtPortBytes		
			Counter,
		xmtPortFramesFECN
			Counter,
		xmtPortFramesBECN
			Counter,
		xmtPortFramesDiscXceedQDepth
			Counter,
		xmtPortBytesDiscXceedQDepth
			Counter,
		xmtPortFramesDuringLMIAlarm
			Counter,
		xmtPortBytesDuringLMIAlarm
			Counter,
		xmtFramesAbort		
			Counter,
		xmtFramesUnderrun		
			Counter,
		xmtPortKbpsAIR
			INTEGER,
		xmtBufNotAvailable
			Counter,
		portClrButton
			INTEGER,
		rcvFramesDiscNoChan
			Counter,
		rcvFramesDiscOverrun
			Counter
}

cntPortNum OBJECT-TYPE
	SYNTAX	INTEGER
	ACCESS	read-only
	STATUS	mandatory
	DESCRIPTION		  
		"Refers to the logical port index
		 For FRSM12 card:
		 The ifIndex of the port's corresponding row in ifTable.
		 Byte  3 = Chassis Number, Byte 2 = Slot Number,
		 Byte 1 & 0 = Encoded unique number for Port.
		"
	::= { frPortCntPortGrpEntry 1}

rcvPortFrames OBJECT-TYPE
	SYNTAX	Counter
	ACCESS	read-only
	STATUS	mandatory
	DESCRIPTION		  
		"The number of frames Received on the ingress
		"
	::= { frPortCntPortGrpEntry	2 }

rcvPortBytes OBJECT-TYPE
	SYNTAX	Counter
	ACCESS	read-only
	STATUS	mandatory
	DESCRIPTION		  
		"The number of bytes Received on the ingress
		"
	::= { frPortCntPortGrpEntry	3 }

rcvPortFramesDE OBJECT-TYPE
	SYNTAX	Counter
	ACCESS	read-only
	STATUS	mandatory
	DESCRIPTION		  
		"The number of frames with DE bit set Received on the ingress
		"
	::= { frPortCntPortGrpEntry	4 }

rcvPortFramesFECN OBJECT-TYPE
	SYNTAX	Counter
	ACCESS	read-only
	STATUS	mandatory
	DESCRIPTION		  
		"The number of frames with FECN bit set Received on the ingress
		"
	::= { frPortCntPortGrpEntry	5 }

rcvPortFramesBECN OBJECT-TYPE
	SYNTAX	Counter
	ACCESS	read-only
	STATUS	mandatory
	DESCRIPTION		  
		"The number of frames with BECN bit set Received on the ingress
		"
	::= { frPortCntPortGrpEntry	6 }

rcvFramesDiscCRCError OBJECT-TYPE
	SYNTAX	Counter
	ACCESS	read-only
	STATUS	mandatory
	DESCRIPTION		  
		"The number of frames discarded on the ingress
		 due to CRC error
		"
	::= { frPortCntPortGrpEntry	7 }

rcvFramesDiscAlignmentError OBJECT-TYPE
	SYNTAX	Counter
	ACCESS	read-only
	STATUS	mandatory
	DESCRIPTION		  
		"The number of frames discarded on the ingress
		 due to Alignment error
		"
	::= { frPortCntPortGrpEntry	8 }

rcvFramesDiscIllegalLen OBJECT-TYPE
	SYNTAX	Counter
	ACCESS	read-only
	STATUS	mandatory
	DESCRIPTION		  
		"The number of frames discarded on the ingress
		 due to illegal length
		"
	::= { frPortCntPortGrpEntry	9 }

rcvFramesDiscIllegalHeader OBJECT-TYPE
	SYNTAX	Counter
	ACCESS	read-only
	STATUS	mandatory
	DESCRIPTION		  
		"The number of frames discarded on the ingress
		 due to illegal header
		"
	::= { frPortCntPortGrpEntry	10 }

rcvFramesAbort OBJECT-TYPE
	SYNTAX	Counter
	ACCESS	read-only
	STATUS	mandatory
	DESCRIPTION		  
		"The number of received frames aborted
		"
	::= { frPortCntPortGrpEntry	11 }

rcvFramesUnknownDLCI OBJECT-TYPE
	SYNTAX	Counter
	ACCESS	read-only
	STATUS	mandatory
	DESCRIPTION		  
		"The number of frames received with an unknown DLCI
		"
	::= { frPortCntPortGrpEntry	12 }

rcvLastUnknownDLCI OBJECT-TYPE
	SYNTAX	INTEGER
	ACCESS	read-only
	STATUS	mandatory
	DESCRIPTION		  
		"The last unknown DLCI received
		"
	::= { frPortCntPortGrpEntry	13 }

rcvPortFramesTaggedFECN OBJECT-TYPE
	SYNTAX	Counter
	ACCESS	read-only
	STATUS	mandatory
	DESCRIPTION		  
		"The number of frames received that were
		 tagged with FECN bit
		"
	::= { frPortCntPortGrpEntry	14 }

rcvPortFramesTaggedBECN OBJECT-TYPE
	SYNTAX	Counter
	ACCESS	read-only
	STATUS	mandatory
	DESCRIPTION		  
		"The number of frames received that were
		 tagged with BECN bit
		"
	::= { frPortCntPortGrpEntry	15 }

rcvPortFramesTaggedDE OBJECT-TYPE
	SYNTAX	Counter
	ACCESS	read-only
	STATUS	mandatory
	DESCRIPTION		  
		"The number of frames received that were
		 tagged with DE bit
		"
	::= { frPortCntPortGrpEntry	16 }

rcvPortFramesDiscXceedDEThresh OBJECT-TYPE
	SYNTAX	Counter
	ACCESS	read-only
	STATUS	mandatory
	DESCRIPTION		  
		"The number of frames discarded on the ingress
		 due to exceeded DE Threshold
		"
	::= { frPortCntPortGrpEntry	17 }

rcvPortKbpsAIR OBJECT-TYPE
	SYNTAX	INTEGER
	ACCESS	read-only
	STATUS	mandatory
	DESCRIPTION		  
		"Received Average Information Rate in KBPS
		"
	::= { frPortCntPortGrpEntry	18 }

rcvBufNotAvailable OBJECT-TYPE
	SYNTAX	Counter
	ACCESS	read-only
	STATUS	mandatory
	DESCRIPTION		  
		"The number of times the receiver is turned off
		"
	::= { frPortCntPortGrpEntry	19 }

xmtPortFrames OBJECT-TYPE
	SYNTAX	Counter
	ACCESS	read-only
	STATUS	mandatory
	DESCRIPTION		  
		"The number of frames transmitted
		"
	::= { frPortCntPortGrpEntry	20 }

xmtPortBytes OBJECT-TYPE
	SYNTAX	Counter
	ACCESS	read-only
	STATUS	mandatory
	DESCRIPTION		  
		"The number of bytes transmitted
		"
	::= { frPortCntPortGrpEntry	21 }

xmtPortFramesFECN OBJECT-TYPE
	SYNTAX	Counter
	ACCESS	read-only
	STATUS	mandatory
	DESCRIPTION		  
		"The number of frames transmittedc with
		 FECN bit already set
		"
	::= { frPortCntPortGrpEntry	22 }

xmtPortFramesBECN OBJECT-TYPE
	SYNTAX	Counter
	ACCESS	read-only
	STATUS	mandatory
	DESCRIPTION		  
		"The number of frames transmitted with
		 BECN bit already set
		"
	::= { frPortCntPortGrpEntry	23 }

xmtPortFramesDiscXceedQDepth OBJECT-TYPE
	SYNTAX	Counter
	ACCESS	read-only
	STATUS	mandatory
	DESCRIPTION		  
		"The number of frames discarded on the egress
		 due to exceeded queue depth

		 For FRSM12 Card: Not Supported
		"
	::= { frPortCntPortGrpEntry	24 }

xmtPortBytesDiscXceedQDepth OBJECT-TYPE
	SYNTAX	Counter
	ACCESS	read-only
	STATUS	mandatory
	DESCRIPTION		  
		"The number of bytes discarded on the egress
		 due to exceeded queue depth

		 For FRSM12 Card: Not Supported
		"
	::= { frPortCntPortGrpEntry	25 }

xmtPortFramesDuringLMIAlarm OBJECT-TYPE
	SYNTAX	Counter
	ACCESS	read-only
	STATUS	mandatory
	DESCRIPTION		  
		"The number of frames transmitted during
		 LMI logical port alarm
		"
	::= { frPortCntPortGrpEntry	26 }

xmtPortBytesDuringLMIAlarm OBJECT-TYPE
	SYNTAX	Counter
	ACCESS	read-only
	STATUS	mandatory
	DESCRIPTION		  
		"The number of bytes transmitted during
		 LMI logical port alarm
		"
	::= { frPortCntPortGrpEntry	27 }

xmtFramesAbort OBJECT-TYPE
	SYNTAX	Counter
	ACCESS	read-only
	STATUS	mandatory
	DESCRIPTION		  
		"The number of transmit frames aborted

		 For FRSM12 Card: Not Supported
		"
	::= { frPortCntPortGrpEntry	28 }

xmtFramesUnderrun OBJECT-TYPE
	SYNTAX	Counter
	ACCESS	read-only
	STATUS	mandatory
	DESCRIPTION		  
		"The number of frames discarded due to underrun
		"
	::= { frPortCntPortGrpEntry	29 }

xmtPortKbpsAIR OBJECT-TYPE
	SYNTAX	INTEGER
	ACCESS	read-only
	STATUS	mandatory
	DESCRIPTION		  
		"Transmit Average Information Rate in KBPS
		"
	::= { frPortCntPortGrpEntry	30 }

xmtBufNotAvailable OBJECT-TYPE
	SYNTAX	Counter
	ACCESS	read-only
	STATUS	mandatory
	DESCRIPTION		  
		"The number of times the transmitter is turned off

		 For FRSM12 Card: Not Supported
		"
	::= { frPortCntPortGrpEntry	31 }

portClrButton OBJECT-TYPE
	SYNTAX	INTEGER {
               noaction (1),
               clear (2)
        }
	ACCESS	read-write
	STATUS	mandatory
	DESCRIPTION		  
		"Port clear button. Resets all counters.
		"
	::= { frPortCntPortGrpEntry	32 }

rcvFramesDiscNoChan OBJECT-TYPE
        SYNTAX  Counter
        ACCESS  read-only
        STATUS  mandatory
        DESCRIPTION
                "The number of frames received when no channel is setup
                "
        ::= { frPortCntPortGrpEntry     33 }

rcvFramesDiscOverrun OBJECT-TYPE
        SYNTAX  Counter
        ACCESS  read-only
        STATUS  mandatory
        DESCRIPTION
            " The number of frames discarded in Ingress direction
             due to FIFO overrun in HDLC Controller.

             This object is not applicable to MGX Release 1.x
            "
        ::= { frPortCntPortGrpEntry     34 }


-- ------------------------------------------------------------------------
-- End of frPortCntPortGrp group definitions


--
-- ----------------------------------------------------------------------
-- BASIS Project MIB
-- 
--






-- frPort        		OBJECT IDENTIFIER ::= { frameRelay 1 }
-- frPortCnt		OBJECT IDENTIFIER ::= { frPort 2 }
-- frPortCntSig  		OBJECT IDENTIFIER ::= { frPortCnt 2 }
frPortCntSigCLLMGrp   	OBJECT IDENTIFIER ::= { frPortCntSig 2 }


-- ------------------------------------------------------------------------
--
-- frPortCntSigCLLM group
-- Port counter signalling values
--
-- ------------------------------------------------------------------------


frPortCntSigCLLMGrpTable	OBJECT-TYPE
	SYNTAX	SEQUENCE OF FrPortCntSigCLLMGrpEntry
	ACCESS	not-accessible
	STATUS	mandatory
	DESCRIPTION
		"The CLLM counter table is for logical port interface
		"
	::= { frPortCntSigCLLMGrp 1 }

frPortCntSigCLLMGrpEntry	OBJECT-TYPE
	SYNTAX	FrPortCntSigCLLMGrpEntry
	ACCESS	not-accessible
	STATUS	mandatory
	DESCRIPTION
		" An entry for logical port
		"
	INDEX	{ cllmSigPortNum }
	::= { frPortCntSigCLLMGrpTable 1 }

FrPortCntSigCLLMGrpEntry ::=
	SEQUENCE {
	   	cllmSigPortNum 	              	INTEGER,
		rcvFramesCLLM             	Counter, 
		rcvBytesCLLM             	Counter, 
		xmtFramesCLLM             	Counter, 
		xmtBytesCLLM             	Counter, 
		cllmFailures             	Counter
		}


cllmSigPortNum OBJECT-TYPE
	SYNTAX	INTEGER
	ACCESS	read-only
	STATUS	mandatory
	DESCRIPTION		  
		"Refers to the logical port index
		 For FRSM12 card:
		 The ifIndex of the port's corresponding row in ifTable.
		 Byte  3 = Chassis Number, Byte 2 = Slot Number,
		 Byte 1 & 0 = Encoded unique number for Port.
		"
	::= { frPortCntSigCLLMGrpEntry 1}

rcvFramesCLLM OBJECT-TYPE
	SYNTAX	Counter
	ACCESS	read-only
	STATUS	mandatory
	DESCRIPTION		  
		"The number of CLLM frames received
		"
	::= { frPortCntSigCLLMGrpEntry 2}

rcvBytesCLLM OBJECT-TYPE
	SYNTAX	Counter
	ACCESS	read-only
	STATUS	mandatory
	DESCRIPTION		  
		"The number of CLLM bytes received
		"
	::= { frPortCntSigCLLMGrpEntry 3}

xmtFramesCLLM OBJECT-TYPE
	SYNTAX	Counter
	ACCESS	read-only
	STATUS	mandatory
	DESCRIPTION		  
		"The number of CLLM frames transmitted
		"
	::= { frPortCntSigCLLMGrpEntry 4}

xmtBytesCLLM OBJECT-TYPE
	SYNTAX	Counter
	ACCESS	read-only
	STATUS	mandatory
	DESCRIPTION		  
		"The number of CLLM bytes transmitted
		"
	::= { frPortCntSigCLLMGrpEntry 5}

cllmFailures OBJECT-TYPE
	SYNTAX	Counter
	ACCESS	read-only
	STATUS	mandatory
	DESCRIPTION		  
		"The number of times an expected CLLM message was not received
		"
	::= { frPortCntSigCLLMGrpEntry 6}




-- ------------------------------------------------------------------------
-- End of frPortCntSigCLLMGrp group definitions


--
-- ----------------------------------------------------------------------
-- BASIS Project MIB
-- 
--






-- frPort        		OBJECT IDENTIFIER ::= { frameRelay 1 }
-- frPortCnt		OBJECT IDENTIFIER ::= { frPort 2 }
-- frPortCntSig  		OBJECT IDENTIFIER ::= { frPortCnt 2 }
frPortCntSigLMIGrp   	OBJECT IDENTIFIER ::= { frPortCntSig 1 }


-- ------------------------------------------------------------------------
--
-- frPortCntSigLMI group
-- Port counter signalling values
--
-- ------------------------------------------------------------------------


frPortCntSigLMIGrpTable	OBJECT-TYPE
	SYNTAX	SEQUENCE OF FrPortCntSigLMIGrpEntry
	ACCESS	not-accessible
	STATUS	mandatory
	DESCRIPTION
		"The LMI counter table is for logical port interface
		 there are upto 248 entries (for 8 E1s) and upto 
		 192 entries (for 8 T1s). In FRSM-VHS, there are
		 upto 256 entries.
		"
	::= { frPortCntSigLMIGrp 1 }

frPortCntSigLMIGrpEntry	OBJECT-TYPE
	SYNTAX	FrPortCntSigLMIGrpEntry
	ACCESS	not-accessible
	STATUS	mandatory
	DESCRIPTION
		" An entry for logical port
		"
	INDEX	{ lmiSigPortNum }
	::= { frPortCntSigLMIGrpTable 1 }

FrPortCntSigLMIGrpEntry ::=
	SEQUENCE {
	   	lmiSigPortNum 	              	INTEGER,
		rcvStatusInquiry              	Counter, 
		rcvInvalidRequest             	Counter, 
		rcvUNISeqMismatch             	Counter, 
		xmtStatus			Counter, 
		xmtAsynchUpdate			Counter, 
		uniSignalingTimeout		Counter, 
		xmtStatusInquiry		Counter, 
		rcvStatus			Counter, 
		rcvAsynchUpdate			Counter, 
		rcvNNISeqMismatch             	Counter, 
		nniSignalingTimeout		Counter
		}


lmiSigPortNum OBJECT-TYPE
	SYNTAX	INTEGER
	ACCESS	read-only
	STATUS	mandatory
	DESCRIPTION		  
		"Refers to the logical port index
		 For FRSM12 card:
		 The ifIndex of the port's corresponding row in ifTable.
		 Byte  3 = Chassis Number, Byte 2 = Slot Number,
		 Byte 1 & 0 = Encoded unique number for Port.
		"
	::= { frPortCntSigLMIGrpEntry 1}

rcvStatusInquiry OBJECT-TYPE
	SYNTAX	Counter
	ACCESS	read-only
	STATUS	mandatory
	DESCRIPTION		  
		"The number of Status Inquiry messages received
		"
	::= { frPortCntSigLMIGrpEntry 2}

rcvInvalidRequest OBJECT-TYPE
	SYNTAX	Counter
	ACCESS	read-only
	STATUS	mandatory
	DESCRIPTION		  
		"The number of Invalid Request messages received
		"
	::= { frPortCntSigLMIGrpEntry 3}

rcvUNISeqMismatch OBJECT-TYPE
	SYNTAX	Counter
	ACCESS	read-only
	STATUS	mandatory
	DESCRIPTION		  
		"The number of times UNI messages 
		 with sequence number mismatches were received
		"
	::= { frPortCntSigLMIGrpEntry 4}

xmtStatus OBJECT-TYPE
	SYNTAX	Counter
	ACCESS	read-only
	STATUS	mandatory
	DESCRIPTION		  
		"The number of times Status response messages transmitted
		"
	::= { frPortCntSigLMIGrpEntry 5}

xmtAsynchUpdate OBJECT-TYPE
	SYNTAX	Counter
	ACCESS	read-only
	STATUS	mandatory
	DESCRIPTION		  
		"The number of times Asynch Status messages transmitted
		"
	::= { frPortCntSigLMIGrpEntry 6}

uniSignalingTimeout OBJECT-TYPE
	SYNTAX	Counter
	ACCESS	read-only
	STATUS	mandatory
	DESCRIPTION		  
		"The number of times UNI Status requests were not received
		"
	::= { frPortCntSigLMIGrpEntry 7}

xmtStatusInquiry OBJECT-TYPE
	SYNTAX	Counter
	ACCESS	read-only
	STATUS	mandatory
	DESCRIPTION		  
		"The number of Status Inquiry messages transmitted
		"
	::= { frPortCntSigLMIGrpEntry 8}

rcvStatus OBJECT-TYPE
	SYNTAX	Counter
	ACCESS	read-only
	STATUS	mandatory
	DESCRIPTION		  
		"The number of times Status response messages received
		"
	::= { frPortCntSigLMIGrpEntry 9}

rcvAsynchUpdate OBJECT-TYPE
	SYNTAX	Counter
	ACCESS	read-only
	STATUS	mandatory
	DESCRIPTION		  
		"The number of times Asynch Status messages received
		"
	::= { frPortCntSigLMIGrpEntry 10}

rcvNNISeqMismatch OBJECT-TYPE
	SYNTAX	Counter
	ACCESS	read-only
	STATUS	mandatory
	DESCRIPTION		  
		"The number of times NNI messages 
		 with sequence number mismatches were received
		"
	::= { frPortCntSigLMIGrpEntry 11}

nniSignalingTimeout OBJECT-TYPE
	SYNTAX	Counter
	ACCESS	read-only
	STATUS	mandatory
	DESCRIPTION		  
		"The number of times NNI Status requests were not received
		"
	::= { frPortCntSigLMIGrpEntry 12}


-- ------------------------------------------------------------------------
-- End of frPortCntSigLMIGrp group definitions


--
-- ----------------------------------------------------------------------
-- BASIS Project MIB
-- 
--





-- frPort 		OBJECT IDENTIFIER ::= { frameRelay 1 }
frPortStateGrp 	OBJECT IDENTIFIER ::= { frPort 3 }

-- ------------------------------------------------------------------------
--
-- Group frChannelState
-- Contains status information for channels
--
-- ------------------------------------------------------------------------


frPortStateGrpTable OBJECT-TYPE
	SYNTAX  SEQUENCE OF FrPortStateGrpEntry
	ACCESS  not-accessible
	STATUS  mandatory
	DESCRIPTION
		"Table of transmit/receive states of ports.
		"
	::= { frPortStateGrp 1 }

frPortStateGrpEntry OBJECT-TYPE
	SYNTAX FrPortStateGrpEntry
	ACCESS not-accessible
	STATUS mandatory
	DESCRIPTION
		"An entry for logical port.
		"
	INDEX	{ statePortNum }
	::= { frPortStateGrpTable 1 }

FrPortStateGrpEntry ::=
	SEQUENCE {
		statePortNum
         		INTEGER,
		portState
         		INTEGER,
		portSignallingState
			INTEGER,
		portOversubscribed
         		INTEGER,
		portIngrPercentUtil
			INTEGER,
		portEgrPercentUtil
			INTEGER
		}

statePortNum OBJECT-TYPE
	SYNTAX	INTEGER
	ACCESS	read-only
	STATUS	mandatory
	DESCRIPTION		  
		"Refers to the logical port index
		 For FRSM12 card:
		 The ifIndex of the port's corresponding row in ifTable.
		 Byte  3 = Chassis Number, Byte 2 = Slot Number,
		 Byte 1 & 0 = Encoded unique number for Port.
		"
	::= { frPortStateGrpEntry 1}

portState OBJECT-TYPE
	SYNTAX  INTEGER {
		notConfigured(1),
		active(2),
		remoteLoopback(3),
		failedDueToLine(4),
		failedDueToSignalling(5),
		inactive(6),
		inBert(7),
		farEndRemoteLoopback(8),
		latchDS0DropFeLoop(9),
		latchDS0LineFeLoop(10),
		latchOcuFeLoop(11),
		latchCsuFeLoop(12),
		latchDsuFeLoop(13),
		latchHL96FeLoop(14),
		v54PolynomialFeLoop(15)
	}
	ACCESS  read-only
	STATUS  mandatory
	DESCRIPTION
		"This variable indicates the state of the
		 logical port
		"
	::= { frPortStateGrpEntry 2}
 
portSignallingState OBJECT-TYPE
	SYNTAX	INTEGER (0..'ffffff'h) 
	ACCESS	read-only
	STATUS	mandatory
	DESCRIPTION
		"Bit 0 = 0 -> LMI O.K. or not enabled
		 Bit 0 = 1 -> LMI failed
		 Bit 1 = 0 -> CLLM O.K. or not enabled
		 Bit 1 = 1 -> CLLM failed
		"

	::= { frPortStateGrpEntry 3}


portOversubscribed  OBJECT-TYPE		
	SYNTAX	INTEGER {
		false (1),
		true (2)
		}
	ACCESS read-only
        STATUS  mandatory
        DESCRIPTION
        "This variable indicates the whether the port is 
		over subscribed or not
        "
	::= { frPortStateGrpEntry 4}

portIngrPercentUtil		OBJECT-TYPE
	SYNTAX  INTEGER (0..1000)  
	ACCESS read-only 
	STATUS  mandatory  
	DESCRIPTION    
		"Percentage Utilization of the Port in the Ingress
		 direction.
		" 
	::= { frPortStateGrpEntry 5}


portEgrPercentUtil		OBJECT-TYPE
	SYNTAX  INTEGER (0..1000)  
	ACCESS read-only 
	STATUS  mandatory  
	DESCRIPTION    
		"Percentage Utilization of the Port in the Egress
		 direction.
		" 
	::= { frPortStateGrpEntry 6}




-- ------------------------------------------------------------------------
-- End of frPortState group definitions



-- frPort                  OBJECT IDENTIFIER ::= { frameRelay 1 }
-- frPortCnf               OBJECT IDENTIFIER ::= { frPort 1 }
-- frPortCnfResPartGrp     OBJECT IDENTIFIER ::= { frPortCnf 5 }

-- --------------------------------------------------------------------
--
--
--              LOGICAL PORT CONFIG Resource Partition Group
--
--
-- --------------------------------------------------------------------

frPortCnfResPartGrpTable	OBJECT-TYPE
	SYNTAX  SEQUENCE OF FrPortCnfResPartGrpEntry
	ACCESS  not-accessible
	STATUS  mandatory
	DESCRIPTION
		"This table contains the configuration of port resource 
		 partition
		"
	::= {frPortCnfResPartGrp 1}

frPortCnfResPartGrpEntry		OBJECT-TYPE
	SYNTAX  FrPortCnfResPartGrpEntry
	ACCESS  not-accessible
	STATUS  mandatory
	DESCRIPTION
		"An entry for logical port
		"
	INDEX  { frResPartPortNum, frResPartCtrlrNum }
	::= { frPortCnfResPartGrpTable 1 }

FrPortCnfResPartGrpEntry ::=
	SEQUENCE {
		frResPartPortNum	INTEGER,
		frResPartCtrlrNum	INTEGER,
		frResPartRowStatus	INTEGER,
		frResPartNumOfLcnAvail	INTEGER,
		frResPartDlciLow	INTEGER,
		frResPartDlciHigh	INTEGER,
		frResPartIngrPctBW	INTEGER,
		frResPartEgrPctBW	INTEGER,
        frResPartCtrlrID        INTEGER
	}

frResPartPortNum	OBJECT-TYPE
        SYNTAX  INTEGER
        ACCESS  read-only
        STATUS  mandatory
        DESCRIPTION
                "This is the logical port number, the index to this table.
		 If we have T1 card then the maximum port number is 192
		 and if we have E1 card the maximum port number can be 248
		 For FRSM VHS 2CT3 the maximum port number is 256.
		 For FRSM12 card:
		 The ifIndex of the port's corresponding row in ifTable.
		 Byte  3 = Chassis Number, Byte 2 = Slot Number,
		 Byte 1 & 0 = Encoded unique number for Port.
                "
        ::= { frPortCnfResPartGrpEntry 1 }

frResPartCtrlrNum OBJECT-TYPE
        SYNTAX  INTEGER {
		par (1),
		pnni(2),
		tag (3)
	}
        ACCESS  read-only
        STATUS  mandatory
        DESCRIPTION
                "This is index for controller using the port
                 In MGX release 1.0, the value par should be used
                 In MGX release 2.0, the value pnni should be used
                "
        ::= { frPortCnfResPartGrpEntry 2 }

frResPartRowStatus OBJECT-TYPE
        SYNTAX  INTEGER {
		add (1),
		del (2),
		mod (3)
	}
        ACCESS  read-write
        STATUS  mandatory
        DESCRIPTION
         " This will add, delete or modify the partition.
          In MGX Release1.0:
          To add an entry, this object should be set to add, value for
          other objects should not be specified. FRSM will choose
          default values for all other objects.

          In MGX Release2.0:
          To add an entry, this object should be set to add, value
          for  frResPartCtrlrID may be specified. FRSM will choose
          default values for all other objects.

          Currently the value mod is not supported.

          To delete an entry, this object has to be set to del.
          The resource partition can be deleted only after
          deleting all the connections (LCNs).
		"
        ::= { frPortCnfResPartGrpEntry 3 }

--changed the LCN avail range from 1000 to 4000 for vhs.
frResPartNumOfLcnAvail OBJECT-TYPE
        SYNTAX  INTEGER (0..16000)
        ACCESS  read-write
        STATUS  mandatory
        DESCRIPTION
                " This represents number of LCNs available for this
                  controller and this port
                  FRSM VHS 2CT3 can support LCNs upto 4000.
                  FRSM12 can support LCNs upto 16000.
                "
        ::= { frPortCnfResPartGrpEntry 4 }

frResPartDlciLow OBJECT-TYPE
        SYNTAX  INTEGER (0..8388607)
        ACCESS  read-write
        STATUS  mandatory
        DESCRIPTION
                "This represents low end of reserved DLCI
                "
        ::= { frPortCnfResPartGrpEntry 5 }

frResPartDlciHigh OBJECT-TYPE
        SYNTAX  INTEGER (0..8388607)
        ACCESS  read-write
        STATUS  mandatory
        DESCRIPTION
                "This represents high end of reserved DLCI
                "
        ::= { frPortCnfResPartGrpEntry 6 }

frResPartIngrPctBW OBJECT-TYPE
        SYNTAX  INTEGER (0..100)
        ACCESS  read-write
        STATUS  mandatory
        DESCRIPTION
                "The percentage of total ingress bandwidth reserved 
                "
        ::= { frPortCnfResPartGrpEntry 7 }

frResPartEgrPctBW OBJECT-TYPE
        SYNTAX  INTEGER (0..100)
        ACCESS  read-write
        STATUS  mandatory
        DESCRIPTION
                "The percentage of total egress bandwidth reserved 
                "
        ::= { frPortCnfResPartGrpEntry 8 }

frResPartCtrlrID OBJECT-TYPE
    SYNTAX INTEGER(1..255)
    ACCESS read-write
    STATUS mandatory
    DESCRIPTION
        "This is the controller identifier for the  resource patition.
         The  default value is set for PNNI controller.
        "
    DEFVAL { 2 }
    ::= { frPortCnfResPartGrpEntry 9 }

--FRSM_VHS: new group added for the FRSM_VHS
 
-- frPort        			OBJECT IDENTIFIER ::= { frameRelay 1 }
-- frPortCnf				OBJECT IDENTIFIER ::= { frPort 1 }
-- frPortServiceQueGrp                  OBJECT IDENTIFIER ::= { frPortCnf 4 }

-- --------------------------------------------------------------------
--
--
--		LOGICAL PORT CONFIG Group
--
--
-- --------------------------------------------------------------------


frPortServiceQueGrpTable	OBJECT-TYPE
	SYNTAX	SEQUENCE OF FrPortServiceQueGrpEntry
	ACCESS	not-accessible
	STATUS	mandatory
	DESCRIPTION
		"The config table is for logical port interface. 
		 In FRSM-VHS, there are 256 entries for FRSM-2CT3 card and
		 2 entries for FRSM-T3/E3/HS2/T3B/E3B/HS2B-HSSI cards and
		 8 entries for FRSM-HS2B-12IN1. The table is currently
		 supported only in FRSM-VHS when the object egrQosFeature
		 in the cardSpecific group is set to egrQosFeatureEnabled. 

		"
	::= { frPortServiceQueGrp 1 }


frPortServiceQueGrpEntry	OBJECT-TYPE
	SYNTAX	FrPortServiceQueGrpEntry
	ACCESS	not-accessible
	STATUS	mandatory
	DESCRIPTION
		" An entry for logical port
		"
	INDEX	{frServPortNum, portServiceQueueNo }
    ::= { frPortServiceQueGrpTable 1 }

FrPortServiceQueGrpEntry ::=
	SEQUENCE {
		frServPortNum 	
			INTEGER,
		portServiceQueueNo
			INTEGER,
        portEgresQDepth
            INTEGER,
        portEgresECNThresh
            INTEGER,
        portEgresDEThresh
            INTEGER,
		portQBwInc
			INTEGER,
		portBytesDiscXceedQueFull
			Counter,
		portBytesDiscXceedDEThresh
			Counter
		}

frServPortNum	OBJECT-TYPE
	SYNTAX	INTEGER (1..256) 
	ACCESS	read-only
	STATUS	mandatory
	DESCRIPTION
		"This is the logical port number.
		"
	::= { frPortServiceQueGrpEntry 1}

portServiceQueueNo      OBJECT-TYPE
    SYNTAX  INTEGER{
		highpriorityQ(1),
		rtVBRQ(2),
		nrtVBRandABRQ(3),
		uBRQ(4),
		queue5(5),
		queue6(6),
		queue7(7),
		queue8(8)
	}
	ACCESS  read-write
	STATUS  mandatory
	DESCRIPTION
	"This identifies the Q depending on the Service Type
	 1 High Priority Queue
	 2 rt VBR Queue
	 3 nrt VBR and ABR Queue
	 4 UBR Queue
	 queue5(5) to queue8(8) are reserved for future use
	 There are 8 queues but only four are being used as of now.
	"
	::= { frPortServiceQueGrpEntry 2 }

portEgresQDepth      OBJECT-TYPE
	SYNTAX  INTEGER(0..2097151)
	ACCESS  read-write
	STATUS  mandatory
	DESCRIPTION
	"Indicates the peak Egress queue depth for the logical port.
	 The total queue depth of all connections mapped to this queue
	 should not exceed this value.
	"
	DEFVAL {1048575}
	::= { frPortServiceQueGrpEntry 3 }

portEgresECNThresh        OBJECT-TYPE
	SYNTAX  INTEGER(0..2097151)
	ACCESS  read-write
	STATUS  mandatory
	DESCRIPTION
	"ECN threshold for the logical port. If the total queue depth of
	 all connections mapped to this port queue exceeds this threshold,
	 then the appropriate ECN bit (FECN in the downstream direction and
	 BECN in the upstream direction) get set.
	"
	DEFVAL {104857}
	::= { frPortServiceQueGrpEntry 4 }

portEgresDEThresh OBJECT-TYPE
	SYNTAX  INTEGER(0..2097151)
	ACCESS  read-write
	STATUS  mandatory
	DESCRIPTION
	"DE threshold for the logical port. If the total queue depth of
	 all connections mapped to this port queue exceeds this threshold,
	 and the DE bit is set in the incoming frame, then the frame gets
	 dropped.
	"
	DEFVAL {524287}
	::= { frPortServiceQueGrpEntry 5 }

portQBwInc      OBJECT-TYPE
	SYNTAX  INTEGER(0..16383)
	ACCESS  read-only
	STATUS  mandatory
	DESCRIPTION
	"Denotes the bandwidth increment for this port queue. The
	 bandwidth increment is the percentage of the port bandwidth
	 used by all connections mapped to a particular queue scaled
	 by the value 16384.
	"
	::= { frPortServiceQueGrpEntry 6 }

portBytesDiscXceedQueFull OBJECT-TYPE
	SYNTAX	Counter
	ACCESS	read-only
	STATUS	mandatory
	DESCRIPTION
	"Counter maintained for the no of bytes discarded due to
	 port queue depth exceeded.
	"
	::= { frPortServiceQueGrpEntry 7 }

portBytesDiscXceedDEThresh	OBJECT-TYPE
	SYNTAX	Counter
	ACCESS	read-only
	STATUS	mandatory
	DESCRIPTION
	"Counter maintained for the no of bytes discarded due to
	 DE threshold exceeded.
	"
	::= { frPortServiceQueGrpEntry 8 }


-- ------------------------------------------------------------------
--
-- BASIS project  CARD SPECIFIC SM MIB
-- 
-- 
-- Created by Shawn K. 5/17/95 
--
-- ------------------------------------------------------------------




smFeatures              OBJECT IDENTIFIER ::= {cardSpecific 6}
smRateControlConfig     OBJECT IDENTIFIER ::= {cardSpecific 7}
smCardUtilization       OBJECT IDENTIFIER ::= {cardSpecific 11}
smRasConfig             OBJECT IDENTIFIER ::= {cardSpecific 18}
rasOamLpbkInfo          OBJECT IDENTIFIER ::= {cardSpecific 19}

-- ------------------------------------------------------------------
--
--  Group "smFeatures"
--  Service Module Features enabled for this card.
--  This contains all the features specific to SM card such as
--  Rate Control, Channelized and forsight feature.
--
-- ------------------------------------------------------------------

channelizedAllowed OBJECT-TYPE
    SYNTAX  INTEGER {
	nonChannelized(1),
	channelized(2)
	}
    ACCESS  read-only
    STATUS  mandatory
    DESCRIPTION
        "BRAM parameter indicating whether this card will support
         DS0 channels.
        "
    ::= { smFeatures 1 }

rateControlAllowed OBJECT-TYPE
    SYNTAX  INTEGER {
        rateControlDisabled(1),
        rateControlEnabled(2)
        }
    ACCESS  read-only
    STATUS  mandatory
    DESCRIPTION
        "BRAM parameter indicating whether this card will support
         foresight.
        "
    ::= { smFeatures 2 }

svcAllowed OBJECT-TYPE
    SYNTAX  INTEGER {
        svcDisabled(1),
        svcEnabled(2)
        }
    ACCESS  read-only
    STATUS  mandatory
    DESCRIPTION
        "BRAM parameter indicating whether this card will support
         svc.
        "
    ::= { smFeatures 3 }

funiAllowed OBJECT-TYPE
    SYNTAX  INTEGER {
        funiDisabled(1),
        funiEnabled(2)
        }
    ACCESS  read-only
    STATUS  mandatory
    DESCRIPTION
        "BRAM parameter indicating whether this card will support
         FUNI.
        "
    ::= { smFeatures 4 }

imaAllowed OBJECT-TYPE
    SYNTAX  INTEGER {
        imaDisabled(1),
        imaEnabled(2)
        }
    ACCESS  read-only
    STATUS  mandatory
    DESCRIPTION
        "BRAM parameter indicating whether this card will support
         Inverse Multiplexing for ATM (IMA) feature
        "
    ::= { smFeatures 5 }

mulTrksAllowed OBJECT-TYPE
    SYNTAX  INTEGER {
        mulTrksDisabled(1),
        mulTrksEnabled(2)
        }
    ACCESS  read-only
    STATUS  mandatory
    DESCRIPTION
        "BRAM parameter indicating whether this card will support
         multiple IMA trunks feature.
	 A value of 1 indicates that the feature is not allowed and
	 a value of 2 indicates that the features is allowed
        "
    ::= { smFeatures 6 }

egrQosFeature OBJECT-TYPE
	SYNTAX  INTEGER {
		egrQosFeatureEnabled(1),
		egrQosFeatureDisabled(2),
		notApplicable(3)
		}
	ACCESS  read-only
	STATUS  mandatory
	DESCRIPTION
		 "If this   is set to egrQosFeatureEnabled then
		the various class of service viz. Hi Priority, VBR rt, etc.
		as defined by the channel MIB object chanServType are supported.
		If this is set to  egrQosFeatureDisabled then, the priority based 
		queuing as defined by the channel MIB object egressQSelect is 
		supported."
	::= { smFeatures 7 }


-- ------------------------------------------------------------------
--
--  Group "smRateControlConfig"
--  Service Module Rate Control Configuration Parameters for this card.
--
-- ------------------------------------------------------------------
 
rateUp OBJECT-TYPE
    SYNTAX  INTEGER (1..100)
    ACCESS  read-write
    STATUS  mandatory
    DESCRIPTION
        "Rate Up value for this card.
        "
    ::= { smRateControlConfig 1 }
 
 
rateDown OBJECT-TYPE
    SYNTAX  INTEGER (1..100)
    ACCESS  read-write
    STATUS  mandatory
    DESCRIPTION
        "Rate Down value for this card.
        "
    ::= { smRateControlConfig 2 }
 
rateFastDown OBJECT-TYPE
    SYNTAX  INTEGER (1..100)
    ACCESS  read-write
    STATUS  mandatory
    DESCRIPTION
        "Rate Fast Down value for this card.
        "
    ::= { smRateControlConfig 3 }
 
 
rtdMeasurementTime OBJECT-TYPE
    SYNTAX  INTEGER (1..255)
    ACCESS  read-write
    STATUS  mandatory
    DESCRIPTION
        "Round Trip delay measurement time in secs for this card.
        "
    ::= { smRateControlConfig 4 }
 
qirTimeout OBJECT-TYPE
    SYNTAX  INTEGER (1..255)
    ACCESS  read-write
    STATUS  mandatory
    DESCRIPTION
        "QIR timeout in secs for this card.
        "
    ::= { smRateControlConfig 5 }


-- ------------------------------------------------------------------
--
--  Group "smCardUtilization"
--  Service Module Card Utilization Parameters for this card.
--
-- ------------------------------------------------------------------
cardOversubscribed  OBJECT-TYPE		
	SYNTAX	INTEGER {
		false (1),
		true (2)
		}
	ACCESS read-only
        STATUS  mandatory
        DESCRIPTION
        "This variable indicates the whether the card is 
		over subscribed or not
        "
	::= { smCardUtilization 1}

cardIngrPercentUtil		OBJECT-TYPE
	SYNTAX  INTEGER (0..1000)  
	ACCESS read-only 
	STATUS  mandatory  
	DESCRIPTION    
		"Percentage Utilization of the Card in the Ingress
		 direction.
		" 
	::= { smCardUtilization 2}


-- ------------------------------------------------------------------
--
--	Group "smRasConfig" 
--	Provides objects for configuring the RAS feature on this card.
--
-- ------------------------------------------------------------------

rasOamlpbkAllowed 	OBJECT-TYPE
    SYNTAX  INTEGER {
        rasOamlpbkEnabled (1),
        rasOamlpbkDisabled (2)
                    }   
    ACCESS  read-write
    STATUS  mandatory
    DESCRIPTION
        "Object indicating whether RAS- OAM loopback test is enabled or
	 disabled for this card.
        "
    ::= { smRasConfig 1 }

rasOamlpbkFrequency OBJECT-TYPE
    SYNTAX  INTEGER (1..10)
    ACCESS  read-write
    STATUS  mandatory
    DESCRIPTION
        "Object indicating the frequency in minutes in which RAS task sends
	 one OAM loopback cell per idle connection.
        "
    ::= { smRasConfig 2 }


-- ----------------------------------------------------------------
--
--       Group   rasOamLpbkInfo
--       Provide objects for sending loopback test results
--
-- ----------------------------------------------------------------
-- changed the upper limit from 3 to 15 to support 4000 connections 
-- for VHS cards.

chanPacketNumber   OBJECT-TYPE
    SYNTAX INTEGER (0..15)
    ACCESS read-only
    STATUS mandatory
    DESCRIPTION
        "Each trap will send status for 256 channels bitmapping the
	 status. This object identities the chunk of 256 channels. The channel 
	 numbers for which the trap indicates the status is found as  
	 chanPacketNumber * 256 + bitoffset + 16. This object cannot be set or 
	 read.
	"

    ::= { rasOamLpbkInfo 1 }

chanOAMstatus32    OBJECT-TYPE
    SYNTAX INTEGER 
    ACCESS read-only
    STATUS mandatory
    DESCRIPTION
        "Bit map indicating Ras_oam_lpbk test state of 32 channels from
         chanPacketNumber * 256 + 16 to chanPacketNumber * 256 + 47
	 MSB represent lower channel and LSB represent higher channel
         0 in bit position indicate lpbk test ok
         1 in bit position indicate lpbk test failed
         This object cannot be set or read
        "
    ::= { rasOamLpbkInfo 2 }
 
chanOAMstatus64    OBJECT-TYPE
    SYNTAX INTEGER 
    ACCESS read-only
    STATUS mandatory
    DESCRIPTION
        "Bit map indicating Ras_oam_lpbk test state of 32 channels from
         chanPacketNumber * 256 + 48 to chanPacketNumber * 256 + 79 
	 MSB represent lower channel and LSB represent higher channel
         0 in bit position indicate lpbk test ok
         1 in bit position indicate lpbk test failed
         This object cannot be set or read
        "
 
    ::= { rasOamLpbkInfo 3 }

chanOAMstatus96    OBJECT-TYPE
    SYNTAX INTEGER
    ACCESS read-only
    STATUS mandatory
    DESCRIPTION
        "Bit map indicating Ras_oam_lpbk test state of 32 channels from
         chanPacketNumber * 256 + 80 to chanPacketNumber * 256 + 111
	 MSB represent lower channel and LSB represent higher channel
         0 in bit position indicate lpbk test ok
         1 in bit position indicate lpbk test failed
         This object cannot be set or read
        "
 
    ::= { rasOamLpbkInfo 4 }
 
chanOAMstatus128   OBJECT-TYPE
    SYNTAX INTEGER 
    ACCESS read-only
    STATUS mandatory
    DESCRIPTION
        "Bit map indicating Ras_oam_lpbk test state of 32 channels from
         chanPacketNumber * 256 + 112 to chanPacketNumber * 256 + 143
	 MSB represent lower channel and LSB represent higher channel
         0 in bit position indicate lpbk test ok
         1 in bit position indicate lpbk test failed
         This object cannot be set or read
        "
 
    ::= { rasOamLpbkInfo 5 }

chanOAMstatus160   OBJECT-TYPE
    SYNTAX INTEGER 
    ACCESS read-only
    STATUS mandatory
    DESCRIPTION
        "Bit map indicating Ras_oam_lpbk test state of 32 channels from
         chanPacketNumber * 256 + 144 to chanPacketNumber * 256 + 175
	 MSB represent lower channel and LSB represent higher channel
         0 in bit position indicate lpbk test ok
         1 in bit position indicate lpbk test failed
         This object cannot be set or read
        "
 
    ::= { rasOamLpbkInfo 6 }
 
chanOAMstatus192   OBJECT-TYPE
    SYNTAX INTEGER 
    ACCESS read-only
    STATUS mandatory
    DESCRIPTION
        "Bit map indicating Ras_oam_lpbk test state of 32 channels from
         chanPacketNumber * 256 + 176 to chanPacketNumber * 256 + 207
	 MSB represent lower channel and LSB represent higher channel
         0 in bit position indicate lpbk test ok
         1 in bit position indicate lpbk test failed
         This object cannot be set or read
        "
 
    ::= { rasOamLpbkInfo 7 }

chanOAMstatus224   OBJECT-TYPE
    SYNTAX INTEGER 
    ACCESS read-only
    STATUS mandatory
    DESCRIPTION
        "Bit map indicating Ras_oam_lpbk test state of 32 channels from
         chanPacketNumber * 256 + 208 to chanPacketNumber * 256 + 239
	 MSB represent lower channel and LSB represent higher channel
         0 in bit position indicate lpbk test ok
         1 in bit position indicate lpbk test failed
         This object cannot be set or read
        "
 
    ::= { rasOamLpbkInfo 8 }
 
chanOAMstatus256   OBJECT-TYPE
    SYNTAX INTEGER 
    ACCESS read-only
    STATUS mandatory
    DESCRIPTION
        "Bit map indicating Ras_oam_lpbk test state of 32 channels from
         chanPacketNumber * 256 + 240 to chanPacketNumber * 256 + 271
	 MSB represent lower channel and LSB represent higher channel
         0 in bit position indicate lpbk test ok
         1 in bit position indicate lpbk test failed
         This object cannot be set or read
        "
 
    ::= { rasOamLpbkInfo 9 }

 
-- frPortCnfX21PortGrp  	OBJECT IDENTIFIER ::= { frPortCnf 3 }

-- --------------------------------------------------------------------
--
--
--		LOGICAL PORT CONFIG Group
--
--
-- --------------------------------------------------------------------


frPortCnfX21PortGrpTable	OBJECT-TYPE
	SYNTAX	SEQUENCE OF FrPortCnfX21PortGrpEntry
	ACCESS	not-accessible
	STATUS	mandatory
	DESCRIPTION
		"The config table is for X.21/HSSI logical port interface
		"
	::= { frPortCnfX21PortGrp 1 }


frPortCnfX21PortGrpEntry	OBJECT-TYPE
	SYNTAX	FrPortCnfX21PortGrpEntry
	ACCESS	not-accessible
	STATUS	mandatory
	DESCRIPTION
		" An entry for logical port
		"
	INDEX	{ x21portNum }
    ::= { frPortCnfX21PortGrpTable 1 }

FrPortCnfX21PortGrpEntry ::=
	SEQUENCE {
		x21portNum 	
			INTEGER,
		x21portLineNum 	
			INTEGER,
      		x21portRowStatus
         		INTEGER,
      		x21portFlagsBetweenFrames
         		INTEGER,
      		x21portEqueueServiceRatio
			INTEGER,
		x21portSpeed
			INTEGER,
		x21portAdmin
			INTEGER,
		x21portType
			INTEGER,
		x21portSvcStatus
               		INTEGER,
		x21portSvcInUse
               		INTEGER,
		x21portSvcShareLcn
               		INTEGER,
		x21portSvcLcnLow
               		INTEGER,
		x21portSvcLcnHigh
			INTEGER,
		x21portSvcDlciLow
			INTEGER,
		x21portSvcDlciHigh
			INTEGER,
		x21portDeleteSvcs
			INTEGER,
		x21portIngrSvcBandW
			INTEGER,
		x21portEgrSvcBandW
			INTEGER
		}

x21portNum OBJECT-TYPE
	SYNTAX	INTEGER (1..4) 
	ACCESS	read-only
	STATUS	mandatory
	DESCRIPTION
		"This is logical port number.
		 The HSSI backcard can support upto 3 ports,
		 whereas the X.21 can support 4 logical ports.
		 No defaults.
		"
	::= { frPortCnfX21PortGrpEntry 1}

x21portLineNum	OBJECT-TYPE
	SYNTAX	INTEGER (1..4) 
	ACCESS	read-write
	STATUS	mandatory
	DESCRIPTION
		"This represents the line number.
		 On FRSM-HS1 the HSSI can support 3 lines
		 and X.21 4 lines.
		 No defaults.
		"
	::= { frPortCnfX21PortGrpEntry 2}

x21portRowStatus  OBJECT-TYPE		
	SYNTAX	INTEGER {
		add(1),
		del(2),
		mod(3)
		}
	ACCESS read-write
        STATUS  mandatory
        DESCRIPTION
        "This variable adds, deletes, or modifies the port
	 1- add
	 2 - delete
	 3 - modify
	 Default is add.
        "
        ::= { frPortCnfX21PortGrpEntry 3 }

x21portFlagsBetweenFrames OBJECT-TYPE
	SYNTAX	INTEGER (1..10) 
	ACCESS	read-write
	STATUS	mandatory
	DESCRIPTION
		"Number of flags transmitted between two consecutive
		 HDLC frames.
		 Default is 1 flag.
		"
	::= { frPortCnfX21PortGrpEntry 4 }

x21portEqueueServiceRatio OBJECT-TYPE
	SYNTAX	INTEGER (1..15) 
	ACCESS	read-write
	STATUS	mandatory
	DESCRIPTION
		"Number of times queue 1 is serviced 
		 for every time queue 2 is serviced.
		 Default is 1.
		"
	::= { frPortCnfX21PortGrpEntry 5 }

x21portSpeed OBJECT-TYPE
        SYNTAX  INTEGER
	ACCESS  read-only
        STATUS  mandatory
        DESCRIPTION
                "Port speed in kbps. At present it is same
		 as line speed.
		 No defaults.
                "
        ::= { frPortCnfX21PortGrpEntry 6 }

x21portAdmin OBJECT-TYPE
        SYNTAX	INTEGER {
		up(1),
		down(2),
		write-Only(3)
                }
        ACCESS read-write
        STATUS  mandatory
        DESCRIPTION
                " Up/down used to up and down the port.
		 Default is the up state.
                "
        ::= { frPortCnfX21PortGrpEntry 7 }

x21portType OBJECT-TYPE
	SYNTAX	INTEGER {
		frame-relay(1),
		frFUNI(2),
		frame-forward(3)
            }
	ACCESS	read-write
	STATUS	mandatory
	DESCRIPTION
		"This represents port type. The processing of the
		 frames depends on the type of the port.
		"
	::= { frPortCnfX21PortGrpEntry 8 }

x21portSvcStatus OBJECT-TYPE
	SYNTAX	INTEGER {
            disable(1),
            enable(2)
            }
	ACCESS	read-write
	STATUS	mandatory
	DESCRIPTION
		"This represents SVC status
		"
	::= { frPortCnfX21PortGrpEntry 9 }

x21portSvcInUse	OBJECT-TYPE
	SYNTAX	INTEGER {
            not-use(1),
            in-use(2)
            }
	ACCESS	read-write
	STATUS	mandatory
	DESCRIPTION
		"This represents port svc in use
		"
	::= { frPortCnfX21PortGrpEntry 10 }

x21portSvcShareLcn	OBJECT-TYPE
	SYNTAX	INTEGER {
            port-based(1),
            card-based(2)
            }
	ACCESS	read-only
	STATUS	mandatory
	DESCRIPTION
		"This represents port type
		"
	::= { frPortCnfX21PortGrpEntry 11 }

x21portSvcLcnLow OBJECT-TYPE
	SYNTAX	INTEGER (16..271)
	ACCESS	read-only
	STATUS	mandatory
	DESCRIPTION
		"This represents low end of reserved LCN for svc
		"
	::= { frPortCnfX21PortGrpEntry 12 }

x21portSvcLcnHigh OBJECT-TYPE
	SYNTAX	INTEGER (16..271)
	ACCESS	read-only
	STATUS	mandatory
	DESCRIPTION
		"This represents high end of reserved LCN for svc
		"
	::= { frPortCnfX21PortGrpEntry 13 }

x21portSvcDlciLow	OBJECT-TYPE
	SYNTAX	INTEGER (0..1023)
	ACCESS	read-only
	STATUS	mandatory
	DESCRIPTION
		"This represents low end of reserved DLCI for svc
		"
	::= { frPortCnfX21PortGrpEntry 14 }

x21portSvcDlciHigh	OBJECT-TYPE
	SYNTAX	INTEGER (0..1023)
	ACCESS	read-only
	STATUS	mandatory
	DESCRIPTION
		"This represents high end of reserved DLCI for svc
		"
	::= { frPortCnfX21PortGrpEntry 15 }


x21portDeleteSvcs OBJECT-TYPE
	SYNTAX	INTEGER {
		delete(1),
		other(2)
		}
	ACCESS  read-write
        STATUS  mandatory
        DESCRIPTION
        "Setting this object to 1 indicates that all the SVC
	 connections on the given port has to be deleted
        "
	::= { frPortCnfX21PortGrpEntry 16 }

x21portIngrSvcBandW	OBJECT-TYPE
	SYNTAX	INTEGER
	ACCESS	read-only
	STATUS	mandatory
	DESCRIPTION
		"This represents Ingress Bandwidth reserve for SVC
		"
	::= { frPortCnfX21PortGrpEntry 17 }

x21portEgrSvcBandW	OBJECT-TYPE
	SYNTAX	INTEGER
	ACCESS	read-only
	STATUS	mandatory
	DESCRIPTION
		"This represents Egress Bandwidth reserve for SVC
		"
	::= { frPortCnfX21PortGrpEntry 18 }


--
-- ----------------------------------------------------------------------
-- BASIS Project MIB
-- 
--






x21AlmCnfGrp	OBJECT IDENTIFIER ::= { x21 2 }

-- ------------------------------------------------------------------------
-- x21AlmConfig group
--
-- This group contains X.21/HSSI line alarm configuration table
-- ------------------------------------------------------------------------

x21AlmCnfGrpTable OBJECT-TYPE
	SYNTAX	SEQUENCE OF X21AlmCnfGrpEntry
	ACCESS	not-accessible
	STATUS	mandatory
	DESCRIPTION
		"The FRSM-HS1/HS2 interface alarm configuration table.
		"
	::= { x21AlmCnfGrp 1 }

x21AlmCnfGrpEntry OBJECT-TYPE
	SYNTAX	X21AlmCnfGrpEntry
	ACCESS  not-accessible
	STATUS  mandatory
	DESCRIPTION
		"An entry in the X.21/HSSI Alarm Configuration table
		"
	INDEX	{ x21AlmCnfLineNum }
	::= { x21AlmCnfGrpTable 1 }

X21AlmCnfGrpEntry ::=
	SEQUENCE {
		x21AlmCnfLineNum	INTEGER,
		x21Severity		INTEGER
      	}

x21AlmCnfLineNum OBJECT-TYPE
	SYNTAX	INTEGER (1..8)
	ACCESS	read-write
	STATUS	mandatory
	DESCRIPTION
		"X.21/HSSI line number.
		 No defaults.
		 FRSM-HS2/HS2B-HSSI supports a range from 1 to 2
		 FRSM-HS2B-12IN1 supports a range from 1 to 8
		"
	::= { x21AlmCnfGrpEntry 1 }


x21Severity	OBJECT-TYPE
	SYNTAX	INTEGER {
		minor(1),
		major(2),
		dontcare(3)
	}
	ACCESS	read-write
	STATUS	mandatory
	DESCRIPTION
		"This variable is used to setup the severity of LOS or clock
		 mismatch alarm. Whenever the above condition arises, the
		 FRSM-HS1/HS2/HS2B will send the alarm with appropriate status.
		"
	::= { x21AlmCnfGrpEntry 2 }





--
-- ----------------------------------------------------------------------
-- BASIS Project MIB
-- 
--






x21AlmGrp OBJECT IDENTIFIER ::= { x21 3 }

-- ------------------------------------------------------------------------
-- X.21/HSSI Alarm Group
--
-- This group contains X.21/HSSI line alarm table
-- ------------------------------------------------------------------------

x21AlmGrpTable OBJECT-TYPE
	SYNTAX	SEQUENCE OF X21AlmGrpEntry
	ACCESS	not-accessible
	STATUS	mandatory
	DESCRIPTION
		"The X.21/HSSI interface alarm configuration table.
		 The size of table is given by the value of x21LineNum"
	::= { x21AlmGrp 1 }

x21AlmGrpEntry OBJECT-TYPE
	SYNTAX	X21AlmGrpEntry
	ACCESS  not-accessible
	STATUS  mandatory
	DESCRIPTION
		"An entry in the X21 Alarm table"
	INDEX	{ x21AlmLineNum }
	::= { x21AlmGrpTable 1 }

X21AlmGrpEntry ::=
	SEQUENCE {
		x21AlmLineNum		INTEGER,
		x21LineAlarmState	INTEGER,
		x21LineEIAStatus	INTEGER,
		x21AlarmClrButton	INTEGER
	}

x21AlmLineNum OBJECT-TYPE
	SYNTAX	INTEGER (1..8)
	ACCESS	read-only
	STATUS	mandatory
	DESCRIPTION
		"This object is the identifier (line number) of a X.21/HSSI
		 interface.
		 FRSM-HS2/HS2B-HSSI supports a range from 1 to 2
		 FRSM-HS2B-12IN1 supports a range from 1 to 8
		"
	::= { x21AlmGrpEntry 1 }

x21LineAlarmState OBJECT-TYPE
	SYNTAX	INTEGER (0..1023)
	ACCESS	read-only
	STATUS  mandatory
	DESCRIPTION
		"This variable is a bitmap of the X21 Line ALarms
		 on the FRSM-HS1. A value of zero indicates no alarms.
		 Itemized below are the individual bits:
		 BitPosition    Alarm
		 -----------    -----
		  0		C/I signal is OFF (also used to indicate LOS)
                  1             Clock rate mismatch (used in DTE mode)
		  2		Internal Loopback (diagnostic loopback)
		  3		HSSI Local LoopA (line is in loopback)
                  4             HSSI Local LoopB (line is in loopback)
		  5		Remote Loopback (line is transmitting loopcodes)
		  6             For V35 DTE mode, DCD and CTS both are inactive
                  7             For V35 DCE mode, RTS is inactive
                  8             No cable attached to V35 backcard
                  9             Wrong cable attached to V35 backcard
                 If all the bit-states are 0s:
                  - line is not in alarm, or
                  - line not in loopback, or
                  - line is transmitting any loopback codes.
		"
	::= { x21AlmGrpEntry 2 }

x21LineEIAStatus OBJECT-TYPE
	SYNTAX	INTEGER	(0..'7'h)
	ACCESS	read-only
	STATUS	mandatory
	DESCRIPTION
		"Indicates the status of X.21/HSSI lines:
		 0x01 -- c-lead high
		 0x02 -- i-lead high
		 0x04 -- LC-lead high (valid only for HSSI DCE mode).
		"
	::= { x21AlmGrpEntry 3 }

x21AlarmClrButton OBJECT-TYPE
	SYNTAX  INTEGER {
		noaction (1),
		clear (2)
	}
	ACCESS  read-write
	STATUS  mandatory
	DESCRIPTION
		"This variable is used to clear all the alarms for the line.
		 1 = No action
		 2 = Clear alarm
		"
	::= { x21AlmGrpEntry 4 }

--
-- ----------------------------------------------------------------------
-- BASIS Project MIB
-- 
--



x21CnfGrp	OBJECT IDENTIFIER ::= { x21 1 }

-- ------------------------------------------------------------------------
-- X.21 Config Group
--
-- This group contains X.21 line configuration table
-- ------------------------------------------------------------------------

x21CnfGrpTable OBJECT-TYPE
	SYNTAX	SEQUENCE OF X21CnfGrpEntry
	ACCESS	not-accessible
	STATUS	mandatory
	DESCRIPTION
		"The X21 Configuration table. The table size is
		 given by the value of x21LineNumofValidEntries
		"
	::= { x21CnfGrp 1 }

x21CnfGrpEntry OBJECT-TYPE
	SYNTAX	X21CnfGrpEntry
	ACCESS	not-accessible
	STATUS	mandatory
	DESCRIPTION
		"An entry in the X21 Configuration table.
		"
        INDEX	{ x21LineNum }

	::= { x21CnfGrpTable 1 }

X21CnfGrpEntry ::=
	SEQUENCE {
		x21LineNum
			INTEGER,
		x21LineEnable
			INTEGER,
		x21LineType
			INTEGER,
       		x21LineRate
			INTEGER,
		x21LineLoopbackCommand
			INTEGER,
		x21LineSendCode
			INTEGER,
		x21LineLoopbackCodeDetection
			INTEGER,
		x21ConnectorType
			INTEGER,
		x21InvertClock
			INTEGER,
		x21LineInterfaceType
			INTEGER,
		x21ClkFrequencyThreshold
			INTEGER,
		serialLineRate
			INTEGER,
		serialLineRateVariation
			INTEGER
    		}

x21LineNum OBJECT-TYPE
	SYNTAX	INTEGER (1..8)
	ACCESS	read-only
	STATUS	mandatory
	DESCRIPTION
		"
		 This object is the identifier of a X.21 interface.
		 No defaults.
		 FRSM-HS2/HS2B-HSSI supports a range from 1 to 2
		 FRSM-HS2B-12IN1 supports a range from 1 to 8
		"
	::= { x21CnfGrpEntry 1 }

x21LineEnable  OBJECT-TYPE
	SYNTAX	INTEGER {
		disable(1),
		enable(2),
		modify(3)
		}
	ACCESS read-write
	STATUS  mandatory
	DESCRIPTION
		"This variable disables, enables or modifies a line
		 1 - disable
		 2 - enable
		 3 - modify
		Default is enable.
		"
	::= { x21CnfGrpEntry 2 }

x21LineType OBJECT-TYPE
	SYNTAX  INTEGER {
		dte(1),
		dce(2),
		dteST(3)
   		}
	ACCESS  read-write
	STATUS  mandatory
	DESCRIPTION
		"This variable indicates the type X21 line type.
		 The line-type affects the clock -- the DCE device
		 always provides the clock and DTE accepts it.
		 dteST is only applicable to V.35 interfaces
		 Default is DTE.
		"
	::= { x21CnfGrpEntry 3 }


x21LineRate OBJECT-TYPE
  	SYNTAX  INTEGER {
		r48Kbps(1),
		r56Kbps(2),
		r64Kbps(3),
		r112Kbps(4),
		r128Kbps(5),
		r168Kbps(6),
		r192Kbps(7),
		r224Kbps(8),
		r256Kbps(9),
		r280Kbps(10),
		r320Kbps(11),
		r336Kbps(12),
		r384Kbps(13),
		r392Kbps(14),
		r448Kbps(15),
		r512Kbps(16),
		r768Kbps(17),
		r1024Kbps(18),
		r1536Kbps(19),
		r1544Kbps(20),
		r1792Kbps(21),
		r1920Kbps(22),
		r1984Kbps(23),
		r2048Kbps(24),
		r3097Kbps(25),
		r3157Kbps(26),
		r4096Kbps(27),
		r4645Kbps(28),
		r4736Kbps(29),
		r6195Kbps(30),
		r6315Kbps(31),
		r7744Kbps(32),
		r7899Kbps(33),
		r8192Kbps(34),
		r9289Kbps(35),
		r9472Kbps(36),
		r10240Kbps(37),
		r10890Kbps(38),
		r11060Kbps(39),
		r12390Kbps(40),
		r12630Kbps(41),
		r13900Kbps(42),
		r14220Kbps(43),
		r14340Kbps(44),
		r15490Kbps(45),
		r15800Kbps(46),
		r16380Kbps(47),
		r20030Kbps(48),
		r24990Kbps(49),
		r52Mbps(50),
-- FRSM_VHS added for frsm_vhs
		r17370Kbps(51),
		r18950Kbps(52),
		r20530Kbps(53),
		r22100Kbps(54),
		r23680Kbps(55),
--
-- n*T1 rates. Added for FRSM_VHS
-- note that 1.544Kbps is already enumerated above
--
		r3088Kbps(56),
		r4632Kbps(57),
		r6176Kbps(58),
		r7720Kbps(59),
		r9264Kbps(60),
		r10808Kbps(61),
		r12352Kbps(62),
		r13896Kbps(63),
		r15440Kbps(64),
		r16984Kbps(65),
		r18528Kbps(66),
		r20072Kbps(67),
		r21616Kbps(68),
		r23160Kbps(69),
		r24704Kbps(70),
		r26248Kbps(71),
		r27792Kbps(72),
		r29336Kbps(73),
		r30880Kbps(74),
		r32424Kbps(75),
		r33968Kbps(76),
		r35512Kbps(77),
		r37056Kbps(78),
		r38600Kbps(79),
		r40144Kbps(80),
		r41688Kbps(81),
		r43232Kbps(82),
		r44776Kbps(83),
		r46320Kbps(84),
		r47864Kbps(85),
		r49408Kbps(86),
		r50952Kbps(87),
--
-- n*E1 rates. Added for FRSM_VHS.		
--
		r6144Kbps(88),
		r12288Kbps(89),
		r14336Kbps(90),
		r16384Kbps(91),
		r18432Kbps(92),
		r20480Kbps(93),
		r22528Kbps(94),
		r24576Kbps(95),
		r26624Kbps(96),
		r28672Kbps(97),
		r30720Kbps(98),
		r32768Kbps(99),
		r34816Kbps(100),
		r36864Kbps(101),
		r38912Kbps(102),
		r40960Kbps(103),
		r43008Kbps(104),
		r45056Kbps(105),
		r47104Kbps(106),
		r49152Kbps(107),
		r51200Kbps(108)
	}
	ACCESS  read-write
	STATUS  mandatory
	DESCRIPTION
		"This variable configures the X.21/HSSI/V.35 line-rate.
		 Note that enumerations 51 through 108 are supported
		 only by FRSM-HS2/HS2B card.

		 default is r48Kbps on FRSM-HS2B-12IN1
		 default is r52Mbps on FRSM-HS2/HS2B-HSSI
		"
	::= { x21CnfGrpEntry 4 }

x21LineLoopbackCommand OBJECT-TYPE
	SYNTAX  INTEGER {
		x21NoLoop(1),
		x21DiagnosticMetallicLoop(2),
		x21DiagnosticFrontcardLoop(3),
		x21RemoteLoop(4),
		v35MetallicLoop(5)
   		}
         ACCESS  read-write
         STATUS  mandatory
         DESCRIPTION
		"This variable represents the  loopback  state
        	 x21NoLoop
			Not in the loopback state. Normal traffic can be sent
        	 x21DiagnosticMetallicLoop
			Loopbacks the line on the back-card towards the Network.
        	 x21DiagnosticFrontcardLoop
			Loopbacks the line on the frontcard toward the Network.
        	 x21RemoteLoop
             		The remote NTU is in the loop back mode.
			In this state, the FRSM-HS1 is sending the loopback 
			code to remote NTU.
	 	 Default is x21NoLoop.
		 Note: Before going into one of the loopbacks the state
		 should be x21NoLoop.
		"
	::= { x21CnfGrpEntry 5 }

x21LineSendCode OBJECT-TYPE
	SYNTAX  INTEGER {
		x21NoCode(1),
		x21SendLoopACode(2),
		x21SendLoopBCode(3),
		x21SendLocalLoopCode(4),
		x21SendRemoteLoopCode(5),
		x21SendUnLoopCode(6)
   	}
	ACCESS  read-write
	STATUS  mandatory
	DESCRIPTION
        	"This variable indicates what type of  code  is
        	 being sent across the X.21/HSSI interface by the
		 device. The values mean:
		 
		x21NoCode: No loopback.

        	x21SendLoopACode:
             		Start sending Loop A code. Valid only if
			the backcard is HSSI and the line-type is DTE.
			This command loops the line module of the remote
			device.

        	x21SendLoopBCode:
             		Start sending Loop B code. Valid only if the
			backcard is HSSI and the line-type is DTE.
			This command loops the digital section of the
			remote device.

        	x21SendLocalLoopCode:
             		Start sending CCITT X.21 Loopback Type 3 code.
			This is valid only if the backcard is X.21 type.

        	x21SendRemoteLoopCode:
             		Start sending CCITT X.21 Loopback Type 2 code.
			This is valid only if the backcard is X.21 type.
		
	       	x21SendUnLoopCode:
             		Sending a loopback termination request.
			Valid for both HSSI and X.21 lines.

		To execute any of the loop-codes the x21LineLoopbackCommand
		should be set to x21RemoteLoop.
		Once the x21SendUnLoopCode succeeds the x21LineLoopbackCommand
		would transition back to x21NoLoop state.
	
		Default is x21NoCode."
	::= { x21CnfGrpEntry 6 }

x21LineLoopbackCodeDetection OBJECT-TYPE
	SYNTAX  INTEGER {
		codeDetectDisabled(1),
		codeDetectEnabled(2)
		}
        ACCESS  read-write
        STATUS  mandatory
        DESCRIPTION
                "Enable detection of line Loopback Codes.
		 In the current release, the loopback detection
		 is implemented only in HSSI DCE mode.
		 Default is codeDetectDisabled.
                "
        ::= { x21CnfGrpEntry 7 }

x21ConnectorType OBJECT-TYPE
	SYNTAX  INTEGER {
		x21Backcard(1),
		hssiBackcard(2),
		v35Backcard(3)
		}
        ACCESS  read-only
        STATUS  mandatory
        DESCRIPTION
		"back card type
		 This object is not used by FRSM-HS2/HS2B
		"
	::= { x21CnfGrpEntry 8 }

x21InvertClock OBJECT-TYPE
       SYNTAX INTEGER {
                  nonInvertedAndNotLooped(1),
                  invertedAndNotLooped(2),
                  nonInvertedAndLooped(3),
                  invertedAndLooped(4)
       }
       ACCESS read-write
       STATUS mandatory
       DESCRIPTION
              "This object configures two options:
              a) To invert the clock sent by HS1/HS2B with the TX data or not.
              b) If DCE,to expect the receive clock looped back from DTE or not.
	         If DTE,to loop back the receive clock from DCE or not.
 
            nonInvertedAndNotLooped(1)- a)=dont invert, b)=dont expect rcv clock/
							   dont loop rcv clock
            invertedAndNotLooped(2)   - a)=invert,      b)=dont expect rcv clock/
							   dont loop rcv clock
            nonInvertedAndLooped(3)   - a)=dont invert, b)=expect rcv clock/
							   loop rcv clock
            invertedAndLooped(4)      - a)=invert,      b)=expect rcv clock/
							   loop rcv clock
 
	    Enums 1 and 2 are applicable for X.21/HSSI/V.35 interfaces.
	    Enums 3 and 4 are applicable only for V.35.

            Default for X.21/HSSI is nonInvertedAndNotLooped(1)
            Default for V.35 is nonInvertedAndLooped(3)
            This object is not used by FRSM-HS2/FRSM-HS2B-HSSI
            This object is used by FRSM-HS2B-12IN1 and default
            values are nonInvertedAndNotLooped(1) for X.21, 
			nonInvertedAndLooped(3) for V.35
              "
       ::= { x21CnfGrpEntry 9 }

x21LineInterfaceType OBJECT-TYPE
       SYNTAX INTEGER {
         hssi(1),
         x21(2),
         v35(3)
       }
       ACCESS read-write
       STATUS mandatory
       DESCRIPTION
       " This object indicates serial interface type.
         Default is hssi.
		 
		 This object is not is configurable in FRSM-HS2
		 and FRSM-HS2B-HSSI. It will be set hssi by
		 default for these cards
		 
		 This object is configurable in FRSM-H2B-12IN1.
		 Default is v35"
       ::= { x21CnfGrpEntry 10}

x21ClkFrequencyThreshold OBJECT-TYPE
       SYNTAX INTEGER (1..5)
       ACCESS read-write
       STATUS mandatory
       DESCRIPTION
       "This object indicates user configurable percentage of
          clock frequency, which is used by DTE clock monitoring
          to declare clock rate out of bound alarm. This object
          is valid only for X.21/v.35/HSSI DTE interfaces.
		  This object is supported by FRSM-HS2 and FRSM-HS2/B"

       DEFVAL { 3 }
         ::= { x21CnfGrpEntry 11}

serialLineRate OBJECT-TYPE
       SYNTAX INTEGER (48000..51840000)
       ACCESS read-write
       STATUS mandatory
       DESCRIPTION
       " line rate for X.21/HSSI/V.35 interfaces
	     in bps. This object is supported only
		 by FRSM-HS2/B card, only multiples of
		 1000 are accepted.
		 
		 Default is 48Kbps for X.21/V.35 interfaces
		 and 51840Kbps for HSSI interface

		 "
         ::= { x21CnfGrpEntry 12}

serialLineRateVariation OBJECT-TYPE
       SYNTAX INTEGER 
       ACCESS read-only
       STATUS mandatory
       DESCRIPTION
       " This object indicates line rate variation of
         HSSI/X.21/V.35 DCE interfaces in ppm (parts
		 per million). i.e.

		 clock generated from DCE hardware interface =
		   (serialLineRate +/- (serialLineRateVariation
				        * 10^6)/ serialLineRate)

		 This object is supported only by FRSM-HS2/B card "

         ::= { x21CnfGrpEntry 13}


-- Scalars

x21LineNumofValidEntries OBJECT-TYPE
	SYNTAX	INTEGER
	ACCESS	read-only
	STATUS	mandatory
	DESCRIPTION
		"The number of X.21/HSSI configuration entries
		 (regardless of their current configuration) in
		 the x21ConfigTable table."
	::= { x21CnfGrp 2 }

--
-- ----------------------------------------------------------------------
-- BASIS Project MIB
--
--
-- VISM cardSpecific vismConfig group
--
-- ------------------------------------------------------------------
--
-- Modification History
-- 06/08 Removed vismDspTable as there is no requirement for monitoring
--       individual DSPs.
-- 07/02 Added objects for VISM15 Alabama & South Carolena projects
-- 07/23 Modified to incorporate the changes from review meeting.
-- 08/31 Regrouped objects into 4 different groups
-- 09/08 Added thirtyms & fourtyms to vismPacketizationPeriod
-- 11/03 Adding 10ms to Jitter Initial Delay (CSCdp24063)
--       Commented out obsoleted objects vismEcanDspCnt, EcanCnfNR,
--       EcanCnfNoiseMatch(CSCdp05637)
-- 11/22 Add aal1Svc to vismMode.
-- 11/30 Add aal1Svc to vismPrevMode.
-- 12/07 Obsoleted vismNsapAddress as it was not used.
-- 02/04 Added the description that IP address should be configured before adding
--       endpoints
-- 00/02/09 Enforce max number endpoints based upon template number
--
-- VISM153
-- 03/10  Introduced vismAal2Grp for vism1.53 release
--        Introduced vismTftpServerDn object
--        Deprecated vismEcanCnfIdleDirection and IdlePattern
-- VISM153
--
-- 04/12  Added vismXgcpBearerNetworkType, Connection type and vc type
-- 04/19  Added co4 bearer continuity timer
-- 04/20  changing the range of vismJitterInitialDelay, this requirement
--        came from DSP group, we should allow the user to configure as
--        much range as the DSP supports.
--
-- 03/02/2000 Modify description for vismConfigChangeTypeBitMap:
--            Add bitmap for lapd table change and rudp session table
--            change.
--            bit 15 set = vismLapdTable changed
--            bit 16 set = vismRudpSessionCnfTable changed
--
-- 04/25/2000 making Indiana MIB changes.
--
-- 07/17/2000 Added two new scalar objects vismExtDnsServerDn and
--            vismFeatureBitMap in vismSystemGrp.  Deprecated 
--            vismPrevMode in the same group. 
--
-- 08/25/2000 Changed the range of vismBearerContinuityTimer range
--              from 200..10000 to 0..10000
--            Added vismVoIpDTMFRelay, vismVoIPCasTransport, vismVoipVADTimer
--                  vismVoIpTrippleRedundancy into vismVoIpGrp
--            Added vismVADTolerance and vismVADDutyCycle objects into vismSystemGrp
--            Changed the default value of vismJitterBufferDelay to 40 milli secs. 
--
-- 10/09/2000 Remove switchedVoipCASBh and switchedVoipPRIBh from vismMode.
--
-- 10/10/2000 Remove supermode from vismMode.
--
-- 11/17/2000 Added vismInteropGrp for penn-maintainance release
-- 
-- 1/11/2001 Change vismMode enums back to the vaule before 10/09/2000
--
-- 1/31/2001 Change clearChannel value from 6 back to 4 in vismUpspeedCodec.

-- VISM 2.2
-- 5/30/2001 Added vismBearerContinuityTest as a part of vismSystemGrp 
--           to go in VISMRI release.
--
-- 05/11/2001 Added vismCaleaEnable for VISMRI release
--
-- 06/29/2001 Added Change traps for MGC Redundancy Grp tables for VISMRI
--
-- 07/20/2001 Deprecated vismJitterInitialDelay and vismJitterDelayMode objects
--            for RI release
--
-- 07/11/2001 Added a scalar object vismVoIpNTECapabilityNegotiate in
--            vismVoIpGrp.
-- 07/14/2001 Added a scalar object vismVoIpSIDPayloadType in
--            vismVoIpGrp.
-- 07/15/2001 Added 3 scalar objects vismVoIpDPvcOamCellGap vismVoIpDPvcRetryCnt 
--            vismVoIpDPvcRecoverCnt in vismVoIpGrp
-- 08/08/2001 Added vismRtcpRecvMultiplier, vismVoIpLapdTrunkPVC object in 
--            vismVoIPGrp    
-- 08/09/2001 Modified description of vismVADDutyCycle object
--        
-- vismAal2CidFillTimer range extended to 5 .. 100
-- 09/10/2001 Added G723.1-h and G.723.1-L as VBD codec
--
-- 08/21/2001 Modified the default value for vismVoIpDtmfRelay to true {vismVoIpGrp 5}
--
-- 08/21/2001 Modified the default value for vismVoIpTripleRedanduncy to false {vismVoIPGrp 7}
-- 
-- 08/21/2001 Added g726-16, g726-24, and g726-40 codec to vismUpspeedCodec {vismDspGrp 9} 
--
-- 08/21/2001 Added vismVoIpEventNegotiationPolicy {vismVoIpGrp 16}
--
-- 09/28/2001 Added announcement change in vismConfigChangeTypeBitMap object
--
-- 11/27/2001 Added voipAndAal1Svc (9) in vismMode for turning on CLIs for
-- both VoIP and AAL1SVC.
--
-- 04/23/2002 modified the vismCaleaEnable description

-- VISM 3.1 
-- 05/20/2002 Added a object vismPayloadType in vismDspGrp
--
-- 05/20/2002 Added a object vismDynamicPT in vismInteropGrp
-- 
-- 06/13/2000 Modify description for vismConfigChangeTypeBitMap:
--            Add bitmap for vismSessionSet and vismSessionGrp table change.
--            
--            bit 27 set = vismSessionSetTable changed 
--            bit 28 set = vismSessionGrpTable changed 


 
vismConfig       OBJECT IDENTIFIER ::= {cardSpecific 17}

-- ------------------------------------------------------------------
--
-- vismConfig group
--
-- This group is an extension to the existing cardGeneric group of AXIPOPMIB. 
--  i.e., in addition to these new VISM specific groups, we still use the 
--  generic card groups also.
--
-- The MIB variables in this group have been defined to configure or
-- monitor the VISM specific card level parameters.
--
-- ------------------------------------------------------------------

vismIpGrp        OBJECT IDENTIFIER ::= {vismConfig 1}
vismVoIpGrp      OBJECT IDENTIFIER ::= {vismConfig 2}
vismDspGrp       OBJECT IDENTIFIER ::= {vismConfig 3}
vismSystemGrp    OBJECT IDENTIFIER ::= {vismConfig 4}
vismTrapObjGrp   OBJECT IDENTIFIER ::= {vismConfig 5}
vismAal2Grp      OBJECT IDENTIFIER ::= {vismConfig 6}
vismInteropGrp   OBJECT IDENTIFIER ::= {vismConfig 7}

-- ------------------------------------------------------------------
--
-- vismIpGrp group
--
-- This group contains objects that are specific to IP. 
--
-- ------------------------------------------------------------------

vismIpAddress    OBJECT-TYPE
    SYNTAX IpAddress
    ACCESS read-write
    STATUS mandatory
    DESCRIPTION
        " The IP address of VISM card. Each VISM card has its own IP address.
          IP address for each VISM card is required to communicate with the
          Call agent. The IP address should be configured before adding
          endpoints.
          This object is applicable if the mode is voIP or switching.

          From vism 2.0.3 release onwards this object can be
          configured in any application but will be applicable only
          in switching applications.
        "
    ::= {vismIpGrp 1}

vismSubNetMask    OBJECT-TYPE
    SYNTAX  IpAddress
    ACCESS  read-write
    STATUS  mandatory
    DESCRIPTION
        " SUB-NETMASK of the VISM IP interface. 
	  This object is applicable if the mode is voIP or switching.

          From vism 2.0.3 release onwards this object can be
          configured in any application but will be applicable only
          in switching applications.

        "
    ::= { vismIpGrp 2 }

vismControlTos    OBJECT-TYPE
    SYNTAX  INTEGER (0..255)
    ACCESS  read-write
    STATUS  mandatory
    DESCRIPTION
        " This object is used to provision the bitmask used for the 
          TOS (Type Of Service) octet for cells carrying the control  
          (xGCP ) traffic. 
          Default value 96 = 0x60 => Precedence = 3 and TOS nibble = 0
          The bitmask can be only a byte value.
        "
    DEFVAL { 96 }
    ::= { vismIpGrp 3 }

vismBearerIpAddress    OBJECT-TYPE
     SYNTAX IpAddress
     ACCESS read-write
     STATUS mandatory
     DESCRIPTION
         " The bearer IP address of VISM card. This is an optional second
           IP address of the VISM card. If this bearer IP address is defined,
           the vismIpAddress automatically becomes the control IP address.
  
           From vism 2.0.3 release onwards this object can be
           configured in any application but will be applicable only
           in switching applications.
         "
     ::= {vismIpGrp 4}

vismBearerSubNetMask    OBJECT-TYPE
     SYNTAX  IpAddress
     ACCESS  read-write
     STATUS  mandatory
     DESCRIPTION
         " Bearer SUB-NETMASK of the VISM IP interface.
           This optional bearer subnet mask must be provided
           when vismBearerIpAddress is provided.

           From vism 2.0.3 release onwards this object can be
           configured in any application but will be applicable only
           in switching applications.

         "
     ::= { vismIpGrp 5 }

-- vismSUIpAddress    OBJECT-TYPE
--    SYNTAX IpAddress
--    ACCESS read-write
--    STATUS mandatory
-- obsolete
--        This object is superseded by mgcTable in MGMIB. From VISM1.5 release
--        onwards, VISM can communicate with more than one call agent/Media
--        Gateway Controller. Hence instead of a single SUIpAddress, a table
--        is used to represent the IP addresses of the Media Gateway Controllers.
--    DESCRIPTION
--        " The IP address of the SU (Signaling Unit) to which VISM card backhauls
--          signaling. VISM and SU exchange two types of messages -
--          control messages as specified in the SGCP protocol and signaling 
--          messages which are backhauled from VISM to SU over RUDP protocol.
--          Both these protocol messages are carried as IP datagram over 
--          AAL5 from VISM to the router which routes the messages to the SU.
--        "
--    ::= {vismConfig 3}

--vismDomainName    OBJECT-TYPE
--    SYNTAX  DisplayString (SIZE(0..64))
--    ACCESS  read-write
--    STATUS  mandatory
-- obsolete
--          This object is superseded by mgName in MGMIB.
--    DESCRIPTION
--        " The domain name of VISM card. This is required for each VISM 
--          card as part of the EndPointID which is used as a parameter 
--          in SGCP commands issued from the Call agent. 
--        "
--    ::= { vismConfig 5 }


-- ------------------------------------------------------------------
--
-- vismVoIPGrp group
--
-- This group contains objects that are specific to VoIP. 
--
-- ------------------------------------------------------------------

vismBearerTos    OBJECT-TYPE
    SYNTAX  INTEGER (0..255)
    ACCESS  read-write
    STATUS  mandatory
    DESCRIPTION
        " This object is used to provision the bitmask used for the
          TOS (Type Of Service) octet for cells carrying VoIP bearer 
          (RTP ) traffic.
          Default value 160 = 0xA0 => Precedence = 5 and TOS nibble = 0
          The bitmask can be only a byte value.
        "
    DEFVAL { 160 }
    ::= { vismVoIpGrp 1 }





vismRtcpRepInterval OBJECT-TYPE
    SYNTAX  INTEGER (500..15000)
    ACCESS  read-write
    STATUS  mandatory
    DESCRIPTION
        " This attribute defines the RTCP report interval (
          defined in RFC 1889). This indicates the interval at which
          the RTCP reports should be sent to the participating members. The
          value is expressed in units of milliseconds. The RTCP reports are not
          sent at a fixed rate at this interval. Rather, this value is used as
          a base value to arrive at a random number between 0.5 and 1.5 times
          this value.
 
          This interval timer also serves the purpose of RTP packets receive
          timer. At every 'vismRtcpRecvMultiplier' times this interval, where
          'vismRtcpRecvMultiplier'is specified in the MIB object below, a check
          is made on a VoIP connection (which is in SENDRECV or RECVONLY xGCP
          modes) to see if any RTP packets have been received. If not,
          gateway-initiated DLCX should be sent to the Call Agent.
 
          Currently, this interval timer is a card-specific value, which means
          the value is configurable on a per card basis and not on a per call
          basis.
	
          This value is applicable for VoIP adaptation only.

          From vism 2.0.3 release onwards this object can be configured in any
          mode/adaptations, but will be applicable only in voip adaptation.
        "
    DEFVAL {5000}
    ::= { vismVoIpGrp 2 }




vismRtpReceiveTimer OBJECT-TYPE
    SYNTAX  INTEGER {
            disable (1),
            enable (2)
            }
    ACCESS  read-write
    STATUS  mandatory
    DESCRIPTION
        "
        This object defines whether the RTP packets receive timer on the VISM
        needs to be enabled or not. For some VoIP applications (as in 
        South Carolina release), if a connection is in send-recv mode or 
        recv-only mode, after the bearer cur-through is done, the RTP stream
        should be monitored for RTP packets. If there are no packets received
        within a time interval specified by 5 seconds, then a Gateway initiated
        DLCX (Delete connection) should be sent on that connection.

        If this object is set to enable, the RTP stream is monitored. 
        Otherwise, it is not monitored.

        This value is applicable for VoIP adaptation only. 
        From vism 2.0.3 release onwards this object can be configured in any
        mode/adaptations, but will be applicable only in voip adaptation.

        "
    DEFVAL {disable}
    ::= { vismVoIpGrp 3 }

--VISM1.53
-- This object is deprecated as we have a seperate per codec packetization
-- period table

vismPacketizationPeriod    OBJECT-TYPE
    SYNTAX  INTEGER {
            tenms     (10),
            twentyms  (20),
            thirtyms  (30),
            fourtyms  (40)
            }
    ACCESS  read-only
    STATUS  deprecated
    DESCRIPTION
        " This object is used to provision the packetization period
          to be applied.
          This object is applicable for VoIP adaptation only. For 
          VoAAL2 adaptations, the packetization period is derived from
          the profile table entry. For VoAAL1 adaptation, it is fixed
          at 5.875 ms.

        "
    DEFVAL { tenms }
    ::= { vismVoIpGrp 4 }

--VISM1.53
--
vismVoIpDtmfRelay  OBJECT-TYPE
    SYNTAX    TruthValue
    ACCESS    read-write
    STATUS    mandatory
    DESCRIPTION
        "
          This attribute defines whether the DTMF (Dual Tone, Multi-Frequency)
          digits need to be transported to the other endpoint via NSE packets.

          The value in this object will be utilised when the Call Agent does
          not specify this. 
        "
        DEFVAL { true }
      ::= {vismVoIpGrp 5}

vismVoIpCasTransport OBJECT-TYPE
    SYNTAX    TruthValue
    ACCESS    read-write
    STATUS    mandatory
    DESCRIPTION
        "This attribute defines whether the CAS (ABCD bits) bits need to be
         transported to the other endpoint via NSE packets.

        The value in this object will be utilized when the Call Agent does not
        specify this. 
        "
       DEFVAL {false}
      ::= {vismVoIpGrp 6}

vismVoIpTripleRedundancy  OBJECT-TYPE
    SYNTAX    TruthValue
    ACCESS    read-write
    STATUS    mandatory
    DESCRIPTION

        "This attribute defines whether triple redundancy is enabled or not.
         With triple redundancy, NSEs are sent three times at 20 ms intervals.
         For reliable channels, triple redundancy can be disabled in order to
         save the bandwidth and the processing overheads.

         The value in this object will be utilized when the Call Agent does not
         specify this. 
        "
       DEFVAL {false}
      ::= {vismVoIpGrp 7}

vismVoIpVADTimer OBJECT-TYPE
    SYNTAX    INTEGER(250..65535)
    ACCESS    read-write
    STATUS    mandatory
    DESCRIPTION
        "This attribute defines the hangover time for VAD in milliseconds.
         Once the voice inactivity is detected, the gateway will wait for
         this duration before activating silence suppression. 

         The value in this object will be utilized when the Call Agent does
         not specify this. 
        "
        DEFVAL { 250 }
        ::= {vismVoIpGrp 8}

vismVoIpNTECapabilityNegotiate  OBJECT-TYPE
    SYNTAX    TruthValue
    ACCESS    read-write
    STATUS    mandatory
    DESCRIPTION
        "
          This attribute defines whether the VISM has the capability to 
          negotiate the list of events either NSE (Named Signal Event)
          or NTE (Named Telephony Events), using rtpmap and fmtpmap in
          the SDP. 
          
          If the value is TRUE, then VISM will include / accept rtpmap 
          and fmtpmap in the SDP. Any events NSE / NTE not listed will
          be interpreted as not supported.

          If the value is FALSE, then VISM will neither include nor
          accept rtpmap for X-NSE & X-NTE, and fmtpmap. For the backward 
          compatibility sake VISM will transmit DTMF digits using NSEs
          if the value is FALSE
        "
        DEFVAL { true }
      ::= {vismVoIpGrp 9}

vismVoIpSIDPayloadType  OBJECT-TYPE
    SYNTAX    INTEGER(0..255)
    ACCESS    read-write
    STATUS    mandatory
    DESCRIPTION
        "This attribute sets the payload type of a RTP packet carrying SID
         which is sent to the other end when silence is detected. The default 
         value is in accordance to the earlier revisions of 
         draft-ietf-avt-provile-new-10.txt
        "
         DEFVAL { 13 }
         ::= {vismVoIpGrp 10}

vismVoIpDPvcOamCellGap OBJECT-TYPE
    SYNTAX    INTEGER(10..5000)
    ACCESS    read-write
    STATUS    mandatory
    DESCRIPTION
        "This attribute defines the inter cell gap for dual PVC OAM cells.
         The value represents the time in milliseconds.
        "
        DEFVAL { 500 }
        ::= {vismVoIpGrp 11}

vismVoIpDPvcRetryCnt OBJECT-TYPE
    SYNTAX    INTEGER(1..20)
    ACCESS    read-write
    STATUS    mandatory
    DESCRIPTION
        "This attribute defines the threshold for failure of a PVC. If the
         number of consecutive OAM cells sent for which no ack was received
         equals this number then the connection is considered failed.
        "
        DEFVAL { 3 }
        ::= {vismVoIpGrp 12}

vismVoIpDPvcRecoverCnt OBJECT-TYPE
    SYNTAX    INTEGER(1..20)
    ACCESS    read-write
    STATUS    mandatory
    DESCRIPTION
        "This attribute defines the threshold for recovery of a PVC. If
         the number of consecutive OAM cells sent for which ack was received 
         equals this number then the connection is considered recovered 
         from failure.
        "
        DEFVAL { 5 }
        ::= {vismVoIpGrp 13}

vismRtcpRecvMultiplier OBJECT-TYPE
    SYNTAX  INTEGER (1..10)
    ACCESS  read-write
    STATUS  mandatory
    DESCRIPTION
        " The 'vismRtcpRepInterval' MIB object specified above defines an 
          approximate RTCP report interval (defined in RFC 1889) which indicates
          the interval in milliseconds at which the RTCP reports should be sent
          to the participating members. 
 
          This MIB object, 'vismRtcpRecvMultiplier', defines how many times the
          RTCP reports may fail before exception condition activity may be done.
          At this number of times specified in this MIB object times the RTCP
          Report Interval, a check is made on a VoIP connection (which
          is in SENDRECV or RECVONLY xGCP modes) to see if any RTP packets
          have been received. If not, gateway-initiated DLCX should be
          sent to the Call Agent.
 
          Currently, this interval multiplier is a card-specific value, which
          means the value is configurable on a per card basis and not on a per
          call basis.
	
          This value is applicable for VoIP adaptation only.

        "
    DEFVAL {3}
    ::= { vismVoIpGrp 14 }

vismVoIpLapdTrunkPVC OBJECT-TYPE
    SYNTAX  INTEGER {
            control (1),
            bearer (2)
            }
    ACCESS  read-write
    STATUS  mandatory
    DESCRIPTION
        "This object should be used for VoIP Trunking applications and only
         if the signalling type is configured to be CCS. By default the PRI
         D-channel information will be sent on the control channel. If the 
         control network is totally seperated from the bearer network then
         the user needs to set this object to 'bearer' to send his Lapd trunk
         messages to the remote VISM. 
        "
        DEFVAL { control }
        ::= {vismVoIpGrp 15}

vismVoIpEventNegotiationPolicy  OBJECT-TYPE
    SYNTAX    INTEGER {
              none (1),
              proprietary (2),
              all (3)
              }
    ACCESS    read-write
    STATUS    mandatory
    DESCRIPTION
        "
          This attribute defines whether or not the VISM should advertise 
	  the event codecs, NSE (Named Signal Events), NTE (Named Telephony 
	  Events), or Cisco-rtp, in addition to the list of events specified 
	  by the call agent.

          If the value is none, then VISM will not include any more event 
	  codecs than what has been specified by the call agent.

          If the value is proprietary, then VISM can advertise proprietary 
	  event codecs in addition to the event codecs specified by the call 
	  agent.

          If the value is all, then VISM can advertise both proprietary as well
	  as standard event codecs in addition to the event codecs specified by 
	  the call agent.
        "
        DEFVAL { proprietary }
      ::= {vismVoIpGrp 16}



--
-- ------------------------------------------------------------------
--
-- vismDspGrp group
--
-- This group contains objects that are used manage DSPs on the VISM card.
--
-- ------------------------------------------------------------------

-- VISM1.53
-- Deprecated the following two objects as it was never used !!
vismEcanCnfIdlePattern    OBJECT-TYPE
    SYNTAX  INTEGER {
            pattern1 (1),
            pattern2 (2),
            pattern3 (3),
            pattern4 (4)
            }
    ACCESS  read-only
    STATUS  deprecated
    DESCRIPTION
        " Echo Canceller pattern for Idle code.
          Mu-Law : 1 - 7f,   2 - ff, 3 - 7f or ff, 4 - f7
          A-Law  : 1 - None, 2 - 54, 3 - 55, 4 - Programable Idle code.
          DEFVAL : pattern3 (7f or ff) for Mu-law and
                   pattern2 (54) for A-Law.
        "
    ::= { vismDspGrp 1 }
 
vismEcanCnfIdleDirection    OBJECT-TYPE
    SYNTAX  INTEGER {
            both    (1),
            either  (2),
            send    (3),
            receive (4)
            }
    ACCESS  read-only
    STATUS  deprecated
    DESCRIPTION
        " Echo Canceller Idle Direction. This determines in 
          which direction the Idle code must be present.
        "
    DEFVAL { both }
    ::= { vismDspGrp 2 }
-- VISM1.53

vismCompCnfPacketSize    OBJECT-TYPE
    SYNTAX  INTEGER (80..160)
    ACCESS  read-write
    STATUS  mandatory
    DESCRIPTION
        " Compressed output packet size - This value is used in the DSP
          interface API commands to configure the DSPs for the maximum
          packet size.
          The valid values are 80 and 160 only.
	  NOTE: This object is not used currently.
          In future it is applicable only if the mode is VoAAL1.

          From vism 2.0.3 release onwards this object can be configured in any
          mode/adaptations, but will be applicable only in aal1 adaptation.
        "
    DEFVAL { 80 }
    ::= { vismDspGrp 3 }

vismERL    OBJECT-TYPE
    SYNTAX  INTEGER {
            zerodb  (1),
            threedb (2),
            sixdb   (3),
            worstdb (4)
            }
    ACCESS  read-write
    STATUS  mandatory
    DESCRIPTION
        " This object is used to provision the return echo lost, 
          i.e the db loss of the echo that the DSPs are supposed 
          to cancel.
        "
    DEFVAL { sixdb }
    ::= { vismDspGrp 4 }

 
--
-- The following object is deprecated in RI release because per codec
-- based vismCodecJitterDelayMode is introduced
--
vismJitterDelayMode    OBJECT-TYPE
    SYNTAX  INTEGER {
            fixed     (1),
            adaptive  (2)
            }
    ACCESS  read-write
    STATUS  deprecated
    DESCRIPTION
         " This object is used to provision the jitter buffer mode
           to be apply to a call connection. 
           The possible values are:
           fixed   - means use a constant jitter buffer size, which 
                     is defined by the vismJitterInitialDelay mib 
                     variable.
           adaptive - means let the DSP pick the optimal value for 
                     the call connection.
         "
    DEFVAL { fixed }
    ::= { vismDspGrp 5 }

 
--
-- The following object is deprecated in RI release because per codec
-- based vismCodecJitterInitialdelay is introduced
--
vismJitterInitialDelay    OBJECT-TYPE
    SYNTAX  INTEGER {
            zero       (1),
            five       (5),
            ten        (10),
            fifteen    (15),
            twenty     (20),
            twentyfive (25),
            thirty     (30),
            thirtyfive (35),
            fourty     (40),
            fortyfive (45),
            fifty      (50),
            fiftyfive  (55),
            sixty      (60),
            sixtyfive  (65),
            seventy    (70),
            seventyfive (75),
            eighty     (80),
            eightyfive (85),
            ninty      (90),
            ninetyfive  (95),
            hundred    (100)
            }
    ACCESS  read-write
    STATUS  deprecated
    DESCRIPTION
         " Defines the jitter buffer size. If the  vismJitterDelayMode 
           is set to be fixed, the jitter buffer is fixed at this value 
           for the call. If vismJitterDelayMode is adaptive, this is 
           the initial jitter  buffer size, and the DSP will adapt to 
           an optimal size.

           The range 10,20,30,40,50,60,70,80,90,100 is applicable to
           1.5 release only.

           The range 1,5,10,15,20,25,30,35 .... is applicable from vism2.0
           release onwards.
 
           The valid range for template 1 : 1,10,20,30,40,50,60,70,80,90,100
           The valid range for template 2 : 1,5,10,15,20,25,30,35,40,45,50,
                                            55,60,65,70,75,80,85,90,95,100.

           When the template of the card changes, either from template 1
           to 2 or vice versa the value of this object will be implicitly
           set to default value.
 
         "
    DEFVAL { fourty }
    ::= { vismDspGrp 6 }

 
vismAdaptiveGainControl    OBJECT-TYPE
    SYNTAX  INTEGER {
            off    (1),
            on     (2)
            }
    ACCESS  read-write
    STATUS  mandatory
    DESCRIPTION
         "If set to on, the DSP will adjust the gain of the
          of the call connection to an optimal value.
         "
    DEFVAL { off }
    ::= { vismDspGrp 7 }

vismDspHealth OBJECT-TYPE
    SYNTAX  INTEGER 
    ACCESS  read-only
    STATUS  mandatory
    DESCRIPTION
        " This attribute indicates the health of the DSPs. It is a 
          percentage of the total number of DSPs that are currently 
          functional. Currently No action is planned upon the failure 
          of a DSP chip in a card, other than resetting the card.
        "
    ::= { vismDspGrp 8 }

-- vismEcanDspCnt    OBJECT-TYPE
--    SYNTAX  INTEGER (0..12)
--    ACCESS  read-write
--    STATUS  mandatory
-- obsolete
-- This object is replaced by the CodecTemplate
--    DESCRIPTION
--        " No. of Echo Canceller DSPs the VISM card need to be configured with
--          from a pool of 12 multi-purpose DSPs. Remaining DSPs are used for
--          compression.
--        "
--    DEFVAL { 12 } 
--    ::= { vismDspGrp 9 }
--
--vismEcanCnfNR    OBJECT-TYPE
--    SYNTAX  INTEGER {
--            restoreOnLowEnergy (1),
--            restoreOnCallEnd   (2)
--            }
--    ACCESS  read-write
--    STATUS  mandatory
-- obsolete
-- This object is not provisionable any more
--    DESCRIPTION
--        " Echo Canceller NR (Non Linear Processor Re-enable).
--          1 - Restore NLP on low energy
--          2 - Restore NLP on end of call.
--          This parameter is applicable only when ToneDisable=G.165.
--          NLP is also known as Noise Matching.
--        "
--    DEFVAL { restoreOnLowEnergy }
--    ::= { vismDspGrp 10 }
-- 
--vismEcanCnfNoiseMatch    OBJECT-TYPE
--    SYNTAX  INTEGER {
--            randomize (1),
--            inject    (2)
--            }
--    ACCESS  read-write
--    STATUS  mandatory
-- obsolete
-- This object is not provisionable any more
--    DESCRIPTION
--        " Echo Canceller Noise Matching.
--          1 - Phase randomize low level residual
--          2 - Inject noise in place of low level residual.
--        "
--    DEFVAL { randomize }
--    ::= { vismDspGrp 11 }
-- 
--
vismUpspeedCodec  OBJECT-TYPE
      SYNTAX     INTEGER {
                g-711u   (1),
                g-711a   (2),
                g-726-32 (3),
                clearChannel (4),
                g-723h    (5),
                g-723l    (6),
              	g-726-16 (7),
                g-726-24 (8),
                g-726-40 (9)
              }
       ACCESS  read-write
       STATUS  mandatory
       DESCRIPTION 
            "
              This object specifies the codec to be used when 
              fax upspeed happens.
            
              The default value for this object is G.711u when
              the line type is T1 and G.711a when the line type is
              E1

              This object is applicable only in the case of 
              VOIP applications, for AAL2 the upspeedCodec is obtained
              from profile table and this object will have no
              affect.
            "
        ::= {vismDspGrp 9}


vismPayloadType  OBJECT-TYPE
       SYNTAX    INTEGER (0..256) 
       ACCESS    read-write
       STATUS    mandatory
       DESCRIPTION
            "
              This object specifies the payload type to be used when
              fax upspeed happens.

              IANA values (0..95) are static payload and (96..127) are
              dynamic payload type.

              This object is applicable only in the case of
              VOIP applications, for AAL2 the upspeedCodec is obtained
              from profile table and this object will have no
              affect.
            "
        DEFVAL { 256 }
        ::= {vismDspGrp 10}
 
-- ------------------------------------------------------------------
--
-- vismSystemGrp group
--
-- This group contains objects that are specific to the card. 
--
-- ------------------------------------------------------------------
 
vismDaughterCardSerialNum    OBJECT-TYPE
    SYNTAX  DisplayString (SIZE (0..6))
    ACCESS  read-only
    STATUS  mandatory
    DESCRIPTION
        " A unique value for each VISM daughter card, entered in nvram
          by manf. The serial No. is on the non-volatile RAM on the
          VISM daughter card.
        "
    ::= { vismSystemGrp 1 }
 
vismDaughterCardDescription    OBJECT-TYPE
    SYNTAX DisplayString (SIZE (0..20))
    ACCESS read-only
    STATUS mandatory
    DESCRIPTION
        " Describes the VISM daughter card.
        "
    ::= { vismSystemGrp 2 }

vismDaughterCardHWRev    OBJECT-TYPE
    SYNTAX DisplayString (SIZE (0..2))
    ACCESS read-only
    STATUS mandatory
    DESCRIPTION
        " Hardware revision number for the daughter card.
        "
    ::= { vismSystemGrp 3 }


vismEcanEncoding    OBJECT-TYPE
    SYNTAX  INTEGER {
            mu-law (1),
            a-law  (2)
            }
    ACCESS  read-only
    STATUS  mandatory
    DESCRIPTION
        " Voice encoding type, Mu-law or A-law. 
          mu-law is returned for T1 lines and a-law is returned for E1 lines.
        "
    ::= { vismSystemGrp 4 }

vismMode OBJECT-TYPE
    SYNTAX  INTEGER {
                voipSwitching          (1),
                aal2Trunking           (2),
                aal1Svc                (3),
-- <Ignored
                switchedVoipCASBh      (4),
                switchedVoipPRIBh      (5),
                switchedAal2CASBh      (6),
-- Ignored>
                switchedAal2Svc        (7),
                switchedAal2Pvc        (8),
                voipAndAal1Svc         (9),
-- <Ignored
                superMode              (99),
-- Ignored>
                unknownMode            (100)
                }
    ACCESS  read-only
    STATUS  mandatory
    DESCRIPTION
        " This attribute defines the connection model that the VISM card
          is configured to operate with. This object can be modified by
          CLI only. The CLI 'cnfvismmode' can be used to set this object.
          VISM card will be reset after modifying this parameter
          for the VISM card to come up in the new mode.

          Each mode enables a set of features on the VISM card.

          The feature set for each of the above modes is :
          voipSwitching - VoIP mode. In this mode VISM interacts
                          with the Call Agent using XGCP protocol,
                          bearer path is VoIP (AAL5). This mode is also 
                          used for VoIP applications that dosen't use 
                          call agent. (VoIP Trunking)
          aal2Trunking  - AAL2 Trunking mode. In this mode VISM does not
                          interact with the Call Agent. Bearer Path is AAL2.
          aal1Svc       - AAL1 SVC mode. In this mode VISM interacts with
                          Call Agent using XGCP protocol over AAL5 control
                          PVCs. In this mode, bearer path is VoAAL1 and the
                          bearer connections are SVCs. i.e VISM dynamically
                          sets-up and tears down bearer connections. This
                          value is applicable in VISM2.0 and onwards.
          switchedVoipCASBh, switchedVoipPRIBh, switchedAal2CASBh,
          switchedAal2Svc and  superMode are ignored.

          switchedAal2Pvc - Switched and trunked AAL2 PVC with CAS xGCP
                            backhaul, CCS and CAS forwarding.

          switchedAal2Svc - Switched AAL2 SVC with PRI backhaul.

          voipAndAal1Svc - VoIP and ATM Groomer.

          unknowMode - Unknown mode, when user change vismFeatureBitMap
                       to a combination of Features that are not in
                       the above modes.

          This object has to be synchronized with vismFeatureBitMap.
          When vismFeatureBitMag is changed this object will be implictly
          set to the mode that has the right combination of features.
          From Indiana release and onwards, when user change mode VISM
          card is not reset and the configuration is not cleared.


        "
    DEFVAL { voipSwitching }
    ::= { vismSystemGrp 5 }

vismPrevMode OBJECT-TYPE
    SYNTAX  INTEGER {
                voipSwitching (1),
                aal2Trunking  (2),
                aal1Svc       (3),
                aal2PvcSwitching (4)
                }
    ACCESS  read-only
    STATUS  deprecated
    DESCRIPTION
        " This attribute indicates the mode in which VISM was operating
          before the vismMode value was changed. i.e It gives the value
          of vismMode before it got changed to the current value.

          When the card comes up in the default mode, the value of
          vismPrevMode will be the same as vismMode.
          From Indiana release and onwards, when user change mode VISM
          card is not reset and the configuration is not cleared. 
          Therefore we don't need this object anymore.
        "
    DEFVAL { voipSwitching }
    ::= { vismSystemGrp 6 }


vismCacEnable OBJECT-TYPE
    SYNTAX  INTEGER {
			disable (1),
			enable (2)
			}
    ACCESS  read-write
    STATUS  mandatory
    DESCRIPTION
        " This attribute describes whether CAC (Connection Admission Control)
	  functionality needs to be applied on the VISM card, on a per PVC
	  basis. For some applications, the CAC functionality may not be 
	  required and in that case, it has to be disabled on a card basis.
        "
    DEFVAL { enable }
    ::= { vismSystemGrp 7 }

vismAvailableDs0Count OBJECT-TYPE
    SYNTAX  INTEGER (0..248)
    ACCESS  read-only
    STATUS  mandatory
    DESCRIPTION
        " This attribute describes the no. of DS0s available for new
 	  connections on VISM. This is modified by the VISM firmware 
	  after each connection is setup.
          In indiana release the number of connections has been
          increased to 248, as the number of endpoints supported has 
          been increased.
        "
    ::= { vismSystemGrp 8 }


vismAppliedTemplate OBJECT-TYPE
    SYNTAX  INTEGER 
    ACCESS  read-only
    STATUS  mandatory
    DESCRIPTION
        " This attribute describes the Codec template currently configured
	  on the VISM card. The value refers to an index to the 
          vismCodecTemplate table. This template is applicable for all 
          connections on the card.

          When a switch is made to a new template, the number of channels
          (endpoints) in use will be checked to ensure the switch will not
          occur if there are more endpoints active at the present time than
          what the new template (vismCodecTemplateMaxChanCount) allows.

          Also whenever an attempt is made to add a new endpoint for any
          template, this template maximum number will limit the number of
          endpoints that may be added for this template.

        "
    ::= { vismSystemGrp 9 }


-- 
-- This object has been obsoleted (1.53)
--
--
-- vismNsapAddress    OBJECT-TYPE
--     SYNTAX  OCTET STRING (SIZE (1 | 4..21)) 
--     ACCESS  read-write
--     STATUS  deprecated
--     DESCRIPTION
--         " VISM NSAP Address - Required for VoATM. Each VISM card acts 
--           as an ATM UNI CPE and hence needs NSAP address. 
--         "
--     ::= { vismSystemGrp 10 }
--


vismTftpServerDn     OBJECT-TYPE
    SYNTAX     DisplayString (SIZE (1..64))
    ACCESS     read-write
    STATUS     mandatory
    DESCRIPTION

         "
          This object holds the domain name of the tftp server from where
          the cas module will download the cas files. 
 
          This domain name can be resolved internally or externally. 
          Before configuring this object the domain name should be added 
          in the mgDomainNameTable and at least one Ip address (internal 
          or external) should be associated with this domain name in 
          mgcResolutionTable.

          By default, the object is set to TFTPDOMAIN. 

          Before the last entry corresponding to the tftp domain is deleted 
          from the mgDomainNameTable or the last Ip address associated with
          this object is deleted from mgcResolutionTable, it should be set
          to 'TFTPDOMAIN'.

          If the user configures 'localhost' to be the tftp server domain 
          then the cas files will be downloaded from PXM.
          
          If the user configures the domain name to be TFTPDOMIAN or 
          localhost then that entry need not be present in 
          mgDomainNameTable or mgcResolutionTable.
         "
       ::= {vismSystemGrp 11}

-- VISM1.53

vismXgcpBearerNetworkType    OBJECT-TYPE
   SYNTAX    INTEGER {
                ip (1),
                atm (2)
              }
   ACCESS    read-write
   STATUS    mandatory
   DESCRIPTION
        "
          This object specifies the network type to use in order to transport
          bearer traffic.
          The user can configure this to IP or ATM based on where the VISM
          will be located. 
           
          If the call agent specifies the network type in the MGCP local
          connection options (CRCX request), then the configuration of 
          this object will have no effect, else the value of this object
          will be used when sending CRCX response. 

          This object is applicable only from vism 2.0.3 release onwards.
       "
   DEFVAL{ip}
    ::= {vismSystemGrp 12}

vismXgcpBearerVCType           OBJECT-TYPE
    SYNTAX      INTEGER {
                 pvc (1),
                 svc (2)
               }
    ACCESS     read-write
    STATUS     mandatory
    DESCRIPTION
      "
        This object specifies the vc type to use in order to transport bearer
        traffic.

        If the call agent specifies the VC type in the MGCP local
        connection options (CRCX request), then the configuration of this
        object will have no effect, else the value of this object will be
        used when sending CRCX response.
        
        This object is applicable only from vism 2.0.3 release onwards.
     "
    DEFVAL{pvc}
     ::= {vismSystemGrp 13}

vismXgcpBearerConnectionType   OBJECT-TYPE
   SYNTAX      INTEGER {
                 aal1Sdt (1),
                 aal2     (2),
                 notApplicable (3)
               }
   ACCESS      read-write
   STATUS      mandatory
   DESCRIPTION
       "
         This object specifies the connection type used to transport 
         bearer traffic. If the BearerNetworkType is chosen to be IP 
         then the value of this object has to be/will be set to not-applicable.
  
         If the call agent specifies the connection type in the MGCP local
         connection options (CRCX request), then the configuration of this
         object will have no effect, else the value of this object will be
         used when sending CRCX response.
        
         This object is applicable only from vism2.0.3 release onwards.
       "
   DEFVAL{notApplicable}
   ::= {vismSystemGrp 14}

vismBearerContinuityTimer    OBJECT-TYPE
    SYNTAX       INTEGER (0 .. 10000)
    ACCESS       read-write
    STATUS       mandatory
    DESCRIPTION
       "
         This object specifies the co4 (bearer continuity) timer in
         millisecs.

         The timer will be started in the terminating/orginating
         gateway for a duration as specified in this MIB object  when a 
         co3 message is sent from the terminating/orginating gateway to the 
         originating/terminating gateway.

         If the terminating/originating gateway does not receive co4 as an 
         acknowledgement from the originating/termintaing gateway and the timer expires,  
         gateway initiated DLCX is sent to the call agent from the terminating/originating
          gateway.

         This object is applicable when the call agent feature is available.
       " 
       DEFVAL{1000}
      ::={vismSystemGrp 15}

vismCodecNegotiationOption  OBJECT-TYPE
     SYNTAX INTEGER {
            lcoRcdLcl   (1),
            lcoLclRcd   (2),
            rcdLcoLcl   (3),
            rcdLclLco   (4),
            lclLcoRcd   (5),
            lclRcdLco   (6)
          }
     ACCESS  read-write
     STATUS  mandatory
     DESCRIPTION
           "
             This object helps in forming an ordered intersection
             of lists and one of the lists must be used in determining
             the resulting order of codecs.
 
              Lco - local connection options
              Rcd - remote connection description
              Lcl - local codec list 

             If the value of this object is 1 then effectively
             we are giving first priority to the local connection options
             sent by the Call Agent, followed by remote connection
             description sent by the remote gateway (CA) and the last 
             priority will be to local codec list stored in vism.

             If the value of this object is 2 then effectively we are
             giving first priority to local connection options sent
             by the call agent, followed by local codec list stored 
             in vism and the last priority will be to remote connection
             description sent by the remote gateway (or remote CA).
             
             If the value of this object is 3 then  effectively we are
             giving first priority to remote connection description sent
             by the remote gateway /call agent, followed by local 
             connection options sent by the call agent and the last priority 
             will be to the local codec list stored on the local gateway(vism).

             If the value of this object is 4 then effectively we are
             giving first priority to remote connection description sent
             by the remote gateway/CA followed by local codec list stored 
             on the local gateway and the last priority will be to the local
             connection options sent by the CA.

             If the value of this object is 5 then effectively we are
             giving first priority to local codec list stored on the
             local gateway (vism) followed by local connection options 
             sent by the call agent and the last priority will be
             to remote connection description sent by the remote gateway
             (or remote CA). 

             If the value of this object is 6 then effectively we are
             giving first priority to local codec list stored on the 
             vism followed by remote connection description sent by the
             remote gateway (or remote CA) and the last priority will be to 
             local connection options sent by the call agent.

           "
           DEFVAL {lcoRcdLcl}
          ::= {vismSystemGrp 16}

vismProfileNegotiationOption  OBJECT-TYPE
SYNTAX INTEGER { 
            lcoRcdLcl   (1),
            lcoLclRcd   (2),
            rcdLcoLcl   (3),
            rcdLclLco   (4),
            lclLcoRcd   (5),
            lclRcdLco   (6)
          }
     ACCESS  read-write
     STATUS  mandatory
     DESCRIPTION
           "
             This object helps in forming an ordered intersection 
             of lists and one of the lists must be used in determining
             the resulting order of profiles.


              Lco - local connection options
              Rcd - remote connection description
              Lcl - local codec list

             If the value of this object is 1 then effectively
             we are giving first priority to the local connection options
             sent by the Call Agent, followed by remote connection
             description sent by the remote gateway (CA) and the last
             priority will be to local codec list stored in vism.

             If the value of this object is 2 then effectively we are
             giving first priority to local connection options sent
             by the call agent, followed by local codec list stored
             in vism and the last priority will be to remote connection
             description sent by the remote gateway (or remote CA).
            
             If the value of this object is 3 then  effectively we are
             giving first priority to remote connection description sent
             by the remote gateway /call agent, followed by local
             connection options sent by the call agent and the last priority
             will be to the local codec list stored on the local gateway(vism).

             If the value of this object is 4 then effectively we are
             giving first priority to remote connection description sent
             by the remote gateway/CA followed by local codec list stored
             on the local gateway and the last priority will be to the local
             connection options sent by the CA.

             If the value of this object is 5 then effectively we are
             giving first priority to local codec list stored on the
             local gateway (vism) followed by local connection options
             sent by the call agent and the last priority will be
             to remote connection description sent by the remote gateway
             (or remote CA).

             If the value of this object is 6 then effectively we are
             giving first priority to local codec list stored on the
             vism followed by remote connection description sent by the
             remote gateway (or remote CA) and the last priority will be to
             local connection options sent by the call agent.

           "
           DEFVAL {lcoRcdLcl}
          ::= {vismSystemGrp 17}

vismCarrierLossPolicy    OBJECT-TYPE
       SYNTAX    INTEGER {
                              previousCodec (1),
                              upspeedCodec  (2)
                         }
       ACCESS   read-write
       STATUS   mandatory
       DESCRIPTION
            "
               This object defines the policy that needs to be applied
               when a carrier loss is detected.

               This states whether to switch to the pre-upspeed codec or
               to remain with the upspeed codec.

               This object is applicable in case of SVCs. This object
               will be applicable in case of PVC if the per PVC object -
               vismChanCarrierLossPolicy (defined in vismChanCacTable)
               is set to 'unspecified'.

               Configuring this object will not have any affect when
               card level cac is disabled (vismCacEnable).
            "
       DEFVAL { previousCodec }
      ::= {vismSystemGrp 18}

vismCacRejectionPolicy   OBJECT-TYPE
    SYNTAX    INTEGER {
                        delete (1),
                        maintain (2)
                      }
    ACCESS    read-write
    STATUS    mandatory
    DESCRIPTION
        "This attribute defines the policy that needs to be applied
         once the CAC function rejects the upspeeding of a connection,
         due to a fax/modem switch-over request. The applicable options
         are:
         1 - To delete the connection that got rejected by CAC for upspeed
         2 - To maintain the connection with the prior compression scheme.
          This object is applicable in case of SVCs . This object will be
          applicable in case of PVCs if the per PVC object -
          vismChanCacRejectionPolicy (defined in vismChanCacTable) is set to
          'unspecified'.

          Configuring this object will not have any affect when
          card level cac is disabled (vismCacEnable).

        "
    DEFVAL{maintain}
    ::= {vismSystemGrp  19}

vismExtDnsServerDn     OBJECT-TYPE
    SYNTAX     DisplayString (SIZE (1..64))
    ACCESS     read-write
    STATUS     mandatory
    DESCRIPTION
         "
          This object refers to the domain name of the external DNS server
          which will be used to resolve other domain name.
 
          Currently this domain name can only be resolved internally. 
          Therefore, before configuring this object not only
          the domain name has to be added in the mgDomainNameTable with
          resolution type 'internalOnly' but also at least one IP address 
          has been added with this domain name in mgcResolutionTable.

          Before deleting external DNS server from mgDomainNameTable or
          deleting the last IP address associated with the external DNS
          server this object should be set to 'NULL'. After we change
          the value of this object to NULL, all the externally resolved
          IP address in mgcResolutionTable will be purged. 

          By default this object will be set to 'NULL'.
         "
       ::= { vismSystemGrp 20 }

vismFeatureBitMap OBJECT-TYPE
    SYNTAX  INTEGER 
    ACCESS read-write
    STATUS mandatory
    DESCRIPTION
        "This object denotes the bit map for VISM features. It indicates
         the current features that are enabled. It should be consistant
         with vismMode. When user change vismMode, this object is 
         implicitly set to the feature combination that inidicate to 
         that mode. The change of vismFeatureBitMap will not cause VISM
         to reset and the configuration will not be cleared.

         For each bit, value 1 means the feature is enabled, 0 means
         disabled.
         Bit 0 - AAL1 adaptation         
         Bit 1 - AAL2 adaptation
         Bit 2 - AAL5 adaptation (Bearer network type is IP).
         Bit 3 - Switching (with Call Agent)
         Bit 4 - Trunking (without Call Agent)
         Bit 5 - Bearer VC type is PVC.
         Bit 6 - Bearer VC type is SVC.
         Bit 7 - CAS signaling
         Bit 8 - PRI backhaul
         Bit 9 - CCS signaling
         Bit 10 - Domain Name

         For example, 0x5AC corresponds to vismMode 1 (VoipSwitching).

         Currently this object is not settable, it can only be set thru
         some debug commands.
        " 
    ::= { vismSystemGrp 21 } 

vismVADTolerance  OBJECT-TYPE
       SYNTAX  INTEGER(1..10000)
       ACCESS  read-write
       STATUS  mandatory
       DESCRIPTION
           "
             The value in this object refers to the customer accepted
             drop rate for voice connections when the bandwidth usage
             exceeds allowed value.

             The actual range of this object is 0.0001% - 1.00 %

             The unit is in percentage, since the default is 0.01 %,
             and since we cannot express such fractions
             in MIB , it is being multiplied by 10000 .

             However, when the underlying CAC module is notified of
             the change in this object,  then the value
             has to be divided by a factor of 10000.

             Multiplication factor 10000 is picked as someone might be
             interested in a tolerance as low as 0.0001%.

             This object will be applicable in case of aal2 SVCs where
             the user does not add a PVC and also this object will be
             applicable if the per PVC level object (vismChanVADTolerance)
             is configured to have a value of zero.

             Configuring this object will not have any affect when
             card level cac is disabled (vismCacEnable).
         
           "
       DEFVAL {100}
       ::= {vismSystemGrp 22}

vismVADDutyCycle  OBJECT-TYPE
       SYNTAX  INTEGER (1..100)  
       ACCESS  read-write
       STATUS  mandatory
       DESCRIPTION
           "
             This object refers to the talk-spurts duty cycle.
             The unit is in percentage.
 
             When the value of this object is to be passed
             to underlying CAC module in VISM this value has to
             be divided by 100.

             This causes the actual range of this object to be 
             0.01 to 0.99 and not 0.01 to 1.00 as specified in 
             the range of values above.  Since a value of 100 
             will cause a floating point exception, this value 
             is disallowed.

             The default value is 0.61 and since we cannot
             have fractions in a MIB variable the value
             is being multiplied by 100 and is expressed as
             61.

             This object will be applicable in case of aal2 SVCs where
             the user does not add a PVC and also this object will be
             applicable if the per PVC level object (vismChanVADDutyCycle)
             is configured to have a value of zero.

             Configuring this object will not have any affect when
             card level cac is disabled (vismCacEnable).

           "
       DEFVAL {61}
       ::= {vismSystemGrp 23}

vismAggregateTrafficClipping OBJECT-TYPE
    SYNTAX  INTEGER {
            disable (1),
            enable (2)
            }
    ACCESS  read-write
    STATUS  mandatory
    DESCRIPTION
        "This attribute defines the aggregate traffic clipping policy
         which is applicable to all bearer traffic generated at VISM card.
         The applicable options are:
         1 - aggregate traffic clipping is disabled, VISM card traffic 
             management does not perform aggregate traffic clipping.
         2 - aggregate traffic clipping is enabled, VISM card traffic 
             management performs aggregate traffic clipping.

         This is applicable to only AAL2 SVC voice bearer traffic.

         When aggregate traffic clipping is enabled, VISM card can discard cells
         which are exceeding VISM card aggregate SVC bandwidth which is specified
         as vismAggregateSvcBandwidth value. 
        "
    DEFVAL { enable }
    ::= { vismSystemGrp 24 }

vismAggregateSvcBandwidth OBJECT-TYPE
    SYNTAX    INTEGER(0..100000)
    ACCESS    read-write
    STATUS    mandatory
    DESCRIPTION
        "The aggregate svc bandwidth is used for AAL2 SVC aggregate SVC
         Connection Admision Control and also used for aggregate traffic 
         clipping at VISM card when vismAggregateTrafficClipping is enabled.

         This is expressed in cells per second. This need to be configured
         for AAL2 SVC aggregate bandwidth call admision control to admit
         AAL2 SVC connections at VISM card.
        "
        DEFVAL { 0 }
    ::= { vismSystemGrp 25 }

vismBearerContinuityTest  OBJECT-TYPE
    SYNTAX    TruthValue
    ACCESS    read-write
    STATUS    mandatory
    DESCRIPTION
        "This attribute defines whether the bearer continuity test for a connection
         will be performed at the time of call setup or not.

         When the vismBearerContinuityTest is enabled, the terminating media Gateway
         initiates a NSE/type 3 packet towards the originating gateway and
         starts a timer defined by vismBearerContinuityTimer. 

         The originating gateway, on receipt of co3, responds by sending a co4 
         to the terminating end.

         If the terminating gateway doesn't receive co4 NSE/type 3 packet with in 
         the time defined by co4 timer, it initiates a GW-initiated DLCX to the call
         agent which in turn deletes the connection.
         
         The value in this object will be utilised when the Call Agent does not
         specify this.
        "
        DEFVAL {false}
    ::= {vismSystemGrp 26}

vismCaleaEnable OBJECT-TYPE
    SYNTAX  TruthValue
    ACCESS  read-write
    STATUS  mandatory
    DESCRIPTION
        " This attribute describes whether CALEA (Communication
          Assistance for Law Enforcement Agency)) functionality needs 
	  to be enabled on the VISM card. This attribute enables/disables
	  this feature at a card level. This command is only applicable 
          for CALEA enable image.
        "
    DEFVAL { false }
    ::= { vismSystemGrp 27 }

--
--
-- ------------------------------------------------------------------
--
-- vismInteropGrp group
--
-- This group contains objects which will enhance the interoperability 
-- functionalities of VISM
--
-- ------------------------------------------------------------------

vismXgcpSdpOst OBJECT-TYPE
      SYNTAX   INTEGER 
               {
                 enable (1),
                 disable (2)
               }
      ACCESS   read-write
      STATUS   mandatory
      DESCRIPTION
            "
            This object is used to enable/disable building of s=,t=,o= lines
            in SDP message.

            If this object is set to 'enable' then it indicates that the o=, s=, t=
            lines be built before sending SDP (Session Description Protocol),
            if it set to 'disable' then it indicates that the o=,s=,t= 
            parameters need not be built for SDP.

            where  o  field indicates the owner/creator and session identifier
                   s  field indicates the session name
                   t  field indicates the duration while a session is valid.
            "
            DEFVAL {enable}
        ::= {vismInteropGrp 1}


vismDynamicPT  OBJECT-TYPE
      SYNTAX   INTEGER
               {
                 enable (1),
                 disable (2)
               }
      ACCESS   read-write
      STATUS   mandatory
      DESCRIPTION
            "
            This object is used to enable / disable dynamic payload type 
            configuration on the VISM Card.
            "
            DEFVAL {disable}
        ::= {vismInteropGrp 2}

--
-- 
-- ------------------------------------------------------------------
--
-- vismTrapObj group
--
-- This group contains objects that are defined for the purpose of sending
-- in trap varbinds.
--
-- ------------------------------------------------------------------
vismConfigChangeTypeBitMap OBJECT-TYPE
    SYNTAX  INTEGER 
    ACCESS read-only
    STATUS mandatory
    DESCRIPTION
        "Configuration change Type BitMap used in vismTableChanged
         trap and vismScalarChanged trap.
 
         When used in vismTableChanged trap, the bits indicate the following:

	bit 0 set = mgcTable changed
	bit 1 set = mgEndpointTable changed
	bit 2 set = mgcResolutionTable changed 
	bit 3 set = srcpPeerTable changed
	bit 4 set = vismDsx1Table changed
	bit 5 set = vismXgcpPeerTable changed
	bit 6 set = xgcpPackageTable changed
	bit 7 set = vismChanCacTable changed
	bit 8 set = vismCasVariantTable changed
	bit 9 set = vismCasXgcpVariantTable changed
	bit 10 set = vismAal2CidCnfTable changed
	bit 11 set = dsx0VismCnfTable changed
	bit 12 set = vismHdlcChanCnfTable changed
	bit 13 set = lineAssignmentTable changed
        bit 14 set = vismCodecCnfTable changed
        bit 15 set = vismLapdTable changed
        bit 16 set = vismRudpSessionCnfTable changed
        bit 17 set = aal2ProfilesGrpTable changed
        bit 18 set = mgDomainNameTable changed
        bit 19 set = vismPortCnfGrpTable changed
        bit 20 set = mgcRedundancyGrpTable changed
        bit 21 set = mgcRedundancyGrpParamTable changed
        bit 22 set = srcpPeerGrpParamTable changed
        bit 23 set = vismRtpConnGrpTable changed
        bit 24 set = vismCodecGenParmTable changed
        bit 25 set = t38FaxRelayGrpTable changed
        bit 26 set = mgcRedundancyProtocolTable changed
        bit 27 set = vismSessionSetTable changed
        bit 28 set = vismSessionGrpTable changed

         When used in vismScalarChanged trap, the bits indicate the following:

	bit 0 set =  mediaGateway group changed
	bit 1 set =  mediaGatewayEndpoint group changed
	bit 2 set =  mediaGatewayControllerResolution group changed
	bit 3 set =  srcpAdminObjects group changed
	bit 4 set =  vismConfig group changed
	bit 5 set =  vismXgcpCoreObjects group  changed
	bit 6 set =  xgcpCoreObjects group changed
	bit 7 set =  xgcpExtensionObjects group changed
	bit 8 set =  xgcpPackageObjects group changed

	bit 9 set =  vismSvcAtmQosGrp Objects group changed
	bit 10 set =  vismSvcTrfScalingGrp Objects group changed
	bit 11 set =  vismSvcAal2CidGrp Objects group changed
	bit 12 set =  srcpAdminRetryObjects Objects group changed

	bit 13 set =  vismConfig IpGrp      group objects changed
	bit 14 set =  vismConfig VoipGrp    group objects changed
	bit 15 set =  vismConfig DspGrp     group objects changed
	bit 16 set =  vismConfig SystemGrp  group objects changed
	bit 17 set =  vismConfig Aal2Grp    group objects changed
	bit 18 set =  vismConfig InteropGrp group objects changed

	bit 19 set =  announceControlGrp Objects group changed
	bit 20 set =  vismXgcpEnhancementsObjects group changed


         default value is 0, no change
 
         This MIB makes sense only in traps. A GET
         on this may not return a Useful result.
        "
    DEFVAL { 0 }
    ::= { vismTrapObjGrp 1 }


vismTrapIntIndex1    OBJECT-TYPE
    SYNTAX  INTEGER 
    ACCESS  read-only
    STATUS  mandatory
    DESCRIPTION
        "This object is used only for the purpose of sending it in
         the trap varbind. This object is used for two purposes:

         1. When the integer index of a SMIv2 table has to be sent, 
         this object will be used instead of the actual index object. 
         The instance value of the object will be the instance value 
         of the actual index.

         2. In the config change trap trapVismTableChange, to send the
         index value of the table entry which got changed. This object
         will contain the value of the first integer index.

         The NMS applications should not depend on the implementation 
         of this object. The SNMP Requests(GET,GET-NEXT) may not be 
         valid for this object.
        "
    ::= { vismTrapObjGrp 2 }

vismTrapIntIndex2    OBJECT-TYPE
    SYNTAX  INTEGER 
    ACCESS  read-only
    STATUS  mandatory
    DESCRIPTION
        "This object is used only for the purpose of sending it in
         the trap varbind. This object is used for two purposes:

         1. This object will be used when the SMIv2 table has two 
         index objects and the 2nd object is an integer. This object 
         will be used instead of the actual second index object. The 
         instance value of the object will be the instance value of 
         the actual second index.

         2. In the config change trap trapVismTableChange, to send the
         index value of the table entry which got changed. This object
         will contain the value of the second integer index.

         The NMS applications should not depend on the implementation 
         of this object. The SNMP Requests(GET,GET-NEXT) may not be 
         valid for this object.
        "
    ::= { vismTrapObjGrp 3 }

vismTrapStrIndex1    OBJECT-TYPE
    SYNTAX  OCTET STRING (SIZE(0..66))
    ACCESS  read-only
    STATUS  mandatory
    DESCRIPTION
        "This object is used only for the purpose of sending it in
         the trap varbind. This object is used for two purposes:

         1. When the OctetString index of a SMIv2 table has to be sent, 
         this object will be used instead of the actual index object. 
         The instance value of the object will be the instance value of 
         the actual index.

         2. In the config change trap trapVismTableChange, to send the
         index value of the table entry which got changed. This object
         will contain the value of the first OctetString index.

         The NMS applications should not depend on the implementation 
         of this object. The SNMP Requests(GET,GET-NEXT) may not be 
         valid for this object.
        "
    ::= { vismTrapObjGrp 4 }

-- VISM1.53
-- ------------------------------------------------------------------
--
-- vismAal2Group 
--
-- This group contains objects that are specific to aal2 applications
-- where vismAal2SubcellMuxing and vismAal2CidFillTimer is applicable in both trunking and 
-- switching applications, while the rest of the objects
-- are applicable only in aal2 switching applications.
--
-- ------------------------------------------------------------------

vismAal2SubcellMuxing    OBJECT-TYPE
    SYNTAX  TruthValue 
    ACCESS  read-write
    STATUS  mandatory
    DESCRIPTION
         "
          This object is a card level parameter for AAL2 adaptation and 
          it identifies the mutiplexing function of the AAL2 Common Part 
          Sublayer. When it is disabled then each CPS-Packet would fill 
          only one or two cells with padding. (Partial fill cells) Note 
          that the length field for each CPS-Packet can be up to 64bytes.
          When this option is enabled then mutiple streams of CPS-Packets 
          are mutiplexed to a single ATM connection without partial fill 
          unless there is time-out. Refer to ITU-T I.363.2 for more 
          information. 
 
          When the muxing type changes if cids are present, then we need to 
          check for CAC voilation for all cids, if the CAC fails then the 
          change request will be rejected else the muxing status will be changed
          and the vismAal2MuxingTrap will be sent and the card will be reset .
          All the existing connecitons will come up in new muxing type.

          when the muxing type changes while there are no cids then the
          card will NOT be reset, but the vismAal2MuxingTrap will be sent.
         "
    ::= { vismAal2Grp 1 }
-- VISM1.53

vismAal2DtmfRelay  OBJECT-TYPE
    SYNTAX    TruthValue
    ACCESS    read-write
    STATUS    mandatory
    DESCRIPTION
        "
          This attribute defines whether the DTMF (Dual Tone Multi Frequency)
          digits need to be transported to the other end-point or not.
     
          The value in this object will be utilised when the Call Agent does 
          not specify this in CRCX.
        "
        DEFVAL { false }
      ::= {vismAal2Grp 2}

vismAal2CasTransport OBJECT-TYPE
    SYNTAX    TruthValue
    ACCESS    read-write
    STATUS    mandatory
    DESCRIPTION
        "This attribute defines whether the CAS (ABCD bits) bits need to be
        transported to the other endpoint. In the case of switching application,
        the CAS bits are backhauled to the Call Agent through xGCP-CAS protocol.
        
        The value in this object will be utilised when the Call Agent does not
        specify this in CRCX.
        "
       DEFVAL {false}
      ::= {vismAal2Grp 3}

vismAal2Type3Redundancy  OBJECT-TYPE
    SYNTAX    TruthValue
    ACCESS    read-write
    STATUS    mandatory
    DESCRIPTION
        "This attribute defines whether the triple redundancy is supported
         for type 3 packets in AAL2 SVC/PVC . When Triple redundancy is enabled , 
         the type 3 packets (CAS bits, dialled digits and user state control 
         packets) are transmitted in triplicates with an interval defined as 
         per the standards I.366.2. For channels which are quite reliable, 
         triple redundancy can be disabled in order to save the
         bandwidth and the processing overheads.

         The value in this object will be utilised when the Call Agent does not
         specify this in CRCX.
        "
       DEFVAL {true}
      ::= {vismAal2Grp 4}

vismAal2VADTimer OBJECT-TYPE  
    SYNTAX    INTEGER(250..65535)
    ACCESS    read-write
    STATUS    mandatory
    DESCRIPTION
        "This attribute defines the hangover time for VAD in milliseconds.
         Once the voice inactivity is detected, the gateway will wait for
         this duration before activating silence suppression on an AAL2 SVC/PVC.
        
         The value in this object will be utilised when the Call Agent does 
         not specify this in CRCX.
        "
        DEFVAL { 250 }
      ::= {vismAal2Grp 5}

vismAal2CidFillTimer  OBJECT-TYPE
   SYNTAX      INTEGER(5..100)
   ACCESS      read-write
   STATUS      mandatory
   DESCRIPTION
      "
      This attribute defines the time (millisecs) to wait for filling
      up the cell when the next packet is not ready.

      After waiting for the time configured in this object, the
      cell will be sent out.
      This timer has no effect when vismAal2SubcellMuxing is disabled.

      This object is applicable only for aal2 adaptations.
      "
      DEFVAL {30}
      ::= {vismAal2Grp 6}

--
-- ----------------------------------------------------------------------
-- BASIS Project MIB
--
--
-- VISM specific Channel Configuration group 
-- ------------------------------------------------------------------
-- 
-- Modification History
-- 07/23 Modified to incorporate the changes from review meeting.
-- 09/23 Removed option vbr-nrt from vismConnServiceType
-- 09/24 Changed the description of PCR to say that it can not be 
--       changed when there are active calls.
-- 11/10 Changed the description of protection related parameters
--       to say the PCR value for primary and secondary should be
--       same, primary should be added before the secondary, channel
--       should be unprotected before deleting.(CSCdp15434)
-- 11/22 vismConnPCR is mandatory parameter, hence the default values specified 
--       are not applicable. Removing the default values from the description
-- 12/28/99 Changed vismCnfChanNum, vismChanFallbackLcn from (32..279) to
--          (131..510) and vismChanNumNextAvailable from (0..279) to (0..510)
-- 12/30/99 Changed upper range for vismConnPCR, vismConnRemotePCR, 
--          vismChanScrIngress, vismChanScrEgress from 72000 to 75600                                 
-- 12/30 removed other channel type form vismChanApplication object
-- 02/14/00 modified vismConnServiceType description: vbr-rt not supported
-- 04/25/2000 added enum vbr-nrt into vismConnServiceType as it was required
--             by Indiana release. Also added vismFarEndAddressType, 
--             vismFarEndE164Address, vismFarEndGWIDAddress, 
--             vismFarEndNSAPAddress  and vismVCCI                  
-- 12/20/2001 added vismConnAdminStatus for upcon/dncon CWM requirment
-- 08/28/01 Added description for vismChanTestType - the SET request should
--          contain only this parameter
-- 11/12/01 Added four more service type for vismConnServiceType - This addition
--          required for a connection between VISM-PR and RPM-PR through PXM1E/PXM45
--  
-- 04/23/02 Modified the vismMaxCost description for matching with other SM module
--          


 
-- ------------------------------------------------------------------
-- For VoIP support, VISM needs one active AAL5 bearer PVC and one active 
-- AAL5 control PVC between the VISM card and the PXM. The redundant PVC
-- feature is supported for AAL5 PVCs. Each redundant PVC pair has one
-- active PVC and one standby PVC. There can be one AAL5 bearer redundant
-- PVC pair and one AAL5 control redundant PVC pair. 
--
-- All PVCs are added on the ATM virtual port=1.
--
-- For the AAL2 trunking application, there can be multiple AAL2 bearer 
-- PVCs. Also, AAL2 bearer PVC in this case, is between the two 
-- media gateways, instead of just between the VISM and the PXM. Upto 64 
-- AAL2 bearer PVCs are supported for this application.
--
--
-- ------------------------------------------------------------------

vismChanCnfGrpTable    OBJECT-TYPE
    SYNTAX  SEQUENCE OF VismChanCnfGrpEntry
    ACCESS  not-accessible
    STATUS  mandatory
    DESCRIPTION
        "The channel config table for voice traffic.
        "
    ::= { vismChanCnfGrp 1 }

vismChanCnfGrpEntry    OBJECT-TYPE
    SYNTAX  VismChanCnfGrpEntry
    ACCESS  not-accessible
    STATUS  mandatory
    DESCRIPTION
        "An entry for each voice channel.
        "
    INDEX { vismCnfChanNum }
    ::= { vismChanCnfGrpTable 1 }

VismChanCnfGrpEntry ::=
    SEQUENCE {
        vismCnfChanNum            INTEGER,
        vismChanRowStatus         INTEGER,
        vismChanPortNum           INTEGER,
        vismChanLocRmtLpbkState   INTEGER,
        vismChanTestType          INTEGER,
        vismChanTestState         INTEGER,
        vismChanRTDResult         INTEGER,
        vismChanPvcType           INTEGER,
        vismChanConnType          INTEGER,
-- Connection parameters, used by PXM
        vismLocalVpi              INTEGER,
        vismLocalVci              INTEGER,
        vismLocalNSAP             OCTET STRING,
        vismRemoteVpi             INTEGER,
        vismRemoteVci             INTEGER,
        vismRemoteNSAP            OCTET STRING,
        vismMastership            INTEGER,
        vismVpcFlag               INTEGER,
        vismConnServiceType       INTEGER,
        vismRoutingPriority       INTEGER,
        vismMaxCost               INTEGER,
        vismRestrictTrunkType     INTEGER,
-- VISM_15
        vismConnPCR               INTEGER,
-- VISM_15
        vismConnPercentUtil       INTEGER,
        vismConnRemotePCR         INTEGER,
        vismConnRemotePercentUtil INTEGER,
        vismChanProtection        INTEGER,
        vismChanPreference        INTEGER,
        vismChanActivityState     INTEGER,
        vismChanLockingState   INTEGER,
-- VISM_15
		vismChanScrIngress		  INTEGER,
		vismChanMbsIngress		  INTEGER,
		vismChanCdvt	 		  INTEGER,
		vismChanClrIngress		  INTEGER,
                vismConnPCREgress                 INTEGER,
		vismChanScrEgress		  INTEGER,
		vismChanMbsEgress		  INTEGER,
		vismChanClrEgress		  INTEGER,
		vismChanApplication		  INTEGER,
		vismChanFallbackLcn		  INTEGER,
-- VISM_15
-- VISM 2.0 addition
		vismChanReroute   		  TruthValue,
         vismFarEndAddressType    INTEGER,
         vismFarEndE164Address    DisplayString,
         vismFarEndGWIDAddress    DisplayString,
         vismFarEndNSAPAddress    OCTET STRING,
         vismVCCI                 INTEGER,
         vismConnAdminStatus      INTEGER
}


vismCnfChanNum    OBJECT-TYPE
    SYNTAX  INTEGER (131..510)
    ACCESS  read-only
    STATUS  mandatory
    DESCRIPTION
        "Logical Channel Number for the PVC. 
        "
    ::= { vismChanCnfGrpEntry 1 }
 
vismChanRowStatus    OBJECT-TYPE
    SYNTAX  INTEGER {
            add (1),
            del (2),
            mod (3),
-- added outOfService for VISM 2.0
            outOfService (4)
            }
    ACCESS  read-write
    STATUS  mandatory
-- modified description for VISM 2.0
    DESCRIPTION
       " An entry is created by setting this object to add. Once the entry
         is added, the value mod is returned for successive GETs. The value
         mod is used to modify an existing entry. An entry is deleted by
         setting this object to del.

         Setting this object to outOfService takes the channel out of service
         or brings the channel 'down'. The channel can be brought 'up' again
         by setting the object to mod.

         If there is redundant configuration for the channel, an active
         channel can be deleted only after locking the channel. 
       "
    ::= { vismChanCnfGrpEntry 2 }
 
vismChanPortNum    OBJECT-TYPE
    SYNTAX  INTEGER
    ACCESS  read-write
    STATUS  mandatory  
    DESCRIPTION   
       " This refers to the virtual port between VISM and PXM. This number
         is defaulted to the appropriate number for the shelf. (1 for PXM1
         and 255 for PXM1E)  
        " 
    ::= { vismChanCnfGrpEntry 3 }

vismChanLocRmtLpbkState    OBJECT-TYPE
    SYNTAX  INTEGER {
            enable  (1),
            disable (2)
            }
    ACCESS  read-write
    STATUS  mandatory
    DESCRIPTION
        "Loopback on cellbus in egress direction.
         This variable enables or disables the remote loopback for each channel.
         When you enable this option on a connection (channel) then all the
         cells that are coming from the network side would be looped back
         toward the network and all the frames coming from the user side
         would be dropped.
        "
    DEFVAL { disable }
    ::= { vismChanCnfGrpEntry 4 }
 
vismChanTestType    OBJECT-TYPE
    SYNTAX  INTEGER {
            testcon   (1),
            testdelay (2),
            notest    (3)
            }
    ACCESS  read-write
    STATUS  mandatory
    DESCRIPTION
        "This is the type of the test.
         1 = Test Continuity
         2 = Test Delay
         3 = No test
            notest is meant for GET only.
         While doing a SET on this object, the SET request should contain 
         only this parameter and no other MIB objects in this table. 
        "
    ::= { vismChanCnfGrpEntry 5 }
 
vismChanTestState    OBJECT-TYPE
    SYNTAX  INTEGER  {
            passed        (1),
            failed        (2),
            inprogress    (3),
            notinprogress (4)
            }
    ACCESS  read-only
    STATUS  mandatory
    DESCRIPTION
        "This shows the state of the test.
        "
    ::= { vismChanCnfGrpEntry 6 }
 
vismChanRTDResult    OBJECT-TYPE
    SYNTAX  INTEGER (1..65535)
    ACCESS  read-only
    STATUS  mandatory
    DESCRIPTION
        "This is round trip delay in milliseconds.
        "
    ::= { vismChanCnfGrpEntry 7 }
 
-- VISM_15

vismChanPvcType    OBJECT-TYPE
    SYNTAX  INTEGER  {
--            voIP  (1)
			  aal-5 (1),
			  aal-2 (2),
			  aal-1 (3)
            }
    ACCESS  read-write
    STATUS  mandatory
    DESCRIPTION
          "PVC type. In VISM 1.0 pvc type VoIP was supported. It has been
                 deprecated in the current release. 
        
                This is a mandatory parameter when adding a PVC.
        "
    DEFVAL { aal-5 }
    ::= { vismChanCnfGrpEntry 8 }
-- VISM_15
 
vismChanConnType    OBJECT-TYPE
    SYNTAX  INTEGER  {
            pvc(1)
            }
    ACCESS  read-write
    STATUS  mandatory
    DESCRIPTION
        "Connection type.
        "
    DEFVAL { pvc }
    ::= { vismChanCnfGrpEntry 9 }
 
-- ------------------------------------------------------------------
-- The following variables are specific for PopEYE 
--
-- ------------------------------------------------------------------

vismLocalVpi    OBJECT-TYPE
    SYNTAX  INTEGER (0..255)
    ACCESS  read-only
    STATUS  mandatory
    DESCRIPTION
        "This VPI together with the local VCI and NSAP represents the
         local end point in this connection.
         GET on this object returns value=0.
        "
    ::= { vismChanCnfGrpEntry 10 }

vismLocalVci    OBJECT-TYPE
    SYNTAX  INTEGER (0..65535)
    ACCESS  read-only
    STATUS  mandatory
    DESCRIPTION
        "This VCI together with the local VPI and NSAP represents the
         local end point in this connection.
         GET on this object returns the vismCnfChanNum or LCN.
        "
    ::= { vismChanCnfGrpEntry 11 }

vismLocalNSAP    OBJECT-TYPE
    SYNTAX  OCTET STRING (SIZE(20))
    ACCESS  read-write
    STATUS  mandatory
    DESCRIPTION
        "This NSAP is 20 bytes binary, among these 20 bytes: 13 bytes
         as prefix(node name), 2 bytes for Cisco ID, 1 byte rsvd, 3 bytes for
         logical interface: slot (1 byte) and port number (2 bytes), 
         the last byte is for SEL.
        "
    ::= { vismChanCnfGrpEntry 12 }

vismRemoteVpi    OBJECT-TYPE
    SYNTAX  INTEGER (0..65535)
    ACCESS  read-write
    STATUS  mandatory
    DESCRIPTION
        "This VPI together with the remote VCI and NSAP represents the
         remote end point in this connection.
           
                This parameter is required only if vismMastership is set to master.
       
        "
    ::= { vismChanCnfGrpEntry 13 }

vismRemoteVci    OBJECT-TYPE
    SYNTAX  INTEGER (0..65535)
    ACCESS  read-write
    STATUS  mandatory
    DESCRIPTION
        "This VCI together with the remote VPI and NSAP represents the
         remote end point in this connection.
               
                This parameter is required only if vismMastership is set to master.
         "
    ::= { vismChanCnfGrpEntry 14 }

vismRemoteNSAP    OBJECT-TYPE
    SYNTAX  OCTET STRING (SIZE(20))
    ACCESS  read-write
    STATUS  mandatory
    DESCRIPTION
        "This NSAP is 20 bytes binary, among these 20 bytes: 13 bytes
         as prefix, 2 bytes for Cisco ID, 1 byte rsvd, 3 bytes for
         logical interface: slot (1 byte) and port number (2 bytes), 
         the last byte is for SEL.
         
         This parameter is required only if vismMastership is set to master.
         This object contains the NSAP address of the cross-connect (PXM/AUSM).
     
        "
    ::= { vismChanCnfGrpEntry 15 }

vismMastership    OBJECT-TYPE
    SYNTAX INTEGER {
           master  (1),
           slave   (2),
           unknown (3)
           }
    ACCESS read-write
    STATUS mandatory
    DESCRIPTION
        " This is used by PXM to determine if this end point is
          master or slave.
          For VoIP channel, the value is master (1).
        "
    DEFVAL { master }
    ::= { vismChanCnfGrpEntry 16 }

vismVpcFlag    OBJECT-TYPE
    SYNTAX INTEGER {
           vcc (2)
           }
    ACCESS read-write
    STATUS mandatory
    DESCRIPTION
        " This is used by PXM to identify the connection type.
        "
    DEFVAL { vcc }
    ::= { vismChanCnfGrpEntry 17 }
 
-- VISM_15

vismConnServiceType    OBJECT-TYPE
    SYNTAX INTEGER{
           cbr      (1),
           vbr-rt   (2),
           vbr-nrt  (3),
           vbr3-rt  (4),
           vbr2-rt  (5),
	   vbr2-nrt (6),
           vbr3-nrt (7)
           }
    ACCESS read-write
    STATUS mandatory
    DESCRIPTION
        "This specifies the class of service or service type
         1 ==> Constant Bit Rate

	 2 ==> Variable Bit Rate 1 (Real Time)
	       Although, VISM does not do any kind of traffic shaping, 
               the PVC has to be specified as vbr-rt for PXM to treat
               the connection as a VBR1 connection.
         Variable Bit Rate is not currently supported.

         3 ==> Variable Bit Rate 1 (non real time)
               VISM has to support all these kinds of traffic rates from
               Indiana release onwards
         The service type of the connection cannot be modified once
         the PVC is added. 

	 4 ==> Variable Bit Rate 3 (Real Time)
	       Although, VISM does not do any kind of traffic shaping, 
               the PVC has to be specified as vbr3-rt for PXM to treat
               the connection as a VBR3 connection.
         Variable Bit Rate is not currently supported.

	 5 ==> Variable Bit Rate 2 (Real Time)
	       Although, VISM does not do any kind of traffic shaping, 
               the PVC has to be specified as vbr2-rt for PXM to treat
               the connection as a VBR2 connection.
         Variable Bit Rate is not currently supported.

         6 ==> Variable Bit Rate 2 (non real time)
               VISM has to support all these kinds of traffic rates from
               Indiana release onwards
         The service type of the connection cannot be modified once
         the PVC is added. 

         7 ==> Variable Bit Rate 3 (non real time)
               VISM has to support all these kinds of traffic rates from
               Indiana release onwards
         The service type of the connection cannot be modified once
         the PVC is added. 


        "
    DEFVAL { cbr }
    ::= { vismChanCnfGrpEntry 18 }
-- VISM_15
        
vismRoutingPriority    OBJECT-TYPE
    SYNTAX  INTEGER (1..15)
    ACCESS    read-write
    STATUS     mandatory
    DESCRIPTION
        " This is used by PXM to determine how important 
          this connection is when selecting connections to route.
        "
    DEFVAL { 8 }
    ::= { vismChanCnfGrpEntry 19 }
    
vismMaxCost    OBJECT-TYPE
    SYNTAX    INTEGER (1..2147483647)
    ACCESS    read-write
    STATUS    mandatory
    DESCRIPTION
        " Maximum allowed cost. It is related to Cost Based Routing.
          This is used by PXM so that it won't choose a path with
          a cost greater than this configured level. This is not
          necessary to be provided in the connection setup request,
          if not provided, the default value 255 will be used.
          When used with PAR controller the valid range is 1..65535 and the
          default value is 255.
          When used with PNNI controller the valid range is 1..2147483647 and
          the default value is 2147483647.

        "
    ::= { vismChanCnfGrpEntry 20 }

vismRestrictTrunkType    OBJECT-TYPE
    SYNTAX  INTEGER {
            noresriction     (1),
            terrestrialTrunk (2),
            sateliteTrunk    (3)
            }
    ACCESS  read-write
    STATUS  mandatory
    DESCRIPTION
        " Restricted trunk type for routing, used by PXM. It 
          specifies that the connection either cannot be routed over
          satelite trunks, or terrestrial trunks, or it can be on
          any type of trunk. It is not necessary to be provide in
          the connection setup request, the default value is 
          noresriction(1).
        "
    DEFVAL { noresriction }
    ::= { vismChanCnfGrpEntry 21 }
 
-- VISM_15
vismConnPCR      OBJECT-TYPE
    SYNTAX  INTEGER(1..100000)
    ACCESS  read-write
    STATUS  mandatory
    DESCRIPTION
      "This indicates bandwidth(Peak Cell Rate) in cells per second
       from the local end i.e in the ingress direction of the PVC.
       For a VoIP bearer PVC, the max value is 75600 cps.
       For a VoIP control PVC, the max value is 24400 cps.

       For AAL2 PVCs, the PCR to be specified has to be computed based on:
	a) The no. of channels multiplexed on an AAL2 PVC
	b) The Codec (Compression Algorithm) used.
	c) The VAD factor
	d) Partial fill factor.

         For a AAL2 bearer PVC, the max value is 60,000 cps on E1 card and 
           50,000 cps on T1 card. 
         For a signaling PVC, the max value is 400 cps.
   
        This is a mandatory parameter when adding a PVC. Hence a default
        value is not applicable. This parameter can not be changed when 
        there are calls active on the PVC.

        From Indiana release onwards
        For a VOIP bearer PVC the max allowed value is 80000 
        For a VOIP control PVC the max allowed value is 20000 
        increased as we will allow 248 endpoints.

        For Aal2 the values remain the same 50000/60000.

        For vbr connections the minimum value of PCR is 15. 
      "
    ::= { vismChanCnfGrpEntry 22 }
-- VISM_15

vismConnPercentUtil    OBJECT-TYPE
    SYNTAX  INTEGER  (0..100)
    ACCESS  read-write
    STATUS  mandatory
    DESCRIPTION
        "This is the expected long-term utilization of the
         channel by this end-point.
         Currently only 100 is allowed.
        "
    DEFVAL { 100 }
    ::= { vismChanCnfGrpEntry 23 }

vismConnRemotePCR    OBJECT-TYPE
    SYNTAX  INTEGER(1..100000)
    ACCESS  read-write
    STATUS  mandatory
    DESCRIPTION
      "This indicates bandwidth(Peak Cell Rate) from the other end i.e
       in the egress direction of the PVC. This value is expressed in 
       units of cells per second.
       If not set, will be set to the same as local end PCR.
        From Indiana release onwards
        The range of this object is  1..100000
      "
    ::= { vismChanCnfGrpEntry 24 }

vismConnRemotePercentUtil    OBJECT-TYPE
    SYNTAX INTEGER  (0..100)
    ACCESS read-write
    STATUS mandatory
    DESCRIPTION
        "This is the expected long-term utilization of the
         channel by the other end-point.
         Currently only 100 is allowed.
        "
    DEFVAL { 100 }
    ::= { vismChanCnfGrpEntry 25 }


vismChanProtection    OBJECT-TYPE
    SYNTAX  INTEGER {
            protected     (1),
            unprotected   (2)
            }
    ACCESS read-write
    STATUS mandatory
    DESCRIPTION
        "This object is used to configure a PVC protection group (or redundant group)
         with the PVCs protecting each other. Currently only two PVCs are supported
         in a protection group. One of them is primary and the other one is secondary.
         This is intended for PVCs designated to carry control traffic and needs to 
         be protected.  (However the same PVC may also be used to carry VoIP bearer 
         traffic or other traffic). 

         Channels that are protected share the following characteristics:

         1. They are monitored for their health (including emission of traps in 
            case of state changes)

         2. An active channel is protected by another protected channel which is 
            standby. This means when an active channel fails, switchover to another 
            channel will happen if one is available. 

         3. It is also possible to do a forced switchover (through locking). 
            Even in the case of forced switchover, switchover to another 
            channel, which is in standby, will happen.

         4. Channels may be locked to force switchover and/or to take the 
            channel out of service in a graceful fashion.

         This object takes the default value of unprotected during the creation of the 
         table entry. Once the primary and secondary channels have been created as 
         unprotected channels, they can be protected by doing a SET on the primary
         channel by specifying the vismChanProtection as protected and by specifying the
         vismChanFallbackLcn as the LCN number of the secondary channel. 

         The sequence of operations for setting up the protection group is:
           step 1: Add primary channel as unprotected
           step 2: Add secondary channel as unprotected. The PCR value for the secondary 
                   should be the same as that of the primary.
           step 3: Do a SET on the primary channel with vismChanProtection set to protected
                   and vismChanFallbackLcn set to the LCN number of the secondary channel.
                   This operation sets-up the protection group.  The primary channel becomes
                   active and the secondary channel becomes standby. 
        
         Please note that all the cac releated parameters for the both the PVCs
         in the protecting group should be same. In other words the vismChanCacMaster
         vismChanCarrierLossPolicy, vismChanCacRejectionPolicy, VAD tolerance  etc.. 
         should have the same value for the PVCs that are protecting each other, else
         the set request to protect two channels will be rejected.
      
         Once the protection group is setup, if the active channel fails, it automatically 
         switches over to the standby. The standby channel then becomes active.

         The channels can be removed from the protection group by setting this object to
         unprotected. 

         Deletion of a protected channel is not allowed. Channels have to be removed from
         the protection group first before deleting. The sequence of operations for deleting
         protected channels is:
             step 1: Remove the  channels from the protection group by setting 
                     vismChanProtection to unprotected.
             step 2: Delete secondary channel.
             step 3: Delete primary channel.
        "
      DEFVAL { unprotected }
    ::= { vismChanCnfGrpEntry 26 }


vismChanPreference    OBJECT-TYPE
 SYNTAX INTEGER  {
                        primary (1),
                        secondary (2)
                   }
    ACCESS read-write
    STATUS mandatory
    DESCRIPTION
        "This object is used to identify a PVC as primary or secondary.
         The primary PVC should be added before the secondary. Similarly
         secondary should be deleted before deleting the primary. 

         When the protection group is setup, the primary becomes active and secondary 
         becomes standby. The distinction of primary and secondary is meaningful only 
         if the PVC is protected.
        
         This is a mandatory parameter when adding a PVC.
         "
        DEFVAL { primary }
    ::= { vismChanCnfGrpEntry 27 }


vismChanActivityState    OBJECT-TYPE
    SYNTAX  INTEGER {
            active     (1),
            standby    (2),
            failed     (3),
            unknown    (4)
            }
    ACCESS read-only
    STATUS mandatory
    DESCRIPTION
        "Indicates whether the PVC is currently used to carry IP traffic or not,
         and whether it has failed. 

         The possible states are:

         active  - Channel is healthy and is currently designated to carry IP 
                   traffic. A channel can only be active if it is also unlocked.
         standby - Channel is healthy but not designated to carry IP traffic.
                   Switchover to this channel is allowed.
         failed  - Channel is unable to carry any traffic.
         unknown - Channel is unprotected and hence health of the channel is not
                   monitored.

         The default value upon creation of the row will be standby for a 
         protected channel and unknown for an unprotected channel. VISM may then
         transition a protected channel to active if it determines that this
         channel should be the one carrying the traffic.
        "
    ::= { vismChanCnfGrpEntry 28 }

vismChanLockingState    OBJECT-TYPE
    SYNTAX  INTEGER {
            unlock   (1),
            lock     (2)
            }
    ACCESS read-write
    STATUS mandatory
    DESCRIPTION
        "This object is used to control the switchover of protected channels. 

         The possible values are:

         unlock -  Transition state to unlock. A channel which is in lock state
                   has to be brought to unlock state for it to be available for
                   switchover. 

                   Whether a switchover to a channel is allowed or not is 
                   dependent on both vismChanActivityState and 
                   vismChanLockingState. A switchover is allowed if its 
                   vismChanActivityState is standby and its vismChanLockingState
                   is unlock.

                   Changing the vismChanLockingState to unlock does not cause a
                   change in the vismChanActivityState.

                   A channel which is in unlock state may carry traffic 
                   depending on its activity state (active or standby). 

         lock   -  Transition state to lock. If the activity state is active,
                   it transitions to standby and a switchover occurs to another
                   channel which is standby and unlocked. 

                   When a channel is in lock state, switchover to this channel 
                   is not allowed. 

                   A channel which is in lock state, is always in either standby
                   or failed state. Hence it will not carry any traffic.

                   Switchover to a channel which is in lock state is not allowed.

        The default value of this object is unlock. It can be set to locked to 
        force a switchover and/or to perform maintenance operations related to
        that channel.

        A channel that is unprotected will always be in unlock state. It can 
        not be set to lock state.
        "
        DEFVAL { unlock }
    ::= { vismChanCnfGrpEntry 29 }

-- VISM_15

-- The following three objects are defined for VBR type connections
-- only. Even though no special processing is done for VBR connections
-- on VISM, the following parameters are still required for making a
-- PVC connection with the AUSM card, which is the other end of the 
-- PVC in the trunking application. 

vismChanScrIngress               OBJECT-TYPE
    SYNTAX  INTEGER(1..100000) 
    ACCESS read-write
    STATUS mandatory
    DESCRIPTION
	" This object defines the SCR (Sustained Cell Rate) for the PVC. 
	SCR is used for vbr connection types only. Although, based on the 
	value of SCR, any kind of traffic shaping is not done on the VISM
	card, this value is useful for setting up the parameters for the
	end-to-end PVC.
	This value is expressed in units of cells per second.

	This object defines the SCR value for the ingress direction of
	the PVC. 
        From Indiana release onwards
        For a VOIP bearer PVC the max value is 80000 
        For a VOIP control PVC the max value is 20000 
        increased as we will allow 248 endpoints.

        For Aal2 the values remain the same (50000/60000).
        If the user provides a value that is greater than vismConnPCR
        then the SET request will be rejected.
        
        For vbr connections the allowed range of values of SCR is from 
        15 - PCR.
	"
    ::= { vismChanCnfGrpEntry 30 }

vismChanMbsIngress               OBJECT-TYPE
	SYNTAX  INTEGER
    ACCESS  read-write
    STATUS  mandatory
    DESCRIPTION
	"
	This object defines the MBS (Max. Burst Size) in cells per second.
	This object is meaningful for VBR connections only. 

	This object defines the MBS value for the ingress direction of
	the PVC. 

        The MBS value cannot be greater than 10 times vismChanSCRIngress value.
	"
    ::= { vismChanCnfGrpEntry 31 }

vismChanClrIngress               OBJECT-TYPE
	SYNTAX  INTEGER
    ACCESS  read-write
    STATUS  mandatory
    DESCRIPTION
	" This object defines the CLR (Cell Loss Ratio) for the PVC.
	This field is also meaningful for VBR connections only.

	This object defines the CLR value for the ingress direction of
	the PVC. 
	"
    ::= { vismChanCnfGrpEntry 32 }

vismChanCdvt              OBJECT-TYPE
	SYNTAX  INTEGER(1..30)
    ACCESS  read-write
    STATUS  mandatory
    DESCRIPTION
        "
        This object defines the CDVT (Cell Delay Variation Tolerance) for the
        connection. CDVT is useful for detemining the playout buffer size in
        the DSPs. This object is applicable only in AAL1 adaptation. For AAL2, 
        the equivalent of this parameter, known as PDVT (Packet Delay Variation
        Tolerance) is internally derived.

        "
        DEFVAL { 2 }
    ::= { vismChanCnfGrpEntry 33 }

vismConnPCREgress               OBJECT-TYPE
    SYNTAX  INTEGER(1..100000) 
    ACCESS read-write
    STATUS mandatory
-- status obsolete
-- This object is the same as vismConnRemotePCR
    DESCRIPTION
	" This object defines the PCR (Peak Cell Rate) for the PVC. 
	PCR is applicable to all connection service types ie. CBR, RT-VBR
	and nRT-VBR.

	This value is expressed in units of cells per second.

	This object defines the PCR value for the egress direction of
	the PVC.

                This is a mandatory parameter when adding a PVC.

	"
    ::= { vismChanCnfGrpEntry 34 }

vismChanScrEgress               OBJECT-TYPE
    SYNTAX  INTEGER(1..100000) 
    ACCESS read-write
    STATUS mandatory
    DESCRIPTION
	" This object defines the SCR (Sustained Cell Rate) for the PVC. 
	SCR is used for vbr connection types only. Although, based on the 
	value of SCR, any kind of traffic shaping is not done on the VISM
	card, this value is useful for setting up the parameters for the
	end-to-end PVC.
	This value is expressed in units of cells per second.

	This object defines the SCR value for the egress direction of
	the PVC. 
        From Indiana release onwards the range of this
        object has been increased to 100000.

	"
    ::= { vismChanCnfGrpEntry 35 }

vismChanMbsEgress               OBJECT-TYPE
	SYNTAX  INTEGER
    ACCESS  read-write
    STATUS  mandatory
    DESCRIPTION
	"
	This object defines the MBS (Max. Burst Size) in cells per second.
	This object is meaningful for VBR connections only. 

	This object defines the MBS value for the egress direction of
	the PVC. 
	"
    ::= { vismChanCnfGrpEntry 36 }

vismChanClrEgress               OBJECT-TYPE
	SYNTAX  INTEGER
    ACCESS  read-write
    STATUS  mandatory
    DESCRIPTION
	" This object defines the CLR (Cell Loss Ratio) for the PVC.
	This field is also meaningful for VBR connections only.

	This object defines the MBS value for the egress direction of
	the PVC. 
	"
    ::= { vismChanCnfGrpEntry 37 }

vismChanApplication		  OBJECT-TYPE
	SYNTAX  INTEGER {
				control (1),
				bearer  (2),
				signaling (3)
			}
    ACCESS  read-write
    STATUS  mandatory
    DESCRIPTION
	"
	This object defines the application that the LCN is used for.
	There are 4 types of PVCs known so far:

	1 - Control PVC used for carrying control traffic only (SGCP packets)
	2 - bearer PVC, used for carrying voice payload traffic only
	3 - signaling PVC, used for carrying the signaling protocol messages 
   
                This is a mandatory parameter when adding a PVC.
      
	"
	DEFVAL { bearer }
    ::= { vismChanCnfGrpEntry 38 }

vismChanFallbackLcn		  OBJECT-TYPE
	SYNTAX  INTEGER(131..510)
    ACCESS  read-write
    STATUS  mandatory
    DESCRIPTION
	"
	This object defines the LCN to be used as a fallback mechanism, 
        in case the primary PVC fails. This is applicable if the PVC is 
        configured for redundancy. The redundancy is applicable for both 
        applications i.e control PVC and bearer PVC.
     This object is applicable only if the vismChanProtection is set to 
        protected. It is mandatory if the PVC is protected. 
	"
    ::= { vismChanCnfGrpEntry 39 }

-- VISM 2.0 addition

vismChanReroute    OBJECT-TYPE
    SYNTAX TruthValue
    ACCESS read-write
    STATUS mandatory
    DESCRIPTION
       " This is used by the administrator to trigger the re-routing
         of the connection. The rerouting takes effect, when this object
         is set to true(1). When set to false (2), no action is taken.
         A get on this object always returns false (2).
       "
    DEFVAL {false}
    ::= { vismChanCnfGrpEntry 40 }

vismFarEndAddressType    OBJECT-TYPE
    SYNTAX  INTEGER {
                        notapplicable (1),
                        nsap  (2),
                        e164  (3),
                        gwid  (4),
                        unspecified (5)
                    }
    ACCESS  read-write
    STATUS  mandatory
    DESCRIPTION
        " The address type can be one of five types: NSAP, E164, GWID, notapplicable 
          or unspecified.  It determines which object contains the scope for the VCCI, 
          i.e. whether the VCCI needs to be unique relative to NSAP, E164 address or GWID.
          In case of nsap, object vismFarEndNSAPAddress contains the address.  In case
          of e164, object vismFarEndE164Address contains the address.  In case of gwid,
          object vismFarEndGWIDAddress contains the address.  In case this object is
          set to notapplicable, no valid addresses are required and no
          validation of VCCI uniqueness for a remote address is performed.
          In case this object is set to unspecified, no valid addresses are
          required but VCCI needs to be unique.

          While this object is writeable, it is recommended not to change the
          value of this object once it has been created.  However, upon
          modification to any value other than notapplicable, it will be ensured
          that the resulting combination of VCCI and remote address is unique.
          Requests that would result in a non-unique combination will be rejected.

          If the vismFarEndAddressType is one of nsap, e164 or gwid, the far end
          address has to be specified.
       "
DEFVAL { notapplicable }
    ::= { vismChanCnfGrpEntry 41 }


vismFarEndE164Address    OBJECT-TYPE
    SYNTAX  DisplayString (SIZE(1..15))
    ACCESS  read-write
    STATUS  mandatory
    DESCRIPTION
        " The E.164 address of the far end peer. The address is expressed
          as decimal numbers with up to 15 digits.  If the vismFarEndAddressType
          is different from e164, this object is not applicable and it should be
          ignored.  

          This object serves as the scope for VCCI identifiers (vismVCCI) if
          vismFarEndAddressType is equal to e164.  In that case, the combination
          of (vismFarEndE164Address, vismVCCI) will always be unique for any given
          agent.  It thus constitutes a label denoting the scope for a VCCI
          address space; it has no purpose otherwise.  
          
          While this object is writeable, it is recommended not to change the 
          value of this object once it has been created.  However, upon 
          modification, it will be ensured that the resulting combination of
          VCCI and remote E164 address is unique (as long as the remote address
          type is E164).  Requests that would result in a non-unique combination
          will be rejected.  Beyond this, there are no other integrity constraints
          that will be enforced for this object.  This includes network-level
          consistency with the actual address of the remote peer.
         
          The value of this object cannot be modified when there are active
          calls on this PVC. The valid characters allowed are '0..9'.
        "
    ::= { vismChanCnfGrpEntry 42 }


vismFarEndGWIDAddress    OBJECT-TYPE
    SYNTAX  DisplayString (SIZE(1..64))
    ACCESS  read-write
    STATUS  mandatory
    DESCRIPTION
        " The gateway ID of the far end peer. The address is expressed as ASCII
          characters. If the vismFarEndAddressType is different from gwid,
          this object is not applicable and it should be ignored.  

          This object serves as the scope for VCCI identifiers (vismVCCI) if
          vismFarEndAddressType is equal to gwid.  In that case, the combination
          of (vismFarEndGWIDAddress, vismVCCI) will always be unique for any given
          agent.  It thus constitutes a label denoting the scope for a VCCI
          address space; it has no purpose otherwise.  
          
          While this object is writeable, it is recommended not to change the 
          value of this object once it has been created.  However, upon 
          modification, it will be ensured that the resulting combination of
          VCCI and far end GWID address is unique (as long as the vismFarEndAddress
          type is GWID).  Requests that would result in a non-unique combination
          will be rejected.  Beyond this, there are no other integrity constraints
          that will be enforced for this object.  This includes network-level
          consistency with the actual address of the remote peer.
         
          The value of this object cannot be modified when there are active
          calls on this PVC. All ASCII characters are allowed by this object.
        "
    ::= { vismChanCnfGrpEntry 43 }

vismFarEndNSAPAddress OBJECT-TYPE
    SYNTAX  OCTET STRING (SIZE(20))
    ACCESS  read-write
    STATUS  mandatory
    DESCRIPTION
            "
              This object contains the 20 byte NSAP address of the far end peer.
              If the vismFarEndAddressType is different from nsap, this object 
              is not applicable and it should be ignored.  

              This object serves as the scope for VCCI identifiers (vismVCCI) if
              vismFarEndAddressType is equal to nsap.  In that case, the
              combination of (vismFarEndNSAPAddress, vismVCCI) will always be unique 
              for any given agent.  It thus constitutes a label denoting the scope  
              for a VCCI address space; it has no purpose otherwise.  
          
              While this object is writeable, it is recommended not to change the 
              value of this object once it has been created. However, upon 
              modification, it will be ensured that the resulting combination of
              VCCI and far end NSAP address is unique (as long as the far end
              address type is GWID).  Requests that would result in a non-unique
              combination will be rejected.  Beyond this, there are no other integrity
              constraints that will be enforced for this object.  This includes 
              network-level consistency with the actual address of the remote peer.
            
              The value of this object cannot be modified when there are active
              calls on this PVC.

              When the user adds a connection, by default the value of this object 
              will be set to vismRemoteNSAP, unless the user specifies a value for
              this object. This object is represented as hex (0 .. 9,A .. F)
              
            "
     ::= {vismChanCnfGrpEntry 44 }


vismVCCI    OBJECT-TYPE
    SYNTAX  INTEGER (0..65535)
    ACCESS  read-write
    STATUS  mandatory
    DESCRIPTION
        " The VCCI, or Virtual Circuit Connection Identifier, is a
          variable that identifies a virtual circuit connection between
          two nodes.  A virtual circuit connection, or  VCC, consists of
          one virtual circuit link or a series of concatenated virtual
          circuit links. In its most common usage, the value  of the VCCI
          is unique between the nodes at the extremities of the virtual
          circuit connection, but not on a network-wide basis. Hence,  its
          value needs to be qualified by the ATM addresses of these end
          nodes. At one of these end nodes, its value needs to be qualified
          by the ATM address of the far-end node. Some applications can
          extend this definition to make the VCCI value unique on a network-
          wide basis. This is specially possible when VCCIs are administered
          from a management system and not locally assigned  by a node.

          In this MIB, the VCCI serves as a label to be assigned by an 
          external application.   VCCIs need to be unique for a given 
          remote peer, however, the same VCCI can be reused for different 
          remote peers.  Accordingly, the combination of (remote address, VCCI) 
          will always be unique for any given agent. This allows a controller 
          to refer to a VC by the VCCI and remote peer address, in contrast to 
          VPI/VCI and port.  It thus constitutes a convenience feature, 
          providing an alternative identification scheme for a VC which is 
          managed by an outside user, such as a management system.  

          The remote peer address can be specified in NSAP, E.164, or GWID
          format, as indicated by the address type (vismRemoteAddressType).  
          Depending on the address type specified, uniqueness will be relative 
          to NSAP, E.164 address, or GWID. 

          While this object is writeable, it is recommended not to change the 
          value of this object once it has been created.  However, upon 
          modification, it will be ensured that the resulting combination of VCCI
          and remote address is unique.  Requests that would result in a non-unique
          combination will be rejected.  Beyond this, there are no other
          integrity constraints that will be enforced for this object.  This 
          includes network-level consistency whether the remote peer, or an 
          external controller, use the same VCCI designation for the VC.  
           
        "
    DEFVAL { 0 }
    ::= { vismChanCnfGrpEntry 45 }


vismConnAdminStatus OBJECT-TYPE
    SYNTAX INTEGER {
        up(1),
        down(2)
    }
    ACCESS read-write
    STATUS mandatory
    DESCRIPTION
        "This object specifies channel administration status.
         "
    DEFVAL {up}
    ::= { vismChanCnfGrpEntry 46 }



-- VISM_15

vismChanNumNextAvailable    OBJECT-TYPE
    SYNTAX INTEGER  (0..510)
    ACCESS read-only
    STATUS mandatory
    DESCRIPTION
        "This variable contains the next unused channel number.
         When channels are available the range is 32..510.
         This number can be used in channel config table.
         Value 0 for this variable indicates that
         no more channels are available. 
        "
    ::= { vismChanCnfGrp 2 }

--
-- ----------------------------------------------------------------------
-- BASIS Project MIB
--
--
-- VISM specific Channel State group 
--
-- ------------------------------------------------------------------
-- Modification History
-- 12/28/99 Changed vismStateChanNum range from (32..279) to (131..510)
--
-- 12/26/01 Added vismChanStatusBitMap to vsimChanStateGrpTable.
--
-- 03/04/01 fix a vismChanStatusBitmap description typo.
--
-- ------------------------------------------------------------------



vismChanStateGrp        OBJECT IDENTIFIER ::= { vismChanGrp 2 }

-- ------------------------------------------------------------------
-- For VoIP support we need only one PVC between the VISM card
-- and the PXM.
-- This PVC is added on the network port=255, which has the 
-- portSpeed=192*64 kbps for VISM-8T1 and 240 * 64 kbps for VISM-8E1.
-- Note that this network port is pre-configured on the VISM card,
-- and no need to configure it.
-- ------------------------------------------------------------------

vismChanStateGrpTable OBJECT-TYPE
    SYNTAX  SEQUENCE OF VismChanStateGrpEntry
    ACCESS  not-accessible
    STATUS  mandatory
    DESCRIPTION
        "voice connection state table
        "
    ::= { vismChanStateGrp 1 }
 
vismChanStateGrpEntry OBJECT-TYPE
    SYNTAX  VismChanStateGrpEntry
    ACCESS  not-accessible
    STATUS  mandatory
 
    DESCRIPTION
        " An entry for each channel (PVC)
        "
    INDEX   { vismStateChanNum }
    ::= { vismChanStateGrpTable 1 }


VismChanStateGrpEntry ::=
    SEQUENCE {
        vismStateChanNum          INTEGER,
        vismChanState             INTEGER,
        vismChanXmtATMState       INTEGER,
        vismChanRcvATMState       INTEGER,
        vismChanStatusBitMap      INTEGER
	}


vismStateChanNum OBJECT-TYPE
    SYNTAX  INTEGER (131..510)
    ACCESS  read-only
    STATUS  mandatory
    DESCRIPTION
        "Refers to the channel Number LCN.
        "
    ::= { vismChanStateGrpEntry 1 }
 


vismChanState OBJECT-TYPE
    SYNTAX  INTEGER {
            notConfigured (1),
            okay          (2),
            alarm         (3)
            }
    ACCESS  read-only
    STATUS  mandatory
    DESCRIPTION
        " Channel status.
        "
    ::= { vismChanStateGrpEntry 2 }
 


vismChanXmtATMState OBJECT-TYPE
    SYNTAX  INTEGER {
            other       (1),
            normal      (2),
            sendingAIS  (3),
            sendingFERF (4)
            }
    ACCESS  read-only
    STATUS  mandatory
    DESCRIPTION
        "
          This variable indicates the transmit state of channel
          on the ATM side(towards the network).
        "
    ::= { vismChanStateGrpEntry 3 }
 
vismChanRcvATMState OBJECT-TYPE
    SYNTAX  INTEGER {
            other         (1),
            normal        (2),
            receivingAIS  (3),
            receivingFERF (4)
            }
    ACCESS  read-only
    STATUS  mandatory
    DESCRIPTION
        "
          This variable indicates the receive state of channel
          on the ATM side(from the network).
        "
    ::= { vismChanStateGrpEntry 4 }


vismChanStatusBitMap OBJECT-TYPE
    SYNTAX  INTEGER (0..'ff'h)
    ACCESS  read-only
    STATUS  mandatory
    DESCRIPTION
        "This variable indicates the consolidated bit map of 
         the channel alarm state.

        Individual bit positions are as defined below, all reserved
        bits will be set to zero.

        Bit position   Fail/Alarm     Reason
        ------------   ----------     ------
            0           Alarm         Reserved
            1           Alarm         n/w side CC failure/AIS/RDI Rx
            2           Fail          Conditioned (Abit from n/w)
            3           Alarm         Reserved
            4           Fail          Reserved 
            5           Fail          Reserved
            6           Alarm         Reserved
            7           Alarm         Reserved

            Fail bitmap mask : 0x34
            Alarm bitmap mask: 0xCB
        "

    ::= { vismChanStateGrpEntry 5}


--
-- ----------------------------------------------------------------------
-- BASIS Project MIB
--
--
-- VISM specific Channel Counters group 
--
-- ------------------------------------------------------------------
--
-- Modification History
-- 07/23 Incorporated the changes suggested in the review meeting. 
-- 09/01 Obsoleted legacy counters, these were not being used.
-- 11/03 Deleted the above obsoleted counters from the table (CSCdp05637)
-- 11/22 Change description for vismChanAal2OamLpbLostCells to be 
--       applicable for all PVCs.
-- 12/28/99 Changed vismCntChanNum (32..279) to (131..510)



vismChanCntGrp          OBJECT IDENTIFIER ::= { vismChanGrp 3 }

-- ------------------------------------------------------------------
 
vismChanCntGrpTable OBJECT-TYPE
    SYNTAX  SEQUENCE OF VismChanCntGrpEntry
    ACCESS  not-accessible
    STATUS  mandatory
    DESCRIPTION
        "vism channel counters table. This table gets implicitly created and
         deleted at the time of creation and deletion of ChanCnfGrp.
        "
    ::= { vismChanCntGrp 1 }
 
vismChanCntGrpEntry OBJECT-TYPE
    SYNTAX  VismChanCntGrpEntry
    ACCESS  not-accessible
    STATUS  mandatory
    DESCRIPTION
        " An entry for each voice channel.
        "
    INDEX   { vismCntChanNum }
    ::= { vismChanCntGrpTable 1}
 
VismChanCntGrpEntry ::=
    SEQUENCE {
        vismCntChanNum                          INTEGER,
        vismCntClrButton                        INTEGER,
-- VISM_15
                vismChanAal2HecErrors                           Counter,
                vismChanAal2CrcErrors                           Counter,
                vismChanAal2OamLpbLostCells                     Counter,
                vismChanAal2InvOsfCells                 Counter,
                vismChanAal2InvParCells                 Counter,
                vismChanAal2CpsSentPkts                 Counter,
                vismChanAal2CpsRcvdPkts                 Counter,
                vismChanAal2CpsInvCidPkts               Counter,
                vismChanAal2CpsInvUuiPkts                       Counter,
                vismChanAal2CpsInvLenPkts                       Counter,
                vismChanAal5InvCpiPdus                          Counter,
                vismChanAal5OversizedSdusRcvdPdus       Counter,
                vismChanAal5InvLenPdus                          Counter,
                vismChanAal5Crc32ErrorPdus                      Counter,
                vismChanAal5ReassemTimerExpiryPdus  Counter
 
 
-- VISM_15
}

vismCntChanNum OBJECT-TYPE
    SYNTAX  INTEGER (131..510)
    ACCESS  read-only
    STATUS  mandatory
    DESCRIPTION
        "Refers to the logical channel Number.
        "
    ::= { vismChanCntGrpEntry 1 }

-- vismChanReassCells   OBJECT-TYPE
--    SYNTAX  Counter
--    ACCESS  read-only
--    STATUS  mandatory
-- obsolete
--    DESCRIPTION
--        "The number of cells played out to T1/E1 port.
--        "
--    ::= { vismChanCntGrpEntry   2 }
-- 
-- vismChanGenCells     OBJECT-TYPE
--    SYNTAX  Counter
--    ACCESS  read-only
--    STATUS  mandatory
-- obsolete
--    DESCRIPTION
--        "The number of cells generated from T1/E1 port.
--        "
--    ::= { vismChanCntGrpEntry   3 }
-- 
-- vismChanPointerReframes  OBJECT-TYPE
--    SYNTAX  Counter
--    ACCESS  read-only
--    STATUS  mandatory
-- obsolete
--    DESCRIPTION
--        "The number of events of SDT pointers wrong arrival.
--        "
--    ::= { vismChanCntGrpEntry   4 }
-- 
-- vismChanBufUnderflows    OBJECT-TYPE
--    SYNTAX  Counter
--    ACCESS  read-only
--    STATUS  mandatory
-- obsolete
--    DESCRIPTION
--        "The number of buffer underflows in Egress direction.
--        "
--    ::= { vismChanCntGrpEntry   5 }
-- 
-- vismChanBufOverflows OBJECT-TYPE
--    SYNTAX  Counter
--    ACCESS  read-only
--    STATUS  mandatory
-- obsolete
--    DESCRIPTION
--        "The number of buffer overflows in Egress direction.
--        "
--    ::= { vismChanCntGrpEntry   6 }
-- 
-- vismChanIngrDiscardedBytes   OBJECT-TYPE
--    SYNTAX  Counter
--    ACCESS  read-only
--    STATUS  mandatory
-- obsolete
--    DESCRIPTION
--        "The number of bytes discarded due to shelf alarm in ingress
--         direction from port data.
--        "
--    ::= { vismChanCntGrpEntry   7 }
-- 
-- vismChanUflowInsCells    OBJECT-TYPE
--    SYNTAX  Counter
--    ACCESS  read-only
--    STATUS  mandatory
-- obsolete
--    DESCRIPTION
--        "The Number of All 1's cells inserted in case of
--         Egress Buffer Underflow.
--        "
--    ::= { vismChanCntGrpEntry   8 }
-- 
-- vismChanOflowDropBytes   OBJECT-TYPE
--    SYNTAX  Counter
--    ACCESS  read-only
--    STATUS  mandatory
-- obsolete
--    DESCRIPTION
--        "The Number of bytes discarded in Egress direction because of
--         Egress buffer overflow.
--        "
--    ::= { vismChanCntGrpEntry 9 }
--

vismCntClrButton   OBJECT-TYPE
    SYNTAX  INTEGER {
            noAction      (1),
            resetCounters (2)
            }
    ACCESS  read-only
    STATUS  mandatory
    DESCRIPTION
        "writing a value of 2 resets all the counters.
        "
    ::= { vismChanCntGrpEntry 10 }

-- VISM_15
vismChanAal2HecErrors     OBJECT-TYPE
    SYNTAX  Counter
    ACCESS  read-only
    STATUS  mandatory
    DESCRIPTION
        "The count of egress AAL2 CPS(Common Part Sub-layer) PDUs dropped
		 due to HEC (Header Error Control) error.
        "
    ::= { vismChanCntGrpEntry   11 }
 
vismChanAal2CrcErrors     OBJECT-TYPE
    SYNTAX  Counter
    ACCESS  read-only
    STATUS  mandatory
    DESCRIPTION
        "The count of egress AAL2 type3 CPS PDUs dropped due to
		invalid CRC-10 error. CRC validation is for type 3 packets only.
		Type 1 packets are not subjected to CRC-10 error validation. Also
		this counter keeps track of CRC-10 errors for the type 3 packets
		which are generated by the the datamover CPU only. It does not take
		into account of type3 packets generated by the DSPs.
        "
    ::= { vismChanCntGrpEntry   12 }
 

vismChanAal2OamLpbLostCells       OBJECT-TYPE
    SYNTAX  Counter
    ACCESS  read-only
    STATUS  mandatory
    DESCRIPTION
        "The count of OAM loopback cells lost. OAM loopback cells are sent
         on a periodic basis (1sec) on each PVC to monitor the health of 
         the PVC. This is applicable for all PVCs.
        "
    ::= { vismChanCntGrpEntry   13 }

vismChanAal2InvOsfCells   OBJECT-TYPE
    SYNTAX  Counter
    ACCESS  read-only
    STATUS  mandatory
    DESCRIPTION
        "The Number of AAL2 cells dropped due to invalid OSF (OffSet Field)
                 in the egress direction.
        "
    ::= { vismChanCntGrpEntry   14 }

vismChanAal2InvParCells   OBJECT-TYPE
    SYNTAX  Counter
    ACCESS  read-only
    STATUS  mandatory
    DESCRIPTION
        "The Number of AAL2 cells dropped due to invalid Parity bit field
                 in the egress direction.
        "
    ::= { vismChanCntGrpEntry   15 }

 
vismChanAal2CpsSentPkts         OBJECT-TYPE
    SYNTAX  Counter
    ACCESS  read-only
    STATUS  mandatory
    DESCRIPTION
        "The count of AAL2 CPS packets sent to the network.
        "
    ::= { vismChanCntGrpEntry   16 }

vismChanAal2CpsRcvdPkts       OBJECT-TYPE
    SYNTAX  Counter
    ACCESS  read-only
    STATUS  mandatory
    DESCRIPTION
      "The count of AAL2 CPS packets received from the network. This does
                 not include the packets which are counted as error packets.
        "
    ::= { vismChanCntGrpEntry   17 }

 
vismChanAal2CpsInvCidPkts         OBJECT-TYPE
    SYNTAX  Counter
    ACCESS  read-only
    STATUS  mandatory
    DESCRIPTION
        "The count of AAL2 CPS packets dropped in the egress direction 
                 due to invalid CID (Channel ID). The CID may be considered as 
                 invalid if -
                a) It is out of range.
                b) It is not configured
        "
    ::= { vismChanCntGrpEntry   18 }
 
vismChanAal2CpsInvUuiPkts         OBJECT-TYPE
    SYNTAX  Counter
    ACCESS  read-only
    STATUS  mandatory
    DESCRIPTION
        "The count of AAL2 CPS packets dropped in the egress direction
                due to invalid UUI (User-to-User Info.) field. 
        "
    ::= { vismChanCntGrpEntry   19 }


vismChanAal2CpsInvLenPkts         OBJECT-TYPE
    SYNTAX  Counter
    ACCESS  read-only
    STATUS  mandatory
    DESCRIPTION
        "The count of AAL2 CPS packets dropped in the egress direction
                due to invalid length field. 
        "
    ::= { vismChanCntGrpEntry   20 }
 
vismChanAal5InvCpiPdus                          OBJECT-TYPE
    SYNTAX  Counter
    ACCESS  read-only
    STATUS  mandatory
    DESCRIPTION
        "The count of AAL5 PDUs dropped in the egress direction
                due to invalid CPI (common part indicator) field in the
                AAL5 PDU trailer. This is applicable only to the PVCs
            configured as AAL5 PVCs (VoIP PVCs or CCS PVCs in the 
                case of VoAAL2 application).
        "
    ::= { vismChanCntGrpEntry   21 }
 
vismChanAal5OversizedSdusRcvdPdus         OBJECT-TYPE
    SYNTAX  Counter
    ACCESS  read-only
    STATUS  mandatory
    DESCRIPTION
        "The count of AAL5 PDUs dropped due to the SDU size
                 bigger than the configured value. This is applicable
                 for AAL5 PVCs only.
        "
    ::= { vismChanCntGrpEntry   22 }
 
vismChanAal5InvLenPdus    OBJECT-TYPE
    SYNTAX  Counter
    ACCESS  read-only
    STATUS  mandatory
    DESCRIPTION
        "The count of AAL5 PDUs dropped due to the length
                 violations. This is applicable to the CCS PVCs.
                 The HDLC frames should have a minimum frame size
                 in order for the proper interpretation by the 
                 upper layer protocol. 
        "
    ::= { vismChanCntGrpEntry   23 }
 
vismChanAal5Crc32ErrorPdus                      OBJECT-TYPE
    SYNTAX  Counter
    ACCESS  read-only
    STATUS  mandatory
    DESCRIPTION
        "The count of AAL5 PDUs dropped in the egress direction
                 due to CRC-32 errors detected by the SAR. 
        "
    ::= { vismChanCntGrpEntry   24 }
 
vismChanAal5ReassemTimerExpiryPdus        OBJECT-TYPE
    SYNTAX  Counter
    ACCESS  read-only
    STATUS  mandatory
    DESCRIPTION
        "The count of AAL5 PDU reassembly timer expirations.
                The timers are maintained in the egress direction
                for building an AAL5 PDU from the cells.
        "
    ::= { vismChanCntGrpEntry   25 }

-- VISM_15

--
-- ----------------------------------------------------------------------
-- BASIS Project MIB
--
--
-- VISM specific Port Configuration group 
--
-- ------------------------------------------------------------------
--
-- Modification History
-- 08/26 Changed legacy description
-- 
-- 11/22 Added DEFVAL clause for vismPortLineNum and vismPortDs0ConfigBitMap 
--
--       Adding and deleting port is now supported through SNMP. (Earlier
--       it was deing done using CLI only). Hence changing the description
--       accordingly.  
--
--       Changed DEFVAL of vismPortType from userPort to voIP. (VISM always
--       supported the value of voIP. It was wrongly specified as userPort
--       in the DEFVAL clause).
--  12/30/99 Changed the description of vismPortSpeed to take care of the
--           increased speed for VoIP because of Dual PVC support75600.
-- 05/12/2000 made vismPortSpeed object writable
--



vismPortCnfGrp          OBJECT IDENTIFIER ::= { vismPort 1 }

-- ------------------------------------------------------------------------
--
-- vismPortConfig group
--
-- This port configuration group is used for configuring the virtual
-- port between VISM and PXM. This group contains only a single port
-- which is the network port.
-- 
-- The virtual port has to be configured before adding connections (LCNs). 
-- All the LCNs are added on the same port. 
--
-- ------------------------------------------------------------------------

vismPortCnfGrpTable    OBJECT-TYPE
    SYNTAX    SEQUENCE OF VismPortCnfGrpEntry
    ACCESS    not-accessible
    STATUS    mandatory
    DESCRIPTION
        "Port configuration table for the virtual port.
	 Only one entry is allowed in this table.
        "
    ::= { vismPortCnfGrp 1 }


vismPortCnfGrpEntry    OBJECT-TYPE
    SYNTAX    VismPortCnfGrpEntry
    ACCESS    not-accessible
    STATUS    mandatory
    DESCRIPTION
        " An entry for logical port.
        "
    INDEX    { vismPortNum }
    ::= { vismPortCnfGrpTable 1 }

VismPortCnfGrpEntry ::=
    SEQUENCE {
        vismPortNum             INTEGER,
        vismPortRowStatus       INTEGER,
        vismPortLineNum         INTEGER,
        vismPortType            INTEGER,
        vismPortDs0ConfigBitMap INTEGER,
        vismPortSpeed           INTEGER,
        vismPortState           INTEGER
        }

vismPortNum    OBJECT-TYPE
    SYNTAX    INTEGER
    ACCESS    read-only
    STATUS    mandatory
    DESCRIPTION
        "This is a logical port number. If PXM1 is the PXM
         used on the shelf this object should be set to 1.
         For PXM1E this object should be set to 255.
          .
        "
    ::= { vismPortCnfGrpEntry 1}


vismPortRowStatus  OBJECT-TYPE
    SYNTAX  INTEGER {
            add(1),
            del(2),
            mod(3)
            }
    ACCESS read-write
    STATUS  mandatory
    DESCRIPTION
        "To add, del or modify a port.

         To add the port, this object has to be set to add, values
         for other objects should not be specififed (refer to Note 1).
         VISM will choose default values for all other objects (Note 1).

         Once added, the value mod is returned for a GET.
       
         To delete the port, this object has to be set to del. The port
         can be deleted only after deleting all the connections and the
         resource partition.
         
         Note 1: From VISM 2.x release onwards, vismPortRowStatus will be
         set to mod after adding the VISM port. Also, vismPortSpeed can
         be specified optionaly when VISM port is added.
         
        "
    ::= { vismPortCnfGrpEntry 2 }

vismPortLineNum    OBJECT-TYPE
    SYNTAX    INTEGER (0..8) 
    ACCESS    read-write
    STATUS    mandatory
    DESCRIPTION
        "This represents the line number to which this port is associated.
         Since the network port is not associated with any line,
         line number 0 is returned on a GET.

	     This object is currently not used and SET is not allowed on this
	     object.
        "
    DEFVAL { 0 }
    ::= { vismPortCnfGrpEntry 3}

vismPortType    OBJECT-TYPE
    SYNTAX    INTEGER {
              voIP     (1),
              userPort (2)
              }
    ACCESS    read-write
    STATUS    mandatory
    DESCRIPTION
        "The value of this object is always set to voIP. It indicates that
         it is the network port. The same value is used even when VISM 
         supports VoAAL1 or VoAAL2.

         The value userPort is not applicable for VISM.
         SET is not allowed on this object.
        "
    DEFVAL { voIP }
    ::= { vismPortCnfGrpEntry 4 }

vismPortDs0ConfigBitMap    OBJECT-TYPE
    SYNTAX    INTEGER (0..'ffffff'h) 
    ACCESS    read-write
    STATUS    mandatory
    DESCRIPTION
        "This respesents the bit map of DS0s which is used to create
         this port.  Bit 0 represents DS0-1.
         Since this object is not applicable to the network port, 
         value 0 is returned on a GET.
         SET is not allowed on this object.
        "
    DEFVAL { 0 }
    ::= { vismPortCnfGrpEntry 5 }

vismPortSpeed       OBJECT-TYPE
    SYNTAX  INTEGER (1..5651320)
    ACCESS  read-write
    STATUS  mandatory
    DESCRIPTION
        "The speed of the port in cells per second.
         It is used by VISM card to advertise virtual port bandwidth to 
         the controller, SVC and PVC connection admission control and 
         aggregate traffic clipping.

         This object can be modified only when there is no existing
         resource partition on the port.

         Changed from read-only to read-write from VISM2.x release.
        "
    DEFVAL { 5651320 }
    ::= { vismPortCnfGrpEntry 6 }

vismPortState OBJECT-TYPE
    SYNTAX  INTEGER {
            notConfigured(1),
            active       (2)
            }
    ACCESS  read-only
    STATUS  mandatory
    DESCRIPTION
        "This object indicates the state of the port.
        "
    ::= { vismPortCnfGrpEntry 7 }

--
-- ----------------------------------------------------------------------
-- BASIS Project MIB
--
--
-- VISM specific Port Resource Partition Configuration group
--
-- ------------------------------------------------------------------
--
-- Modification History
--
-- 11/22 Moved the default value for vismResPartCtrlrID from the description
--       section to  DEFVAL clause.
--
--       Added the description for mode-dependent default values for
--       vismResPartNumOfLcnAvail 
-- 
--       Adding and deleting resource partition is now supported through SNMP.
--        (Earlier it was deing done using CLI only). Hence changing the 
--         description accordingly.
--
-- 12/28/99 Changed vismResPartNumOfLcnAvail(0..248) to (0..380),
--          vismResPartLcnLow,vismResPartLcnHigh (1..248) to (131..510)
--
-- 01/06/00    changed the default for LcnHigh & LcnLow for the new Lcn range
--
-- 05/12/2000  modified description to reflect the elimination of modes
--             from vism 2.0.3 (Indiana) release onwards.
 
 

vismPortResPartCnfGrp        OBJECT IDENTIFIER ::= { vismPort 2 }

-- --------------------------------------------------------------------
--
--              PORT Resource Partition Configuration Group
--
-- This table is used to partition the PVCs(LCN) on the ports,
-- based on the controllers like par, pnni and tag.
--
-- Currently there is only one resource partition. In MGX release 1.0,
-- this belongs to the par controller. In MGX release 2.0, this belongs to
-- the pnni controller.
--
-- --------------------------------------------------------------------

vismPortResPartCnfGrpTable    OBJECT-TYPE
    SYNTAX  SEQUENCE OF VismPortResPartCnfGrpEntry
    ACCESS  not-accessible
    STATUS  mandatory
    DESCRIPTION
        "This table contains the configuration of port resource
         partition.
         Currently this table contains a single row.
        "
    ::= {vismPortResPartCnfGrp 1}

vismPortResPartCnfGrpEntry    OBJECT-TYPE
    SYNTAX  VismPortResPartCnfGrpEntry
    ACCESS  not-accessible
    STATUS  mandatory
    DESCRIPTION
        "An entry for port resource partition.
        "
    INDEX  { vismResPartPortNum, vismResPartCtrlrNum }
    ::= { vismPortResPartCnfGrpTable 1 }

VismPortResPartCnfGrpEntry ::=
    SEQUENCE {
        vismResPartPortNum        INTEGER,
        vismResPartCtrlrNum       INTEGER,
        vismResPartRowStatus      INTEGER,
        vismResPartNumOfLcnAvail  INTEGER,
        vismResPartLcnLow         INTEGER,
        vismResPartLcnHigh        INTEGER,
        vismResPartIngrPctBW      INTEGER,
        vismResPartEgrPctBW       INTEGER,
        vismResPartCtrlrID        INTEGER
        }

vismResPartPortNum    OBJECT-TYPE
    SYNTAX  INTEGER
    ACCESS  read-only
    STATUS  mandatory
    DESCRIPTION
        "This is the logical port number, the index to this table.
         If PXM1 is the PXM used on the shelf this object should 
         be set to 1. For PXM1E this object should be set to 255.
        "
    ::= { vismPortResPartCnfGrpEntry 1 }

vismResPartCtrlrNum OBJECT-TYPE
    SYNTAX  INTEGER {
            par (1),
            pnni(2),
            tag (3)
            }
    ACCESS  read-only
    STATUS  mandatory
    DESCRIPTION
        "This is index for controller using the port.
         
         In MGX release 1.0, the value par should be used.
         In MGX release 2.0, the value pnni should be used.
        "
    ::= { vismPortResPartCnfGrpEntry 2 }

vismResPartRowStatus OBJECT-TYPE
    SYNTAX  INTEGER {
            add (1),
            del (2),
            mod (3)
            }
    ACCESS  read-write
    STATUS  mandatory
    DESCRIPTION
        "This will add, delete or modify the partition.

         In MGX Release1.0:
             To add an entry, this object should be set to add, value
             for other objects should not be specified. VISM will choose
             default values for all other objects. 
         In MGX Release2.0:
             To add an entry, this object should be set to add, value
             for  vismResPartCtrlrID may be specified. VISM will choose
             default values for all other objects. 

         Currently the value mod is not supported.

         To delete an entry, this object has to be set to del. The resource
         partition can be deleted only after deleting all the connections 
         (LCNs).
        "
    ::= { vismPortResPartCnfGrpEntry 3 }

vismResPartNumOfLcnAvail OBJECT-TYPE
    SYNTAX  INTEGER (0..380)
    ACCESS  read-write
    STATUS  mandatory
    DESCRIPTION
        "This represents number of LCNs available for this
         controller and this port. The default value for this
         object is chosen based on vismMode :
             default value in voipSwitching mode - 3
             default value in aal2Trunking mode - 72
         Currently SET is not allowed on this object.

         From vism2.0.3 release onwards as there is no 
         concept of modes the number of lcns will 
         be set to maximum of number of lcns supported.
        "
    ::= { vismPortResPartCnfGrpEntry 4 }

vismResPartLcnLow OBJECT-TYPE
    SYNTAX  INTEGER(131..510)
    ACCESS  read-write
    STATUS  mandatory
    DESCRIPTION
        "This represents low end of reserved LCN.
         Currently SET is not allowed on this object.
        "
    DEFVAL { 131 }
    ::= { vismPortResPartCnfGrpEntry 5 }

vismResPartLcnHigh OBJECT-TYPE
    SYNTAX  INTEGER(131..510)
    ACCESS  read-write
    STATUS  mandatory
    DESCRIPTION
        "This represents high end of reserved LCN.
         Currently SET is not allowed on this object.
        "
    DEFVAL { 510 }
    ::= { vismPortResPartCnfGrpEntry 6 }

vismResPartIngrPctBW OBJECT-TYPE
    SYNTAX  INTEGER (0..100)
    ACCESS  read-write
    STATUS  mandatory
    DESCRIPTION
        "The percentage of total ingress bandwidth reserved.
         Since we have only one LCN for VoIP, the value is 100.
         Currently SET is not allowed on this object.

         From vism 2.0.3  release onwards since the mode will be
         gone this object will be writable.
        "
    DEFVAL { 100 }
    ::= { vismPortResPartCnfGrpEntry 7 }

vismResPartEgrPctBW OBJECT-TYPE
    SYNTAX  INTEGER (0..100)
    ACCESS  read-write
    STATUS  mandatory
    DESCRIPTION
        "The percentage of total egress bandwidth reserved 
         Since we have only one LCN for VoIP, the value is 100.
         Currently SET is not allowed on this object.
         
         From vism 2.0.3  release onwards since the mode will be
         gone this object will be writable.
        "
    DEFVAL { 100 }
    ::= { vismPortResPartCnfGrpEntry 8 }

vismResPartCtrlrID OBJECT-TYPE
    SYNTAX INTEGER(1..255)
    ACCESS read-write
    STATUS mandatory
    DESCRIPTION
        "This is the controller identifier of the PNNI controller. 
        "
    DEFVAL { 2 }
    ::= { vismPortResPartCnfGrpEntry 9 }


--
-- ----------------------------------------------------------------------
-- VISM1.5 Alabama Project MIB
--
--
-- VISM CAC (Connection Admission Control) group
--
-- ------------------------------------------------------------------
--
-- Modification History
-- 07/23 Incorporated the changes suggested in the review meeting. 
-- 12/28/99 Changed vismChanNum (32..279) to (131..510)
-- 04/25/2000 to make Indiana mib changes
-- 08/28/2000 Changed the range of vismChanVADTolerance and 
--              vismChanVADDutyCycle to include  0 



-- ------------------------------------------------------------------

vismChanCacTable OBJECT-TYPE
    SYNTAX  SEQUENCE OF VismChanCacEntry
    ACCESS  not-accessible
    STATUS  mandatory
    DESCRIPTION
        "This table defines the CAC success or failure statistics. CAC
		functionality is applied on a per PVC basis for accepting
		the new calls in a switching model (i.e when CRCX message is
		received from the Call Agent) and when adding a new binding 
		between a CID and a PVC in the AAL2 trunking application 
		('addcid' command). In both switching and trunking
		models, the CAC functionality is applied for upspeeding the
		connections due to the detection of fax/modem tone on a 
		connection configured with voice compression.
        "
    ::= { vismChanCnfGrp 3 }
 
vismChanCacEntry    OBJECT-TYPE
    SYNTAX  VismChanCacEntry
    ACCESS  not-accessible
    STATUS  mandatory
    DESCRIPTION
        "
		This table is used for CAC functions on a PVC. Each entry in this 
		table corresponds to a PVC, since the CAC functionality is applied
		on a per PVC basis. The bandwidth is allocated on a per PVC basis
		and the connection admission control is done by comparing the 
		available bandwidth on a PVC with the required bandwidth as a result
		of new connection setup request or upspeed request.
		The entries in this table are implicitly created and deleted with
		the creation and deletion of entries in vismChanCnfGrpEntry.
		"
    INDEX { vismChanNum }
    ::= { vismChanCacTable 1 }
 

VismChanCacEntry ::=
    SEQUENCE {
		vismChanNum 		   INTEGER,
		vismChanCacMaster	   INTEGER,
		vismChanCacPassedCons 	   Counter,
		vismChanCacRejectedCons    Counter,
		vismChanCacRejectionPolicy INTEGER,
                vismChanCarrierLossPolicy  INTEGER,
                vismChanVADTolerance       INTEGER, 
                vismChanVADDutyCycle       INTEGER,
                networkCacConfigState      INTEGER
          }

vismChanNum 	OBJECT-TYPE
	SYNTAX    INTEGER(131..510)
    ACCESS    read-only
    STATUS    mandatory
    DESCRIPTION
        "This attribute defines the index for the vismChanCac Table. The LCN
		Number is the same as the LCN value used as the index for the
		vismChanCnfGrpTable i.e. vismCnfChanNum 
        "
    ::= {vismChanCacEntry  1}

vismChanCacMaster     OBJECT-TYPE
	SYNTAX    INTEGER {
			master (1),
			slave  (2)
	}
    ACCESS    read-write
    STATUS    mandatory
    DESCRIPTION
        "This attribute defines whether the PVC is the master end or
		slave end. CAC functionality is applied only at the master
		end of the PVC. It is not necessary if the PVC end is configured
		as the slave end. This is to prevent the glare condition resulting
		from the simulatenous allocation of the same bandwidth for different
		calls from both the ends.
        This parameter is applicable only in the trunking mode.
        "
	DEFVAL { master }
    ::= {vismChanCacEntry  2}

vismChanCacPassedCons 	OBJECT-TYPE
	SYNTAX    Counter
    ACCESS    read-only
    STATUS    mandatory
    DESCRIPTION
        "This attribute defines the count of connections that
		passed successfully the CAC function. CAC functionality is
		applied either due to
		1) The CRCX message sent to VISM from the Call Agent to set
		up a new connection OR at the time of 'addcid' command in
		AAL2 trunking application.
		2) Upspeed request due to Fax/modem tone detection on a
		connection configured for compression.
		For the initial version of Alabama release, only case 2 is
		valid.			
		
        "
    ::= {vismChanCacEntry  3}

vismChanCacRejectedCons 	OBJECT-TYPE
	SYNTAX    Counter
    ACCESS    read-only
    STATUS    mandatory
    DESCRIPTION
        "This attribute defines the count of connections that 
		got rejected due to CAC function. The CAC rejection was   
		 due to the bandwidth not being available on a given PVC. 
        "
    ::= {vismChanCacEntry  4}

vismChanCacRejectionPolicy 	OBJECT-TYPE
	SYNTAX    INTEGER {
				delete (1),
				maintain (2),
                                unspecified (3)
			  }
    ACCESS    read-write
    STATUS    mandatory
    DESCRIPTION
        "This attribute defines the policy that needs to be applied
		 once the CAC function rejects the upspeeding of a connection,
		due to a fax/modem switch-over request. The applicable options
		are
		1 - To delete the connection that got rejected by CAC for upspeed
		2 - To maintain the connection with the prior compression scheme.
		Note that the default value of maintaining the prior encoding 
		scheme is applicable in the trunking application only since the
		connection is not deleted after the fax/modem switchover.
		In the case of switching application, the connection is deleted
		after the fax/modem switchover.
                From Indiana release onwards by default the value
                of this object will be unspecified. 

                If the value of this object is 'unspecified' then the 
                cac rejection policy as defined in the card 
                level object vismCacRejectionPolicy will be used,
                else the value of this object will be used .
 
                Configuring this object will not have any affect when
                card level cac is disabled (vismCacEnable).

        "
    ::= {vismChanCacEntry  5}


vismChanCarrierLossPolicy    OBJECT-TYPE
       SYNTAX    INTEGER {
                              previousCodec (1),
                              upspeedCodec  (2), 
                              unspecified   (3)
                         }
       ACCESS   read-write
       STATUS   mandatory
       DESCRIPTION
            " 
               This object defines the policy that needs to be applied  
               when a carrier loss is detected.

               This states whether to switch to the pre-upspeed codec or
               to remain with the upspeed codec.

               By default the value of this object will be unspecified
               in that case the card level object value (vismCarrierLossPolicy)
               will be used.
               Configuring this object will not have any affect when
               card level cac is disabled (vismCacEnable).

            "
       DEFVAL{unspecified}
      ::= {vismChanCacEntry 6}

vismChanVADTolerance  OBJECT-TYPE
       SYNTAX  INTEGER(0..10000)
       ACCESS  read-write
       STATUS  mandatory
       DESCRIPTION
           "
             The value in this object refers to the customer accepted 
             drop rate for voice connections when the bandwidth usage
             exceeds allowed value.      
             
             The actual range of this object is 0.0001% - 1.00 %
            
             The unit is in percentage, since the default is 0.01 %,
             and since we cannot express such fractions
             in MIB , it is being multiplied by 10000 .

             However, when the underlying CAC module is notified of
             the change in this object,  then the value
             has to be divided by a factor of 10000. 

             Multiplication factor 10000 is picked as someone might be 
             interested in a tolerance as low as 0.0001%.

             A value of zero indicates an invalid value. In that
             case the card level object value will be used (vismVADTolerance).

             Configuring this object will not have any affect when
             card level cac is disabled (vismCacEnable).

           " 
       DEFVAL {100}
       ::= {vismChanCacEntry 7}

vismChanVADDutyCycle  OBJECT-TYPE
       SYNTAX  INTEGER (0..100)   
       ACCESS  read-write
       STATUS  mandatory
       DESCRIPTION
           "
             This object refers to the talk-spurts duty cycle.
             The unit is in percentage.
  
             The actual range of this object is 0.01 to 0.99 %
             and not 0.01 to 1.00 % as specified in the range
             values above.  Since a value of 100 will cause a 
             floating point exception, this value is disallowed.

             The default value is 0.61% and since we cannot
             have fractions in a MIB variable the value
             is being multiplied by 100 and is expressed as
             61.

             When the value of this object is to be passed
             to underlying CAC module in VISM this value has to
             be divided by 100.  

             A value of zero indicates an invalid value. In that
             case the card level object value will be used (vismVADDutyCycle).

             Configuring this object will not have any affect when
             card level cac is disabled (vismCacEnable).

             only value 1 - 99 is allowed to be set.
           " 
       DEFVAL {61}
       ::= {vismChanCacEntry 8}


networkCacConfigState     OBJECT-TYPE
        SYNTAX    INTEGER {
                        ok (1),
                        notOk  (2)
        }
    ACCESS    read-only
    STATUS    mandatory
    DESCRIPTION
        "  This attribute defines whether the originating and terminating
           VISMs are configured properly or not, by default the
           configuration is assumed to be ok and this object is set
           to ok, if later during upspeed if we discover that both
           the originating and terminating VISMs are configured as 
           either cac master or slave then it is considered as an 
           invalid configuration and this object will be set to 'notOk' 
           and trapNetworkCacConfigState change trap will be sent. 
                
           This parameter is applicable only in trunking applications.
        "
        DEFVAL { ok }
    ::= {vismChanCacEntry  9}


--
-- ----------------------------------------------------------------------
-- BASIS Project MIB
--
--
-- VISM cardSpecific vismCas group
--
-- ------------------------------------------------------------------
--
-- Modification History
-- 
-- 10/25 Changed the DEFVAL for vismCasDigitMethod from mf to dtmf
--
-- 11/23 Added DEFVAL clause for vismCasCountryCode
--
-- 03/10 Removed sentences which says vismCasVariantTable is only
--       applicable for cas backhaul feature, and also added that
--       the vismCasXgcpVariantTable is implicitly created only
--       in switching mode. 
--
-- 04/19      Change the range of vismCasTRinging from 10 - 100 to 100 - 600
--            and the default value from 30 to 180.
--
-- 04/03/2001 Add new MIB object: vismCasVarientSource and deprecated two 
--            MIB objects: vismCasTRinging and vismCasCountryCode. Added 
--            additional comments to the vismCasRowStatus DESCRIPTION. 
--


 
 
vismCasGrp              OBJECT IDENTIFIER ::= { voice 8 }
 









-- ------------------------------------------------------------------
--
-- vismCasConfig group
--
--
-- The MIB variables in this group have been defined to configure
-- the CAS backhaul feature on VISM. In the current release, CAS
-- is backhauled to the Call Agent using SGCP protocol. VISM card
-- can be configured with different CAS variants by downlading the
-- file which contains the signal definition and the state machine
-- information about the CAS variant.
--
-- ------------------------------------------------------------------


vismCasVariantTable OBJECT-TYPE
    SYNTAX  SEQUENCE OF VismCasVariantEntry
    ACCESS  not-accessible
    STATUS  mandatory
    DESCRIPTION
        "This table contains configuration information about 
         different CAS variants.
        "
    ::= { vismCasGrp 1 }

vismCasVariantEntry OBJECT-TYPE
    SYNTAX  VismCasVariantEntry
    ACCESS  not-accessible
    STATUS  mandatory
    DESCRIPTION
        "An entry in the vismCasVariantTable. Each entry consists 
         of configuration information for a specific CAS variant.

         An entry may be created by specifying vismCasVariantName, 
         and vismCasFileName. Upon the creation of the table entry, 
         the file specified by vismCasFileName will be downloaded 
         and the CAS finite state machine will be initialized based 
         on the information contained in this file.
        "
    INDEX { vismCasVariantName }
    ::= { vismCasVariantTable 1 }

VismCasVariantEntry ::=
    SEQUENCE {
        vismCasVariantName      DisplayString,
        vismCasFileName         DisplayString,
        vismCasTRinging         INTEGER,
        vismCasDigitMethod      INTEGER,
        vismCasInterdigitTpart  INTEGER,
        vismCasInterdigitTcrit  INTEGER,
        vismCasInterdigitTMF    INTEGER,
        vismCasVariantState     INTEGER,
        vismCasRowStatus        INTEGER,
        vismCasCountryCode      DisplayString,
        vismCasVariantSource    INTEGER
        }

vismCasVariantName    OBJECT-TYPE
    SYNTAX  DisplayString 
    ACCESS  read-only
    STATUS  mandatory
    DESCRIPTION
        " This object is a string identifier for the CAS variant. 
          It is used as index to the table.
          The maximum length allowed is 64 bytes.
        "
    ::= { vismCasVariantEntry 1 }

vismCasFileName    OBJECT-TYPE
    SYNTAX  DisplayString(SIZE (2..64))
    ACCESS  read-write
    STATUS  mandatory
    DESCRIPTION
        " This object gives the name of the file which contains the signal 
          definition and the Finite State Machine definition for the CAS 
          variant. The name is supplied during the creation of the table entry.  
          Modifying the value of this object is not allowed.
          Upon the creation of the table entry, the file will be downloaded
          from a tftp server configured in the vismTftpServerDn object
          and the CAS finite state machine will be initialized
          based on the information contained in this file.
          This object must be provided in order to create en entry in this table.
        "
    ::= { vismCasVariantEntry 2 }



-- This object is deprecated as we have a separate ringing timeout
-- on a per line basis

vismCasTRinging    OBJECT-TYPE
    SYNTAX  INTEGER(10..600) 
    ACCESS  read-write
    STATUS  deprecated
    DESCRIPTION
        " This object gives the ringing time in seconds for the Cas 
          Variant. The ringing will be on until this timer expires or 
          until an off hook is received. 
        "
    DEFVAL { 180 }
    ::= { vismCasVariantEntry 3 }





vismCasDigitMethod    OBJECT-TYPE
    SYNTAX  INTEGER {
             mf (1),
             dtmf (2)
            }
    ACCESS  read-write
    STATUS  mandatory
    DESCRIPTION
        " The default digit method to be used for digit collection.
          If the digit method can not be derived from the digit map
          specified by the call agent in the XGCP message, this digit
          method will be used.
        "
    DEFVAL { dtmf }
    ::= { vismCasVariantEntry 4 }





vismCasInterdigitTpart    OBJECT-TYPE
    SYNTAX  INTEGER (10..10000)
    ACCESS  read-write
    STATUS  mandatory
    DESCRIPTION
        " This object represents the partial dial timing in
          seconds and is used along with a digit map as the 
          inter-digit timer.
          The timer is not started untill the first digit is 
          entered, and the timer is restarted after each new 
          digit is entered untill either a digit map match or 
          mismatch occurs. 
        "
    DEFVAL { 16 }
    ::= { vismCasVariantEntry 5 }





vismCasInterdigitTcrit    OBJECT-TYPE
    SYNTAX  INTEGER (0..10000)
    ACCESS  read-write
    STATUS  mandatory
    DESCRIPTION
        " This object represents the critical timing in seconds. 
          If used along with a digit map, the timer is started when 
          the last digit is received. i.e and when no more digits 
          are required for a digit map match. After this timer
          expires, the digit map match is assumed to be complete.
          If used without a digit map, the timer is started 
          immediately and cancelled (but not restarted) as soon 
          as a digit is entered.
        "
    DEFVAL { 4 }
    ::= { vismCasVariantEntry 6 }





vismCasInterdigitTMF    OBJECT-TYPE
    SYNTAX  INTEGER(1..10) 
    ACCESS  read-write
    STATUS  mandatory
    DESCRIPTION
        "This object represents the interdigit timeout value for MF
         digits. The timeout value is in seconds. 
        "
    DEFVAL { 1 }
    ::= { vismCasVariantEntry 7 }





vismCasVariantState    OBJECT-TYPE
    SYNTAX  INTEGER {
            notConfigured  (1),
            configInProgress (2),
            configured (3)
            }
    ACCESS  read-only
    STATUS  mandatory
    DESCRIPTION
        "This variable indicates the configuration status of the 
         CAS variant. When the table entry is created, downloading
         of the file will be initiated and the state will be set to
         configInProgress. Once the file is successfully downloaded
         and the CAS finite state machine successfully initialized,
         the state will be set to configured. If the initialization
         fails, the state will be set to notConfigured.
        "
    ::= { vismCasVariantEntry 8 }





vismCasRowStatus  OBJECT-TYPE		
	SYNTAX	INTEGER {
		active(1),
		createAndGo(4),
		destroy(6)
		}
	ACCESS read-write
        STATUS  mandatory
        DESCRIPTION
        "This variable allows to add, delete or modify the entry for
         a CAS variant.

         createAndGo: Use this to add an entry in this table, provided the
                      vismCasVariantName and vismCasFileName MIB objects are 
                      available to be set.

         active: This values is returned, once the row is created

         destroy: Use this to delete an entry from this table.
        "
        ::= { vismCasVariantEntry 9 }



-- This object is deprecated as we have a seperate country code tone plans
-- on a per line basis

vismCasCountryCode    OBJECT-TYPE
    SYNTAX  DisplayString(SIZE (0..2))
    ACCESS  read-write
    STATUS  deprecated
    DESCRIPTION
        " Represents a case-insensitive 2-letter country code
          taken from ISO-3166. 
        "
    DEFVAL { "US" }
    ::= { vismCasVariantEntry 10 }





vismCasVariantSource    OBJECT-TYPE
    SYNTAX  INTEGER {
            unspecified (1),
            internal    (2),
            external    (3)
            }
    ACCESS  read-write
    STATUS  mandatory
    DESCRIPTION
        "This object specifies where the file defining this CAS variant
         resides.

         1. Unspecified. This value indicates that the location of the file is not
                         specified here. In this case, the location is determined
                         based on whether the TFTP server domain is defined on
                         VISM. The file is built into the firmware if no tftp
                         domain is defined on VISM and resides on the TFTP server
                         if a TFTP domain is defined on VISM.
         2. Internal. Indicates that the file is built into the firmware.
         3. External. Indicates that the file resides on the TFTP server
                      configured on VISM.
        "
    DEFVAL { unspecified }
    ::= { vismCasVariantEntry 11 }













-- --------------------------------------------
-- vismCasXgcpVariantTable
-- --------------------------------------------

vismCasXgcpVariantTable OBJECT-TYPE
    SYNTAX  SEQUENCE OF VismCasXgcpVariantEntry
    ACCESS  not-accessible
    STATUS  mandatory
    DESCRIPTION
        "
         An entry in this table is implicitly created/deleted
         when an entry in vismCasVariantTable is created/deleted in 
         switching mode ."
    ::= { vismCasGrp 2 }

vismCasXgcpVariantEntry OBJECT-TYPE
    SYNTAX  VismCasXgcpVariantEntry
    ACCESS  not-accessible
    STATUS  mandatory
    DESCRIPTION
        "An entry in the vismCasXgcpVariantTable.
        "
    INDEX { vismCasXgcpVariantName }
    ::= { vismCasXgcpVariantTable 1 }

VismCasXgcpVariantEntry ::=
    SEQUENCE {
        vismCasXgcpVariantName        DisplayString,
        vismCasXgcpFileName           DisplayString,
        vismCasXgcpMaxReXmitTime      INTEGER,
        vismCasXgcpInitialReXmitTime  INTEGER,
        vismCasXgcpMaxRetries         INTEGER
        }

vismCasXgcpVariantName    OBJECT-TYPE
    SYNTAX  DisplayString 
    ACCESS  read-only
    STATUS  mandatory
    DESCRIPTION
        " This object is a string identifier for the CAS variant. 
          It is used as index to the table.
        "
    ::= { vismCasXgcpVariantEntry 1 }

vismCasXgcpFileName    OBJECT-TYPE
    SYNTAX  DisplayString 
    ACCESS  read-only
    STATUS  mandatory
-- obsolete
    DESCRIPTION
        " This object gives the name of the file which contains the signal 
          definition and the Finite State Machine definition for the CAS 
          variant.
        "
    ::= { vismCasXgcpVariantEntry 2 }

vismCasXgcpMaxReXmitTime    OBJECT-TYPE
    SYNTAX  INTEGER (10..10000)
    ACCESS  read-write
    STATUS  mandatory
    DESCRIPTION
        " This object represents the maximum timeout value in milli seconds,
          used for retransmitting unacknowledged XGCP messages at the 
          Call Agent - CAS/PBX interface. The value of this object 
          is settable in 10 ms increments. 
        "
    DEFVAL { 500 }
    ::= { vismCasXgcpVariantEntry 3 }

vismCasXgcpInitialReXmitTime    OBJECT-TYPE
    SYNTAX  INTEGER (10..10000)
    ACCESS  read-write
    STATUS  mandatory
    DESCRIPTION
        " This object represents the initial timeout value in milli seconds,
          used for retransmitting unacknowledged XGCP messages at the 
          Call Agent - CAS/PBX interface. The value of this object 
          is settable in 10 ms increments. 
        "
    DEFVAL { 100 }
    ::= { vismCasXgcpVariantEntry 4 }

vismCasXgcpMaxRetries    OBJECT-TYPE
    SYNTAX  INTEGER (0..10)
    ACCESS  read-write
    STATUS  mandatory
    DESCRIPTION
        " This object specifies the number of retries for a 
          message that exceeds vismCasXgcpMaxReXmitTime or 
          vismCasXgcpInitialReXmitTime.
        "
    DEFVAL { 4 }
    ::= { vismCasXgcpVariantEntry 5 }
 








--
-- ----------------------------------------------------------------------
-- VISM1.5 Alabama Project MIB
--
--
-- VISM CID Table group
--
-- ------------------------------------------------------------------
--
-- Modification History
-- 07/23 Incorporated the changes suggested in the review meeting. 
-- 
-- 10/25 Added a new value clearChannel for vismAal2CidCodecType
-- 10/25 Added vismAal2InitVadTimer object to Cid table
-- 11/22 Added more description for RowStatus to specify what values
--       need to be used for adding/deleting and what are the mandatory
--       parameters for adding. Also added the description
--       that modifying an entry in CID table is not allowed.
--
-- 11/23  Changed the DEFVAL for vismAal2CidProfileType from itu to custom
--
--        Added DEFVAL clause for vismAal2CidProfileNum
--
-- 11/22 Change the description for vismAal2CidCasTransport and 
--       vismAal2CidDtmfTransport default value to be true.
--
-- 12/22 Removed reference to cnfcid from vismAal2CidCodecType description
-- 12/24 vismAal2InitVadTimer range changed from 200..65535 to 250..65535. 
--       The default value of this object changed from 200 to 250.
-- 12/28 Changed vismAal2CidLcn (32..279) to (131..510)
-- 02/23 Changed some old descriptions which are no longer valid
--
-- VISM1.53
-- 03/10/00 Introduced new object vismAal2CnfPktPeriod 
--          Added new object to configure Idle Channel Suppression on a cid.
-- VISM1.53
-- 04/25/2000 changed the mib description of vismAal2CnfPktPeriod and vismAal2CidVad
-- INDIANA
-- 07/-6/2000 Added vismAal2CidState object also changed the range
--            of vismAal2EndptNum
-- 08/25/2000 Changed the range of vismCidNum to 8..255 
--
-- 10/10/2000 Changed the description of vismAal2ProfileType and 
--            vismAal2ProfileNum to say that they are mandatory 
--            parameters for adding a cid.
--
-- 01/17/2001 Add g-726-16, g-726-24, g-726-40 to vismAal2CidCodecType
--
-- 01/19/2001 change codec type to g726r16000, g726r24000, g726r40000
-- 09/10/2001 Added codec G723 family
--
-- 09/28/2001 add vismAal2CidFailReason for CSCdv43998




vismAal2CidGrp       OBJECT IDENTIFIER ::= {vismChanGrp 4}
 
-- ------------------------------------------------------------------
vismAal2CidCnfTable OBJECT-TYPE
    SYNTAX  SEQUENCE OF VismAal2CidEntry
    ACCESS  not-accessible
    STATUS  mandatory
    DESCRIPTION
       "This table is defined to establish the binding between an endpoint
        and a PVC/CID pair in the case of AAL2 adaptation.  This table is
	created and used in trunking mode VISM application only. 

        The maximum number of CIDs that can be configured depends on the
        current codec template being used as represented by vismAppliedTemplate
        object. The signaling type of the line has to be configured before
        adding any CID on that line.

        "
    ::= { vismAal2CidGrp 1 }
 
vismAal2CidEntry    OBJECT-TYPE
    SYNTAX  VismAal2CidEntry
    ACCESS  not-accessible
    STATUS  mandatory
    DESCRIPTION
        "
		Please see the above description.
		"
    INDEX { vismAal2CidLcn, vismAal2CidNum }
    ::= { vismAal2CidCnfTable 1 }
 

VismAal2CidEntry ::=
    SEQUENCE {
		vismAal2CidNum 		        INTEGER,
		vismAal2CidLcn		        INTEGER,
                vismAal2EndptNum            INTEGER,
		vismAal2CidRowStatus 		INTEGER,
		vismAal2CidType3Redundancy	TruthValue,
		vismAal2CidVad		        TruthValue,
		vismAal2CidProfileType		INTEGER,
		vismAal2CidProfileNum		INTEGER,
		vismAal2CidCodecType		INTEGER,
		vismAal2CidDtmfTransport	TruthValue,
		vismAal2CidCasTransport		TruthValue,
		vismAal2CidEcanEnable		TruthValue,
		vismAal2InitVadTimer		INTEGER,
-- VISM1.53
                vismAal2CnfPktPeriod            INTEGER,
                vismAal2CidICSEnable            TruthValue,
-- VISM1.53
                vismAal2CidState                INTEGER,
                vismAal2CidFailReason           INTEGER
}

vismAal2CidNum 	OBJECT-TYPE
    SYNTAX    INTEGER (8..255)
    ACCESS    read-only
    STATUS    mandatory
    DESCRIPTION
        "This attribute defines part of the index for the cid Table. 
         vismAal2CidNum is the CID (or Channel ID) of a voice channel. CID has to be
	 the same at both endpoints for a connection. CID is unique only within
	 the context of a Virtual Circuit (PVC or SVC).
        "
    ::= {vismAal2CidEntry  1}

vismAal2CidLcn 	OBJECT-TYPE
    SYNTAX    INTEGER (131..510)
    ACCESS    read-only
    STATUS    mandatory
    DESCRIPTION
        "This attribute defines part of the index for the cid Table. 
	 Since CID is unique to a PVC, a combination of LCN and CID uniquely
	 identifies a voice connection.
	 This field refers to vismChanNum defined in vismChanCnfGrp.
        "
    ::= {vismAal2CidEntry  2}

vismAal2EndptNum     OBJECT-TYPE
    SYNTAX  INTEGER(1..65535)
    ACCESS  read-write
    STATUS  mandatory
    DESCRIPTION
          "This attribute defines the endpoint number to which this
           CId is associated. It is the same as mgEndpointNumber in 
           in mgEndpointTable 
          "
     ::= {vismAal2CidEntry 3}

vismAal2CidRowStatus 	OBJECT-TYPE
    SYNTAX    INTEGER {
			  active (1),
			  createAndGo (4),
			  destroy (6)
			  }
    ACCESS    read-write
    STATUS    mandatory
    DESCRIPTION
        "This variable allows to add or delete a CID.  A CID can only be 
         added or deleted. Once added, mdifying an entry is not allowed.
         createAndGo: Use this to add an entry in this table.
         active: This values is returned, once the row is created
         destroy: Use this to delete an entry from this table.

         For creating a CID, a value for vismAal2EndptNum, vismAal2CidCodecType 
         vismAal2CidProfileType, vismAal2CidProfileNum must be provided. To all 
         other objects, defaults defined by the agent implementation may apply.
        "
    ::= {vismAal2CidEntry  4}

vismAal2CidType3Redundancy 	OBJECT-TYPE
	SYNTAX    TruthValue
    ACCESS    read-write
    STATUS    mandatory
    DESCRIPTION
        "This attribute defines whether the triple redundancy is supported
         for type 3 packets in AAL2 for this channel. When Triple redundancy 
         is enabled for a channel, the type 3 packets (CAS bits, dialled digits
         and user state control packets) are transmitted in triplicates with an
         interval defined as per the standards I.366.2. For channels which are
         quite reliable, triple redundancy can be disabled in order to save the
         bandwidth and the processing overheads. 

         The default value of this object is true if either
         vismAal2CidCasTransport or vismAal2CidDtmfTransport is true, otherwise
         the default value is false.
        "
    ::= {vismAal2CidEntry  5}

vismAal2CidVad 	OBJECT-TYPE
	SYNTAX    TruthValue
    ACCESS    read-write
    STATUS    mandatory
    DESCRIPTION
        "This attribute defines whether the VAD (Voice Activity Detection) 
         has to be applied on this channel, upon detection of silence. 
         For algorithms that do not have VAD (Voice Activity Detection) 
         standards, Cisco-proprietary VAD can be applied and the generic 
         SID packet as specified in I.366.2 standards can be sent to the 
         other end. 
 
         When the codecType is clearChannel vad has to be off.
        "
	DEFVAL { false }
    ::= {vismAal2CidEntry  6}

vismAal2CidProfileType 	OBJECT-TYPE
	SYNTAX    INTEGER {
				itu	(1),
				atm (2),
				custom (3),
				none (4)
			  }
    ACCESS    read-write
    STATUS    mandatory
    DESCRIPTION
        "This attribute defines the profile type. The profile type 
         defines which group of the profile tables the profile number 
         should correspond to. There are three possible groups:
         itu - corresponding to the tables in ITU 
         format in the profile is being used.
         atm - This is not supported
         custom - VISM specific custom profiles

         For doing a SET on this object, a value for vismAal2CidprofileNum also
         has to be specified.
 
         This is a mandatory parameter while adding a cid.
        "
	DEFVAL { custom }
    ::= {vismAal2CidEntry  7}

vismAal2CidProfileNum 	OBJECT-TYPE
	SYNTAX    INTEGER
    ACCESS    read-write
    STATUS    mandatory
    DESCRIPTION
        "This attribute defines the profile number. A profile is a set of
         entries, where each entry specifies an encoding format with a UUI range
         and length. This set defines a mapping that informs the receiver of a
         type 1 packet how to interpret the packet contents, i.e. which encoding
         format in the profile is being used.

         For doing a SET on this object, a value for vismAal2CidprofileType also
         has to be specified.
         
         This is a mandatory parameter while adding a cid.
        "
	DEFVAL { 100 }
    ::= {vismAal2CidEntry  8}

vismAal2CidCodecType 	OBJECT-TYPE
	SYNTAX    INTEGER {
                g711u        (1),
                g711a        (2),
                g726r32000   (3),
                g729a        (4),
                g729ab       (5),
                clearChannel (6),
                g726r16000   (7),
                g726r24000   (8),
                g726r40000   (9),
                g723h        (11),
                g723ah       (12),
                g723l        (13),
                g723al       (14)
				}
    ACCESS    read-write
    STATUS    mandatory
    DESCRIPTION
        "This attribute defines the codec Type used for the connection. 

		g711u        represents PCMU with 64 kbps.
		g711a        represents PCMA with 64 kbps.
        g726r32000   represents G.726 at rate 32 kbps
        g726r16000   represents G.726 at rate 16 kbps
        g726r24000   represents G.726 at rate 24 kbps
        g726r40000   represents G.726 at rate 40 kbps
		g729a        represents G.729 Annex A algorithm.
		g729ab       represents G.729 Annex A and Annex B algorithm.
		clearChannel represents CCD with 64 kbps.
		g723h        represents G.723.1-H at rate 6.3kbps.
		g723ah       represents G.723.1-H at rate 6.3kbps with Silence Supression(SID)
				     ON.
		g723l        represents G.723.1-L at rate 5.3kbps.
		g723al       represents G.723.1-L at rate 5.3kbps with Silence Supression(SID)
				     ON.

        Note : 
			1. When codec type is clearChannel, vismAal2CidProfileType
               and vismAal2CidProfileNum are not applicable and will be ignored.

            2. Value 10 is RESERVED and can't be used in future. 

        "
    ::= {vismAal2CidEntry  9}

vismAal2CidDtmfTransport	 	OBJECT-TYPE
	SYNTAX    TruthValue
    ACCESS    read-write
    STATUS    mandatory
    DESCRIPTION
        "This attribute defines whether the DTMF (Dual Tone Multi Frequency)
	digits need to be transported to the other end-point. 
        "
	DEFVAL { true }
    ::= {vismAal2CidEntry  10}

vismAal2CidCasTransport		OBJECT-TYPE
	SYNTAX    TruthValue
    ACCESS    read-write
    STATUS    mandatory
    DESCRIPTION
        "This attribute defines whether the CAS (ABCD bits) bits need to be
	transported to the other endpoint. In the case of switching application,
	the CAS bits are backhauled to the Call Agent thro' xGCP-CAS protocol.

	Note that if the line signaling type is CAS the default value is TRUE,
	else the default value is FALSE.
        "
    ::= {vismAal2CidEntry  11}

vismAal2CidEcanEnable		OBJECT-TYPE
    SYNTAX    TruthValue
    ACCESS    read-write
    STATUS    mandatory
    DESCRIPTION
        "This attribute defines whether Echo Cancellation has to be enabled
         on this connection. If it is set to True, echo cancellation is 
         enabled. If it is set to False, echo cancellation is disabled.
        "
	DEFVAL { true }
    ::= {vismAal2CidEntry  12}

vismAal2InitVadTimer		OBJECT-TYPE
    SYNTAX    INTEGER(250..65535)
    ACCESS    read-write
    STATUS    mandatory
    DESCRIPTION
        "This attribute defines the hangover time for VAD in milliseconds. 
         Once the voice inactivity is detected, the gateway will wait for 
         this duration before activating silence suppression.
        "
	DEFVAL { 250 }
    ::= {vismAal2CidEntry  13}

-- VISM1.53

vismAal2CnfPktPeriod         OBJECT-TYPE
   SYNTAX    INTEGER 
              {
                five (5),
                ten (10),
                twenty (20),
                thirty(30),
                fourty (40)
              }
   ACCESS    read-write
   STATUS    mandatory
   DESCRIPTION
       "
       This object is used to configure the packetization period for
       a given codec. This pkt  period has to be a valid entry in the profile table.
       Profile type and number identify a unique profile table and one codec
       type in this table might have one or more packetization period. This
       is applicable only if the vismAal2CidCodecType is G.729a. 

       The configurable values for G.729a are 10,20,30 & 40. 
       If a cid entry is configured with a codec other than G.729a then the user
       cannot configure the pkt period for that codec and the pkt period is picked
       from the profile table. 
  
       Hence when we do get/walk on this entry/table any one of the above values could
       be returned.

       The packetization periods of 20, 30 and 40 ms. are not allowable in
       case of G729-a for the list of profiles that we support now. We can
       only support 10ms.

	   For G.723 the configurable values is 30.  Default value would be 30.

       Please see ENG-45055 or ITU specification I.366.2 annex P for more 
       information.
       "
     DEFVAL{ten}
     ::= {vismAal2CidEntry 14}

vismAal2CidICSEnable     OBJECT-TYPE
     SYNTAX        TruthValue
     ACCESS        read-write
     STATUS        mandatory
     DESCRIPTION
        "
          This object is used to enable or disable the Idle Channel Suppresion for
          a cid. This can be specified while adding the cid and cannot be modified.

          When the Idle Channel Suppression is enabled the DSP will look for the 
          idle cas (ABCD bits) pattern specified in ds0IdleCode in dsx0 MIB. If
          the idle pattern is present the DSP stops generating voice packets towards
          ATM side. By default the ds0IdleCode will be zero unless the user has 
          configured it before adding the cid. If the ds0IdleCode is 
          changed after the cid is added it will have no affect unless the card is reset.

          Idle Channel Suppression is applicable only for trunking application,
          In case of switching there is no need for Idle channel Suppression as the
          calls are teared down and set up dynamically.
   
        "
        DEFVAL {false}
        ::= {vismAal2CidEntry 15}

-- VISM1.53

vismAal2CidState OBJECT-TYPE
    SYNTAX      INTEGER {
                cidStateActive        (1),
                cidStateFailed        (2)
                }
    ACCESS     read-only
    STATUS     mandatory
    DESCRIPTION
            "Indicates the state of the cid.
             active - the cid is in service and operational
             failed - the cid is in service but not operational,
                      e.g. because the PVC that the cid belongs to 
                           is receiving F5 level alarm
   
             When VISM sees alarm on a CID (network side) sets
             this object to cidStateFailed, trapVismCidState
             trap will be sent, and an AIS will be sent
             on the ds0 that this cid corresponds to. 

             If the whole PVC is in alarm then all the cids 
             on that PVC will be set to cidStateFailed, 
             trapVismChanFailed trap will be sent and all 
             the ds0's that corresponds to each of the cids
             on this PVC will be in alarm. (NOTE: no trapVismCidState
             will be sent).

             If VISM sees an alarm on a ds0 in a line then 
             an RAI will be sent on the cid that corresponds
             to this ds0, however the cid will not be put in
             failed state.
            "
    ::= { vismAal2CidEntry 16 }

vismAal2CidFailReason OBJECT-TYPE
    SYNTAX      INTEGER {
                self        (1),
                highLevel   (2),
                both        (3),
                notFail     (4)
                }
    ACCESS     read-only
    STATUS     mandatory
    DESCRIPTION
            "This object is used to indicate the cid failure
             reason.
                 self: fail because of non-PVC alarm
                 highLevel: fail because of PVC alarm
                 both: fail because of both PVC and non-PVC alarm
                 notFail: not fail
            "
    DEFVAL {notFail}
    ::= { vismAal2CidEntry 17 }



--
--
-- =====================================================================
-- VISM 2.0 Project MIB
--
--
--
--
--    Revision history:
--                      Second draft : August 25, 1999
--
--
-- ====================================================================
--
-- Modification History
--
-- 1/31/2001 Change hyphen to "=" in this file
--



vismSvcGrp            OBJECT IDENTIFIER ::= { voice 10 }

-- 
-- VISM 2.0 Counters
-- 


vismSvcTxSetups  OBJECT-TYPE
    SYNTAX     Counter
    ACCESS     read-only
    STATUS     mandatory
    DESCRIPTION
        " This is the number of Setup messages sent to the PXM
          from the VISM since VISM reset.
        "
    ::= { vismSvcGrp 1 }
    
vismSvcRxSetups  OBJECT-TYPE
    SYNTAX     Counter
    ACCESS     read-only
    STATUS     mandatory
    DESCRIPTION
        " This is the number of Setup messages received by the VISM
          from the PXM since VISM reset.
        " 
    ::= { vismSvcGrp 2 }
    
vismSvcTxCallProcs  OBJECT-TYPE
    SYNTAX     Counter
    ACCESS     read-only
    STATUS     mandatory
    DESCRIPTION
        " This is the number of Call proceeding messages sent to the PXM
          from the VISM since VISM reset.
        "
    ::= { vismSvcGrp 3 }
    
vismSvcRxCallProcs  OBJECT-TYPE
    SYNTAX     Counter
    ACCESS     read-only
    STATUS     mandatory
    DESCRIPTION
        " This is the number of Call proceeding messages received by the VISM
          from the PXM since VISM reset.
        " 
    ::= { vismSvcGrp 4 }
    
vismSvcTxConns  OBJECT-TYPE
    SYNTAX     Counter
    ACCESS     read-only
    STATUS     mandatory
    DESCRIPTION
        " This is the number of Connect messages sent to the PXM
          from the VISM since VISM reset.
        "
    ::= { vismSvcGrp 5 }
    
vismSvcTxConnAcks  OBJECT-TYPE
    SYNTAX     Counter
    ACCESS     read-only
    STATUS     mandatory
    DESCRIPTION
        " This is the number of Connect ack messages sent to the PXM
          from the VISM since VISM reset.
        "
    ::= { vismSvcGrp 6 }
    
vismSvcRxConns  OBJECT-TYPE
    SYNTAX     Counter
    ACCESS     read-only
    STATUS     mandatory
    DESCRIPTION
        " This is the number of Connect messages received by the VISM
          from the PXM since VISM reset.
        " 
    ::= { vismSvcGrp 7 }
    
vismSvcRxConnAcks  OBJECT-TYPE
    SYNTAX     Counter
    ACCESS     read-only
    STATUS     mandatory
    DESCRIPTION
        " This is the number of Connect ack messages received by the VISM
          from the PXM since VISM reset.
        " 
    ::= { vismSvcGrp 8 }
    
vismSvcTxReleases  OBJECT-TYPE
    SYNTAX     Counter
    ACCESS     read-only
    STATUS     mandatory
    DESCRIPTION
        " This is the number of Release messages sent to the PXM
          from the VISM since VISM reset.
        "
    ::= { vismSvcGrp 9 }
    
vismSvcTxReleaseCompls  OBJECT-TYPE
    SYNTAX     Counter
    ACCESS     read-only
    STATUS     mandatory
    DESCRIPTION
        " This is the number of Release complete messages sent to the PXM
          from the VISM since VISM reset.
        "
    ::= { vismSvcGrp 10 }
    
vismSvcRxReleases  OBJECT-TYPE
    SYNTAX     Counter
    ACCESS     read-only
    STATUS     mandatory
    DESCRIPTION
        " This is the number of Release messages received by the VISM
          from the PXM since VISM reset.
        " 
    ::= { vismSvcGrp 11 }
    
vismSvcRxReleaseCompls  OBJECT-TYPE
    SYNTAX     Counter
    ACCESS     read-only
    STATUS     mandatory
    DESCRIPTION
        " This is the number of Release complete messages received by the VISM
          from the PXM since VISM reset.
        " 
    ::= { vismSvcGrp 12 }
    
vismSvcTxRestarts  OBJECT-TYPE
    SYNTAX     Counter
    ACCESS     read-only
    STATUS     mandatory
    DESCRIPTION
        " This is the number of Restart messages sent to the PXM
          from the VISM since VISM reset.
        "
    ::= { vismSvcGrp 13 }
    
vismSvcTxRestartAcks  OBJECT-TYPE
    SYNTAX     Counter
    ACCESS     read-only
    STATUS     mandatory
    DESCRIPTION
        " This is the number of Restart ack messages sent to the PXM
          from the VISM since VISM reset.
        "
    ::= { vismSvcGrp 14 }
    
vismSvcRxRestarts  OBJECT-TYPE
    SYNTAX     Counter
    ACCESS     read-only
    STATUS     mandatory
    DESCRIPTION
        " This is the number of Restart messages received by the VISM
          from the PXM since VISM reset.
        " 
    ::= { vismSvcGrp 15 }
    
vismSvcRxRestartAcks  OBJECT-TYPE
    SYNTAX     Counter
    ACCESS     read-only
    STATUS     mandatory
    DESCRIPTION
        " This is the number of Restart ack messages received by the VISM
          from the PXM since VISM reset.
        "
    ::= { vismSvcGrp 16 }
    
vismSvcTxResyncStrts  OBJECT-TYPE
    SYNTAX     Counter
    ACCESS     read-only
    STATUS     mandatory
    DESCRIPTION
        " This is the number of Resync start messages sent to the PXM
          from the VISM since VISM reset.
        "
    ::= { vismSvcGrp 17 }
    
vismSvcTxResyncStrtAcks  OBJECT-TYPE
    SYNTAX     Counter
    ACCESS     read-only
    STATUS     mandatory
    DESCRIPTION
        " This is the number of Resync start ack messages sent to the PXM
          from the VISM since VISM reset.
        "
    ::= { vismSvcGrp 18 }
    
vismSvcRxResyncStrts  OBJECT-TYPE
    SYNTAX     Counter
    ACCESS     read-only
    STATUS     mandatory
    DESCRIPTION
        " This is the number of Resync start messages received by the VISM
          from the PXM since VISM reset.
        " 
    ::= { vismSvcGrp 19 }
    
vismSvcRxResyncStrtAcks  OBJECT-TYPE
    SYNTAX     Counter
    ACCESS     read-only
    STATUS     mandatory
    DESCRIPTION
        " This is the number of Resync start ack messages received by the VISM
          from the PXM since VISM reset.
        " 
    ::= { vismSvcGrp 20 }
    
vismSvcTxResyncEnds  OBJECT-TYPE
    SYNTAX     Counter
    ACCESS     read-only
    STATUS     mandatory
    DESCRIPTION
        " This is the number of Resync end messages sent to the PXM
          from the VISM since VISM reset.
        "
    ::= { vismSvcGrp 21 }
    
vismSvcTxResyncEndAcks  OBJECT-TYPE
    SYNTAX     Counter
    ACCESS     read-only
    STATUS     mandatory
    DESCRIPTION
        " This is the number of Resync end ack messages sent to the PXM
          from the VISM since VISM reset.
        "
    ::= { vismSvcGrp 22 }
    
vismSvcRxResyncEnds  OBJECT-TYPE
    SYNTAX     Counter
    ACCESS     read-only
    STATUS     mandatory
    DESCRIPTION
        " This is the number of Resync end messages received by the VISM
          from the PXM since VISM reset.
        " 
    ::= { vismSvcGrp 23 }
    
vismSvcRxResyncEndAcks  OBJECT-TYPE
    SYNTAX     Counter
    ACCESS     read-only
    STATUS     mandatory
    DESCRIPTION
        " This is the number of Resync end ack messages received by the VISM
          from the PXM since VISM reset.
        " 
    ::= { vismSvcGrp 24 }
    
vismSvcTxBulkResyncs  OBJECT-TYPE
    SYNTAX     Counter
    ACCESS     read-only
    STATUS     mandatory
    DESCRIPTION
        " This is the number of Bulk resync messages sent to the PXM
          from the VISM since VISM reset.
        "
    ::= { vismSvcGrp 25 }
    
vismSvcRxBulkResyncs  OBJECT-TYPE
    SYNTAX     Counter
    ACCESS     read-only
    STATUS     mandatory
    DESCRIPTION
        " This is the number of Bulk resync messages received by the VISM
          from the PXM since VISM reset.
        " 
    ::= { vismSvcGrp 26 }
    
vismSvcCallProcExpiries  OBJECT-TYPE
    SYNTAX     Counter
    ACCESS     read-only
    STATUS     mandatory
    DESCRIPTION
        " Call proceeding expirations
        "
    ::= { vismSvcGrp 27 }
    
vismSvcReleasExpiries  OBJECT-TYPE
    SYNTAX     Counter
    ACCESS     read-only
    STATUS     mandatory
    DESCRIPTION
        " Release completion expirations
        "
    ::= { vismSvcGrp 28 }
    
vismSvcConnExpiries  OBJECT-TYPE
    SYNTAX     Counter
    ACCESS     read-only
    STATUS     mandatory
    DESCRIPTION
        " Connect expirations
        "
    ::= { vismSvcGrp 29 }
    
vismSvcConnAckExpiries  OBJECT-TYPE
    SYNTAX     Counter
    ACCESS     read-only
    STATUS     mandatory
    DESCRIPTION
        " Connect ack expirations
        "
    ::= { vismSvcGrp 30 }
    
vismSvcRestartExpiries  OBJECT-TYPE
    SYNTAX     Counter
    ACCESS     read-only
    STATUS     mandatory
    DESCRIPTION
        " Restart expirations
        "
    ::= { vismSvcGrp 31 }
    
vismSvcResyncExpiries  OBJECT-TYPE
    SYNTAX     Counter
    ACCESS     read-only
    STATUS     mandatory
    DESCRIPTION
        " Resync expirations
        "
    ::= { vismSvcGrp 32 }
    
--
-- =================================================================
-- VISM2.x
-- 
-- scalar MIB objects defined to configure VISM voice ATM Svc 
-- signalling parameters that are used as defaults:
--  1. vismSvcAtmQosGrp: 
--         voice SVC signalling QoS parameters
--  2. vismSvcTrfScalingGrp: 
--         scaling factor to SVC signalling traffic parameters
--  3. aal2 svc cid number.
--         default AAL2 CID used for single CID AAL2 SVCs
-- =================================================================
--

vismSvcCnfGroups        OBJECT IDENTIFIER ::= { voice 19 }

vismSvcAtmQosGrp        OBJECT IDENTIFIER ::= { vismSvcCnfGroups 1 }

vismSvcAtmQosCdv OBJECT-TYPE
        SYNTAX          INTEGER (500..20000)
        ACCESS          read-write
        STATUS          mandatory
        DESCRIPTION
            "End-to-end cell delay variation used in voice SVC establishment.
             It is used to guarantee the quality of the route selected for 
             a voice SVC. It is applicable to both AAL1 and AAL2 SVC connection 
             establishment. The value specified to this object is in 
             'micro-seconds'. This value is sent in voice SVC setup messages 
             in extended quality of services information element as the 
             objective value.
            "
        REFERENCE
            "The references are from ATM Forum 'Voice & Telephony over ATM' 
             specifications af-vtoa-0089.000, af-vtoa-0113.000.
            "
        DEFVAL     { 20000 }
        ::= { vismSvcAtmQosGrp 1 }

vismSvcAtmQosCtd OBJECT-TYPE
        SYNTAX          INTEGER (20000..150000)
        ACCESS          read-write
        STATUS          mandatory
        DESCRIPTION
            "End-to-end maximum cell transfer delay used in voice SVC 
             establishment. It is used to guarantee the quality of the route 
             selected for a voice SVC. It is applicable to both AAL1 and AAL2 
             SVC connection establishment. The value specified to this object 
             is in 'micro-seconds'. This value is sent in voice SVC setup 
             messages in end-to-end transit delay information element as 
             the objective value.
            "
        REFERENCE
            "The references are from ITU G-Series Recomendations: 
             G.114 - One-way transmission time.
            "
        DEFVAL     { 150000 }
        ::= { vismSvcAtmQosGrp 2 }

vismSvcAtmQosClr OBJECT-TYPE
        SYNTAX          INTEGER (4..8)
        ACCESS          read-write
        STATUS          mandatory
        DESCRIPTION
            "Maximum Cell Loss Ratio used in voice SVC establishment.
             It is used to guarantee the quality of the route selected for 
             a voice SVC. It is applicable to both AAL1 and AAL2 SVC connection 
             establishment. This value is sent in voice SVC setup messages in 
             extended quality of services information element as maximum cell 
             loss ratio value.
            "
        REFERENCE
            " The references are from BellCore specifications - GR.1110
            "
        DEFVAL     { 8 }
        ::= { vismSvcAtmQosGrp 3 }

-- vismSvcTrfScalingGrp
-- ===================================================================
vismSvcTrfScalingGrp       OBJECT IDENTIFIER ::= { vismSvcCnfGroups 2 }

vismSvcTrfScalingFactor  OBJECT-TYPE
        SYNTAX          INTEGER (50..200)
        ACCESS          read-write
        STATUS          mandatory
        DESCRIPTION
            "Traffic scaling Factor used to compute factored bandwidth which is
             used in ATM signaling to establish voice SVC. When this value is 
             less than 100 it can be referred as a `discount factor' and when 
             more than 100 referred as an `excess factor'
             It is applicable only to VBR SVC connection establishment.
             The traffic scaling is not applicable to AAL2 SVC calls that 
             require G.711 and clear channel codecs
            "
        DEFVAL     { 100 }
        ::= { vismSvcTrfScalingGrp 1 }

-- vismSvcAal2CidGrp
-- ====================================================================
vismSvcAal2CidGrp           OBJECT IDENTIFIER ::= { vismSvcCnfGroups 3 }

vismSvcAal2CidNumber    OBJECT-TYPE
        SYNTAX          INTEGER (8..255)
        ACCESS          read-write
        STATUS          mandatory
        DESCRIPTION
            "The default AAL2 Channel IDentification (CID) number 
             used for AAL2 SVC connections.
            "
        REFERENCE
            "The references are from ITU I-Series Recomendations: 
             I.363.2 B-ISDN ATM Adaptation Layer specification: Type 2 AAL.
            "
        DEFVAL     { 100 }
        ::= { vismSvcAal2CidGrp 1 }

-- ----------------------------------------------------------------------
-- BASIS Project MIB
--
-- VISM Signaling group 
-- This file contains the table for configuring 
-- and maintaining the counters for the HDLC channels on VISM. 
-- ------------------------------------------------------------------
--
-- Modification History
-- 07/23 Incorporated the changes suggested in the review meeting. 
-- 11/09 changed HdlcChanNum range to  1-248 
-- 12/28/99 changed vismHdlcLcnNum (32..279) to (131..510)
-- 02/09 To accommodate PRI and GR303 backhaul project the following
--       changes are made:
--       1) Change the description of create and delete an entry in 
--          vismHdlcChanTable.
--       2) Change vismHdlcMaxFrameSize from configrable to not 
--          configrable.
--       3) Change the description of vismHdlcLcnNum. It is not 
--          applicable for PRI and GR-303.
-- 04/06 Deprecate vismHdlcMaxFrameSize.



vismSigGrp          OBJECT IDENTIFIER ::= { voice 6 }


-- ------------------------------------------------------------------
--
-- ------------------------------------------------------------------

vismHdlcChanTable    OBJECT-TYPE
    SYNTAX  SEQUENCE OF VismHdlcChanEntry
    ACCESS  not-accessible
    STATUS  mandatory
    DESCRIPTION
        "This table is used for maintaining the statistics info
		for the HDLC channels on VISM. It also keeps track of some
		configurable parameters required for proper operation of
		HDLC driver in VISM. 
        "
    ::= { vismSigGrp 1 }

vismHdlcChanEntry    OBJECT-TYPE
    SYNTAX  VismHdlcChanEntry
    ACCESS  not-accessible
    STATUS  mandatory
    DESCRIPTION
        "An entry for each HDLC channel."
    INDEX { vismHdlcChanNum }
    ::= { vismHdlcChanTable 1 }

VismHdlcChanEntry ::=
    SEQUENCE {
		vismHdlcChanNum			INTEGER,
		vismHdlcRowStatus		INTEGER,
		vismHdlcMaxFrameSize	INTEGER,
		vismHdlcLcnNum        	INTEGER,
		vismHdlcXmtFrames    	Counter,
		vismHdlcRcvFrames	    Counter,
		vismHdlcRcvCrcErrors	Counter,
		vismHdlcRcvBufOverflows	Counter,
		vismHdlcTxUnderflows	Counter,
		vismHdlcTxAbortFrames   Counter,
		vismHdlcRxAbortFrames   Counter
}

vismHdlcChanNum    OBJECT-TYPE
    SYNTAX  INTEGER(1..248) 
    ACCESS  read-only
    STATUS  mandatory
    DESCRIPTION
        " This object is the index of this table. 
          It refers to the ds0IfIndex in the dsx0VismCnfTable.
        "
    ::= { vismHdlcChanEntry 1 }
 
vismHdlcRowStatus    OBJECT-TYPE
	SYNTAX	INTEGER {
		active(1),
		createAndGo(4),
		destroy(6)
		}
	ACCESS read-write
        STATUS  mandatory
        DESCRIPTION
        "This variable allows to add, delete or modify the entry.
         createAndGo: Use this to add an entry in this table.
         There are two case of creating a entry: 1) a ccs channel
         is explicitly created for Aal2 trunking. In this case, if
         the DS0 already created for PRI or GR-303 the request of
         creation should be rejected.
         2) A Hdlc entry will be implicitly created before creating
         a LAPD entry. In this case if the DS0 is already used for 
         Aal2 trunking the request should be rejected. No entry in 
         Lapd shall be created. 
 
         active: This values is returned, once the row is created
         destroy: Use this to delete an entry from this table. 
         According to the creation, an entry can be explicitly 
         destroyed or implicitly removed.
        "
    ::= { vismHdlcChanEntry 2 }
 
vismHdlcMaxFrameSize    OBJECT-TYPE
    SYNTAX  INTEGER 
    ACCESS  read-only
    STATUS  deprecated
    DESCRIPTION
        "This object describes the maximum frame size that is 
         allowed on this HDLC channel. This value is not configurable.
         The value for this object is 264.
        "
    ::= { vismHdlcChanEntry 3 }

vismHdlcLcnNum    OBJECT-TYPE
    SYNTAX  INTEGER(131..510) 
    ACCESS  read-write
    STATUS  mandatory
    DESCRIPTION
        "This object describes LCN or the PVC channel number with
		 which the HDLC channel is associated with. It is applicable
		 only for trunking applications where the CCS frames are 
		 transmitted to the other end point over an AAL5 PVC. For
		 PRI or GR-303 applications, this is not applicable since the
		 CCS frames in that case are backhauled to the call agent.
        "
    ::= { vismHdlcChanEntry 4 }

vismHdlcXmtFrames    OBJECT-TYPE
    SYNTAX  Counter 
    ACCESS  read-only
    STATUS  mandatory
    DESCRIPTION
        "This object maintains the count of HDLC frames transmitted 
		to the HDLC channel on VISM.
        "
    ::= { vismHdlcChanEntry 5 }

vismHdlcRcvFrames    OBJECT-TYPE
    SYNTAX  Counter 
    ACCESS  read-only
    STATUS  mandatory
    DESCRIPTION
        "This object maintains the count of HDLC frames received 
		from the HDLC channel on VISM.
        "
    ::= { vismHdlcChanEntry 6 }

vismHdlcRcvCrcErrors    OBJECT-TYPE
    SYNTAX  Counter 
    ACCESS  read-only
    STATUS  mandatory
    DESCRIPTION
        "This object describes the count of HDLC frames dropped
		due to CRC errors in the frames received from the HDLC
		Channel. 
        "
    ::= { vismHdlcChanEntry 7 }

vismHdlcRcvBufOverflows    OBJECT-TYPE
    SYNTAX  Counter 
    ACCESS  read-only
    STATUS  mandatory
    DESCRIPTION
        "This object describes the count of HDLC receiver 
		 buffer overflow condition. This can occur if the rate
		 of arrival of HDLC frames from the line is more than
		 the processing rate by the CPU.
        "
    ::= { vismHdlcChanEntry 8 }

vismHdlcTxUnderflows    OBJECT-TYPE
    SYNTAX  Counter 
    ACCESS  read-only
    STATUS  mandatory
    DESCRIPTION
        "This object describes the count of HDLC Tx underflow
		 condition. 
        "
    ::= { vismHdlcChanEntry 9 }

vismHdlcTxAbortFrames	OBJECT-TYPE
    SYNTAX  Counter 
    ACCESS  read-only
    STATUS  mandatory
    DESCRIPTION
        "This object describes the count of HDLC Abort frames
		transmitted.
        "
    ::= { vismHdlcChanEntry 10 }

vismHdlcRxAbortFrames	OBJECT-TYPE
    SYNTAX  Counter 
    ACCESS  read-only
    STATUS  mandatory
    DESCRIPTION
        "This object describes the count of HDLC Abort frames
		received.
        "
    ::= { vismHdlcChanEntry 11 }


--
-- ----------------------------------------------------------------------
-- VISM1.5 Alabama Project MIB
--
--
-- VISM Bearer Connection Table group
--
-- ------------------------------------------------------------------
--
-- Modification History
-- 07/23 Incorporated the changes suggested in the review meeting.
-- 12/28/99 Changed bearerLcn range from (32..279) to (131..510)
-- 03/10/2000 added 4 aal2 counters
-- 05/24/2000 changed the range of bearerEndptNum to 65535 but
--                          we only support 248 endpoints
-- 01/12/2001 Added counterClearButton
-- ------------------------------------------------------------------



bearerConnGrp       OBJECT IDENTIFIER ::= {voice 9}
 
-- ------------------------------------------------------------------
bearerConnTable OBJECT-TYPE
    SYNTAX  SEQUENCE OF BearerConnEntry
    ACCESS  not-accessible
    STATUS  mandatory
    DESCRIPTION
        " This table describes the statistical information available 
		on a per-bearer connection basis. These values are applicable
		equally to an endpoint. However, a separate table has been 
		maintained instead of extending the endpoint table because 
		the endpoint table is the standards-based MgMib."
    ::= { bearerConnGrp 1 }
 
bearerConnEntry    OBJECT-TYPE
    SYNTAX  BearerConnEntry
    ACCESS  not-accessible
    STATUS  mandatory
    DESCRIPTION
        "
	Each entry in this table corresponds to a bearer connection,
	that was setup by binding an endpoint with VC/CID pair, either
	through CLI or SNMP. The statistical counters in this table 
	are generic voice quality parameters that are equally applicable
	in all types of Voice Over Packet adapations (VoIP, VoAAL1 and 
	VoAAL2). However, they are maintained only in the PVC (trunking)
	model because, these counters get reset in the switching model
	on a per call basis.
	The entries in this table are implicitly created/deleted at the 
        time of creation/deletion of entries in the Aal2Cid table. 
	"
    INDEX { bearerEndptNum }
    ::= { bearerConnTable 1 }
 

BearerConnEntry ::=
    SEQUENCE {
		bearerEndptNum		INTEGER,
                bearerCid               INTEGER,
                bearerLcn               INTEGER,
                bearerSentPkts          Counter,
                bearerRcvdPkts          Counter,
                bearerSentOctets        Counter,
                bearerRcvdOctets        Counter,
                bearerLostPkts          Counter,
                bearerJitter            INTEGER,
                bearerLatency           INTEGER,
-- VISM1.53
                bearerAal2ExtAISCnts    Counter,
                bearerAal2ExtRAICnts    Counter,
                bearerAal2ConnAISCnts   Counter,
                bearerAal2ConnRDICnts   Counter,
-- VISM1.53
                bearerCntClrButton      INTEGER
}

bearerEndptNum 	OBJECT-TYPE
	SYNTAX    INTEGER(1..65535)
    ACCESS    read-only
    STATUS    mandatory
    DESCRIPTION
        "This attribute defines the index for the bearer connection Table. 
		This refers to the same value as the index to the mgEndpoint Table 
		ie. mgEndpointNumber
        "
    ::= {bearerConnEntry  1}

bearerCid     OBJECT-TYPE
	SYNTAX    INTEGER
    ACCESS    read-only
    STATUS    mandatory
    DESCRIPTION
        "This attribute defines the CID (Channel ID associated with this 
	 bearer connection.This refers to the same value as 
         vismAal2CidNum in the vismAal2CidCnfTable.
        "
    ::= {bearerConnEntry  2}

bearerLcn     OBJECT-TYPE
	SYNTAX    INTEGER(131..510)
    ACCESS    read-only
    STATUS    mandatory
    DESCRIPTION
        "This attribute defines the PVC or LCN number to which this bearer
		 connection is associated with.
		 This refers to the same value as in vismChanNum in vismChanCnfGrp
		 table.
        "
    ::= {bearerConnEntry  3}

bearerSentPkts   OBJECT-TYPE
        SYNTAX    Counter
    ACCESS    read-only
    STATUS    mandatory
    DESCRIPTION
        "This attribute defines the count of packets sent towards the network
		since setup. 
        "
    ::= {bearerConnEntry  4}

bearerRcvdPkts   OBJECT-TYPE
        SYNTAX    Counter
    ACCESS    read-only
    STATUS    mandatory
    DESCRIPTION
        "This attribute defines the count of packets received from the
		network since setup.
        "
    ::= {bearerConnEntry  5}

bearerSentOctets    OBJECT-TYPE
        SYNTAX    Counter
    ACCESS    read-only
    STATUS    mandatory
    DESCRIPTION
        "This attribute defines the count of bytes sent towards the network
		since this connection setup.
        "
    ::= {bearerConnEntry  6}

bearerRcvdOctets    OBJECT-TYPE
        SYNTAX    Counter
    ACCESS    read-only
    STATUS    mandatory
    DESCRIPTION
        "This attribute defines the count of bytes received from the network
		since this connection setup.
        "
    ::= {bearerConnEntry  7}

bearerLostPkts   OBJECT-TYPE
        SYNTAX    Counter
    ACCESS    read-only
    STATUS    mandatory
    DESCRIPTION
        "This attribute defines the count of packets lost in the egress 
         direction (from the network). This is a computed number based on the
   	 expected number of packets and the actual number of packets arrived 
         from the network.
         Currently this object is not used.
        "
    ::= {bearerConnEntry  8}

bearerJitter    OBJECT-TYPE
	SYNTAX    INTEGER
    ACCESS    read-only
    STATUS    mandatory
    DESCRIPTION
        "This attribute defines the jitter (a.k.a interarrival jitter) 
		This value is determined by the DSP and obtained by the HOST processor
		upon querying the DSP on a periodic basis. This value is expressed
		in units of milliseconds.
           Currently this object is not used.
        "
    ::= {bearerConnEntry  9}

bearerLatency   OBJECT-TYPE
	SYNTAX    INTEGER
    ACCESS    read-only
    STATUS    mandatory
    DESCRIPTION
        "This attribute defines the latency (a.k.a end-to-end average
		transmission delay for a voice packet. This value is expressed
		in units of milliseconds.
         Currently this object is not used.    
    "
    ::= {bearerConnEntry  10}

-- VISM1.53

bearerAal2ExtAISCnts    OBJECT-TYPE
        SYNTAX       Counter
        ACCESS       read-only
        STATUS       mandatory
        DESCRIPTION
           "
              This object contains the number of external AIS aal2 Type3 packets
              received. 

              External AIS - is a Alarm Indication Signal associated with a maintenance
              alarm detected on a defective maintenance span, that is transmitted in 
              the direction of the defect as a substitute for normal signal. The purpose
              is to show the downstream  entities that a defect has been identified
              and to prevent other maintenance alrams consequent to this first defect.

              External AIS bit stream is represented by an all 1's signal.
              Ref - ITU-T Rec. M.20 sec. 5.4.2 a
           "  
        ::= {bearerConnEntry 11}


bearerAal2ExtRAICnts    OBJECT-TYPE
        SYNTAX       Counter
        ACCESS       read-only
        STATUS       mandatory
        DESCRIPTION
           "
              This object contains the number of external RAI aal2 Type3 packets
              received. 

              External RAI - is a Remote Alarm Indication signal that is transmitted
              upstream from an entity that has detected defects persisting long enough
              to constitute a received signal failure. Its purpose is to report in
              the backward direction that there is an interruption of service in the
              forward direction.
              Ref - ITU-T Rec. G.704 section 2.1.3.1.3 
           "
        ::= {bearerConnEntry 12}

bearerAal2ConnAISCnts   OBJECT-TYPE
        SYNTAX       Counter
        ACCESS       read-only
        STATUS       mandatory
        DESCRIPTION
           "
              This object contains the number of external Conn AIS aal2 Type2 packets
              received. 

              External Conn AIS - is a Alarm Indicating Signal transmitted in the 
              downstream direction from the AAL type 2 connecting point that first 
              detects a defect affecting the AAL type 2 connection; this includes
              defects indicated by lower layers.
              Ref - ITU-T Rec. I.610 sec 6.2.2.1.1.1
           "
        ::= {bearerConnEntry 13}

bearerAal2ConnRDICnts   OBJECT-TYPE
        SYNTAX       Counter 
        ACCESS       read-only
        STATUS       mandatory
        DESCRIPTION
           "
              This object contains the number of external Conn RDI (Remote Defect Ind.)
              aal2 Type2 packets received. 

              External Conn RDI -  is a signal transmitted upstream by an AAl type 2 
              endpoint that is in an alarm state as the result of having received
              an AAL type2 connection AIS or having detected a defect that affects
              the AAL type2 connection.
           "
        ::= {bearerConnEntry 14}

-- VISM1.53


bearerCntClrButton   OBJECT-TYPE
        SYNTAX       INTEGER {
                        noaction(1),
                        clear (2)
                        }
        ACCESS       read-write
        STATUS       mandatory
        DESCRIPTION
        " This object is used to clear bearerSentPkts, bearerRcvdPkts,
          bearerSentOctets, and bearerRcvdOctets.
        "
        ::= {bearerConnEntry 15}
 

--
-- ----------------------------------------------------------------------
-- BASIS Project MIB
--
--
-- VISM specific dsx0 configuration group 
--
-- ------------------------------------------------------------------
--
-- Modification History
-- 07/23 Incorporated the changes suggested in the review meeting. 
--
-- 11/23 Added DEFVAL clause for ds0IdleCode,  ds0SeizedCode 
-- VISM1.53
-- 03/10/00 Added ds0CadenceTimeOn and ds0CadenceTimeOff for vism1.53 release
--        modified ds0CasVariantName object's description.
--        ds0TransmitcodesEnable is deprecate
--        added three objects  ds0InsertLocalCas AND ds0LocalCasPattern
--          ds0LoopbackCommand 
-- VISM1.53
-- July 10th 2000 INDIANA - added cas knobs for INDIANA release

-- VISMRI release
-- 03/14/2001 Added two new objects ds0CasMinDelayDialTime and ds0CasMinStartDialTime
-- 05/24/2001 Added two new objects ds0InputGain and ds0OutputAttenuation
-- 06/11/2001 Added new object ds0MusicThreshold

-- VISM2.2
-- 06/09/2001 Rhode Island - added objects for glare handling, flash definition and 
--            per-endpoint package
--
-- 08/24/2001 Rhode Island - added new object for SID packet enable/disable handling
--




 

 

-- ------------------------------------------------------------------
--
-- dsx0Vism
-- This group is a replica of the standard DS0 MIB (RFC 2494), with slight
-- modifications. Since ifTable is not supported in AXIPOPMIBS, and since
-- DS0 MIB (RFC 2494) rquires the support of ifTable mib, rather than using
-- the standard mib as is, the objects have been copied to the AXIPOP branch.
-- The objects ds0IfType and ds0CasVariantName are extensions to the 
-- standard DS0 MIB.
--
--
-- This group contains the objects necessary to configure the DS0s on
-- T1/E1 lines of VISM.
-- -----------------------------------------------------------------

dsx0VismCnfTable        OBJECT-TYPE
    SYNTAX  SEQUENCE OF Dsx0VismCnfEntry
    ACCESS  not-accessible
    STATUS  mandatory
    DESCRIPTION
        "The entries in this table are created and deleted implicitly at the 
         time of adding and deleting the line. For every DS0 on a line, one 
		row will be created.
        "
    ::= { dsx0Vism 1 }
 
dsx0VismCnfEntry	OBJECT-TYPE
    SYNTAX  Dsx0VismCnfEntry	
    ACCESS  not-accessible
    STATUS  mandatory
    DESCRIPTION
        "
      This ds0 table contains both cas related
      and non cas related parameters.
   
      The non cas related parameters are applicable
      accross all line signaling types, while the
      following cas related parameters
      are applicable only if the signaling type
      of the line to which this ds0 belongs
      is cas.

                ds0IdleCode
                ds0SeizedCode
                ds0ReceivedCode
                ds0CasVariantName
                ds0CasCadenceOnTime
                ds0CasCadenceOffTime
                ds0InsertLocalCas
                ds0LocalCasPattern
                ds0CasParameterSource
                ds0CasOnHookMinMakeTime
                ds0CasOffHookMinMakeTime
                ds0CasWinkMinMakeTime
                ds0CasWinkMaxMakeTime
                ds0CasWinkBreakTime
                ds0CasGlareTime
                ds0CasGaurdTime
                ds0CasDelayImmedStart
                ds0CasMinDelayDialTime
                ds0CasMinStartDialTime
                ds0CasFlashMinMakeTime
                ds0CasFlashMaxMakeTime
                ds0CasDirectionality
                ds0CasGlarePolicy
                ds0CasIncomingMgcpPackage
                ds0CasOutgoingMgcpPackage
           

        When the line signaling type changes from cas to non-cas and
        vice versa, then the user will be forced to delete
        endpoint/ccs channels  associated with any ds0 on that line
        When an endpoint is deleted the ds0CasVariantName associated
        with that endpoint will also be implicitly deleted.
        Other than that none of the above cas related parameters are 
        modified across line signaling type changes.
		"
    INDEX { ds0IfIndex }
    ::= { dsx0VismCnfTable 1 }
 


Dsx0VismCnfEntry ::=
    SEQUENCE {
		ds0IfIndex 			INTEGER,
		ds0RobbedBitSignalling 		TruthValue,
		ds0IdleCode			INTEGER,
		ds0SeizedCode		        INTEGER,
		ds0ReceivedCode		        INTEGER,
		ds0TransmitCodesEnable		TruthValue,
		ds0BundleMapped		        INTEGER,
		ds0IfType			INTEGER,
		ds0CasVariantName	        DisplayString,
-- VISM1.53
                ds0CasCadenceOnTime             INTEGER,
                ds0CasCadenceOffTime            INTEGER,
                ds0InsertLocalCas               TruthValue,
                ds0LocalCasPattern              INTEGER,
                ds0LoopbackCommand              INTEGER,
-- VISM1.53
                ds0CasParameterSource           INTEGER,
                ds0CasOnHookMinMakeTime         INTEGER,
                ds0CasOffHookMinMakeTime        INTEGER,
                ds0CasWinkMinMakeTime           INTEGER,
                ds0CasWinkMaxMakeTime           INTEGER,
                ds0CasWinkBreakTime             INTEGER,
                ds0CasGlareTime                 INTEGER,
                ds0CasGaurdTime                 INTEGER,
                ds0CasDelayImmedStart           INTEGER,
                ds0SignalingType                INTEGER,
                ds0CasMinDelayDialTime          INTEGER,
                ds0CasMinStartDialTime          INTEGER, 
-- VISMRI release
                ds0CasFlashMinMakeTime          INTEGER,
                ds0CasFlashMaxMakeTime          INTEGER,
                ds0CasDirectionality            INTEGER,
                ds0CasGlarePolicy               INTEGER,
                ds0CasIncomingMgcpPackage       DisplayString,
                ds0CasOutgoingMgcpPackage       DisplayString,
                ds0InputGain                    INTEGER,
                ds0OutputAttenuation            INTEGER,
                ds0MusicThreshold               INTEGER,
		ds0SidPacket                    TruthValue

}



ds0IfIndex 	OBJECT-TYPE
	SYNTAX    INTEGER (1..248)
    ACCESS    read-only
    STATUS    mandatory
    DESCRIPTION
        "This attribute defines the index for this table.
		This is derived from the following formula:
		index = 31 * (Ds1# - 1) + ds0#
           
            where : Ds1# - The T1/E1 line number in the range 1 - 8.
                    ds0# - The ds0 channel number ranging from
                            1 to 24 for T1
                        and 1 to 31 for E1.
 

        "
    ::= {dsx0VismCnfEntry  1}


ds0RobbedBitSignalling OBJECT-TYPE
       SYNTAX  TruthValue
       ACCESS  read-write
       STATUS  mandatory
       DESCRIPTION
               "This object indicates if Robbed Bit Signalling is
               turned on or off for a given ds0.  This only
               applies to DS0s on a DS1 link.  For E1 links the
               value is always off (false). For T1 links, the default 
               value is true if the line is configured for CAS signaling,
               the default value is false if the line is configured for
               CCS signaling or no signaling.
               "
       ::= { dsx0VismCnfEntry 2 }


ds0IdleCode OBJECT-TYPE
        SYNTAX  INTEGER(0..15)
        ACCESS  read-write
        STATUS  mandatory
        DESCRIPTION
               "This object contains the code transmitted in the
               ABCD bits when the ds0 is not connected and
               ds0TransmitCodesEnable is enabled.  The object is
               a bitmap and the various bit positions are:
                     Bit 0 (value 1)     D bit
                     Bit 1 (value 2)     C bit
                     Bit 2 (value 4)     B bit
                     Bit 3 (value 8)     A bit
				This object is useful for ds0 conditioning to be
				done if an alarm condition is detected from the
				network side. DS0 conditioning is implemented in
				the trunking application only.
				This object is not applicable in the CAS backhaul
				application.

                                From vism 2.0.3 release onwards this object can
                                be configured in any mode, but will be applicable
                                only in trunking application and will be ignored
                                in other applications.
                  "
       DEFVAL { 0 }
       ::= { dsx0VismCnfEntry 3 }

ds0SeizedCode OBJECT-TYPE
        SYNTAX  INTEGER(0..15)
        ACCESS  read-write
        STATUS  mandatory
        DESCRIPTION
               "This object contains the code transmitted in the
               ABCD bits when the ds0 is connected and
               ds0TransmitCodesEnable is enabled.  The object is
               a bitmap and the various bit positions are:
                     Bit 0 (value 1)     D bit
                     Bit 1 (value 2)     C bit
                     Bit 2 (value 4)     B bit
                     Bit 3 (value 8)     A bit
				This object is useful for ds0 conditioning to be
				done if an alarm condition is detected from the
				network side. DS0 conditioning is implemented in
				the trunking application only.
				This object is not applicable in the CAS backhaul
				application.
                                From vism 2.0.3 release onwards this object can
                                be configured in any mode, but will be applicable
                                only in trunking application and will be ignored
                                in other applications.

                 "
       DEFVAL { 15 }
       ::= { dsx0VismCnfEntry 4 }

ds0ReceivedCode OBJECT-TYPE
        SYNTAX  INTEGER(0..15)
        ACCESS  read-only
        STATUS  mandatory
        DESCRIPTION
               "This object contains the code being received in
               the ABCD bits.  The object is a bitmap and the
               various bit positions are:
                     Bit 0 (value 1)    D bit
                     Bit 1 (value 2)    C bit
                     Bit 2 (value 4)    B bit
                     Bit 3 (value 8)    A bit"
       ::= { dsx0VismCnfEntry 5 }

-- VISM1.53
-- This object is deprecated and moved to Dsx1VismCnfGrp table
ds0TransmitCodesEnable OBJECT-TYPE
        SYNTAX TruthValue
        ACCESS  read-only
        STATUS  deprecated
        DESCRIPTION
               "This object determines if the idle and seized
               codes are transmitted. If the value of this object
               is true then the codes are transmitted.
               This object is not applicable in the CAS backhaul
               application."
       DEFVAL { true }
       ::= { dsx0VismCnfEntry 6 }
-- VISM1.53
ds0BundleMapped OBJECT-TYPE
        SYNTAX INTEGER
        ACCESS  read-only
        STATUS  mandatory
        DESCRIPTION
               "This object indicates endpoint number as specified
				by mgEndpointNumber of endpoint table.
				If it is not associated with any endpoint, then it 
				is set to -1.
				It should be noted that the endpoint is associated
				with bearer DS0s only. For signaling channel or DS0
				as in the case of CCS channel, there is no endpoint
				number associated with it and the value is set to -1.
			   "
       ::= { dsx0VismCnfEntry 7 }


ds0IfType OBJECT-TYPE
        SYNTAX INTEGER {
		bearer (81),
		ccs-signaling (63),
		unknown (1)
		}
        ACCESS  read-only
        STATUS  mandatory
        DESCRIPTION
               "This object indicates the interface type associated
				with the ds0. 
				ds0 ifType is considered as bearer if it the DS0 is
				used for carrying voice traffic.
				ds0 ifType is considered as ccs-signaling, if the DS0
				is configured as the D-channel  
			   "
       ::= { dsx0VismCnfEntry 8 }


ds0CasVariantName     OBJECT-TYPE
        SYNTAX DisplayString (SIZE(0..255))
        ACCESS  read-write
        STATUS  mandatory
        DESCRIPTION
               "This object indicates the index to the CAS variant 
		table. This parameter can be configured after configuring
                this ds0 as an endpoint. This object cannot be modified
                while connections exist on this endpoint. The CAS variant 
                table is used for configuring the system parameters associated
                with various types of CAS signaling methods supported
                on VISM.
               "
       ::= { dsx0VismCnfEntry 9 }

-- VISM1.53
 
ds0CasCadenceOnTime     OBJECT-TYPE
     SYNTAX    INTEGER(2..9999)
     ACCESS    read-write
     STATUS    mandatory
     DESCRIPTION
              " This attribute describes the duration during which the digit 
                tone is generated.
                This object is applicable only for CAS backhaul applications.
                For trunking application it is not applicable.
                The value is expresssed in units of milliseconds.
                From vism2.0.3 release onwards this object can
                configured in any application, but will be applicable
                only in non-trunking applications and will be ignored
                in other applications.

              "
     DEFVAL {75}
    ::= {dsx0VismCnfEntry 10 }

ds0CasCadenceOffTime  OBJECT-TYPE
     SYNTAX    INTEGER(0..9999)
     ACCESS    read-write
     STATUS    mandatory
     DESCRIPTION
              " This attribute corresponds to the silence between the
                digit tones. 
                This object is applicable only for CAS backhaul applications.
                For trunking application it is not applicable.
                The value is expresssed in units of milliseconds.

                From vism2.0.3 release onwards this object can
                configured in any application, but will be applicable
                only in non-trunking applications and will be ignored
                in other applications.


              "
     DEFVAL {75}
    ::= {dsx0VismCnfEntry 11}

ds0InsertLocalCas    OBJECT-TYPE
    SYNTAX       TruthValue
    ACCESS       read-write
    STATUS       mandatory
    DESCRIPTION
            "
                This object tells the framer whether to force the cas bits
                to a value defined by ds0LocalCasPattern or not.
            
                If this is enabled the framer will force the cas (ABCD) bits
                to a value defined in ds0LocalCasPattern by ignorning the
                cas bits sent by DSP. Else the framer will transmit the cas 
                bits sent by DSP. 

                Setting of this object is not allowed when the signaling type
                of this line is cas.

                Also setting of this object is not allowed when the 
                ds0LoopbackCommand is set to RemoteLoop, because in this 
                situation we are suppose to loopback whatever comes from
                the TDM side and not force the cas bits to something else.

                This object can be set only if the line type is T1.
            "
      DEFVAL {false} 
       ::= {dsx0VismCnfEntry 12}

ds0LocalCasPattern    OBJECT-TYPE
   SYNTAX       INTEGER(0..15)
   ACCESS       read-write
   STATUS       mandatory
   DESCRIPTION
        "
           This object contains the pattern that the cas (ABCD) bits will have
           when ds0InsertLocalCas is enabled.
        "
        DEFVAL{0}
        ::={dsx0VismCnfEntry 13}


ds0LoopbackCommand    OBJECT-TYPE
    SYNTAX       INTEGER {
                          noLoop (1),
                          remoteLoop (2),
                          localLoop (3)
                        }
    ACCESS       read-write
    STATUS       mandatory
    DESCRIPTION 
        "
          This object represents the loopback type at the ds0 level.The
          ds0 configuration overrides the line level configuration.
          
	  NoLoop
                     There is no loopback on this ds0.

          LocalLoop
                     The data received from the ATM side is loopedback
                     to the ATM side.

          RemoteLoop 
                     The data from the TDM side is looped back to the
                     TDM side.                       
          
          Setting of this object to RemoteLoop will not be allowed when
          insert local cas for this ds0 (ds0InsertLocalCas object) is 
          enabled as we are suppose to force the cas bits to the pattern
          configured in ds0LocalCasPattern, and not do loopback on the TDM side.
          	
        "
        DEFVAL{noLoop}
        ::= {dsx0VismCnfEntry 14}

-- VISM1.53

ds0CasParameterSource  OBJECT-TYPE
       SYNTAX  INTEGER
                 {
                   casAppl (1),
                   mibValue (2)
                 } 
       ACCESS  read-write
       STATUS  mandatory
       DESCRIPTION
        "
         This object indicates VISM whether to read the cas related 
         timer parameters from the casAppl file downloaded for that 
         endpoint or to read from this mib. 

         This gives the flexibility of configuring
         different cas related timer values for different 
         endpoints associated with the same cas variant.

         This object cannot be configured if the signaling
         type for the line to which this ds0 belongs is non cas.
         For a cas line this object CAN only be configured
         only after associating this ds0 with an endpoint.
        "
        DEFVAL{casAppl}
       ::= { dsx0VismCnfEntry 15 }

ds0CasOnHookMinMakeTime   OBJECT-TYPE
       SYNTAX  INTEGER (0..65535)
       ACCESS  read-write
       STATUS  mandatory
       DESCRIPTION
        "
         This indicates the the minimum time in msecs 
         for which the on hook pattern should be present in order for it 
         to be recognised else the signal will be considered to be a 
         spurious signal and will be ignored.

         This object cannot be configured if the signaling
         type for the line to which this ds0 belongs is non cas.
         For a cas line this object CAN only be configured
         only after associating this ds0 with an endpoint.

         This object will be applicable if ds0CasParameterSource
         has a value of mibValue (2).
         The allowed range for this object is 10..1000
        "
       DEFVAL {300}
       ::= { dsx0VismCnfEntry 16 }

ds0CasOffHookMinMakeTime   OBJECT-TYPE
       SYNTAX  INTEGER (0..65535)
       ACCESS  read-write
       STATUS  mandatory
       DESCRIPTION
        "
          This indicates the minimum time in msecs for 
          which the off hook pattern should be present in order for it to be 
          recognised else the signal will be considered to be a spurious signal
          and will be ignored.
    
          This object cannot be configured if the signaling
          type for the line to which this ds0 belongs is non cas.

          For a cas line this object CAN only be configured
          only after associating this ds0 with an endpoint
          This object will be applicable if ds0CasParameterSource
          has a value of mibValue (2).
          The allowed range for this object is 10..1000

         "
       DEFVAL {20}
       ::= { dsx0VismCnfEntry 17 }

ds0CasWinkMinMakeTime  OBJECT-TYPE
       SYNTAX  INTEGER (0..65535)
       ACCESS  read-write
       STATUS  mandatory
       DESCRIPTION
        "
        The wink consists of off-hook A-B bit pattern, followed
        by on-hook A-B bit pattern in timed sequence.
        This object indicates the minimum duration for which
        the off-hook part of wink signal should persist.

        This object cannot be configured if the signaling
        type for the line to which this ds0 belongs is non cas. 
        For a cas line this object CAN only be configured
        only after associating this ds0 with an endpoint
        
        This object will be applicable if ds0CasParameterSource         
        has a value of mibValue (2).
        The allowed range for this object is 10..1000 and the
        range is in msecs.

       "
       DEFVAL {100}
       ::= { dsx0VismCnfEntry 18 }

ds0CasWinkMaxMakeTime  OBJECT-TYPE
       SYNTAX  INTEGER (0..65535)
       ACCESS  read-write
       STATUS  mandatory
       DESCRIPTION
       "
        The wink consists of off-hook A-B bit pattern, followed
        by on-hook A-B bit pattern in timed sequence.
        This object indicates the maximum duration for which the 
        off-hook part of the wink signal should persist, if it 
        exceeds this time limit the signal will be considered to 
        be spurious and will be ignored. 
       
        This object cannot be configured if the signaling
        type for the line to which this ds0 belongs is non cas.
        For a cas line this object CAN only be configured
        only after associating this ds0 with an endpoint
        
        This object will be applicable if ds0CasParameterSource         
        has a value of mibValue (2).

        The allowed range for this object is 10..3000 and the units
        is in msecs.

        This object should be greater than or equal to ds0CasWinkMinMakeTime
       "
       DEFVAL {350}
       ::= { dsx0VismCnfEntry 19 }

ds0CasWinkBreakTime    OBJECT-TYPE 
       SYNTAX  INTEGER (0..65535)
       ACCESS  read-write
       STATUS  mandatory
       DESCRIPTION
       "
       The wink consists of off-hook A-B bit pattern, followed
       by on-hook A-B bit pattern in timed sequence.
       This object indicates the minimum
       duration for which the on-hook part of wink signal should persist.

       This object cannot be configured if the signaling
       type for the line to which this ds0 belongs is non cas.
       For a cas line this object CAN only be configured
       only after associating this ds0 with an endpoint
       
       This object will be applicable if ds0CasParameterSource         
       has a value of mibValue (2).
       The allowed range for this object is 10..1000 and the units.
       is in msecs.

       "
       DEFVAL {70}
       ::= { dsx0VismCnfEntry 20 }

ds0CasGlareTime        OBJECT-TYPE         
       SYNTAX  INTEGER (0..65535)
       ACCESS  read-write
       STATUS  mandatory
       DESCRIPTION
       "
        When the terminating gateway receives off Hook event
        from the Call Agent it starts the timer specified in
        this object to see if the terminating side is also 
        trying to originate a call. If this is true, we have
        a 'glare' condition. The way glare is resolved is 
        thru this user programmable timer, we will not honor
        any off hook events from the originating PBX during 
        this time.
 
        This object cannot be configured if the signaling
        type for the line to which this ds0 belongs is non CAS.
        For a CAS line this object can only be configured
        only after associating this ds0 with an endpoint
        
        This object will be applicable if ds0CasParameterSource         
        has a value of mibValue (2).

        The allowed range for this object is 10..10000 and the units
        is in msecs.

       "
       DEFVAL {100}
       ::= { dsx0VismCnfEntry 21 }

ds0CasGaurdTime        OBJECT-TYPE        
       SYNTAX  INTEGER (0..65535)
       ACCESS  read-write
       STATUS  mandatory
       DESCRIPTION
       "
        The gaurd time is the duration between the end of one call
        and the start of next call. This object specifies what should
        be such a duration. All state changes from the PBX are ignored 
        for this duration. After receiving DLCX, this timer will be
        started for a period as configured in this object, and will
        not honor any off-hook events before the expiration of this timer.
          
        This object cannot be configured if the signaling
        type for the line to which this ds0 belongs is non cas.

        For a cas line this object CAN only be configured
        only after associating this ds0 with an endpoint
        This object will be applicable if ds0CasParameterSource         
        has a value of mibValue (2).

        The allowed range for this object is 10..1000 and the units
        is in msecs.

       "
       DEFVAL {800}
       ::= { dsx0VismCnfEntry 22 }

ds0CasDelayImmedStart  OBJECT-TYPE       
       SYNTAX  INTEGER (0..65535)
       ACCESS  read-write
       STATUS  mandatory
       DESCRIPTION
       "
        This timer indicates the time that VISM should wait before 
        outpulsing digits to the PBX after sending an off hook event. 
        This applies only to immediate start protocol.

        This object cannot be configured if the signaling
        type for the line to which this ds0 belongs is non cas.
        For a cas line this object CAN only be configured
        only after associating this ds0 with an endpoint.
        
        This object will be applicable if ds0CasParameterSource         
        has a value of mibValue (2).

        The allowed range for this object is 10..1000 and the units
        is in msecs.

        "
       DEFVAL {500}
       ::= { dsx0VismCnfEntry 23 }


ds0SignalingType     OBJECT-TYPE
    SYNTAX  INTEGER {
            cas (1),
            ccs  (2),
            none (3)
            }
    ACCESS  read-only
    STATUS  mandatory
    DESCRIPTION
        " This attribute indicates the type of signaling on the line
          to which this ds0 belongs.

          CAS - Channel Associated Signaling
          CCS - Common Channel Signaling
          none - no signaling used.

          This object will be implicitly set to line signaling
          type every time it changes.
        "
    DEFVAL { none }
      ::= {dsx0VismCnfEntry 24}




ds0CasMinDelayDialTime     OBJECT-TYPE
    SYNTAX  INTEGER
    ACCESS  read-write
    STATUS  mandatory
    DESCRIPTION
        " This is an object for an E & M signaling protocol like wink-start for
          this ds0.  The difference is that the address-control signal is different
          from wink. The originating VISM, on receiving a seize (AB=11) from the PBX,
          responds by sending the delay-dial (AB=11) signal back to the PBX.  When
          the originating VISM is ready to collect the digits, it sends a start-dial
          (AB=00) signal.  This operation is symmetric.  So the terminating VISM, on
          seizing a trunk, should receive AB=11 (as an ack that the trunk is 
          operational).  Subsequently, when it receives the start signal (AB=00) from
          the connected PBX, it should outpulse the digits.  The rest of the operation
          is similiar to wink-start.


          The allowed range for this object is 100..1000 with units in milliseconds.


          In delay-dial operation, the outgoing interface (this interface), after
          sending a seize signal (AB = 11), waits for the delay-dial signal (AB = 11).
          The delay-dial signal, apart from acknowledging the seize signal, tells this
          interface that the connected equipment is not ready for the digits yet.
          This object specifies the time in milliseconds, after which incoming
          AB=11 will be interpreted by this interface as the delay-dial signal.

          References:  Generic Requirements, GR-506-CORE, Issue 1, June 1996,  
                       Revision 1, November 1996,
                       LSSGR: Signaling for Analog Interfaces
                       Section 11.2.3 is about 'Delay-Dial Operation' (in general) 
                       In particular, section 11.2.3.1 ([R11-21] is about these
                       timing requirements. 

        "
    DEFVAL {100}
      ::= {dsx0VismCnfEntry 25}




ds0CasMinStartDialTime     OBJECT-TYPE
    SYNTAX  INTEGER
    ACCESS  read-write
    STATUS  mandatory
    DESCRIPTION
        " This is an object for an E & M signaling protocol like wink-start for
          this ds0.  The difference is that the address-control signal is different
          from wink. The originating VISM, on receiving a seize (AB=11) from the PBX,
          responds by sending the delay-dial (AB=11) signal back to the PBX.  When
          the originating VISM is ready to collect the digits, it sends a start-dial
          (AB=00) signal.  This operation is symmetric.  So the terminating VISM, on
          seizing a trunk, should receive AB=11 (as an ack that the trunk is 
          operational).  Subsequently, when it receives the start signal (AB=00) from
          the connected PBX, it should outpulse the digits.  The rest of the operation
          is similiar to wink-start.


          The allowed range for this object is 70..1000 with units in milliseconds.


          In delay-dial operation, the outgoing interface (this interface), after
          receiving a delay-dial signal (AB=11) from the connected equipment, waits
          for the start-dial signal (AB = 00) before sending the digits to the
          connected equipment. The start-dial signal tells this interface that the
          connected equipment is ready for the digits. This object specifies the
          time in milliseconds, after which incoming AB=00 will be interpreted by
          this interface as the start dial signal.

          References:  Generic Requirements, GR-506-CORE, Issue 1, June 1996,  
                       Revision 1, November 1996,
                       LSSGR: Signaling for Analog Interfaces
                       Section 11.2.3 is about 'Delay-Dial Operation' (in general) 
                       In particular, section 11.2.3.1 ([R11-22] and [R11-23]) is
                       about these timing requirements. 

        "
    DEFVAL {70}
      ::= {dsx0VismCnfEntry 26}





ds0CasFlashMinMakeTime     OBJECT-TYPE
    SYNTAX  INTEGER
    ACCESS  read-write
    STATUS  mandatory
    DESCRIPTION
        " Flash is a CAS signal generated by users to request special services. The 
          interpretation of the flash depends on the protocol in use. The signal itself 
          is an on-hook followed by an off-hook. This object specifies the minimum 
          duration for the signal to be recognized as a flash by VISM. This duration, 
          expressed in milliseconds, is defined as the elapsed time between the 
          off-to-on-hook transition followed by the on-to-off-hook transition. 
          If the on-hook duration is shorter than the value of this object, the signal 
          will be ignored.


          This object cannot be configured if the signaling type for the line to which 
          this ds0 belongs is non-CAS. For a CAS line, this object can only be configured 
          after associating this ds0 with an endpoint.  If no endpoint was added for this
          Ds0, any configuration attempt will be rejected.

          This object will be applicable if ds0CasParameterSource         
          has a value of mibvalue (2).

          The allowed range for this object is 50..1550 (msec).
        "
    DEFVAL {300}
      ::= {dsx0VismCnfEntry 27}




ds0CasFlashMaxMakeTime     OBJECT-TYPE
    SYNTAX  INTEGER
    ACCESS  read-write
    STATUS  mandatory
    DESCRIPTION
        " Flash is a CAS signal generated by users to request special services. The 
          interpretation of the flash depends on the protocol in use. The signal itself 
          is an on-hook followed by an off-hook. This object specifies the maximum 
          duration for the signal to be recognized as a flash by VISM. This duration, 
          expressed in milliseconds, is defined as the elapsed time between the 
          off-to-on-hook transition followed by the on-to-off-hook transition. 
          If the on-hook duration is longer than the value of this object, the signal 
          will be ignored.


          This object cannot be configured if the signaling type for the line to which 
          this ds0 belongs is non-CAS.

          For a CAS line, this object can only be configured after associating this ds0
          with an endpoint.  This means that if no endpoint was added for this Ds0,
          any configuration set attempt will be rejected, but any get will be allowed.


          This object will be applicable if ds0CasParameterSource         
          has a value of 'mibvalue'(2).

          The allowed range for this object is 50..1550 (msec.) with the additional 
          requirement that the value of this object should be greater than or equal 
          to ds0CasFlashMinMakeTime.
        "
    DEFVAL {1400}
      ::= {dsx0VismCnfEntry 28}





ds0CasDirectionality       OBJECT-TYPE
    SYNTAX  INTEGER {
            bidirectional (1),
            incoming      (2),
            outgoing      (3)
            }
    ACCESS  read-write
    STATUS  mandatory
    DESCRIPTION
        " This object specifies the direction in which CAS calls will be accepted on 
          this endpoint.  If this object is set to incoming, then calls from the 
          connected PBX will be accepted by VISM on this endpoint. If set to outgoing, 
          VISM will send calls towards the connected PBX and not accept calls from 
          the PBX. For VISM to both send and receive calls on this endpoint, this 
          object should be set to bidirectional. The main difference between 
          bidirectional and one-way trunks is the occurrence of glare. On bidirectional 
          trunks, since both VISM and the connected PBX can seize the endpoint at 
          approximately the same time, glare (dual seizure) is likely to occur. 
          The protocol assigned to a bidirectional endpoint should be capable of 
          detecting and resolving glare. Wink-start and delay-dial are examples of 
          protocols capable of glare handling and immediate-start, ground-start and 
          loop-start, of those that cannot.


          This object cannot be configured if the signaling type for the line to which 
          this ds0 belongs is non-CAS.

          For a CAS line, this object can only be configured after associating this ds0
          with an endpoint.  This means that if no endpoint was added for this Ds0,
          any configuration set attempt will be rejected, but any get will be allowed.
        "
    DEFVAL {bidirectional}
      ::= {dsx0VismCnfEntry  29}





ds0CasGlarePolicy          OBJECT-TYPE
    SYNTAX  INTEGER {
            controlling  (1),
            releasing    (2)
            }
    ACCESS  read-write
    STATUS  mandatory
    DESCRIPTION
        " This object specifies how a bidirectional endpoint should resolve glare. 
          This object will be used only if dsx0VismDirectionality of the endpoint is 
          bidirectional. When glare is detected, if this object is set to controlling, 
          VISM will wait for the connected PBX to assert on-hook. When the connected 
          PBX goes on-hook, VISM proceeds to dial the numbers out waits for answer. 
          If this object is set to releasing, VISM indicates the glare situation to 
          the Call Agent (as specified by the control protocol), prepares to collect 
          digits from the PBX and asserts on hook. The incoming call should go through.  
          If the CAS protocol assigned to the endpoint cannot detect glare or if it 
          cannot resolve glare according to the policy provisioned via this object, 
          this object will not be used.


          This object cannot be configured if the signaling type for the line to which 
          this ds0 belongs is non-CAS.

          For a CAS line, this object can only be configured after associating this ds0
          with an endpoint.  This means that if no endpoint was added for this Ds0,
          any configuration set attempt will be rejected, but any get will be allowed.
        "
    DEFVAL {controlling}
      ::= {dsx0VismCnfEntry 30}




ds0CasIncomingMgcpPackage  OBJECT-TYPE
    SYNTAX  DisplayString (SIZE(0..255))
    ACCESS  read-write
    STATUS  mandatory
    DESCRIPTION
        " This object, in conjunction with the card level  persistentXgcpEventsTable, 
          controls how persistent CAS events (like seize, disconnect, etc) related 
          to an incoming call observed on this DS0 are notified to the Media 
          Gateway Controller (MGC). 


          At the card level, the persistentXgcpEventsTable allows MGCP package-event 
          combinations to be configured as persistent. For example, when L/hd is added 
          to the persistentXgcpEventsTable, the hook-down event in line package will be 
          notified to the MGC every time it is observed without the MGC requesting for 
          that event.


          Since the same CAS event can map to different MGCP events under different 
          packages (eg. the CAS event 'seize' can be 'sup' in 'MS' package and 'hd' 
          in 'BL' package) and different lines could be running different packages at 
          a given time, there needs to be a per-DS0 object indicating what package 
          should be used while notifying CAS events observed on that DS0. This object, 
          ds0CasIncomingMgcpPackage specifies the package that will be used while 
          notifying CAS events observed on an incoming call on this DS0.


          This object can be set to a package name from xgcpCapabilityPackageTable whose 
          xgcpCapabilityPackageEnable is true or the string 'basic' indicating that one 
          of the basic packages in that table (G, T, L, H, R, D or M) to which the 
          observed event belongs can be used.


          This object is used only if the protocol is MGCP. If the notification is in 
          response to an RQNT, VISM uses the package (and event name) that the MGC used 
          to request the event regardless what this object is set to. 


          In the absence of an RQNT, the observed CAS event is encoded according to the 
          package that this object specifies. A 'seize' observed on the CAS signaling 
          channel on this DS0, for example is encoded as 'ms/sup' if this object is 
          set to 'ms', 'bl/hd' if this object is set to 'bl' or as 'L/hd' if this object is 
          set to 'basic'. If this package/event is present in persistentXgcpEventsTable, 
          a notification is generated, otherwise this event is discarded.


          An attempt to set this object to a package name whose
          xgcpCapabilityPackageEnable is false in xgcpCapabilityPackageTable will fail.

          This object is used only if the ds0CasDirectionality is set to bidirectional 
          or incoming.
        "
      ::= {dsx0VismCnfEntry 31}






ds0CasOutgoingMgcpPackage OBJECT-TYPE
    SYNTAX  DisplayString (SIZE(0..255))
    ACCESS  read-write
    STATUS  mandatory
    DESCRIPTION
        " This object, in conjunction with the card level  persistentXgcpEventsTable, 
          controls how persistent CAS events (like answer, disconnect, etc) related 
          to an outgoing call observed on this DS0 are notified to the Media 
          Gateway Controller (MGC). 


          At the card level, the persistentXgcpEventsTable allows MGCP package-event 
          combinations to be configured as persistent. For example, when L/hd is added 
          to the persistentXgcpEventsTable, the hook-down event in line package will be 
          notified to the MGC every time it is observed without the MGC requesting for 
          that event.


          Since the same CAS event can map to different MGCP events under different 
          packages (eg. the CAS event 'answer' can be 'ans' in 'MS' package and 'hd' 
          in 'BL' package) and different lines could be running different packages at 
          a given time, there needs to be a per-DS0 object indicating what package 
          should be used while notifying CAS events observed on that DS0. This object, 
          ds0CasOutgoingMgcpPackage specifies the package that will be used while 
          notifying CAS events observed on an outgoing call on this DS0.


          This object can be set to a package name from xgcpCapabilityPackageTable whose 
          xgcpCapabilityPackageEnable is true or the string 'basic' indicating that one 
          of the basic packages in that table (G, T, L, H, R, D or M) to which the 
          observed event belongs can be used.


          This object is used only if the protocol is MGCP. If the notification is in 
          response to an RQNT, VISM uses the package (and event name) that the MGC used 
          to request the event regardless what this object is set to. 


          In the absence of an RQNT, the observed CAS event is encoded according to the 
          package that this object specifies. An answer observed on the CAS signaling 
          channel on this DS0, for example is encoded as 'ms/ans' if this object is 
          set to 'ms', 'bl/hd' if this object is set to 'bl' or as 'L/hd' if this object is 
          set to 'basic'. If this package/event is present in persistentXgcpEventsTable, 
          a notification is generated, otherwise this event is discarded.


          An attempt to set this object to a package name whose
          xgcpCapabilityPackageEnable is false in xgcpCapabilityPackageTable will fail.

          This object is used only if the ds0CasDirectionality is set to bidirectional 
          or outgoing.
        "
      ::= {dsx0VismCnfEntry 32}



ds0InputGain     OBJECT-TYPE
    SYNTAX  INTEGER (-6..14)
    ACCESS  read-write
    STATUS  mandatory
    DESCRIPTION
        "This object indicates the amount of gain inserted at the receiver
         side of a ds0 channel, in dB (decibel) units. The default value 
         of this object is 0 dB.

         The input gain settings only define a gain/loss relative 
         to the 0 dB setting. The absolute loss at the 0 dB setting could be 
         implementation dependent based on the desired network loss plan.

         This object can be set when there are active call going on, and 
         in this case the new gain will take effective immediately. It can
         also be set at both unbound endpoints and bound but non-active 
         endpoints. 
        "
    DEFVAL { 0 }
      ::= {dsx0VismCnfEntry 33}



ds0OutputAttenuation     OBJECT-TYPE
    SYNTAX  INTEGER (0..14)
    ACCESS  read-write
    STATUS  mandatory
    DESCRIPTION
        "This object contains the amount of attenuation inserted 
         at the transmit side of a ds0 channel, in dB (decibel) units. 

         The output attenuation settings only define a loss relative to
         0 dB setting. The absolute loss at the 0 dB setting could be
         implementation dependent based on the desired network loss plan.

         This object can be set when there are active call going on, 
         and in this case the new gain will take effective immediately. 
         It can also be set at both unbound endpoints and bound but 
         non-active endpoints. 
        "
    DEFVAL { 0 }
      ::= {dsx0VismCnfEntry 34}



ds0MusicThreshold     OBJECT-TYPE
    SYNTAX  INTEGER (-70..-30)
    ACCESS  read-write
    STATUS  mandatory
    DESCRIPTION
        "The indicates Music On Hold Threshold in dBm. Based on this
         value, VISM DSP will interprete the incoming signal from TDM side 
         as either silence or voice, and consequently turn on or off VAD. 

         This object can be set when there is active call going on at the
         ds0 channel, and at both unbound endpoints and bound non-active 
         endpoints. 
        "
    DEFVAL { -38 }
      ::= {dsx0VismCnfEntry 35}




ds0SidPacket     OBJECT-TYPE
    SYNTAX       TruthValue
    ACCESS       read-write
    STATUS       mandatory
    DESCRIPTION
            "
                This object specifies whether the Silence Indication Detection 
		(SID) packet should be generated when silence suppression is in 
		active mode. The SID packet indicates the noise level during
		silence, which is used as a reference to generate comfort noise 
		on the other side of the gateway.  
            
                This object is used for VoIP only.
            "
      DEFVAL {true} 
       ::= {dsx0VismCnfEntry 36}



--
-------------------------------------------------------------------
--
--  dsx0VismChanMapTable
-- This table defines the mapping between the Ds0 and the ifIndex
-- used to index the table dsx0VismCnfTable.
------------------------------------------------------------------- 

dsx0VismChanMapTable OBJECT-TYPE
    SYNTAX  SEQUENCE OF Dsx0VismChanMapEntry
    ACCESS  not-accessible
    STATUS  mandatory
    DESCRIPTION
        "This table is created implicitly at the time of creating and deleting 
		the endpoints. This table provides the mapping information from a line
		and channel to obtain an index for that channel."
 	::= { dsx0Vism 2 }
 
dsx0VismChanMapEntry    OBJECT-TYPE
    SYNTAX  Dsx0VismChanMapEntry
    ACCESS  not-accessible
    STATUS  mandatory
    DESCRIPTION
        "
        Please see the above description.
        "
    INDEX { dsx1LineNum, ds0ChanNum }
    ::= { dsx0VismChanMapTable 1 }
 
 
Dsx0VismChanMapEntry	::=
    SEQUENCE {
		dsx1LineNum 		INTEGER,
		ds0ChanNum 			INTEGER,
		ds0ChanMapIfIndex	INTEGER
}

dsx1LineNum 		OBJECT-TYPE
    SYNTAX INTEGER (1..8)
    ACCESS  read-only
    STATUS  mandatory
    DESCRIPTION
           "This object describes the physical line number on
			VISM card.
          "
   ::= { dsx0VismChanMapEntry 1 }

ds0ChanNum 			OBJECT-TYPE
    SYNTAX INTEGER (1..31)
    ACCESS  read-only
    STATUS  mandatory
    DESCRIPTION
           "This object describes the ds0 number or channel number
			within a T1 or E1 line. 
			The valid channel numbers are 1 to 24 for T1 line
			and 1 - 31 for E1 line.
           "
   ::= { dsx0VismChanMapEntry 2 }

ds0ChanMapIfIndex	OBJECT-TYPE
    SYNTAX INTEGER
    ACCESS  read-only
    STATUS  mandatory
    DESCRIPTION
           "This object describes the ifIndex derived based on the
			line number and the channel number within the line according
			to the formula:
			IfIndex = 31 * (Ds1# - 1) + ds0#
			
			where : Ds1# - The T1/E1 line number in the range 1 - 8.
			        ds0# - The ds0 channel number ranging from
							1 to 24 for T1
						and 1 to 31 for E1.

           "
   ::= { dsx0VismChanMapEntry 3 }


--
-- ----------------------------------------------------------------------
-- VISM1.5 Alabama Project MIB
--
--
-- VISM Codec Template Configuration group
-- VISM Codec Template is used to define the set of Codecs supported
-- in VISM. This information is useful in downloading the DSP images
-- with different images, based on the compression needs and the no.
-- of channels required. 
-- Currently 3 DSP firmware images are supported:
-- 1) Echo Cancellation DSP
-- 2) G.711 - Supports upto 16 channels of G.711 per DSP
-- 3) Compression - Supports upto 8 channels of G.711 and upto 5
--    channels of G.726/32 or G.729a
-- ------------------------------------------------------------------
--
-- Modification History
-- 07/23 Incorporated the changes suggested in the review meeting. 
--
-- 10/25 Added a new bit value clearChannel in vismCodecSupported
-- 3/6/2001 Change definition of vismCodecSupported, added more bits
--          for new codecs.
--


 
vismCodecTemplateCnfGrp       OBJECT IDENTIFIER ::= {voice 7}
 
-- ------------------------------------------------------------------

vismCodecTemplateCnfGrpTable OBJECT-TYPE
    SYNTAX  SEQUENCE OF VismCodecTemplateCnfGrpEntry
    ACCESS  not-accessible
    STATUS  mandatory
    DESCRIPTION
        "This table defines the DSP templates that are applicable on
		 a card basis. It defines the set of codecs supported in each
		 template and the maximum number of DS0s supported on the VISM
		 card for a given template. 
        "
    ::= { vismCodecTemplateCnfGrp 1 }
 
vismCodecTemplateCnfGrpEntry    OBJECT-TYPE
    SYNTAX  VismCodecTemplateCnfGrpEntry
    ACCESS  not-accessible
    STATUS  mandatory
    DESCRIPTION
        "An entry is defined for each set of codecs supported.
		The codecs supported are a combination of :
	 	G.711Mu (PCM - Mu-law)
	 	G.711A (PCM - A-law)
		G.726/32 (ADPCM)
		G.729a (CS-ACELP - Annex A)
		G.729ab (CS-ACELP - Annex B)
		clearChannel (clear channel voice)
		G.723.1-H
		G.723.1a-H
		G.723.1-L
		G.723.1a-L
        "
    INDEX { vismCodecTemplateNum }
    ::= { vismCodecTemplateCnfGrpTable 1 }
 


VismCodecTemplateCnfGrpEntry ::=
    SEQUENCE {
		vismCodecTemplateNum 		INTEGER,
		vismCodecSupported			INTEGER,
	  	vismCodecTemplateMaxChanCount 	INTEGER	
}

vismCodecTemplateNum 	OBJECT-TYPE
	SYNTAX    INTEGER(1..100)
    ACCESS    read-only
    STATUS    mandatory
    DESCRIPTION
        "This attribute defines the index for the CodecTemplate
		 table. Template number is input at the time of configuring
		 a template using 'cnftemp' CLI command. 
        "
    ::= {vismCodecTemplateCnfGrpEntry  1}
 
vismCodecSupported		OBJECT-TYPE
	SYNTAX    INTEGER
    ACCESS    read-only
    STATUS    mandatory
    DESCRIPTION
        "This attribute represents a bit map of Codecs supported
		in this template.
		Bit 0 - represents the G.711 Mu-law codec.
		Bit 1 - represents the G.711 A-law codec.
		Bit 2 - represents the G.726 at rate 32 kbps.
		Bit 3 - represents the G.729a codec.
		Bit 4 - represents the G.729ab codec.
		Bit 5 - represents clear channel.
		Bit 6 - represents the G.726 at rate 16 kbps
		Bit 7 - represents the G.726 at rate 24 kbps
		Bit 8 - represents the G.726 at rate 40 kbps
		Bit 9 - Internal use (T.38)
		Bit 10 - represents the G.723.1-H codec.
		Bit 11 - represents the G.723.1a-H codec.
		Bit 12 - represents the G.723.1-L codec.
		Bit 13 - represents the G.723.1a-L codec.
		The remaining bits will be defined in future when other
		types of codecs are supported.
        "
    ::= { vismCodecTemplateCnfGrpEntry 2}
 

vismCodecTemplateMaxChanCount 	OBJECT-TYPE	
	SYNTAX    INTEGER
    ACCESS    read-only
    STATUS    mandatory
    DESCRIPTION
        "The max. number of channels supported for this template.
		Based on the codec that is of the maximum complexity, the
		maximum no. of channels that can be supported with a given
		set of codecs is determined and stored in this variable. 
        "
    ::= { vismCodecTemplateCnfGrpEntry 3}
 
--
-- ----------------------------------------------------------------------
-- BASIS Project MIB
--
--
-- VISM cardSpecific vismCodecCnf group
--
-- ------------------------------------------------------------------
--
-- Modification History
-- 03/10 Initial version checked-in
-- 04/19 Added vismCodecPreference 
-- 04/20 Added description to indicate that vismCodecPreference is 
--       applicable only from VISM20 release onwards
-- 04/27/2000 INDIANA MIB changes
-- 01/19/2001 Change G.726-32 to G.726 at rate 32 kbps
-- 01/23/2001 Added g726r16000, g726r24000 and g726r40000 to 
--            vismCodecCnfIndex. Change vismCodecPreference definition.
-- 08/22/2001 Added g723.1 family   
--




   vismCodecCnfGrp  OBJECT IDENTIFIER ::= { voice 18 }
 
-- ------------------------------------------------------------------
--
-- vismCodecCnf  group
--
--
-- The MIB variables in this group have been defined to configure
-- the packetization period on a per codec basis. This table is
-- applicable only in voipSwitching applications.For aal2Trunking
-- applications we will be using Profile table  
--
-- ------------------------------------------------------------------


vismCodecCnfTable OBJECT-TYPE
    SYNTAX  SEQUENCE OF VismCodecCnfEntry
    ACCESS  not-accessible
    STATUS  mandatory
    DESCRIPTION
        "This table contains configuration information about 
         different codecs and there packetization periods. 
        "
    ::= { vismCodecCnfGrp 1 }

vismCodecCnfEntry OBJECT-TYPE
    SYNTAX  VismCodecCnfEntry 
    ACCESS  not-accessible
    STATUS  mandatory
    DESCRIPTION
        "An entry in the vismCodecCnf table. Each entry consists 
         of packetization period information for a specific codec.

         All the entries in this table are implicitly created when the card
         comes up with appropriate default values and the user can modify the
         packetization period for a particular codec any point in time.
        "
    INDEX { vismCodecCnfIndex}
    ::= { vismCodecCnfTable 1 }

VismCodecCnfEntry ::=
    SEQUENCE
       {
          vismCodecCnfIndex    INTEGER,
          vismCodecName        DisplayString,
          vismCodecPktPeriod   INTEGER,
          vismCodecPreference  INTEGER,
          vismCodecString      DisplayString,
          vismCodecIanaType    INTEGER
       }

vismCodecCnfIndex    OBJECT-TYPE
    SYNTAX  INTEGER {
                                g711u        (1),
                                g711a        (2),
                                g726r32000   (3),
                                g729a        (4),
                                g729ab       (5),
                                clearChannel (6),
                                g726r16000   (7),
                                g726r24000   (8),
                                g726r40000   (9),
                                g723h        (11),
                                g723ah       (12),
                                g723l        (13),
                                g723al       (14)

              }
    ACCESS  read-only
    STATUS  mandatory
    DESCRIPTION
        " This object is a index to this table.
            1 represents  G.711u  
            2 represents  G.711a  
            3 represents  G.726 at rate 32 kbps 
            4 represents  G.729a   
            5 represents  G.729ab 
            6 represents  clear channel
            7 represents  G.726 at rate 16 kbps
            8 represents  G.726 at rate 24 kbps
            9 represents  G.726 at rate 40 kbps
           10 RESERVED
           11 represents  G.723.1-H at rate 6.4kbps
           12 represents  G.723.1a-H at rate 6.4kbps with SID
           13 represents  G.723.1-L at rate 5.3kbps
           14 represents  G.723.1a-L at rate 5.3kbps with SID

        "
    ::= { vismCodecCnfEntry 1 }

vismCodecName   OBJECT-TYPE
    SYNTAX  DisplayString (SIZE (1..64))
    ACCESS  read-only
    STATUS  mandatory
    DESCRIPTION
        " This object holds the name of the codec
          for example index 1 will have G.711u as the codec name
          index 2 will have G.711a as the codec name and so on....
        "
     ::= {vismCodecCnfEntry 2}

vismCodecPktPeriod OBJECT-TYPE
    SYNTAX  INTEGER
           {
             ten    (10),
             twenty (20),
             thirty (30),
             fourty (40),
             sixty  (60)
           }
    ACCESS  read-write
    STATUS  mandatory
    DESCRIPTION
        " This object gives the packetization period for a particular codec
          in milli secs.  
             for  G.711a  allowed values are  10 & 20
             for  G.711u  allowed values are 10 & 20 
             for  G.726 at rate 32 kbps allowed values are 10 ,20 30 & 40
             for  G.729a   allowed values are 10, 20 ,30 & 40
             for  G.729ab  allowed values are 10, 20, 30 & 40 
             for clear channel allowed values are 10 and 20
             for  G.723  allowed values are  30 & 60
			 Default value for G.723 is 30 and for other codecs it is 10.
        "
    ::= { vismCodecCnfEntry 3 }

            
vismCodecPreference OBJECT-TYPE
     SYNTAX   INTEGER (0..65535) 
     ACCESS   read-write
     STATUS   mandatory
     DESCRIPTION
         "
          This object contains the user configured preference for
          each codec. Lower the number, higher the preference of the
          codec . Since currently we only have 14 codecs supported, the 
          allowed range of this object is 0-13. 

          If the call agent does not specify the preferred codec list
          in CRCX request then the codec used will be the one of highest
          preference, as configured in this object.

          The default preference based on the codec type is 
             G729ab will have preference 1
             G729a  will have preference 2
             G726 at rate 16 kbps will have preference 3
             G726 at rate 24 kbps will have preference 4 
             G726 at rate 32 kbps will have preference 5 
             G726 at rate 40 kbps will have preference 6 
             G.711u will have preference 7 for T1 and will have
                                 preference 8 for E1 
             G.711a will have preference 7 for E1 card and will
                             have preference 8 for T1 
             clearChannel will have preference 9 
             G723H  will have preference 10
             G723AH will have preference 11
             G723L  will have preference 12
             G723AL will have preference 13

          This object is not applicable in releases earlier than VISM2.0.1.
          If the preference of a codec is zero then that codec will not
          be used. 
         "  
       ::= {vismCodecCnfEntry 4}

vismCodecString      OBJECT-TYPE
      SYNTAX         DisplayString (SIZE (1..64))
      ACCESS         read-write
      STATUS         mandatory
      DESCRIPTION
        "
          The local connection option or SDP descriptor string that vism 
          would get from the call agent for the codec to be used will be
          in the form of PCMU, PCMA, G726 at rate 32 kbps, G729a, CCD .....
             where in PCMU stands for G711u
                      PCMA stands for G711a
                 and  CCD  stands for clear channel

          This object serves as a mapping string, and the vism will use the 
          value configured in this object to match the SDP 
          descriptor string obtained for a codec in a CRCX 
          or MDCX message.

          Since the entries in this table are implicitly created
          by default the entry with codec = 
                 G.711u  will have a value of PCMU
                 G.711a  will have a value of PCMA
                 clear channel will have a value of CCD
                 G.726 at rate 32 kbps will have G726 at rate 32 kbps
                 G.726 at rate 16 kbps will have G726 at rate 16 kbps
                 G.726 at rate 24 kbps will have G726 at rate 24 kbps
                 G.726 at rate 40 kbps will have G726 at rate 40 kbps
                 G.729a  will have G729a
                 G.729ab will have G729ab
                 G.723.1-H will have G723H
                 G.723.1a-H will have G723AH
                 G.723.1-L will have G723L
                 G.723.1a-L will have G723AL
            
        "
       ::= {vismCodecCnfEntry 5}
 

vismCodecIanaType    OBJECT-TYPE
     SYNTAX          INTEGER (0..96)
     ACCESS          read-write
     STATUS          mandatory
     DESCRIPTION
          " 
            The codecs are assigned types (numbers) by IANA.  
            This object will contain such a number.  In future we may have 
            more numbers.
           
            currently by default we have PCMU =  0
                                          G.726 at rate 32 kbps  = 2
                                          PCMA =  8
                                  and the rest codecs will have 96
 
            If in a SDP string we would just receive an IANA type number and 
            not the codec string, then vism would use the value in
            this object to derive the actual codec to be used in the bearer
            path.

            The valid Iana type numbers currently defined are from (0 .. 95)
            So if an entry has a value of 96 that means it is not a registered
            codec.In that case the actual codec will be determined by the 
            vism using the rtpmap in SDP string. 
         "
         ::= {vismCodecCnfEntry 6} 


            
--
-- ----------------------------------------------------------------------
-- VISM 2.x Project MIB
--    Revision history:
--           initial draft : Thu Aug  3 16:29:53 PDT 2000
--
-- It contains MIB objects for VISM CAC (connection admission control)
-- failure statistics applicable to both SVC and PVC connections.
-- 
-- ----------------------------------------------------------------------
--




-- vismCardCacFailuresGrp
-- ---------------------------------------------------------------------
vismCardCacFailuresGrp     OBJECT IDENTIFIER ::= { voice  20 }

vismPortCacPvcAddFailures  OBJECT-TYPE
    SYNTAX     Counter
    ACCESS     read-only
    STATUS     mandatory
    DESCRIPTION
        "Total number of attempts to add or modify a PVC to VISM virtual port 
         that were rejected by port level connection admission control.
        "
    ::= { vismCardCacFailuresGrp 1 }

vismPortCacSvcAddFailures  OBJECT-TYPE
    SYNTAX     Counter
    ACCESS     read-only
    STATUS     mandatory
    DESCRIPTION
        "Total number of attempts to add a SVC to VISM virtual port 
         that were rejected by port level connection admission control.
        "
    ::= { vismCardCacFailuresGrp 2 }

vismVcCacPvcFailures  OBJECT-TYPE
    SYNTAX     Counter
    ACCESS     read-only
    STATUS     mandatory
    DESCRIPTION
        "Total number of attempts to admit voice connections over bearer PVC
         connections that were rejected by voice connection admission control.

         It is sum of all voice connection admission control failures
         for all VISM bearer PVC connections.
        "
    ::= { vismCardCacFailuresGrp 3 }

vismVcCacPvcUpspeedFailures  OBJECT-TYPE
    SYNTAX     Counter
    ACCESS     read-only
    STATUS     mandatory
    DESCRIPTION
        "Total number of attempts to upspeed voice connections over bearer PVC
         connections that were rejected by Port Level Connection Admission
         Control.
        "
    ::= { vismCardCacFailuresGrp 4 }

vismPortCacSvcUpspeedFailures  OBJECT-TYPE
    SYNTAX     Counter
    ACCESS     read-only
    STATUS     mandatory
    DESCRIPTION
        "Total number of attempts to upspeed voice connections over bearer SVC
         connections that were rejected by Port Level Connection Admission
         Control.
        "
    ::= { vismCardCacFailuresGrp 5 }

END
