-- *************************************************
-- TridiumR3 - M I B . m y
-- 
-- Revision History:
--    25 March 99   Robert Adams    Original Niagara R2 code
--    18 Dec 2002   Scott Hoye      Modified for Niagara
--                                  R3 SNMP implementation.
--
-- Copyright 1999 Tridium, Inc.
-- *************************************************
--


TRIDIUMR3-MIB DEFINITIONS ::= BEGIN

-- MIB II Extension Definitions for hub management

IMPORTS 
         OBJECT-TYPE 
               FROM RFC-1212
         TRAP-TYPE
               FROM RFC-1215
         enterprises
               FROM RFC1155-SMI
         DisplayString
               FROM RFC1213-MIB;

    tridium           OBJECT IDENTIFIER ::= { enterprises 4131 }
    tridiumStation    OBJECT IDENTIFIER ::= { tridium 1 }

version    OBJECT-TYPE
    SYNTAX     DisplayString
    ACCESS     read-only
    STATUS     mandatory
    DESCRIPTION
    "Current software version"
    ::=  { tridiumStation 1 }

action   OBJECT-TYPE
    SYNTAX            INTEGER{
                       noAction(0),
                       ackAll(1)
                      }
    ACCESS            read-write
    STATUS            mandatory
    DESCRIPTION
    "Provides means for manager to perform actions on the alarm table. 0 (no action) or 1 (acknowledge all)."
    ::=  { tridiumStation 2 }

-- ***********************************
-- *
-- *  Alarm table declarations
-- *
-- ***********************************

alarmTable   OBJECT-TYPE
    SYNTAX                SEQUENCE OF AlarmTableEntry
    ACCESS                not-accessible
    STATUS                mandatory
    DESCRIPTION
    "A list of alarms in the station which have an snmp recipient (configured to store received alarms)."
    ::=  { tridiumStation 3 }

alarmTableEntry  OBJECT-TYPE
    SYNTAX                AlarmTableEntry
    ACCESS                not-accessible
    STATUS                mandatory
    DESCRIPTION
    "An alarm table entry containing data for a specific alarm."
    INDEX  { IMPLIED uuid }  ::=   { alarmTable 1 }

AlarmTableEntry ::= SEQUENCE {
        timestamp        DisplayString,
        uuid             OCTET STRING,
        sourceState      INTEGER,
        ackState         INTEGER,
        ackRequired      INTEGER,        
        source           DisplayString,
        alarmClass       DisplayString,
        priority         INTEGER,
        normalTime       DisplayString,
        ackTime          DisplayString,
        user             DisplayString,
        alarmData        DisplayString,
        alarmTransition  INTEGER,
        lastUpdate       DisplayString
    }

timestamp   OBJECT-TYPE
    SYNTAX           DisplayString
    ACCESS           read-only
    STATUS           mandatory
    DESCRIPTION
    "Indicates the time when the alarm occurred."
    ::=   { alarmTableEntry 1 }

uuid   OBJECT-TYPE
    SYNTAX           OCTET STRING(SIZE(0..255))
    ACCESS           read-only
    STATUS           mandatory
    DESCRIPTION
    "The unique universal identifier of the alarm."
    ::=   { alarmTableEntry 2 }

sourceState   OBJECT-TYPE
    SYNTAX           INTEGER {
                       normal(0),
                       offnormal(1),
                       fault(2),
                       alert(3)
                     }
    ACCESS           read-only
    STATUS           mandatory
    DESCRIPTION
    "The current state of the source.  normal(0), offnormal(1), fault(2), or alert(3)."
    ::=   { alarmTableEntry 3 }

ackState   OBJECT-TYPE
    SYNTAX           INTEGER {
                       acked(0),
                       unacked(1),
                       ackPending(2)     
                     }
    ACCESS           read-write
    STATUS           mandatory
    DESCRIPTION
    "Indicates if the alarm has been acknowledged.  acked(0), unacked(1), or ackPending(2).  
     Alarm can be acknowledged by setting ackState to 'acked'(0)"
    ::=   { alarmTableEntry 4 }

ackRequired   OBJECT-TYPE
    SYNTAX           INTEGER {
                       false(0),
                       true(1)     
                     }
    ACCESS           read-only
    STATUS           mandatory
    DESCRIPTION
    "Indicates if an acknowledgement is required for the alarm.  false(0), or true(1)."
    ::=   { alarmTableEntry 5 }

source    OBJECT-TYPE
    SYNTAX           DisplayString
    ACCESS           read-only
    STATUS           mandatory
    DESCRIPTION
    "Indicates the path to the station object which generated the alarm."
    ::=   { alarmTableEntry 6 }
    
alarmClass  OBJECT-TYPE
    SYNTAX           DisplayString
    ACCESS           read-only
    STATUS           mandatory
    DESCRIPTION
    "The alarm class for the alarm."
    ::=   { alarmTableEntry 7 }

priority   OBJECT-TYPE
    SYNTAX           INTEGER(0..255)
    ACCESS           read-only
    STATUS           mandatory
    DESCRIPTION
    "The priority of the alarm (0=high, 255=low)."
    ::=   { alarmTableEntry 8 }

normalTime   OBJECT-TYPE
    SYNTAX           DisplayString
    ACCESS           read-only
    STATUS           mandatory
    DESCRIPTION
    "The time at which the alarm goes back to normal state."
    ::=   { alarmTableEntry 9 }

ackTime  OBJECT-TYPE
    SYNTAX           DisplayString
    ACCESS           read-only
    STATUS           mandatory
    DESCRIPTION
    "The time at which the alarm is acked. Note that 
     interpretation of this value depends upon the state of the alarm."
    ::=   { alarmTableEntry 10 }

user   OBJECT-TYPE
    SYNTAX           DisplayString
    ACCESS           read-only
    STATUS           mandatory
    DESCRIPTION
    "The name of the user who acknowledged the alarm."
    ::=   { alarmTableEntry 11 }

alarmData     OBJECT-TYPE
    SYNTAX           DisplayString
    ACCESS           read-only
    STATUS           mandatory
    DESCRIPTION
    "A string containing dynamic alarm data, in key-value pairs."
    ::=   { alarmTableEntry 12 }

alarmTransition   OBJECT-TYPE
    SYNTAX           INTEGER {
                       normal(0),
                       offnormal(1),
                       fault(2),
                       alert(3)
                     }
    ACCESS           read-only
    STATUS           mandatory
    DESCRIPTION
    "The initial state of the source.  normal(0), offnormal(1), fault(2), or alert(3)."
    ::=   { alarmTableEntry 13 }

lastUpdate  OBJECT-TYPE
    SYNTAX           DisplayString
    ACCESS           read-only
    STATUS           mandatory
    DESCRIPTION
    "The time at which the alarm was last updated. Updates occur 
     at creation, acknowlegement, and changes to alarmData such as notes."
    ::=   { alarmTableEntry 14 }

-- ***********************************
-- *
-- *  Input table declarations
-- *
-- ***********************************

inputTable   OBJECT-TYPE
    SYNTAX                SEQUENCE OF InputTableEntry
    ACCESS                not-accessible
    STATUS                mandatory
    DESCRIPTION
    "A list of snmp input object values."
    ::=  { tridiumStation 4 }

inputTableEntry  OBJECT-TYPE
    SYNTAX                InputTableEntry
    ACCESS                not-accessible
    STATUS                mandatory
    DESCRIPTION
    "An input table entry containing data for a specific input."
    INDEX  { inputIndex }  ::=   { inputTable 1 }

InputTableEntry ::= SEQUENCE {
        inputIndex       INTEGER,
        inputName        DisplayString,
        inputValue       DisplayString
    }

inputIndex   OBJECT-TYPE
    SYNTAX           INTEGER(0..2147483647)
    ACCESS           read-only
    STATUS           mandatory
    DESCRIPTION
    "The index in the input table for a particular snmp input
	 object.  Used to address table entries."
    ::=   { inputTableEntry 1 }


inputName    OBJECT-TYPE
    SYNTAX           DisplayString
    ACCESS           read-only
    STATUS           mandatory
    DESCRIPTION
    "Name of station object."
    ::=   { inputTableEntry 2 }

inputValue    OBJECT-TYPE
    SYNTAX           DisplayString
    ACCESS           read-write
    STATUS           mandatory
    DESCRIPTION
    "Current value of station object. Is writeable."
    ::=   { inputTableEntry 3 }

-- ***********************************
-- *
-- *  Output table declarations
-- *
-- ***********************************

outputTable   OBJECT-TYPE
    SYNTAX                SEQUENCE OF OutputTableEntry
    ACCESS                not-accessible
    STATUS                mandatory
    DESCRIPTION
    "A list of snmp output (read-only) object values."
    ::=  { tridiumStation 5 }

outputTableEntry  OBJECT-TYPE
    SYNTAX                OutputTableEntry
    ACCESS                not-accessible
    STATUS                mandatory
    DESCRIPTION
    "An output table entry containing data for a specific output."
    INDEX  { outputIndex }  ::=   { outputTable 1 }

OutputTableEntry ::= SEQUENCE {
        outputIndex       INTEGER,
        outputName        DisplayString,
        outputValue       DisplayString
    }

outputIndex   OBJECT-TYPE
    SYNTAX           INTEGER(0..2147483647)
    ACCESS           read-only
    STATUS           mandatory
    DESCRIPTION
    "The index in the output table for a particular snmp output
	 object.  Used to address table entries."
    ::=   { outputTableEntry 1 }


outputName    OBJECT-TYPE
    SYNTAX           DisplayString
    ACCESS           read-only
    STATUS           mandatory
    DESCRIPTION
    "Name of station object."
    ::=   { outputTableEntry 2 }

outputValue    OBJECT-TYPE
    SYNTAX           DisplayString
    ACCESS           read-only
    STATUS           mandatory
    DESCRIPTION
    "Current value of station object. Is read-only."
    ::=   { outputTableEntry 3 }


-- ***********************************
-- *
-- *  Alarm trap declarations
-- *
-- ***********************************


stationAlarm TRAP-TYPE
-- Non-reverse mappable trap
    ENTERPRISE tridiumStation
    VARIABLES { timestamp,
                uuid,
                sourceState,
                ackState,
                ackRequired,        
                source,
                alarmClass,
                priority,
                normalTime,
                ackTime,
                user,
                alarmData,
                alarmTransition,
                lastUpdate }
--  Status
--    mandatory
    DESCRIPTION
        "The stationAlarm trap is generated when a Niagara alarm is received
         by an snmp recipient which has routing alarms to a network manager
         enabled.  It contains useful information from the alarm record."
    ::= 1


END
