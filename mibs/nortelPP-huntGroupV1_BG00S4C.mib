Nortel-Magellan-Passport-HuntGroupMIB
DEFINITIONS ::= BEGIN



IMPORTS

      OBJECT-TYPE
   FROM RFC-1212

      components,
      passportMIBs
   FROM Nortel-Magellan-Passport-UsefulDefinitionsMIB

      Counter32,
      DisplayString,
      StorageType,
      RowStatus,
      Integer32,
      Unsigned32
   FROM Nortel-Magellan-Passport-StandardTextualConventionsMIB

      AsciiString,
      Link
   FROM Nortel-Magellan-Passport-TextualConventionsMIB;




-- LAST-UPDATED   "9902010000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     HuntGroup Enterprise MIB."

huntGroupMIB OBJECT IDENTIFIER ::= { passportMIBs 130 }










-- HuntGroup/n
-- The HuntGroup component provides a hunt group capability for 
-- switched calls (SVCs).
-- A hunt group is a single DNA used to represent a group of service 
-- DNAs. A customer calling the DNA of the hunt group receives the 
-- benefits of higher capacity and availability as calls are spread across 
-- several lines.

hg OBJECT IDENTIFIER ::= { components 131 }



hgRowStatusTable OBJECT-TYPE
   SYNTAX     SEQUENCE OF HgRowStatusEntry
   ACCESS     not-accessible
   STATUS     mandatory
   DESCRIPTION
     "This entry controls the addition and deletion of 
      hg components."
::= { hg 1 }

hgRowStatusEntry OBJECT-TYPE
   SYNTAX     HgRowStatusEntry
   ACCESS     not-accessible
   STATUS     mandatory
   DESCRIPTION
     "A single entry in the table represents a single 
      hg component."
   INDEX {
      hgIndex }
::= { hgRowStatusTable 1 }

HgRowStatusEntry ::= SEQUENCE {
   hgRowStatus
      RowStatus,
   hgComponentName
      DisplayString,
   hgStorageType
      StorageType,
   hgIndex
      Integer32 }

hgRowStatus OBJECT-TYPE
   SYNTAX     RowStatus 
   ACCESS     read-write
   STATUS     mandatory
   DESCRIPTION
     "This variable is used as the basis for SNMP naming of
      hg components.
      These components can be added and deleted."
::= { hgRowStatusEntry 1 }

hgComponentName OBJECT-TYPE
   SYNTAX     DisplayString 
   ACCESS     read-only
   STATUS     mandatory
   DESCRIPTION
     "This variable provides the component's string name for
      use with the ASCII Console Interface"
::= { hgRowStatusEntry 2 }

hgStorageType OBJECT-TYPE
   SYNTAX     StorageType 
   ACCESS     read-only
   STATUS     mandatory
   DESCRIPTION
     "This variable represents the storage type value for the
      hg tables."
::= { hgRowStatusEntry 4 }

hgIndex OBJECT-TYPE
   SYNTAX     Integer32 (1..65535)
   ACCESS     not-accessible
   STATUS     mandatory
   DESCRIPTION
     "This variable represents the index for the hg tables."
::= { hgRowStatusEntry 10 }

hgCidDataTable OBJECT-TYPE
   SYNTAX     SEQUENCE OF HgCidDataEntry
   ACCESS     not-accessible
   STATUS     mandatory
   DESCRIPTION
     "This group contains the attribute for a component's Customer 
      Identifier (CID). Refer to the attribute description for a detailed 
      explanation of CIDs."
::= { hg 10 }

hgCidDataEntry OBJECT-TYPE
   SYNTAX     HgCidDataEntry
   ACCESS     not-accessible
   STATUS     mandatory
   DESCRIPTION
     "An entry in the hgCidDataTable."
   INDEX {
      hgIndex }
::= { hgCidDataTable 1 }

HgCidDataEntry ::= SEQUENCE {
   hgCustomerIdentifier
      Unsigned32 }

hgCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { hgCidDataEntry 1 }

hgNsapAddressTable OBJECT-TYPE
   SYNTAX     SEQUENCE OF HgNsapAddressEntry
   ACCESS     not-accessible
   STATUS     mandatory
   DESCRIPTION
     "This group contains attributes common to all NSAP format 
      addresses."
::= { hg 11 }

hgNsapAddressEntry OBJECT-TYPE
   SYNTAX     HgNsapAddressEntry
   ACCESS     not-accessible
   STATUS     mandatory
   DESCRIPTION
     "An entry in the hgNsapAddressTable."
   INDEX {
      hgIndex }
::= { hgNsapAddressTable 1 }

HgNsapAddressEntry ::= SEQUENCE {
   hgAddress
      AsciiString }

hgAddress OBJECT-TYPE
   SYNTAX     AsciiString (SIZE (1..17))
   ACCESS     read-write
   STATUS     mandatory
   DESCRIPTION
     "The address attribute specifies the numbering plan and digits which 
      form a unique DNA identifier of the hunt group. The format of the 
      address attribute is <numberingPlan>.<digits> where numbering 
      plan is x for X.121 and e for E.164. An example X.121 address is 
      x.12345678."
::= { hgNsapAddressEntry 1 }

hgProvTable OBJECT-TYPE
   SYNTAX     SEQUENCE OF HgProvEntry
   ACCESS     not-accessible
   STATUS     mandatory
   DESCRIPTION
     "The Provisioned group contains the provisioned attributes of the 
      hunt group."
::= { hg 12 }

hgProvEntry OBJECT-TYPE
   SYNTAX     HgProvEntry
   ACCESS     not-accessible
   STATUS     mandatory
   DESCRIPTION
     "An entry in the hgProvTable."
   INDEX {
      hgIndex }
::= { hgProvTable 1 }

HgProvEntry ::= SEQUENCE {
   hgLogicalProcessor
      Link,
   hgSelectionPolicy
      INTEGER,
   hgMaxHuntAttempts
      Unsigned32,
   hgAppendSuffixDigits
      INTEGER }

hgLogicalProcessor OBJECT-TYPE
   SYNTAX     Link 
   ACCESS     read-write
   STATUS     mandatory
   DESCRIPTION
     "This attribute specifies the logical processor on which the hunt 
      group process will execute. The Lp/n Eng Hgs component contains 
      statistics for all hunt groups on the LP."
::= { hgProvEntry 1 }

hgSelectionPolicy OBJECT-TYPE
   SYNTAX     INTEGER  {
                 startFromZero(0),
                 rotary(1),
                 mostAvailable(2) }
   ACCESS     read-write
   STATUS     mandatory
   DESCRIPTION
     "The selectionPolicy attribute specifies the algorithm used to select a 
      hunt group member.
      
      A value of startFromZero means that on a new call, the first 
      available member starting from the member with the lowest 
      instance value is selected. Subsequent hunts for the same call select 
      the first available member starting from the previously chosen 
      member. This algorithm is used when it is desirable to have the first 
      member receive the majority of the calls and subsequent members 
      only receive calls in overflow situations.
      
      A value of rotary means that on a new call, the first available 
      member is selected starting from the member which received the 
      last new call. Subsequent hunts for the same call select the first 
      available member starting from the previously chosen member. This 
      algorithm is used when it is desirable to loadspread the calls equally 
      across the members.
      
      A value of mostAvailable means that on a new call, the most 
      available member is selected based on the availability information 
      received from the member. Subsequent hunts for the same call 
      select the most available member starting from the previously 
      chosen member. This algorithm is used when it is desirable to send 
      each call to the member which has the highest probability of 
      connecting it."
   DEFVAL     { mostAvailable }
::= { hgProvEntry 2 }

hgMaxHuntAttempts OBJECT-TYPE
   SYNTAX     Unsigned32 (1..63)
   ACCESS     read-write
   STATUS     mandatory
   DESCRIPTION
     "The maxHuntAttempts attribute specifies the maximum attempts 
      allowed to hunt the call. Hunting ceases if either this maximum is 
      exceeded or the member list is exhausted."
   DEFVAL     { 63 }
::= { hgProvEntry 3 }

hgAppendSuffixDigits OBJECT-TYPE
   SYNTAX     INTEGER  {
                 no(0),
                 yes(1) }
   ACCESS     read-write
   STATUS     mandatory
   DESCRIPTION
     "The appendSuffixDigits attribute specifies how suffix called address 
      digits are handled. Suffix called address digits are any trailing 
      digits, signalled in a call, beyond the provisioned hunt group 
      address. If this attribute is set to yes, suffix digits are appended to 
      the member address before the call is forwarded to the member. If it 
      is set to no, suffix digits are not appended to the member address."
   DEFVAL     { yes }
::= { hgProvEntry 4 }

hgStateTable OBJECT-TYPE
   SYNTAX     SEQUENCE OF HgStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { hg 20 }

hgStateEntry OBJECT-TYPE
   SYNTAX     HgStateEntry
   ACCESS     not-accessible
   STATUS     mandatory
   DESCRIPTION
     "An entry in the hgStateTable."
   INDEX {
      hgIndex }
::= { hgStateTable 1 }

HgStateEntry ::= SEQUENCE {
   hgAdminState
      INTEGER,
   hgOperationalState
      INTEGER,
   hgUsageState
      INTEGER }

hgAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { hgStateEntry 1 }

hgOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { hgStateEntry 2 }

hgUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { hgStateEntry 3 }

hgOperationalTable OBJECT-TYPE
   SYNTAX     SEQUENCE OF HgOperationalEntry
   ACCESS     not-accessible
   STATUS     mandatory
   DESCRIPTION
     "The Operational group contains the operational attributes of the 
      hunt group."
::= { hg 21 }

hgOperationalEntry OBJECT-TYPE
   SYNTAX     HgOperationalEntry
   ACCESS     not-accessible
   STATUS     mandatory
   DESCRIPTION
     "An entry in the hgOperationalTable."
   INDEX {
      hgIndex }
::= { hgOperationalTable 1 }

HgOperationalEntry ::= SEQUENCE {
   hgHuntAttempts
      Counter32,
   hgFailedCalls
      Counter32,
   hgInitialHuntAttempts
      Counter32,
   hgAvailabilityUpdates
      Counter32,
   hgMaxAddrLenExceeded
      Counter32,
   hgBadPackets
      Counter32 }

hgHuntAttempts OBJECT-TYPE
   SYNTAX     Counter32 
   ACCESS     read-only
   STATUS     mandatory
   DESCRIPTION
     "This attribute counts the total number of hunt attempts made by the 
      hunt group. The count includes both initial and subsequent hunt 
      attempts. This count is contained within the huntAttempts attribute 
      of the Lp/n Eng Hgs component. This counter wraps to 0 when it 
      exceeds its maximum value."
::= { hgOperationalEntry 2 }

hgFailedCalls OBJECT-TYPE
   SYNTAX     Counter32 
   ACCESS     read-only
   STATUS     mandatory
   DESCRIPTION
     "This attribute counts the number of calls which could not be 
      connected by any of the hunt group members. This could occur if 
      the hunt group is locked or has exhausted its member list. If a call 
      cannot be connected by the hunt group it is sent to call redirection. 
      This counter wraps to 0 when it exceeds its maximum value."
::= { hgOperationalEntry 3 }

hgInitialHuntAttempts OBJECT-TYPE
   SYNTAX     Counter32 
   ACCESS     read-only
   STATUS     mandatory
   DESCRIPTION
     "This attribute counts the number of new (non-hunted) calls received 
      by the hunt group which are forwarded to a member. This counter 
      wraps to 0 when it exceeds its maximum value."
::= { hgOperationalEntry 4 }

hgAvailabilityUpdates OBJECT-TYPE
   SYNTAX     Counter32 
   ACCESS     read-only
   STATUS     mandatory
   DESCRIPTION
     "This attribute counts the number of availability update packets 
      received by the hunt group from its members. This counter wraps to 
      0 when it exceeds its maximum value."
::= { hgOperationalEntry 5 }

hgMaxAddrLenExceeded OBJECT-TYPE
   SYNTAX     Counter32 
   ACCESS     read-only
   STATUS     mandatory
   DESCRIPTION
     "This attribute counts the number of times a member could not be 
      selected to receive a call with suffix address digits because its DNA 
      length would exceed the maximum of 14 digits with the suffix digits 
      appended. This counter wraps to 0 when it exceeds its maximum 
      value."
::= { hgOperationalEntry 6 }

hgBadPackets OBJECT-TYPE
   SYNTAX     Counter32 
   ACCESS     read-only
   STATUS     mandatory
   DESCRIPTION
     "This attribute counts the number of unrecognizable packets received 
      by the hunt group and discarded. This counter wraps to 0 when it 
      exceeds its maximum value."
::= { hgOperationalEntry 7 }


-- Hg/n HuntGroupMember/n
-- The HuntGroupMember component defines an instance of a hunt 
-- group member.

hgHgM OBJECT IDENTIFIER ::= { hg 2 }



hgHgMRowStatusTable OBJECT-TYPE
   SYNTAX     SEQUENCE OF HgHgMRowStatusEntry
   ACCESS     not-accessible
   STATUS     mandatory
   DESCRIPTION
     "This entry controls the addition and deletion of 
      hgHgM components."
::= { hgHgM 1 }

hgHgMRowStatusEntry OBJECT-TYPE
   SYNTAX     HgHgMRowStatusEntry
   ACCESS     not-accessible
   STATUS     mandatory
   DESCRIPTION
     "A single entry in the table represents a single 
      hgHgM component."
   INDEX {
      hgIndex,
      hgHgMIndex }
::= { hgHgMRowStatusTable 1 }

HgHgMRowStatusEntry ::= SEQUENCE {
   hgHgMRowStatus
      RowStatus,
   hgHgMComponentName
      DisplayString,
   hgHgMStorageType
      StorageType,
   hgHgMIndex
      Integer32 }

hgHgMRowStatus OBJECT-TYPE
   SYNTAX     RowStatus 
   ACCESS     read-write
   STATUS     mandatory
   DESCRIPTION
     "This variable is used as the basis for SNMP naming of
      hgHgM components.
      These components can be added and deleted."
::= { hgHgMRowStatusEntry 1 }

hgHgMComponentName OBJECT-TYPE
   SYNTAX     DisplayString 
   ACCESS     read-only
   STATUS     mandatory
   DESCRIPTION
     "This variable provides the component's string name for
      use with the ASCII Console Interface"
::= { hgHgMRowStatusEntry 2 }

hgHgMStorageType OBJECT-TYPE
   SYNTAX     StorageType 
   ACCESS     read-only
   STATUS     mandatory
   DESCRIPTION
     "This variable represents the storage type value for the
      hgHgM tables."
::= { hgHgMRowStatusEntry 4 }

hgHgMIndex OBJECT-TYPE
   SYNTAX     Integer32 (1..63)
   ACCESS     not-accessible
   STATUS     mandatory
   DESCRIPTION
     "This variable represents the index for the hgHgM tables."
::= { hgHgMRowStatusEntry 10 }

hgHgMProvTable OBJECT-TYPE
   SYNTAX     SEQUENCE OF HgHgMProvEntry
   ACCESS     not-accessible
   STATUS     mandatory
   DESCRIPTION
     "The Provisioned group contains the provisioned attributes of the 
      hunt group member."
::= { hgHgM 10 }

hgHgMProvEntry OBJECT-TYPE
   SYNTAX     HgHgMProvEntry
   ACCESS     not-accessible
   STATUS     mandatory
   DESCRIPTION
     "An entry in the hgHgMProvTable."
   INDEX {
      hgIndex,
      hgHgMIndex }
::= { hgHgMProvTable 1 }

HgHgMProvEntry ::= SEQUENCE {
   hgHgMAddress
      AsciiString }

hgHgMAddress OBJECT-TYPE
   SYNTAX     AsciiString (SIZE (1..17))
   ACCESS     read-write
   STATUS     mandatory
   DESCRIPTION
     "The address attribute specifies the numbering plan and digits which 
      form a unique DNA identifier of the hunt group member. The 
      format of the address attribute is <numberingPlan>.<digits> where 
      numbering plan is x for X.121 and e for E.164. An example X.121 
      address is x.12345678."
::= { hgHgMProvEntry 1 }

hgHgMStateTable OBJECT-TYPE
   SYNTAX     SEQUENCE OF HgHgMStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { hgHgM 11 }

hgHgMStateEntry OBJECT-TYPE
   SYNTAX     HgHgMStateEntry
   ACCESS     not-accessible
   STATUS     mandatory
   DESCRIPTION
     "An entry in the hgHgMStateTable."
   INDEX {
      hgIndex,
      hgHgMIndex }
::= { hgHgMStateTable 1 }

HgHgMStateEntry ::= SEQUENCE {
   hgHgMAdminState
      INTEGER,
   hgHgMOperationalState
      INTEGER,
   hgHgMUsageState
      INTEGER }

hgHgMAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { hgHgMStateEntry 1 }

hgHgMOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { hgHgMStateEntry 2 }

hgHgMUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { hgHgMStateEntry 3 }

hgHgMOperationalTable OBJECT-TYPE
   SYNTAX     SEQUENCE OF HgHgMOperationalEntry
   ACCESS     not-accessible
   STATUS     mandatory
   DESCRIPTION
     "The Operational group defines operational attributes associated 
      with the HuntGroupMember component."
::= { hgHgM 12 }

hgHgMOperationalEntry OBJECT-TYPE
   SYNTAX     HgHgMOperationalEntry
   ACCESS     not-accessible
   STATUS     mandatory
   DESCRIPTION
     "An entry in the hgHgMOperationalTable."
   INDEX {
      hgIndex,
      hgHgMIndex }
::= { hgHgMOperationalTable 1 }

HgHgMOperationalEntry ::= SEQUENCE {
   hgHgMAvailability
      Unsigned32,
   hgHgMAvailabilityUpdates
      Counter32,
   hgHgMCallsRefused
      Counter32 }

hgHgMAvailability OBJECT-TYPE
   SYNTAX     Unsigned32 (0..4095)
   ACCESS     read-write
   STATUS     mandatory
   DESCRIPTION
     "This attribute indicates the current availability of the member.
      The higher the value, the more available the member is perceived to 
      be. A value of 0 indicates the member is unavailable.
      
      A member must be considered 'available' by the hunt group in 
      order to receive a call, regardless of the selection policy in use. The 
      hunt group members report whether or not they are available to 
      receive calls to the hunt group. Some services base their availability 
      on unused logical channels, others on bandwidth or memory 
      capacity.
      
      During initialization, the hunt group assumes all of its members are 
      equally available and sets their availability value to the maximum 
      of 4095. Similarly, a new hunt group member added to an existing 
      hunt group has its availability value initialized to 4095. This 
      ensures that members which have not reported their availability to 
      the hunt group are tried in order to trigger the member to report its 
      true availability.
      
      The availability of a member can change in the following ways:
      - Hunt group members can report their availability to the hunt group 
      using a DPRS availability packet.
      - A network operator can temporarily change the value by the Set 
      command. This change remains in effect until changed again by any 
      of these ways.
      - The hunt group resets a member's availability to the maximum of 
      4095 if it has been 0 for at least 2.5 hours. This ensures that 'lost' 
      availability information does not prevent a member from returning 
      to service."
   DEFVAL     { 4095 }
::= { hgHgMOperationalEntry 1 }

hgHgMAvailabilityUpdates OBJECT-TYPE
   SYNTAX     Counter32 
   ACCESS     read-only
   STATUS     mandatory
   DESCRIPTION
     "This attribute counts the number of availability update packets 
      received by the hunt group member. This counter wraps to 0 when it 
      exceeds its maximum value."
::= { hgHgMOperationalEntry 2 }

hgHgMCallsRefused OBJECT-TYPE
   SYNTAX     Counter32 
   ACCESS     read-only
   STATUS     mandatory
   DESCRIPTION
     "This attribute counts the number of call packets which were 
      returned to the hunt group by the member because it could not 
      connect the call. If this counter increments frequently, it could 
      indicate a problem with the member's reporting of its availability to 
      the hunt group or an incompatibility in the call options. This 
      counter wraps to 0 when it exceeds its maximum value."
::= { hgHgMOperationalEntry 3 }




-- 
-- Version and Compliance statements
-- 



-- Object-Group Statement:
-- A list of all current accessible leaf objects.

-- OBJECTS { hgHuntAttempts,
--           hgLogicalProcessor,
--           hgAdminState,
--           hgHgMCallsRefused,
--           hgOperationalState,
--           hgHgMAvailabilityUpdates,
--           hgHgMUsageState,
--           hgBadPackets,
--           hgRowStatus,
--           hgHgMComponentName,
--           hgCustomerIdentifier,
--           hgStorageType,
--           hgHgMStorageType,
--           hgHgMAddress,
--           hgInitialHuntAttempts,
--           hgAppendSuffixDigits,
--           hgSelectionPolicy,
--           hgHgMOperationalState,
--           hgHgMAvailability,
--           hgComponentName,
--           hgUsageState,
--           hgMaxAddrLenExceeded,
--           hgAvailabilityUpdates,
--           hgMaxHuntAttempts,
--           hgAddress,
--           hgHgMAdminState,
--           hgHgMRowStatus,
--           hgFailedCalls }
-- STATUS  mandatory
-- DESCRIPTION
--   "A list of all current accessible leaf objects."

huntGroupGroup OBJECT IDENTIFIER ::= { huntGroupMIB 1 }
huntGroupGroupBE OBJECT IDENTIFIER ::= { huntGroupGroup 5 }
huntGroupGroupBE01 OBJECT IDENTIFIER ::= { huntGroupGroupBE 2 }
huntGroupGroupBE01A OBJECT IDENTIFIER ::= { huntGroupGroupBE01 2 }



-- Agent-Capabilities Statement:

-- PRODUCT-RELEASE "Passport Release 7.0 HuntGroup."
-- STATUS          mandatory
-- DESCRIPTION     "HuntGroup MIB: MIB Version BE01A,
--                  Software Version BG00S4C."
-- SUPPORTS        Nortel-Magellan-Passport-HuntGroupMIB
--    INCLUDES     { huntGroupGroupBE01A }

huntGroupCapabilities OBJECT IDENTIFIER ::= { huntGroupMIB 3 }
huntGroupCapabilitiesBE OBJECT IDENTIFIER ::= { huntGroupCapabilities 5 }
huntGroupCapabilitiesBE01 OBJECT IDENTIFIER ::= { huntGroupCapabilitiesBE 2 }
huntGroupCapabilitiesBE01A OBJECT IDENTIFIER ::= { huntGroupCapabilitiesBE01 2 }





END
