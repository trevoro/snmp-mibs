Nortel-Magellan-Passport-FrameRelayEngMIB
DEFINITIONS ::= BEGIN



IMPORTS

      OBJECT-TYPE
   FROM RFC-1212

      passportMIBs
   FROM Nortel-Magellan-Passport-UsefulDefinitionsMIB

      DisplayString,
      StorageType,
      RowStatus,
      Gauge32,
      Unsigned32
   FROM Nortel-Magellan-Passport-StandardTextualConventionsMIB

      NonReplicated
   FROM Nortel-Magellan-Passport-TextualConventionsMIB

      lpIndex,
      lpEngIndex,
      lpEng
   FROM Nortel-Magellan-Passport-LogicalProcessorMIB;




-- LAST-UPDATED   "9808030000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     FrameRelayEng Enterprise MIB."

frameRelayEngMIB OBJECT IDENTIFIER ::= { passportMIBs 73 }










-- 
-- Lp Eng FrameRelaySystem
-- This component holds engineering parameters and statistics used by 
-- Frame Relay on this LP.

lpEngFrs OBJECT IDENTIFIER ::= { lpEng 3 }



lpEngFrsRowStatusTable OBJECT-TYPE
   SYNTAX     SEQUENCE OF LpEngFrsRowStatusEntry
   ACCESS     not-accessible
   STATUS     mandatory
   DESCRIPTION
     "This entry controls the addition and deletion of 
      lpEngFrs components."
::= { lpEngFrs 1 }

lpEngFrsRowStatusEntry OBJECT-TYPE
   SYNTAX     LpEngFrsRowStatusEntry
   ACCESS     not-accessible
   STATUS     mandatory
   DESCRIPTION
     "A single entry in the table represents a single 
      lpEngFrs component."
   INDEX {
      lpIndex,
      lpEngIndex,
      lpEngFrsIndex }
::= { lpEngFrsRowStatusTable 1 }

LpEngFrsRowStatusEntry ::= SEQUENCE {
   lpEngFrsRowStatus
      RowStatus,
   lpEngFrsComponentName
      DisplayString,
   lpEngFrsStorageType
      StorageType,
   lpEngFrsIndex
      NonReplicated }

lpEngFrsRowStatus OBJECT-TYPE
   SYNTAX     RowStatus 
   ACCESS     read-write
   STATUS     mandatory
   DESCRIPTION
     "This variable is used as the basis for SNMP naming of
      lpEngFrs components.
      These components can be added and deleted."
::= { lpEngFrsRowStatusEntry 1 }

lpEngFrsComponentName OBJECT-TYPE
   SYNTAX     DisplayString 
   ACCESS     read-only
   STATUS     mandatory
   DESCRIPTION
     "This variable provides the component's string name for
      use with the ASCII Console Interface"
::= { lpEngFrsRowStatusEntry 2 }

lpEngFrsStorageType OBJECT-TYPE
   SYNTAX     StorageType 
   ACCESS     read-only
   STATUS     mandatory
   DESCRIPTION
     "This variable represents the storage type value for the
      lpEngFrs tables."
::= { lpEngFrsRowStatusEntry 4 }

lpEngFrsIndex OBJECT-TYPE
   SYNTAX     NonReplicated 
   ACCESS     not-accessible
   STATUS     mandatory
   DESCRIPTION
     "This variable represents the index for the lpEngFrs tables."
::= { lpEngFrsRowStatusEntry 10 }

lpEngFrsOperTable OBJECT-TYPE
   SYNTAX     SEQUENCE OF LpEngFrsOperEntry
   ACCESS     not-accessible
   STATUS     mandatory
   DESCRIPTION
     "This group contains the Frame Relay default or current engineering 
      parameters and statistics for this LP."
::= { lpEngFrs 10 }

lpEngFrsOperEntry OBJECT-TYPE
   SYNTAX     LpEngFrsOperEntry
   ACCESS     not-accessible
   STATUS     mandatory
   DESCRIPTION
     "An entry in the lpEngFrsOperTable."
   INDEX {
      lpIndex,
      lpEngIndex,
      lpEngFrsIndex }
::= { lpEngFrsOperTable 1 }

LpEngFrsOperEntry ::= SEQUENCE {
   lpEngFrsMaxCalls
      Unsigned32,
   lpEngFrsHeadroomCalls
      Unsigned32,
   lpEngFrsCurrentCalls
      Gauge32,
   lpEngFrsCallsRefused
      Unsigned32 }

lpEngFrsMaxCalls OBJECT-TYPE
   SYNTAX     Unsigned32 (0..1000000)
   ACCESS     read-only
   STATUS     mandatory
   DESCRIPTION
     "This attribute indicates the maximum number of Frame Relay (FR) 
      calls of any type (PVC, SPVC, or SVC) which can be 
      simultaneously 'current' on the LP. Note that 'current' doesn't 
      necessarily mean that the call is in data transfer. It minimally means 
      that such a call can subsequently generate accounting records. 
      When the value of currentCalls reaches the value of maxCalls for 
      FR on this LP, subsequent call attempts are rejected by the FR 
      service."
   DEFVAL     { 1000000 }
::= { lpEngFrsOperEntry 1 }

lpEngFrsHeadroomCalls OBJECT-TYPE
   SYNTAX     Unsigned32 (0..1000000)
   ACCESS     read-only
   STATUS     mandatory
   DESCRIPTION
     "This attribute indicates a number which allows a network engineer 
      to do some statistical multiplexing for admitting calls when certain 
      overload conditions are reached. For setting this, refer to the 
      Engineering Guidelines. It depends on conditions such as the 
      expected sustained SVC call setup/clear rates and how conservative 
      one wants to be in certain 'error' conditions where many calls are 
      cleared simultaneously."
   DEFVAL     { 1000000 }
::= { lpEngFrsOperEntry 2 }

lpEngFrsCurrentCalls OBJECT-TYPE
   SYNTAX     Gauge32 (0..4294967295)
   ACCESS     read-only
   STATUS     mandatory
   DESCRIPTION
     "This attribute counts the total number of Frame Relay calls (initially 
      just FrUni and FrNni) which are 'current'. Note that 'current' 
      doesn't necessarily mean that the call is in data transfer. It 
      minimally means that such a call can subsequently generate 
      accounting records."
::= { lpEngFrsOperEntry 3 }

lpEngFrsCallsRefused OBJECT-TYPE
   SYNTAX     Unsigned32 (0..4294967295)
   ACCESS     read-only
   STATUS     mandatory
   DESCRIPTION
     "This attribute counts the total number of call connections (including 
      calls from the link as well as calls from the subnet) that have been 
      refused because currentCalls has reached the limits, as specified by 
      the engineering formulas for Frs on this LP."
::= { lpEngFrsOperEntry 4 }


-- 
-- Lp Eng Frs Override
-- This component holds provisionable engineering parameters used 
-- by Frame Relay on this LP.

lpEngFrsOv OBJECT IDENTIFIER ::= { lpEngFrs 2 }



lpEngFrsOvRowStatusTable OBJECT-TYPE
   SYNTAX     SEQUENCE OF LpEngFrsOvRowStatusEntry
   ACCESS     not-accessible
   STATUS     mandatory
   DESCRIPTION
     "This entry controls the addition and deletion of 
      lpEngFrsOv components."
::= { lpEngFrsOv 1 }

lpEngFrsOvRowStatusEntry OBJECT-TYPE
   SYNTAX     LpEngFrsOvRowStatusEntry
   ACCESS     not-accessible
   STATUS     mandatory
   DESCRIPTION
     "A single entry in the table represents a single 
      lpEngFrsOv component."
   INDEX {
      lpIndex,
      lpEngIndex,
      lpEngFrsIndex,
      lpEngFrsOvIndex }
::= { lpEngFrsOvRowStatusTable 1 }

LpEngFrsOvRowStatusEntry ::= SEQUENCE {
   lpEngFrsOvRowStatus
      RowStatus,
   lpEngFrsOvComponentName
      DisplayString,
   lpEngFrsOvStorageType
      StorageType,
   lpEngFrsOvIndex
      NonReplicated }

lpEngFrsOvRowStatus OBJECT-TYPE
   SYNTAX     RowStatus 
   ACCESS     read-write
   STATUS     mandatory
   DESCRIPTION
     "This variable is used as the basis for SNMP naming of
      lpEngFrsOv components.
      These components can be added and deleted."
::= { lpEngFrsOvRowStatusEntry 1 }

lpEngFrsOvComponentName OBJECT-TYPE
   SYNTAX     DisplayString 
   ACCESS     read-only
   STATUS     mandatory
   DESCRIPTION
     "This variable provides the component's string name for
      use with the ASCII Console Interface"
::= { lpEngFrsOvRowStatusEntry 2 }

lpEngFrsOvStorageType OBJECT-TYPE
   SYNTAX     StorageType 
   ACCESS     read-only
   STATUS     mandatory
   DESCRIPTION
     "This variable represents the storage type value for the
      lpEngFrsOv tables."
::= { lpEngFrsOvRowStatusEntry 4 }

lpEngFrsOvIndex OBJECT-TYPE
   SYNTAX     NonReplicated 
   ACCESS     not-accessible
   STATUS     mandatory
   DESCRIPTION
     "This variable represents the index for the lpEngFrsOv tables."
::= { lpEngFrsOvRowStatusEntry 10 }

lpEngFrsOvProvTable OBJECT-TYPE
   SYNTAX     SEQUENCE OF LpEngFrsOvProvEntry
   ACCESS     not-accessible
   STATUS     mandatory
   DESCRIPTION
     "This group contains the Frame Relay provisionable engineering 
      parameters for this LP.
      DESCRIPTION"
::= { lpEngFrsOv 10 }

lpEngFrsOvProvEntry OBJECT-TYPE
   SYNTAX     LpEngFrsOvProvEntry
   ACCESS     not-accessible
   STATUS     mandatory
   DESCRIPTION
     "An entry in the lpEngFrsOvProvTable."
   INDEX {
      lpIndex,
      lpEngIndex,
      lpEngFrsIndex,
      lpEngFrsOvIndex }
::= { lpEngFrsOvProvTable 1 }

LpEngFrsOvProvEntry ::= SEQUENCE {
   lpEngFrsOvMaxCalls
      Unsigned32,
   lpEngFrsOvHeadroomCalls
      Unsigned32 }

lpEngFrsOvMaxCalls OBJECT-TYPE
   SYNTAX     Unsigned32 (0..1000000)
   ACCESS     read-write
   STATUS     mandatory
   DESCRIPTION
     "This attribute specifies the maximum number of Frame Relay calls 
      of any type (PVC, SPVC, or SVC) which can be simultaneously 
      'current' on this LP. Note that 'current' doesn't necessarily mean 
      that the call is in data transfer. It minimally means that such a call 
      can subsequently generate accounting records. When the value of 
      currentCalls reaches the value of maxCalls for FR on this LP, 
      subsequent call attempts are rejected by the FR services."
   DEFVAL     { 1000000 }
::= { lpEngFrsOvProvEntry 1 }

lpEngFrsOvHeadroomCalls OBJECT-TYPE
   SYNTAX     Unsigned32 (0..1000000)
   ACCESS     read-write
   STATUS     mandatory
   DESCRIPTION
     "This attribute specifies a number which allows a network engineer 
      to do some statistical multiplexing for admitting calls when certain 
      overload conditions are reached. For setting this, refer to the 
      Engineering Guidelines. It depends on conditions such as the 
      expected sustained SVC call setup/clear rates and how conservative 
      one wants to be in certain 'error' conditions where many calls are 
      cleared simultaneously."
   DEFVAL     { 1000000 }
::= { lpEngFrsOvProvEntry 2 }




-- 
-- Version and Compliance statements
-- 



-- Object-Group Statement:
-- A list of all current accessible leaf objects.

-- OBJECTS { lpEngFrsOvStorageType,
--           lpEngFrsCallsRefused,
--           lpEngFrsComponentName,
--           lpEngFrsOvComponentName,
--           lpEngFrsHeadroomCalls,
--           lpEngFrsOvHeadroomCalls,
--           lpEngFrsCurrentCalls,
--           lpEngFrsStorageType,
--           lpEngFrsRowStatus,
--           lpEngFrsOvRowStatus,
--           lpEngFrsMaxCalls,
--           lpEngFrsOvMaxCalls }
-- STATUS  mandatory
-- DESCRIPTION
--   "A list of all current accessible leaf objects."

frameRelayEngGroup OBJECT IDENTIFIER ::= { frameRelayEngMIB 1 }
frameRelayEngGroupBE OBJECT IDENTIFIER ::= { frameRelayEngGroup 5 }
frameRelayEngGroupBE00 OBJECT IDENTIFIER ::= { frameRelayEngGroupBE 1 }
frameRelayEngGroupBE00A OBJECT IDENTIFIER ::= { frameRelayEngGroupBE00 2 }



-- Agent-Capabilities Statement:

-- PRODUCT-RELEASE "Passport Release 7.0 FrameRelayEng."
-- STATUS          mandatory
-- DESCRIPTION     "FrameRelayEng MIB: MIB Version BE00A,
--                  Software Version BG00S4C."
-- SUPPORTS        Nortel-Magellan-Passport-FrameRelayEngMIB
--    INCLUDES     { frameRelayEngGroupBE00A }

frameRelayEngCapabilities OBJECT IDENTIFIER ::= { frameRelayEngMIB 3 }
frameRelayEngCapabilitiesBE OBJECT IDENTIFIER ::= { frameRelayEngCapabilities 5 }
frameRelayEngCapabilitiesBE00 OBJECT IDENTIFIER ::= { frameRelayEngCapabilitiesBE 1 }
frameRelayEngCapabilitiesBE00A OBJECT IDENTIFIER ::= { frameRelayEngCapabilitiesBE00 2 }





END
