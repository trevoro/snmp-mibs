Nortel-MsCarrier-MscPassport-VoiceNetworkingMIB
DEFINITIONS ::= BEGIN



IMPORTS

      OBJECT-TYPE
   FROM RFC-1212

      mscPassportMIBs,
      mscComponents
   FROM Nortel-MsCarrier-MscPassport-UsefulDefinitionsMIB

      Counter32,
      RowPointer,
      DisplayString,
      StorageType,
      RowStatus,
      InterfaceIndex,
      Gauge32,
      Integer32,
      Unsigned32
   FROM Nortel-MsCarrier-MscPassport-StandardTextualConventionsMIB

      AsciiString,
      Hex,
      NonReplicated,
      DigitString,
      EnterpriseDateAndTime,
      PassportCounter64,
      Link
   FROM Nortel-MsCarrier-MscPassport-TextualConventionsMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     VoiceNetworking Enterprise MIB."

voiceNetworkingMIB OBJECT IDENTIFIER ::= { mscPassportMIBs 109 }










-- SigChan/n		
-- The SigChan component defines the signalling characteristics of the 
-- connection to the external equipment. 

mscSigChan OBJECT IDENTIFIER ::= { mscComponents 115 }



mscSigChanRowStatusTable OBJECT-TYPE
   SYNTAX     SEQUENCE OF MscSigChanRowStatusEntry
   ACCESS     not-accessible
   STATUS     mandatory
   DESCRIPTION
     "This entry controls the addition and deletion of 
      mscSigChan components."
::= { mscSigChan 1 }

mscSigChanRowStatusEntry OBJECT-TYPE
   SYNTAX     MscSigChanRowStatusEntry
   ACCESS     not-accessible
   STATUS     mandatory
   DESCRIPTION
     "A single entry in the table represents a single 
      mscSigChan component."
   INDEX {
      mscSigChanIndex }
::= { mscSigChanRowStatusTable 1 }

MscSigChanRowStatusEntry ::= SEQUENCE {
   mscSigChanRowStatus
      RowStatus,
   mscSigChanComponentName
      DisplayString,
   mscSigChanStorageType
      StorageType,
   mscSigChanIndex
      Integer32 }

mscSigChanRowStatus OBJECT-TYPE
   SYNTAX     RowStatus 
   ACCESS     read-write
   STATUS     mandatory
   DESCRIPTION
     "This variable is used as the basis for SNMP naming of
      mscSigChan components.
      These components can be added and deleted."
::= { mscSigChanRowStatusEntry 1 }

mscSigChanComponentName OBJECT-TYPE
   SYNTAX     DisplayString 
   ACCESS     read-only
   STATUS     mandatory
   DESCRIPTION
     "This variable provides the component's string name for
      use with the ASCII Console Interface"
::= { mscSigChanRowStatusEntry 2 }

mscSigChanStorageType OBJECT-TYPE
   SYNTAX     StorageType 
   ACCESS     read-only
   STATUS     mandatory
   DESCRIPTION
     "This variable represents the storage type value for the
      mscSigChan tables."
::= { mscSigChanRowStatusEntry 4 }

mscSigChanIndex OBJECT-TYPE
   SYNTAX     Integer32 (1..16)
   ACCESS     not-accessible
   STATUS     mandatory
   DESCRIPTION
     "This variable represents the index for the mscSigChan tables."
::= { mscSigChanRowStatusEntry 10 }

mscSigChanCidDataTable OBJECT-TYPE
   SYNTAX     SEQUENCE OF MscSigChanCidDataEntry
   ACCESS     not-accessible
   STATUS     mandatory
   DESCRIPTION
     "This group contains the attribute for a component's Customer 
      Identifier (CID). Refer to the attribute description for a detailed 
      explanation of CIDs."
::= { mscSigChan 100 }

mscSigChanCidDataEntry OBJECT-TYPE
   SYNTAX     MscSigChanCidDataEntry
   ACCESS     not-accessible
   STATUS     mandatory
   DESCRIPTION
     "An entry in the mscSigChanCidDataTable."
   INDEX {
      mscSigChanIndex }
::= { mscSigChanCidDataTable 1 }

MscSigChanCidDataEntry ::= SEQUENCE {
   mscSigChanCustomerIdentifier
      Unsigned32 }

mscSigChanCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { mscSigChanCidDataEntry 1 }

mscSigChanIfEntryTable OBJECT-TYPE
   SYNTAX     SEQUENCE OF MscSigChanIfEntryEntry
   ACCESS     not-accessible
   STATUS     mandatory
   DESCRIPTION
     "This group contains the provisionable attributes for the ifEntry."
::= { mscSigChan 101 }

mscSigChanIfEntryEntry OBJECT-TYPE
   SYNTAX     MscSigChanIfEntryEntry
   ACCESS     not-accessible
   STATUS     mandatory
   DESCRIPTION
     "An entry in the mscSigChanIfEntryTable."
   INDEX {
      mscSigChanIndex }
::= { mscSigChanIfEntryTable 1 }

MscSigChanIfEntryEntry ::= SEQUENCE {
   mscSigChanIfAdminStatus
      INTEGER,
   mscSigChanIfIndex
      InterfaceIndex }

mscSigChanIfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { mscSigChanIfEntryEntry 1 }

mscSigChanIfIndex OBJECT-TYPE
   SYNTAX     InterfaceIndex (1..65535)
   ACCESS     read-only
   STATUS     mandatory
   DESCRIPTION
     "This is the index for the IfEntry. Its value is automatically initialized 
      during the provisioning process."
::= { mscSigChanIfEntryEntry 2 }

mscSigChanOperStatusTable OBJECT-TYPE
   SYNTAX     SEQUENCE OF MscSigChanOperStatusEntry
   ACCESS     not-accessible
   STATUS     mandatory
   DESCRIPTION
     "This group includes the Operational Status attribute. This attribute 
      defines the current operational state of this component."
::= { mscSigChan 102 }

mscSigChanOperStatusEntry OBJECT-TYPE
   SYNTAX     MscSigChanOperStatusEntry
   ACCESS     not-accessible
   STATUS     mandatory
   DESCRIPTION
     "An entry in the mscSigChanOperStatusTable."
   INDEX {
      mscSigChanIndex }
::= { mscSigChanOperStatusTable 1 }

MscSigChanOperStatusEntry ::= SEQUENCE {
   mscSigChanSnmpOperStatus
      INTEGER }

mscSigChanSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { mscSigChanOperStatusEntry 1 }

mscSigChanStateTable OBJECT-TYPE
   SYNTAX     SEQUENCE OF MscSigChanStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscSigChan 103 }

mscSigChanStateEntry OBJECT-TYPE
   SYNTAX     MscSigChanStateEntry
   ACCESS     not-accessible
   STATUS     mandatory
   DESCRIPTION
     "An entry in the mscSigChanStateTable."
   INDEX {
      mscSigChanIndex }
::= { mscSigChanStateTable 1 }

MscSigChanStateEntry ::= SEQUENCE {
   mscSigChanAdminState
      INTEGER,
   mscSigChanOperationalState
      INTEGER,
   mscSigChanUsageState
      INTEGER }

mscSigChanAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscSigChanStateEntry 1 }

mscSigChanOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscSigChanStateEntry 2 }

mscSigChanUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscSigChanStateEntry 3 }

mscSigChanProvTable OBJECT-TYPE
   SYNTAX     SEQUENCE OF MscSigChanProvEntry
   ACCESS     not-accessible
   STATUS     mandatory
   DESCRIPTION
     "This group represents the provisionable attributes of a SigChan."
::= { mscSigChan 104 }

mscSigChanProvEntry OBJECT-TYPE
   SYNTAX     MscSigChanProvEntry
   ACCESS     not-accessible
   STATUS     mandatory
   DESCRIPTION
     "An entry in the mscSigChanProvTable."
   INDEX {
      mscSigChanIndex }
::= { mscSigChanProvTable 1 }

MscSigChanProvEntry ::= SEQUENCE {
   mscSigChanCommentText
      AsciiString,
   mscSigChanOctothorpeEod
      INTEGER,
   mscSigChanForceNpiTon
      INTEGER,
   mscSigChanDefaultNpiTon
      INTEGER }

mscSigChanCommentText OBJECT-TYPE
   SYNTAX     AsciiString (SIZE (0..40))
   ACCESS     read-write
   STATUS     mandatory
   DESCRIPTION
     "Use of this attribute is at the discretion of the system administrator. 
      Typically, this attribute specifies the name of the customer that is 
      using this SigChan."
::= { mscSigChanProvEntry 1 }

mscSigChanOctothorpeEod OBJECT-TYPE
   SYNTAX     INTEGER  {
                 yes(0),
                 no(1) }
   ACCESS     read-write
   STATUS     mandatory
   DESCRIPTION
     "This attribute specifies whether the octothorpe should be used as an 
      end of dialling indication. When this character is received, only the 
      digits that have been received to that point will be used for address 
      resolution. All subsequent digits will be forwarded to the far-end, 
      but they will not be used. 
      The octothorpe will not be sent to the far-end."
   DEFVAL     { no }
::= { mscSigChanProvEntry 2 }

mscSigChanForceNpiTon OBJECT-TYPE
   SYNTAX     INTEGER  {
                 yes(0),
                 no(1) }
   ACCESS     read-write
   STATUS     mandatory
   DESCRIPTION
     "This attribute, together with the defaultNpiTon attribute, controls 
      Numbering Plan Identifier (NPI) and Type Of Number (TON) 
      values to be used by the SigChan component for egress calls (if 
      applicable).
      If set to yes, NPI and TON values defined by the defaultNpiTon 
      attribute unconditionally overwrite values received in the call setup 
      message from the subnet."
   DEFVAL     { no }
::= { mscSigChanProvEntry 3 }

mscSigChanDefaultNpiTon OBJECT-TYPE
   SYNTAX     INTEGER  {
                 unknown(0),
                 international(1),
                 national(2),
                 subscriber(3),
                 p0(4),
                 p1(5),
                 p2(6),
                 p3(7),
                 p4(8),
                 p5(9),
                 p6(10),
                 p7(11),
                 casUnknown(12) }
   ACCESS     read-write
   STATUS     mandatory
   DESCRIPTION
     "This attribute, together with the forceNpiTon attribute, controls 
      Numbering Plan Identifier (NPI) and Type Of Number (TON) 
      values to be used by the SigChan component for egress calls (if 
      applicable).
      The combination of NPI and TON values defined by the 
      defaultNpiTon attribute is used for an egress call whenever:
      - the call setup message received from subnet indicates that NPI or 
      TON information is not supplied or doesn't make sense, or
      - attribute forceNpiTon is set to yes
      Mapping between values of the defaultNpiTon attribute and 
      associated combinations of NPI and TON values follows:
      casUnknown: NPI=unknown (0) TON=unknown (0)
      unknown: NPI=E.164 (1) TON=unknown (0)
      international: NPI=E.164 (1) TON=international (1)
      national: NPI=E.164 (1) TON=national (2)
      subscriber: NPI=E.164 (1) TON=subscriber (4)
      p0: NPI=private(9) TON=0
      p1: NPI=private(9) TON=1
      p2: NPI=private(9) TON=2
      p3: NPI=private(9) TON=3
      p4: NPI=private(9) TON=4
      p5: NPI=private(9) TON=5
      p6: NPI=private(9) TON=6
      p7: NPI=private(9) TON=7"
   DEFVAL     { casUnknown }
::= { mscSigChanProvEntry 4 }

mscSigChanSubroutesTable OBJECT-TYPE
   SYNTAX     SEQUENCE OF MscSigChanSubroutesEntry
   ACCESS     not-accessible
   STATUS     mandatory
   DESCRIPTION
     "This attribute identifies all of the VoiceSubroutes which are 
      associated with this signalling channel."
::= { mscSigChan 307 }

mscSigChanSubroutesEntry OBJECT-TYPE
   SYNTAX     MscSigChanSubroutesEntry
   ACCESS     not-accessible
   STATUS     mandatory
   DESCRIPTION
     "An entry in the mscSigChanSubroutesTable."
   INDEX {
      mscSigChanIndex,
      mscSigChanSubroutesValue }
::= { mscSigChanSubroutesTable 1 }

MscSigChanSubroutesEntry ::= SEQUENCE {
   mscSigChanSubroutesValue
      Link,
   mscSigChanSubroutesRowStatus
      RowStatus }

mscSigChanSubroutesValue OBJECT-TYPE
   SYNTAX     Link 
   ACCESS     read-write
   STATUS     mandatory
   DESCRIPTION
     "This variable represents both the value and the index for the
      mscSigChanSubroutesTable."
::= { mscSigChanSubroutesEntry 1 }

mscSigChanSubroutesRowStatus OBJECT-TYPE
   SYNTAX     RowStatus 
   ACCESS     write-only
   STATUS     mandatory
   DESCRIPTION
     "This variable is used to control the addition and deletion 
      of individual values of the mscSigChanSubroutesTable."
::= { mscSigChanSubroutesEntry 2 }

mscSigChanDegradedSubroutesTable OBJECT-TYPE
   SYNTAX     SEQUENCE OF MscSigChanDegradedSubroutesEntry
   ACCESS     not-accessible
   STATUS     mandatory
   DESCRIPTION
     "This attribute lists all of the VoiceSubroute components that do not 
      have all of their SwitchedVoiceService subcomponents available for 
      use."
::= { mscSigChan 308 }

mscSigChanDegradedSubroutesEntry OBJECT-TYPE
   SYNTAX     MscSigChanDegradedSubroutesEntry
   ACCESS     not-accessible
   STATUS     mandatory
   DESCRIPTION
     "An entry in the mscSigChanDegradedSubroutesTable."
   INDEX {
      mscSigChanIndex,
      mscSigChanDegradedSubroutesValue }
::= { mscSigChanDegradedSubroutesTable 1 }

MscSigChanDegradedSubroutesEntry ::= SEQUENCE {
   mscSigChanDegradedSubroutesValue
      RowPointer }

mscSigChanDegradedSubroutesValue OBJECT-TYPE
   SYNTAX     RowPointer 
   ACCESS     read-only
   STATUS     mandatory
   DESCRIPTION
     "This variable represents both the value and the index for the
      mscSigChanDegradedSubroutesTable."
::= { mscSigChanDegradedSubroutesEntry 1 }

-- 
-- *** THIS SUBTREE CURRENTLY NOT IMPLEMENTED ***
-- 

-- SigChan/n Bchannel/n
-- This component contains operational attributes of an individual 
-- B-channel serviced by the SigChan component. The Bchannel 
-- component instance value reflects the external (protocol specific) 
-- channel number. In nB+D configurations, channel number also 
-- reflects the related interface:
-- Bchannel/1-xx - primary interface,
-- Bchannel/101-1xx - secondary interface,
-- Bchannel/201-2xx - tertiary interface,
-- Bchannel/301-3xx - quaternary interface

mscSigChanBch OBJECT IDENTIFIER ::= { mscSigChan 7 }



mscSigChanBchRowStatusTable OBJECT-TYPE
   SYNTAX     SEQUENCE OF MscSigChanBchRowStatusEntry
   ACCESS     not-accessible
   STATUS     mandatory
   DESCRIPTION
     "*** THIS TABLE CURRENTLY NOT IMPLEMENTED ***

      This entry controls the addition and deletion of 
      mscSigChanBch components."
::= { mscSigChanBch 1 }

mscSigChanBchRowStatusEntry OBJECT-TYPE
   SYNTAX     MscSigChanBchRowStatusEntry
   ACCESS     not-accessible
   STATUS     mandatory
   DESCRIPTION
     "A single entry in the table represents a single 
      mscSigChanBch component."
   INDEX {
      mscSigChanIndex,
      mscSigChanBchIndex }
::= { mscSigChanBchRowStatusTable 1 }

MscSigChanBchRowStatusEntry ::= SEQUENCE {
   mscSigChanBchRowStatus
      RowStatus,
   mscSigChanBchComponentName
      DisplayString,
   mscSigChanBchStorageType
      StorageType,
   mscSigChanBchIndex
      Integer32 }

mscSigChanBchRowStatus OBJECT-TYPE
   SYNTAX     RowStatus 
   ACCESS     read-only
   STATUS     mandatory
   DESCRIPTION
     "This variable is used as the basis for SNMP naming of
      mscSigChanBch components.
      These components cannot be added nor deleted."
::= { mscSigChanBchRowStatusEntry 1 }

mscSigChanBchComponentName OBJECT-TYPE
   SYNTAX     DisplayString 
   ACCESS     read-only
   STATUS     mandatory
   DESCRIPTION
     "This variable provides the component's string name for
      use with the ASCII Console Interface"
::= { mscSigChanBchRowStatusEntry 2 }

mscSigChanBchStorageType OBJECT-TYPE
   SYNTAX     StorageType 
   ACCESS     read-only
   STATUS     mandatory
   DESCRIPTION
     "This variable represents the storage type value for the
      mscSigChanBch tables."
::= { mscSigChanBchRowStatusEntry 4 }

mscSigChanBchIndex OBJECT-TYPE
   SYNTAX     Integer32 (1..331)
   ACCESS     not-accessible
   STATUS     mandatory
   DESCRIPTION
     "This variable represents the index for the mscSigChanBch tables."
::= { mscSigChanBchRowStatusEntry 10 }

mscSigChanBchOperTable OBJECT-TYPE
   SYNTAX     SEQUENCE OF MscSigChanBchOperEntry
   ACCESS     not-accessible
   STATUS     mandatory
   DESCRIPTION
     "*** THIS TABLE CURRENTLY NOT IMPLEMENTED ***

      This group contains various operational attributes of a B-channel 
      serviced by a Signalling Channel."
::= { mscSigChanBch 4 }

mscSigChanBchOperEntry OBJECT-TYPE
   SYNTAX     MscSigChanBchOperEntry
   ACCESS     not-accessible
   STATUS     mandatory
   DESCRIPTION
     "An entry in the mscSigChanBchOperTable."
   INDEX {
      mscSigChanIndex,
      mscSigChanBchIndex }
::= { mscSigChanBchOperTable 1 }

MscSigChanBchOperEntry ::= SEQUENCE {
   mscSigChanBchStatus
      INTEGER,
   mscSigChanBchTimeSlot
      Unsigned32,
   mscSigChanBchVsrInstance
      Unsigned32,
   mscSigChanBchCalledDirectoryNumber
      DigitString }

mscSigChanBchStatus OBJECT-TYPE
   SYNTAX     INTEGER  {
                 unknown(0),
                 maintB(1),
                 idle(2),
                 busy(3),
                 ingress(4),
                 egress(5),
                 idleMaintenance(6),
                 ingressMaintenance(7),
                 egressMaintenance(8),
                 outOfService(9) }
   ACCESS     read-only
   STATUS     mandatory
   DESCRIPTION
     "This attribute indicates what is current internal B-channel state.
      The attribute may have the following values for any supported 
      access signalling protocol on Passport: 
      unknown, the B-channel has not registered yet for SigChan services
      maintB, the B-channel is undergoing a maintenance action
      idle, the B-channel is available for ingress/egress calls
      busy, the B-channel is currently being used for an ingress or egress 
      call
      ingress, the B-channel is currently being used for an ingress call 
      (from the external network to the subnet)
      egress, the B-channel is currently being used for an egress call 
      (from the subnet to the external network)
      
      In addition, CCS protocols supporting SERVICE messaging may 
      also use the following values:
      idleMaintenance, the B-channel received a SERVICE message 
      placing the channel in maintenance, and no calls are active on the 
      channel
      ingressMaintenance, the B-channel received a SERVICE message 
      placing the channel in maintenance, and an incoming call is active 
      on the channel
      egressMaintenance, the B-channel received a SERVICE message 
      placing the channel in maintenance, and an outgoing call is active 
      on the channel
      outOfService, a SERVICE message to or from the PBX has placed 
      the channel out of service"
   DEFVAL     { unknown }
::= { mscSigChanBchOperEntry 1 }

mscSigChanBchTimeSlot OBJECT-TYPE
   SYNTAX     Unsigned32 (0..100)
   ACCESS     read-only
   STATUS     mandatory
   DESCRIPTION
     "This attribute indicates which timeslot the B-channel uses."
   DEFVAL     { 0 }
::= { mscSigChanBchOperEntry 2 }

mscSigChanBchVsrInstance OBJECT-TYPE
   SYNTAX     Unsigned32 (0..255)
   ACCESS     read-only
   STATUS     mandatory
   DESCRIPTION
     "This attribute indicates the component instance of the 
      VoiceSubroute to which the B-channel belongs."
   DEFVAL     { 0 }
::= { mscSigChanBchOperEntry 3 }

mscSigChanBchCalledDirectoryNumber OBJECT-TYPE
   SYNTAX     DigitString (SIZE (1..32))
   ACCESS     read-only
   STATUS     mandatory
   DESCRIPTION
     "This attribute indicates the dialled number for the currently active 
      call on this B-channel."
::= { mscSigChanBchOperEntry 4 }


-- SigChan/n Gateway
-- This component contains operational attributes which describe 
-- gateway capabilities of the SigChan component as well as the basic 
-- statistics related to calls requiring signalling protocol conversion.

mscSigChanGw OBJECT IDENTIFIER ::= { mscSigChan 15 }



mscSigChanGwRowStatusTable OBJECT-TYPE
   SYNTAX     SEQUENCE OF MscSigChanGwRowStatusEntry
   ACCESS     not-accessible
   STATUS     mandatory
   DESCRIPTION
     "This entry controls the addition and deletion of 
      mscSigChanGw components."
::= { mscSigChanGw 1 }

mscSigChanGwRowStatusEntry OBJECT-TYPE
   SYNTAX     MscSigChanGwRowStatusEntry
   ACCESS     not-accessible
   STATUS     mandatory
   DESCRIPTION
     "A single entry in the table represents a single 
      mscSigChanGw component."
   INDEX {
      mscSigChanIndex,
      mscSigChanGwIndex }
::= { mscSigChanGwRowStatusTable 1 }

MscSigChanGwRowStatusEntry ::= SEQUENCE {
   mscSigChanGwRowStatus
      RowStatus,
   mscSigChanGwComponentName
      DisplayString,
   mscSigChanGwStorageType
      StorageType,
   mscSigChanGwIndex
      NonReplicated }

mscSigChanGwRowStatus OBJECT-TYPE
   SYNTAX     RowStatus 
   ACCESS     read-only
   STATUS     mandatory
   DESCRIPTION
     "This variable is used as the basis for SNMP naming of
      mscSigChanGw components.
      These components cannot be added nor deleted."
::= { mscSigChanGwRowStatusEntry 1 }

mscSigChanGwComponentName OBJECT-TYPE
   SYNTAX     DisplayString 
   ACCESS     read-only
   STATUS     mandatory
   DESCRIPTION
     "This variable provides the component's string name for
      use with the ASCII Console Interface"
::= { mscSigChanGwRowStatusEntry 2 }

mscSigChanGwStorageType OBJECT-TYPE
   SYNTAX     StorageType 
   ACCESS     read-only
   STATUS     mandatory
   DESCRIPTION
     "This variable represents the storage type value for the
      mscSigChanGw tables."
::= { mscSigChanGwRowStatusEntry 4 }

mscSigChanGwIndex OBJECT-TYPE
   SYNTAX     NonReplicated 
   ACCESS     not-accessible
   STATUS     mandatory
   DESCRIPTION
     "This variable represents the index for the mscSigChanGw tables."
::= { mscSigChanGwRowStatusEntry 10 }

mscSigChanGwStatsTable OBJECT-TYPE
   SYNTAX     SEQUENCE OF MscSigChanGwStatsEntry
   ACCESS     not-accessible
   STATUS     mandatory
   DESCRIPTION
     "This group provides signalling gateway related statistical attributes 
      for the SigChan component."
::= { mscSigChanGw 101 }

mscSigChanGwStatsEntry OBJECT-TYPE
   SYNTAX     MscSigChanGwStatsEntry
   ACCESS     not-accessible
   STATUS     mandatory
   DESCRIPTION
     "An entry in the mscSigChanGwStatsTable."
   INDEX {
      mscSigChanIndex,
      mscSigChanGwIndex }
::= { mscSigChanGwStatsTable 1 }

MscSigChanGwStatsEntry ::= SEQUENCE {
   mscSigChanGwRequiredConversions
      Counter32,
   mscSigChanGwUnsupportedConversions
      Counter32 }

mscSigChanGwRequiredConversions OBJECT-TYPE
   SYNTAX     Counter32 
   ACCESS     read-only
   STATUS     mandatory
   DESCRIPTION
     "This attribute counts the total number of calls that have been made 
      from the subnet to the interface (that is external equipment, for 
      example a PBX) which needed signalling protocol conversion. The 
      value wraps to zero when it exceeds its maximum. The count 
      includes both, supported and unsupported conversions."
::= { mscSigChanGwStatsEntry 1 }

mscSigChanGwUnsupportedConversions OBJECT-TYPE
   SYNTAX     Counter32 
   ACCESS     read-only
   STATUS     mandatory
   DESCRIPTION
     "This attribute counts the total number of calls that have been made 
      from the subnet to the interface (that is external equipment, for 
      example a PBX) which needed signalling protocol conversion but 
      were rejected since the requested conversion was not supported. 
      The value wraps to zero when it exceeds its maximum."
::= { mscSigChanGwStatsEntry 2 }

mscSigChanGwGwcTable OBJECT-TYPE
   SYNTAX     SEQUENCE OF MscSigChanGwGwcEntry
   ACCESS     not-accessible
   STATUS     obsolete
   DESCRIPTION
     "This attribute has been migrated to gatewayCapability."
::= { mscSigChanGw 301 }

mscSigChanGwGwcEntry OBJECT-TYPE
   SYNTAX     MscSigChanGwGwcEntry
   ACCESS     not-accessible
   STATUS     obsolete
   DESCRIPTION
     "An entry in the mscSigChanGwGwcTable."
   INDEX {
      mscSigChanIndex,
      mscSigChanGwIndex,
      mscSigChanGwGwcIndex }
::= { mscSigChanGwGwcTable 1 }

MscSigChanGwGwcEntry ::= SEQUENCE {
   mscSigChanGwGwcIndex
      INTEGER,
   mscSigChanGwGwcValue
      INTEGER }

mscSigChanGwGwcIndex OBJECT-TYPE
   SYNTAX     INTEGER  {
                 etsiQsigPG(0),
                 nisPG(1),
                 analogAndCasPG(2),
                 euroIsdnPG(3),
                 mcdnPG(4),
                 mcdnUniPG(5) }
   ACCESS     not-accessible
   STATUS     obsolete
   DESCRIPTION
     "This variable represents the mscSigChanGwGwcTable
      specific index for the mscSigChanGwGwcTable."
::= { mscSigChanGwGwcEntry 1 }

mscSigChanGwGwcValue OBJECT-TYPE
   SYNTAX     INTEGER  {
                 noGw(0),
                 singleEndedGw(1),
                 doubleEndedGw(2),
                 singleOrDoubleEndedGw(3),
                 nativePG(4) }
   ACCESS     read-only
   STATUS     obsolete
   DESCRIPTION
     "This variable represents an individual value for the
      mscSigChanGwGwcTable."
::= { mscSigChanGwGwcEntry 2 }

mscSigChanGwGatewayCapTable OBJECT-TYPE
   SYNTAX     SEQUENCE OF MscSigChanGwGatewayCapEntry
   ACCESS     not-accessible
   STATUS     mandatory
   DESCRIPTION
     "This attribute indicates the SigChan component's capability to 
      convert from one access signalling type to another. Access 
      signalling protocols (protocols between a Passport and external 
      switching equipment, for example a PBX) are grouped into protocol 
      groups. Protocols within the same protocol group are considered 
      completely compatible. This means that no extra processing is 
      needed when a call originates from an ingress link using protocol A 
      and terminates on an egress link using protocol B if protocols A and 
      B belong to the same protocol group. The following protocol groups 
      are defined:
      etsiQsigPG - ETSI QSIG protocol group containing ETSI QSIG 
      protocol,
      mcdnFamilyPG - MCDN Family protocol group containing NIS, 
      Meridian Customer Defined Network (MCDN) peer to peer, and 
      MCDN User to Network (UNI) protocols,
      analogAndCasPG - Analog and CAS protocol group containing 
      most of the analog and channel associated signalling protocols with 
      steady state line signalling and DTMF register signalling,
      euroIsdnPG - EURO ISDN protocol group containing most of the 
      European national ISDN protocols based on ETSI ISDN (ETSI-T) 
      standard.
      For every of the protocols group this attribute indicates what is the 
      level of protocol conversion support available on the SigChan 
      component:
      noGw - no protocol conversion available for the protocol group,
      singleEndedGw - only full protocol conversion available for the 
      protocol group (that is the SigChan component on the other side of 
      the subnet does not have to get involved in the gateway processing),
      doubleEndedGw - only partial protocol conversion available for the 
      protocol group (that is both SigChan components, ingress and 
      egress, have to get involved in signalling conversion),
      singleOrDoubleEndedGw - both, full and partial protocol 
      conversions available for the protocol group,
      nativePG - the protocol group is the native protocol group for the 
      SigChan component."
::= { mscSigChanGw 302 }

mscSigChanGwGatewayCapEntry OBJECT-TYPE
   SYNTAX     MscSigChanGwGatewayCapEntry
   ACCESS     not-accessible
   STATUS     mandatory
   DESCRIPTION
     "An entry in the mscSigChanGwGatewayCapTable."
   INDEX {
      mscSigChanIndex,
      mscSigChanGwIndex,
      mscSigChanGwGatewayCapIndex }
::= { mscSigChanGwGatewayCapTable 1 }

MscSigChanGwGatewayCapEntry ::= SEQUENCE {
   mscSigChanGwGatewayCapIndex
      INTEGER,
   mscSigChanGwGatewayCapValue
      INTEGER }

mscSigChanGwGatewayCapIndex OBJECT-TYPE
   SYNTAX     INTEGER  {
                 etsiQsigPG(0),
                 mcdnPG(1),
                 analogAndCasPG(2),
                 euroIsdnPG(3) }
   ACCESS     not-accessible
   STATUS     mandatory
   DESCRIPTION
     "This variable represents the mscSigChanGwGatewayCapTable
      specific index for the mscSigChanGwGatewayCapTable."
::= { mscSigChanGwGatewayCapEntry 1 }

mscSigChanGwGatewayCapValue OBJECT-TYPE
   SYNTAX     INTEGER  {
                 noGw(0),
                 singleEndedGw(1),
                 doubleEndedGw(2),
                 singleOrDoubleEndedGw(3),
                 nativePG(4) }
   ACCESS     read-only
   STATUS     mandatory
   DESCRIPTION
     "This variable represents an individual value for the
      mscSigChanGwGatewayCapTable."
::= { mscSigChanGwGatewayCapEntry 2 }

-- 
-- *** THIS SUBTREE CURRENTLY NOT IMPLEMENTED ***
-- 

-- SigChan/n NcaSession/n
-- This component represents a single Non Call-Associated signalling 
-- Session (NCAS) serviced by the SigChan component. Non 
-- call-associated signalling sessions are only supported on some 
-- Common Channel Signalling (CCS) protocols (for example ETSI 
-- QSIG, ETSI UNI ISDN). The instance value of a NcaSession 
-- component is an arbitrary number which does not change during an 
-- individual NCAS session.

mscSigChanNcas OBJECT IDENTIFIER ::= { mscSigChan 16 }



mscSigChanNcasRowStatusTable OBJECT-TYPE
   SYNTAX     SEQUENCE OF MscSigChanNcasRowStatusEntry
   ACCESS     not-accessible
   STATUS     mandatory
   DESCRIPTION
     "*** THIS TABLE CURRENTLY NOT IMPLEMENTED ***

      This entry controls the addition and deletion of 
      mscSigChanNcas components."
::= { mscSigChanNcas 1 }

mscSigChanNcasRowStatusEntry OBJECT-TYPE
   SYNTAX     MscSigChanNcasRowStatusEntry
   ACCESS     not-accessible
   STATUS     mandatory
   DESCRIPTION
     "A single entry in the table represents a single 
      mscSigChanNcas component."
   INDEX {
      mscSigChanIndex,
      mscSigChanNcasIndex }
::= { mscSigChanNcasRowStatusTable 1 }

MscSigChanNcasRowStatusEntry ::= SEQUENCE {
   mscSigChanNcasRowStatus
      RowStatus,
   mscSigChanNcasComponentName
      DisplayString,
   mscSigChanNcasStorageType
      StorageType,
   mscSigChanNcasIndex
      Integer32 }

mscSigChanNcasRowStatus OBJECT-TYPE
   SYNTAX     RowStatus 
   ACCESS     read-only
   STATUS     mandatory
   DESCRIPTION
     "This variable is used as the basis for SNMP naming of
      mscSigChanNcas components.
      These components cannot be added nor deleted."
::= { mscSigChanNcasRowStatusEntry 1 }

mscSigChanNcasComponentName OBJECT-TYPE
   SYNTAX     DisplayString 
   ACCESS     read-only
   STATUS     mandatory
   DESCRIPTION
     "This variable provides the component's string name for
      use with the ASCII Console Interface"
::= { mscSigChanNcasRowStatusEntry 2 }

mscSigChanNcasStorageType OBJECT-TYPE
   SYNTAX     StorageType 
   ACCESS     read-only
   STATUS     mandatory
   DESCRIPTION
     "This variable represents the storage type value for the
      mscSigChanNcas tables."
::= { mscSigChanNcasRowStatusEntry 4 }

mscSigChanNcasIndex OBJECT-TYPE
   SYNTAX     Integer32 (0..65535)
   ACCESS     not-accessible
   STATUS     mandatory
   DESCRIPTION
     "This variable represents the index for the mscSigChanNcas tables."
::= { mscSigChanNcasRowStatusEntry 10 }

mscSigChanNcasOperTable OBJECT-TYPE
   SYNTAX     SEQUENCE OF MscSigChanNcasOperEntry
   ACCESS     not-accessible
   STATUS     mandatory
   DESCRIPTION
     "*** THIS TABLE CURRENTLY NOT IMPLEMENTED ***

      This group contains various operational attributes of a non 
      call-associated signalling session serviced by a SigChan 
      component."
::= { mscSigChanNcas 100 }

mscSigChanNcasOperEntry OBJECT-TYPE
   SYNTAX     MscSigChanNcasOperEntry
   ACCESS     not-accessible
   STATUS     mandatory
   DESCRIPTION
     "An entry in the mscSigChanNcasOperTable."
   INDEX {
      mscSigChanIndex,
      mscSigChanNcasIndex }
::= { mscSigChanNcasOperTable 1 }

MscSigChanNcasOperEntry ::= SEQUENCE {
   mscSigChanNcasDirection
      INTEGER,
   mscSigChanNcasCallReference
      Hex,
   mscSigChanNcasCalledDirectoryNumber
      DigitString,
   mscSigChanNcasDuration
      Unsigned32 }

mscSigChanNcasDirection OBJECT-TYPE
   SYNTAX     INTEGER  {
                 ingress(1),
                 egress(2) }
   ACCESS     read-only
   STATUS     mandatory
   DESCRIPTION
     "This attribute indicates what is the direction of the non 
      call-associated signalling session. The attribute may have the 
      following values:
      ingress, the NCAS session is originated by the external equipment 
      into the subnet
      egress, the NCAS session is originated by the subnet into the 
      external equipment"
::= { mscSigChanNcasOperEntry 1 }

mscSigChanNcasCallReference OBJECT-TYPE
   SYNTAX     Hex (0..65535)
   ACCESS     read-only
   STATUS     mandatory
   DESCRIPTION
     "This attribute indicates which call reference the NCAS session uses."
::= { mscSigChanNcasOperEntry 2 }

mscSigChanNcasCalledDirectoryNumber OBJECT-TYPE
   SYNTAX     DigitString (SIZE (1..32))
   ACCESS     read-only
   STATUS     mandatory
   DESCRIPTION
     "This attribute indicates the dialled number for the NCAS session."
::= { mscSigChanNcasOperEntry 3 }

mscSigChanNcasDuration OBJECT-TYPE
   SYNTAX     Unsigned32 (0..4294967295)
   ACCESS     read-only
   STATUS     mandatory
   DESCRIPTION
     "This attribute indicates duration of the NCAS session since its 
      establishment."
   DEFVAL     { 0 }
::= { mscSigChanNcasOperEntry 4 }


-- SigChan/n VnetInternalCauseManipulation
-- This component represents the provisionable attributes for the 
-- internal, Passport and subnet generated cause codes of an 
-- establishing call. This component can be added for most of the 
-- ISDN (common channel signalling) protocols (EtsiQsig, NisSig, 
-- EuroIsdn) and cannot be added for a channel associated signalling 
-- protocol. This component is useful in a network where the 
-- originating PBX has restricted conditions to initiating alternate 
-- rerouting (rerouting on just one, specific, clearing cause code).

mscSigChanICmap OBJECT IDENTIFIER ::= { mscSigChan 18 }



mscSigChanICmapRowStatusTable OBJECT-TYPE
   SYNTAX     SEQUENCE OF MscSigChanICmapRowStatusEntry
   ACCESS     not-accessible
   STATUS     mandatory
   DESCRIPTION
     "This entry controls the addition and deletion of 
      mscSigChanICmap components."
::= { mscSigChanICmap 1 }

mscSigChanICmapRowStatusEntry OBJECT-TYPE
   SYNTAX     MscSigChanICmapRowStatusEntry
   ACCESS     not-accessible
   STATUS     mandatory
   DESCRIPTION
     "A single entry in the table represents a single 
      mscSigChanICmap component."
   INDEX {
      mscSigChanIndex,
      mscSigChanICmapIndex }
::= { mscSigChanICmapRowStatusTable 1 }

MscSigChanICmapRowStatusEntry ::= SEQUENCE {
   mscSigChanICmapRowStatus
      RowStatus,
   mscSigChanICmapComponentName
      DisplayString,
   mscSigChanICmapStorageType
      StorageType,
   mscSigChanICmapIndex
      NonReplicated }

mscSigChanICmapRowStatus OBJECT-TYPE
   SYNTAX     RowStatus 
   ACCESS     read-write
   STATUS     mandatory
   DESCRIPTION
     "This variable is used as the basis for SNMP naming of
      mscSigChanICmap components.
      These components can be added and deleted."
::= { mscSigChanICmapRowStatusEntry 1 }

mscSigChanICmapComponentName OBJECT-TYPE
   SYNTAX     DisplayString 
   ACCESS     read-only
   STATUS     mandatory
   DESCRIPTION
     "This variable provides the component's string name for
      use with the ASCII Console Interface"
::= { mscSigChanICmapRowStatusEntry 2 }

mscSigChanICmapStorageType OBJECT-TYPE
   SYNTAX     StorageType 
   ACCESS     read-only
   STATUS     mandatory
   DESCRIPTION
     "This variable represents the storage type value for the
      mscSigChanICmap tables."
::= { mscSigChanICmapRowStatusEntry 4 }

mscSigChanICmapIndex OBJECT-TYPE
   SYNTAX     NonReplicated 
   ACCESS     not-accessible
   STATUS     mandatory
   DESCRIPTION
     "This variable represents the index for the mscSigChanICmap tables."
::= { mscSigChanICmapRowStatusEntry 10 }

mscSigChanICmapIntCauseTable OBJECT-TYPE
   SYNTAX     SEQUENCE OF MscSigChanICmapIntCauseEntry
   ACCESS     not-accessible
   STATUS     mandatory
   DESCRIPTION
     "This group contains the provisionable, Passport generated clearing 
      reasons of an establishing call."
::= { mscSigChanICmap 100 }

mscSigChanICmapIntCauseEntry OBJECT-TYPE
   SYNTAX     MscSigChanICmapIntCauseEntry
   ACCESS     not-accessible
   STATUS     mandatory
   DESCRIPTION
     "An entry in the mscSigChanICmapIntCauseTable."
   INDEX {
      mscSigChanIndex,
      mscSigChanICmapIndex }
::= { mscSigChanICmapIntCauseTable 1 }

MscSigChanICmapIntCauseEntry ::= SEQUENCE {
   mscSigChanICmapEgressLinkOutOfServCause
      Unsigned32,
   mscSigChanICmapChanOrCircNotAvailCause
      Unsigned32,
   mscSigChanICmapTempFailureCause
      Unsigned32,
   mscSigChanICmapSwitchCongestCause
      Unsigned32,
   mscSigChanICmapReqChanOrCircNotAvailCause
      Unsigned32,
   mscSigChanICmapResourceUnavailCause
      Unsigned32,
   mscSigChanICmapServNotAllowedCause
      Unsigned32,
   mscSigChanICmapNoSuchChannelCause
      Unsigned32,
   mscSigChanICmapIncompatDestCause
      Unsigned32 }

mscSigChanICmapEgressLinkOutOfServCause OBJECT-TYPE
   SYNTAX     Unsigned32 (0..127 | 128)
   ACCESS     read-write
   STATUS     mandatory
   DESCRIPTION
     "This attribute specifies the cause code sent to the originating PBX 
      when the data link to the remote PBX is down or when remote 
      channels are in maintenance. 
      If the component is not added or if the default value autoConfigure 
      is provisioned for the attribute the cause code sent to the originating 
      PBX is not manipulated and the clearing process is not influenced. 
      For this case, a typical cause code value sent back to the originating 
      PBX is 27.

      VALUES (

      128 = autoConfigure

      )"
   DEFVAL     { 128 }
::= { mscSigChanICmapIntCauseEntry 1 }

mscSigChanICmapChanOrCircNotAvailCause OBJECT-TYPE
   SYNTAX     Unsigned32 (0..127 | 128)
   ACCESS     read-write
   STATUS     mandatory
   DESCRIPTION
     "This attribute specifies the cause code sent to the originating PBX if 
      no timeslot is available for an incoming call. 
      If the component is not added or if the default value autoConfigure 
      is provisioned for the attribute the cause code sent to the originating 
      PBX is not manipulated and the clearing process is not influenced. 
      For this case, a typical cause code value sent back to the originating 
      PBX is 34.

      VALUES (

      128 = autoConfigure

      )"
   DEFVAL     { 128 }
::= { mscSigChanICmapIntCauseEntry 2 }

mscSigChanICmapTempFailureCause OBJECT-TYPE
   SYNTAX     Unsigned32 (0..127 | 128)
   ACCESS     read-write
   STATUS     mandatory
   DESCRIPTION
     "This attribute specifies the cause code sent to the originating PBX 
      when PORS fails to establish a call due to congestion or a disabled 
      trunk. It is also generated when the calling side fails to decode 
      payload capabilities sent by the called side. 
      If the component is not added or if the default value autoConfigure 
      is provisioned for the attribute the cause code sent to the originating 
      PBX is not manipulated and the clearing process is not influenced. 
      For this case, a typical cause code value sent back to the originating 
      PBX is 41.

      VALUES (

      128 = autoConfigure

      )"
   DEFVAL     { 128 }
::= { mscSigChanICmapIntCauseEntry 3 }

mscSigChanICmapSwitchCongestCause OBJECT-TYPE
   SYNTAX     Unsigned32 (0..127 | 128)
   ACCESS     read-write
   STATUS     mandatory
   DESCRIPTION
     "This attribute specifies the cause code sent to the originating PBX 
      when the allocation of internal resources for an incoming call fails. 
      If the component is not added or if the default value autoConfigure 
      is provisioned for the attribute the cause code sent to the originating 
      PBX is not manipulated and the clearing process is not influenced. 
      For this case, typical cause code values sent back to the originating 
      PBX are 42 for NIS and 41 for ETSI.

      VALUES (

      128 = autoConfigure

      )"
   DEFVAL     { 128 }
::= { mscSigChanICmapIntCauseEntry 4 }

mscSigChanICmapReqChanOrCircNotAvailCause OBJECT-TYPE
   SYNTAX     Unsigned32 (0..127 | 128)
   ACCESS     read-write
   STATUS     mandatory
   DESCRIPTION
     "This attribute specifies the cause code sent to the originating PBX 
      when an exclusively requested channel is not in service or a channel 
      request is unsuccessful. 
      If the component is not added or if the default value autoConfigure 
      is provisioned for the attribute the cause code sent to the originating 
      PBX is not manipulated and the clearing process is not influenced. 
      For this case, a typical cause code value sent back to the originating 
      PBX is 44.

      VALUES (

      128 = autoConfigure

      )"
   DEFVAL     { 128 }
::= { mscSigChanICmapIntCauseEntry 5 }

mscSigChanICmapResourceUnavailCause OBJECT-TYPE
   SYNTAX     Unsigned32 (0..127 | 128)
   ACCESS     read-write
   STATUS     mandatory
   DESCRIPTION
     "This attribute specifies the cause code sent to the originating PBX 
      when the path establishing timer expires, when the switched voice 
      service associated to a call is locked by CAS or when an H-channel 
      is requested. 
      If the component is not added or if the default value autoConfigure 
      is provisioned for the attribute the cause code sent to the originating 
      PBX is not manipulated and the clearing process is not influenced. 
      For this case, typical cause code values sent back to the originating 
      PBX are 47 for NIS and 44 for ETSI.

      VALUES (

      128 = autoConfigure

      )"
   DEFVAL     { 128 }
::= { mscSigChanICmapIntCauseEntry 6 }

mscSigChanICmapServNotAllowedCause OBJECT-TYPE
   SYNTAX     Unsigned32 (0..127 | 128)
   ACCESS     read-write
   STATUS     mandatory
   DESCRIPTION
     "This attribute specifies the cause code sent to the originating PBX 
      when the requested call type (voice or data) is not compatible with 
      Vroute typeOfRoute at the calling side. 
      If the component is not added or if the default value autoConfigure 
      is provisioned for the attribute the cause code sent to the originating 
      PBX is not manipulated and the clearing process is not influenced. 
      For this case, a typical cause code value sent back to the originating 
      PBX is 63.

      VALUES (

      128 = autoConfigure

      )"
   DEFVAL     { 128 }
::= { mscSigChanICmapIntCauseEntry 7 }

mscSigChanICmapNoSuchChannelCause OBJECT-TYPE
   SYNTAX     Unsigned32 (0..127 | 128)
   ACCESS     read-write
   STATUS     mandatory
   DESCRIPTION
     "This attribute specifies the cause code sent to the originating PBX 
      when a requested channel does not exist. 
      If the component is not added or if the default value autoConfigure 
      is provisioned for the attribute the cause code sent to the originating 
      PBX is not manipulated and the clearing process is not influenced. 
      For this case, a typical cause code value sent back to the originating 
      PBX is 82.

      VALUES (

      128 = autoConfigure

      )"
   DEFVAL     { 128 }
::= { mscSigChanICmapIntCauseEntry 8 }

mscSigChanICmapIncompatDestCause OBJECT-TYPE
   SYNTAX     Unsigned32 (0..127 | 128)
   ACCESS     read-write
   STATUS     mandatory
   DESCRIPTION
     "This attribute specifies the cause code sent to the originating PBX 
      when the calling and called side capabilities do not match. 
      If the component is not added or if the default value autoConfigure 
      is provisioned for the attribute the cause code sent to the originating 
      PBX is not manipulated and the clearing process is not influenced. 
      For this case, a typical cause code value sent back to the originating 
      PBX is 88.

      VALUES (

      128 = autoConfigure

      )"
   DEFVAL     { 128 }
::= { mscSigChanICmapIntCauseEntry 9 }


-- VoiceRoute/n		
-- A VoiceRoute component defines the common characteristics of the 
-- connections to a Private Branch Exchange (PBX). There is normally 
-- one VoiceRoute per attached PBX.

mscVRoute OBJECT IDENTIFIER ::= { mscComponents 116 }



mscVRouteRowStatusTable OBJECT-TYPE
   SYNTAX     SEQUENCE OF MscVRouteRowStatusEntry
   ACCESS     not-accessible
   STATUS     mandatory
   DESCRIPTION
     "This entry controls the addition and deletion of 
      mscVRoute components."
::= { mscVRoute 1 }

mscVRouteRowStatusEntry OBJECT-TYPE
   SYNTAX     MscVRouteRowStatusEntry
   ACCESS     not-accessible
   STATUS     mandatory
   DESCRIPTION
     "A single entry in the table represents a single 
      mscVRoute component."
   INDEX {
      mscVRouteIndex }
::= { mscVRouteRowStatusTable 1 }

MscVRouteRowStatusEntry ::= SEQUENCE {
   mscVRouteRowStatus
      RowStatus,
   mscVRouteComponentName
      DisplayString,
   mscVRouteStorageType
      StorageType,
   mscVRouteIndex
      Integer32 }

mscVRouteRowStatus OBJECT-TYPE
   SYNTAX     RowStatus 
   ACCESS     read-write
   STATUS     mandatory
   DESCRIPTION
     "This variable is used as the basis for SNMP naming of
      mscVRoute components.
      These components can be added and deleted."
::= { mscVRouteRowStatusEntry 1 }

mscVRouteComponentName OBJECT-TYPE
   SYNTAX     DisplayString 
   ACCESS     read-only
   STATUS     mandatory
   DESCRIPTION
     "This variable provides the component's string name for
      use with the ASCII Console Interface"
::= { mscVRouteRowStatusEntry 2 }

mscVRouteStorageType OBJECT-TYPE
   SYNTAX     StorageType 
   ACCESS     read-only
   STATUS     mandatory
   DESCRIPTION
     "This variable represents the storage type value for the
      mscVRoute tables."
::= { mscVRouteRowStatusEntry 4 }

mscVRouteIndex OBJECT-TYPE
   SYNTAX     Integer32 (1..16)
   ACCESS     not-accessible
   STATUS     mandatory
   DESCRIPTION
     "This variable represents the index for the mscVRoute tables."
::= { mscVRouteRowStatusEntry 10 }

mscVRouteProvTable OBJECT-TYPE
   SYNTAX     SEQUENCE OF MscVRouteProvEntry
   ACCESS     not-accessible
   STATUS     mandatory
   DESCRIPTION
     "This group contains the provisionable attributes of a Voice 
      Networking VoiceRoute component."
::= { mscVRoute 10 }

mscVRouteProvEntry OBJECT-TYPE
   SYNTAX     MscVRouteProvEntry
   ACCESS     not-accessible
   STATUS     mandatory
   DESCRIPTION
     "An entry in the mscVRouteProvTable."
   INDEX {
      mscVRouteIndex }
::= { mscVRouteProvTable 1 }

MscVRouteProvEntry ::= SEQUENCE {
   mscVRouteCommentText
      AsciiString,
   mscVRouteTypeOfRoute
      INTEGER,
   mscVRouteDiallingPlan0
      OCTET STRING,
   mscVRouteDiallingPlan1
      OCTET STRING,
   mscVRouteDiallingPlan2
      OCTET STRING,
   mscVRouteHuntingAlgorithm
      INTEGER,
   mscVRouteMinimumDigitsToRoute
      Unsigned32,
   mscVRouteVoiceNetworkingCallServer
      Link,
   mscVRouteOverrideDirectoryNumber
      DigitString,
   mscVRoutePrivateNetworkIdentifer
      Unsigned32 }

mscVRouteCommentText OBJECT-TYPE
   SYNTAX     AsciiString (SIZE (0..40))
   ACCESS     read-write
   STATUS     mandatory
   DESCRIPTION
     "Use of this attribute is at the discretion of the system administrator. 
      Typically, it specifies the name of the customer that is using this 
      VoiceRoute."
::= { mscVRouteProvEntry 1 }

mscVRouteTypeOfRoute OBJECT-TYPE
   SYNTAX     INTEGER  {
                 voice(0),
                 data(1),
                 voiceData(2) }
   ACCESS     read-write
   STATUS     mandatory
   DESCRIPTION
     "This attribute specifies the type of calls (either voice, data, or both 
      voice and data) that this VoiceRoute will accept from the Passport 
      subnet and the local PBX. If typeOfRoute is set to voice, then all 
      data calls from the subnet and the local PBX will be rejected. If 
      typeOfRoute is set to data, then all voice calls from the subnet and 
      the local PBX will be rejected. If typeOfRoute is set to voiceData, 
      then all data and voice calls will be accepted from the subnet and 
      the local PBX."
   DEFVAL     { voiceData }
::= { mscVRouteProvEntry 2 }

mscVRouteDiallingPlan0 OBJECT-TYPE
   SYNTAX     OCTET STRING (SIZE (2))
   ACCESS     read-write
   STATUS     mandatory
   DESCRIPTION
     "This attribute specifies how to map the numbering plan indication 
      and the type of number into the Vncs database diallingPlan0. For 
      more information refer to NTP 241-7001-4xx Voice Networking 
      Users Guide. There are three numbering plans that are allowed, 
      unknown, E.164, and private. Within each of these, there are eight 
      possible type of numbers. Since the name for the type of numbers 
      for the private numbering plans varies from protocol to protocol, a 
      generic scheme has been adopted.
      unknown means that the sending and receiving switches have no 
      knowledge of the numbering plan.
      international means that the sending switch has identified the 
      number format as matching the E.164 international dialling.
      national means that the sending switch has identified the number as 
      conforming to the E.164 national dialling plan
      subscriber means that the number is the address of a customer 
      conforming to the local public network.
      p0, p1, p2, p3, p4, p5, p6 and p7 are private numbering plans, with a 
      type of number zero to seven.
      casUnknown means any number received from a Channel 
      Associated Signalling (CAS) trunk.

      Description of bits:
      unknown(0)
      international(1)
      national(2)
      subscriber(3)
      p0(4)
      p1(5)
      p2(6)
      p3(7)
      p4(8)
      p5(9)
      p6(10)
      p7(11)
      casUnknown(12)"
   DEFVAL     { 'fff8'H }
::= { mscVRouteProvEntry 6 }

mscVRouteDiallingPlan1 OBJECT-TYPE
   SYNTAX     OCTET STRING (SIZE (2))
   ACCESS     read-write
   STATUS     mandatory
   DESCRIPTION
     "This attribute specifies how to map the numbering plan indication 
      and the type of number into the Vncs database diallingPlan1. For 
      more information refer to NTP 241-7001-4xx Voice Networking 
      Users Guide. There are three numbering plans that are allowed, 
      unknown, E.164, and private. Within each of these, there are eight 
      possible type of numbers. Since the name for the type of numbers 
      for the private numbering plans varies from protocol to protocol, a 
      generic scheme has been adopted.
      unknown means that the sending and receiving switches have no 
      knowledge of the numbering plan.
      international means that the sending switch has identified the 
      number format as matching the E.164 international dialling plan.
      national means that the sending switch has identified the number as 
      conforming to the E.164 national dialling plan
      subscriber means that the number is the address of a customer 
      conforming to the local public network.
      p0, p1, p2, p3, p4, p5, p6 and p7 are private numbering plans, with a 
      type of number zero to seven.
      casUnknown means any number received from a Channel 
      Associated Signalling (CAS) trunk.

      Description of bits:
      unknown(0)
      international(1)
      national(2)
      subscriber(3)
      p0(4)
      p1(5)
      p2(6)
      p3(7)
      p4(8)
      p5(9)
      p6(10)
      p7(11)
      casUnknown(12)"
::= { mscVRouteProvEntry 7 }

mscVRouteDiallingPlan2 OBJECT-TYPE
   SYNTAX     OCTET STRING (SIZE (2))
   ACCESS     read-write
   STATUS     mandatory
   DESCRIPTION
     "This attribute specifies how to map the numbering plan indication 
      and the type of number into the Vncs database diallingPlan2. For 
      more information refer to NTP 241-7001-4xx Voice Networking 
      Users Guide. There are three numbering plans that are allowed, 
      unknown, E.164, and private. Within each of these, there are eight 
      possible type of numbers. Since the name for the type of numbers 
      for the private numbering plans varies from protocol to protocol, a 
      generic scheme has been adopted.
      unknown means that the sending and receiving switches have no 
      knowledge of the numbering plan.
      international means that the sending switch has identified the 
      number format as matching the E.164 international dialling plan.
      national means that the sending switch has identified the number as 
      conforming to the E.164 national dialling plan
      subscriber means that the number is the address of a customer 
      conforming to the local public network.
      p0, p1, p2, p3, p4, p5, p6 and p7 are private numbering plans, with a 
      type of number zero to seven.
      casUnknown means any number received from a Channel 
      Associated Signalling (CAS) trunk.

      Description of bits:
      unknown(0)
      international(1)
      national(2)
      subscriber(3)
      p0(4)
      p1(5)
      p2(6)
      p3(7)
      p4(8)
      p5(9)
      p6(10)
      p7(11)
      casUnknown(12)"
::= { mscVRouteProvEntry 8 }

mscVRouteHuntingAlgorithm OBJECT-TYPE
   SYNTAX     INTEGER  {
                 bottomUpLinear(0),
                 topDownLinear(1) }
   ACCESS     read-write
   STATUS     mandatory
   DESCRIPTION
     "This attribute specifies the type of hunting algorithm that should be 
      used by the VoiceRoute and VoiceSubroutes when selecting a 
      channel to make an outgoing call. 
      bottomUpLinear means that a call from the subnet will be passed to 
      the lowest instance of the VoiceSubroutes, which in turn will pass 
      the call to the lowest instance of SwitchedVoiceService. If there are 
      no available SwitchedVoiceServices in that VoiceSubroute then the 
      process will be repeated for the next lowest instance of 
      VoiceSubroute.
      topDownLinear means that a call from the subnet will be passed to 
      the highest instance of the VoiceSubroutes, which in turn will pass 
      the call to the highest instance of SwitchedVoiceService. If there are 
      no available SwitchedVoiceServices in that VoiceSubroute then the 
      process will be repeated for the next highest instance of 
      VoiceSubroute."
   DEFVAL     { bottomUpLinear }
::= { mscVRouteProvEntry 9 }

mscVRouteMinimumDigitsToRoute OBJECT-TYPE
   SYNTAX     Unsigned32 (1..16)
   ACCESS     read-write
   STATUS     mandatory
   DESCRIPTION
     "This attribute specifies the number of digits that must be received 
      before an address resolution request will be sent to the 
      VoiceNetworkingCallServer. Once this level has been exceeded an 
      address resolution request will be sent for every digit received until 
      the dialled number has been resolved in the database.
      This number should be set to a value which represents the average 
      number of digits that will allow for a unique end-point to be 
      identified. If the number is set too low, then the number of 
      simultaneous calls that can be handled by the 
      VoiceNetworkingCallServer will be reduced since the number of 
      address resolution requests sent for each call will be increased. If it 
      is set too high then address resolution request messages will not be 
      sent to the VoiceNetworkingCallServer until the end-of-dial timer 
      has expired (approximately 12 seconds after the last digit has been 
      received). This can result in very long call setup times."
   DEFVAL     { 3 }
::= { mscVRouteProvEntry 10 }

mscVRouteVoiceNetworkingCallServer OBJECT-TYPE
   SYNTAX     Link 
   ACCESS     read-write
   STATUS     mandatory
   DESCRIPTION
     "This attribute specifies which Vncs instance should be used by all 
      calls into this VoiceRoute from the PBX."
::= { mscVRouteProvEntry 11 }

mscVRouteOverrideDirectoryNumber OBJECT-TYPE
   SYNTAX     DigitString (SIZE (0..24))
   ACCESS     read-write
   STATUS     mandatory
   DESCRIPTION
     "The number specified here will be used in place of the dialled 
      number to lookup the destination in the 
      VoiceNetworkingCallServer. A null string means that the routing 
      decision should be based on the dialled number.
      The numbering plan type that will be used will be noAccessCode."
   DEFVAL     { ''H }  -- ""
::= { mscVRouteProvEntry 12 }

mscVRoutePrivateNetworkIdentifer OBJECT-TYPE
   SYNTAX     Unsigned32 (0..32700)
   ACCESS     read-write
   STATUS     mandatory
   DESCRIPTION
     "This attribute specifies the private network identifier (PNI) value. If 
      the value is zero then connectionless supplementary service 
      transport for TCAP formatted FACILITY messages is not 
      supported."
   DEFVAL     { 0 }
::= { mscVRouteProvEntry 13 }

mscVRouteCidDataTable OBJECT-TYPE
   SYNTAX     SEQUENCE OF MscVRouteCidDataEntry
   ACCESS     not-accessible
   STATUS     mandatory
   DESCRIPTION
     "This group contains the attribute for a component's Customer 
      Identifier (CID). Refer to the attribute description for a detailed 
      explanation of CIDs."
::= { mscVRoute 11 }

mscVRouteCidDataEntry OBJECT-TYPE
   SYNTAX     MscVRouteCidDataEntry
   ACCESS     not-accessible
   STATUS     mandatory
   DESCRIPTION
     "An entry in the mscVRouteCidDataTable."
   INDEX {
      mscVRouteIndex }
::= { mscVRouteCidDataTable 1 }

MscVRouteCidDataEntry ::= SEQUENCE {
   mscVRouteCustomerIdentifier
      Unsigned32 }

mscVRouteCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { mscVRouteCidDataEntry 1 }

mscVRouteIfEntryTable OBJECT-TYPE
   SYNTAX     SEQUENCE OF MscVRouteIfEntryEntry
   ACCESS     not-accessible
   STATUS     mandatory
   DESCRIPTION
     "This group contains the provisionable attributes for the ifEntry."
::= { mscVRoute 12 }

mscVRouteIfEntryEntry OBJECT-TYPE
   SYNTAX     MscVRouteIfEntryEntry
   ACCESS     not-accessible
   STATUS     mandatory
   DESCRIPTION
     "An entry in the mscVRouteIfEntryTable."
   INDEX {
      mscVRouteIndex }
::= { mscVRouteIfEntryTable 1 }

MscVRouteIfEntryEntry ::= SEQUENCE {
   mscVRouteIfAdminStatus
      INTEGER,
   mscVRouteIfIndex
      InterfaceIndex }

mscVRouteIfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { mscVRouteIfEntryEntry 1 }

mscVRouteIfIndex OBJECT-TYPE
   SYNTAX     InterfaceIndex (1..65535)
   ACCESS     read-only
   STATUS     mandatory
   DESCRIPTION
     "This is the index for the IfEntry. Its value is automatically initialized 
      during the provisioning process."
::= { mscVRouteIfEntryEntry 2 }

mscVRouteStateTable OBJECT-TYPE
   SYNTAX     SEQUENCE OF MscVRouteStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscVRoute 13 }

mscVRouteStateEntry OBJECT-TYPE
   SYNTAX     MscVRouteStateEntry
   ACCESS     not-accessible
   STATUS     mandatory
   DESCRIPTION
     "An entry in the mscVRouteStateTable."
   INDEX {
      mscVRouteIndex }
::= { mscVRouteStateTable 1 }

MscVRouteStateEntry ::= SEQUENCE {
   mscVRouteAdminState
      INTEGER,
   mscVRouteOperationalState
      INTEGER,
   mscVRouteUsageState
      INTEGER }

mscVRouteAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscVRouteStateEntry 1 }

mscVRouteOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscVRouteStateEntry 2 }

mscVRouteUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscVRouteStateEntry 3 }

mscVRouteOperStatusTable OBJECT-TYPE
   SYNTAX     SEQUENCE OF MscVRouteOperStatusEntry
   ACCESS     not-accessible
   STATUS     mandatory
   DESCRIPTION
     "This group includes the Operational Status attribute. This attribute 
      defines the current operational state of this component."
::= { mscVRoute 14 }

mscVRouteOperStatusEntry OBJECT-TYPE
   SYNTAX     MscVRouteOperStatusEntry
   ACCESS     not-accessible
   STATUS     mandatory
   DESCRIPTION
     "An entry in the mscVRouteOperStatusTable."
   INDEX {
      mscVRouteIndex }
::= { mscVRouteOperStatusTable 1 }

MscVRouteOperStatusEntry ::= SEQUENCE {
   mscVRouteSnmpOperStatus
      INTEGER }

mscVRouteSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { mscVRouteOperStatusEntry 1 }

mscVRouteStatsTable OBJECT-TYPE
   SYNTAX     SEQUENCE OF MscVRouteStatsEntry
   ACCESS     not-accessible
   STATUS     mandatory
   DESCRIPTION
     "This group provides the operational attributes for the VoiceRoute 
      component. It contains information relating to calls that originate 
      from the network."
::= { mscVRoute 15 }

mscVRouteStatsEntry OBJECT-TYPE
   SYNTAX     MscVRouteStatsEntry
   ACCESS     not-accessible
   STATUS     mandatory
   DESCRIPTION
     "An entry in the mscVRouteStatsTable."
   INDEX {
      mscVRouteIndex }
::= { mscVRouteStatsTable 1 }

MscVRouteStatsEntry ::= SEQUENCE {
   mscVRouteTotalCallsFromSubnet
      Counter32,
   mscVRouteCallsClearedNoChannel
      Counter32,
   mscVRouteCallsClearedOutOfService
      Counter32,
   mscVRouteCallsRejected
      Counter32 }

mscVRouteTotalCallsFromSubnet OBJECT-TYPE
   SYNTAX     Counter32 
   ACCESS     read-only
   STATUS     mandatory
   DESCRIPTION
     "This attribute counts the total number of calls that have been 
      received from the Passport subnet, including calls that fail.
      The value wraps to zero when it reaches its maximum."
::= { mscVRouteStatsEntry 1 }

mscVRouteCallsClearedNoChannel OBJECT-TYPE
   SYNTAX     Counter32 
   ACCESS     read-only
   STATUS     mandatory
   DESCRIPTION
     "This attribute counts the total number of calls from the subnet that 
      were rejected when all of the in-service channels were busy. When a 
      call is rejected for this reason, the cause code sent to the originator 
      is 34, no circuit/channel available.
      The value wraps to zero when it reaches its maximum."
::= { mscVRouteStatsEntry 2 }

mscVRouteCallsClearedOutOfService OBJECT-TYPE
   SYNTAX     Counter32 
   ACCESS     read-only
   STATUS     mandatory
   DESCRIPTION
     "This attribute counts the total number of calls from the subnet that 
      were rejected because all of the channels were out-of-service. A 
      channel is considered out-of-service if it is unavailable for any 
      reason other than it is being engaged in handling a call. That is, an 
      operator lock of any of the components required for the channel's 
      operation, or problems which interfere with the connection to the 
      PBX, will cause the channel to be considered out-of-service. When 
      a call is rejected for this reason, the cause code sent back to the 
      originator is 27, destination out-of-service.
      The value wraps to zero when it reaches its maximum."
::= { mscVRouteStatsEntry 3 }

mscVRouteCallsRejected OBJECT-TYPE
   SYNTAX     Counter32 
   ACCESS     read-only
   STATUS     mandatory
   DESCRIPTION
     "This attribute counts the total number of calls from the subnet that 
      were rejected because they were: 
      1) voice calls to a typeOfRoute which is set to data,
      2) data calls to a typeOfRoute which is set to voice,
      3) using a signalling protocol which is incompatible with this end.
      The value wraps to zero when it reaches its maximum."
::= { mscVRouteStatsEntry 4 }

mscVRouteSubroutesTable OBJECT-TYPE
   SYNTAX     SEQUENCE OF MscVRouteSubroutesEntry
   ACCESS     not-accessible
   STATUS     mandatory
   DESCRIPTION
     "This attribute specifies all of the VoiceSubroutes which are 
      associated with this VoiceRoute. There are only 4 VoiceSubroutes 
      allowed per VoiceRoute."
::= { mscVRoute 309 }

mscVRouteSubroutesEntry OBJECT-TYPE
   SYNTAX     MscVRouteSubroutesEntry
   ACCESS     not-accessible
   STATUS     mandatory
   DESCRIPTION
     "An entry in the mscVRouteSubroutesTable."
   INDEX {
      mscVRouteIndex,
      mscVRouteSubroutesValue }
::= { mscVRouteSubroutesTable 1 }

MscVRouteSubroutesEntry ::= SEQUENCE {
   mscVRouteSubroutesValue
      Link,
   mscVRouteSubroutesRowStatus
      RowStatus }

mscVRouteSubroutesValue OBJECT-TYPE
   SYNTAX     Link 
   ACCESS     read-write
   STATUS     mandatory
   DESCRIPTION
     "This variable represents both the value and the index for the
      mscVRouteSubroutesTable."
::= { mscVRouteSubroutesEntry 1 }

mscVRouteSubroutesRowStatus OBJECT-TYPE
   SYNTAX     RowStatus 
   ACCESS     write-only
   STATUS     mandatory
   DESCRIPTION
     "This variable is used to control the addition and deletion 
      of individual values of the mscVRouteSubroutesTable."
::= { mscVRouteSubroutesEntry 2 }

mscVRouteDegradedSubroutesTable OBJECT-TYPE
   SYNTAX     SEQUENCE OF MscVRouteDegradedSubroutesEntry
   ACCESS     not-accessible
   STATUS     mandatory
   DESCRIPTION
     "This attribute indicates all of the VoiceSubroutes that have at least 
      one SwitchedVoiceService whose operationalState is disabled."
::= { mscVRoute 310 }

mscVRouteDegradedSubroutesEntry OBJECT-TYPE
   SYNTAX     MscVRouteDegradedSubroutesEntry
   ACCESS     not-accessible
   STATUS     mandatory
   DESCRIPTION
     "An entry in the mscVRouteDegradedSubroutesTable."
   INDEX {
      mscVRouteIndex,
      mscVRouteDegradedSubroutesValue }
::= { mscVRouteDegradedSubroutesTable 1 }

MscVRouteDegradedSubroutesEntry ::= SEQUENCE {
   mscVRouteDegradedSubroutesValue
      RowPointer }

mscVRouteDegradedSubroutesValue OBJECT-TYPE
   SYNTAX     RowPointer 
   ACCESS     read-only
   STATUS     mandatory
   DESCRIPTION
     "This variable represents both the value and the index for the
      mscVRouteDegradedSubroutesTable."
::= { mscVRouteDegradedSubroutesEntry 1 }


-- VRoute/n Debug		
-- The Debug component defines the debug operational characteristics 
-- of the VoiceRoute component.

mscVRouteDebug OBJECT IDENTIFIER ::= { mscVRoute 2 }



mscVRouteDebugRowStatusTable OBJECT-TYPE
   SYNTAX     SEQUENCE OF MscVRouteDebugRowStatusEntry
   ACCESS     not-accessible
   STATUS     mandatory
   DESCRIPTION
     "This entry controls the addition and deletion of 
      mscVRouteDebug components."
::= { mscVRouteDebug 1 }

mscVRouteDebugRowStatusEntry OBJECT-TYPE
   SYNTAX     MscVRouteDebugRowStatusEntry
   ACCESS     not-accessible
   STATUS     mandatory
   DESCRIPTION
     "A single entry in the table represents a single 
      mscVRouteDebug component."
   INDEX {
      mscVRouteIndex,
      mscVRouteDebugIndex }
::= { mscVRouteDebugRowStatusTable 1 }

MscVRouteDebugRowStatusEntry ::= SEQUENCE {
   mscVRouteDebugRowStatus
      RowStatus,
   mscVRouteDebugComponentName
      DisplayString,
   mscVRouteDebugStorageType
      StorageType,
   mscVRouteDebugIndex
      NonReplicated }

mscVRouteDebugRowStatus OBJECT-TYPE
   SYNTAX     RowStatus 
   ACCESS     read-only
   STATUS     mandatory
   DESCRIPTION
     "This variable is used as the basis for SNMP naming of
      mscVRouteDebug components.
      These components cannot be added nor deleted."
::= { mscVRouteDebugRowStatusEntry 1 }

mscVRouteDebugComponentName OBJECT-TYPE
   SYNTAX     DisplayString 
   ACCESS     read-only
   STATUS     mandatory
   DESCRIPTION
     "This variable provides the component's string name for
      use with the ASCII Console Interface"
::= { mscVRouteDebugRowStatusEntry 2 }

mscVRouteDebugStorageType OBJECT-TYPE
   SYNTAX     StorageType 
   ACCESS     read-only
   STATUS     mandatory
   DESCRIPTION
     "This variable represents the storage type value for the
      mscVRouteDebug tables."
::= { mscVRouteDebugRowStatusEntry 4 }

mscVRouteDebugIndex OBJECT-TYPE
   SYNTAX     NonReplicated 
   ACCESS     not-accessible
   STATUS     mandatory
   DESCRIPTION
     "This variable represents the index for the mscVRouteDebug tables."
::= { mscVRouteDebugRowStatusEntry 10 }


-- VoiceRoute/n Interface
-- This component defines the interface between a voice route and a 
-- PBX. It is ignored for calls running on 1pDS1V or 1pE1V cards.

mscVRouteInterface OBJECT IDENTIFIER ::= { mscVRoute 3 }



mscVRouteInterfaceRowStatusTable OBJECT-TYPE
   SYNTAX     SEQUENCE OF MscVRouteInterfaceRowStatusEntry
   ACCESS     not-accessible
   STATUS     mandatory
   DESCRIPTION
     "This entry controls the addition and deletion of 
      mscVRouteInterface components."
::= { mscVRouteInterface 1 }

mscVRouteInterfaceRowStatusEntry OBJECT-TYPE
   SYNTAX     MscVRouteInterfaceRowStatusEntry
   ACCESS     not-accessible
   STATUS     mandatory
   DESCRIPTION
     "A single entry in the table represents a single 
      mscVRouteInterface component."
   INDEX {
      mscVRouteIndex,
      mscVRouteInterfaceIndex }
::= { mscVRouteInterfaceRowStatusTable 1 }

MscVRouteInterfaceRowStatusEntry ::= SEQUENCE {
   mscVRouteInterfaceRowStatus
      RowStatus,
   mscVRouteInterfaceComponentName
      DisplayString,
   mscVRouteInterfaceStorageType
      StorageType,
   mscVRouteInterfaceIndex
      NonReplicated }

mscVRouteInterfaceRowStatus OBJECT-TYPE
   SYNTAX     RowStatus 
   ACCESS     read-only
   STATUS     mandatory
   DESCRIPTION
     "This variable is used as the basis for SNMP naming of
      mscVRouteInterface components.
      These components cannot be added nor deleted."
::= { mscVRouteInterfaceRowStatusEntry 1 }

mscVRouteInterfaceComponentName OBJECT-TYPE
   SYNTAX     DisplayString 
   ACCESS     read-only
   STATUS     mandatory
   DESCRIPTION
     "This variable provides the component's string name for
      use with the ASCII Console Interface"
::= { mscVRouteInterfaceRowStatusEntry 2 }

mscVRouteInterfaceStorageType OBJECT-TYPE
   SYNTAX     StorageType 
   ACCESS     read-only
   STATUS     mandatory
   DESCRIPTION
     "This variable represents the storage type value for the
      mscVRouteInterface tables."
::= { mscVRouteInterfaceRowStatusEntry 4 }

mscVRouteInterfaceIndex OBJECT-TYPE
   SYNTAX     NonReplicated 
   ACCESS     not-accessible
   STATUS     mandatory
   DESCRIPTION
     "This variable represents the index for the mscVRouteInterface tables."
::= { mscVRouteInterfaceRowStatusEntry 10 }

mscVRouteInterfaceProvTable OBJECT-TYPE
   SYNTAX     SEQUENCE OF MscVRouteInterfaceProvEntry
   ACCESS     not-accessible
   STATUS     mandatory
   DESCRIPTION
     "This group contains attributes specifying the interface to a PBX."
::= { mscVRouteInterface 10 }

mscVRouteInterfaceProvEntry OBJECT-TYPE
   SYNTAX     MscVRouteInterfaceProvEntry
   ACCESS     not-accessible
   STATUS     mandatory
   DESCRIPTION
     "An entry in the mscVRouteInterfaceProvTable."
   INDEX {
      mscVRouteIndex,
      mscVRouteInterfaceIndex }
::= { mscVRouteInterfaceProvTable 1 }

MscVRouteInterfaceProvEntry ::= SEQUENCE {
   mscVRouteInterfaceIngressAudioGain
      INTEGER,
   mscVRouteInterfaceEgressAudioGain
      INTEGER,
   mscVRouteInterfaceTandemPassThrough
      INTEGER,
   mscVRouteInterfaceEchoCancellation
      INTEGER,
   mscVRouteInterfaceComfortNoiseCap
      INTEGER,
   mscVRouteInterfaceSpeechHangoverTime
      Unsigned32,
   mscVRouteInterfaceFaxHangoverTimeG711G726
      Unsigned32,
   mscVRouteInterfaceModemFaxSpeechDiscrim
      INTEGER,
   mscVRouteInterfaceEchoTailDelay
      Unsigned32,
   mscVRouteInterfaceEchoReturnLoss
      Unsigned32,
   mscVRouteInterfaceEcanBypassMode
      INTEGER }

mscVRouteInterfaceIngressAudioGain OBJECT-TYPE
   SYNTAX     INTEGER (-12..12)
   ACCESS     read-write
   STATUS     mandatory
   DESCRIPTION
     "This attribute specifies the gain in dB that is applied to data coming 
      from outside the network before it is transferred across the network. 
      It applies to voice, modem and fax traffic. For example, ingress gain 
      is applied to audio data coming from a PBX. If ingressAudioGain is 
      negative, a loss is applied.
      
      ingressAudioGain and egressAudioGain are used in loss planning, 
      which is the configuration of the devices in a network to ensure that 
      the signal level from any point in the network to any other point is 
      correct.
      
      ingressAudioGain is ignored for calls on 1pDS1V and 1pE1V cards. 
      For calls running on these cards, ingress audio gain is not under the 
      user's control and egress audio gain is determined by the audioGain 
      attribute in the appropriate Vncs/m VoiceProfile/n."
   DEFVAL     { 0 }
::= { mscVRouteInterfaceProvEntry 1 }

mscVRouteInterfaceEgressAudioGain OBJECT-TYPE
   SYNTAX     INTEGER (-12..12)
   ACCESS     read-write
   STATUS     mandatory
   DESCRIPTION
     "This attribute specifies the gain in dB that is applied to data leaving 
      the network. It applies to voice, modem and fax traffic. For 
      example, egress gain is applied to audio data going to a PBX. If 
      egressAudioGain is negative, a loss is applied.
      
      ingressAudioGain and egressAudioGain are used in loss planning, 
      which is the configuration of the devices in the network to ensure 
      that the signal level from any point in the network to any other point 
      is correct. 
      
      egressAudioGain is ignored for calls running on 1pDS1V and 
      1pE1V cards. For calls running on these cards, egress audio gain is 
      determined by the audioGain attribute in the appropriate Vncs/m 
      VoiceProfile/n."
   DEFVAL     { 0 }
::= { mscVRouteInterfaceProvEntry 2 }

mscVRouteInterfaceTandemPassThrough OBJECT-TYPE
   SYNTAX     INTEGER  {
                 disabled(0),
                 enabled(1) }
   ACCESS     read-write
   STATUS     mandatory
   DESCRIPTION
     "This attribute specifies whether tandem pass through is desired. If 
      tandemPassThrough is enabled, tandem pass through is used if 
      possible. If tandemPassThrough is disabled, tandem pass through is 
      not used under any circumstances. The actual state of tandem pass 
      through is indicated in Vsr Svs Framer tptStatus.
      
      The negotiated tandem pass through is available in Vsr Svs Framer 
      negotiatedTandemPassThrough.
      
      Tandem pass through is not supported on 1pDS1V and 1pE1V 
      cards, so tandemPassThrough is ignored on these cards."
   DEFVAL     { disabled }
::= { mscVRouteInterfaceProvEntry 3 }

mscVRouteInterfaceEchoCancellation OBJECT-TYPE
   SYNTAX     INTEGER  {
                 off(0),
                 on(1) }
   ACCESS     read-write
   STATUS     obsolete
   DESCRIPTION
     "This attribute has been migrated to echoCancellation."
   DEFVAL     { on }
::= { mscVRouteInterfaceProvEntry 5 }

mscVRouteInterfaceComfortNoiseCap OBJECT-TYPE
   SYNTAX     INTEGER (-78 | -65 | -60 | -54 | -52 | -50 | -48 | -46 | -44 | -42 | -40)
   ACCESS     read-write
   STATUS     mandatory
   DESCRIPTION
     "This attribute specifies the maximum level at which comfort noise is 
      generated. The comfort noise is limited by comfortNoiseCap before 
      egressAudioGain is applied. The default value of -40 dBm0 equates 
      to the maximum level of comfort noise available and effectively 
      disables the comfortNoiseCap."
   DEFVAL     { -40 }
::= { mscVRouteInterfaceProvEntry 6 }

mscVRouteInterfaceSpeechHangoverTime OBJECT-TYPE
   SYNTAX     Unsigned32 (10..500)
   ACCESS     read-write
   STATUS     mandatory
   DESCRIPTION
     "This attribute specifies the time after the end of speech before 
      silence suppression starts. It applies only to voice traffic. It is not 
      used unless Vsr Svs Framer negotiatedSilenceSuppression is on, 
      congested or slowAndCongested.
      
      Higher values of speechHangoverTime reduce undesirable clipping 
      but increase bandwidth usage.
      
      speechHangoverTime is not used on DS1V, E1V, 1pDS1V, 1pE1V 
      and J2MV cards."
   DEFVAL     { 150 }
::= { mscVRouteInterfaceProvEntry 7 }

mscVRouteInterfaceFaxHangoverTimeG711G726 OBJECT-TYPE
   SYNTAX     Unsigned32 (300..20000)
   ACCESS     read-write
   STATUS     mandatory
   DESCRIPTION
     "This attribute specifies the time after the end of fax traffic before 
      G.711/G.726 fax idle suppression starts. It applies only if the 
      negotiated fax encoding, available in Vsr Svs Framer 
      negotiatedEncoding, is g711, g726 or g711G726 and Vsr Svs 
      Framer negotiatedFisG711G726 is on.
      
      Higher values of faxHangoverTimeG711G726 reduce undesirable 
      clipping but increase bandwidth usage.
      
      faxHangoverTimeG711G726 is not used on DS1V, E1V, 1pDS1V, 
      1pE1V and J2MV cards."
   DEFVAL     { 1000 }
::= { mscVRouteInterfaceProvEntry 8 }

mscVRouteInterfaceModemFaxSpeechDiscrim OBJECT-TYPE
   SYNTAX     INTEGER  {
                 off(0),
                 on(1) }
   ACCESS     read-write
   STATUS     mandatory
   DESCRIPTION
     "This attribute specifies whether this VoiceRoute differentiates 
      between modemFax traffic and speech. If modemFaxSpeechDiscrim 
      is on and a false 2100 Hz tone is detected, any Svs using this route 
      reverts to speech mode when speech is detected.
      
      modemFaxSpeechDiscrim is not used on DS1V, E1V, 1pDS1V, 
      1pE1V and J2MV cards."
   DEFVAL     { on }
::= { mscVRouteInterfaceProvEntry 9 }

mscVRouteInterfaceEchoTailDelay OBJECT-TYPE
   SYNTAX     Unsigned32 (32 | 64)
   ACCESS     read-write
   STATUS     mandatory
   DESCRIPTION
     "This attribute specifies the maximum echo canceller tail delay 
      coverage. It should be selected higher than the summation of the 
      round trip delay of echo and hybrid response time. A 32 msec 
      setting is good for a radius of 2700 km, assuming that the signal is 
      going through 4 exchanges and the hybrid response time is 6 msec. 
      A 64 msec setting offers even greater coverage (more distance or 
      more switches), with comparable convergence time. The 
      recommended setting is 64 msec. This attribute is not used on 
      DS1V, E1V, 1pDS1V, 1pE1V, J2MV, 1pE1Mvp, 1pDS1Mvp, or 
      1pTTC2mMvp card."
   DEFVAL     { 64 }
::= { mscVRouteInterfaceProvEntry 10 }

mscVRouteInterfaceEchoReturnLoss OBJECT-TYPE
   SYNTAX     Unsigned32 (0 | 3 | 6)
   ACCESS     read-write
   STATUS     mandatory
   DESCRIPTION
     "This attribute specifies the echo return loss parameter of the echo 
      canceller. 0 db is the normal value for most line conditions. If the 
      line quality is poor, in terms of echo, selecting a higher value may 
      allow the echo canceller to perform better. A side effect is that the 
      voice level is attenuated by the same amount, which may not always 
      be acceptable. This attribute is not used on DS1V, E1V, 1pDS1V, 
      1pE1V, J2MV, 1pE1Mvp, 1pDS1Mvp, or 1pTTC2mMvp card."
   DEFVAL     { 0 }
::= { mscVRouteInterfaceProvEntry 11 }

mscVRouteInterfaceEcanBypassMode OBJECT-TYPE
   SYNTAX     INTEGER  {
                 g164(0),
                 g165(1),
                 never(2) }
   ACCESS     read-write
   STATUS     mandatory
   DESCRIPTION
     "This attribute specifies when version 2 internal echo cancellers are 
      placed in bypass mode on this VoiceRoute.  This attribute only 
      applies if v2 of echoCancellation is on. If ecanBypassMode is g165, 
      the internal echo canceller is placed in bypass mode as per ITU-T 
      G.165. If ecanBypassMode is g164, the internal echo canceller is 
      placed in bypass mode as per ITU-T G.164. If ecanBypassMode is 
      never, the internal echo canceller is never placed in bypass mode. 
      This mode should only be used for debugging.
      
      This attribute does not apply to 1pE1V, 1pDS1V, J2MV, 1pE1Mvp, 
      1pDS1Mvp or 1pTTC2mMvp cards."
   DEFVAL     { g165 }
::= { mscVRouteInterfaceProvEntry 15 }

mscVRouteInterfaceStructuredEchoCancellationTable OBJECT-TYPE
   SYNTAX     SEQUENCE OF MscVRouteInterfaceStructuredEchoCancellationEntry
   ACCESS     not-accessible
   STATUS     mandatory
   DESCRIPTION
     "This attribute specifies whether echo cancellation is performed on 
      this VoiceRoute. v1 specifies whether echo cancellation is 
      performed by version 1 internal echo cancellers. v2 specifes 
      whether echo cancellation is performed by version 2 echo 
      cancellers. If echoCancellation is on, the internal echo canceller is 
      enabled and echo cancellation is performed. If echoCancellation is 
      off, the internal echo canceller is placed in transparent bypass mode 
      and echo cancellation is never performed."
::= { mscVRouteInterface 474 }

mscVRouteInterfaceStructuredEchoCancellationEntry OBJECT-TYPE
   SYNTAX     MscVRouteInterfaceStructuredEchoCancellationEntry
   ACCESS     not-accessible
   STATUS     mandatory
   DESCRIPTION
     "An entry in the mscVRouteInterfaceStructuredEchoCancellationTable."
   INDEX {
      mscVRouteIndex,
      mscVRouteInterfaceIndex,
      mscVRouteInterfaceStructuredEchoCancellationIndex }
::= { mscVRouteInterfaceStructuredEchoCancellationTable 1 }

MscVRouteInterfaceStructuredEchoCancellationEntry ::= SEQUENCE {
   mscVRouteInterfaceStructuredEchoCancellationIndex
      INTEGER,
   mscVRouteInterfaceStructuredEchoCancellationValue
      INTEGER }

mscVRouteInterfaceStructuredEchoCancellationIndex OBJECT-TYPE
   SYNTAX     INTEGER  {
                 v1(0),
                 v2(1) }
   ACCESS     not-accessible
   STATUS     mandatory
   DESCRIPTION
     "This variable represents the mscVRouteInterfaceStructuredEchoCancellationTable
      specific index for the mscVRouteInterfaceStructuredEchoCancellationTable."
::= { mscVRouteInterfaceStructuredEchoCancellationEntry 1 }

mscVRouteInterfaceStructuredEchoCancellationValue OBJECT-TYPE
   SYNTAX     INTEGER  {
                 off(0),
                 on(1) }
   ACCESS     read-write
   STATUS     mandatory
   DESCRIPTION
     "This variable represents an individual value for the
      mscVRouteInterfaceStructuredEchoCancellationTable."
::= { mscVRouteInterfaceStructuredEchoCancellationEntry 2 }


-- vroute/n Dna
-- This is the description of the VRoute Dna component. It offers a 
-- subset of the generic Dna component attributes.

mscVRouteDna OBJECT IDENTIFIER ::= { mscVRoute 4 }



mscVRouteDnaRowStatusTable OBJECT-TYPE
   SYNTAX     SEQUENCE OF MscVRouteDnaRowStatusEntry
   ACCESS     not-accessible
   STATUS     mandatory
   DESCRIPTION
     "This entry controls the addition and deletion of 
      mscVRouteDna components."
::= { mscVRouteDna 1 }

mscVRouteDnaRowStatusEntry OBJECT-TYPE
   SYNTAX     MscVRouteDnaRowStatusEntry
   ACCESS     not-accessible
   STATUS     mandatory
   DESCRIPTION
     "A single entry in the table represents a single 
      mscVRouteDna component."
   INDEX {
      mscVRouteIndex,
      mscVRouteDnaIndex }
::= { mscVRouteDnaRowStatusTable 1 }

MscVRouteDnaRowStatusEntry ::= SEQUENCE {
   mscVRouteDnaRowStatus
      RowStatus,
   mscVRouteDnaComponentName
      DisplayString,
   mscVRouteDnaStorageType
      StorageType,
   mscVRouteDnaIndex
      NonReplicated }

mscVRouteDnaRowStatus OBJECT-TYPE
   SYNTAX     RowStatus 
   ACCESS     read-only
   STATUS     mandatory
   DESCRIPTION
     "This variable is used as the basis for SNMP naming of
      mscVRouteDna components.
      These components cannot be added nor deleted."
::= { mscVRouteDnaRowStatusEntry 1 }

mscVRouteDnaComponentName OBJECT-TYPE
   SYNTAX     DisplayString 
   ACCESS     read-only
   STATUS     mandatory
   DESCRIPTION
     "This variable provides the component's string name for
      use with the ASCII Console Interface"
::= { mscVRouteDnaRowStatusEntry 2 }

mscVRouteDnaStorageType OBJECT-TYPE
   SYNTAX     StorageType 
   ACCESS     read-only
   STATUS     mandatory
   DESCRIPTION
     "This variable represents the storage type value for the
      mscVRouteDna tables."
::= { mscVRouteDnaRowStatusEntry 4 }

mscVRouteDnaIndex OBJECT-TYPE
   SYNTAX     NonReplicated 
   ACCESS     not-accessible
   STATUS     mandatory
   DESCRIPTION
     "This variable represents the index for the mscVRouteDna tables."
::= { mscVRouteDnaRowStatusEntry 10 }

mscVRouteDnaAddressTable OBJECT-TYPE
   SYNTAX     SEQUENCE OF MscVRouteDnaAddressEntry
   ACCESS     not-accessible
   STATUS     mandatory
   DESCRIPTION
     "Address group contains attributes common to all Dna's. Every Dna 
      used in the network is defined with this group of 2 attributes. String 
      of address digits is complemented by type of address and Npi. 
      These attributes are used to interpret format of the address digits."
::= { mscVRouteDna 10 }

mscVRouteDnaAddressEntry OBJECT-TYPE
   SYNTAX     MscVRouteDnaAddressEntry
   ACCESS     not-accessible
   STATUS     mandatory
   DESCRIPTION
     "An entry in the mscVRouteDnaAddressTable."
   INDEX {
      mscVRouteIndex,
      mscVRouteDnaIndex }
::= { mscVRouteDnaAddressTable 1 }

MscVRouteDnaAddressEntry ::= SEQUENCE {
   mscVRouteDnaNumberingPlanIndicator
      INTEGER,
   mscVRouteDnaDataNetworkAddress
      DigitString }

mscVRouteDnaNumberingPlanIndicator OBJECT-TYPE
   SYNTAX     INTEGER  {
                 x121(0),
                 e164(1) }
   ACCESS     read-write
   STATUS     mandatory
   DESCRIPTION
     "This attribute indicates the Numbering Plan Indicator (NPI) of the 
      Dna that is entered. Address may belong to X.121 or E.164 plans. 
      X.121 is used in packet svitched data networks."
   DEFVAL     { e164 }
::= { mscVRouteDnaAddressEntry 1 }

mscVRouteDnaDataNetworkAddress OBJECT-TYPE
   SYNTAX     DigitString (SIZE (0..15))
   ACCESS     read-write
   STATUS     mandatory
   DESCRIPTION
     "Dna attribute contains digits which form unique identifier of the 
      customer interface. It can be compared (approximation only) to 
      telephone number where phone number identifies unique telephone 
      set. Dna digits are selected and assigned by network operators."
::= { mscVRouteDnaAddressEntry 2 }


-- Vroute/n VoiceAccounting
-- The VoiceAccounting component defines the operational 
-- characteristics of the accounting system of the Vroute component. 
-- Accounting record generation for calls on the Vroute is managed by 
-- this component.

mscVRouteAcct OBJECT IDENTIFIER ::= { mscVRoute 5 }



mscVRouteAcctRowStatusTable OBJECT-TYPE
   SYNTAX     SEQUENCE OF MscVRouteAcctRowStatusEntry
   ACCESS     not-accessible
   STATUS     mandatory
   DESCRIPTION
     "This entry controls the addition and deletion of 
      mscVRouteAcct components."
::= { mscVRouteAcct 1 }

mscVRouteAcctRowStatusEntry OBJECT-TYPE
   SYNTAX     MscVRouteAcctRowStatusEntry
   ACCESS     not-accessible
   STATUS     mandatory
   DESCRIPTION
     "A single entry in the table represents a single 
      mscVRouteAcct component."
   INDEX {
      mscVRouteIndex,
      mscVRouteAcctIndex }
::= { mscVRouteAcctRowStatusTable 1 }

MscVRouteAcctRowStatusEntry ::= SEQUENCE {
   mscVRouteAcctRowStatus
      RowStatus,
   mscVRouteAcctComponentName
      DisplayString,
   mscVRouteAcctStorageType
      StorageType,
   mscVRouteAcctIndex
      NonReplicated }

mscVRouteAcctRowStatus OBJECT-TYPE
   SYNTAX     RowStatus 
   ACCESS     read-only
   STATUS     mandatory
   DESCRIPTION
     "This variable is used as the basis for SNMP naming of
      mscVRouteAcct components.
      These components cannot be added nor deleted."
::= { mscVRouteAcctRowStatusEntry 1 }

mscVRouteAcctComponentName OBJECT-TYPE
   SYNTAX     DisplayString 
   ACCESS     read-only
   STATUS     mandatory
   DESCRIPTION
     "This variable provides the component's string name for
      use with the ASCII Console Interface"
::= { mscVRouteAcctRowStatusEntry 2 }

mscVRouteAcctStorageType OBJECT-TYPE
   SYNTAX     StorageType 
   ACCESS     read-only
   STATUS     mandatory
   DESCRIPTION
     "This variable represents the storage type value for the
      mscVRouteAcct tables."
::= { mscVRouteAcctRowStatusEntry 4 }

mscVRouteAcctIndex OBJECT-TYPE
   SYNTAX     NonReplicated 
   ACCESS     not-accessible
   STATUS     mandatory
   DESCRIPTION
     "This variable represents the index for the mscVRouteAcct tables."
::= { mscVRouteAcctRowStatusEntry 10 }

mscVRouteAcctProvTable OBJECT-TYPE
   SYNTAX     SEQUENCE OF MscVRouteAcctProvEntry
   ACCESS     not-accessible
   STATUS     mandatory
   DESCRIPTION
     "This group contains the provisionable attributes of a 
      VoiceAccounting component."
::= { mscVRouteAcct 2 }

mscVRouteAcctProvEntry OBJECT-TYPE
   SYNTAX     MscVRouteAcctProvEntry
   ACCESS     not-accessible
   STATUS     mandatory
   DESCRIPTION
     "An entry in the mscVRouteAcctProvTable."
   INDEX {
      mscVRouteIndex,
      mscVRouteAcctIndex }
::= { mscVRouteAcctProvTable 1 }

MscVRouteAcctProvEntry ::= SEQUENCE {
   mscVRouteAcctAccountCollection
      OCTET STRING,
   mscVRouteAcctAccountClass
      Unsigned32,
   mscVRouteAcctServiceExchange
      Unsigned32,
   mscVRouteAcctDigitsSuppressed
      Unsigned32,
   mscVRouteAcctAccountingOptions
      OCTET STRING }

mscVRouteAcctAccountCollection OBJECT-TYPE
   SYNTAX     OCTET STRING (SIZE (1))
   ACCESS     read-write
   STATUS     mandatory
   DESCRIPTION
     "This attribute specifies that accounting records are to be collected 
      for the various reasons: bill, test, study, audit.  The last of the 
      parameters, force, specifies that accounting records are to be 
      collected irrespective of other collection reasons.  If none of these 
      reasons is set, then accounting will be suppressed.

      Description of bits:
      bill(0)
      test(1)
      study(2)
      audit(3)
      force(4)"
::= { mscVRouteAcctProvEntry 2 }

mscVRouteAcctAccountClass OBJECT-TYPE
   SYNTAX     Unsigned32 (0..255)
   ACCESS     read-write
   STATUS     mandatory
   DESCRIPTION
     "This attribute specifies the accounting class which is reserved for 
      network operations usage. Its value is returned in the accounting 
      record in the local and remote service type attributes. The use of 
      this attribute is decided by the network operator."
   DEFVAL     { 0 }
::= { mscVRouteAcctProvEntry 3 }

mscVRouteAcctServiceExchange OBJECT-TYPE
   SYNTAX     Unsigned32 (0..255)
   ACCESS     read-write
   STATUS     mandatory
   DESCRIPTION
     "This attribute specifies  a user defined value, Data Service 
      Exchange, as entered by the network operator and reported in the 
      accounting record."
   DEFVAL     { 0 }
::= { mscVRouteAcctProvEntry 4 }

mscVRouteAcctDigitsSuppressed OBJECT-TYPE
   SYNTAX     Unsigned32 (0..8)
   ACCESS     read-write
   STATUS     mandatory
   DESCRIPTION
     "This attribute specifies the number of trailing digits which will be 
      suppressed in the calledNumber in the accounting records. Each of 
      the specified number of trailing digits are replaced with an 'X'. 
      This option exists to satisfy privacy requirements in a number of 
      countries."
   DEFVAL     { 0 }
::= { mscVRouteAcctProvEntry 5 }

mscVRouteAcctAccountingOptions OBJECT-TYPE
   SYNTAX     OCTET STRING (SIZE (1))
   ACCESS     read-write
   STATUS     mandatory
   DESCRIPTION
     "This attribute specifies optional settings for the voice networking 
      accounting system. The options are:
      suppressTerminatingEndRecords - setting this option suppresses 
      the generation of accounting records at the destination node. This 
      reduces the volume of accounting data. This option has local 
      significance only. It only suppresses the generation of accounting 
      records for calls received by this node.

      Description of bits:
      notused0(0)
      suppressTerminatingEndRecords(1)"
::= { mscVRouteAcctProvEntry 6 }


-- VoiceSubroute/n		
-- A VoiceSubroute component defines the characteristics of the 
-- connection to a Private Branch Exchange (PBX). A VoiceSubroute 
-- is a collection of 64 kbit/s channels on the same physical DS1 or E1 
-- interface. Typically there is one VoiceSubroute per physical link. 

mscVsr OBJECT IDENTIFIER ::= { mscComponents 117 }



mscVsrRowStatusTable OBJECT-TYPE
   SYNTAX     SEQUENCE OF MscVsrRowStatusEntry
   ACCESS     not-accessible
   STATUS     mandatory
   DESCRIPTION
     "This entry controls the addition and deletion of 
      mscVsr components."
::= { mscVsr 1 }

mscVsrRowStatusEntry OBJECT-TYPE
   SYNTAX     MscVsrRowStatusEntry
   ACCESS     not-accessible
   STATUS     mandatory
   DESCRIPTION
     "A single entry in the table represents a single 
      mscVsr component."
   INDEX {
      mscVsrIndex }
::= { mscVsrRowStatusTable 1 }

MscVsrRowStatusEntry ::= SEQUENCE {
   mscVsrRowStatus
      RowStatus,
   mscVsrComponentName
      DisplayString,
   mscVsrStorageType
      StorageType,
   mscVsrIndex
      Integer32 }

mscVsrRowStatus OBJECT-TYPE
   SYNTAX     RowStatus 
   ACCESS     read-write
   STATUS     mandatory
   DESCRIPTION
     "This variable is used as the basis for SNMP naming of
      mscVsr components.
      These components can be added and deleted."
::= { mscVsrRowStatusEntry 1 }

mscVsrComponentName OBJECT-TYPE
   SYNTAX     DisplayString 
   ACCESS     read-only
   STATUS     mandatory
   DESCRIPTION
     "This variable provides the component's string name for
      use with the ASCII Console Interface"
::= { mscVsrRowStatusEntry 2 }

mscVsrStorageType OBJECT-TYPE
   SYNTAX     StorageType 
   ACCESS     read-only
   STATUS     mandatory
   DESCRIPTION
     "This variable represents the storage type value for the
      mscVsr tables."
::= { mscVsrRowStatusEntry 4 }

mscVsrIndex OBJECT-TYPE
   SYNTAX     Integer32 (1..255)
   ACCESS     not-accessible
   STATUS     mandatory
   DESCRIPTION
     "This variable represents the index for the mscVsr tables."
::= { mscVsrRowStatusEntry 10 }

mscVsrCidDataTable OBJECT-TYPE
   SYNTAX     SEQUENCE OF MscVsrCidDataEntry
   ACCESS     not-accessible
   STATUS     mandatory
   DESCRIPTION
     "This group contains the attribute for a component's Customer 
      Identifier (CID). Refer to the attribute description for a detailed 
      explanation of CIDs."
::= { mscVsr 10 }

mscVsrCidDataEntry OBJECT-TYPE
   SYNTAX     MscVsrCidDataEntry
   ACCESS     not-accessible
   STATUS     mandatory
   DESCRIPTION
     "An entry in the mscVsrCidDataTable."
   INDEX {
      mscVsrIndex }
::= { mscVsrCidDataTable 1 }

MscVsrCidDataEntry ::= SEQUENCE {
   mscVsrCustomerIdentifier
      Unsigned32 }

mscVsrCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { mscVsrCidDataEntry 1 }

mscVsrIfEntryTable OBJECT-TYPE
   SYNTAX     SEQUENCE OF MscVsrIfEntryEntry
   ACCESS     not-accessible
   STATUS     mandatory
   DESCRIPTION
     "This group contains the provisionable attributes for the ifEntry."
::= { mscVsr 11 }

mscVsrIfEntryEntry OBJECT-TYPE
   SYNTAX     MscVsrIfEntryEntry
   ACCESS     not-accessible
   STATUS     mandatory
   DESCRIPTION
     "An entry in the mscVsrIfEntryTable."
   INDEX {
      mscVsrIndex }
::= { mscVsrIfEntryTable 1 }

MscVsrIfEntryEntry ::= SEQUENCE {
   mscVsrIfAdminStatus
      INTEGER,
   mscVsrIfIndex
      InterfaceIndex }

mscVsrIfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { mscVsrIfEntryEntry 1 }

mscVsrIfIndex OBJECT-TYPE
   SYNTAX     InterfaceIndex (1..65535)
   ACCESS     read-only
   STATUS     mandatory
   DESCRIPTION
     "This is the index for the IfEntry. Its value is automatically initialized 
      during the provisioning process."
::= { mscVsrIfEntryEntry 2 }

mscVsrProvTable OBJECT-TYPE
   SYNTAX     SEQUENCE OF MscVsrProvEntry
   ACCESS     not-accessible
   STATUS     mandatory
   DESCRIPTION
     "This group represents the provisionable attributes of a 
      VoiceSubroute."
::= { mscVsr 12 }

mscVsrProvEntry OBJECT-TYPE
   SYNTAX     MscVsrProvEntry
   ACCESS     not-accessible
   STATUS     mandatory
   DESCRIPTION
     "An entry in the mscVsrProvTable."
   INDEX {
      mscVsrIndex }
::= { mscVsrProvTable 1 }

MscVsrProvEntry ::= SEQUENCE {
   mscVsrCommentText
      AsciiString,
   mscVsrVoiceRoute
      Link,
   mscVsrSignallingChannel
      Link }

mscVsrCommentText OBJECT-TYPE
   SYNTAX     AsciiString (SIZE (0..40))
   ACCESS     read-write
   STATUS     mandatory
   DESCRIPTION
     "Use of this attribute is at the discretion of the system administrator. 
      Typically, it specifies the name of the customer that is using this 
      VoiceSubroute. Typical use of this attribute is to store customer 
      name."
::= { mscVsrProvEntry 1 }

mscVsrVoiceRoute OBJECT-TYPE
   SYNTAX     Link 
   ACCESS     read-write
   STATUS     mandatory
   DESCRIPTION
     "This attribute specifies the VoiceRoute component that this 
      VoiceSubroute belongs to."
::= { mscVsrProvEntry 3 }

mscVsrSignallingChannel OBJECT-TYPE
   SYNTAX     Link 
   ACCESS     read-write
   STATUS     mandatory
   DESCRIPTION
     "This attribute specifies the signalling channel to be used by the 
      VoiceSubroute."
::= { mscVsrProvEntry 311 }

mscVsrStateTable OBJECT-TYPE
   SYNTAX     SEQUENCE OF MscVsrStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscVsr 13 }

mscVsrStateEntry OBJECT-TYPE
   SYNTAX     MscVsrStateEntry
   ACCESS     not-accessible
   STATUS     mandatory
   DESCRIPTION
     "An entry in the mscVsrStateTable."
   INDEX {
      mscVsrIndex }
::= { mscVsrStateTable 1 }

MscVsrStateEntry ::= SEQUENCE {
   mscVsrAdminState
      INTEGER,
   mscVsrOperationalState
      INTEGER,
   mscVsrUsageState
      INTEGER }

mscVsrAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscVsrStateEntry 1 }

mscVsrOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscVsrStateEntry 2 }

mscVsrUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscVsrStateEntry 3 }

mscVsrOperStatusTable OBJECT-TYPE
   SYNTAX     SEQUENCE OF MscVsrOperStatusEntry
   ACCESS     not-accessible
   STATUS     mandatory
   DESCRIPTION
     "This group includes the Operational Status attribute. This attribute 
      defines the current operational state of this component."
::= { mscVsr 14 }

mscVsrOperStatusEntry OBJECT-TYPE
   SYNTAX     MscVsrOperStatusEntry
   ACCESS     not-accessible
   STATUS     mandatory
   DESCRIPTION
     "An entry in the mscVsrOperStatusTable."
   INDEX {
      mscVsrIndex }
::= { mscVsrOperStatusTable 1 }

MscVsrOperStatusEntry ::= SEQUENCE {
   mscVsrSnmpOperStatus
      INTEGER }

mscVsrSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { mscVsrOperStatusEntry 1 }

mscVsrStatsTable OBJECT-TYPE
   SYNTAX     SEQUENCE OF MscVsrStatsEntry
   ACCESS     not-accessible
   STATUS     mandatory
   DESCRIPTION
     "This group provides the operational statistics for the VoiceSubroute 
      component."
::= { mscVsr 15 }

mscVsrStatsEntry OBJECT-TYPE
   SYNTAX     MscVsrStatsEntry
   ACCESS     not-accessible
   STATUS     mandatory
   DESCRIPTION
     "An entry in the mscVsrStatsTable."
   INDEX {
      mscVsrIndex }
::= { mscVsrStatsTable 1 }

MscVsrStatsEntry ::= SEQUENCE {
   mscVsrTotalCallsFromIf
      Counter32,
   mscVsrTotalFailedCallsFromIf
      Counter32,
   mscVsrInvalidNumberingPlanCalls
      Counter32,
   mscVsrAddressResolutionFailedCalls
      Counter32,
   mscVsrAddressIncompleteCalls
      Counter32,
   mscVsrPathAttributesNotMetCalls
      Counter32,
   mscVsrPathSetupTimeOutCalls
      Counter32,
   mscVsrCallsRejectedLocally
      Counter32,
   mscVsrCallsRejectedByFarEnd
      Counter32 }

mscVsrTotalCallsFromIf OBJECT-TYPE
   SYNTAX     Counter32 
   ACCESS     read-only
   STATUS     mandatory
   DESCRIPTION
     "This attribute indicates the total number of calls that have been 
      received by this VoiceSubroute from the PBX.
      The value wraps to zero when it reaches its maximum."
::= { mscVsrStatsEntry 1 }

mscVsrTotalFailedCallsFromIf OBJECT-TYPE
   SYNTAX     Counter32 
   ACCESS     read-only
   STATUS     mandatory
   DESCRIPTION
     "This attribute counts indicates the total number of calls that have 
      been received by this VoiceSubroute from the PBX which failed to 
      be successfully routed through the subnet for various reasons.
      The value wraps to zero when it reaches its maximum."
::= { mscVsrStatsEntry 2 }

mscVsrInvalidNumberingPlanCalls OBJECT-TYPE
   SYNTAX     Counter32 
   ACCESS     read-only
   STATUS     mandatory
   DESCRIPTION
     "This attribute counts the calls from the interface for which the type 
      of number and the numbering plan identification was not associated 
      to an access code. The numbering plan types noAccessCode, 
      accessCode1 and accessCode2 are provisioned in the VoiceRoute. 
      Refer to NTP-241-7001-xxx for more information.
      The value wraps to zero when it reaches its maximum."
::= { mscVsrStatsEntry 3 }

mscVsrAddressResolutionFailedCalls OBJECT-TYPE
   SYNTAX     Counter32 
   ACCESS     read-only
   STATUS     mandatory
   DESCRIPTION
     "This attribute counts the calls from the interface which had dialled 
      numbers that had no entry in the VoiceNetworkingCallServer data 
      base.
      The value wraps to zero when it reaches its maximum."
::= { mscVsrStatsEntry 4 }

mscVsrAddressIncompleteCalls OBJECT-TYPE
   SYNTAX     Counter32 
   ACCESS     read-only
   STATUS     mandatory
   DESCRIPTION
     "This attribute counts the calls from the interface which had dialled 
      numbers with insufficient digits to resolve to a unique entry in the 
      VoiceNetworkingCallServer data base.
      The value wraps to zero when it reaches its maximum."
::= { mscVsrStatsEntry 5 }

mscVsrPathAttributesNotMetCalls OBJECT-TYPE
   SYNTAX     Counter32 
   ACCESS     read-only
   STATUS     mandatory
   DESCRIPTION
     "This attribute counts the calls from the interface for which a path to 
      the end point could not be established based on the attributes 
      specified in the VoiceProfile.
      The value wraps to zero when it reaches its maximum."
::= { mscVsrStatsEntry 6 }

mscVsrPathSetupTimeOutCalls OBJECT-TYPE
   SYNTAX     Counter32 
   ACCESS     read-only
   STATUS     mandatory
   DESCRIPTION
     "This attribute counts the calls from the interface for which a path to 
      the end point could not be established due to a subnet path setup 
      time-out.
      The value wraps to zero when it reaches its maximum."
::= { mscVsrStatsEntry 7 }

mscVsrCallsRejectedLocally OBJECT-TYPE
   SYNTAX     Counter32 
   ACCESS     read-only
   STATUS     mandatory
   DESCRIPTION
     "This attribute counts the calls from the interface which were 
      rejected by the originating end because it was:
      1) a data call on a voice only VoiceRoute, or
      2) a voice call on a data only VoiceRoute, or 
      3) a data call to an end-point whose VoiceProfile prevents data calls 
      from being made.
      The value wraps to zero when it reaches its maximum."
::= { mscVsrStatsEntry 8 }

mscVsrCallsRejectedByFarEnd OBJECT-TYPE
   SYNTAX     Counter32 
   ACCESS     read-only
   STATUS     mandatory
   DESCRIPTION
     "This attribute counts the calls from the interface which were 
      rejected by the far-end. This rejection could be due to:
      1) no free channels at the end-point, or 
      2) a voice call going to a data only VoiceRoute, or 
      3) a data call going to a voice only VoiceRoute, or 
      4) a signalling protocol incompatibility between end-points.
      The value wraps to zero when it reaches its maximum."
::= { mscVsrStatsEntry 9 }

mscVsrOperTable OBJECT-TYPE
   SYNTAX     SEQUENCE OF MscVsrOperEntry
   ACCESS     not-accessible
   STATUS     mandatory
   DESCRIPTION
     "This group provides the operational attributes for the VoiceSubroute 
      component."
::= { mscVsr 16 }

mscVsrOperEntry OBJECT-TYPE
   SYNTAX     MscVsrOperEntry
   ACCESS     not-accessible
   STATUS     mandatory
   DESCRIPTION
     "An entry in the mscVsrOperTable."
   INDEX {
      mscVsrIndex }
::= { mscVsrOperTable 1 }

MscVsrOperEntry ::= SEQUENCE {
   mscVsrActiveChannels
      Counter32,
   mscVsrPeakActiveChannels
      Counter32,
   mscVsrActiveVoiceChannels
      Counter32,
   mscVsrActiveModemChannels
      Counter32,
   mscVsrActiveDataChannels
      Counter32,
   mscVsrPeakActiveVoiceChannels
      Counter32,
   mscVsrPeakActiveModemChannels
      Counter32,
   mscVsrPeakActiveDataChannels
      Counter32,
   mscVsrActiveFaxRelayChannels
      Gauge32,
   mscVsrActiveTptChannels
      Gauge32,
   mscVsrPeakActiveFaxRelayChannels
      Gauge32,
   mscVsrPeakActiveTptChannels
      Gauge32 }

mscVsrActiveChannels OBJECT-TYPE
   SYNTAX     Counter32 
   ACCESS     read-only
   STATUS     mandatory
   DESCRIPTION
     "This attribute indicates the total number of B-channels that 
      currently have active calls."
::= { mscVsrOperEntry 2 }

mscVsrPeakActiveChannels OBJECT-TYPE
   SYNTAX     Counter32 
   ACCESS     read-only
   STATUS     mandatory
   DESCRIPTION
     "This attribute indicates the peak number of B-channels that were 
      active during the previous polling period."
::= { mscVsrOperEntry 3 }

mscVsrActiveVoiceChannels OBJECT-TYPE
   SYNTAX     Counter32 
   ACCESS     read-only
   STATUS     mandatory
   DESCRIPTION
     "This attribute indicates the number of B-channels that are currently 
      carrying voice."
::= { mscVsrOperEntry 4 }

mscVsrActiveModemChannels OBJECT-TYPE
   SYNTAX     Counter32 
   ACCESS     read-only
   STATUS     mandatory
   DESCRIPTION
     "This attribute indicates the number of B-channels that are currently 
      active, where a 2100Hz tone was detected."
::= { mscVsrOperEntry 5 }

mscVsrActiveDataChannels OBJECT-TYPE
   SYNTAX     Counter32 
   ACCESS     read-only
   STATUS     mandatory
   DESCRIPTION
     "This attribute indicates the number of B-channels that are currently 
      active carrying data."
::= { mscVsrOperEntry 6 }

mscVsrPeakActiveVoiceChannels OBJECT-TYPE
   SYNTAX     Counter32 
   ACCESS     read-only
   STATUS     mandatory
   DESCRIPTION
     "This attribute indicates the peak number of B-channels that were 
      active carrying voice during the previous polling period."
::= { mscVsrOperEntry 7 }

mscVsrPeakActiveModemChannels OBJECT-TYPE
   SYNTAX     Counter32 
   ACCESS     read-only
   STATUS     mandatory
   DESCRIPTION
     "This attribute indicates the peak number of active B-channels that a 
      2100Hz tone was detected during the previous polling period."
::= { mscVsrOperEntry 8 }

mscVsrPeakActiveDataChannels OBJECT-TYPE
   SYNTAX     Counter32 
   ACCESS     read-only
   STATUS     mandatory
   DESCRIPTION
     "This attribute indicates the maximum number of B-channels that 
      were active carrying data during the previous polling period."
::= { mscVsrOperEntry 9 }

mscVsrActiveFaxRelayChannels OBJECT-TYPE
   SYNTAX     Gauge32 (0..30)
   ACCESS     read-only
   STATUS     mandatory
   DESCRIPTION
     "This attribute indicates the number of B-channels that are currently 
      performing fax relay."
::= { mscVsrOperEntry 10 }

mscVsrActiveTptChannels OBJECT-TYPE
   SYNTAX     Gauge32 (0..32)
   ACCESS     read-only
   STATUS     mandatory
   DESCRIPTION
     "This attribute indicates the number of B-channels that are currently 
      performing tandem pass through."
::= { mscVsrOperEntry 11 }

mscVsrPeakActiveFaxRelayChannels OBJECT-TYPE
   SYNTAX     Gauge32 (0..30)
   ACCESS     read-only
   STATUS     mandatory
   DESCRIPTION
     "This attribute indicates the peak number of B-channels that 
      performed fax relay during the previous polling period."
::= { mscVsrOperEntry 12 }

mscVsrPeakActiveTptChannels OBJECT-TYPE
   SYNTAX     Gauge32 (0..30)
   ACCESS     read-only
   STATUS     mandatory
   DESCRIPTION
     "This attribute indicates the peak number of B-channels that 
      performed tandem pass through during the previous polling period."
::= { mscVsrOperEntry 13 }


-- Vsr/n SwitchedVoiceService/n		
-- The SwitchedVoiceService component defines the operational 
-- characteristics of the connection to a Private Branch Exchange 
-- (PBX). One instance of this component must be required for each 
-- channel (that is, timeslot) which is part of the VoiceSubroute.

mscVsrSvs OBJECT IDENTIFIER ::= { mscVsr 2 }



mscVsrSvsRowStatusTable OBJECT-TYPE
   SYNTAX     SEQUENCE OF MscVsrSvsRowStatusEntry
   ACCESS     not-accessible
   STATUS     mandatory
   DESCRIPTION
     "This entry controls the addition and deletion of 
      mscVsrSvs components."
::= { mscVsrSvs 1 }

mscVsrSvsRowStatusEntry OBJECT-TYPE
   SYNTAX     MscVsrSvsRowStatusEntry
   ACCESS     not-accessible
   STATUS     mandatory
   DESCRIPTION
     "A single entry in the table represents a single 
      mscVsrSvs component."
   INDEX {
      mscVsrIndex,
      mscVsrSvsIndex }
::= { mscVsrSvsRowStatusTable 1 }

MscVsrSvsRowStatusEntry ::= SEQUENCE {
   mscVsrSvsRowStatus
      RowStatus,
   mscVsrSvsComponentName
      DisplayString,
   mscVsrSvsStorageType
      StorageType,
   mscVsrSvsIndex
      Integer32 }

mscVsrSvsRowStatus OBJECT-TYPE
   SYNTAX     RowStatus 
   ACCESS     read-write
   STATUS     mandatory
   DESCRIPTION
     "This variable is used as the basis for SNMP naming of
      mscVsrSvs components.
      These components can be added and deleted."
::= { mscVsrSvsRowStatusEntry 1 }

mscVsrSvsComponentName OBJECT-TYPE
   SYNTAX     DisplayString 
   ACCESS     read-only
   STATUS     mandatory
   DESCRIPTION
     "This variable provides the component's string name for
      use with the ASCII Console Interface"
::= { mscVsrSvsRowStatusEntry 2 }

mscVsrSvsStorageType OBJECT-TYPE
   SYNTAX     StorageType 
   ACCESS     read-only
   STATUS     mandatory
   DESCRIPTION
     "This variable represents the storage type value for the
      mscVsrSvs tables."
::= { mscVsrSvsRowStatusEntry 4 }

mscVsrSvsIndex OBJECT-TYPE
   SYNTAX     Integer32 (1..32)
   ACCESS     not-accessible
   STATUS     mandatory
   DESCRIPTION
     "This variable represents the index for the mscVsrSvs tables."
::= { mscVsrSvsRowStatusEntry 10 }

mscVsrSvsIfEntryTable OBJECT-TYPE
   SYNTAX     SEQUENCE OF MscVsrSvsIfEntryEntry
   ACCESS     not-accessible
   STATUS     mandatory
   DESCRIPTION
     "This group contains the provisionable attributes for the ifEntry."
::= { mscVsrSvs 11 }

mscVsrSvsIfEntryEntry OBJECT-TYPE
   SYNTAX     MscVsrSvsIfEntryEntry
   ACCESS     not-accessible
   STATUS     mandatory
   DESCRIPTION
     "An entry in the mscVsrSvsIfEntryTable."
   INDEX {
      mscVsrIndex,
      mscVsrSvsIndex }
::= { mscVsrSvsIfEntryTable 1 }

MscVsrSvsIfEntryEntry ::= SEQUENCE {
   mscVsrSvsIfAdminStatus
      INTEGER,
   mscVsrSvsIfIndex
      InterfaceIndex }

mscVsrSvsIfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { mscVsrSvsIfEntryEntry 1 }

mscVsrSvsIfIndex OBJECT-TYPE
   SYNTAX     InterfaceIndex (1..65535)
   ACCESS     read-only
   STATUS     mandatory
   DESCRIPTION
     "This is the index for the IfEntry. Its value is automatically initialized 
      during the provisioning process."
::= { mscVsrSvsIfEntryEntry 2 }

mscVsrSvsOperTable OBJECT-TYPE
   SYNTAX     SEQUENCE OF MscVsrSvsOperEntry
   ACCESS     not-accessible
   STATUS     mandatory
   DESCRIPTION
     "This group provides the operational attributes for the 
      SwitchedVoiceService component."
::= { mscVsrSvs 12 }

mscVsrSvsOperEntry OBJECT-TYPE
   SYNTAX     MscVsrSvsOperEntry
   ACCESS     not-accessible
   STATUS     mandatory
   DESCRIPTION
     "An entry in the mscVsrSvsOperTable."
   INDEX {
      mscVsrIndex,
      mscVsrSvsIndex }
::= { mscVsrSvsOperTable 1 }

MscVsrSvsOperEntry ::= SEQUENCE {
   mscVsrSvsStatus
      INTEGER,
   mscVsrSvsProfileNumber
      Counter32,
   mscVsrSvsCallType
      INTEGER,
   mscVsrSvsCalledNumber
      DigitString,
   mscVsrSvsCallingNumber
      DigitString,
   mscVsrSvsClearCauseCode
      Hex }

mscVsrSvsStatus OBJECT-TYPE
   SYNTAX     INTEGER  {
                 idle(0),
                 seized(1),
                 answered(2),
                 clearing(3),
                 lockout(4),
                 idleMaintenance(5) }
   ACCESS     read-only
   STATUS     mandatory
   DESCRIPTION
     "This attribute indicates the current state of the channel. 
      idle means that there is no call currently active on this channel.
      seized means that the channel is currently setting up a call, but a 
      connect message has not been received.
      answered means that a connect message has been received.
      clearing means that the call is being taken down.
      lockout means that due to glare or channel rejection, the channel is 
      available for ingress calls only. That is, either the PBX and the 
      Passport tried to seize the channel for a call at the same time (glare), 
      or the PBX rejected the Passport seizure.
      idleMaintenance means that due to explicit channel maintenance 
      messages, the channel is not available for egress calls. This can only 
      happen when the protocol control places the channel into a 
      maintenance state, and only happens if the Passport receives a 
      message causing the channel state change such as the SERVICE 
      maintenance message."
::= { mscVsrSvsOperEntry 1 }

mscVsrSvsProfileNumber OBJECT-TYPE
   SYNTAX     Counter32 
   ACCESS     read-only
   STATUS     mandatory
   DESCRIPTION
     "This attribute indicates the VoiceProfile number that is being used 
      for this call. If no call is active, then it displays the value of the last 
      profile used."
::= { mscVsrSvsOperEntry 2 }

mscVsrSvsCallType OBJECT-TYPE
   SYNTAX     INTEGER  {
                 voice(0),
                 data(1),
                 modem(2) }
   ACCESS     read-only
   STATUS     mandatory
   DESCRIPTION
     "This attribute indicates the type of call that this channel is currently 
      carrying. If no call is active, then it displays the value for the last 
      call."
::= { mscVsrSvsOperEntry 3 }

mscVsrSvsCalledNumber OBJECT-TYPE
   SYNTAX     DigitString (SIZE (1..32))
   ACCESS     read-only
   STATUS     mandatory
   DESCRIPTION
     "This attribute indicates the dialled number that is active on this 
      channel. If no call is active, then it displays the dialled number from 
      the last call."
::= { mscVsrSvsOperEntry 4 }

mscVsrSvsCallingNumber OBJECT-TYPE
   SYNTAX     DigitString (SIZE (1..16))
   ACCESS     read-only
   STATUS     mandatory
   DESCRIPTION
     "This attribute indicates the originator's number for the currently 
      active call. If no call is active, then it displays the originator's 
      number from the last call."
::= { mscVsrSvsOperEntry 5 }

mscVsrSvsClearCauseCode OBJECT-TYPE
   SYNTAX     Hex (0..127)
   ACCESS     read-only
   STATUS     mandatory
   DESCRIPTION
     "This attribute indicates the clear cause code of the call. This code is 
      always the Q.931 code, regardless of the access protocol."
::= { mscVsrSvsOperEntry 6 }

mscVsrSvsStatsTable OBJECT-TYPE
   SYNTAX     SEQUENCE OF MscVsrSvsStatsEntry
   ACCESS     not-accessible
   STATUS     mandatory
   DESCRIPTION
     "This group provides the operational attributes for the 
      SwitchedVoiceService component."
::= { mscVsrSvs 13 }

mscVsrSvsStatsEntry OBJECT-TYPE
   SYNTAX     MscVsrSvsStatsEntry
   ACCESS     not-accessible
   STATUS     mandatory
   DESCRIPTION
     "An entry in the mscVsrSvsStatsTable."
   INDEX {
      mscVsrIndex,
      mscVsrSvsIndex }
::= { mscVsrSvsStatsTable 1 }

MscVsrSvsStatsEntry ::= SEQUENCE {
   mscVsrSvsTotalCalls
      Counter32,
   mscVsrSvsTotalCallSeconds
      Counter32 }

mscVsrSvsTotalCalls OBJECT-TYPE
   SYNTAX     Counter32 
   ACCESS     read-only
   STATUS     mandatory
   DESCRIPTION
     "This attribute counts the call attempts processed on this channel (in 
      both directions). This counter includes the number of unsuccessful 
      as well as successful call attempts.
      The value wraps when it reaches its maximum."
::= { mscVsrSvsStatsEntry 1 }

mscVsrSvsTotalCallSeconds OBJECT-TYPE
   SYNTAX     Counter32 
   ACCESS     read-only
   STATUS     mandatory
   DESCRIPTION
     "This attribute indicates the total number of seconds that this channel 
      is handling a call. This is regardless of whether the call is successful 
      or not. In other words, this is the amount of time that the channel is 
      not in the idle state.
      The value wraps when it reaches its maximum."
::= { mscVsrSvsStatsEntry 2 }

mscVsrSvsStateTable OBJECT-TYPE
   SYNTAX     SEQUENCE OF MscVsrSvsStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscVsrSvs 14 }

mscVsrSvsStateEntry OBJECT-TYPE
   SYNTAX     MscVsrSvsStateEntry
   ACCESS     not-accessible
   STATUS     mandatory
   DESCRIPTION
     "An entry in the mscVsrSvsStateTable."
   INDEX {
      mscVsrIndex,
      mscVsrSvsIndex }
::= { mscVsrSvsStateTable 1 }

MscVsrSvsStateEntry ::= SEQUENCE {
   mscVsrSvsAdminState
      INTEGER,
   mscVsrSvsOperationalState
      INTEGER,
   mscVsrSvsUsageState
      INTEGER }

mscVsrSvsAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscVsrSvsStateEntry 1 }

mscVsrSvsOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscVsrSvsStateEntry 2 }

mscVsrSvsUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscVsrSvsStateEntry 3 }

mscVsrSvsOperStatusTable OBJECT-TYPE
   SYNTAX     SEQUENCE OF MscVsrSvsOperStatusEntry
   ACCESS     not-accessible
   STATUS     mandatory
   DESCRIPTION
     "This group includes the Operational Status attribute. This attribute 
      defines the current operational state of this component."
::= { mscVsrSvs 15 }

mscVsrSvsOperStatusEntry OBJECT-TYPE
   SYNTAX     MscVsrSvsOperStatusEntry
   ACCESS     not-accessible
   STATUS     mandatory
   DESCRIPTION
     "An entry in the mscVsrSvsOperStatusTable."
   INDEX {
      mscVsrIndex,
      mscVsrSvsIndex }
::= { mscVsrSvsOperStatusTable 1 }

MscVsrSvsOperStatusEntry ::= SEQUENCE {
   mscVsrSvsSnmpOperStatus
      INTEGER }

mscVsrSvsSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { mscVsrSvsOperStatusEntry 1 }


-- Vsr/n Svs/n Framer
-- The Framer component controls link layer framing for application 
-- components sending and receiving data on a link interface. It is also 
-- through Framer, that an application component is associated with a 
-- specific hardware link interface.
-- The Framer component provides provisionable attributes related to 
-- datapath aspects of the hardware interface rather than interface 
-- specific attributes (such as modem leads and clocking) which are 
-- associated with specific hardware components (such as E1 or DS1).
-- The Framer component also provides a provisionable attribute 
-- which binds the application component to a specific hardware 
-- component.
-- The Framer component contains operational attributes for link 
-- interface datapath statistics (such as frame counts).

mscVsrSvsFramer OBJECT IDENTIFIER ::= { mscVsrSvs 2 }



mscVsrSvsFramerRowStatusTable OBJECT-TYPE
   SYNTAX     SEQUENCE OF MscVsrSvsFramerRowStatusEntry
   ACCESS     not-accessible
   STATUS     mandatory
   DESCRIPTION
     "This entry controls the addition and deletion of 
      mscVsrSvsFramer components."
::= { mscVsrSvsFramer 1 }

mscVsrSvsFramerRowStatusEntry OBJECT-TYPE
   SYNTAX     MscVsrSvsFramerRowStatusEntry
   ACCESS     not-accessible
   STATUS     mandatory
   DESCRIPTION
     "A single entry in the table represents a single 
      mscVsrSvsFramer component."
   INDEX {
      mscVsrIndex,
      mscVsrSvsIndex,
      mscVsrSvsFramerIndex }
::= { mscVsrSvsFramerRowStatusTable 1 }

MscVsrSvsFramerRowStatusEntry ::= SEQUENCE {
   mscVsrSvsFramerRowStatus
      RowStatus,
   mscVsrSvsFramerComponentName
      DisplayString,
   mscVsrSvsFramerStorageType
      StorageType,
   mscVsrSvsFramerIndex
      NonReplicated }

mscVsrSvsFramerRowStatus OBJECT-TYPE
   SYNTAX     RowStatus 
   ACCESS     read-only
   STATUS     mandatory
   DESCRIPTION
     "This variable is used as the basis for SNMP naming of
      mscVsrSvsFramer components.
      These components cannot be added nor deleted."
::= { mscVsrSvsFramerRowStatusEntry 1 }

mscVsrSvsFramerComponentName OBJECT-TYPE
   SYNTAX     DisplayString 
   ACCESS     read-only
   STATUS     mandatory
   DESCRIPTION
     "This variable provides the component's string name for
      use with the ASCII Console Interface"
::= { mscVsrSvsFramerRowStatusEntry 2 }

mscVsrSvsFramerStorageType OBJECT-TYPE
   SYNTAX     StorageType 
   ACCESS     read-only
   STATUS     mandatory
   DESCRIPTION
     "This variable represents the storage type value for the
      mscVsrSvsFramer tables."
::= { mscVsrSvsFramerRowStatusEntry 4 }

mscVsrSvsFramerIndex OBJECT-TYPE
   SYNTAX     NonReplicated 
   ACCESS     not-accessible
   STATUS     mandatory
   DESCRIPTION
     "This variable represents the index for the mscVsrSvsFramer tables."
::= { mscVsrSvsFramerRowStatusEntry 10 }

mscVsrSvsFramerProvTable OBJECT-TYPE
   SYNTAX     SEQUENCE OF MscVsrSvsFramerProvEntry
   ACCESS     not-accessible
   STATUS     mandatory
   DESCRIPTION
     "This group contains the base provisioning data for the Framer 
      component. Application or hardware interface specific provisioning 
      data is contained in other provisionable Framer groups."
::= { mscVsrSvsFramer 10 }

mscVsrSvsFramerProvEntry OBJECT-TYPE
   SYNTAX     MscVsrSvsFramerProvEntry
   ACCESS     not-accessible
   STATUS     mandatory
   DESCRIPTION
     "An entry in the mscVsrSvsFramerProvTable."
   INDEX {
      mscVsrIndex,
      mscVsrSvsIndex,
      mscVsrSvsFramerIndex }
::= { mscVsrSvsFramerProvTable 1 }

MscVsrSvsFramerProvEntry ::= SEQUENCE {
   mscVsrSvsFramerInterfaceName
      Link }

mscVsrSvsFramerInterfaceName OBJECT-TYPE
   SYNTAX     Link 
   ACCESS     read-write
   STATUS     mandatory
   DESCRIPTION
     "This attribute contains a hardware component name.
      
      The attribute associates the application with a specific link. This 
      defines the module processor on which Framer's parent component 
      (as well as Framer itself) will run."
::= { mscVsrSvsFramerProvEntry 1 }

mscVsrSvsFramerStateTable OBJECT-TYPE
   SYNTAX     SEQUENCE OF MscVsrSvsFramerStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscVsrSvsFramer 14 }

mscVsrSvsFramerStateEntry OBJECT-TYPE
   SYNTAX     MscVsrSvsFramerStateEntry
   ACCESS     not-accessible
   STATUS     mandatory
   DESCRIPTION
     "An entry in the mscVsrSvsFramerStateTable."
   INDEX {
      mscVsrIndex,
      mscVsrSvsIndex,
      mscVsrSvsFramerIndex }
::= { mscVsrSvsFramerStateTable 1 }

MscVsrSvsFramerStateEntry ::= SEQUENCE {
   mscVsrSvsFramerAdminState
      INTEGER,
   mscVsrSvsFramerOperationalState
      INTEGER,
   mscVsrSvsFramerUsageState
      INTEGER }

mscVsrSvsFramerAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscVsrSvsFramerStateEntry 1 }

mscVsrSvsFramerOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscVsrSvsFramerStateEntry 2 }

mscVsrSvsFramerUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscVsrSvsFramerStateEntry 3 }

mscVsrSvsFramerStatsTable OBJECT-TYPE
   SYNTAX     SEQUENCE OF MscVsrSvsFramerStatsEntry
   ACCESS     not-accessible
   STATUS     mandatory
   DESCRIPTION
     "This group contains the operational statistics data for a Framer 
      component."
::= { mscVsrSvsFramer 15 }

mscVsrSvsFramerStatsEntry OBJECT-TYPE
   SYNTAX     MscVsrSvsFramerStatsEntry
   ACCESS     not-accessible
   STATUS     mandatory
   DESCRIPTION
     "An entry in the mscVsrSvsFramerStatsTable."
   INDEX {
      mscVsrIndex,
      mscVsrSvsIndex,
      mscVsrSvsFramerIndex }
::= { mscVsrSvsFramerStatsTable 1 }

MscVsrSvsFramerStatsEntry ::= SEQUENCE {
   mscVsrSvsFramerTotalCells
      Unsigned32,
   mscVsrSvsFramerAudioCells
      Unsigned32,
   mscVsrSvsFramerSilenceCells
      Unsigned32,
   mscVsrSvsFramerModemCells
      Unsigned32,
   mscVsrSvsFramerCurrentEncodingRate
      INTEGER,
   mscVsrSvsFramerLrcErrors
      Unsigned32,
   mscVsrSvsFramerFrmLostInNetwork
      Unsigned32,
   mscVsrSvsFramerFrmUnderRuns
      Unsigned32,
   mscVsrSvsFramerFrmDumped
      Unsigned32,
   mscVsrSvsFramerModemSilenceCells
      Counter32,
   mscVsrSvsFramerCurrentEncoding
      INTEGER,
   mscVsrSvsFramerTptStatus
      INTEGER,
   mscVsrSvsFramerFaxRelayCells
      Counter32,
   mscVsrSvsFramerModemFaxCells
      Unsigned32,
   mscVsrSvsFramerFaxIdleCells
      Counter32 }

mscVsrSvsFramerTotalCells OBJECT-TYPE
   SYNTAX     Unsigned32 (0..4294967295)
   ACCESS     read-only
   STATUS     mandatory
   DESCRIPTION
     "This attribute counts the total number of cells received from the 
      interface.
      Each cell contains 44 bytes of data from the DS0 channel. Since a 
      DS0 provides data at 64 kbit/s, each cell contains 5.5 ms of audio 
      data.
      This data flow is measured before compression is performed on the 
      channel.
      This counter wraps to zero after reaching its maximum value."
::= { mscVsrSvsFramerStatsEntry 1 }

mscVsrSvsFramerAudioCells OBJECT-TYPE
   SYNTAX     Unsigned32 (0..4294967295)
   ACCESS     read-only
   STATUS     mandatory
   DESCRIPTION
     "This attribute counts the total number of cells containing audio data 
      received from the interface while the channel was seized. A CCS 
      channel is always considered to be seized. Audio data includes cells 
      containing voice as well modem audio, but not silence. 
      A cell contains 44 bytes of data from the DS0 channel(5.5 ms).
      This flow is measured before compression is performed on the 
      channel.
      This counter wraps to zero after reaching its maximum value."
::= { mscVsrSvsFramerStatsEntry 2 }

mscVsrSvsFramerSilenceCells OBJECT-TYPE
   SYNTAX     Unsigned32 (0..4294967295)
   ACCESS     read-only
   STATUS     mandatory
   DESCRIPTION
     "This attribute counts the total number of cells containing silence 
      data received from the interface which was not forwarded into the 
      network, thus saving bandwidth. A channel may go into silence due 
      to the operation of the silence suppression feature or for CAS 
      channels when the ABCD signalling bits go idle.
      A cell contains 44 bytes of data from the DS0 channel(5.5 ms).
      This flow is measured before compression is performed on the 
      channel.
      This counter wraps to zero after reaching its maximum value."
::= { mscVsrSvsFramerStatsEntry 4 }

mscVsrSvsFramerModemCells OBJECT-TYPE
   SYNTAX     Unsigned32 (0..4294967295)
   ACCESS     read-only
   STATUS     obsolete
   DESCRIPTION
     "This attribute is migrated into modemFaxCells."
::= { mscVsrSvsFramerStatsEntry 5 }

mscVsrSvsFramerCurrentEncodingRate OBJECT-TYPE
   SYNTAX     INTEGER  {
                 n640(1),
                 n320(2),
                 n240(3),
                 n160(4),
                 n80(5),
                 n144(6),
                 n120(7),
                 n96(8),
                 n72(9),
                 n63(10),
                 n53(11),
                 n48(12),
                 n24(13),
                 n12(14),
                 n03(15) }
   ACCESS     read-only
   STATUS     obsolete
   DESCRIPTION
     "This attribute has been migrated to currentRate in Operational 
      group."
::= { mscVsrSvsFramerStatsEntry 6 }

mscVsrSvsFramerLrcErrors OBJECT-TYPE
   SYNTAX     Unsigned32 (0..4294967295)
   ACCESS     read-only
   STATUS     mandatory
   DESCRIPTION
     "This attribute counts the number of frames received from the 
      network with LRC errors."
::= { mscVsrSvsFramerStatsEntry 7 }

mscVsrSvsFramerFrmLostInNetwork OBJECT-TYPE
   SYNTAX     Unsigned32 (0..4294967295)
   ACCESS     read-only
   STATUS     mandatory
   DESCRIPTION
     "This attribute counts the number of frames which the service knows 
      it did not receive from the network although they were sent in to the 
      network from the far end."
::= { mscVsrSvsFramerStatsEntry 8 }

mscVsrSvsFramerFrmUnderRuns OBJECT-TYPE
   SYNTAX     Unsigned32 (0..4294967295)
   ACCESS     read-only
   STATUS     mandatory
   DESCRIPTION
     "This attribute counts the number of times that a frame was needed 
      but was not available because it had been delayed too long in the 
      network.
      This error may occur repeatedly if the interface clocks at the two 
      access points to the network are operating at different rates."
::= { mscVsrSvsFramerStatsEntry 9 }

mscVsrSvsFramerFrmDumped OBJECT-TYPE
   SYNTAX     Unsigned32 (0..4294967295)
   ACCESS     read-only
   STATUS     mandatory
   DESCRIPTION
     "This attribute counts the number of frames which have been 
      dumped because the output queue grew too large. This can occur if 
      the clock rate on the incoming interface is faster than the clock rate 
      on the outgoing interface and there are no silence periods to absorb 
      the difference, or when a compression rate change occurs.
      This count wraps to zero after reaching its maximum value."
::= { mscVsrSvsFramerStatsEntry 10 }

mscVsrSvsFramerModemSilenceCells OBJECT-TYPE
   SYNTAX     Counter32 
   ACCESS     read-only
   STATUS     obsolete
   DESCRIPTION
     "This attribute is migrated into faxIdleCells."
::= { mscVsrSvsFramerStatsEntry 26 }

mscVsrSvsFramerCurrentEncoding OBJECT-TYPE
   SYNTAX     INTEGER  {
                 g729(1),
                 g728(2),
                 g723(3),
                 g726(4),
                 g711(5),
                 v22(32),
                 v22bis(33),
                 faxRelay(64),
                 v27(65),
                 v29(66),
                 v17(67),
                 none(255) }
   ACCESS     read-only
   STATUS     obsolete
   DESCRIPTION
     "This attribute has been migrated to currentEncoding in Operational 
      group."
::= { mscVsrSvsFramerStatsEntry 27 }

mscVsrSvsFramerTptStatus OBJECT-TYPE
   SYNTAX     INTEGER  {
                 operating(0),
                 rejected(1),
                 monitoring(2),
                 disabled(3) }
   ACCESS     read-only
   STATUS     obsolete
   DESCRIPTION
     "This attribute has been migrated to tptStatus in Operational group."
::= { mscVsrSvsFramerStatsEntry 28 }

mscVsrSvsFramerFaxRelayCells OBJECT-TYPE
   SYNTAX     Counter32 
   ACCESS     read-only
   STATUS     mandatory
   DESCRIPTION
     "This attribute counts the total number of fax relay cells sent to the 
      network.
      
      This counter wraps to zero after reaching its maximum value."
::= { mscVsrSvsFramerStatsEntry 35 }

mscVsrSvsFramerModemFaxCells OBJECT-TYPE
   SYNTAX     Unsigned32 (0..4294967295)
   ACCESS     read-only
   STATUS     mandatory
   DESCRIPTION
     "This attribute counts the total number of cells containing modem 
      data received from the interface while the channel was seized. A 
      CCS channel is always considered to be seized. Cells are considered 
      to be modem data if a constant energy level above          -25 dBmO 
      is detected for more than 900 ms. An energy level below -36 dBmO 
      for more than 650 ms is required to detect that the modem is no 
      longer present. 
      A cell contains 44 bytes of data from the DS0 channel (5.5 ms).
      This flow is measured before compression is performed on the 
      channel.
      This counter wraps to zero after reaching its maximum value."
::= { mscVsrSvsFramerStatsEntry 36 }

mscVsrSvsFramerFaxIdleCells OBJECT-TYPE
   SYNTAX     Counter32 
   ACCESS     read-only
   STATUS     mandatory
   DESCRIPTION
     "This attribute counts the total number of cells containing silent fax 
      data received from the interface which were not forwarded into the 
      network, thus saving bandwidth. A channel may go into silence due 
      to the silence Suppression feature or for CAS channels when the 
      ABCD signalling bits go idle.
      
      A cell contains 44 bytes of data from the DS0 channel (5.5 ms). 
      This flow is measured before compression is performed on the 
      channel.
      
      This counter wraps to zero after reaching its maximum value."
::= { mscVsrSvsFramerStatsEntry 37 }

mscVsrSvsFramerOperTable OBJECT-TYPE
   SYNTAX     SEQUENCE OF MscVsrSvsFramerOperEntry
   ACCESS     not-accessible
   STATUS     mandatory
   DESCRIPTION
     "This group contains the operational data for a Svs Framer."
::= { mscVsrSvsFramer 16 }

mscVsrSvsFramerOperEntry OBJECT-TYPE
   SYNTAX     MscVsrSvsFramerOperEntry
   ACCESS     not-accessible
   STATUS     mandatory
   DESCRIPTION
     "An entry in the mscVsrSvsFramerOperTable."
   INDEX {
      mscVsrIndex,
      mscVsrSvsIndex,
      mscVsrSvsFramerIndex }
::= { mscVsrSvsFramerOperTable 1 }

MscVsrSvsFramerOperEntry ::= SEQUENCE {
   mscVsrSvsFramerOpCurrentEncoding
      INTEGER,
   mscVsrSvsFramerCurrentRate
      INTEGER,
   mscVsrSvsFramerOpTptStatus
      INTEGER }

mscVsrSvsFramerOpCurrentEncoding OBJECT-TYPE
   SYNTAX     INTEGER  {
                 g729(1),
                 g728(2),
                 g723(3),
                 g726(4),
                 g711(5),
                 v22(32),
                 v22bis(33),
                 faxRelay(64),
                 v27(65),
                 v29(66),
                 v17(67),
                 none(255) }
   ACCESS     read-only
   STATUS     mandatory
   DESCRIPTION
     "This attribute indicates the encoding currently being performed on 
      this channel. g711 indicates that pulse code modulation (PCM) 
      defined by ITU-T G.711 is being performed. g726 indicates that 
      adaptive differential pulse code modulation (ADPCM) defined by 
      ITU-T G.726 is being performed. g728 indicates that the Low Delay 
      Coded Excited Linear Predictive Coder (LD-CELP) algorithm 
      defined by ITU-T G.728 is being performed. g729 indicates that the 
      Conjunctive Structure Algebraic Code Excited Linear Predictive 
      Coder (CS-ACELP) algorithm defined by ITU-T G.729 is being 
      performed. v27 indicates that the algorithm defined by ITU-T V.27 
      is being performed. v29 indicates that the algorithm defined by 
      ITU-T V.29 is being performed."
::= { mscVsrSvsFramerOperEntry 1 }

mscVsrSvsFramerCurrentRate OBJECT-TYPE
   SYNTAX     INTEGER  {
                 n0(0),
                 n640(1),
                 n320(2),
                 n240(3),
                 n160(4),
                 n80(5),
                 n144(6),
                 n120(7),
                 n96(8),
                 n72(9),
                 n63(10),
                 n53(11),
                 n48(12),
                 n24(13),
                 n12(14),
                 n03(15) }
   ACCESS     read-only
   STATUS     mandatory
   DESCRIPTION
     "This attribute indicates the current encoding rate for frames being 
      sent to the network."
::= { mscVsrSvsFramerOperEntry 2 }

mscVsrSvsFramerOpTptStatus OBJECT-TYPE
   SYNTAX     INTEGER  {
                 operating(0),
                 monitoring(2),
                 disabled(3) }
   ACCESS     read-only
   STATUS     mandatory
   DESCRIPTION
     "This attribute indicates the current status of the tandem pass through 
      algorithm. If tptStatus is operating, the tandem pass through 
      algorithm is cutting through a voice switch. If tptStatus is 
      monitoring, negotiatedTandemPassThrough is enabled, but the 
      tandem pass through algorithm is not cutting through a voice 
      switch. If tptStatus is disabled, negotiatedTandemPassThrough is 
      disabled."
::= { mscVsrSvsFramerOperEntry 3 }

mscVsrSvsFramerNegTable OBJECT-TYPE
   SYNTAX     SEQUENCE OF MscVsrSvsFramerNegEntry
   ACCESS     not-accessible
   STATUS     mandatory
   DESCRIPTION
     "This group contains the attributes indicating the results of voice 
      networking end to end negotiation."
::= { mscVsrSvsFramer 17 }

mscVsrSvsFramerNegEntry OBJECT-TYPE
   SYNTAX     MscVsrSvsFramerNegEntry
   ACCESS     not-accessible
   STATUS     mandatory
   DESCRIPTION
     "An entry in the mscVsrSvsFramerNegTable."
   INDEX {
      mscVsrIndex,
      mscVsrSvsIndex,
      mscVsrSvsFramerIndex }
::= { mscVsrSvsFramerNegTable 1 }

MscVsrSvsFramerNegEntry ::= SEQUENCE {
   mscVsrSvsFramerNegotiatedSilenceSuppression
      INTEGER,
   mscVsrSvsFramerNegotiatedFisG711G726
      INTEGER,
   mscVsrSvsFramerNegotiatedDtmfRegeneration
      INTEGER,
   mscVsrSvsFramerNegotiatedV17AsG711G726
      INTEGER,
   mscVsrSvsFramerNegotiatedTandemPassThrough
      INTEGER }

mscVsrSvsFramerNegotiatedSilenceSuppression OBJECT-TYPE
   SYNTAX     INTEGER  {
                 off(0),
                 on(1),
                 congested(2),
                 slow(3),
                 slowAndCongested(4) }
   ACCESS     read-write
   STATUS     mandatory
   DESCRIPTION
     "This attribute indicates the result of negotiating silence suppression 
      with the remote end across the subnet. The parameter used for 
      negotiating with the remote end is provisioned in Vncs Vp 
      silenceSuppression.
      
      If negotiatedSilenceSuppression is off, silence suppression is never 
      performed.
      If negotiatedSilenceSuppression is on, silence suppression is always 
      performed.
      If negotiatedSilenceSuppression is congested, silence suppression is 
      performed only when the network is congested.
      If negotiatedSilenceSuppression is slow, silence suppression begins 
      after 10 to 20 seconds without any speech or audio being detected.
      If negotiatedSilenceSuppression is slowAndCongested, both the 
      slow and congested options are applied."
::= { mscVsrSvsFramerNegEntry 1 }

mscVsrSvsFramerNegotiatedFisG711G726 OBJECT-TYPE
   SYNTAX     INTEGER  {
                 off(0),
                 on(1) }
   ACCESS     read-write
   STATUS     mandatory
   DESCRIPTION
     "This attribute indicates the result of negotiating G.711/G.726 fax 
      idle suppression with the remote end across the subnet. The 
      parameter used for negotiating with the remote end is provisioned in 
      Vncs Vp faxIdleSuppressionG711G726."
::= { mscVsrSvsFramerNegEntry 2 }

mscVsrSvsFramerNegotiatedDtmfRegeneration OBJECT-TYPE
   SYNTAX     INTEGER  {
                 off(0),
                 on(1) }
   ACCESS     read-write
   STATUS     mandatory
   DESCRIPTION
     "This attribute indicates the result of negotiating DTMF regeneration 
      with the remote end across the subnet. The parameter used for 
      negotiating with the remote end is provisioned in Vncs Vp 
      dtmfRegeneration.
      
      If negotiatedDtmfRegeneration is on, DTMF tones received from 
      the link are first converted to digits before being sent to the subnet. 
      When a digit is received from the subnet, its respective DTMF tone 
      is generated before being sent to the link. 
      
      If negotiatedDtmfRegeneration is off, DTMF tones are transported 
      transparently."
::= { mscVsrSvsFramerNegEntry 3 }

mscVsrSvsFramerNegotiatedV17AsG711G726 OBJECT-TYPE
   SYNTAX     INTEGER  {
                 no(0),
                 yes(1) }
   ACCESS     read-only
   STATUS     mandatory
   DESCRIPTION
     "This attribute indicates how this SwitchedVoiceService negotiates 
      with V.17 fax machines, as determined by negotiation with the 
      remote end across the subnet. The parameter used for negotiating 
      with the remote end is provisioned in Vncs Vp 
      v17EncodedAsG711G726.
      
      If negotiatedV17AsG711G726 is no, V.17 fax machines are 
      instructed to use V.29, and V.29 fax traffic sent by fax machines is 
      demodulated and encoded using fax relay.
      
      If negotiatedV17AsG711G726 is yes, V.17 fax machines are 
      permitted to use V.17 and V.17 fax traffic sent by fax machines is 
      encoded using G.711 or G.726, at the rates given in 
      negotiatedRates."
::= { mscVsrSvsFramerNegEntry 4 }

mscVsrSvsFramerNegotiatedTandemPassThrough OBJECT-TYPE
   SYNTAX     INTEGER  {
                 disabled(0),
                 enabled(1) }
   ACCESS     read-only
   STATUS     mandatory
   DESCRIPTION
     "This attribute indicates the result of negotiating tandem pass 
      through with the remote end across the subnet. The parameter used 
      for negotiating with the remote end is provisioned in Vncs Vp 
      tandemPassThrough."
::= { mscVsrSvsFramerNegEntry 5 }

mscVsrSvsFramerFrmToNetworkTable OBJECT-TYPE
   SYNTAX     SEQUENCE OF MscVsrSvsFramerFrmToNetworkEntry
   ACCESS     not-accessible
   STATUS     mandatory
   DESCRIPTION
     "This attribute counts the number of frames sent to the network at 
      each encoding rate. Fax relay cells are not included."
::= { mscVsrSvsFramer 315 }

mscVsrSvsFramerFrmToNetworkEntry OBJECT-TYPE
   SYNTAX     MscVsrSvsFramerFrmToNetworkEntry
   ACCESS     not-accessible
   STATUS     mandatory
   DESCRIPTION
     "An entry in the mscVsrSvsFramerFrmToNetworkTable."
   INDEX {
      mscVsrIndex,
      mscVsrSvsIndex,
      mscVsrSvsFramerIndex,
      mscVsrSvsFramerFrmToNetworkIndex }
::= { mscVsrSvsFramerFrmToNetworkTable 1 }

MscVsrSvsFramerFrmToNetworkEntry ::= SEQUENCE {
   mscVsrSvsFramerFrmToNetworkIndex
      INTEGER,
   mscVsrSvsFramerFrmToNetworkValue
      Unsigned32 }

mscVsrSvsFramerFrmToNetworkIndex OBJECT-TYPE
   SYNTAX     INTEGER  {
                 n64KbitS(0),
                 n32KbitS(1),
                 n24KbitS(2),
                 n16KbitS(3),
                 n8KbitS(4) }
   ACCESS     not-accessible
   STATUS     mandatory
   DESCRIPTION
     "This variable represents the mscVsrSvsFramerFrmToNetworkTable
      specific index for the mscVsrSvsFramerFrmToNetworkTable."
::= { mscVsrSvsFramerFrmToNetworkEntry 1 }

mscVsrSvsFramerFrmToNetworkValue OBJECT-TYPE
   SYNTAX     Unsigned32 (0..4294967295)
   ACCESS     read-only
   STATUS     mandatory
   DESCRIPTION
     "This variable represents an individual value for the
      mscVsrSvsFramerFrmToNetworkTable."
::= { mscVsrSvsFramerFrmToNetworkEntry 2 }

mscVsrSvsFramerFrmFromNetworkTable OBJECT-TYPE
   SYNTAX     SEQUENCE OF MscVsrSvsFramerFrmFromNetworkEntry
   ACCESS     not-accessible
   STATUS     mandatory
   DESCRIPTION
     "This attribute counts the number of frames received from the 
      network at each encoding rate."
::= { mscVsrSvsFramer 316 }

mscVsrSvsFramerFrmFromNetworkEntry OBJECT-TYPE
   SYNTAX     MscVsrSvsFramerFrmFromNetworkEntry
   ACCESS     not-accessible
   STATUS     mandatory
   DESCRIPTION
     "An entry in the mscVsrSvsFramerFrmFromNetworkTable."
   INDEX {
      mscVsrIndex,
      mscVsrSvsIndex,
      mscVsrSvsFramerIndex,
      mscVsrSvsFramerFrmFromNetworkIndex }
::= { mscVsrSvsFramerFrmFromNetworkTable 1 }

MscVsrSvsFramerFrmFromNetworkEntry ::= SEQUENCE {
   mscVsrSvsFramerFrmFromNetworkIndex
      INTEGER,
   mscVsrSvsFramerFrmFromNetworkValue
      Unsigned32 }

mscVsrSvsFramerFrmFromNetworkIndex OBJECT-TYPE
   SYNTAX     INTEGER  {
                 n64KbitS(0),
                 n32KbitS(1),
                 n24KbitS(2),
                 n16KbitS(3),
                 n8KbitS(4) }
   ACCESS     not-accessible
   STATUS     mandatory
   DESCRIPTION
     "This variable represents the mscVsrSvsFramerFrmFromNetworkTable
      specific index for the mscVsrSvsFramerFrmFromNetworkTable."
::= { mscVsrSvsFramerFrmFromNetworkEntry 1 }

mscVsrSvsFramerFrmFromNetworkValue OBJECT-TYPE
   SYNTAX     Unsigned32 (0..4294967295)
   ACCESS     read-only
   STATUS     mandatory
   DESCRIPTION
     "This variable represents an individual value for the
      mscVsrSvsFramerFrmFromNetworkTable."
::= { mscVsrSvsFramerFrmFromNetworkEntry 2 }

mscVsrSvsFramerNEncodingTable OBJECT-TYPE
   SYNTAX     SEQUENCE OF MscVsrSvsFramerNEncodingEntry
   ACCESS     not-accessible
   STATUS     mandatory
   DESCRIPTION
     "This attribute indicates the results of negotiating audio call 
      encodings for voice, modemFax and fax traffic with the remote end 
      across the subnet. The parameters used for negotiating with the 
      remote end are provisioned in Vncs Vp voiceEncodingChoice and 
      Vncs Vp modemFaxEncodingChoice.
      
      voice traffic is all traffic from the start of a call or speech until a 
      2100 Hz tone or call release. modemFax traffic is all traffic after a 
      2100 Hz tone but before a fax preamble, speech or call release. fax 
      traffic is all traffic after a fax preamble but before speech or call 
      release.
      
      g711 indicates that pulse code modulation (PCM) defined by ITU-T 
      G.711 is the negotiated encoding.
      g726 indicates that Adaptive Differential Pulse Code Modulation 
      (ADPCM) defined by ITU-T G.726 is the negotiated encoding. 
      g711G726 indicates that pulse code modulation (PCM) defined by 
      ITU-T G.711 and Adaptive Differential Pulse Code Modulation 
      (ADPCM) defined by ITU-T G.726 are both negotiated encodings. 
      If negotiatedEncoding is g711G726, the actual encoding performed 
      can be either G.711 or G.726, depending on network congestion.
      g728 indicates that Low Delay Coded Excited Linear Predictive 
      Coder (CS-ACELP) defined by ITU-T G.728 is the negotiated 
      encoding.
      g729 indicates that Conjunctive Structure Algebraic Code Excited 
      Linear Predictive Coder (CS-ACELP) defined by ITU-T G.729 is 
      the negotiated encoding.
      v29V27Relay indicates that fax relay using ITU-T V.29 or ITU-T 
      V.27 is the negotiated encoding.
      v17V29V27Relay indicates that fax relay using ITU-T V.17, ITU-T 
      V.29, or ITU-T V.27 is the negotiated encoding.
      
      If all negotiated encodings are none, the negotiation of audio call 
      encodings is not complete."
::= { mscVsrSvsFramer 467 }

mscVsrSvsFramerNEncodingEntry OBJECT-TYPE
   SYNTAX     MscVsrSvsFramerNEncodingEntry
   ACCESS     not-accessible
   STATUS     mandatory
   DESCRIPTION
     "An entry in the mscVsrSvsFramerNEncodingTable."
   INDEX {
      mscVsrIndex,
      mscVsrSvsIndex,
      mscVsrSvsFramerIndex,
      mscVsrSvsFramerNEncodingIndex }
::= { mscVsrSvsFramerNEncodingTable 1 }

MscVsrSvsFramerNEncodingEntry ::= SEQUENCE {
   mscVsrSvsFramerNEncodingIndex
      INTEGER,
   mscVsrSvsFramerNEncodingValue
      INTEGER }

mscVsrSvsFramerNEncodingIndex OBJECT-TYPE
   SYNTAX     INTEGER  {
                 voice(0),
                 modemFax(1),
                 fax(2) }
   ACCESS     not-accessible
   STATUS     mandatory
   DESCRIPTION
     "This variable represents the mscVsrSvsFramerNEncodingTable
      specific index for the mscVsrSvsFramerNEncodingTable."
::= { mscVsrSvsFramerNEncodingEntry 1 }

mscVsrSvsFramerNEncodingValue OBJECT-TYPE
   SYNTAX     INTEGER  {
                 g729(1),
                 g728(2),
                 g726(4),
                 g711(5),
                 g711G726(31),
                 v29V27Relay(64),
                 v17V29V27Relay(68),
                 none(255) }
   ACCESS     read-write
   STATUS     mandatory
   DESCRIPTION
     "This variable represents an individual value for the
      mscVsrSvsFramerNEncodingTable."
::= { mscVsrSvsFramerNEncodingEntry 2 }

mscVsrSvsFramerNRatesTable OBJECT-TYPE
   SYNTAX     SEQUENCE OF MscVsrSvsFramerNRatesEntry
   ACCESS     not-accessible
   STATUS     mandatory
   DESCRIPTION
     "This attribute indicates the results of negotiating minimum and 
      maximum rates for voice, modemFax and fax traffic with the 
      remote end across the subnet. The parameters used for negotiating 
      with the remote end are provisioned in Vncs Vp voiceRates and 
      Vncs Vp modemFaxRates."
::= { mscVsrSvsFramer 479 }

mscVsrSvsFramerNRatesEntry OBJECT-TYPE
   SYNTAX     MscVsrSvsFramerNRatesEntry
   ACCESS     not-accessible
   STATUS     mandatory
   DESCRIPTION
     "An entry in the mscVsrSvsFramerNRatesTable."
   INDEX {
      mscVsrIndex,
      mscVsrSvsIndex,
      mscVsrSvsFramerIndex,
      mscVsrSvsFramerNRatesTrafficIndex,
      mscVsrSvsFramerNRatesRateIndex }
::= { mscVsrSvsFramerNRatesTable 1 }

MscVsrSvsFramerNRatesEntry ::= SEQUENCE {
   mscVsrSvsFramerNRatesTrafficIndex
      INTEGER,
   mscVsrSvsFramerNRatesRateIndex
      INTEGER,
   mscVsrSvsFramerNRatesValue
      INTEGER }

mscVsrSvsFramerNRatesTrafficIndex OBJECT-TYPE
   SYNTAX     INTEGER  {
                 voice(0),
                 modemFax(1),
                 fax(2) }
   ACCESS     not-accessible
   STATUS     mandatory
   DESCRIPTION
     "This variable represents the next to last index for the 
      mscVsrSvsFramerNRatesTable."
::= { mscVsrSvsFramerNRatesEntry 1 }

mscVsrSvsFramerNRatesRateIndex OBJECT-TYPE
   SYNTAX     INTEGER  {
                 min(0),
                 max(1) }
   ACCESS     not-accessible
   STATUS     mandatory
   DESCRIPTION
     "This variable represents the final index for the 
      mscVsrSvsFramerNRatesTable."
::= { mscVsrSvsFramerNRatesEntry 2 }

mscVsrSvsFramerNRatesValue OBJECT-TYPE
   SYNTAX     INTEGER  {
                 n00(0),
                 n03(1),
                 n12(2),
                 n24(3),
                 n48(4),
                 n72(5),
                 n96(6),
                 n120(7),
                 n144(8),
                 n80(66),
                 n160(67),
                 n240(68),
                 n320(69),
                 n640(70) }
   ACCESS     read-write
   STATUS     mandatory
   DESCRIPTION
     "This variable represents an individual value for the
      mscVsrSvsFramerNRatesTable."
::= { mscVsrSvsFramerNRatesEntry 3 }


-- Vsr/m Svs/n Framer VfpDebug
-- This component contains debugging attributes for a voice service 
-- running on a DS1V, E1V, 1pDS1V, 1pE1V or J2MV functional 
-- processor.

mscVsrSvsFramerVfpDebug OBJECT IDENTIFIER ::= { mscVsrSvsFramer 5 }



mscVsrSvsFramerVfpDebugRowStatusTable OBJECT-TYPE
   SYNTAX     SEQUENCE OF MscVsrSvsFramerVfpDebugRowStatusEntry
   ACCESS     not-accessible
   STATUS     mandatory
   DESCRIPTION
     "This entry controls the addition and deletion of 
      mscVsrSvsFramerVfpDebug components."
::= { mscVsrSvsFramerVfpDebug 1 }

mscVsrSvsFramerVfpDebugRowStatusEntry OBJECT-TYPE
   SYNTAX     MscVsrSvsFramerVfpDebugRowStatusEntry
   ACCESS     not-accessible
   STATUS     mandatory
   DESCRIPTION
     "A single entry in the table represents a single 
      mscVsrSvsFramerVfpDebug component."
   INDEX {
      mscVsrIndex,
      mscVsrSvsIndex,
      mscVsrSvsFramerIndex,
      mscVsrSvsFramerVfpDebugIndex }
::= { mscVsrSvsFramerVfpDebugRowStatusTable 1 }

MscVsrSvsFramerVfpDebugRowStatusEntry ::= SEQUENCE {
   mscVsrSvsFramerVfpDebugRowStatus
      RowStatus,
   mscVsrSvsFramerVfpDebugComponentName
      DisplayString,
   mscVsrSvsFramerVfpDebugStorageType
      StorageType,
   mscVsrSvsFramerVfpDebugIndex
      NonReplicated }

mscVsrSvsFramerVfpDebugRowStatus OBJECT-TYPE
   SYNTAX     RowStatus 
   ACCESS     read-only
   STATUS     mandatory
   DESCRIPTION
     "This variable is used as the basis for SNMP naming of
      mscVsrSvsFramerVfpDebug components.
      These components cannot be added nor deleted."
::= { mscVsrSvsFramerVfpDebugRowStatusEntry 1 }

mscVsrSvsFramerVfpDebugComponentName OBJECT-TYPE
   SYNTAX     DisplayString 
   ACCESS     read-only
   STATUS     mandatory
   DESCRIPTION
     "This variable provides the component's string name for
      use with the ASCII Console Interface"
::= { mscVsrSvsFramerVfpDebugRowStatusEntry 2 }

mscVsrSvsFramerVfpDebugStorageType OBJECT-TYPE
   SYNTAX     StorageType 
   ACCESS     read-only
   STATUS     mandatory
   DESCRIPTION
     "This variable represents the storage type value for the
      mscVsrSvsFramerVfpDebug tables."
::= { mscVsrSvsFramerVfpDebugRowStatusEntry 4 }

mscVsrSvsFramerVfpDebugIndex OBJECT-TYPE
   SYNTAX     NonReplicated 
   ACCESS     not-accessible
   STATUS     mandatory
   DESCRIPTION
     "This variable represents the index for the mscVsrSvsFramerVfpDebug tables."
::= { mscVsrSvsFramerVfpDebugRowStatusEntry 10 }


-- Vsr/m Svs/n Framer MvpDebug
-- This component contains debugging attributes on a voice service's 
-- framer running on a 1pE1Mvp, 1pDS1Mvp or 1pTTC2mMvp 
-- functional processor.

mscVsrSvsFramerMvpDebug OBJECT IDENTIFIER ::= { mscVsrSvsFramer 6 }



mscVsrSvsFramerMvpDebugRowStatusTable OBJECT-TYPE
   SYNTAX     SEQUENCE OF MscVsrSvsFramerMvpDebugRowStatusEntry
   ACCESS     not-accessible
   STATUS     mandatory
   DESCRIPTION
     "This entry controls the addition and deletion of 
      mscVsrSvsFramerMvpDebug components."
::= { mscVsrSvsFramerMvpDebug 1 }

mscVsrSvsFramerMvpDebugRowStatusEntry OBJECT-TYPE
   SYNTAX     MscVsrSvsFramerMvpDebugRowStatusEntry
   ACCESS     not-accessible
   STATUS     mandatory
   DESCRIPTION
     "A single entry in the table represents a single 
      mscVsrSvsFramerMvpDebug component."
   INDEX {
      mscVsrIndex,
      mscVsrSvsIndex,
      mscVsrSvsFramerIndex,
      mscVsrSvsFramerMvpDebugIndex }
::= { mscVsrSvsFramerMvpDebugRowStatusTable 1 }

MscVsrSvsFramerMvpDebugRowStatusEntry ::= SEQUENCE {
   mscVsrSvsFramerMvpDebugRowStatus
      RowStatus,
   mscVsrSvsFramerMvpDebugComponentName
      DisplayString,
   mscVsrSvsFramerMvpDebugStorageType
      StorageType,
   mscVsrSvsFramerMvpDebugIndex
      NonReplicated }

mscVsrSvsFramerMvpDebugRowStatus OBJECT-TYPE
   SYNTAX     RowStatus 
   ACCESS     read-only
   STATUS     mandatory
   DESCRIPTION
     "This variable is used as the basis for SNMP naming of
      mscVsrSvsFramerMvpDebug components.
      These components cannot be added nor deleted."
::= { mscVsrSvsFramerMvpDebugRowStatusEntry 1 }

mscVsrSvsFramerMvpDebugComponentName OBJECT-TYPE
   SYNTAX     DisplayString 
   ACCESS     read-only
   STATUS     mandatory
   DESCRIPTION
     "This variable provides the component's string name for
      use with the ASCII Console Interface"
::= { mscVsrSvsFramerMvpDebugRowStatusEntry 2 }

mscVsrSvsFramerMvpDebugStorageType OBJECT-TYPE
   SYNTAX     StorageType 
   ACCESS     read-only
   STATUS     mandatory
   DESCRIPTION
     "This variable represents the storage type value for the
      mscVsrSvsFramerMvpDebug tables."
::= { mscVsrSvsFramerMvpDebugRowStatusEntry 4 }

mscVsrSvsFramerMvpDebugIndex OBJECT-TYPE
   SYNTAX     NonReplicated 
   ACCESS     not-accessible
   STATUS     mandatory
   DESCRIPTION
     "This variable represents the index for the mscVsrSvsFramerMvpDebug tables."
::= { mscVsrSvsFramerMvpDebugRowStatusEntry 10 }


-- Vsr/n Svs/m Framer PcmCapture
-- This component contains attributes for PCM data capture.

mscVsrSvsFramerPcmCapture OBJECT IDENTIFIER ::= { mscVsrSvsFramer 7 }



mscVsrSvsFramerPcmCaptureRowStatusTable OBJECT-TYPE
   SYNTAX     SEQUENCE OF MscVsrSvsFramerPcmCaptureRowStatusEntry
   ACCESS     not-accessible
   STATUS     mandatory
   DESCRIPTION
     "This entry controls the addition and deletion of 
      mscVsrSvsFramerPcmCapture components."
::= { mscVsrSvsFramerPcmCapture 1 }

mscVsrSvsFramerPcmCaptureRowStatusEntry OBJECT-TYPE
   SYNTAX     MscVsrSvsFramerPcmCaptureRowStatusEntry
   ACCESS     not-accessible
   STATUS     mandatory
   DESCRIPTION
     "A single entry in the table represents a single 
      mscVsrSvsFramerPcmCapture component."
   INDEX {
      mscVsrIndex,
      mscVsrSvsIndex,
      mscVsrSvsFramerIndex,
      mscVsrSvsFramerPcmCaptureIndex }
::= { mscVsrSvsFramerPcmCaptureRowStatusTable 1 }

MscVsrSvsFramerPcmCaptureRowStatusEntry ::= SEQUENCE {
   mscVsrSvsFramerPcmCaptureRowStatus
      RowStatus,
   mscVsrSvsFramerPcmCaptureComponentName
      DisplayString,
   mscVsrSvsFramerPcmCaptureStorageType
      StorageType,
   mscVsrSvsFramerPcmCaptureIndex
      NonReplicated }

mscVsrSvsFramerPcmCaptureRowStatus OBJECT-TYPE
   SYNTAX     RowStatus 
   ACCESS     read-only
   STATUS     mandatory
   DESCRIPTION
     "This variable is used as the basis for SNMP naming of
      mscVsrSvsFramerPcmCapture components.
      These components cannot be added nor deleted."
::= { mscVsrSvsFramerPcmCaptureRowStatusEntry 1 }

mscVsrSvsFramerPcmCaptureComponentName OBJECT-TYPE
   SYNTAX     DisplayString 
   ACCESS     read-only
   STATUS     mandatory
   DESCRIPTION
     "This variable provides the component's string name for
      use with the ASCII Console Interface"
::= { mscVsrSvsFramerPcmCaptureRowStatusEntry 2 }

mscVsrSvsFramerPcmCaptureStorageType OBJECT-TYPE
   SYNTAX     StorageType 
   ACCESS     read-only
   STATUS     mandatory
   DESCRIPTION
     "This variable represents the storage type value for the
      mscVsrSvsFramerPcmCapture tables."
::= { mscVsrSvsFramerPcmCaptureRowStatusEntry 4 }

mscVsrSvsFramerPcmCaptureIndex OBJECT-TYPE
   SYNTAX     NonReplicated 
   ACCESS     not-accessible
   STATUS     mandatory
   DESCRIPTION
     "This variable represents the index for the mscVsrSvsFramerPcmCapture tables."
::= { mscVsrSvsFramerPcmCaptureRowStatusEntry 10 }


-- ...Lc
-- This component contains all of the operation attributes for a Path 
-- Oriented Logical Connection.

mscVsrSvsLCo OBJECT IDENTIFIER ::= { mscVsrSvs 3 }



mscVsrSvsLCoRowStatusTable OBJECT-TYPE
   SYNTAX     SEQUENCE OF MscVsrSvsLCoRowStatusEntry
   ACCESS     not-accessible
   STATUS     mandatory
   DESCRIPTION
     "This entry controls the addition and deletion of 
      mscVsrSvsLCo components."
::= { mscVsrSvsLCo 1 }

mscVsrSvsLCoRowStatusEntry OBJECT-TYPE
   SYNTAX     MscVsrSvsLCoRowStatusEntry
   ACCESS     not-accessible
   STATUS     mandatory
   DESCRIPTION
     "A single entry in the table represents a single 
      mscVsrSvsLCo component."
   INDEX {
      mscVsrIndex,
      mscVsrSvsIndex,
      mscVsrSvsLCoIndex }
::= { mscVsrSvsLCoRowStatusTable 1 }

MscVsrSvsLCoRowStatusEntry ::= SEQUENCE {
   mscVsrSvsLCoRowStatus
      RowStatus,
   mscVsrSvsLCoComponentName
      DisplayString,
   mscVsrSvsLCoStorageType
      StorageType,
   mscVsrSvsLCoIndex
      NonReplicated }

mscVsrSvsLCoRowStatus OBJECT-TYPE
   SYNTAX     RowStatus 
   ACCESS     read-only
   STATUS     mandatory
   DESCRIPTION
     "This variable is used as the basis for SNMP naming of
      mscVsrSvsLCo components.
      These components cannot be added nor deleted."
::= { mscVsrSvsLCoRowStatusEntry 1 }

mscVsrSvsLCoComponentName OBJECT-TYPE
   SYNTAX     DisplayString 
   ACCESS     read-only
   STATUS     mandatory
   DESCRIPTION
     "This variable provides the component's string name for
      use with the ASCII Console Interface"
::= { mscVsrSvsLCoRowStatusEntry 2 }

mscVsrSvsLCoStorageType OBJECT-TYPE
   SYNTAX     StorageType 
   ACCESS     read-only
   STATUS     mandatory
   DESCRIPTION
     "This variable represents the storage type value for the
      mscVsrSvsLCo tables."
::= { mscVsrSvsLCoRowStatusEntry 4 }

mscVsrSvsLCoIndex OBJECT-TYPE
   SYNTAX     NonReplicated 
   ACCESS     not-accessible
   STATUS     mandatory
   DESCRIPTION
     "This variable represents the index for the mscVsrSvsLCo tables."
::= { mscVsrSvsLCoRowStatusEntry 10 }

mscVsrSvsLCoPathDataTable OBJECT-TYPE
   SYNTAX     SEQUENCE OF MscVsrSvsLCoPathDataEntry
   ACCESS     not-accessible
   STATUS     mandatory
   DESCRIPTION
     "This group contains all operational attributes for the path oriented 
      LCo."
::= { mscVsrSvsLCo 10 }

mscVsrSvsLCoPathDataEntry OBJECT-TYPE
   SYNTAX     MscVsrSvsLCoPathDataEntry
   ACCESS     not-accessible
   STATUS     mandatory
   DESCRIPTION
     "An entry in the mscVsrSvsLCoPathDataTable."
   INDEX {
      mscVsrIndex,
      mscVsrSvsIndex,
      mscVsrSvsLCoIndex }
::= { mscVsrSvsLCoPathDataTable 1 }

MscVsrSvsLCoPathDataEntry ::= SEQUENCE {
   mscVsrSvsLCoState
      INTEGER,
   mscVsrSvsLCoOverrideRemoteName
      AsciiString,
   mscVsrSvsLCoEnd
      INTEGER,
   mscVsrSvsLCoCostMetric
      Unsigned32,
   mscVsrSvsLCoDelayMetric
      Unsigned32,
   mscVsrSvsLCoRoundTripDelay
      Unsigned32,
   mscVsrSvsLCoSetupPriority
      Unsigned32,
   mscVsrSvsLCoHoldingPriority
      Unsigned32,
   mscVsrSvsLCoRequiredTxBandwidth
      Gauge32,
   mscVsrSvsLCoRequiredRxBandwidth
      Gauge32,
   mscVsrSvsLCoRequiredTrafficType
      INTEGER,
   mscVsrSvsLCoPermittedTrunkTypes
      OCTET STRING,
   mscVsrSvsLCoRequiredSecurity
      Unsigned32,
   mscVsrSvsLCoRequiredCustomerParameter
      Unsigned32,
   mscVsrSvsLCoEmissionPriority
      Unsigned32,
   mscVsrSvsLCoDiscardPriority
      Unsigned32,
   mscVsrSvsLCoPathType
      INTEGER,
   mscVsrSvsLCoRetryCount
      Unsigned32,
   mscVsrSvsLCoPathFailureCount
      Unsigned32,
   mscVsrSvsLCoReasonForNoRoute
      INTEGER,
   mscVsrSvsLCoLastTearDownReason
      INTEGER,
   mscVsrSvsLCoPathFailureAction
      INTEGER,
   mscVsrSvsLCoBumpPreference
      INTEGER,
   mscVsrSvsLCoOptimization
      INTEGER,
   mscVsrSvsLCoPathUpDateTime
      EnterpriseDateAndTime }

mscVsrSvsLCoState OBJECT-TYPE
   SYNTAX     INTEGER  {
                 pathDown(0),
                 selectingRoute(1),
                 connecting(2),
                 pathUp(3),
                 pathDownRetrying(4) }
   ACCESS     read-only
   STATUS     mandatory
   DESCRIPTION
     "This attribute reflects the current state of the connection. The 
      pathDown state indicates a connection that has no remote end 
      provisioned or the application has not yet signalled for a path. The 
      selectingRoute state occurs when a request has been sent to route 
      selector and it has not yet responded. The connectingState occurs 
      while a path is being established. The pathUp state is the normal 
      operational state of a path. The pathDownRetrying state indicates a 
      path that attempted route selection but received no route and is now 
      waiting to retry route selection again."
::= { mscVsrSvsLCoPathDataEntry 1 }

mscVsrSvsLCoOverrideRemoteName OBJECT-TYPE
   SYNTAX     AsciiString (SIZE (0..40))
   ACCESS     read-write
   STATUS     mandatory
   DESCRIPTION
     "If set and the current PLC remoteName is blank this remoteName 
      will override the blank PLC remoteName. Usually you would set 
      this attribute and then lock/unlock the service component which 
      will result in this new overrideRemoteName being used as if it had 
      been provisioned into the PLC remoteName. The advantage of this 
      attribute is that the connection's remoteName can be changed 
      immediately without having to 'activate prov' but the disadvantage 
      is that the overrideRemoteName is not permanent and if the card or 
      switch is reset the override will be lost."
::= { mscVsrSvsLCoPathDataEntry 2 }

mscVsrSvsLCoEnd OBJECT-TYPE
   SYNTAX     INTEGER  {
                 calling(0),
                 called(1) }
   ACCESS     read-only
   STATUS     mandatory
   DESCRIPTION
     "This attribute identifies whether this is the calling or called end of 
      the path."
::= { mscVsrSvsLCoPathDataEntry 3 }

mscVsrSvsLCoCostMetric OBJECT-TYPE
   SYNTAX     Unsigned32 (0..65535)
   ACCESS     read-only
   STATUS     mandatory
   DESCRIPTION
     "This attribute gives the route's total cost metric. It is calculated as 
      the sum of the cost metric of all trunks in the path at the time the 
      connection was established. The cost metric of a trunk is defined by 
      the trunkCost attribute of the Trunk component. The costMetric for 
      an LCo that is originated and terminated on the same module is 0."
::= { mscVsrSvsLCoPathDataEntry 4 }

mscVsrSvsLCoDelayMetric OBJECT-TYPE
   SYNTAX     Unsigned32 (0..100000)
   ACCESS     read-only
   STATUS     mandatory
   DESCRIPTION
     "This attribute gives the total delay of the route as the one way delay 
      for a 512 byte packet. It is calculated as the sum of the delays of all 
      trunks in the path stored in topology at the time the connection was 
      established. The delay for an LCo that is originated and terminated 
      on the same module is 0."
::= { mscVsrSvsLCoPathDataEntry 5 }

mscVsrSvsLCoRoundTripDelay OBJECT-TYPE
   SYNTAX     Unsigned32 (0..200000)
   ACCESS     read-only
   STATUS     mandatory
   DESCRIPTION
     "This attribute contains the time taken for a packet (cell) of 44 bytes 
      to be transmitted to the remote LCo and return to this LCo. The 
      number reported is given in milliseconds to the nearest millisecond. 
      A value of one millisecond is reported if the time is less than 1 
      millisecond even though the delay may be less than 1 Millisecond 
      when the LCo is originated and terminated on the same module."
::= { mscVsrSvsLCoPathDataEntry 6 }

mscVsrSvsLCoSetupPriority OBJECT-TYPE
   SYNTAX     Unsigned32 (0..4)
   ACCESS     read-only
   STATUS     mandatory
   DESCRIPTION
     "This attribute gives the priority at which the current path is 
      established. Zero is the highest priority and four is the lowest. The 
      holdingPriority, a complementary attribute of this component, 
      indicates the priority a path maintains once it is established."
::= { mscVsrSvsLCoPathDataEntry 7 }

mscVsrSvsLCoHoldingPriority OBJECT-TYPE
   SYNTAX     Unsigned32 (0..4)
   ACCESS     read-only
   STATUS     mandatory
   DESCRIPTION
     "This attribute gives the priority at which a path holds its current 
      path once the path is established. Zero is the highest priority and 
      four is the lowest. The setupPriority, a complementary attribute, 
      indicates the priority of a path at establishment time."
::= { mscVsrSvsLCoPathDataEntry 8 }

mscVsrSvsLCoRequiredTxBandwidth OBJECT-TYPE
   SYNTAX     Gauge32 (0..4294967295)
   ACCESS     read-only
   STATUS     mandatory
   DESCRIPTION
     "This attribute gives the actual bandwidth (in bits per second) 
      reserved by this path on each of the trunks of its route. This attribute 
      represents the bandwidth for traffic outgoing to the remote end 
      point. The originating end of the connection determines this value."
::= { mscVsrSvsLCoPathDataEntry 9 }

mscVsrSvsLCoRequiredRxBandwidth OBJECT-TYPE
   SYNTAX     Gauge32 (0..4294967295)
   ACCESS     read-only
   STATUS     mandatory
   DESCRIPTION
     "This attribute gives the actual bandwidth (in bits per second) 
      reserved by this path on each of trunks of its route. This attribute 
      represents the bandwidth for traffic incoming from the remote end 
      point. The originating end of the connection determines this value"
::= { mscVsrSvsLCoPathDataEntry 10 }

mscVsrSvsLCoRequiredTrafficType OBJECT-TYPE
   SYNTAX     INTEGER  {
                 voice(0),
                 data(1),
                 video(2),
                 trafficType1(3),
                 trafficType2(4),
                 trafficType3(5),
                 trafficType4(6),
                 trafficType5(7) }
   ACCESS     read-only
   STATUS     mandatory
   DESCRIPTION
     "This operational attribute indicates the type of traffic transmitted 
      over the path. There are eight possible traffic types, and the path can 
      transmit only one of them. The originating end of the connection 
      determines the type. These are arbitrary designations for traffic 
      type. The voice, data and video traffic types are defined, and five 
      other arbitrary traffic types can be defined by the network 
      administration. This attribute is used in the route selection process 
      to restrict the route to trunks that support this traffic type. The 
      supportedTrafficType trunk attribute lists all the types of traffic 
      allowed on the trunk. For example, if requiredTrafficType is 
      specified as trafficType1 then only trunks that include trafficType1 
      in supportedTrafficType, will be candidates for this connection."
::= { mscVsrSvsLCoPathDataEntry 11 }

mscVsrSvsLCoPermittedTrunkTypes OBJECT-TYPE
   SYNTAX     OCTET STRING (SIZE (1))
   ACCESS     read-only
   STATUS     mandatory
   DESCRIPTION
     "This operational attribute lists up to eight types of trunk that can be 
      used on the route. The originating end of the connection determines 
      the types. The terrestrial and satellite trunk types have been 
      defined, leaving six remaining arbitrary types that can be defined by 
      the network administration. The trunk's type is indicated in the 
      trunkType attribute of the Trunk component. When selecting a 
      route, PORS only chooses trunks whose trunkType are in the 
      permittedTrunkTypes for the path.

      Description of bits:
      terrestrial(0)
      satellite(1)
      trunkType1(2)
      trunkType2(3)
      trunkType3(4)
      trunkType4(5)
      trunkType5(6)
      trunkType6(7)"
::= { mscVsrSvsLCoPathDataEntry 12 }

mscVsrSvsLCoRequiredSecurity OBJECT-TYPE
   SYNTAX     Unsigned32 (0..7)
   ACCESS     read-only
   STATUS     mandatory
   DESCRIPTION
     "This attribute indicates the required minimum level of security of 
      the trunks on the route. Zero represents the most secure and seven 
      represents the least secure. The trunk's security is indicated by the 
      trunkSecurity attribute of the Trunk component, and has values 
      identical in range and meaning to the requiredSecurity attribute. 
      PORS ensures that any route selected does not contain a trunk 
      whose trunkSecurity attribute is numerically greater than the 
      requiredSecurity."
::= { mscVsrSvsLCoPathDataEntry 13 }

mscVsrSvsLCoRequiredCustomerParameter OBJECT-TYPE
   SYNTAX     Unsigned32 (0..7)
   ACCESS     read-only
   STATUS     mandatory
   DESCRIPTION
     "This attribute indicates the allowed customer defined parameter of 
      the trunks on the route.The originating end of the connection 
      determines the customer defined parameter. Its value, a number 
      from zero to seven, is chosen by a network administration to have a 
      meaning specific to their network, thus allowing them to customize 
      the use of their trunks. A complementary trunk attribute, 
      customerParameter, also has a value from zero to seven. The route 
      selection process does not consider trunks whose 
      customerParameter is greater than the requiredCustomerParameter 
      of the path."
::= { mscVsrSvsLCoPathDataEntry 14 }

mscVsrSvsLCoEmissionPriority OBJECT-TYPE
   SYNTAX     Unsigned32 (0..2)
   ACCESS     read-only
   STATUS     mandatory
   DESCRIPTION
     "This attribute indicates the urgency with which packets on the path 
      are emitted by the trunks on the route. The originating end of the 
      connection selects the emissionPriority. EmissionPriority of zero 
      indicates the highest emission priority, while two indicates the 
      lowest emission priority. Packets with a higher emissionPriority (or 
      numerically less) are serviced and sent out before the packets of 
      lower emissionPriority (or numerically higher)."
::= { mscVsrSvsLCoPathDataEntry 15 }

mscVsrSvsLCoDiscardPriority OBJECT-TYPE
   SYNTAX     Unsigned32 (1..3)
   ACCESS     read-only
   STATUS     mandatory
   DESCRIPTION
     "This attribute indicates the importance of the packets on the 
      path.The originating end of the connection sets discardPriority. One 
      is used for paths carrying the most important traffic, and three is 
      used for paths carrying the least important traffic. Packets with 
      lower discardPriority(numerically lower) are discarded after 
      packets with a higher discardPriority(numerically higher)."
::= { mscVsrSvsLCoPathDataEntry 16 }

mscVsrSvsLCoPathType OBJECT-TYPE
   SYNTAX     INTEGER  {
                 normal(0),
                 manual(1),
                 forced(2) }
   ACCESS     read-only
   STATUS     mandatory
   DESCRIPTION
     "This attribute indicates whether the path for this PLC was 
      determined automatically or by static provisioning. Normal 
      pathTypes are selected automatically by Route Selector.The other 
      pathTypes are both manual pathTypes where the operator must 
      specify, through provisioning, a static route termed the manualPath. 
      A manual pathType connection is nearly identical to a normal path 
      type connection with the exception that the route is pre-provisioned. 
      For a manual pathType, bandwidth reservations are respected along 
      the path exactly as in a normal path. The last type, the forced 
      pathType, is also a manual path but regardless of the bandwidth 
      available the route is granted provided the trunks are operational 
      and there are sufficient Logical Channels (LChs).
      
      The forced pathType could result in over committing the reserved 
      bandwidth allowed on a trunk. A better way to achieve the effects of 
      a forced pathType is to use a manual pathType with setupPriority = 
      0 and holdingPriority = 0. In this manner the path will reserve 
      correct bandwidth and it will bump other paths if required while not 
      being bumped itself."
::= { mscVsrSvsLCoPathDataEntry 17 }

mscVsrSvsLCoRetryCount OBJECT-TYPE
   SYNTAX     Unsigned32 (0..255)
   ACCESS     read-only
   STATUS     mandatory
   DESCRIPTION
     "This attribute is the count of the number of times the path chosen 
      during route selection could not be instantiated. This count should 
      be three or below if the network is performing adequately. A high 
      value indicates that the route selection is often performed using an 
      out-of-date view of available network bandwidth and/or topology.
      This attribute will only increase at the calling end of the connection.
      This attribute is reset each time a path reconnects and stops 
      counting when it reaches its maximum value."
::= { mscVsrSvsLCoPathDataEntry 18 }

mscVsrSvsLCoPathFailureCount OBJECT-TYPE
   SYNTAX     Unsigned32 (0..65535)
   ACCESS     read-only
   STATUS     mandatory
   DESCRIPTION
     "This attribute is the count of the number of times the path has 
      successfully connected. It is set to zero the first time the path is up. 
      If a path fails anytime after connecting this count will be 
      incremented when the path is up again. Failed route requests do not 
      count in this statistic. See retryCount above. This attribute stops 
      counting at its maximum value."
::= { mscVsrSvsLCoPathDataEntry 19 }

mscVsrSvsLCoReasonForNoRoute OBJECT-TYPE
   SYNTAX     INTEGER  {
                 none(0),
                 destinationNameTooLong(1),
                 destinationNotSpecified(2),
                 unknownDestinationName(3),
                 incorrectDestination(4),
                 incorrectDestinationEndPoint(5),
                 unknownSource(6),
                 unknownDestination(7),
                 sameNode(8),
                 routeCostTooMuch(9),
                 routesDelayTooLong(10),
                 attributesNotMet(11),
                 anError(12),
                 attributeProfileProblem(13),
                 manualPathIndexProblem(14) }
   ACCESS     read-only
   STATUS     mandatory
   DESCRIPTION
     "This attribute is the route selection's reasonForNoRoute and 
      provides a brief reason for which a route was not selected. The 
      reasons are essentially self-explanatory. Perhaps two reasons for no 
      route require some explanation. The reason 
      unknownRemoteNodeName is issued when the remote node name 
      is not in the topological database. The reason plcAttributesNotMet 
      is issued when there is no network connectivity at a level specified 
      by the PLC attributes. This reason is also issued when there is no 
      physical connectivity between two end nodes."
   DEFVAL     { none }
::= { mscVsrSvsLCoPathDataEntry 20 }

mscVsrSvsLCoLastTearDownReason OBJECT-TYPE
   SYNTAX     INTEGER  {
                 none(0),
                 normalShutDown(1),
                 insufficientTxLcOrBandwidth(2),
                 insufficientRxLcOrBandwidth(3),
                 trunkFailure(4),
                 trunkCardFailure(5),
                 operatorForced(6),
                 lostLcnClash(7),
                 networkCongestion(8),
                 trunkNotFound(9),
                 farEndNotFound(10),
                 wrongModuleReached(11),
                 farEndBusy(12),
                 callLoopedBack(13),
                 unknownReason(14),
                 farEndNotReady(15),
                 remoteNameMismatch(16),
                 serviceTypeMismatch(17),
                 reconnectFromFarEnd(18),
                 bumped(19),
                 accessCardFailure(20),
                 optimized(21),
                 overrideRemoteName(22),
                 trunkOrFarEndDidNotSupportMode(23) }
   ACCESS     read-only
   STATUS     mandatory
   DESCRIPTION
     "This attribute reflects the last tear down reason for a connection 
      (LCo). In many cases this displays the reason for a momentary 
      service interruption. This attribute applies to the last path failure 
      only. If a path is no longer up, this may give an indication to the 
      reason that the path has failed. In many cases an alarm will also be 
      generated with more specific information. The following is a brief 
      description of the reasons:
      none - This path has no information for the teardown this is typical 
      of a path provisioned with no remoteName that has not been up.
      normalShutDown - This path has gone down due to normal call 
      termination.
      insufficientTxLcOrBandwidth - At present there is either no 
      available bandwidth or logical channel numbers available on one or 
      more of the trunks for this path in the transmit direction.
      insufficientRxLcOrBandwidth - At present there is either no 
      available bandwidth or logical channel numbers available on one or 
      more of the trunks for this path in the receive direction.
      trunkFailure- A trunk on the path has failed or has gone down due 
      to a provisioning change of a critical attribute.
      trunkCardFailure- A trunk FP card has failed along the path.
      accessCardFailure- The FP on which the peer access service was 
      running has failed.
      operatorForced- The path has terminated due to the operator 
      locking a trunk along the path.
      lostLcnClash- The path has terminated because the PA's at both 
      ends of an intermediate trunk have allocated the same LC to 
      different calls. When this happens both calls must go down and then 
      try to come up again a fraction of a second later (effectively 
      ensuring that they will now be assigned different LC's). It is normal 
      to get the odd clash especially when the PA's usedLC is 
      approaching the PA's maxLC.
      networkCongestion - The path has failed due to control information 
      being lost and not recoverable.
      trunkNotFound - Occurs on a manual path usually. Check for 
      trunks not up or names provisioned incorrectly.
      farEndNotFound - The far end is not provisioned or is not up. 
      Check remote Name.
      wrongModuleReached - This may occur on a manual path. Check 
      provisioning for correct trunk and service names. For a normal 
      path, the network Topology may be changing check remoteName.
      farEndBusy - The far end has been reached but it is busy. Check 
      remoteName and remote end provisioning.
      callLoopedBack - This LCo is provisioned to call itself. Re-
      provision since this is invalid.
      unknownReason - The failure was not resolved.
      farEndNotReady - The remote end was reached but the connection 
      was refused due to the remote end not being enabled.
      remoteNameMismatch - The remote end has alarmed and rejected 
      this setup due to remoteName provisioning.
      serviceTypeMismatch - The remote Service Type does not match 
      this service type. Check provisioning.
      reconnectFromFarEnd - The remote end re-established this 
      connection. Check the remote end lastTearDownReason to 
      determine the real reason.
      bumped - Another call bumped this path from a trunk to get 
      bandwidth (or an LC) which it required to come up. This other path 
      had a higher setupPriority than this path's holdingPriority hence it 
      was allowed to steal the bandwidth (or LC) from this path.
      optimized - This call has been rerouted due to the optimization 
      feature. The call is still active this just indicates why the path 
      changed.
      trunkOrFarEndDidNotSupportMode - This call was unable to 
      complete because a mode required by the service was not supported 
      by one of the trunks the route went through or by the far end service 
      it connected to. Currently the only mode that this applies to is the 
      map/mux mode on TRUNK PA ATM component. Map mode was 
      required by the application (CES/FrAtm etc.) but was not available 
      on the TRUNK PA ATM component through which the call was 
      routed or the far end CES/FrAtm component did not specify the 
      same mode."
   DEFVAL     { none }
::= { mscVsrSvsLCoPathDataEntry 21 }

mscVsrSvsLCoPathFailureAction OBJECT-TYPE
   SYNTAX     INTEGER  {
                 disconnectConnection(0),
                 reRoutePath(1) }
   ACCESS     read-only
   STATUS     mandatory
   DESCRIPTION
     "This attribute displays whether the application is set to tolerate 
      momentary interruption of a path while a new path is selected. If 
      disconnectConnection is displayed, the application is informed as 
      soon as possible about a failure by disconnection. If the attribute 
      displays reRoutePath, the path may attempt an immediate reroute, 
      provided the failure is a recoverable failure. If rerouting fails the 
      application is informed of the failure. 
      With this option set to reRoutePath the LCo may wait up to 30 
      seconds before informing the service of complete disconnection in 
      order to allow both ends to attempt to reconnect. Note that if PLC 
      components are different at both ends only the calling end is 
      allowed to reconnect.
      
      All pathTypes respect this attribute. Also on a manualPath with 
      both ends provisioned with independent paths (at least with respect 
      to the failure) this option will have the desired effect that the path is 
      rerouted without complete disconnection at both ends"
::= { mscVsrSvsLCoPathDataEntry 22 }

mscVsrSvsLCoBumpPreference OBJECT-TYPE
   SYNTAX     INTEGER  {
                 bumpWhenNecessary(0),
                 bumpToObtainBestRoute(1) }
   ACCESS     read-only
   STATUS     mandatory
   DESCRIPTION
     "This attribute specifies when bumping will occur during route 
      selection process. Bumping may occur when necessary or always. It 
      will be necessary for a connection to bump if there is not enough 
      resources for the connection to be established and these resources 
      are occupied by a connection whose setupPriority is lower 
      (numerically higher) than the connection's setupPriority. A 
      connection may also always bump in order to obtain the best route."
::= { mscVsrSvsLCoPathDataEntry 23 }

mscVsrSvsLCoOptimization OBJECT-TYPE
   SYNTAX     INTEGER  {
                 disabled(0),
                 enabled(1) }
   ACCESS     read-only
   STATUS     mandatory
   DESCRIPTION
     "This attribute is used to specify whether this connection should 
      attempt to optimize its path when requested by the routing PORS 
      component. Every path is as optimal as it can be when it is 
      established, but as network traffic patterns and configurations 
      change this path may no longer be as optimal as it could be. The 
      PORS connection manager on a module requests circuits to 
      optimize at the optimization interval."
::= { mscVsrSvsLCoPathDataEntry 24 }

mscVsrSvsLCoPathUpDateTime OBJECT-TYPE
   SYNTAX     EnterpriseDateAndTime (SIZE (0 | 19))
   ACCESS     read-only
   STATUS     mandatory
   DESCRIPTION
     "This is the time stamp when the current path was established or 
      reestablished."
::= { mscVsrSvsLCoPathDataEntry 25 }

mscVsrSvsLCoStatsTable OBJECT-TYPE
   SYNTAX     SEQUENCE OF MscVsrSvsLCoStatsEntry
   ACCESS     not-accessible
   STATUS     mandatory
   DESCRIPTION
     "This group contains the operational statistics attributes for the path 
      oriented LCo."
::= { mscVsrSvsLCo 11 }

mscVsrSvsLCoStatsEntry OBJECT-TYPE
   SYNTAX     MscVsrSvsLCoStatsEntry
   ACCESS     not-accessible
   STATUS     mandatory
   DESCRIPTION
     "An entry in the mscVsrSvsLCoStatsTable."
   INDEX {
      mscVsrIndex,
      mscVsrSvsIndex,
      mscVsrSvsLCoIndex }
::= { mscVsrSvsLCoStatsTable 1 }

MscVsrSvsLCoStatsEntry ::= SEQUENCE {
   mscVsrSvsLCoPktsToNetwork
      PassportCounter64,
   mscVsrSvsLCoBytesToNetwork
      PassportCounter64,
   mscVsrSvsLCoPktsFromNetwork
      PassportCounter64,
   mscVsrSvsLCoBytesFromNetwork
      PassportCounter64 }

mscVsrSvsLCoPktsToNetwork OBJECT-TYPE
   SYNTAX     PassportCounter64 
   ACCESS     read-only
   STATUS     mandatory
   DESCRIPTION
     "This attribute counts the number of packets transmitted to the 
      network over this Logical Connection."
::= { mscVsrSvsLCoStatsEntry 1 }

mscVsrSvsLCoBytesToNetwork OBJECT-TYPE
   SYNTAX     PassportCounter64 
   ACCESS     read-only
   STATUS     mandatory
   DESCRIPTION
     "This attribute counts the number of bytes sent to the network over 
      this Logical Connection."
::= { mscVsrSvsLCoStatsEntry 2 }

mscVsrSvsLCoPktsFromNetwork OBJECT-TYPE
   SYNTAX     PassportCounter64 
   ACCESS     read-only
   STATUS     mandatory
   DESCRIPTION
     "This attribute counts the number of packets received from the 
      remote LCo via the network."
::= { mscVsrSvsLCoStatsEntry 3 }

mscVsrSvsLCoBytesFromNetwork OBJECT-TYPE
   SYNTAX     PassportCounter64 
   ACCESS     read-only
   STATUS     mandatory
   DESCRIPTION
     "This attribute counts the number of bytes received from the remote 
      LCo via the network."
::= { mscVsrSvsLCoStatsEntry 4 }

mscVsrSvsLCoPathTable OBJECT-TYPE
   SYNTAX     SEQUENCE OF MscVsrSvsLCoPathEntry
   ACCESS     not-accessible
   STATUS     mandatory
   DESCRIPTION
     "This attribute contains the trunk component names over which the 
      path has been instantiated and the remote end point name 
      terminating the path."
::= { mscVsrSvsLCo 264 }

mscVsrSvsLCoPathEntry OBJECT-TYPE
   SYNTAX     MscVsrSvsLCoPathEntry
   ACCESS     not-accessible
   STATUS     mandatory
   DESCRIPTION
     "An entry in the mscVsrSvsLCoPathTable."
   INDEX {
      mscVsrIndex,
      mscVsrSvsIndex,
      mscVsrSvsLCoIndex,
      mscVsrSvsLCoPathValue }
::= { mscVsrSvsLCoPathTable 1 }

MscVsrSvsLCoPathEntry ::= SEQUENCE {
   mscVsrSvsLCoPathValue
      AsciiString }

mscVsrSvsLCoPathValue OBJECT-TYPE
   SYNTAX     AsciiString (SIZE (0..40))
   ACCESS     read-only
   STATUS     mandatory
   DESCRIPTION
     "This variable represents both the value and the index for the
      mscVsrSvsLCoPathTable."
::= { mscVsrSvsLCoPathEntry 1 }


-- Vsr/n Svs/n Debug		
-- The Debug component defines the debug operational characteristics 
-- of the svs component.

mscVsrSvsDebug OBJECT IDENTIFIER ::= { mscVsrSvs 4 }



mscVsrSvsDebugRowStatusTable OBJECT-TYPE
   SYNTAX     SEQUENCE OF MscVsrSvsDebugRowStatusEntry
   ACCESS     not-accessible
   STATUS     mandatory
   DESCRIPTION
     "This entry controls the addition and deletion of 
      mscVsrSvsDebug components."
::= { mscVsrSvsDebug 1 }

mscVsrSvsDebugRowStatusEntry OBJECT-TYPE
   SYNTAX     MscVsrSvsDebugRowStatusEntry
   ACCESS     not-accessible
   STATUS     mandatory
   DESCRIPTION
     "A single entry in the table represents a single 
      mscVsrSvsDebug component."
   INDEX {
      mscVsrIndex,
      mscVsrSvsIndex,
      mscVsrSvsDebugIndex }
::= { mscVsrSvsDebugRowStatusTable 1 }

MscVsrSvsDebugRowStatusEntry ::= SEQUENCE {
   mscVsrSvsDebugRowStatus
      RowStatus,
   mscVsrSvsDebugComponentName
      DisplayString,
   mscVsrSvsDebugStorageType
      StorageType,
   mscVsrSvsDebugIndex
      NonReplicated }

mscVsrSvsDebugRowStatus OBJECT-TYPE
   SYNTAX     RowStatus 
   ACCESS     read-only
   STATUS     mandatory
   DESCRIPTION
     "This variable is used as the basis for SNMP naming of
      mscVsrSvsDebug components.
      These components cannot be added nor deleted."
::= { mscVsrSvsDebugRowStatusEntry 1 }

mscVsrSvsDebugComponentName OBJECT-TYPE
   SYNTAX     DisplayString 
   ACCESS     read-only
   STATUS     mandatory
   DESCRIPTION
     "This variable provides the component's string name for
      use with the ASCII Console Interface"
::= { mscVsrSvsDebugRowStatusEntry 2 }

mscVsrSvsDebugStorageType OBJECT-TYPE
   SYNTAX     StorageType 
   ACCESS     read-only
   STATUS     mandatory
   DESCRIPTION
     "This variable represents the storage type value for the
      mscVsrSvsDebug tables."
::= { mscVsrSvsDebugRowStatusEntry 4 }

mscVsrSvsDebugIndex OBJECT-TYPE
   SYNTAX     NonReplicated 
   ACCESS     not-accessible
   STATUS     mandatory
   DESCRIPTION
     "This variable represents the index for the mscVsrSvsDebug tables."
::= { mscVsrSvsDebugRowStatusEntry 10 }


-- Vsr/n Debug		
-- The Debug component defines the debug operational characteristics 
-- of the VoiceSubroute component. There are three main areas of 
-- interest, the VoiceSubroute itself, the call state machines (CSM), 
-- and the call channel manager (CCM).
-- These debug groups can be reached by typing:
-- d Vsr/n debug
-- d Vsr/n debug sr
-- d Vsr/n debug csm
-- d Vsr/n debug ccm

mscVsrDebug OBJECT IDENTIFIER ::= { mscVsr 3 }



mscVsrDebugRowStatusTable OBJECT-TYPE
   SYNTAX     SEQUENCE OF MscVsrDebugRowStatusEntry
   ACCESS     not-accessible
   STATUS     mandatory
   DESCRIPTION
     "This entry controls the addition and deletion of 
      mscVsrDebug components."
::= { mscVsrDebug 1 }

mscVsrDebugRowStatusEntry OBJECT-TYPE
   SYNTAX     MscVsrDebugRowStatusEntry
   ACCESS     not-accessible
   STATUS     mandatory
   DESCRIPTION
     "A single entry in the table represents a single 
      mscVsrDebug component."
   INDEX {
      mscVsrIndex,
      mscVsrDebugIndex }
::= { mscVsrDebugRowStatusTable 1 }

MscVsrDebugRowStatusEntry ::= SEQUENCE {
   mscVsrDebugRowStatus
      RowStatus,
   mscVsrDebugComponentName
      DisplayString,
   mscVsrDebugStorageType
      StorageType,
   mscVsrDebugIndex
      NonReplicated }

mscVsrDebugRowStatus OBJECT-TYPE
   SYNTAX     RowStatus 
   ACCESS     read-only
   STATUS     mandatory
   DESCRIPTION
     "This variable is used as the basis for SNMP naming of
      mscVsrDebug components.
      These components cannot be added nor deleted."
::= { mscVsrDebugRowStatusEntry 1 }

mscVsrDebugComponentName OBJECT-TYPE
   SYNTAX     DisplayString 
   ACCESS     read-only
   STATUS     mandatory
   DESCRIPTION
     "This variable provides the component's string name for
      use with the ASCII Console Interface"
::= { mscVsrDebugRowStatusEntry 2 }

mscVsrDebugStorageType OBJECT-TYPE
   SYNTAX     StorageType 
   ACCESS     read-only
   STATUS     mandatory
   DESCRIPTION
     "This variable represents the storage type value for the
      mscVsrDebug tables."
::= { mscVsrDebugRowStatusEntry 4 }

mscVsrDebugIndex OBJECT-TYPE
   SYNTAX     NonReplicated 
   ACCESS     not-accessible
   STATUS     mandatory
   DESCRIPTION
     "This variable represents the index for the mscVsrDebug tables."
::= { mscVsrDebugRowStatusEntry 10 }




-- 
-- Version and Compliance statements
-- 



-- Object-Group Statement:
-- A list of all current accessible leaf objects.

-- OBJECTS { mscVsrIfIndex,
--           mscSigChanAdminState,
--           mscVsrSvsLCoRequiredTrafficType,
--           mscVsrSvsFramerFaxIdleCells,
--           mscVRouteDnaStorageType,
--           mscVsrSvsLCoRetryCount,
--           mscSigChanIfAdminStatus,
--           mscVsrSvsLCoEmissionPriority,
--           mscSigChanNcasDuration,
--           mscSigChanCustomerIdentifier,
--           mscVsrPeakActiveTptChannels,
--           mscVsrSvsFramerSilenceCells,
--           mscVsrSvsFramerNegotiatedV17AsG711G726,
--           mscVsrSvsFramerStorageType,
--           mscVRouteInterfaceTandemPassThrough,
--           mscVsrSvsLCoDiscardPriority,
--           mscVRouteInterfaceRowStatus,
--           mscSigChanNcasStorageType,
--           mscVRouteDegradedSubroutesValue,
--           mscSigChanICmapRowStatus,
--           mscVRouteDebugRowStatus,
--           mscSigChanGwStorageType,
--           mscVsrRowStatus,
--           mscVsrSvsUsageState,
--           mscSigChanICmapResourceUnavailCause,
--           mscVsrSvsLCoPktsToNetwork,
--           mscSigChanBchStatus,
--           mscVsrSvsLCoRowStatus,
--           mscVsrUsageState,
--           mscVsrPathSetupTimeOutCalls,
--           mscSigChanGwGatewayCapValue,
--           mscVsrSvsFramerFrmToNetworkValue,
--           mscVsrSvsLCoRequiredTxBandwidth,
--           mscVRouteAcctRowStatus,
--           mscVsrSvsFramerNRatesValue,
--           mscVsrSvsCallingNumber,
--           mscVsrSvsFramerPcmCaptureRowStatus,
--           mscVsrSvsStorageType,
--           mscVRouteInterfaceComfortNoiseCap,
--           mscVsrSvsLCoPermittedTrunkTypes,
--           mscSigChanDegradedSubroutesValue,
--           mscVsrSvsLCoStorageType,
--           mscVsrSvsLCoBytesToNetwork,
--           mscVRouteComponentName,
--           mscVsrSvsFramerFaxRelayCells,
--           mscVsrSvsDebugComponentName,
--           mscVsrSvsAdminState,
--           mscVsrSvsFramerTotalCells,
--           mscVsrSvsFramerRowStatus,
--           mscVsrActiveModemChannels,
--           mscVsrSvsLCoOptimization,
--           mscVsrPeakActiveChannels,
--           mscVsrSvsIfAdminStatus,
--           mscVsrCallsRejectedByFarEnd,
--           mscVsrSvsFramerUsageState,
--           mscVsrSvsLCoDelayMetric,
--           mscVsrSvsLCoCostMetric,
--           mscVRouteInterfaceSpeechHangoverTime,
--           mscSigChanICmapComponentName,
--           mscVRouteDiallingPlan2,
--           mscVRouteTypeOfRoute,
--           mscSigChanICmapReqChanOrCircNotAvailCause,
--           mscVRouteCallsClearedOutOfService,
--           mscVsrSvsLCoComponentName,
--           mscVsrSvsFramerOperationalState,
--           mscVsrSvsFramerFrmDumped,
--           mscVRouteSnmpOperStatus,
--           mscVsrSvsLCoOverrideRemoteName,
--           mscVRouteIfIndex,
--           mscVsrSvsProfileNumber,
--           mscVsrSvsCalledNumber,
--           mscVsrSvsFramerOpTptStatus,
--           mscVRouteOverrideDirectoryNumber,
--           mscVsrSvsFramerLrcErrors,
--           mscVRouteAcctStorageType,
--           mscVsrSvsFramerInterfaceName,
--           mscSigChanBchStorageType,
--           mscVsrSvsFramerNegotiatedSilenceSuppression,
--           mscVsrSvsFramerFrmUnderRuns,
--           mscVRouteCallsRejected,
--           mscVsrSvsLCoPathValue,
--           mscVRouteDiallingPlan0,
--           mscVsrSvsTotalCalls,
--           mscVRouteDnaComponentName,
--           mscVsrSvsLCoState,
--           mscVsrSvsFramerFrmLostInNetwork,
--           mscVsrSvsClearCauseCode,
--           mscVsrSvsFramerVfpDebugComponentName,
--           mscVsrPathAttributesNotMetCalls,
--           mscVRouteRowStatus,
--           mscVsrSignallingChannel,
--           mscSigChanSnmpOperStatus,
--           mscVsrPeakActiveFaxRelayChannels,
--           mscVsrPeakActiveVoiceChannels,
--           mscVsrSvsTotalCallSeconds,
--           mscVsrSvsDebugRowStatus,
--           mscSigChanStorageType,
--           mscVRouteDiallingPlan1,
--           mscSigChanICmapServNotAllowedCause,
--           mscVsrSvsFramerVfpDebugRowStatus,
--           mscVRouteUsageState,
--           mscVsrCallsRejectedLocally,
--           mscVRouteInterfaceModemFaxSpeechDiscrim,
--           mscSigChanGwComponentName,
--           mscSigChanNcasComponentName,
--           mscVsrSvsFramerNegotiatedDtmfRegeneration,
--           mscSigChanDefaultNpiTon,
--           mscVRouteOperationalState,
--           mscVsrCommentText,
--           mscVsrActiveDataChannels,
--           mscVRouteDnaDataNetworkAddress,
--           mscVsrTotalCallsFromIf,
--           mscVsrPeakActiveModemChannels,
--           mscVsrAddressIncompleteCalls,
--           mscSigChanNcasCalledDirectoryNumber,
--           mscVsrSvsFramerMvpDebugStorageType,
--           mscVsrSvsLCoPathUpDateTime,
--           mscSigChanRowStatus,
--           mscSigChanICmapStorageType,
--           mscVRouteDebugStorageType,
--           mscVsrSvsSnmpOperStatus,
--           mscVsrStorageType,
--           mscVsrSvsComponentName,
--           mscVsrSvsLCoReasonForNoRoute,
--           mscVsrActiveFaxRelayChannels,
--           mscSigChanForceNpiTon,
--           mscVsrAddressResolutionFailedCalls,
--           mscSigChanUsageState,
--           mscSigChanICmapSwitchCongestCause,
--           mscSigChanComponentName,
--           mscVsrDebugComponentName,
--           mscVsrVoiceRoute,
--           mscVsrAdminState,
--           mscVsrSvsLCoRequiredRxBandwidth,
--           mscVRouteDnaRowStatus,
--           mscVsrSvsFramerVfpDebugStorageType,
--           mscSigChanGwRequiredConversions,
--           mscVsrIfAdminStatus,
--           mscSigChanOperationalState,
--           mscSigChanICmapNoSuchChannelCause,
--           mscVRoutePrivateNetworkIdentifer,
--           mscVsrCustomerIdentifier,
--           mscVsrSvsLCoLastTearDownReason,
--           mscSigChanBchVsrInstance,
--           mscVsrSvsFramerPcmCaptureStorageType,
--           mscVRouteInterfaceFaxHangoverTimeG711G726,
--           mscVsrSvsLCoRequiredSecurity,
--           mscVsrSvsLCoPathFailureCount,
--           mscVsrSvsFramerModemFaxCells,
--           mscSigChanGwUnsupportedConversions,
--           mscVRouteDnaNumberingPlanIndicator,
--           mscVRouteInterfaceStorageType,
--           mscSigChanIfIndex,
--           mscVsrSvsIfIndex,
--           mscSigChanNcasRowStatus,
--           mscVsrSvsLCoPathFailureAction,
--           mscSigChanGwRowStatus,
--           mscVsrSvsLCoHoldingPriority,
--           mscVRouteInterfaceEgressAudioGain,
--           mscVsrSvsLCoRoundTripDelay,
--           mscVsrOperationalState,
--           mscVRouteInterfaceEcanBypassMode,
--           mscVsrSvsFramerMvpDebugComponentName,
--           mscVsrSvsLCoEnd,
--           mscVsrSvsLCoBytesFromNetwork,
--           mscVRouteAcctComponentName,
--           mscSigChanBchComponentName,
--           mscVRouteAcctAccountClass,
--           mscVsrActiveVoiceChannels,
--           mscVRouteAcctAccountingOptions,
--           mscVsrSvsFramerAdminState,
--           mscVsrSvsFramerNEncodingValue,
--           mscVsrSvsLCoPktsFromNetwork,
--           mscVsrSvsLCoBumpPreference,
--           mscVsrSvsFramerOpCurrentEncoding,
--           mscVsrSvsRowStatus,
--           mscVRouteAdminState,
--           mscVsrSvsFramerCurrentRate,
--           mscSigChanICmapTempFailureCause,
--           mscVsrActiveTptChannels,
--           mscVsrDebugRowStatus,
--           mscVsrSvsFramerFrmFromNetworkValue,
--           mscVsrPeakActiveDataChannels,
--           mscSigChanBchCalledDirectoryNumber,
--           mscSigChanICmapEgressLinkOutOfServCause,
--           mscVsrSvsLCoPathType,
--           mscVsrSvsFramerNegotiatedTandemPassThrough,
--           mscVsrSvsFramerComponentName,
--           mscVRouteCommentText,
--           mscVRouteInterfaceIngressAudioGain,
--           mscVRouteAcctDigitsSuppressed,
--           mscVRouteInterfaceEchoReturnLoss,
--           mscVsrSvsFramerNegotiatedFisG711G726,
--           mscVRouteInterfaceComponentName,
--           mscVsrDebugStorageType,
--           mscVRouteAcctAccountCollection,
--           mscSigChanNcasDirection,
--           mscVRouteSubroutesRowStatus,
--           mscVRouteStorageType,
--           mscVsrSvsOperationalState,
--           mscVsrSvsDebugStorageType,
--           mscVsrSvsLCoRequiredCustomerParameter,
--           mscVRouteInterfaceEchoTailDelay,
--           mscVRouteTotalCallsFromSubnet,
--           mscVRouteSubroutesValue,
--           mscVRouteVoiceNetworkingCallServer,
--           mscSigChanBchTimeSlot,
--           mscVRouteDebugComponentName,
--           mscVsrSvsFramerMvpDebugRowStatus,
--           mscVsrComponentName,
--           mscVsrSvsFramerAudioCells,
--           mscVsrSvsCallType,
--           mscSigChanICmapIncompatDestCause,
--           mscSigChanICmapChanOrCircNotAvailCause,
--           mscVRouteMinimumDigitsToRoute,
--           mscSigChanOctothorpeEod,
--           mscVRouteIfAdminStatus,
--           mscSigChanBchRowStatus,
--           mscSigChanCommentText,
--           mscVRouteCustomerIdentifier,
--           mscVsrInvalidNumberingPlanCalls,
--           mscVRouteHuntingAlgorithm,
--           mscVsrSvsStatus,
--           mscSigChanSubroutesRowStatus,
--           mscVRouteAcctServiceExchange,
--           mscVsrActiveChannels,
--           mscVsrSvsLCoSetupPriority,
--           mscSigChanNcasCallReference,
--           mscVsrTotalFailedCallsFromIf,
--           mscVsrSvsFramerPcmCaptureComponentName,
--           mscVRouteInterfaceStructuredEchoCancellationValue,
--           mscSigChanSubroutesValue,
--           mscVRouteCallsClearedNoChannel,
--           mscVsrSnmpOperStatus }
-- STATUS  mandatory
-- DESCRIPTION
--   "A list of all current accessible leaf objects."

voiceNetworkingGroup OBJECT IDENTIFIER ::= { voiceNetworkingMIB 1 }
voiceNetworkingGroupCA OBJECT IDENTIFIER ::= { voiceNetworkingGroup 1 }
voiceNetworkingGroupCA02 OBJECT IDENTIFIER ::= { voiceNetworkingGroupCA 3 }
voiceNetworkingGroupCA02A OBJECT IDENTIFIER ::= { voiceNetworkingGroupCA02 2 }



-- Agent-Capabilities Statement:

-- PRODUCT-RELEASE "MscPassport Release 1.2 VoiceNetworking."
-- STATUS          mandatory
-- DESCRIPTION     "Carrier Passport VoiceNetworking MIB: MIB Version CA02A,
--                  Software Version CA02S9C."
-- SUPPORTS        Nortel-MsCarrier-MscPassport-VoiceNetworkingMIB
--    INCLUDES     { voiceNetworkingGroupCA02A }

voiceNetworkingCapabilities OBJECT IDENTIFIER ::= { voiceNetworkingMIB 3 }
voiceNetworkingCapabilitiesCA OBJECT IDENTIFIER ::= { voiceNetworkingCapabilities 1 }
voiceNetworkingCapabilitiesCA02 OBJECT IDENTIFIER ::= { voiceNetworkingCapabilitiesCA 3 }
voiceNetworkingCapabilitiesCA02A OBJECT IDENTIFIER ::= { voiceNetworkingCapabilitiesCA02 2 }





END
