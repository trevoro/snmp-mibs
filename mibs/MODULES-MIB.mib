--=========================================================
--
-- MIB      : Modules                                                                LANNET Ltd
--
-- Version  : 8.6                                                                         13 Dec. 1998
--
-- RCS Id   : Yigal Nehaysi
--
--=========================================================
--
-- Copyright 1992,1993, 1994, 1995, 1996, 1997, 1998 LANNET,  Ltd.  
-- All Rights Reserved.  
--
-- Reproduction of this document is authorized on condition 
-- that the foregoing copyright notice is included.
--
-- This LANNET SNMP Management Information Base Specification
-- (Specification) embodies LANNET confidential and
-- proprietary intellectual property.  LANNET retains all
-- title and ownership in the Specification, including any revisions
--
-- It is LANNET's intent to encourage the widespread use of this
-- Specification in connection with the management of LANNET products.
-- LANNET grants vendors, end-users, and other interested parties
-- a non-exclusive license to use this Specification in connection
-- with the management of LANNET products.
--
-- This Specification is supplied "as is," and LANNET makes
-- no warranty, either express or implied, as to the use,
-- operation, condition, or performance of the Specification.
--
--=========================================================
--
-- RCS
--
-- Version 8.6
-- 13 Dec. 1998
-- 1. Move softRedundancy table from this file to config.mib - Yigal N.
-- 2. Change the title of the file to LANNET - Yigal N.
--
-- Version 8.5
-- Revision A. -	1. Change lntAtm to atmEdge - Gidi N.
-- 10 Apr. 1997	2. Add association table.         - Gidi N.
--
-- Revision B. -	1. Change associationEntryStatus to associationRowStatus and its
-- 1 May 1997	    enumertion values - Gidi N.
--
-- Revision C. -	1. Add 4 new items atmEdgePortILMIStatus, atmEdgePortSignalStatus,
-- 4 May 1997           atmEdgePortActualUNIVersion and atmEdgePortNetworkPrefix to 
--                               atmEdgePort Table.
--
-- Revision D. -	1. Moved atmedge and cti subtree into new mib file (atmedge.mib).
-- 21 July 1997	2. Add new mib item fethGroupFefiEnable to fethGroup table. - 
--	    Ronen Bar-Tal.
--
-- Version 8.0
-- Revision A.    - 1. spliting lannt80.mib into 3 files config, moduls and applic files
-- 15 Nov 1996        moduls contains eth, tok, ts, ltalk, cl, bRouter, lntFddi, lntAtm, cti sub-trees
--
--=========================================================

MODULES-MIB DEFINITIONS ::= BEGIN

IMPORTS
      IpAddress, Counter 
    FROM RFC1155-SMI
      OBJECT-TYPE
    FROM RFC-1212
      DisplayString
    FROM RFC1213-MIB
      lannet 
    FROM GEN-MIB;

-- Some MIB Compilers need these two lines:
--  enterprises  OBJECT IDENTIFIER ::= 
--                { iso org(3) dod(6) internet(1) private(4) 1 }


eth            OBJECT IDENTIFIER ::= { lannet 12 } -- ethernet group
tok            OBJECT IDENTIFIER ::= { lannet 13 } -- token ring group
ts             OBJECT IDENTIFIER ::= { lannet 14 } -- terminal server group 
ltalk          OBJECT IDENTIFIER ::= { lannet 15 } -- Local Talk group 
cl             OBJECT IDENTIFIER ::= { lannet 16 } -- clock group 
bRouter        OBJECT IDENTIFIER ::= { lannet 21 } -- bridges/routers group
lntFddiGroup    OBJECT IDENTIFIER ::= { lannet 25}  -- For LSF 100, fddi modules


-- Ethernet Agent group. The implementation of this group
-- is mandatory for all  chassis agents which use Ethernet as
-- in-band management protocol.

ethAg OBJECT IDENTIFIER
      ::= { eth 1 } 

ethAgTable OBJECT-TYPE
      SYNTAX  SEQUENCE OF EthAgEntry
      ACCESS  not-accessible
      STATUS  mandatory
      DESCRIPTION
      "Table of attributes which define configuration characteristics
      for  chassis SNMP agents which use Ethernet as in-band 
      management protocol."
      ::= { ethAg 1 } 

ethAgEntry OBJECT-TYPE
      SYNTAX  EthAgEntry
      ACCESS  not-accessible
      STATUS  mandatory
      DESCRIPTION
      "An entry in the table, containing data about a single Ethernet
      agent."
      INDEX  { ethAgId }
      ::= { ethAgTable 1 }

EthAgEntry  ::=
      SEQUENCE  {
	ethAgId
	  INTEGER,
	ethAgPerfBusSelection
	  INTEGER
      }

ethAgId OBJECT-TYPE
      SYNTAX  INTEGER (1..255)
      ACCESS  read-only
      STATUS  mandatory
      DESCRIPTION
      "Index which identifies the Ethernet agent for which the current 
      entry provides information."
      ::= { ethAgEntry 1 }
      
ethAgPerfBusSelection OBJECT-TYPE
      SYNTAX  INTEGER
      ACCESS  read-write
      STATUS  mandatory
      DESCRIPTION
      "Attribute describing the bus attached to the performance data collection 
      hardware on those  agent hardware implementations which support
      configuration management on multi-Ethernet bus enclosures, but performan-
      ce data collection on a single bus."
      ::= { ethAgEntry 2 }
      

-- Ethernet Group (module) group.
-- Implementation of this group is mandatory for all SNMP Agents which
-- manage the configuration of  Ethernet modules.

ethGroup OBJECT IDENTIFIER
      ::= { eth 2 } 


ethGroupTable OBJECT-TYPE
      SYNTAX  SEQUENCE OF EthGroupEntry
      ACCESS  not-accessible
      STATUS  mandatory
      DESCRIPTION
      "Table of attributes which define configuration characteristics
      for  Ethernet modules."
      ::= { ethGroup 1 }

ethGroupEntry OBJECT-TYPE
      SYNTAX  EthGroupEntry
      ACCESS  not-accessible
      STATUS  mandatory
      DESCRIPTION
      "An entry in the table, containing data about a single Ethernet
      module (group)."
      INDEX  { ethGroupId }
      ::= { ethGroupTable 1 }

EthGroupEntry  ::=
      SEQUENCE  {
	ethGroupId
	  INTEGER,
	ethGroupFIFO
	  INTEGER,
	ethGroup10BTPlus
	  INTEGER,
	ethGroupIntPortsRedundancy
	  INTEGER,
	ethGroupBackboneMode
	  INTEGER,
	ethGroupFOIRLPlusMode
	  INTEGER,
	ethGroupWrongPortSelection
	  INTEGER,
	ethGroupBackupBus
	  INTEGER,
	ethGroupSingleBusMode
	  INTEGER,
	ethGroupSpecificOID
	  OBJECT IDENTIFIER,
	ethGroup10FBPlus
	  INTEGER,
	ethGroupMasterClock
	  INTEGER,
	ethGroupIdleTrx
	  INTEGER,
	ethGroupTotalFrames
		  Counter,
	ethGroupTotalOctets
	  Counter,
	ethGroupTotalErrors
	  Counter,
	ethGroupBridgeMode
	   INTEGER,
	ethGroupBroadcastPkts 
	   Counter,
	ethGroupMulticastPkts 
	   Counter
      }

ethGroupId OBJECT-TYPE
      SYNTAX  INTEGER (1..255)
      ACCESS  read-only
      STATUS  mandatory
      DESCRIPTION
      "Index which identifies the group inside the chassis for which this
      entry contains information. Equals the number of the slot by which
      the group is accessed. This value is never greater than chNumberOfSlots."
      ::= { ethGroupEntry 1 }
      
ethGroupFIFO OBJECT-TYPE
      SYNTAX  INTEGER {
	on(1),
	off(2),
	notSupported(255)
      }
      ACCESS  read-only
      STATUS  mandatory
      DESCRIPTION
      "Value ON of this attribute describes an internal FIFO error sensed by 
      the internal hardware mechanism of a  repeater."
      ::= { ethGroupEntry 2 }
      
ethGroup10BTPlus OBJECT-TYPE
      SYNTAX  INTEGER {
	on(1),
	off(2),
	notSupported(255)
      }
      ACCESS read-write
      STATUS mandatory
      DESCRIPTION
      "Value ON of this attribute defines activation of the 10BaseTPlus
      mode - a  proprietary extension of the 10BaseT standard."
      ::= { ethGroupEntry 3 }
      
ethGroupIntPortsRedundancy OBJECT-TYPE
      SYNTAX  INTEGER {
	on(1),
	off(2),
	notSupported(255)
      }
      ACCESS read-write
      STATUS mandatory
      DESCRIPTION
      "Value ON of this attribute defines a redundancy (backup) relationship
      between internal ports 1 and 2 on a  module." 
      ::= { ethGroupEntry 4 }
      
ethGroupBackboneMode OBJECT-TYPE
      SYNTAX  INTEGER {
	on(1),
	off(2),
	notSupported(255)
      }
      ACCESS read-write
      STATUS mandatory
      DESCRIPTION
      "Value On of this attribute defines Backbone Mode of a sensor. Internal
      ports are enabled and the information path goes straightly from external 
      port to internal bus, via corresponding internal port."
      ::= { ethGroupEntry 5 }
      
ethGroupFOIRLPlusMode OBJECT-TYPE
      SYNTAX  INTEGER {
	on(1),
	off(2),
	notSupported(255)
      }
      ACCESS read-write
      STATUS mandatory
      DESCRIPTION
      "Value On of this attribute defines FOIRL of a sensor. When this attribute
      has value ON, FOIRL Plus mode is enabled, while value OFF indicates stan-
      dard FOIRL mode."
      ::= { ethGroupEntry 6 }
      
ethGroupWrongPortSelection OBJECT-TYPE
      SYNTAX  INTEGER {
	on(1),
	off(2),
	notSupported(255)
      }
      ACCESS  read-only
      STATUS  mandatory
      DESCRIPTION
      "A value ON of this attribute warns of incorrect selection of enabled
      ports on sensors which impose restrictions on this configura-
      tion (e.g. integrated local bridges.)"
      ::= { ethGroupEntry 7 }
      
ethGroupBackupBus OBJECT-TYPE
      SYNTAX  INTEGER (1..4) 
      ACCESS  read-write
      STATUS  mandatory
      DESCRIPTION
      "Defines the common secondary bus for Ethernet modules with bus 
      redundancy defined at port level."
      ::= { ethGroupEntry 8 }
      
ethGroupSingleBusMode OBJECT-TYPE
      SYNTAX  INTEGER {
	on(1),
	off(2),
	notSupported(255)
      }
      ACCESS  read-only
      STATUS  mandatory
      DESCRIPTION
      "Value 'on of this attribute defines bus-star mode for cards 
      supporting this type of configuration."
      ::= { ethGroupEntry 9 }

ethGroupSpecificOID OBJECT-TYPE
	SYNTAX OBJECT IDENTIFIER
	ACCESS read-only
	STATUS mandatory
	DESCRIPTION
	"This attribute provides the OID of another group containing 
	additional more specific information regarding this instance."
	::= { ethGroupEntry 10 }

--      Agent 6.0
ethGroup10FBPlus OBJECT-TYPE
	SYNTAX  INTEGER { on(1), off(2), notSupported(255) }
	ACCESS  read-write
	STATUS  mandatory
	DESCRIPTION
	"This variable enables/disables 10BaseFB plus mode."
	::= { ethGroupEntry 11 }


ethGroupMasterClock OBJECT-TYPE
	SYNTAX  INTEGER { on(1), off(2), notSupported(255) }
	ACCESS  read-only
	STATUS  mandatory
	DESCRIPTION
	"This attribute pertains to the SH-E16 chassis and defines the hub in the stack that
	generates the clock."
	::= { ethGroupEntry 12 }


ethGroupIdleTrx OBJECT-TYPE
	SYNTAX  INTEGER { on(1), off(2), notSupported(255) }
	ACCESS  read-write
	STATUS  mandatory
	DESCRIPTION
	"This attribute is relevant to the LE-120Q/SQ modules and when set to 'off' after 
	port disable terminates also light propagation (for redundancy tests)." 
	::= { ethGroupEntry 13 }
      

ethGroupTotalFrames  OBJECT-TYPE
	SYNTAX  Counter
	ACCESS  read-only
	STATUS  mandatory
	DESCRIPTION
	"The total number of frames of valid frame length that have been 
		  received on the ports in this group and for which the FCSError 
		  and CollisionEvent signals were not asserted.
		  This statistic provides one of the parameters necessary for obtaining 
		  the packet error rate.
		  The approximate minimum time for rollover of this counter is 80 hours. 
	  This item is a Repeater MIB counter."
	::= { ethGroupEntry 15}

ethGroupTotalOctets  OBJECT-TYPE
	SYNTAX  Counter
	ACCESS  read-only
	STATUS  mandatory
	DESCRIPTION
	"The total number of octets contained in the valid frames that have 
		  been received on the ports in this group.  This counter is the summation of the
		  values of the ethPortReadableOctets counters for all of the ports in the group.
		 This statistic provides an indicator of the total data transferred.  The approximate 
		 minimum time for rollover of this counter is 58 minutes.
	 This item is a Repeater MIB counter."
	::= { ethGroupEntry 16}

ethGroupTotalErrors  OBJECT-TYPE
	SYNTAX  Counter
	ACCESS  read-only
	STATUS  mandatory
	DESCRIPTION
	"The total number of errors which have occurred on all of the ports in this group. 
		  This counter is the summation of the values of the ethPortTotalErrors counters 
		  for all of the ports in the group.
	  This item is a Repeater MIB counter."
	::= { ethGroupEntry 17}

ethGroupBridgeMode OBJECT-TYPE
	SYNTAX  INTEGER {
		bus1Tobus2(3),
		bus1ToAUIPort(5),
		bus2ToAUIPort(6),
		bus1To10BTPort(9),
		bus2To10BTPort(10),
		portAUITo10BTPort(12)
	}
	ACCESS  read-write
	STATUS  mandatory
	DESCRIPTION
	"This attribute defines between which buses/ports
	  the IELB bridge is bridging."
	::= { ethGroupEntry 18 }

ethGroupBroadcastPkts OBJECT-TYPE
	      SYNTAX Counter
	      ACCESS read-only
	      STATUS mandatory
	      DESCRIPTION
		  "The total number of good packets received that were
		  directed to the broadcast address, through this ports group."
	::= { ethGroupEntry 19 }

ethGroupMulticastPkts OBJECT-TYPE
	      SYNTAX Counter
	      ACCESS read-only
	      STATUS mandatory
	      DESCRIPTION
		  "The total number of good packets received that were
		  directed to a multicast address, through this ports group.
		  Note that this number does not include packets directed to the
		  broadcast address."
	::= { ethGroupEntry 20 }


ethPort OBJECT IDENTIFIER       
      ::= { eth 3 } 


ethPortTable OBJECT-TYPE
      SYNTAX    SEQUENCE OF EthPortEntry
      ACCESS    not-accessible
      STATUS    mandatory
      ::= { ethPort 1 } 

ethPortEntry OBJECT-TYPE
      SYNTAX    EthPortEntry
      ACCESS    not-accessible
      STATUS    mandatory
      INDEX     { ethPortGroupId, ethPortId }
      ::= { ethPortTable 1 }

EthPortEntry ::=
   SEQUENCE {
      ethPortGroupId INTEGER,
      ethPortId INTEGER,
      ethPortFunctionalStatus INTEGER,
      ethPortManPart INTEGER,
      ethPortJabber INTEGER,
      ethPortNoAUILoop INTEGER,
      ethPortMJLP INTEGER,
      ethPortFIFO INTEGER,
      ethPortAutoPartitionState INTEGER,
      ethPortSQETest INTEGER,
      ethPortLastSourceAddr OCTET STRING,
      ethPortUserStatus INTEGER,
      ethPortMainBusSelection INTEGER,
      ethPortTraffic Counter,
      ethPortFramesReceivedOK Counter,
      ethPortRunts Counter,
      ethPortPacketErrors Counter,
      ethPortSpecificOID OBJECT IDENTIFIER,
      ethPortCollisions Counter,
      ethPortPartitions Counter,
      ethPortPygmys Counter,
      ethPortJabberCounter Counter,
      ethPortCoupling INTEGER,
      ethPortPolarity INTEGER,
      ethPortReadableFrames  Counter,
      ethPortReadableOctets Counter,
      ethPortFCSErrors Counter,
      ethPortAlignmentErrors Counter,
      ethPortFramesTooLong Counter,
      ethPortLateEvents Counter,
      ethPortVeryLongEvents Counter,
      ethPortDataRateMismatches Counter,
      ethPortTotalErrors Counter,
      ethPortSourceAddrChanges Counter,
      ethPortOperStatus INTEGER,
      ethPortBroadcastPkts Counter,
      ethPortMulticastPkts Counter
   }

ethPortGroupId OBJECT-TYPE
      SYNTAX  INTEGER
      ACCESS  read-only
      STATUS  mandatory
      DESCRIPTION
      "Id of the group to which the port belongs."
      ::= { ethPortEntry 1 }
      
ethPortId OBJECT-TYPE
      SYNTAX  INTEGER
      ACCESS  read-only
      STATUS  mandatory
      DESCRIPTION
      "Unique Id of the port in the ethPortTable."
      ::= { ethPortEntry 2 }
      
ethPortFunctionalStatus OBJECT-TYPE
      SYNTAX  INTEGER {
	ok(1),
	rld(2),            -- RxLinkDown (Link Test Fail)
	localJabber(3),
	tld(4),            -- TxLinkDown (Remote Link Down)
	remoteJabber(5),
	illSeq(6),
	shortCirc(7),
	partitionOrLocalJabber(8),
	remoteFaultOrLockLost(9),
	remoteFault(10),
	lockLost(11),
	notSupported(255)
      }
      ACCESS  read-only
      STATUS  mandatory
      DESCRIPTION
      "The value of this attribute reflects the functional status of 
      synchronous ports. Note that it is not mandatory that all ports
      support all the enumerated states. 
      ok(1) - fully functional port, transmitting and receiving packets.
      rld(2) - receive link down condition on the port - Indicates a cable 
      or connector failure detected by the port H/W.
      localJabber(3) - fault condition indicating that the port emitted 
      jabber (excessive long transmission)
      tld(4) - transmit link down condition on the port - Indicates a cable or 
      connector failure detected by the H/W of a port connected to the monitored port.
      remoteJabber(5) - fault condition indicating that remote jabber was sensed
      at the port.
      illSeq(6) - fault condition indicating an illegal synchronization sequence
      at the port.
      shortCircuit(7) - short-circuit fault condition detected at the port.
      partitionOrLocalJabber(8) - one of the partition or local jabber (excessive 
      long transmission) was detected at the port of an optical repeater ) -
      remoteFaultOrLockLoss(9) - one of optical repeater fault conditions, 
      detected by the port H/W.
      remoteFault(10) - fault condition, detected by an optical port connected
      to the monitored port.
      lockLost(11) - optical port H/W fault.  "
      ::= { ethPortEntry 3 }
      
ethPortManPart OBJECT-TYPE
      SYNTAX  INTEGER {
	on(1),
	off(2),
	notSupported(255)
      }
      ACCESS  read-write
      STATUS  mandatory
      DESCRIPTION
      "Setting the value of this attribute to ON activates the manual
      partition mechanism at the port  level. Setting the value of this
      attribute to OFF cancels the partition mechanism. The segment
       may reconnect after the reception of 32 packets. Attribute vaild
       for repeater modules from the LE-10 family."
      ::= { ethPortEntry 4 }
      
ethPortJabber OBJECT-TYPE
      SYNTAX  INTEGER {
	on(1),
	off(2),
	notSupported(255)
      }
      ACCESS  read-only
      STATUS  mandatory
      DESCRIPTION
      "Value ON of this attribute reflects jabber transmitted to the port by
      the hardware of a  repeater or transceiver, as a result of
      collisions detected on the port. Valid for all modules in the LE-10 and
      LE-15 families."
      ::= { ethPortEntry 5 }
      
ethPortNoAUILoop OBJECT-TYPE
      SYNTAX  INTEGER {
	on(1),
	off(2),
	notSupported(255)
      }
      ACCESS  read-only
      STATUS  mandatory
      DESCRIPTION
      "Value ON of this attribute indicates that a No AUI Loop fault condition
      was detected on an AUI repeater port. Valid for LE-10C family of modu-
      les."
      ::= { ethPortEntry 6 }
      
ethPortMJLP OBJECT-TYPE
      SYNTAX  INTEGER {
	on(1),
	off(2),
	notSupported(255)
      }
      ACCESS  read-only
      STATUS  mandatory
      DESCRIPTION
      "Value ON of this attribute describes an internal MJLP (MAU Jabber
      Lockup Protection) error sensed by the internal hardware mechanism
      of a  repeater. This mechanism is activated to protect the repeater ports
      from a jabber condition (excessive long transmission) detected on one
      of the port.
      Valid for LE140XTF."
      ::= { ethPortEntry 7 }
      
ethPortFIFO OBJECT-TYPE
      SYNTAX  INTEGER {
	on(1),
	off(2),
	notSupported(255)
      }
      ACCESS  read-only
      STATUS  mandatory
      DESCRIPTION
      "Value ON of this attribute describes an internal FIFO error sensed by the
      internal hardware mechanism of a  repeater.  Valid for LE140XTF."
      ::= { ethPortEntry 8 }
      
ethPortAutoPartitionState OBJECT-TYPE
      SYNTAX  INTEGER {
	autoPartition(1),
	notAutoPartition(2),
	notSupported(255)
      }
      ACCESS  read-only
      STATUS  mandatory
      DESCRIPTION
      "The AutoPart condition indicates that the port is currently partitioned
      by the auto-partition protection mechanism."
      ::= { ethPortEntry 9 }
      
ethPortSQETest OBJECT-TYPE
      SYNTAX  INTEGER {
	enabled(1),
	disabled(2),
	notSupported(255)
      }
      ACCESS  read-write
      STATUS  mandatory
      DESCRIPTION
      "Settable attribute which allows activation of SQE test for 
       integrated transceivers."
      ::= { ethPortEntry 10 }
      
ethPortLastSourceAddr OBJECT-TYPE
      SYNTAX  OCTET STRING
      ACCESS  read-write
      STATUS  mandatory
      DESCRIPTION
      "Ethernet source address of the last readable frame received by this port.
	The value of this item may be set to 000000 (a string of 6 zeros) by a
	management console, but not to any other value. "     
 ::= { ethPortEntry 11 }
      
ethPortUserStatus OBJECT-TYPE
      SYNTAX  INTEGER {
	singleUser(1),
	multiUser(2),
	notSupported(255)
      }
      ACCESS  read-only
      STATUS  mandatory
      DESCRIPTION
      "Attribute defining the connection of a port to a single Ethernet source
      or to a multi-source (segment or star)."
      ::= { ethPortEntry 12 }
      
ethPortMainBusSelection OBJECT-TYPE
      SYNTAX  INTEGER 
      ACCESS  read-write
      STATUS  mandatory
      DESCRIPTION
      "On cards with port-level redundancy, defines the main bus for each 
      port instance as selected by user."
      ::= { ethPortEntry 13 }
      
ethPortTraffic OBJECT-TYPE
      SYNTAX  Counter
      ACCESS  read-only
      STATUS  mandatory
      DESCRIPTION
      "Counter for the number of bits received on this port in frames with legal
      length information."
      ::= { ethPortEntry 14 }
      
ethPortFramesReceivedOK OBJECT-TYPE
      SYNTAX  Counter
      ACCESS  read-only
      STATUS  mandatory
      DESCRIPTION
      "A representation of the total  number of frames of legal length that have
      not been corrupted in transmission. These frames can be encoded and 
      decoded by the commonly available MACs and provide a measure of the 
      network bandwidth being used. The number does not include frames received 
      with frame-too-long, FCS, alignment errors, frames lost due to internal 
      MAC sublayer errors, runts or pygmys."
      ::= { ethPortEntry 15 }
      
ethPortRunts OBJECT-TYPE
      SYNTAX  Counter
      ACCESS  read-only
      STATUS  mandatory
      DESCRIPTION
	       "This counter is incremented by one for each
	       CarrierEvent on this port that meets one of the
	       following two conditions.  Only one test need be
	       made.  a) The ActivityDuration is greater than
	       ShortEventMaxTime and less than ValidPacketMinTime
	       and the CollisionEvent signal is deasserted.  b)
	       The OctetCount is less than 64, the
	       ActivityDuration is greater than ShortEventMaxTime
	       and the CollisionEvent signal is deasserted.
	       ValidPacketMinTime is greater than or equal to 552
	       bit times and less than 565 bit times.

	       An event whose length is greater than 74 bit times
	       but less than 82 bit times shall increment either
	       the shortEvents counter or the runts counter but
	       not both.  A CarrierEvent greater than or equal to
	       552 bit times but less than 565 bit times may or
	       may not be counted as a runt.
	       ValidPacketMinTime has tolerances included to
	       provide for circuit losses between a conformance
	       test point at the AUI and the measurement point
	       within the state machine.

	       Runts usually indicate collision fragments, a
	       normal network event.  In certain situations
	       associated with large diameter networks a
	       percentage of collision fragments may exceed
	       ValidPacketMinTime.

	       The approximate minimum time for rollover of this
	       counter is 16 hours.
       REFERENCE
	       Reference IEEE 802.3 Rptr Mgt, 19.2.6.2, aRunts."
      ::= { ethPortEntry 16 }
      
ethPortPacketErrors OBJECT-TYPE
      SYNTAX  Counter
      ACCESS  read-only
      STATUS  mandatory
      DESCRIPTION
      "Counter for the number of frames with errors detected on the port by
      the  agent hardware. This generic port error comprises too long
      packets, CRC and alignment errors."
      ::= { ethPortEntry 17 }
      
ethPortSpecificOID OBJECT-TYPE
	SYNTAX OBJECT IDENTIFIER
	ACCESS read-only
	STATUS mandatory
	DESCRIPTION
	"This attribute provides the OID of another group containing 
	additional more specific information regarding this instance."
	::= { ethPortEntry 18 }

ethPortCollisions OBJECT-TYPE
	SYNTAX  Counter
	ACCESS  read-only
	STATUS  mandatory
	DESCRIPTION
	"This counter is incremented by one for any
	       CarrierEvent signal on any port for which the
	       CollisionEvent signal on this port is also
	       asserted.

	       The approximate minimum time for rollover of this
	       counter is 16 hours.
	Relevant for MPR and HIMIB modules.
       REFERENCE
	       Reference IEEE 802.3 Rptr Mgt, 19.2.6.2,
	       aCollisions."
	::= { ethPortEntry 19 }

ethPortPartitions OBJECT-TYPE
	SYNTAX  Counter
	ACCESS  read-only
	STATUS  mandatory
	DESCRIPTION
	       "This counter is incremented by one for each time
	       the repeater has automatically partitioned this
	       port.  The conditions that cause port partitioning
	       are specified in the partition state machine in
	       Section 9 [IEEE 802.3 Std].  They are not
	       differentiated here.
	Relevant for MPR and HIMIB modules.
       REFERENCE
	       Reference IEEE 802.3 Rptr Mgt, 19.2.6.2,
	       aAutoPartitions."
	::= { ethPortEntry 20 }

ethPortPygmys OBJECT-TYPE
	SYNTAX  Counter
	ACCESS  read-only
	STATUS  mandatory
	DESCRIPTION
	"The number of pygmys observed on a specified port.
	The pygmy is a short event.
	       This counter is incremented by one for each
	       CarrierEvent on this port with ActivityDuration
	       less than ShortEventMaxTime.  ShortEventMaxTime is
	       greater than 74 bit times and less than 82 bit
	       times.  ShortEventMaxTime has tolerances included
	       to provide for circuit losses between a
	       conformance test point at the AUI and the
	       measurement point within the state machine.

	       Note:  shortEvents may indicate externally
	       generated noise hits which will cause the repeater
	       to transmit Runts to its other ports, or propagate
	       a collision (which may be late) back to the
	       transmitting DTE and damaged frames to the rest of
	       the network.

	       Implementors may wish to consider selecting the
	       ShortEventMaxTime towards the lower end of the
	       allowed tolerance range to accommodate bit losses
	       suffered through physical channel devices not
	       budgeted for within this standard.

	       The approximate minimum time for rollover of this
	       counter is 16 hours.
       REFERENCE
	       Reference IEEE 802.3 Rptr Mgt, 19.2.6.2,
	       aShortEvents."
	::= { ethPortEntry 21 }

ethPortJabberCounter OBJECT-TYPE
	SYNTAX  Counter
	ACCESS  read-only
	STATUS  mandatory
	DESCRIPTION
	"Counter for the number of local jabbers detected on a specific port (LE-115Q)."
	::= { ethPortEntry 22 }

ethPortCoupling  OBJECT-TYPE
	SYNTAX  INTEGER { dc(1), ac(2), notSupported(255) }
	ACCESS  read-only
	STATUS  mandatory
	DESCRIPTION
	"Indication of port's coupling method in Ethernet transceiver 
	modules (LE-115Q).
	The coupling methode can be set on board, using specific jumpers."
	::= { ethPortEntry 23 }

ethPortPolarity  OBJECT-TYPE
	SYNTAX  INTEGER {
		 ok(1),
		 crossed(2),
		 notSupported(255)
	 }
	ACCESS  read-only
	STATUS  mandatory
	DESCRIPTION
	"This item defines the polarity state of the connection to LE-240XTC 
	and LE-280XT ports. If the wires are crossed, the value is crossed(2),
	otherwise ok(1)."
	::= { ethPortEntry 24 }

ethPortReadableFrames OBJECT-TYPE
       SYNTAX    Counter
       ACCESS    read-only
       STATUS    mandatory
       DESCRIPTION
	       "This object is the number of frames of valid
	       frame length that have been received on this port.
	       This counter is incremented by one for each frame
	       received on this port whose OctetCount is greater
	       than or equal to minFrameSize and less than or
	       equal to maxFrameSize (Ref: IEEE 802.3 Std,
	       4.4.2.1) and for which the FCSError and
	       CollisionEvent signals are not asserted.

	       This statistic provides one of the parameters
	       necessary for obtaining the packet error rate.
	       The approximate minimum time for rollover of this
	       counter is 80 hours.
       REFERENCE
	       Reference IEEE 802.3 Rptr Mgt, 19.2.6.2,
	       aReadableFrames."
       ::= { ethPortEntry 25 }

ethPortReadableOctets  OBJECT-TYPE
	SYNTAX  Counter
	ACCESS  read-only
	STATUS  mandatory
	DESCRIPTION
	"This counter is the number of octets contained in valid frames that have 
		been received on this port.It is incremented for each frame received on this 
		port which has been determined to be a readable frame (including FCS octets
		but excluding framing bits and dribble bits).
	       This statistic provides an indicator of the total data transferred.  The
	       approximate minimum time for rollover of this counter is 58 minutes.
	       This object is a Repeater MIB counter."
	::= { ethPortEntry 26 }

ethPortFCSErrors  OBJECT-TYPE
	SYNTAX  Counter
	ACCESS  read-only
	STATUS  mandatory
	DESCRIPTION
	"This counter is incremented by one for each frame received on this port with 
		the FCSError signal asserted and the FramingError and CollisionEvent signals 
	       deasserted and whose OctetCount is greater than or equal to minFrameSize
	       and less than or equal to maxFrameSize (Ref: 4.4.2.1, IEEE 802.3 Std). The 
	       approximate minimum time for rollover of this counter is 80 hours.
	       This object is a Repeater MIB counter."
	::= { ethPortEntry 27 }

ethPortAlignmentErrors  OBJECT-TYPE
	SYNTAX  Counter
	ACCESS  read-only
	STATUS  mandatory
	DESCRIPTION
	"This counter is incremented by one for each frame received on this port with 
		the FCSError and FramingError signals asserted and CollisionEvent signal 
	       deasserted and whose OctetCount is greater than or equal to minFrameSize and
		less than or equal to maxFrameSize (Ref: IEEE 802.3 Std, 4.4.2.1).  The approximate             minimum time for rollover of this counter is 80 hours.
		This object is a Repeater MIB counter."
	::= { ethPortEntry 28 }

ethPortFramesTooLong  OBJECT-TYPE
	SYNTAX  Counter
	ACCESS  read-only
	STATUS  mandatory
	DESCRIPTION
	"This counter is incremented by one for each frame received on this port whose
		OctetCount is greater than maxFrameSize (Ref: 4.4.2.1, IEEE 802.3 Std). The 
	approximate minimum time for rollover of this counter is 61 days.
		This object is a Repeater MIB counter."
	::= { ethPortEntry 29 }

ethPortLateEvents  OBJECT-TYPE
	SYNTAX  Counter
	ACCESS  read-only
	STATUS  mandatory
	DESCRIPTION
	"This counter is incremented by one for each CarrierEvent on this port in which
	 the CollIn(X) variable transitions to the value SQE (Ref:9.6.6.2, IEEE 802.3 Std) 
	while the ActivityDuration is greater than the LateEventThreshold.  Such a
	CarrierEvent is counted twice, as both a collision and as a lateEvent. The 
	approximate minimum time for rollover of this counter is 81 hours.
	This object is a Repeater MIB counter."
	::= { ethPortEntry 30 }

ethPortVeryLongEvents  OBJECT-TYPE
	SYNTAX  Counter
	ACCESS  read-only
	STATUS  mandatory
	DESCRIPTION
	"This counter is incremented by one for each CarrierEvent on this port whose
	ActivityDuration is greater than the MAU Jabber Lockup Protection timer TW3 
	(Ref: 9.6.1 & 9.6.5, IEEE 802.3 Std). Other counters may be incremented as appropriate.
	This object is a Repeater MIB counter."
	::= { ethPortEntry 31 }

ethPortDataRateMismatches  OBJECT-TYPE
	SYNTAX  Counter
	ACCESS  read-only
	STATUS  mandatory
	DESCRIPTION
	"This counter is incremented by one for each frame received on this port that 
	meets all of the following conditions:  
		a) The CollisionEvent signal is not asserted.  
		b) The ActivityDuration is greater than ValidPacketMinTime.  
		c) The frequency (data rate) is detectably mismatched from the local 
		transmit frequency.
	This object is a Repeater MIB counter."
	::= { ethPortEntry 32 }

ethPortTotalErrors  OBJECT-TYPE
	SYNTAX  Counter
	ACCESS  read-only
	STATUS  mandatory
	DESCRIPTION
	"The total number of errors which have occurred on this port.  This counter 
	is the summation of the values of other error counters (for the same port), namely:
		ethPortFCSErrors,
			ethPortAlignmentErrors,
			ethPortFrameTooLongs,
			ethPortShortEvents,
			ethPortLateEvents,
			ethPortVeryLongEvents, and
			ethPortDataRateMismatches.
	This object is a Repeater MIB counter."
	::= { ethPortEntry 33 }

ethPortSourceAddrChanges  OBJECT-TYPE
	SYNTAX  Counter
	ACCESS  read-only
	STATUS  mandatory
	DESCRIPTION
	"This counter is incremented by one for each time that the last source address 
	of frames entering this port has changed. This may indicate whether a link is 
	connected to a single DTE or another multi-user segment. The approximate 
	minimum time for rollover of this counter is 81 hours.
	This object is a Repeater MIB counter."
	::= { ethPortEntry 34}

ethPortOperStatus  OBJECT-TYPE
	SYNTAX  INTEGER  {
		   operational(1),
			   notOperational(2),
		   notSupported(255)
	}
	ACCESS  read-only
	STATUS  mandatory
	DESCRIPTION
	"This object indicates the port's operational status.  The operational(1) status 
	indicates that the port is enabled and working, even though it might be auto-partitioned."
	::= { ethPortEntry 35}

ethPortBroadcastPkts OBJECT-TYPE
	      SYNTAX Counter
	      ACCESS read-only
	      STATUS mandatory
	      DESCRIPTION
		  "The total number of good packets received that were
		  directed to the broadcast address."
	::= { ethPortEntry 36}

ethPortMulticastPkts OBJECT-TYPE
	      SYNTAX Counter
	      ACCESS read-only
	      STATUS mandatory
	      DESCRIPTION
		  "The total number of good packets received that were
		  directed to a multicast address.  Note that this
		  number does not include packets directed to the
		  broadcast address."
	::= { ethPortEntry 37}


ethIntPort OBJECT IDENTIFIER
      ::= { eth 4 }


ethIntPortTable OBJECT-TYPE
      SYNTAX  SEQUENCE OF EthIntPortEntry
      ACCESS  not-accessible
      STATUS mandatory
      ::= { ethIntPort 1 }

ethIntPortEntry OBJECT-TYPE
      SYNTAX    EthIntPortEntry
      ACCESS    not-accessible
      STATUS    mandatory
      INDEX     { ethIntPortGroupId, ethIntPortId }
      ::= { ethIntPortTable 1 }

EthIntPortEntry ::=
      SEQUENCE {
	 ethIntPortGroupId 
	    INTEGER,
	 ethIntPortId
	    INTEGER,
	 ethIntPortPartition 
	    INTEGER,
	 ethIntPortJabber 
	    INTEGER,
	 ethIntPortBackedUp 
	    INTEGER
      }

ethIntPortGroupId OBJECT-TYPE
      SYNTAX  INTEGER (1..255)
      ACCESS  read-only
      STATUS  mandatory
      DESCRIPTION
      "ID of the group to which the internal port belongs."
      ::= { ethIntPortEntry 1 }
      
ethIntPortId OBJECT-TYPE
      SYNTAX  INTEGER (1..255)
      ACCESS  read-only
      STATUS  mandatory
      DESCRIPTION
      "ID of the internal port in the ethIntPortTable."
      ::= { ethIntPortEntry 2 }
      
ethIntPortPartition OBJECT-TYPE
      SYNTAX  INTEGER {
	on(1),
	off(2),
	notSupported(255)
      }
      ACCESS  read-only
      STATUS  mandatory
      DESCRIPTION
      "This condition indicates that the internal port is currently partitioned
      from the bus by the auto-partition protection mechanism."
      ::= { ethIntPortEntry 3 }
      
ethIntPortJabber OBJECT-TYPE
      SYNTAX  INTEGER {
	on(1),
	off(2),
	notSupported(255)
      }
      ACCESS  read-only
      STATUS  deprecated
      DESCRIPTION
      "Value ON of this attribute reflects jabber being transmitted to the bus 
      by the hardware of a  repeater, as a result of collisions detected 
      on the internal bus of the enclosure. This situation is similar to MJLP
      as defined by the Repeater Management standard."
      ::= { ethIntPortEntry 4 }
      
ethIntPortBackedUp OBJECT-TYPE
      SYNTAX INTEGER {
	on(1),
	off(2),
	notSupported(255)
      }
      ACCESS   read-write
      STATUS   mandatory
      DESCRIPTION
      "Indicates that internal port is part of a redundancy scheme."
      ::= { ethIntPortEntry 5 }

      

ethBus OBJECT IDENTIFIER
      ::= { eth 5 } 


ethBusPerfTable OBJECT-TYPE       
      SYNTAX  SEQUENCE OF EthBusPerfEntry
      ACCESS  not-accessible
      STATUS mandatory
      ::= { ethBus 1 }
 
ethBusPerfEntry OBJECT-TYPE
      SYNTAX    EthBusPerfEntry
      ACCESS    not-accessible
      STATUS    mandatory
      INDEX     { ethBusPerfAgId, ethBusPerfId }
      ::= { ethBusPerfTable 1 }
 
EthBusPerfEntry ::=
      SEQUENCE {
	 ethBusPerfAgId
	    INTEGER,
	 ethBusPerfId
	    INTEGER,
	 ethBusTrafficBuffer
	    OCTET STRING,
	 ethBusTrafficThresh
	    INTEGER,
	 ethBusPeakTraffic
	    INTEGER,
	 ethBusTotalCollisions
	    Counter,
	 ethBusTotalPackets
	    Counter,
	 ethBusTotalErrors
	    Counter,
	 ethBusTraffic
	    INTEGER,
	 ethBusUtilization
	    INTEGER,
	 ethBusPeakUtilization
	    INTEGER,
	ethBusThresholdStatus  
	    OCTET STRING 

      }

ethBusPerfAgId OBJECT-TYPE
      SYNTAX  INTEGER (1..255)
      ACCESS  read-only
      STATUS  mandatory
      DESCRIPTION
      "ID of the agent in the ethBusPerfTable."
      ::= { ethBusPerfEntry 1 }
      
ethBusPerfId OBJECT-TYPE
      SYNTAX  INTEGER (1..255)
      ACCESS  read-only
      STATUS  mandatory
      DESCRIPTION
      "ID of the bus in the ethBusPerfTable."
      ::= { ethBusPerfEntry 2 }
      
ethBusTrafficBuffer OBJECT-TYPE
      SYNTAX  OCTET STRING
      ACCESS  read-only
      STATUS  deprecated
      DESCRIPTION
      "Record of traffic for the last second with a resolution of 100 msec. The
       traffic is expressed in percents of the maximum Ethernet traffic and each
      record contains 10 readings, in the range 1..20, expressed on a log(10)
      scale ( value = 10*log10(percent) )."
      ::= { ethBusPerfEntry 3 }
      
ethBusTrafficThresh OBJECT-TYPE
      SYNTAX  INTEGER
      ACCESS  read-write
      STATUS  mandatory
      DESCRIPTION
      "Traffic threshold value. When exceeded, a trap is send to the management
      console. Expressed in percents of the maximum Ethernet traffic, in the
      range 1..20, expressed on a log(10) scale."
      ::= { ethBusPerfEntry 4 }
      
ethBusPeakTraffic OBJECT-TYPE
      SYNTAX  INTEGER                -- Values 1..20 (Log(10) scale)
      ACCESS  read-write
      STATUS  mandatory
      DESCRIPTION
      "Maximal traffic value since last reset of hub or relay. Expressed in per-
      cents of the maximum Ethernet traffic, in the range 1..20,
      expressed on log(10) scale.
      The write access is reserved for resetting the value of the peak."
      ::= { ethBusPerfEntry 5 }
      
ethBusTotalCollisions OBJECT-TYPE
      SYNTAX  Counter
      ACCESS  read-only
      STATUS  mandatory
      DESCRIPTION
      "Counter incremented every time the hub enters a condition caused by
      simultaneous transmission and detection of external activity on one or
      more of its ports."
      ::= { ethBusPerfEntry 6 }
      
ethBusTotalPackets OBJECT-TYPE
      SYNTAX  Counter
      ACCESS  read-only
      STATUS  mandatory
      DESCRIPTION
      "Counter for number of packets (good and errors) detected on the
      Ethernet bus."
      ::= { ethBusPerfEntry 7 }
      
ethBusTotalErrors OBJECT-TYPE
      SYNTAX  Counter
      ACCESS  read-only
      STATUS  mandatory
      DESCRIPTION
      "Counter for number of errors detected on the Ethernet bus. Does not
      take into account the collisions."
      ::= { ethBusPerfEntry 8 }

ethBusTraffic OBJECT-TYPE
      SYNTAX  INTEGER
      ACCESS  read-only
      STATUS  mandatory
      DESCRIPTION
      "Last traffic reading (sampling time =  100 msec). The
      traffic is expressed in percents of the maximum Ethernet traffic
      in the range 1..20, expressed on a log(10)
      scale ( value = 10*log10(percent) )."
      ::= { ethBusPerfEntry 9 }

ethBusUtilization OBJECT-TYPE
	SYNTAX  INTEGER
	ACCESS  read-only
	STATUS  mandatory
	DESCRIPTION
	"Last traffic reading (sampling time =  100 msec). The  traffic is expressed
	 in percents of the maximum Ethernet traffic."
	::= { ethBusPerfEntry 10 }

ethBusPeakUtilization OBJECT-TYPE
	SYNTAX  INTEGER
	ACCESS  read-only
	STATUS  mandatory
	DESCRIPTION
	"Maximal traffic value since last reset of agent. Expressed in percents
	of the maximum effective Ethernet traffic."
	::= { ethBusPerfEntry 11 }

 ethBusThresholdStatus  OBJECT-TYPE  
	SYNTAX  OCTET STRING ( SIZE (4))
	ACCESS  read-only
	STATUS  mandatory
	DESCRIPTION
		"This item is a bitmap that defines the threshold status of the 
		bus, in relation to the alarmPolicyTable. If the bus is monitored 
		by the agent according to policy number x in the 
		alarmPolicyTable, and the threshold condition has occured, 
		then the bit #x in this item will have the value '1'. Otherwise it 
		will be '0'. For x-186 based agents all bits of this item are '0'."
	::= { ethBusPerfEntry 12 }
     

ethBusClockTable OBJECT-TYPE
      SYNTAX  SEQUENCE OF EthBusClockEntry
      ACCESS  not-accessible
      STATUS mandatory
      ::= { ethBus 2 }
 
ethBusClockEntry OBJECT-TYPE
      SYNTAX    EthBusClockEntry
      ACCESS    not-accessible
      STATUS    mandatory
      INDEX     { ethBusClockBusId, ethBusClockId }
      ::= { ethBusClockTable 1 }
 
EthBusClockEntry ::=
      SEQUENCE {
	 ethBusClockBusId
	    INTEGER,
	 ethBusClockId
	    INTEGER,
	 ethBusClockTestResult
	    INTEGER
      }

ethBusClockBusId OBJECT-TYPE
      SYNTAX  INTEGER (1..255)
      ACCESS  read-only
      STATUS  mandatory
      DESCRIPTION
      "ID of the bus in the ethBusClockTable."
      ::= { ethBusClockEntry 1 }
      
ethBusClockId OBJECT-TYPE
      SYNTAX  INTEGER (1..255)
      ACCESS  read-only
      STATUS  mandatory
      DESCRIPTION
      "ID of the clock in the ethBusClockTable."
      ::= { ethBusClockEntry 2 }
      
ethBusClockTestResult OBJECT-TYPE
      SYNTAX  INTEGER {
	ok(1),
	clockFailure(2),
	busFailure(3),
	notSupported(255)
      }
      ACCESS  read-only
      STATUS  mandatory
      DESCRIPTION
      "Values clockFailure(2) and busFailure(3) define the faulty status for
      clock tests. The test is performed by LCL100 module."
      ::= { ethBusClockEntry 3 }


feth OBJECT IDENTIFIER
	::= { eth 6}

--
-- The Basic Port Table & Port Monitor Table  & Port Address Tracking Table
--


fethPort OBJECT IDENTIFIER
	::= { feth 1 }

fethPortTable OBJECT-TYPE
      SYNTAX    SEQUENCE OF FethPortEntry
      ACCESS    not-accessible
      STATUS    mandatory
      DESCRIPTION
     "Table of descriptive, status, performance and error
      information about the ports."
      ::= { fethPort 1 } 

fethPortEntry OBJECT-TYPE
      SYNTAX    FethPortEntry
      ACCESS    not-accessible
      STATUS    mandatory
      DESCRIPTION
     "An entry in the table, containing information,
      performance and  error statistics about a single port." 
      INDEX     { fethPortGroupId, fethPortId }
      ::= { fethPortTable 1 }

FethPortEntry ::=
   SEQUENCE {
      fethPortGroupId INTEGER,
      fethPortId INTEGER,
      fethPortFunctionalStatus INTEGER,
      fethPortFIFO INTEGER,
      fethPortOperStatus INTEGER,
      fethPortAutoPartitionState  INTEGER,
      fethPortFramesReceived Counter,
      fethPortFramesTransmitted Counter,
      fethPortTotalErrors Counter,
      fethPortFramesTransmittedOK Counter,
      fethPortCollisionFrames Counter,
      fethPortAlignmentErrors Counter,
      fethPortRxErrors Counter,
-- lannet 7.1
     fethPortReadableFrames  Counter,
     fethPortUpper32ReadableOctets Counter,
     fethPortLower32ReadableOctets Counter,
     fethPortFCSErrors Counter,
     fethPortFrameTooLongs Counter,
     fethPortShortEvents Counter,
     fethPortRunts Counter,
     fethPortLateEvents Counter,
     fethPortVeryLongEvents Counter,
     fethPortDataRateMismatches Counter,
     fethPortAutoPartitions Counter,
     fethPortSymbolErrors Counter,
     fethPortLastSourceAddress OCTET STRING,
     fethPortSourceAddrChanges Counter,
     fethPortMode   INTEGER,
     fethPortLinkRedundancyMode INTEGER,
     fethPortLinkRedundancyStatus INTEGER,
     fethPortDormantLinkFunctionalStatus INTEGER,
      fethPortUpper32TransmittedOctets Counter,
     fethPortLower32TransmittedOctets Counter,
     fethPortBroadcastReceivedFrames Counter,
     fethPortMulticastReceivedFrames  Counter,
     fethPortEnablePHY INTEGER
      }

fethPortGroupId OBJECT-TYPE
      SYNTAX  INTEGER
      ACCESS  read-only
      STATUS  mandatory
      DESCRIPTION
      "Id of the group to which the port belongs."
      ::= { fethPortEntry 1 }
      
fethPortId OBJECT-TYPE
      SYNTAX  INTEGER
      ACCESS  read-only
      STATUS  mandatory
      DESCRIPTION
      "Unique Id of the port in the ethPortTable."
      ::= { fethPortEntry 2 }
      
fethPortFunctionalStatus OBJECT-TYPE
      SYNTAX  INTEGER {
	ok(1),
	rld(2),            -- RxLinkDown (Link Test Fail)
	rxJabber(3),
	partition(8),
	remoteFault(10),
	wrongSpeed(12),
	notSupported(255)
      }
      ACCESS  read-only
      STATUS  mandatory
      DESCRIPTION
      "The value of this attribute reflects the functional status of 
	LANNET 100BaseTX port.
      Here is the set possible states:
      ok(1)- fully functional port, transmitting and receiving packets.
      rld(2) - receive link down (Link Test Failure) condition on the port -
      indicates a broken connection (cable, connector) detected by the port.
      rxJabber(3) - fault condition indicating that the port received long packet (jabber)
		from the line.
      partition(8) - the port is in partition state.
      remoteFault(10) - fault condition sensed by the remote port.
      wrong speed(12) - 10Mbit transmission sensed by the port."
      ::= { fethPortEntry 3 }

fethPortFIFO OBJECT-TYPE
      SYNTAX  INTEGER {
	on(1),
	off(2),
	notSupported(255)
      }
      ACCESS  read-only
      STATUS  mandatory
      DESCRIPTION
      "Value ON of this attribute describes an internal FIFO error sensed by the
      internal hardware mechanism of a the port."
      ::= { fethPortEntry 4 }
      
fethPortOperStatus  OBJECT-TYPE
	SYNTAX  INTEGER  {
		   operational(1),
		 notOperational(2),
		   notSupported(255)
	}
	ACCESS  read-only
	STATUS  mandatory
	DESCRIPTION
	"This object indicates the port's operational status.
	The operational(1) status  indicates that the port is enabled
	and working, even though it might be auto-partitioned."
	::= { fethPortEntry 5 }

fethPortAutoPartitionState OBJECT-TYPE
      SYNTAX  INTEGER {
	autoPartition(1),
	notAutoPartition(2),
	notSupported(255)
      }
      ACCESS  read-only
      STATUS  mandatory
      DESCRIPTION
      "The AutoPart condition indicates that the port is currently partitioned
      by the auto-partition protection mechanism."
      ::= { fethPortEntry 6 }

fethPortFramesReceived OBJECT-TYPE
      SYNTAX  Counter
      ACCESS  read-only
      STATUS  mandatory
      DESCRIPTION
      "A representation of the total  number of frames received by
	the port from the line. The number includes all frames received 
      even those with RxError or alignment errors or those that had
	been corrupred in transmission."
      ::= { fethPortEntry 7 }

fethPortFramesTransmitted OBJECT-TYPE
      SYNTAX  Counter
      ACCESS  read-only
      STATUS  mandatory
      DESCRIPTION
      "A representation of the total  number of frames transmitted by
        the port to the line. The number includes all frames transmitted." 
      ::= { fethPortEntry 8 }

fethPortTotalErrors  OBJECT-TYPE
	SYNTAX  Counter
	ACCESS  read-only
	STATUS  mandatory
	DESCRIPTION
"The total number of errors which have occurred on 	this port.  
This counter is the summation of the values of other error counters 
(for the same port), namely:
		fethPortFCSErrors,
 		fethPortAlignmentErrors, 
		fethPortFrameTooLongs,
		fethPortShortEvents,
		fethPortLateEvents,
		fethPortVeryLongEvents,
		fethPortDataRateMismatches,

		For LFE-100 only :
		fethPortAlignmentErrors,
		fethPortRxErrors. 

This counter is redundant in the sense that it is the summation of 
information already available through other objects.  However, it is 
included specifically because the regular retrieval of this object as
a means of tracking the health of a port provides a considerable 
optimization of network management traffic over the otherwise necessary
retrieval of the summed counters.
REFERENCE
 Reference IETF 100Base-T Repeater MIB, rptr100MonitorPortTotalErrors."
	::= { fethPortEntry 9 }

fethPortFramesTransmittedOK OBJECT-TYPE
      SYNTAX  Counter
      ACCESS  read-only
      STATUS  mandatory
      DESCRIPTION
      "A representation of the total  number of frames of legal length
	that have not been corrupted in transmission that transmitted by 
	the port to the line. These frames can be encoded and decoded
	by the commonly available MACs. Not supported by LFE1008."
      ::= { fethPortEntry 10 }

fethPortCollisionFrames OBJECT-TYPE
	SYNTAX  Counter
	ACCESS  read-only
	STATUS  mandatory
	DESCRIPTION
	"This counter is incremented by one for any
      CarrierEvent signal on any port for which the
      CollisionEvent signal on this port is also asserted."
      ::= { fethPortEntry 11 }

fethPortAlignmentErrors  OBJECT-TYPE
	SYNTAX  Counter
	ACCESS  read-only
	STATUS  mandatory
	DESCRIPTION
	"This counter is incremented by one for each frame
	received on this port with the FCSError and
	FramingError signals asserted and CollisionEvent signal 
      deasserted and whose OctetCount is greater than 
	or equal to minFrameSize and less than or equal to 
	maxFrameSize." 
	::= { fethPortEntry 12 }

fethPortRxErrors  OBJECT-TYPE
	SYNTAX  Counter
	ACCESS  read-only
	STATUS  mandatory
	DESCRIPTION
	"The total number of received frames with error code violation
	or dose not terminate correctlly."
	::= { fethPortEntry 13 }

fethPortReadableFrames OBJECT-TYPE
       SYNTAX    Counter
       ACCESS    read-only
       STATUS    mandatory
       DESCRIPTION
               "This object is the number of frames of valid
               frame length that have been received on this port.
               This counter is incremented by one for each frame
               received on this port whose OctetCount is greater
               than or equal to minFrameSize and less than or
               equal to maxFrameSize (Ref: IEEE 802.3 Std,
               4.4.2.1) and for which the FCSError and
               CollisionEvent signals are not asserted.

               This statistic provides one of the parameters
               necessary for obtaining the packet error rate.
       REFERENCE
		Reference IEEE Draft Std 802.3u/D4 Rptr Mgt,
		30.4.3.1.4, aReadableFrames.
 		Reference IETF 100Base-T Repeater MIB,
		rptr100MonitorPortReadableFrames."
       ::= { fethPortEntry 14 }

 fethPortUpper32ReadableOctets OBJECT-TYPE
       SYNTAX    Counter
       ACCESS    read-only
       STATUS    mandatory
       DESCRIPTION
               "This object is the number of octets contained in
               valid frames that have been received on this port.
               This counter is incremented by OctetCount for each
               frame received on this port which has been
               determined to be a readable frame (i.e., including
               FCS octets but excluding framing bits and dribble
               bits).

               This statistic provides an indicator of the total
               data transferred.

               Note that this counter and
               fethPortLower32ReadableOctets
               forms a 64 bits counter. It is provided for those
               network management protocols that do not support
               64 bit counters (e.g. SNMP V1) and the repeater
               type is 100Mbs.
       REFERENCE
               Reference IETF 100Base-T Repeater MIB,
               rptr100MonitorPortUpper32ReadableOctets."
       ::= { fethPortEntry 15 }

 fethPortLower32ReadableOctets OBJECT-TYPE
       SYNTAX    Counter
       ACCESS    read-only
       STATUS    mandatory
       DESCRIPTION
               "This object is the number of octets contained in
               valid frames that have been received on this port.
               This counter is incremented by OctetCount for each
               frame received on this port which has been
               determined to be a readable frame (i.e., including
               FCS octets but excluding framing bits and dribble
               bits).

               This statistic provides an indicator of the total
               data transferred.

               Note that this counter and
               fethPortUpper32ReadableOctets
               forms a 64 bits counter. It is provided for those
               network management protocols that do not support
               64 bit counters (e.g. SNMP V1) and the repeater
               type is 100Mbs.
       REFERENCE
               Reference IEEE Draft Std 802.3u/D4 Rptr Mgt,
		30.4.3.1.5,  aReadableOctets.
               Reference IETF 100Base-T Repeater MIB,
               rptr100MonitorPortLower32ReadableOctets."
       ::= { fethPortEntry 16 }

 fethPortFCSErrors OBJECT-TYPE
       SYNTAX    Counter
       ACCESS    read-only
       STATUS    mandatory
       DESCRIPTION
               "This counter is incremented by one for each frame
               received on this port with the FCSError signal
               asserted and the FramingError and CollisionEvent
               signals deasserted and whose OctetCount is greater
               than or equal to minFrameSize and less than or
               equal to maxFrameSize (Ref: 4.4.2.1, IEEE 802.3
               Std).
       REFERENCE
               Reference IEEE Draft Std 802.3u/D4 Rptr Mgt,
		30.4.3.1.6,  aFrameCheckSequenceErrors.
               Reference IETF 100Base-T Repeater MIB,
               rptr100MonitorPortFCSErrors."
       ::= { fethPortEntry 17 }


 fethPortFrameTooLongs OBJECT-TYPE
       SYNTAX    Counter
       ACCESS    read-only
       STATUS    mandatory
       DESCRIPTION
               "This counter is incremented by one for each frame
               received on this port whose OctetCount is greater
               than maxFrameSize (Ref: 4.4.2.1, IEEE 802.3 Std).
               If fethPortFrameTooLongs is incremented
               then neither the fethPortAlignmentErrors
               nor the fethPortFCSErrors counter shall be
               incremented for the frame.
       REFERENCE
               Reference IEEE Draft Std 802.3u/D4 Rptr Mgt, 
		30.4.3.1.8,  aFramesTooLong.
               Reference IETF 100Base-T Repeater MIB,
               rptr100MonitorPortFrameTooLongs."
       ::= { fethPortEntry 18 }

 fethPortShortEvents OBJECT-TYPE
       SYNTAX    Counter
       ACCESS    read-only
       STATUS    mandatory
       DESCRIPTION
               "This counter is incremented by one for each
               CarrierEvent on this port with ActivityDuration
               less than ShortEventMaxTime. 
		ShortEventMaxTime is  84 bits (21 nibbles).

               Note:  shortEvents may indicate externally
               generated noise hits which will cause the repeater
               to transmit Runts to its other ports, or propagate
               a collision (which may be late) back to the
               transmitting DTE and damaged frames to the rest of
               the network.

               Implementors may wish to consider selecting the
               ShortEventMaxTime towards the lower end of the
               allowed tolerance range to accommodate bit losses
               suffered through physical channel devices not
               budgeted for within this standard.

               Note also that clause 27 repeaters do not perform
               fragment extension as clause 9 repeater does.
       REFERENCE
               Reference IEEE Draft Std 802.3u/D4 Rptr Mgt,
		30.4.3.1.9,  aShortEvents.
               Reference IETF 100Base-T Repeater MIB,
               rptr100MonitorPortShortEvents."
       ::= { fethPortEntry 19 }

 fethPortRunts OBJECT-TYPE
       SYNTAX    Counter
       ACCESS    read-only
       STATUS    mandatory
       DESCRIPTION
               "This counter is incremented by one for each
               CarrierEvent on this port that meets one of the
               following two conditions.  Only one test need be
               made.  a) The ActivityDuration is greater than
               ShortEventMaxTime and less than 
		validPacketMinTime  and the CollisionEvent signal
		is deasserted.  b) The OctetCount is less than 64, the
               ActivityDuration is greater than ShortEventMaxTime
               and the CollisionEvent signal is deasserted.
               ValidPacketMinTime is greater than or equal to 552
               bit times and less than 565 bit times.

               ValidPacketMinTime has tolerances included to
               provide for circuit losses between a conformance
               test point at the AUI and the measurement point
               within the state machine.

               Runts usually indicate collision fragments, a
               normal network event.  In certain situations
               associated with large diameter networks a
               percentage of collision fragments may exceed
               ValidPacketMinTime.
       REFERENCE
               Reference IEEE Draft Std 802.3u/D4 Rptr Mgt, 
		30.4.1.3.10,  aRunts.
               Reference IETF 100Base-T Repeater MIB,
               rptr100MonitorPortRunts."
       ::= { fethPortEntry 20 }


 fethPortLateEvents OBJECT-TYPE
       SYNTAX    Counter
       ACCESS    read-only
       STATUS    mandatory
       DESCRIPTION
               "This counter is incremented by one on entering
                the Collision Count Increment state of the
                partition state diagram (fig 27-8) while the
                ActivityDuration is greater than the LateEvent-
                Threshold. Such a CarrierEvent is counted twice,
                as both collision and a late event.

               The LateEventThreshold is greater than 480 bit
               times and less than 565 bit times.
               LateEventThreshold has tolerances included to
               permit an implementation to build a single
               threshold to serve as both the LateEventThreshold
               and ValidPacketMinTime threshold.
       REFERENCE
               Reference IEEE Draft Std 802.3u/D4 Rptr Mgt, 
		30.4.3.1.12,  aLateEvents.
               Reference IETF 100Base-T Repeater MIB,
               rptr100MonitorPortLateEvents."
       ::= { fethPortEntry 21 }

 fethPortVeryLongEvents OBJECT-TYPE
       SYNTAX    Counter
       ACCESS    read-only
       STATUS    mandatory
       DESCRIPTION
               "This counter is incremented by one on entry to
               the Rx Jabber state of the receiver timer state
               diagram (fig 27-7). Other counters may be
               incremented as appropriate.
       REFERENCE
		Reference IEEE Draft Std 802.3u/D4 Rptr Mgt, 
		30.4.3.1.13,  aVeryLongEvents.
               Reference IETF 100Base-T Repeater MIB,
               rptr100MonitorPortVeryLongEvents."
       ::= { fethPortEntry 22 }

 fethPortDataRateMismatches OBJECT-TYPE
       SYNTAX    Counter
       ACCESS    read-only
       STATUS    mandatory
       DESCRIPTION
               "This counter is incremented by one for each frame
               received on this port that meets all of the
               following conditions:  a) the Collision Count
               Increment state of the partition state diagram
               (fig 27-8) has not been entered.  b) The 
		ActivityDuration  is greater than 
		ValidPacketMinTime.  c) The  frequency (data rate)
		is detectably mismatched from the local transmit 
		frequency.  The exact degree of mismatch is vendor 
		specific and is to be  defined by the vendor for 
		conformance testing.

               When this event occurs, other counters whose
               increment conditions were satisfied may or may not
               also be incremented, at the implementor's
               discretion.  Whether or not the repeater was able
               to maintain data integrity is beyond the scope of
               this standard.
       REFERENCE
               Reference IEEE Draft Std 802.3u/D4 Rptr Mgt, 
		30.4.3.1.14, aDataRateMismatches.
               Reference IETF 100Base-T Repeater MIB,
               rptr100MonitorPortDataRateMismatches."
       ::= { fethPortEntry 23 }

 fethPortAutoPartitions OBJECT-TYPE
       SYNTAX    Counter
       ACCESS    read-only
       STATUS    mandatory
       DESCRIPTION
               "This counter is incremented by one on entry to the
               Partition Wait state of the partition state
               diagram (fig 27-8).
       REFERENCE
               Reference IEEE Draft Std 802.3u/D4 Rptr Mgt, 
		30.4.3.1.14, aAutoPartitions.
               Reference IETF 100Base-T Repeater MIB,
               rptr100MonitorPortAutoPartitions."
       ::= { fethPortEntry 24 }

 fethPortSymbolErrors OBJECT-TYPE
       SYNTAX    Counter
       ACCESS    read-only
       STATUS    mandatory
       DESCRIPTION
               "This counter is incremented by one each time when
               valid length packet was received at the port and
               there was at least one occurrence of an invalid
               data symbol. This can increment only once per valid
               carrier event. A collision presence at any port of
               the repeater containing port N, will not cause this
               attribute to increment.

               This Counter has a maximum increment rate of 
		160,000  counts per second for 100Mb/s 
		implementation.
       REFERENCE
		Reference IEEE Draft Std 802.3u/D4 Rptr Mgt, 
		30.4.3.1.17,  aSymbolErrorDuringPacket.
		Reference IETF 100Base-T Repeater MIB,
		rptr100MonitorPortSymbolErrors."
	::= { fethPortEntry 25 }

 fethPortLastSourceAddress OBJECT-TYPE
       SYNTAX    OCTET STRING (SIZE(0..6))
       ACCESS    read-only
       STATUS    deprecated
       DESCRIPTION
               "This object is the SourceAddress of the last
               readable frame (i.e., counted by
               fethPortReadableFrames) received by this
               port.  If no frames have been received by this
               port since the agent began monitoring the port
               activity, the agent shall return a string of
               length zero.
       REFERENCE
               Reference IEEE Draft Std 802.3u/D4 Rptr Mgt,
               30.4.3.1.18, aLastSourceAddress.
               Reference IETF 100Base-T Repeater MIB,
               rptr100AddrTrackLastSourceAddress."
       ::= { fethPortEntry 26 }

 fethPortSourceAddrChanges OBJECT-TYPE
       SYNTAX    Counter
       ACCESS    read-only
       STATUS    mandatory
       DESCRIPTION
               "This counter is incremented by one for each time
               that the fethPortLastSourceAddress attribute
               for this port has changed.

               This may indicate whether a link is connected to a
               single DTE or another multi-user segment.

               The approximate minimum time for rollover of this
               counter is 8 hours.
       REFERENCE
               Reference IEEE Draft Std 802.3u/D4 Rptr Mgt,
               30.4.3.1.19, aSourceAddressChanges.
               Reference IETF 100Base-T Repeater MIB,
               rptr100AddrTrackSourceAddrChanges."
       ::= { fethPortEntry 27 }

fethPortMode OBJECT-TYPE
	SYNTAX  INTEGER {
	          	halfDuplex (1),
	         	fullDuplex (2),
               	fullDuplexAndFlowControl(3),
               	fullDuplexAndISL(4),
               	fullDuplexAndFlowControlAndISL(5),
	         	notSupported (255)
	}
 	ACCESS  read-write
	STATUS  mandatory
	DESCRIPTION
	"The mode of the port.
	halfDuplex(1)- standard mode, usually for segments.
	fullDuplex(2)- standard mode, usually for servers.
	fullDuplexAndFlowControl(3)- the module transmits Flow Control symbols to the line 	between two HUBs in order to control the flow of data.
	fullDuplexAndISL(4)- the module transmits to the line a control-word from the HSB, 	in order to transfer VLANs and Priority to another HUB ( ISL=Inter Switch Link).
	fullDuplexAndFlowControlAndISL(5)- FDX with both Flow Control and ISL modes. It 	is the user's responsibility to set both modules connected to the line, to the same 	mode."
	DEFVAL { halfDuplex }
::= { fethPortEntry 28 }

fethPortLinkRedundancyMode OBJECT-TYPE
	SYNTAX  INTEGER{
       	enable(1),
       	disable(2),
       	notSupported(255)
       	}
	ACCESS  read-write
	STATUS  mandatory
	DESCRIPTION
	"This item is relevant for modules which include redundant links.
	This item enables/disables the Redundancy
             mechanism. When enabled, the Sensor will alternately switch
             between the main and secondary ports/links, upon a predefined failure indication. 
 	See also the fethPortEnablePHY item."	
	DEFVAL { disable }
::= { fethPortEntry 29 }

fethPortLinkRedundancyStatus OBJECT-TYPE
	SYNTAX  INTEGER{
       		firstLinkActive(1),
       		secondLinkActive(2),
       		notSupported(255)
       		}
	ACCESS  read-only
	STATUS  mandatory
	DESCRIPTION
		"This item is relevant for ports which includes redundant
                 	  links. This item indicates which of the links is active.
		 Default value=firstLinkActive(1). "
::= { fethPortEntry 30 } 

fethPortDormantLinkFunctionalStatus OBJECT-TYPE
	SYNTAX  INTEGER{
       		ok(1),
       		rld(2),
       		remoteFault(10),
        		notSupported(255)
      		 }
	ACCESS  read-only
	STATUS  mandatory
	DESCRIPTION
		"The value of this attribute reflects the functionality status
		of the dormant link, in modules such as LEB-200, which
		have link redundancy capability. Note that the Main Link
		functionality status is still reflected by the fethPortFunctionalStatus
		item as usual..
		Default value=ok(1). "
::= { fethPortEntry 31 } 

fethPortUpper32TransmittedOctets OBJECT-TYPE
       SYNTAX    Counter
       ACCESS    read-only
       STATUS    mandatory
       DESCRIPTION
       "This object is the number of octets contained in valid frames that have been transmitted 	on this port. This counter is incremented by OctetCount for each frame transmitted 	on this port which has not been encountered with a collision event. 
        This statistic provides an indicator of the total data transferred.
        Note that this counter and fethPortLower32TransmittedOctets forms a 64 bits counter. It 	is provided for those network management protocols that do not support 64 bit  	counters (e.g. SNMP V1) and the repeater  type is 100Mbs."
 ::= { fethPortEntry 32 }

fethPortLower32TransmittedOctets OBJECT-TYPE
       SYNTAX    Counter
       ACCESS    read-only
       STATUS    mandatory
       DESCRIPTION
       "This object is the number of octets contained in valid frames that have been transmitted 	on this port.This counter is incremented by OctetCount for each frame transmitted on 	this port which has not been encountered with a collision event. 
	This statistic provides an indicator of the total data transferred.
        Note that this counter and fethPortUpper32TransmittedOctets forms a 64 bits counter. It 	is provided for those network management protocols that do not support 64 bit 	counters (e.g. SNMP V1) and the repeater type is 100Mbs."
       ::= { fethPortEntry 33 }

fethPortBroadcastReceivedFrames OBJECT-TYPE
       SYNTAX    Counter
       ACCESS    read-only
       STATUS    mandatory
       DESCRIPTION
       "This object is the number of Broadcast readable frames that have been Received on 	this port."
       ::= { fethPortEntry 34 }

fethPortMulticastReceivedFrames OBJECT-TYPE
       SYNTAX    Counter
       ACCESS    read-only
       STATUS    mandatory
       DESCRIPTION
       "This object is the number of Multicast readable (good) frames that have been Received 	on this port."
       ::= { fethPortEntry 35 }

fethPortEnablePHY OBJECT-TYPE
	SYNTAX  INTEGER{
	enPHY1 (1),
	enPHY2(2),
             notSupported(255)
       }
	ACCESS  read-write
	STATUS  mandatory
	DESCRIPTION
		"This item is relevant for ports which include redundant links
		 (such as LEB200).
		 This item is not valid  and has no effect when the 					 fethPortLinkRedundancyMode=enable(1).
		 This item determines and indicates the active PHY in case that 				 fethPortLinkRedundancyMode is set to disable(2)."
	DEFVAL { enPHY1 }
::= { fethPortEntry 36 }


--
-- The Basic Port Group Table & Group Monitor Table
--



fethGroup OBJECT IDENTIFIER
	::= { feth 2 }


fethGroupTable OBJECT-TYPE
       SYNTAX    SEQUENCE OF FethGroupEntry
       ACCESS    not-accessible
       STATUS    mandatory
       DESCRIPTION
               "Table of descriptive, status, performance and error 
		information about the groups of fast ethernet ports."
       ::= { fethGroup 1 }

fethGroupEntry OBJECT-TYPE
       SYNTAX    FethGroupEntry
       ACCESS    not-accessible
       STATUS    mandatory
       DESCRIPTION
               "An entry in the table, containing  information, total
               performance and error statistics for a single
               group of ports.  Regular retrieval of the information 
		in this table provides a means of tracking the
               performance and health of the networked devices
               attached to this group's ports.

               The counters in this table are redundant in the
               sense that they are the summations of information
               already available through other objects.  However,
               these sums provide a considerable optimization of
               network management traffic over the otherwise
               necessary retrieval of the individual counters
               included in each sum."
       INDEX    { fethGroupId}
       ::= { fethGroupTable 1 }

FethGroupEntry ::=
       SEQUENCE {
	fethGroupId			INTEGER,
	fethGroupOperStatus		INTEGER,
	fethGroupUtilization		INTEGER,
	fethGroupTotalFrames		Counter,
	fethGroupUpper32TotalOctets	Counter,
	fethGroupLower32TotalOctets	Counter,
	fethGroupTotalErrors		Counter,
	fethGroupFefiEnable		INTEGER
	}

fethGroupId OBJECT-TYPE
	SYNTAX    INTEGER (1..1024)
	ACCESS    read-only
	STATUS    mandatory
	DESCRIPTION
	"This object identifies the group within the repeater for which this entry contains
	information. This value is never greater than fethRepeaterGroupCapacity.
	REFERENCE
	Reference IEEE Draft Std 802.3u/D4 Rptr Mgt, 30.4.2.1.1, aGroupID.
	Reference IETF 100Base-T Repeater MIB, rptr100GroupIndex."
	::= { fethGroupEntry 1 }

fethGroupOperStatus OBJECT-TYPE
	SYNTAX    INTEGER {
		other(1),
		operational(2),
		malfunctioning(3),
		notPresent(4),
		underTest(5),
		resetInProgress(6)
		}
	ACCESS    read-only
	STATUS    mandatory
	DESCRIPTION
	"An object that indicates the operational status of the group.
	A status of notPresent(4) indicates that the group
	is temporarily or permanently physically and/or
	logically not a part of the repeater (Stand Alone).
	A status of operational(2) indicates that the group is functioning,
	and a status of malfunctioning(3) indicates that the group is
	malfunctioning in some way (see fethRepeaterOperStatus).
	REFERENCE
	Reference IETF 100Base-T Repeater MIB, rptr100GroupOperStatus."
	::= { fethGroupEntry 2 }

fethGroupUtilization OBJECT-TYPE 
	SYNTAX    INTEGER 
	ACCESS    read-only 
	STATUS    mandatory 
	DESCRIPTION 
	"Utilization of the network, expressed in percentage 
	of the maximum traffic possible ( 100Mbps)"
	::= { fethGroupEntry 3 }

fethGroupTotalFrames OBJECT-TYPE
       SYNTAX    Counter
       ACCESS    read-only
       STATUS    mandatory
       DESCRIPTION
               "The total number of frames of valid frame length
               that have been received on the ports in this group
               and for which the FCSError and CollisionEvent
               signals were not asserted.  This counter is the
               summation of the values of the
               fethPortReadableFrames counters for all of
               the ports in the group.
               This statistic provides one of the parameters
               necessary for obtaining the packet error rate.
       REFERENCE
               Reference IETF 100Base-T Repeater MIB,
               rptr100MonitorGroupTotalFrames."
       ::= { fethGroupEntry 4 }

fethGroupUpper32TotalOctets OBJECT-TYPE
       SYNTAX    Counter
       ACCESS    read-only
       STATUS    mandatory
       DESCRIPTION
               "The total number of octets contained in the valid
               frames that have been received on the ports in
               this group.  This counter is the summation of the
               values of the fethPortReadableOctets
               counters for all of the ports in the group.
               This statistic provides an indicator of the total
               data transferred.
               Note that this counter and
               fethGroupLower32TotalOctets
               forms a 64 bits counter. It is provided for those
               network management protocols that do not support
               64 bit counters (e.g. SNMP V1) and the repeater
               type is 100Mbs.
       REFERENCE
               Reference IETF 100Base-T Repeater MIB,
               rptr100MonitorGroupUpper32TotalOctets."
       ::= { fethGroupEntry 5 }

fethGroupLower32TotalOctets OBJECT-TYPE
       SYNTAX    Counter
       ACCESS    read-only
       STATUS    mandatory
       DESCRIPTION
               "The total number of octets contained in the valid
               frames that have been received on the ports in
               this group.  This counter is the summation of the
               values of the fethPortReadableOctets
               counters for all of the ports in the group.
               This statistic provides an indicator of the total
               data transferred.
               Note that this counter and
               fethGroupUpper32TotalOctets
               forms a 64 bits counter. It is provided for those
               network management protocols that do not support
               64 bit counters (e.g. SNMP V1) and the repeater
               type is 100Mbs.
       REFERENCE
               Reference IETF 100Base-T Repeater MIB,
               rptr100MonitorGroupLower32TotalOctets."
       ::= { fethGroupEntry 6 }

fethGroupTotalErrors OBJECT-TYPE
	SYNTAX    Counter
	ACCESS    read-only
	STATUS    mandatory
	DESCRIPTION
	"The total number of errors which have occurred on all of the ports in this group.
	This counter is the summation of the values of the fethPortTotalErrors counters
	for all of the ports in the group.
	REFERENCE
	Reference IETF 100Base-T Repeater MIB,
	rptr100MonitorGroupTotalErrors."
	::= { fethGroupEntry 7 }

fethGroupFefiEnable  OBJECT-TYPE
	SYNTAX  INTEGER {
		enable(1),
		disable(2),
		notSupported(255)
	}
	ACCESS  read-write
	STATUS mandatory
	DESCRIPTION 
	"This item enables\disables the FEFI mechanism of the PHY  on the module.
	 It enables\disables both the transmission and the recognition of FEFI signals .
	This item is used only in modules that support 100BaseFx."
	::= {fethGroupEntry 8}

-- Token ring devices (Agents and modules)
--
tokRing OBJECT IDENTIFIER ::= { tok 1 } 

tokRingTable OBJECT-TYPE
      SYNTAX  SEQUENCE OF TokRingEntry
      ACCESS  not-accessible
      STATUS mandatory
      ::= { tokRing 1 }
 
tokRingEntry OBJECT-TYPE
      SYNTAX    TokRingEntry
      ACCESS    not-accessible
      STATUS    mandatory
      INDEX     { tokRingAgId, tokRingId }
      ::= { tokRingTable 1 }
 
TokRingEntry ::=
      SEQUENCE {
	 tokRingAgId
	    INTEGER,
	 tokRingId
	    INTEGER,
	 tokRingLeftSlot
	    INTEGER,
	 tokRingRightSlot
	    INTEGER,
	 tokRingTrafficBuffer
	    OCTET STRING,
	 tokRingTrafficThresh
	    INTEGER,
	 tokRingPeakTraffic
	    INTEGER,
	 tokRingNumberOfStations
	    INTEGER,
	 tokRingConfiguration
	    OCTET STRING,
	 tokRingBeaconing
	    INTEGER,
	 tokRingBeaconingStation
	    OCTET STRING,
	 tokRingStationsMatch
	    INTEGER,
	 tokRingTraffic
	    INTEGER,
	 tokRingSecurityMethod
	    INTEGER,
	 tokRingSecurityPolicy
	    OCTET STRING,
	 tokRingSecureAddr
	    OCTET STRING,
	 tokRingLastViolation
	    OCTET STRING,
	 tokRingUtilization
	    INTEGER,
	 tokRingPeakUtilization
	    INTEGER,
	tokRingBeaconingResolution
	    INTEGER,
	tokRingThresholdStatus  
	    OCTET STRING,
	tokRingActiveMonitor  
	    OCTET STRING
      }

tokRingAgId OBJECT-TYPE
      SYNTAX  INTEGER (1..255)
      ACCESS  read-only
      STATUS  mandatory
      DESCRIPTION
      "ID of the agent to which the ring belongs in the tokRingTable."
      ::= { tokRingEntry 1 }
      
tokRingId OBJECT-TYPE
      SYNTAX  INTEGER (1..255)
      ACCESS  read-only
      STATUS  mandatory
      DESCRIPTION
      "ID of the ring in the tokRingTable."
      ::= { tokRingEntry 2 }
      
tokRingLeftSlot OBJECT-TYPE
      SYNTAX  INTEGER (1..255)
      ACCESS  read-only
      STATUS  mandatory
      DESCRIPTION
      "Slot number of the left-most slot of the ring.
      In the token ring stackable hub, 'Left' should be read as 'Up'. "
      ::= { tokRingEntry 3 }
      
tokRingRightSlot OBJECT-TYPE
      SYNTAX  INTEGER (1..255)
      ACCESS  read-write
      STATUS  mandatory
      DESCRIPTION
      "Slot number of the right-most slot of the ring that has a lobe port.
      In the token ring stackable hub, 'Right' should be read as 'Down'. "
      ::= { tokRingEntry 4 }
      
tokRingTrafficBuffer OBJECT-TYPE
      SYNTAX  OCTET STRING
      ACCESS  read-only
      STATUS  deprecated
      DESCRIPTION
      "Record of traffic for the last second with a resolution of 100 msec.
      The traffic is expressed in percents of the maximum effective TR traffic
      (token messages are excluded) and each record contains 10 readings,
      in range 1..20 on log(10) scale."
      ::= { tokRingEntry 5 }
      
tokRingTrafficThresh OBJECT-TYPE
      SYNTAX  INTEGER
      ACCESS  read-write
      STATUS  mandatory
      DESCRIPTION
      "Traffic threshold value. When exceeded, a trap is send to the management
      console. Expressed in percents of the maximum effective TR traffic
      (token messages are excluded) in the range 1..20 on log(10) scale."
      ::= { tokRingEntry 6 }
      
tokRingPeakTraffic OBJECT-TYPE
      SYNTAX  INTEGER                -- Values 1..20 (Log(10) scale)
      ACCESS  read-write
      STATUS  mandatory
      DESCRIPTION
      "Maximal traffic value since last reset of agent. Expressed in percents
      of the maximum effective TR traffic (token messages are excluded), in the
      range 1..20 on log(10) scale.
      The write access is reserved for resetting the value of the peak."
      ::= { tokRingEntry 7 }
      
tokRingNumberOfStations OBJECT-TYPE
      SYNTAX  INTEGER
      ACCESS  read-only
      STATUS  mandatory
      DESCRIPTION
      "Number of Token Ring stations (controllers) detected on the ring. The
      TR controller of the agent card is included in this count."
      ::= { tokRingEntry 8 }
      
tokRingConfiguration OBJECT-TYPE
      SYNTAX  OCTET STRING
      ACCESS  read-only
      STATUS  mandatory
      DESCRIPTION
      "Configuration attribute describing the list of physical addresses
      detected on the Token Ring. Coded in internal  application
      format. "
      ::= { tokRingEntry 9 }
      
tokRingBeaconing OBJECT-TYPE
      SYNTAX  INTEGER {
	on(1),
	off(2),
	notSupported(255)
      }
      ACCESS  read-only
      STATUS  mandatory
      DESCRIPTION
      "This attribute indicates if a beaconing condition is currently
      detected on the ring."
      ::= { tokRingEntry 10 }
      
tokRingBeaconingStation OBJECT-TYPE
      SYNTAX  OCTET STRING
      ACCESS  read-only
      STATUS  mandatory
      DESCRIPTION
      "The MAC address of the last station which was detected as sending
      Beaconing MAC frames on the ring."
      ::= { tokRingEntry 11 }
      
tokRingStationsMatch OBJECT-TYPE
      SYNTAX  INTEGER {
	on(1),
	off(2),
	partial(3),
	notSupported(255)
      }
      ACCESS  read-only
      STATUS  mandatory
      DESCRIPTION
      "This attribute indicates matching between the number of stations
      detected on the ring between the current agent and the next agent
      on Up Stream sense and the number of connected lobe ports.Used by
      the port address correlation mechanism."
      ::= { tokRingEntry 12 }
      
tokRingTraffic OBJECT-TYPE
      SYNTAX  INTEGER
      ACCESS  read-only
      STATUS  mandatory
      DESCRIPTION
      "Last traffic reading (sampling time =  100 msec). The
      traffic is expressed in percents of the maximum Ethernet traffic
      in the range 1..20, expressed on a log(10)
      scale ( value = 10*log10(percent) )."
      ::= { tokRingEntry 13 }

tokRingSecurityMethod OBJECT-TYPE
	SYNTAX  INTEGER { perPort(1), perRing(2), disabled(3),
			notSupported(255) }
	ACCESS  read-write
	STATUS  mandatory
	DESCRIPTION
	"Security scheme selected by the user.
	perPort(1) indicates that secure addresses are defined for
	each secured token ring port.
                perRing(2) indicates that a common set of secure addresses 
                will be allowed for the whole ring.
                disabled(3) - no security method is applied on this ring."
	::= { tokRingEntry 14 }

tokRingSecurityPolicy OBJECT-TYPE
	SYNTAX  OCTET STRING (SIZE(1))
	ACCESS  read-write
	STATUS  mandatory
	DESCRIPTION
	"Security policy (trap only or trap and disconnect) selected for the
	ring. Coded in  internal format."
	::= { tokRingEntry 15 }

tokRingSecureAddr OBJECT-TYPE
	SYNTAX  OCTET STRING
	ACCESS  read-write
	STATUS  mandatory
	DESCRIPTION
	"Secure addresses assigned to the ring. Coded in  internal
	format."
	::= { tokRingEntry 16 }

tokRingLastViolation OBJECT-TYPE
	SYNTAX  OCTET STRING
	ACCESS  read-only
	STATUS  mandatory
	DESCRIPTION
	"MAC address of a last detected intruder."
	::= { tokRingEntry 17 }

tokRingUtilization OBJECT-TYPE
	SYNTAX  INTEGER
	ACCESS  read-only
	STATUS  mandatory
	DESCRIPTION
	"Last traffic reading (sampling time =  100 msec). The traffic is expressed
	in percents of the maximum Token Ring traffic."
	::= { tokRingEntry 18 }

tokRingPeakUtilization OBJECT-TYPE
	SYNTAX  INTEGER
	ACCESS  read-only
	STATUS  mandatory
	DESCRIPTION
	"Maximal traffic value since last reset of agent. Expressed in percents
	of the maximum effective TR traffic (token messages are excluded)."
	::= { tokRingEntry 19 }

tokRingBeaconingResolution OBJECT-TYPE
	SYNTAX  INTEGER {
		enable(1),
		disable(2),
		notSupported(255)
		}
	ACCESS  read-write
	STATUS  mandatory
	DESCRIPTION
	"This parameter enables or disables the beaconing resolution."
	DEFVAL  { enable }
	::= { tokRingEntry 20}

tokRingThresholdStatus  OBJECT-TYPE  
	SYNTAX  OCTET STRING ( SIZE (4))
	ACCESS  read-only
	STATUS  mandatory
	DESCRIPTION
		"This item is a bitmap that defines the threshold status of the 
		ring, in relation to the alarmPolicyTable. If the ring is monitored 
		by the agent according to policy number x in the alarmPolicyTable, 
		and the threshold condition has occured, then the bit #x in this 
		item will have the value '1'. Otherwise it will be '0'. For x-186 based 
		agents all bits of this item are '0'."
	::= { tokRingEntry 21 }

tokRingActiveMonitor  OBJECT-TYPE  
	SYNTAX  OCTET STRING ( SIZE (6))
	ACCESS  read-only
	STATUS  mandatory
	DESCRIPTION
		" The MAC Address of the station functioning as Active Monitor."
	::= { tokRingEntry 22 }

tokGroup OBJECT IDENTIFIER
      ::= {tok 2}


tokGroupTable OBJECT-TYPE      
      SYNTAX  SEQUENCE OF TokGroupEntry
      ACCESS  not-accessible
      STATUS mandatory
      ::= {tokGroup 1}
 
tokGroupEntry OBJECT-TYPE
      SYNTAX    TokGroupEntry
      ACCESS    not-accessible
      STATUS    mandatory
      INDEX     { tokGroupId }
      ::= { tokGroupTable 1 }
 
TokGroupEntry ::=
      SEQUENCE {
	 tokGroupId
	    INTEGER,
	 tokGroupAutoRightLoop
	    INTEGER,
	 tokGroupAutoLeftLoop
	    INTEGER,
	 tokGroupManRightLoop
	    INTEGER,
	 tokGroupManLeftLoop
	    INTEGER,
	 tokGroupRightNeighbor
	    INTEGER,
	 tokGroupLeftNeighbor
	    INTEGER,
	 tokGroupIOMode
	    INTEGER,
	 tokGroupBridgeMode
	    INTEGER,
	 tokGroupManLinkLoop
	    INTEGER,
	 tokGroupManBusLoop
	    INTEGER,
	 tokGroupAutoLinkLoop
	    INTEGER,
	 tokGroupAutoBusLoop
	    INTEGER,
	 tokGroupSpecificOID
	    OBJECT IDENTIFIER,
	 tokGroupStarSpeedDetect
	    INTEGER,
	tokGroupLobeSpeedDetect
	    INTEGER,
	tokGroupLSTBeaconing
	    INTEGER,
	tokGroupLSTBeaconThresh 
	   INTEGER
      }

tokGroupId OBJECT-TYPE
      SYNTAX  INTEGER (1..255)
      ACCESS  read-only
      STATUS  mandatory
      DESCRIPTION
      "Number of the slot in which the group is installed."
      ::= { tokGroupEntry 1 }
      
tokGroupAutoRightLoop OBJECT-TYPE
      SYNTAX  INTEGER {
	on(1),
	off(2),
	notSupported(255)
      }
      ACCESS  read-only
      STATUS  mandatory
      DESCRIPTION
      "Value ON of this attribute signifies that a hardware loop was
      automatically created on a Token Ring module which does not sense
      the existence of another token ring group on the right hand side.
       In the token ring stackable hub, 'Right' should be read as 'Down'. "
      ::= { tokGroupEntry 2 }
      
tokGroupAutoLeftLoop OBJECT-TYPE
      SYNTAX  INTEGER {
	on(1),
	off(2),
	notSupported(255)
      }
      ACCESS  read-only
      STATUS  mandatory
      DESCRIPTION
      "Value ON of this attribute signifies that a hardware loop was
      automatically created on a Token Ring module which does not sense
      the existence of another token ring group on the left hand side.
      In the token ring stackable hub, 'Left' should be read as 'Up'. "

      ::= { tokGroupEntry 3 }
      
tokGroupManRightLoop OBJECT-TYPE
      SYNTAX  INTEGER {
	on(1),
	off(2),
	notSupported(255)
      }
      ACCESS  read-write
      STATUS  mandatory
      DESCRIPTION
      "Setting this attribute to ON signifies a command to the hardware
      to create a loop on the Token Ring module which isolates the ring
      from the right hand side.
       In the token ring stackable hub, 'Right' should be read as 'Down'. "
      ::= { tokGroupEntry 4 }
      
tokGroupManLeftLoop OBJECT-TYPE
      SYNTAX  INTEGER {
	on(1),
	off(2),
	notSupported(255)
      }
      ACCESS  read-write
      STATUS  mandatory
      DESCRIPTION
      "Setting this attribute to ON signifies a command to the hardware
      to create a loop on the Token Ring module which isolates the ring
      from the left hand side.
      In the token ring stackable hub, 'Left' should be read as 'Up'. "

      ::= { tokGroupEntry 5 }
      
tokGroupRightNeighbor OBJECT-TYPE
      SYNTAX  INTEGER {
	   exist(1),
	   notExist(2)
      }
      ACCESS  read-only
      STATUS  mandatory
      DESCRIPTION
      "Attribute defining the existence of a neighbor another token ring
      group on the right hand side of the module.
      In the token ring stackable hub, 'Right' should be read as 'Down'. "
      ::= { tokGroupEntry 6 }
      
tokGroupLeftNeighbor OBJECT-TYPE
      SYNTAX  INTEGER {
	   exist(1),
	   notExist(2)
      }
      ACCESS  read-only
      STATUS  mandatory
      DESCRIPTION
      "Attribute defining the existence of a neighbor another token ring
      group on the left hand side of the module.
      In the token ring stackable hub, 'Left' should be read as 'Up'. "
      ::= { tokGroupEntry 7 }
      
tokGroupIOMode OBJECT-TYPE
      SYNTAX  INTEGER {
		single(1),
		dualRingIn(2),
		dualRingOut(3),
		illegalMode(4),
		lobe(5),
		intRepeater(6),
		star(7),
		starAndRingOut(8),
		starAndRI(10),
		starAndSingle(11),
		starAndIntRepeater(12),
		notSupported(255)
      }
      ACCESS  read-write
      STATUS  mandatory
      DESCRIPTION
      "Attribute defining the I/O mode (single, dual-ring-in, dual-ring-out)
      Lobe, Internal Repeater or Star) of a module from the the LTR-IO family."
      ::= { tokGroupEntry 8 }
      
tokGroupBridgeMode OBJECT-TYPE
      SYNTAX  INTEGER {
		modeA(1),
		modeB(2),
		modeC(3),
		notSupported(255)
      }
      ACCESS  read-write
      STATUS  mandatory
      DESCRIPTION
      "Attribute describing the operational mode of the bridge.
       For ITLB the following modes are defined:
       - Mode A: First channel connected to an external ring (RI,RO connectors)
		 and second channel connected to an internal ring;
       - Mode B: First channel connected to an external ring by a DTE connector
		 and second channel connected to an internal ring;
       - Mode C: First channel connected to an internal left ring and second
		 channel connected to an internal right ring."
      ::= { tokGroupEntry 9 }

tokGroupManLinkLoop OBJECT-TYPE
      SYNTAX  INTEGER {
	on(1),
	off(2),
	notSupported(255)
      }
      ACCESS  read-write
      STATUS  mandatory
      DESCRIPTION
      "Setting the value of this attribute to ON instructs the
      hardware of a  Token Ring repeater module to close the loop in the
      direction of the external connection."
      ::= { tokGroupEntry 10 }
      
tokGroupManBusLoop OBJECT-TYPE
      SYNTAX  INTEGER {
	on(1),
	off(2),
	notSupported(255)
      }
      ACCESS  read-write
      STATUS  mandatory
      DESCRIPTION
      "Setting the value of this attribute to ON instructs the
      hardware of a  Token Ring repeater module to close the loop in the
      direction of the internal bus."
      ::= { tokGroupEntry 11 }
      
tokGroupAutoLinkLoop OBJECT-TYPE
      SYNTAX  INTEGER {
	on(1),
	off(2),
	notSupported(255)
      }
      ACCESS  read-only
      STATUS  mandatory
      DESCRIPTION
      "Value ON of this attribute signifies that a hardware loop has been auto-
      matically closed by the hardwar of the  Token Ring repeater
      as a result of problems on the external link."
      ::= { tokGroupEntry 12 }
      
tokGroupAutoBusLoop OBJECT-TYPE
      SYNTAX  INTEGER {
	on(1),
	off(2),
	notSupported(255)
      }
      ACCESS  read-only
      STATUS  mandatory
      DESCRIPTION
      "Value ON of this attribute signifies that a hardware loop has been auto-
      matically closed by the hardware of the  Token Ring repeater
      as a result of problems on the internal bus."
      ::= { tokGroupEntry 13 }

tokGroupSpecificOID OBJECT-TYPE
	SYNTAX OBJECT IDENTIFIER
	ACCESS read-only
	STATUS mandatory
	DESCRIPTION
	"This attribute provides the OID of another group containing 
	additional more specific information regarding this instance."
	::= { tokGroupEntry 14 }

tokGroupStarSpeedDetect OBJECT-TYPE
	SYNTAX  INTEGER { on(1), off(2), notSupported(255) }
	ACCESS  read-write
	STATUS  mandatory
	DESCRIPTION
	"This attribute enables the speed detection mechanism for the ports which are in star mode"
	::= { tokGroupEntry 15 }

tokGroupLobeSpeedDetect OBJECT-TYPE
      SYNTAX  INTEGER {on(1), off(2), notSupported(255) }
      ACCESS  read-write
      STATUS  mandatory
      DESCRIPTION
      "This attribute enables the speed detection mechanism for 
        all ports which are in Lobe mode, at module level."
      ::= { tokGroupEntry 16 }

 tokGroupLSTBeaconing  OBJECT-TYPE
	SYNTAX 	INTEGER {
		on(1),
		off(2),
		notSupported(255)
		}
	ACCESS	read-only
	STATUS	mandatory
	DESCRIPTION
	"This item is for LST168 only. The ring is in beaconning state. Value
	 'on' informs on beacon fault when the number of consecutive beacon frames is 
	above BeaconThreshold."
	::= { tokGroupEntry 17 }
   
tokGroupLSTBeaconThresh OBJECT-TYPE
	SYNTAX 	INTEGER (1..255)
	ACCESS	read-write
	STATUS	mandatory
	DESCRIPTION
	"This item is for LST168 only.Threshold for the number of consecutive 
	beacon frames in the ring, above which a beaconning fault is alerted."
	::= { tokGroupEntry 18 }
  

tokGroupRingTable OBJECT-TYPE
      SYNTAX  SEQUENCE OF TokGroupRingEntry
      ACCESS  not-accessible
      STATUS mandatory
      ::= { tokGroup 2 }
 
tokGroupRingEntry OBJECT-TYPE
      SYNTAX    TokGroupRingEntry
      ACCESS    not-accessible
      STATUS    mandatory
      INDEX     { tokGroupRingGroupId, tokGroupRingId }
      ::= { tokGroupRingTable 1 }
 
TokGroupRingEntry ::=
      SEQUENCE {
	 tokGroupRingGroupId
	    INTEGER,
	 tokGroupRingId
	    INTEGER,
	 tokGroupRingSpeed
	    INTEGER,
	 tokGroupRingInserted
	    INTEGER,
	tokGroupRingStatus  
	    INTEGER
   }

tokGroupRingGroupId OBJECT-TYPE
      SYNTAX  INTEGER (1..255)
      ACCESS  read-only
      STATUS  mandatory
      DESCRIPTION
      "ID of the group to which the ring belongs."
      ::= { tokGroupRingEntry 1 }
      
tokGroupRingId OBJECT-TYPE
      SYNTAX  INTEGER (1..255)
      ACCESS  read-only
      STATUS  mandatory
      DESCRIPTION
      "ID of the ring."
      ::= { tokGroupRingEntry 2 }
      
tokGroupRingSpeed OBJECT-TYPE
      SYNTAX  INTEGER {
		unknown(1),
		oneMegabit(2),
		fourMegabit(3),
		sixteenMegabit(4),
		sixteenMgbEarly(5) -- for iftc/istc cards
      }
      ACCESS  read-write
      STATUS  mandatory
      DESCRIPTION
      "Attribute describing the bandwidth of the ring."
      ::= { tokGroupRingEntry 3 }
      
tokGroupRingInserted OBJECT-TYPE
      SYNTAX  INTEGER {
		notInserted(1),
		inserted(2),
		notSupported(255)
      }
      ACCESS  read-only
      STATUS  mandatory
      DESCRIPTION
      "Indicates that the bridge interface has inserted itself into
      the ring."
      ::= { tokGroupRingEntry 4 }
  
tokGroupRingStatus  OBJECT-TYPE
      SYNTAX  INTEGER {
                                                up(1),
                                                down(2),
                                                notSupported(255)
                                               }
      ACCESS  read-write
      STATUS  mandatory
      DESCRIPTION
      "This item sets the connection of a TR controller to 
       one of its possible connections, identified by
       the index of this row, for modules with a 
       multiple interface controller (for example ITRP)."
      ::= { tokGroupRingEntry 5 }    
    

tokPort OBJECT IDENTIFIER
      ::= {tok 3}


tokPortTable OBJECT-TYPE
      SYNTAX  SEQUENCE OF TokPortEntry
      ACCESS  not-accessible
      STATUS mandatory
      ::= { tokPort 1 }
 
tokPortEntry OBJECT-TYPE
      SYNTAX    TokPortEntry
      ACCESS    not-accessible
      STATUS    mandatory
      INDEX     { tokPortGroupId, tokPortId }
      ::= { tokPortTable 1 }
 
TokPortEntry ::=
      SEQUENCE {
	 tokPortGroupId
	    INTEGER,
	 tokPortId
	    INTEGER,
	 tokPortBypass
	    INTEGER,
	 tokPortConnected
	    INTEGER,
	 tokPortTCP
	    INTEGER,
	 tokPortCableFault
	    INTEGER,
	 tokPortFunctionalStatus
	    INTEGER,
	 tokPortLastSourceAddr
	    OCTET STRING,
	 tokPortSpecificOID
	    OBJECT IDENTIFIER,
	 tokPortRingSpeedError
	    INTEGER,
	 tokPortSpeedDetect
	    INTEGER,
	 tokPortRingId
	    INTEGER,
	 tokPortMapping
	    INTEGER
      }

tokPortGroupId OBJECT-TYPE
      SYNTAX  INTEGER (1..255)
      ACCESS  read-only
      STATUS  mandatory
      DESCRIPTION
      "ID of the group to which the token ring port belongs."
      ::= { tokPortEntry 1 }
      
tokPortId OBJECT-TYPE
      SYNTAX  INTEGER (1..255)
      ACCESS  read-only
      STATUS  mandatory
      DESCRIPTION
      "ID of the port in the tokPortTable."
      ::= { tokPortEntry 2 }
      
tokPortBypass OBJECT-TYPE
      SYNTAX  INTEGER {
	  on(1),
	  off(2),
	  notSupported(255)
      }
      ACCESS  read-write
      STATUS  mandatory
      DESCRIPTION
      "Setting the value of this attribute to ON causes the by-
      passing of the TokenRing  port."
      ::= { tokPortEntry 3 }
      
tokPortConnected OBJECT-TYPE
      SYNTAX  INTEGER {
	  connected(1),
	  notConnected(2),
	  notSupported(255)
      }
      ACCESS  read-only
      STATUS  mandatory
      DESCRIPTION
      "Attribute which describes the connection status of a Token Ring port 
      (inclusion of the Token Ring controller in the ring)."
      ::= { tokPortEntry 4 }
      
tokPortTCP OBJECT-TYPE
      SYNTAX  INTEGER {
	  on(1),
	  off(2),
	  notSupported(255)
      }
      ACCESS  read-write
      STATUS  mandatory
      DESCRIPTION
      "Setting the value of this attribute to ON causes the activation of the
      cable-fault detection mechanism."
      ::= { tokPortEntry 5 }
      
tokPortCableFault OBJECT-TYPE
      SYNTAX  INTEGER {
	 on(1),
	 off(2),
	 notSupported(255)
      }
      ACCESS  read-only
      STATUS  mandatory
      DESCRIPTION
      "Value ON of this attribute signifies the detection of a cable-fault on
      this specific Token Ring port."
      ::= { tokPortEntry 6 }
      
tokPortFunctionalStatus OBJECT-TYPE
      SYNTAX  INTEGER {
	ok(1),
	rld(2),            -- RxLinkDown
	tld(4),            -- TxLinkDown
	notSupported(255)
      }
      ACCESS  read-only
      STATUS  mandatory
      DESCRIPTION
      "The value of this attribute reflects the functional status of 
      Token Ring ports. Note that it is not mandatory that a certain port
      support all the enumerated states. Here is the lest of the possible
      states:
      ok(1) - fully functional port, transmitting and receiving packets.
      rld(2) - receive link down condition on the port.
      tld(4) - transmit link down condition on the port."
      ::= { tokPortEntry 7 }

tokPortLastSourceAddr OBJECT-TYPE
      SYNTAX  OCTET STRING
      ACCESS  read-only
      STATUS  mandatory
      DESCRIPTION
      "MAC source address of the last readable frame received by this
      port."
      ::= { tokPortEntry 8 }

tokPortSpecificOID OBJECT-TYPE
	SYNTAX OBJECT IDENTIFIER
	ACCESS read-only
	STATUS mandatory
	DESCRIPTION
	"This attribute provides the OID of another group containing 
	additional more specific information regarding this instance."
	::= { tokPortEntry 9 }

tokPortRingSpeedError OBJECT-TYPE
	SYNTAX  INTEGER { on(1), off(2), notSupported(255) }
	ACCESS  read-only
	STATUS  mandatory
	DESCRIPTION
	" This attribute is set to 'on' when the station tries to enter
	the ring with a speed different from the speed of the ring."
	::= { tokPortEntry 10 }

tokPortSpeedDetect  OBJECT-TYPE
	SYNTAX  INTEGER  { on(1), off(2), notSupported(255) }
	ACCESS  read-write
	STATUS  mandatory
	DESCRIPTION
	"This attribute enables the speed detection mechanism on a port level."
	::= { tokPortEntry 11 }

tokPortRingId  OBJECT-TYPE
	SYNTAX  INTEGER
	ACCESS  read-only
	STATUS  mandatory
	DESCRIPTION
	"Unique identifier of the ring/ring segment to which a specific port is connected."
	::= { tokPortEntry 12 }

tokPortMapping  OBJECT-TYPE
	SYNTAX  INTEGER { on(1), off(2), notSupported(255) }
	ACCESS  read-write
	STATUS  mandatory
	DESCRIPTION
	"This attribute enables/disables  participation of the selected port in port-to-address
	correlation algorithm. Default value is on(1)."
	::= { tokPortEntry 13 }

-- This MIB group providing information concerning Token-Ring stations statistics.

tokRingStation OBJECT IDENTIFIER
      ::= {tok 4}

tokRingStationTable OBJECT-TYPE
      SYNTAX  SEQUENCE OF TokRingStationEntry
      ACCESS  not-accessible
      STATUS mandatory
      ::= { tokRingStation 1 }
 
tokRingStationEntry OBJECT-TYPE
      SYNTAX    TokRingStationEntry
      ACCESS    not-accessible
      STATUS    mandatory
      INDEX     { tokRingId, tokRingStationMAC }
      ::= { tokRingStationTable 1 }
 
TokRingStationEntry ::=
      SEQUENCE {
	 tokRingStationRingId
	    INTEGER,
	 tokRingStationMAC
	    OCTET STRING,
	 tokRingStationLineErrors
	    Counter,
	 tokRingStationInternalErrors
	    Counter,
	 tokRingStationBurstErrors
	    Counter,
	 tokRingStationACErrors
	    Counter,
	 tokRingStationAbortsTrans
	    Counter,
	 tokRingStationLostFrames
	    Counter,
	 tokRingStationReceiveCongErrors
	    Counter,
	 tokRingStationFramesCopied
	    Counter,
	 tokRingStationFrequencyErrors
	    Counter,
	 tokRingStationTokenErrors
	    Counter,
	tokRingStationTotalErrors
	    Counter,
	tokRingStationFunctionalType
	    INTEGER
      }

tokRingStationRingId OBJECT-TYPE
      SYNTAX  INTEGER (1..255)
      ACCESS  read-only
      STATUS  mandatory
      DESCRIPTION
	"ID of the ring in the in which the station is inserted."
      ::= { tokRingStationEntry 1 }

tokRingStationMAC  OBJECT-TYPE
      SYNTAX  OCTET STRING
      ACCESS read-only
      STATUS mandatory
      DESCRIPTION
	"This item defines the MAC address (in token ring format)
	 of the station connected to the ring."
      ::= { tokRingStationEntry 2 }

tokRingStationLineErrors  OBJECT-TYPE
     SYNTAX  Counter
     ACCESS  read-only
     STATUS  mandatory
     DESCRIPTION
	"This counter is incremented when a frame or token is copied or repeated by a
	station, the E bit is zero in the frame or token and one of the following
	conditions exists: 
	1) there is a non-data bit (J or K bit) between the SD and the ED of the frame or
		    token, or
	2) there is an FCS error in the frame."
     ::= { tokRingStationEntry 3 }

tokRingStationInternalErrors OBJECT-TYPE
     SYNTAX  Counter
     ACCESS  read-only
     STATUS  mandatory
     DESCRIPTION
	"This counter is incremented when a station recognizes an internal error.
	Internal errors are detected by the adapter's hardware and/or firmware.
	They usually cause the detecting adapter to remove itself from the ring."
     ::= { tokRingStationEntry 4 }

tokRingStationBurstErrors OBJECT-TYPE
     SYNTAX  Counter
     ACCESS  read-only
     STATUS  mandatory
     DESCRIPTION
	"This counter is incremented when a station detects the absence of 
	  transitions for five half-bit timers (burst-five error)."
     ::= { tokRingStationEntry 5 }

tokRingStationACErrors OBJECT-TYPE
     SYNTAX  Counter
     ACCESS  read-only
     STATUS  mandatory
     DESCRIPTION
	"This counter is incremented when a station receives an AMP or SMP 
	frame in which A is equal to C is equal to 0, and then receives another 
	SMP frame with A is equal to C is equal to 0 without first receiving an 
	AMP frame. It denotes a station that cannot set the AC bits properly." 
    ::= { tokRingStationEntry 6 }


tokRingStationAbortsTrans  OBJECT-TYPE
     SYNTAX  Counter
     ACCESS  read-only
     STATUS  mandatory
     DESCRIPTION
	"This counter is incremented when a station transmits an abort delimiter
	 while transmitting." 
    ::= { tokRingStationEntry 7 }


tokRingStationLostFrames OBJECT-TYPE
     SYNTAX  Counter
     ACCESS  read-only
     STATUS  mandatory
     DESCRIPTION
	"This counter is incremented when a station is transmitting and its TRR 
	  timer expires. This condition denotes a condition where a transmitting 
	  station in strip mode does not receive the trailer of the frame before the
	  TRR timer goes off."
     ::= { tokRingStationEntry 8 }

tokRingStationReceiveCongErrors OBJECT-TYPE
     SYNTAX  Counter
     ACCESS  read-only
     STATUS  mandatory
     DESCRIPTION
	"This counter is incremented when a station recognizes a frame addressed
	  to its specific address, but has no available buffer space indicating that 
	  the station is congested."
    ::= { tokRingStationEntry 9 }

tokRingStationFramesCopied OBJECT-TYPE
     SYNTAX  Counter
     ACCESS  read-only
     STATUS  mandatory
     DESCRIPTION
	"This counter is incremented when a station recognizes a frame addressed 
	to its specific address and detects that the FS field A bits are set to 1
	 indicating a possible line hit or duplicate address."
     ::= { tokRingStationEntry 10 }

tokRingStationFrequencyErrors OBJECT-TYPE
     SYNTAX  Counter
     ACCESS  read-only
     STATUS  mandatory
     DESCRIPTION
	"The number of times the interface has detected that the frequency of the
	incoming signal differs from the expected frequency by more than that 
	specified by the IEEE 802.5 standard."
     ::= { tokRingStationEntry 11 }

tokRingStationTokenErrors OBJECT-TYPE
     SYNTAX  Counter
     ACCESS  read-only
     STATUS  mandatory
     DESCRIPTION
	"This counter is incremented when a station acting as the active monitor
	 recognizes an error condition that needs a token transmitted."
     ::= { tokRingStationEntry 12 }

tokRingStationTotalErrors  OBJECT-TYPE
     SYNTAX  Counter
     ACCESS  read-only
     STATUS  mandatory
     DESCRIPTION
	"This counter is the sum of all REM counters for this station, i.e.: LineErrors,
	InternalErrors, BurstErrors, ACErrors, AbortsTrans, LostFrames, FrameCopiedErrors, 
	ReceiveCongestionsErrors, FrequencyErrors, TokenErrors."
     ::= { tokRingStationEntry 13 }

tokRingStationFunctionalType OBJECT-TYPE
     SYNTAX  INTEGER {
		ringStation(1),
		agent(2),
		bridge(3),
		netbios(4),
		ringParameterServer(5),
		ringErrorMonitor(6),
		lanManager(7),
		activeMonitor(8),
		other(9)
     }
     ACCESS  read-only
     STATUS  mandatory
     DESCRIPTION
	"The  function of the concerned station in the ring."
     ::= { tokRingStationEntry 14 }

-- Token Ring Internal Port group
-- Implementation of this group is Optional.

tokIntPort OBJECT IDENTIFIER
      ::= {tok 5}


tokIntPortTable OBJECT-TYPE
      SYNTAX  SEQUENCE OF TokIntPortEntry
      ACCESS  not-accessible
      STATUS  mandatory
      DESCRIPTION
      "Table of configuration attributes for items specific 
      to token ring internal ports, which can not be addressed 
     via the genIntPort group."
      ::= { tokIntPort 1 } 

tokIntPortEntry OBJECT-TYPE
      SYNTAX  TokIntPortEntry
      ACCESS  not-accessible
      STATUS  mandatory
      DESCRIPTION
      "An entry in the table, containing data about a single port." 
      INDEX  { tokIntPortGroupId, tokIntPortId }
      ::= { tokIntPortTable 1 }

TokIntPortEntry  ::=
      SEQUENCE  {
	tokIntPortGroupId
	  INTEGER,
	tokIntPortId
	  INTEGER,
	tokIntPortLeftNeighbor
	  INTEGER,
	tokIntPortRightNeighbor
	  INTEGER,
	tokIntPortManLeftLoop
	  INTEGER,
	tokIntPortManRightLoop
	  INTEGER,
	tokIntPortAutoLeftLoop
	  INTEGER,
	tokIntPortAutoRightLoop
	  INTEGER
}

tokIntPortGroupId  OBJECT-TYPE
      SYNTAX  INTEGER (1..255)
      ACCESS  read-only
      STATUS  mandatory
      DESCRIPTION
      "Index which identifies the group inside the hub for which this
      entry contains information. Equals the number of the slot by which
      the group containing the internal port is accessed. This value is 
      never greater than chNumberOfSlots."
      ::= { tokIntPortEntry 1 }
      
tokIntPortId OBJECT-TYPE
      SYNTAX  INTEGER (1..255)
      ACCESS  read-only
      STATUS  mandatory
      DESCRIPTION
      "Index which identifies the internal port inside the group for which 
      this entry contains information. 
      This value is never greater than genGroupNumberOfIntPorts
      of the group to which the port belongs."
      ::= { tokIntPortEntry 2 }
      
tokIntPortLeftNeighbor  OBJECT-TYPE
      SYNTAX  INTEGER {
			exist(1),
			notExist(2),
			bypass(3)
			}
      ACCESS  read-only
      STATUS  mandatory
      DESCRIPTION
      "Attribute defining the existence of another token ring
      group to the left hand side of the module, on the TR 
      bus to which this intrnal port is connected. The value 
      bypass is reported when the controller is not connected 
      to the bus."
      ::= { tokIntPortEntry 3 }
      
tokIntPortRightNeighbor OBJECT-TYPE
      SYNTAX  INTEGER {
			exist(1),
			notExist(2),
			bypass(3)
			}
      ACCESS  read-only
      STATUS  mandatory
      DESCRIPTION
      "Attribute defining the existence of another token ring
      group to the left hand side of the module, on the TR 
      bus to which this intrnal port is connected. The value 
      bypass is reported when the controller is not connected 
      to the bus."
      ::= { tokIntPortEntry 4 }
      
tokIntPortManLeftLoop  OBJECT-TYPE
      SYNTAX  INTEGER	{
			on(1),
			off(2)
			}
      ACCESS  read-write
      STATUS  mandatory
      DESCRIPTION
      "Setting this attribute to on signifies a command to the hardware
      to create a loop to the left of the module, on the bus  to which 
      this internal port is connected." 
      ::= { tokIntPortEntry 5 }
      
tokIntPortManRightLoop  OBJECT-TYPE
      SYNTAX  INTEGER {
			on(1),
			off(2)
			}
      ACCESS  read-write
      STATUS  mandatory
      DESCRIPTION
      "Setting this attribute to on signifies a command to the hardware
      to create a loop to the left of the module, on the bus  to which 
      this internal port is connected." 
      ::= { tokIntPortEntry 6 }
      
tokIntPortAutoLeftLoop  OBJECT-TYPE
	SYNTAX INTEGER {
			on(1),
			off(2)
			}
	ACCESS read-only
	STATUS mandatory
	DESCRIPTION
      "Value 'on' of this attribute signifies that a left hardware loop was
      created on the Token Ring bus to which this internal port is 
      connected."
	::= { tokIntPortEntry 7 }

tokIntPortAutoRightLoop  OBJECT-TYPE
	SYNTAX  INTEGER{
			on(1),
			off(2)
			}
	ACCESS   read-only
	STATUS  mandatory
	DESCRIPTION
      "Value 'on' of this attribute signifies that a right hardware loop was
      created on the Token Ring bus to which this internal port is 
      connected."
	::= { tokIntPortEntry 8 }


tsGroup OBJECT IDENTIFIER      
      ::= {ts 1}


tsGroupTable OBJECT-TYPE
      SYNTAX  SEQUENCE OF TsGroupEntry
      ACCESS  not-accessible
      STATUS mandatory
      ::= {tsGroup 1}
 
tsGroupEntry OBJECT-TYPE
      SYNTAX    TsGroupEntry
      ACCESS    not-accessible
      STATUS    mandatory
      INDEX     { tsGroupId }
      ::= { tsGroupTable 1 }
 
TsGroupEntry ::=
      SEQUENCE {
	 tsGroupId
	    INTEGER,
	 tsGroupLATStatus
	    INTEGER,
	 tsGroupOperationMode
	    INTEGER
      }

tsGroupId OBJECT-TYPE
      SYNTAX  INTEGER (1..255)
      ACCESS  read-only
      STATUS  mandatory
      DESCRIPTION
      "Number of the slot in which the group is installed."
      ::= { tsGroupEntry 1 }
      
tsGroupLATStatus OBJECT-TYPE
      SYNTAX  INTEGER {
	on(1),
	off(2)
	}
      ACCESS read-only
      STATUS mandatory
      DESCRIPTION
      "Value ON of this attribute means that LAT protocol is Enabled on the
       Ethernet module."
      ::= { tsGroupEntry 2 }
      
tsGroupOperationMode OBJECT-TYPE
      SYNTAX  INTEGER {
	      diagnostics(1),
	      diagnosticsFailure(2),
	      loading(3),
	      loadingFailure(4),
	      operational(5)
      }
      ACCESS  read-only
      STATUS  mandatory
      DESCRIPTION
      "This attribute describes the operation mode of the module in a
      multiprocessor configuration sensor, as reported by interprocessors
      communication."
      ::= { tsGroupEntry 3 }
      

ltalkPort OBJECT IDENTIFIER
      ::= {ltalk 1}


ltalkPortTable OBJECT-TYPE
      SYNTAX  SEQUENCE OF LtalkPortEntry
      ACCESS  not-accessible
      STATUS mandatory
      ::= {ltalkPort 1}
 
ltalkPortEntry OBJECT-TYPE
      SYNTAX    LtalkPortEntry
      ACCESS    not-accessible
      STATUS    mandatory
      INDEX     { ltalkPortGroupId, ltalkPortId }
      ::= { ltalkPortTable 1 }
 
LtalkPortEntry ::=
      SEQUENCE {
	 ltalkPortGroupId
	    INTEGER,
	 ltalkPortId
	    INTEGER,
	 ltalkPortTest
	    INTEGER,
	 ltalkPortTestResult
	    INTEGER,
	 ltalkPortJam
	    INTEGER
      }

ltalkPortGroupId OBJECT-TYPE
      SYNTAX  INTEGER (1..255)
      ACCESS  read-only
      STATUS  mandatory
      DESCRIPTION
      "Number of the group to which the port belongs."
      ::= { ltalkPortEntry 1 }
      
ltalkPortId OBJECT-TYPE
      SYNTAX  INTEGER (1..255)
      ACCESS  read-only
      STATUS  mandatory
      DESCRIPTION
      "ID of the port in the ltalkPortTable."
      ::= { ltalkPortEntry 2 }
      
ltalkPortTest OBJECT-TYPE
      SYNTAX  INTEGER {
	on(1),
	off(2)
      }
      ACCESS  read-write
      STATUS  mandatory
      DESCRIPTION
      "A value ON of this attribute indicates that a port test should be
      performed upon the port defined by the attribute instance."
      ::= { ltalkPortEntry 3 }
      
ltalkPortTestResult OBJECT-TYPE
      SYNTAX  INTEGER {
	ok(1),
	faulty(2)
      }
      ACCESS  read-only
      STATUS  mandatory
      DESCRIPTION
      "Indicates the result of a port test performed on this port."
      ::= { ltalkPortEntry 4 }
      
ltalkPortJam OBJECT-TYPE
      SYNTAX  INTEGER {
	on(1),
	off(2)
      }
      ACCESS  read-only
      STATUS  mandatory
      DESCRIPTION
      "An ON value of this attribute indicates a Jam error on the specific
      port."
      ::= { ltalkPortEntry 5 }
      

clGroup OBJECT IDENTIFIER      
      ::= {cl 1}


clGroupTable OBJECT-TYPE
      SYNTAX  SEQUENCE OF ClGroupEntry
      ACCESS  not-accessible
      STATUS mandatory
      ::= {clGroup 1}
 
clGroupEntry OBJECT-TYPE
      SYNTAX    ClGroupEntry
      ACCESS    not-accessible
      STATUS    mandatory
      INDEX     { clGroupId }
      ::= { clGroupTable 1 }
 
ClGroupEntry ::=
      SEQUENCE {
	 clGroupId
	    INTEGER,
	 clGroupClockRedundancy
	    INTEGER,
	 clGroupMainClock
	    INTEGER,
	 clGroupTestClocks
	    INTEGER
      }

clGroupId OBJECT-TYPE
      SYNTAX  INTEGER (1..255)
      ACCESS  read-only
      STATUS  mandatory
      DESCRIPTION
      "Number of the slot in which the group is installed."
      ::= { clGroupEntry 1 }
      
clGroupClockRedundancy OBJECT-TYPE
      SYNTAX  INTEGER {
	on(1),
	off(2)
	}
      ACCESS read-write
      STATUS mandatory
      DESCRIPTION
      "Value ON of this attribute defines a redundancy (backup) relationship
      between the internal and external clocks on the LCL100 module."
      ::= { clGroupEntry 2 }
      
clGroupMainClock OBJECT-TYPE
      SYNTAX  INTEGER
      ACCESS  read-write
      STATUS  mandatory
      DESCRIPTION
      "Value of this attribute is an index into clPortTable, and defines the 
      clock that should operate or a main clock in redundancy scheme.
      Serves as 'Clock selection' switch on the card."
      ::= { clGroupEntry 3 }
      
clGroupTestClocks OBJECT-TYPE
      SYNTAX  INTEGER {
	on(1),
	off(2)
      }
      ACCESS  read-write
      STATUS  mandatory
      DESCRIPTION
      "A value ON of this attribute indicates that a test should be
      performed on all clock ports."
      ::= { clGroupEntry 4 }
      

clPort OBJECT IDENTIFIER      
      ::= {cl 2}


clPortTable OBJECT-TYPE
      SYNTAX  SEQUENCE OF ClPortEntry
      ACCESS  not-accessible
      STATUS mandatory
      ::= {clPort 1}
 
clPortEntry OBJECT-TYPE
      SYNTAX    ClPortEntry
      ACCESS    not-accessible
      STATUS    mandatory
      INDEX     { clPortGroupId, clPortId }
      ::= { clPortTable 1 }
 
ClPortEntry ::=
      SEQUENCE {
	 clPortGroupId
	    INTEGER,
	 clPortId
	    INTEGER,
	 clPortFunctionalStatus
	    INTEGER
      }

clPortGroupId OBJECT-TYPE
      SYNTAX  INTEGER (1..255)
      ACCESS  read-only
      STATUS  mandatory
      DESCRIPTION
      "Number of the group to which the port belongs."
      ::= { clPortEntry 1 }
      
clPortId OBJECT-TYPE
      SYNTAX  INTEGER (1..255)
      ACCESS  read-only
      STATUS  mandatory
      DESCRIPTION
      "ID of the port in the clPortTable."
      ::= { clPortEntry 2 }
      
clPortFunctionalStatus OBJECT-TYPE
      SYNTAX  INTEGER {
	ok(1),
	faulty(2)
      }
      ACCESS  read-only
      STATUS  mandatory
      DESCRIPTION
      "Indicates whether the clock is faulty or not."
      ::= { clPortEntry 3 }
      

-- Implementation of this group is mandatory for all new 
-- 100Base-T Repeater MIB modules. 
-- It defines OIDs which allow group identification.
-- This will enable conformance to the rptrGroupObjectID 
-- and rptr100GroupObjectID from the standard repeater MIB 



iwb OBJECT IDENTIFIER ::= { bRouter 1 }  --mandatory for the integrated LAN/WAN bridges 
iwr OBJECT IDENTIFIER ::= { bRouter 2 }   --mandatory for the integrated LAN/WAN routers
itr OBJECT IDENTIFIER ::= { bRouter 3 }     --mandatory for the integrated LAN/WAN extenders


iwrGroupTable OBJECT-TYPE
	SYNTAX  SEQUENCE OF IwrGroupEntry
	ACCESS  not-accessible
	STATUS  mandatory
	DESCRIPTION
	"Attributes pertaining to the integrated router module."
	::= { iwr 1 }

iwrGroupEntry OBJECT-TYPE
	SYNTAX  IwrGroupEntry
	ACCESS  not-accessible
	STATUS  mandatory
	DESCRIPTION
	"An entry in the table."
	INDEX   { iwrGroupId }
	::= { iwrGroupTable 1 }

IwrGroupEntry ::=
	SEQUENCE {
	    iwrGroupId
		INTEGER,
	    iwrOperState
		INTEGER,
	    iwrPMState
		INTEGER,
	    iwrIOMState
		INTEGER,
	    iwrEthernetMode
		INTEGER,
	    iwrPrimaryFDDIInsert 
		INTEGER,
	    iwrSecondaryFDDIInsert 
		INTEGER
	    }

iwrGroupId OBJECT-TYPE
	SYNTAX  INTEGER
	ACCESS  read-only
	STATUS  mandatory
	DESCRIPTION
	"Slot number in which the module is located."
	::= { iwrGroupEntry 1 }

iwrOperState OBJECT-TYPE
	SYNTAX  INTEGER { run(1), boot(2), fail(3) }
	ACCESS  read-only
	STATUS  mandatory
	DESCRIPTION
	"One of the possible states of the module.
	run(1) - indicates a successful completion of the boot 
	and self test procedure.
	boot(2) - indicates that the module is performing the
	boot and self-test procedure.
	fail(3) - indicates an unsuccessful completion of the boot 
	and self-test procedure."
	::= { iwrGroupEntry 2 }

iwrPMState OBJECT-TYPE
	SYNTAX  INTEGER { ok(1), fail(2) }
	ACCESS  read-only
	STATUS  mandatory
	DESCRIPTION
	"The state of the Processor Module."
	::= { iwrGroupEntry 3 }

iwrIOMState OBJECT-TYPE
	SYNTAX  INTEGER { ok(1), fail(2) }
	ACCESS  read-only
	STATUS  mandatory
	DESCRIPTION
	"The state of the Input/Output Module."
	::= { iwrGroupEntry 4 }

iwrEthernetMode  OBJECT-TYPE
	SYNTAX  INTEGER { bus4(1), ex10bt(2), notSupported(255) }
	ACCESS  read-write
	STATUS  mandatory
	DESCRIPTION
	"Determines whether the ex10bt(2) LAN controller is connected
	to the front panel 10BaseT or to backplane bus4(1)."
	::= { iwrGroupEntry 5 }

iwrPrimaryFDDIInsert OBJECT-TYPE
	SYNTAX  INTEGER { inserted(1), bypassed(2), notSupported(255) }
	ACCESS  read-only
	STATUS  mandatory
	DESCRIPTION
	"This variable is specific to the IEFR router
	and reflect the status of the Primary - P 
	FDDI interfaces of the router. There is a corresponding LED
	for each one on the front pannel and this information may be
	used to build a 'real-life' representation of the module's pannel
	on a management application."
	::= { iwrGroupEntry 6 }

iwrSecondaryFDDIInsert OBJECT-TYPE
	SYNTAX  INTEGER { inserted(1), bypassed(2), notSupported(255) }
	ACCESS  read-only
	STATUS  mandatory
	DESCRIPTION
	"This variable is specific to the IEFR router
	and reflect the status of the Secondary - S 
	FDDI interfaces of the router. There is a corresponding LED
	for each one on the front pannel and this information may be
	used to build a 'real-life' representation of the module's pannel
	on a management application."
	::= { iwrGroupEntry 7 }

iwrWANTable OBJECT-TYPE
	SYNTAX  SEQUENCE OF IwrWANEntry
	ACCESS  not-accessible
	STATUS  mandatory
	DESCRIPTION
	"WAN data table."
	::= { iwr 2 }

iwrWANEntry OBJECT-TYPE
	SYNTAX  IwrWANEntry
	ACCESS  not-accessible
	STATUS  mandatory
	DESCRIPTION
	"Entry in the table."
	INDEX           { iwrWANGroupId, iwrWANPortId }
	::= { iwrWANTable 1 }

IwrWANEntry ::=
	SEQUENCE {
	     iwrWANGroupId
		INTEGER,
	     iwrWANPortId
		INTEGER,
	     iwrWANConnection
		INTEGER,
	     iwrWANPortCableType
		INTEGER
	}

iwrWANGroupId OBJECT-TYPE
	SYNTAX  INTEGER
	ACCESS  read-only
	STATUS  mandatory
	DESCRIPTION
	"Slot number in which the module is located."
	::= { iwrWANEntry 1 }

iwrWANPortId OBJECT-TYPE
	SYNTAX  INTEGER
	ACCESS  read-only
	STATUS  mandatory
	DESCRIPTION
	"WAN port index."
	::= { iwrWANEntry 2 }

iwrWANConnection OBJECT-TYPE
	SYNTAX  INTEGER { connected(1), disconnected(2) }
	ACCESS  read-only
	STATUS  mandatory
	DESCRIPTION
	"WAN connection status."
	::= { iwrWANEntry 3 }

iwrWANPortCableType OBJECT-TYPE
	SYNTAX  INTEGER { x21(1), rs232(2), v35(3) }
	ACCESS  read-only
	STATUS  mandatory
	DESCRIPTION
	"Cable type connected to the specified WAN port."
	::= { iwrWANEntry 4 }

iwrInterfaceAddrTable OBJECT-TYPE
	SYNTAX  SEQUENCE OF IwrInterfaceEntry
	ACCESS  not-accessible
	STATUS  mandatory
	DESCRIPTION
	"The table contain for each interface:
	1. The IP address that was configured to the interface.
	2. The IP netmask that was configured to the interface.
	    All the network bits are set to 1 and all the hosts
	    bits are set to 0.
	3. The Mac Address assigned to the interface."
	::= { iwr 3 }

iwrInterfaceEntry OBJECT-TYPE
	SYNTAX  IwrInterfaceEntry
	ACCESS  not-accessible
	STATUS  mandatory
	DESCRIPTION
	"Entry in the table."
	INDEX           { iwrInterfaceGroupId, iwrInterfaceId }
	::= { iwrInterfaceAddrTable 1 }

IwrInterfaceEntry ::=
	SEQUENCE {
	     iwrInterfaceGroupId
		INTEGER,
	     iwrInterfaceId
		INTEGER,
	     iwrInterfaceAddr
		IpAddress,
	     iwrInterfaceMask
		IpAddress,
	     iwrInterfaceMacAddress
		OCTET STRING
		}

iwrInterfaceGroupId OBJECT-TYPE
	SYNTAX  INTEGER
	ACCESS  read-only
	STATUS  mandatory
	DESCRIPTION
	"Slot number in which the module is located."
	::= { iwrInterfaceEntry 1 }

iwrInterfaceId OBJECT-TYPE
	SYNTAX  INTEGER
	ACCESS  read-only
	STATUS  mandatory
	DESCRIPTION
	"IP Interface port index."
	::= { iwrInterfaceEntry 2 }

iwrInterfaceAddr OBJECT-TYPE
	SYNTAX  IpAddress
	ACCESS  read-only
	STATUS  mandatory
	DESCRIPTION
	"The IP Address of this indexed port."
	::= { iwrInterfaceEntry 3 }

iwrInterfaceMask OBJECT-TYPE
	SYNTAX  IpAddress
	ACCESS  read-only
	STATUS  mandatory
	DESCRIPTION
	"The IP Address Mask of this indexed port."
	::= { iwrInterfaceEntry 4 }

iwrInterfaceMacAddress OBJECT-TYPE
	SYNTAX  OCTET STRING
	ACCESS  read-only
	STATUS  mandatory
	DESCRIPTION
	"The Mac Address of this indexed interface."
	::= { iwrInterfaceEntry 5 }

itrGroupTable OBJECT-TYPE
	SYNTAX  SEQUENCE OF ItrGroupEntry
	ACCESS  not-accessible
	STATUS  mandatory
	DESCRIPTION
	"Table of attributes pertaining to the ITRE module."
	::= { itr 1 }

itrGroupEntry OBJECT-TYPE
	SYNTAX  ItrGroupEntry
	ACCESS  not-accessible
	STATUS  mandatory
	DESCRIPTION
	"An entry in the table."
	INDEX   { itrGroupId }
	::= { itrGroupTable 1 }

ItrGroupEntry ::=
	SEQUENCE {
	     itrGroupId
		INTEGER,
	     itrMainSWVersion
		DisplayString,
	     itrConfigState
		INTEGER,
	     itrModuleState
		INTEGER
	     }

itrGroupId OBJECT-TYPE
	SYNTAX  INTEGER
	ACCESS  read-only
	STATUS  mandatory
	DESCRIPTION
	"Slot number in which the module is located."
	::= { itrGroupEntry 1 }

itrMainSWVersion OBJECT-TYPE
	SYNTAX  DisplayString
	ACCESS  read-only
	STATUS  mandatory
	DESCRIPTION
	"Software version of the main CPU."
	::= { itrGroupEntry 2 }

itrConfigState OBJECT-TYPE
	SYNTAX  INTEGER { local(1), remote(2), notSupported(255) }
	ACCESS  read-only
	STATUS  mandatory
	DESCRIPTION
	"Configuration state of the module."
	::= { itrGroupEntry 3 }

itrModuleState OBJECT-TYPE
	SYNTAX  INTEGER { oper(1), load(2), setup(3), notSupported(255) }
	ACCESS  read-only
	STATUS  mandatory
	DESCRIPTION
	"State of the ISTC/IFTC modules."
	::= { itrGroupEntry 4 }


itrLinkTable OBJECT-TYPE
	SYNTAX  SEQUENCE OF ItrLinkEntry
	ACCESS  not-accessible
	STATUS  mandatory
	DESCRIPTION
	"ITRE links table."
	::= { itr 2 }

itrLinkEntry OBJECT-TYPE
	SYNTAX  ItrLinkEntry
	ACCESS  not-accessible
	STATUS  mandatory
	DESCRIPTION
	"Entry in the table."
	INDEX           { itrLinkGroupId, itrLinkPortId }
	::= { itrLinkTable 1 }

ItrLinkEntry ::=
	SEQUENCE {
	     itrLinkGroupId
		INTEGER,
	     itrLinkPortId
		INTEGER,
	      itrLinkIf
		INTEGER,
	      itrLinkMode
		INTEGER,
	      itrLinkAsyncRate
		INTEGER,
	      itrLinkSyncRate
		INTEGER,
	      itrLinkParity
		INTEGER,
	      itrLinkParityEvenOdd
		INTEGER,
	      itrLinkStopBit
		INTEGER,
	      itrLinkRemoteLANConn
		INTEGER,
	      itrLinkFunctionalStatus
		INTEGER,
	      itrLinkAdminStatus
		INTEGER,
	      itrLinkReset
		INTEGER,
	      itrLinkConnectionStatus     
		INTEGER,
	      itrLinkDataBits
		INTEGER,
	      itrLinkControlSignalsMode
		INTEGER,
	      itrLinkParityType
		INTEGER
	}

itrLinkGroupId OBJECT-TYPE
	SYNTAX  INTEGER
	ACCESS  read-only
	STATUS  mandatory
	DESCRIPTION
	"Slot number in which the module is located."
	::= { itrLinkEntry 1 }

itrLinkPortId OBJECT-TYPE
	SYNTAX  INTEGER
	ACCESS  read-only
	STATUS  mandatory
	DESCRIPTION
	"Link identifier."
	::= { itrLinkEntry 2 }

itrLinkIf OBJECT-TYPE
	SYNTAX  INTEGER { v11(1), v24(2), v35(3), dte-dce(4) }
	ACCESS  read-only
	STATUS  mandatory
	DESCRIPTION
	"Interface type."
	::= { itrLinkEntry 3 }

itrLinkMode OBJECT-TYPE
	SYNTAX  INTEGER { sync(1), async(2) }
	ACCESS  read-write
	STATUS  mandatory
	DESCRIPTION
	"Synchronous or asynchronous modes on the link."
	::= { itrLinkEntry 4 }

itrLinkAsyncRate OBJECT-TYPE
	SYNTAX  INTEGER { r2400(1), r4800(2), r9600(3),
			r14400(4), r19200(5), r38400(6), r56000(7),
			r57600(8), r64000(9), r115200(10), unknown(255) }
	ACCESS  read-write
	STATUS  mandatory
	DESCRIPTION
	"Possible link speeds that can be set in asynchronous mode."
	::= { itrLinkEntry 5 }

itrLinkSyncRate OBJECT-TYPE
	SYNTAX  INTEGER {
				r1200(1), r2400(2), r4800(3),
				r9600(4), r14400(5), r19200(6),
				r38400(7), r48000(8), r56000(9),
				r57600(10), r64000(11), r112000(12),
				r128000(13), r256000(14), r384000(15),
				r512000(16), r786000(17), r1024000(18),
				r1544000(19), r2048000(20), unknown(255) }
	ACCESS  read-only
	STATUS  mandatory
	DESCRIPTION
	"Link speeds in synchronous mode."
	::= { itrLinkEntry 6 }

itrLinkParity OBJECT-TYPE
	SYNTAX  INTEGER { on(1), off(2), notSupported(255) }
	ACCESS  read-write
	STATUS  deprecated
	DESCRIPTION
	"This attribute enables/disables parity checking."
	::= { itrLinkEntry 7 }

itrLinkParityEvenOdd OBJECT-TYPE
	SYNTAX  INTEGER { even(1), odd(2), notSupported(255) }
	ACCESS  read-write
	STATUS  deprecated
	DESCRIPTION
	"Even or odd parity."
	::= { itrLinkEntry 8 }

itrLinkStopBit OBJECT-TYPE
	SYNTAX  INTEGER { one(1), two(2), none(3), notSupported(255) }
	ACCESS  read-write
	STATUS  mandatory
	DESCRIPTION
	"Number of stop bits (1 or 2 ) in asynchronous mode. The value 'none'
	is returned in synchronous mode."
	::= { itrLinkEntry 9 }

itrLinkRemoteLANConn OBJECT-TYPE
	SYNTAX  INTEGER { connected(1), disconnected(2), notSupported(255) }
	ACCESS  read-only
	STATUS  mandatory
	DESCRIPTION
	"This attribute shows whether the remote ITRE is connected to the LAN."
	::= { itrLinkEntry 10 }

itrLinkFunctionalStatus OBJECT-TYPE
	SYNTAX  INTEGER { ok(1), fail(2), noRxClk(3), disable(4) }
	ACCESS  read-only
	STATUS  mandatory
	DESCRIPTION
	"The attribute represents the status of the WAN link."
	::= { itrLinkEntry 11 }

itrLinkAdminStatus  OBJECT-TYPE
	SYNTAX  INTEGER {
				 enabled(1),
				 enabledOnDemand(2),
				 disabled(3),
				 notSupported(255)
				}
	ACCESS  read-write
	STATUS  mandatory
	DESCRIPTION
	"The administrative status of the WAN port of the ITRE/IERE 
	family. enabled(1) enables the WAN link, disabled(3) disables 
	it, and enableddOnDemand(2) allows the ITRE/IERE to decide whether 
	to open the port or close it. In this case, it's RO value and 
	 the state of the module is reflected in the genPortAdminStatus object."
	::= { itrLinkEntry 12 }

itrLinkReset  OBJECT-TYPE
	SYNTAX  INTEGER {
				 on(1),
				 off(2),
				 notSupported(255)
				}
	ACCESS  read-write
	STATUS  mandatory
	DESCRIPTION
	"Reset the WAN link"
	::= { itrLinkEntry 13 }

itrLinkConnectionStatus     OBJECT-TYPE
	       SYNTAX      INTEGER { on(1), off(2), trying(3),  notSupported(255) }
	       ACCESS       read-only
	       STATUS       mandatory
	       DESCRIPTION
	       "This attribute represents the end-to-end connection status
	of the WAN link. When the connection is ok, the link is 'on(1)'. 
	When the connection is lost the link is 'trying(3)'constantly to 
	re-establish the connection until it becomes 'on(1)' or 'off(2)' ."
	::= { itrLinkEntry 14 }

 itrLinkDataBits     OBJECT-TYPE
	       SYNTAX     INTEGER { seven(1), eight(2), none(3), notSupported(255) }
	       ACCESS      read-write
	       STATUS      mandatory
	       DESCRIPTION 
	       "Number of data bits (7 or 8) in asynchronous mode. The value
	'notSupported' is returned in synchronous mode."
	::= { itrLinkEntry 15 }

itrLinkControlSignalsMode     OBJECT-TYPE
	       SYNTAX     INTEGER { enable(1), disable(2), notSupported(255) }
	       ACCESS     read-write
	       STATUS     mandatory
	       DESCRIPTION
	       "The value of this attribute determines the control signals
	(RTS,CTS, CD) mode while working with a MODEM, either in synchronous or
	asynchronous mode. When the Control Signals Mode is disabled, there is no
	flow control with the MODEM."
	::= { itrLinkEntry 16 }

itrLinkParityType     OBJECT-TYPE
	       SYNTAX     INTEGER { 
			noParity(1),
			even(2),
			odd(3),
			none(4),
			notSupported(255)
	}
	       ACCESS     read-write
	       STATUS     mandatory
	       DESCRIPTION
	       "This attribute represents the parity type in asynchronous
	mode. The value 'none' is returned in synchronous mode."
	::= { itrLinkEntry 17 }


-- FDDI modules and LSF 100

lntFddiPort OBJECT IDENTIFIER ::= {lntFddiGroup 1}

lntFddiPortTable OBJECT-TYPE
SYNTAX SEQUENCE OF LntFddiPortEntry
ACCESS not-accessible
STATUS mandatory
::= { lntFddiPort 1}

lntFddiPortEntry OBJECT-TYPE
	SYNTAX LntFddiPortEntry
	ACCESS not-accessible
	STATUS mandatory
	INDEX {lntFddiPortGroupId, lntFddiPortId}
	::= {lntFddiPortTable 1}

LntFddiPortEntry ::=
	SEQUENCE {
	lntFddiPortGroupId
		INTEGER,
	lntFddiPortId
		INTEGER,
	lntFddiPortMACCurrentPath
		INTEGER,
	lntFddiPortOpticalSwitchExist
		INTEGER,
	lntFddiPortRingConfiguration
		INTEGER,
	lntFddiPortLineStatusA
		INTEGER,
	lntFddiPortLineStatusB
		INTEGER,
	lntFddiPortRxTotalPackets
		Counter,
	lntFddiPortRxTotalOctets
		Counter,
	lntFddiPortTxTotalPackets
		Counter,
	lntFddiPortTxTotalOctets
		Counter,
	lntFddiPortIPXtoFDDIMatching
		INTEGER,
	lntFddiPortFDDItoIPXMatching
		INTEGER
	}

lntFddiPortGroupId OBJECT-TYPE
	SYNTAX INTEGER (1..255)
	ACCESS read-only
	STATUS mandatory
	DESCRIPTION
	"Id of the slot to which the fddi port belongs." 
	::= {lntFddiPortEntry 1 }

lntFddiPortId OBJECT-TYPE
	SYNTAX INTEGER (1..255)
	ACCESS read-only
	STATUS mandatory
	DESCRIPTION
	"Id of the port." 
	::= { lntFddiPortEntry 2 }

lntFddiPortMACCurrentPath OBJECT-TYPE
	SYNTAX INTEGER {
		primary(1),     
		secondary(2)    
	}
	ACCESS read-write
	STATUS mandatory
	DESCRIPTION
	"Indicates the association of the MAC with the link path." 
	::= {lntFddiPortEntry 3}

lntFddiPortOpticalSwitchExist OBJECT-TYPE
	SYNTAX INTEGER {
		exist(1),       
		not-exist(2)    
	}
	ACCESS read-only
	STATUS mandatory
	DESCRIPTION
	"This attribute describes the presence of the optical switch 
	   and for existing optical switches describes the possibility 
	   of the auto-reconfiguration of path resources in the case 
	   of power fault."
	::= { lntFddiPortEntry 4}

lntFddiPortRingConfiguration OBJECT-TYPE
	SYNTAX INTEGER {
		thru(1),        
		wrap-a(2),      
		wrap-b(3),      
		wrap-s(4),      
		isolate(5),
		dualHomingA(6),
		dualHomingB(7)      
	}
	ACCESS read-only
	STATUS mandatory
	DESCRIPTION
	"Attribute which summarizes the status of the fddi link. It is related 
	  to the light detection in the physical fiber."
	::= { lntFddiPortEntry 5}

lntFddiPortLineStatusA OBJECT-TYPE
	SYNTAX INTEGER {
		als(1), -- active line state
		ils(2), -- idle line state
		mls(3), -- master line state
		hls(4), -- halt line state
		qls(5), -- quiet line state
		nls(6), -- noise line state
		sils(7) -- super idle line state
	}
	ACCESS read-only
	STATUS mandatory
	DESCRIPTION
	"Attribute that reflects the status of fddi line, interface a."
	::= {lntFddiPortEntry 6}

lntFddiPortLineStatusB OBJECT-TYPE
	SYNTAX INTEGER {
		als(1), -- active line state
		ils(2), -- idle line state
		mls(3), -- master line state
		hls(4), -- halt line state
		qls(5), -- quiet line state
		nls(6), -- noise line state
		sils(7) -- super idle line state
	}
	ACCESS read-only
	STATUS mandatory
	DESCRIPTION
	"Attribute that reflects the status of fddi line, interface b."
	::= { lntFddiPortEntry 7}

lntFddiPortRxTotalPackets OBJECT-TYPE
	SYNTAX Counter
	ACCESS read-only
	STATUS mandatory
	DESCRIPTION
	"Number of total packets, including errors, received"
	::= { lntFddiPortEntry  8}

lntFddiPortRxTotalOctets OBJECT-TYPE
	SYNTAX Counter
	ACCESS read-only
	STATUS mandatory
	DESCRIPTION
	"Number of total octets, including errors, received"
	::= { lntFddiPortEntry  9}


lntFddiPortTxTotalPackets OBJECT-TYPE
	SYNTAX Counter
	ACCESS read-only
	STATUS mandatory
	DESCRIPTION
	"Number of total packets, including errors, transmitted"
	::= { lntFddiPortEntry 10}

lntFddiPortTxTotalOctets OBJECT-TYPE
	SYNTAX Counter
	ACCESS read-only
	STATUS mandatory
	DESCRIPTION
	"Number of total octets, including errors, transmitted"
	::= { lntFddiPortEntry 11}

lntFddiPortIPXtoFDDIMatching OBJECT-TYPE
	SYNTAX  INTEGER {
		llc(1),
		snap(2),
		tunneled(3),
		fddi-raw(4),
		notSupported(255)
		}     
	ACCESS  read-write
	STATUS  mandatory
	DESCRIPTION
	" Conversion matching from IPX to FDDI in Novell environment"	
::= { lntFddiPortEntry 12}

lntFddiPortFDDItoIPXMatching OBJECT-TYPE
	SYNTAX INTEGER {
		llc(1),
		snap(2),
		eth-2(3),
		eth-raw(4),
		notSupported(255)
	}
	ACCESS read-write
	STATUS mandatory
	DESCRIPTION
	"Conversion matching from FDDI to IPX in Novell environment"
	::= { lntFddiPortEntry 13}

END
