-- MIB created 5/06/99 21:05:41, by
--   SMIC (the next generation) version 1.6.29, November 22, 1994.

SNA-LLC-MIB DEFINITIONS ::= BEGIN

-- From file: "llc.mi2"
-- Compile options "W G A T M"

IMPORTS
    experimental, Counter32, Integer32, TimeTicks
            FROM SNMPv2-SMI
    OBJECT-TYPE
            FROM RFC-1212
    TRAP-TYPE
            FROM RFC-1215
    DisplayString, RowStatus
            FROM SNMPv2-TC-v1
    ifIndex
            FROM RFC1213-MIB;

snaDLCexp OBJECT IDENTIFIER ::= { experimental 51 }
-- MODULE-IDENTITY
--  LastUpdated
--    9410200000Z
--  OrgName
--    IETF SNA DLC MIB Working Group
--  ContactInfo
--    
--           Shannon D. Nix
--           Metaplex, Inc.
--           7412 Wingfoot Dr.
--           Raleigh, NC  27615
--           snix@metaplex.com
--    
--           Wayne Clark (editor)
--           cisco Systems, Inc.
--           3100 Smoketree Ct.
--           Suite 1000
--           Raleigh, NC 27604
--           wclark@cisco.com
--  Descr
--    This is the MIB module for objects used to
--    manage LLC devices.

llc             OBJECT IDENTIFIER ::= { snaDLCexp 1 }
llcPortGroup    OBJECT IDENTIFIER ::= { llc 1 }
llcSapGroup     OBJECT IDENTIFIER ::= { llc 2 }
llcCcGroup      OBJECT IDENTIFIER ::= { llc 3 }
llcTraps        OBJECT IDENTIFIER ::= { llc 4 }
llcConformance  OBJECT IDENTIFIER ::= { llc 5 }
llcCompliances  OBJECT IDENTIFIER ::= { llcConformance 1 }
llcGroups       OBJECT IDENTIFIER ::= { llcConformance 2 }
llcCoreGroups   OBJECT IDENTIFIER ::= { llcGroups 1 }

llcPortAdminTable OBJECT-TYPE
    SYNTAX SEQUENCE OF LlcPortAdminEntry
    ACCESS not-accessible
    STATUS mandatory
    DESCRIPTION
        "This table contains objects that can be
        changed to manage an LLC port.    Changing one
        of these parameters may take effect in the
        operating port immediately or may wait until
        the interface is restarted depending on the
        details of the implementation.
        
        Most of the objects in this read-write table
        have corresponding read-only objects in the
        llcPortOperTable that return the current
        operating value.
        
        The operating values may be different from
        these configured values if  a configured
        parameter was changed after the interface was
        started."
    ::= { llcPortGroup 1 }

llcPortAdminEntry OBJECT-TYPE
    SYNTAX LlcPortAdminEntry
    ACCESS not-accessible
    STATUS mandatory
    DESCRIPTION
        "A list of configured values for an LLC port."
    INDEX { ifIndex }
    ::= { llcPortAdminTable 1 }

LlcPortAdminEntry ::= SEQUENCE {
    llcPortAdminName DisplayString,
    llcPortAdminState INTEGER,
    llcPortAdminMaxIPDUOctetsSend Integer32,
    llcPortAdminMaxIPDUOctetsRcv Integer32,
    llcPortAdminMaxUnackedIPDUsSend INTEGER,
    llcPortAdminMaxUnackedIPDUsRcv INTEGER,
    llcPortAdminMaxRetransmits INTEGER,
    llcPortAdminAckTimer TimeTicks,
    llcPortAdminPbitTimer TimeTicks,
    llcPortAdminRejTimer TimeTicks,
    llcPortAdminBusyTimer TimeTicks,
    llcPortAdminInactTimer TimeTicks,
    llcPortAdminDelayAckCount INTEGER,
    llcPortAdminDelayAckTimer TimeTicks,
    llcPortAdminSimRim INTEGER
    }

llcPortAdminName OBJECT-TYPE
    SYNTAX DisplayString(SIZE(1..10))
--    Rsyntax OCTET STRING(SIZE(1..10))
    ACCESS read-write
    STATUS mandatory
    DESCRIPTION
        "An octet string that defines the physical port
        to which this interface is assigned.  It has
        implementation-specific significance. Its value
        shall be unique within the administered
        system.  It must contain only ASCII printable
        characters.  Should an implementation choose to
        accept a write operation  for this object, it
        causes the logical port definition associated
        with the table instance to be moved to  a
        different physical port.  A write operation
        shall not take effect until the port is cycled
        inactive."
    ::= { llcPortAdminEntry 1 }

llcPortAdminState OBJECT-TYPE
    SYNTAX INTEGER {
        disabled(1),
        enabled(2)
        }
    ACCESS read-write
    STATUS mandatory
    DESCRIPTION
        "This parameter controls the desired state of
        the LLC protocol for this interface."
    DEFVAL { enabled }
    ::= { llcPortAdminEntry 2 }

llcPortAdminMaxIPDUOctetsSend OBJECT-TYPE
    SYNTAX Integer32
    ACCESS read-write
    STATUS mandatory
    DESCRIPTION
        "This object denotes the default maximum I PDU
        size, in octets, that LLCs on this port may
        send to their remote LLC partners. This count
        is referred to as 'N1' in the IEEE 802.2
        specification [??].
        
        This port default value may be overridden by a
        non-zero SAP default value in the
        llcSapAdminMaxIPDUOctetsSend  object or by a
        non-zero value in the
        llcCcAdminMaxIPDUOctetsSend object.
        
        At connection setup, the remote LLC may send,
        using an XID frame, the maximum I PDU size
        which it is prepared to receive. If so, an
        implementation may choose to override the
        administered maximum PDU size with the
        dynamically learned value and should reflect
        this in the llcCcOperMaxIPDUOctetsSend object
        for the connection component.
        
        The I PDU size includes all octets in a frame,
        excluding framing characters, the MAC header
        and link link header."
    ::= { llcPortAdminEntry 3 }

llcPortAdminMaxIPDUOctetsRcv OBJECT-TYPE
    SYNTAX Integer32
    ACCESS read-write
    STATUS mandatory
    DESCRIPTION
        "This object denotes the default maximum I PDU size,
        in octets, that LLCs on this port can expect to receive
        from their remote LLC partners. This count is referred
        to as 'N1' in the IEEE 802.2 specification [??]
        
        This port default value may be overridden by a
        non-zero SAP default value in the
        llcSapAdminMaxIPDUOctetsRcv object or by a non-zero
        value in the llcCcAdminMaxIPDUOctetsRcvd object.
        
        At connection setup, an implementation may choose to
        send this value to the remote LLC, using an XID
        frame.
        
        The I PDU size includes all octets in a frame with the
        exception of the framing characters, the MAC header
        and the link header."
    ::= { llcPortAdminEntry 4 }

llcPortAdminMaxUnackedIPDUsSend OBJECT-TYPE
    SYNTAX INTEGER(1..127)
    ACCESS read-write
    STATUS mandatory
    DESCRIPTION
        "This object denotes the default maximum
        consequetive unacknowledged I PDU frames that
        LLCs on this port may send to their remote LLC
        partners. This count is referred to as 'k' in
        the IEEE 802.2 specification [??].
        
        This port default value may be overridden by a
        non-zero SAP default value in the
        llcSapAdminMaxUnackedIPDUsSend  object or by a
        non-zero value in the
        llcCcAdminMaxUnackedIPDUsSend object.
        
        At connection setup, the remote LLC may send,
        using an XID frame, the maximum number of
        unacknowledged I PDUs which it is prepared to
        receive. If so, an implementation may choose to
        override the administered maximum number of
        unacknowledged PDUs with the dynamicly learned
        value and should reflect this in the
        llcCcOperMaxUnackedIPDUsSend object for the
        connection component."
    DEFVAL { 1 }
    ::= { llcPortAdminEntry 5 }

llcPortAdminMaxUnackedIPDUsRcv OBJECT-TYPE
    SYNTAX INTEGER(1..127)
    ACCESS read-write
    STATUS mandatory
    DESCRIPTION
        "This object denotes the default maximum number
        of unacknowledged I PDUs that LLCs on this port
        can expect to receive from their remote LLC
        partners. This count is referred to as 'k' in
        the IEEE 802.2 specification [??].
        
        This port default value may be overridden by a
        non-zero SAP default value in the
        llcSapAdminMaxUnackedIPDUsRcv object or by a
        non-zero value in the
        llcCcAdminMaxUnackedIPDUsRcvd object.
        
        At connection setup, an implementation may
        choose to send this value to the remote LLC,
        using an XID frame."
    DEFVAL { 1 }
    ::= { llcPortAdminEntry 6 }

llcPortAdminMaxRetransmits OBJECT-TYPE
    SYNTAX INTEGER
    ACCESS read-write
    STATUS mandatory
    DESCRIPTION
        "This object denotes the default value for the
        maximum number of times which LLCs on this port
        shall retry a PDU following the expiration of
        the acknowledgement timer, the P-bit timer or
        the reject timer. When these retries are
        exhausted, the link shall be declared inactive.
        This count is referred to as 'N2' in the IEEE
        802.2 specification [??].
        
        This port default value may be overridden by a
        non-zero SAP default value in the
        llcSapAdminMaxretransmits object or by a
        non-zero value in the llcCcAdminMaxRetransmits
        object."
    DEFVAL { 2 }
    ::= { llcPortAdminEntry 7 }

llcPortAdminAckTimer OBJECT-TYPE
    SYNTAX TimeTicks
    ACCESS read-write
    STATUS mandatory
    DESCRIPTION
        "This object denotes the default value for the
        time interval during which the LLCs on this port
        shall expect to receive either:
        
        1) an acknowledgement to one or more outstanding
        I PDUs.  or 2) a response PDU to an unnumbered
        command PDU.
        
        The expiration of this timer shall cause the
        frame unacknowledged frames to be retransmitted
        (up to N2 times).
        
        alue in the
        llcSapAdminAckTimer object or by a non-zero
        value in the llcCcAdminAckTimer object."
    DEFVAL { 1 }
    ::= { llcPortAdminEntry 8 }

llcPortAdminPbitTimer OBJECT-TYPE
    SYNTAX TimeTicks
    ACCESS read-write
    STATUS mandatory
    DESCRIPTION
        "This object denotes the default value for the
        time interval during which the LLCs on this
        port shall expect to receive a PDU with the F
        bit set to '1' in response to a Type 2 command
        with the P bit set to '1'.
        
        The expiration of this timer shall cause the
        command with the poll bit to be retransmitted
        (up to N2 times).
        
        This port default value may be overridden by a
        non-zero SAP default value in the
        llcSapAdminPbitTimer object or by a non-zero
        value in the llcCcAdminPbitTimer object."
    DEFVAL { 1 }
    ::= { llcPortAdminEntry 9 }

llcPortAdminRejTimer OBJECT-TYPE
    SYNTAX TimeTicks
    ACCESS read-write
    STATUS mandatory
    DESCRIPTION
        "This object denotes the default value for the
        time interval during which the LLCs on this
        port shall expect to receive a reply to a REJ
        PDU.
        
        The expiration of this timer shall cause the
        REJ PDU to be retransmitted (up to N2 times).
        
        This port default value may be overridden by a
        non-zero SAP default value in the
        llcSapAdminRejTimer object or by a non-zero
        value in the llcCcAdminRejTimer object."
    DEFVAL { 1 }
    ::= { llcPortAdminEntry 10 }

llcPortAdminBusyTimer OBJECT-TYPE
    SYNTAX TimeTicks
    ACCESS read-write
    STATUS mandatory
    DESCRIPTION
        "This object denotes the default value for the
        time interval during which the LLCs on this
        port shall expect to receive an indication that
        a busy condition at the remote LLC has
        cleared.
        
        The expiration of this timer shall cause the
        link to be declared inactive.
        
        This port default value may be overridden by a
        non-zero SAP default value in the
        llcSapAdminBusyTimer object or by a non-zero
        value in the llcCcAdminBusyTimer object."
    DEFVAL { 1 }
    ::= { llcPortAdminEntry 11 }

llcPortAdminInactTimer OBJECT-TYPE
    SYNTAX TimeTicks
    ACCESS read-write
    STATUS mandatory
    DESCRIPTION
        "This object denotes the default value for the
        time interval during which the LLCs on this
        port shall expect to receive any PDU from the
        remote LLC.  This function is not described in
        the IEEE 802.2 specification [??] but is widely
        implemented.
        
        The expiration of this timer shall cause the
        local LLC to send a PDU to the remote LLC with
        the P bit set to '1'.
        
        This port default value may be overridden by a
        non-zero SAP default value in the
        llcSapAdminInactTimer object or by a non-zero
        value in the llcCcAdminInactTimer object.
        
        Any value for this object less than or equal to
        the acknowledgement timer shall mean that the
        timer is not used."
    DEFVAL { 1 }
    ::= { llcPortAdminEntry 12 }

llcPortAdminDelayAckCount OBJECT-TYPE
    SYNTAX INTEGER
    ACCESS read-write
    STATUS mandatory
    DESCRIPTION
        "This object denotes the default value for the
        maximum number of consequetive I PDUs which the
        LLCs on this port shall receive during the
        interval defined by llcCcOperDelayTimertime
        without sending an immediate acknowledgement.
        This must be less than or equal to the value of
        llcCcOperMaxUnackIPDURcv. This function is not
        described in the IEEE 802.2 specification [??]
        but is widely implemented.
        
        This port default value may be overridden by a
        non-zero SAP default value in the
        llcSapAdminDelayAckCount object or by a
        non-zero value in the llcCcAdminDelayCount
        object.
        
        A value of one indicates that acknowledgments
        will be sent immediately and that the value of
        llcPortAdminDelayAckTimer shall be ignored."
    DEFVAL { 1 }
    ::= { llcPortAdminEntry 13 }

llcPortAdminDelayAckTimer OBJECT-TYPE
    SYNTAX TimeTicks
    ACCESS read-write
    STATUS mandatory
    DESCRIPTION
        "This object denotes the default value for the
        time interval during which the LLCs on this
        port shall delay acknowledgment of one or more
        I PDUs (up to the value of
        llcCcOperDelayAckCount). This function is not
        described in the IEEE 802.2 specification [??]
        but is widely implemented.
        
        The expiration of this timer shall cause the
        local LLC to acknowledge all unacknowledged I
        PDUs.
        
        This object is associated with the
        llcSapAdminDelayAckCount object and is only
        defined if that object has a value greater than
        one."
    ::= { llcPortAdminEntry 14 }

llcPortAdminSimRim OBJECT-TYPE
    SYNTAX INTEGER {
        no(1),
        yes(2)
        }
    ACCESS read-write
    STATUS mandatory
    DESCRIPTION
        "This object controls the support for
        transmission and receipt of SIM and RIM control
        frames for this port."
    DEFVAL { no }
    ::= { llcPortAdminEntry 15 }

llcPortOperTable OBJECT-TYPE
    SYNTAX SEQUENCE OF LlcPortOperEntry
    ACCESS not-accessible
    STATUS mandatory
    DESCRIPTION
        "This table contains current LLC port
        parameters.  Many of these objects have
        corresponding objects inthe llcPortAdminTable."
    ::= { llcPortGroup 2 }

llcPortOperEntry OBJECT-TYPE
    SYNTAX LlcPortOperEntry
    ACCESS not-accessible
    STATUS mandatory
    DESCRIPTION
        "Currently set parameters for a specific LLC port."
    INDEX { ifIndex }
    ::= { llcPortOperTable 1 }

LlcPortOperEntry ::= SEQUENCE {
    llcPortOperName DisplayString,
    llcPortOperISTATUS INTEGER,
    llcPortOperLastModifyTime TimeTicks,
    llcPortOperLastFailTime TimeTicks,
    llcPortOperLastFailCause INTEGER
    }

llcPortOperName OBJECT-TYPE
    SYNTAX DisplayString(SIZE(1..8))
--    Rsyntax OCTET STRING(SIZE(1..8))
    ACCESS read-only
    STATUS mandatory
    DESCRIPTION
        "An octet string that describes the physical
        port to which this interface is currently
        attached.  It has  implementation-specific
        significance."
    ::= { llcPortOperEntry 1 }

llcPortOperISTATUS OBJECT-TYPE
    SYNTAX INTEGER {
        inactive(1),
        active(2)
        }
    ACCESS read-only
    STATUS mandatory
    DESCRIPTION
        "This parameter describes the initial value of
        the administrative status, ifAdminStatus, of
        this LLC port at last port start-up."
    ::= { llcPortOperEntry 2 }

llcPortOperLastModifyTime OBJECT-TYPE
    SYNTAX TimeTicks
    ACCESS read-only
    STATUS mandatory
    DESCRIPTION
        "This object describes the value of sysUpTime
        when this port definition was last modified.
        If the port has not been modified, then this
        value shall be zero."
    ::= { llcPortOperEntry 3 }

llcPortOperLastFailTime OBJECT-TYPE
    SYNTAX TimeTicks
    ACCESS read-only
    STATUS mandatory
    DESCRIPTION
        "This object describes the value of sysUpTime
        when this LLC port last failed.  If the port
        has not failed, then this value shall be zero."
    ::= { llcPortOperEntry 4 }

llcPortOperLastFailCause OBJECT-TYPE
    SYNTAX INTEGER {
        undefined(1),
        physical(2)
        }
    ACCESS read-only
    STATUS mandatory
    DESCRIPTION
        "This enumerated object describes the cause of
        the last failure of this LLC port.  If the port
        has not failed, then this object has a value of
        undefined(1)."
    DEFVAL { undefined }
    ::= { llcPortOperEntry 5 }

llcPortStatsTable OBJECT-TYPE
    SYNTAX SEQUENCE OF LlcPortStatsEntry
    ACCESS not-accessible
    STATUS mandatory
    DESCRIPTION
        "Each entry in this table contains statistics
        for a specific LLC port."
    ::= { llcPortGroup 3 }

llcPortStatsEntry OBJECT-TYPE
    SYNTAX LlcPortStatsEntry
    ACCESS not-accessible
    STATUS mandatory
    DESCRIPTION
        "A list of statistics for an LLC port."
    INDEX { ifIndex }
    ::= { llcPortStatsTable 1 }

LlcPortStatsEntry ::= SEQUENCE {
    llcPortStatsPhysicalFailures Counter32,
    llcPortStatsPollsIn Counter32,
    llcPortStatsPollsOut Counter32,
    llcPortStatsPollRspsIn Counter32,
    llcPortStatsPollRspsOut Counter32,
    llcPortStatsLocalBusies Counter32,
    llcPortStatsRemoteBusies Counter32,
    llcPortStatsIFramesIn Counter32,
    llcPortStatsIFramesOut Counter32,
    llcPortStatsOctetsIn Counter32,
    llcPortStatsOctetsOut Counter32,
    llcPortStatsProtocolErrs Counter32,
    llcPortStatsActivityTOs Counter32,
    llcPortStatsRetriesExps Counter32,
    llcPortStatsRetransmitsIn Counter32,
    llcPortStatsRetransmitsOut Counter32
    }

llcPortStatsPhysicalFailures OBJECT-TYPE
    SYNTAX Counter32
    ACCESS read-only
    STATUS mandatory
    DESCRIPTION
        "This object reflects the total number of times
        this port has failed due to its physical media
        since port startup.  At port startup time, this
        object must be initialized to zero."
    ::= { llcPortStatsEntry 1 }

llcPortStatsPollsIn OBJECT-TYPE
    SYNTAX Counter32
    ACCESS read-only
    STATUS mandatory
    DESCRIPTION
        "This object reflects the total number of polls
        received by this port since the port was
        created."
    ::= { llcPortStatsEntry 2 }

llcPortStatsPollsOut OBJECT-TYPE
    SYNTAX Counter32
    ACCESS read-only
    STATUS mandatory
    DESCRIPTION
        "This object reflects the total number of polls
        sent by this port since the port was created."
    ::= { llcPortStatsEntry 3 }

llcPortStatsPollRspsIn OBJECT-TYPE
    SYNTAX Counter32
    ACCESS read-only
    STATUS mandatory
    DESCRIPTION
        "This object reflects the total number of poll
        responses received by this port since the port
        was created."
    ::= { llcPortStatsEntry 4 }

llcPortStatsPollRspsOut OBJECT-TYPE
    SYNTAX Counter32
    ACCESS read-only
    STATUS mandatory
    DESCRIPTION
        "This object reflects the total number of poll
        responses sent by this port since the port was
        created."
    ::= { llcPortStatsEntry 5 }

llcPortStatsLocalBusies OBJECT-TYPE
    SYNTAX Counter32
    ACCESS read-only
    STATUS mandatory
    DESCRIPTION
        "This object reflects the total number of
        times that the local link stations on this
        port have entered a busy state (RNR).  This
        object is initialized to zero when the port is
        created."
    ::= { llcPortStatsEntry 6 }

llcPortStatsRemoteBusies OBJECT-TYPE
    SYNTAX Counter32
    ACCESS read-only
    STATUS mandatory
    DESCRIPTION
        "This object reflects the total number of
        times that the adjacent (i.e. remote) link
        stations on this port have entered a busy
        state (RNR).  This object is initialized to
        zero when the port is created."
    ::= { llcPortStatsEntry 7 }

llcPortStatsIFramesIn OBJECT-TYPE
    SYNTAX Counter32
    ACCESS read-only
    STATUS mandatory
    DESCRIPTION
        "This object reflects the total number of
        I-Frames that have been received by link
        stations on this port.  This object is
        initialized to zero when the port is created."
    ::= { llcPortStatsEntry 8 }

llcPortStatsIFramesOut OBJECT-TYPE
    SYNTAX Counter32
    ACCESS read-only
    STATUS mandatory
    DESCRIPTION
        "This object reflects the total number of
        I-Frames that have been transmitted by link
        stations on this port.  This object is
        initialized to zero when the port is created."
    ::= { llcPortStatsEntry 9 }

llcPortStatsOctetsIn OBJECT-TYPE
    SYNTAX Counter32
    ACCESS read-only
    STATUS mandatory
    DESCRIPTION
        "This object reflects the total octets
        received from adjacent link stations on this
        port.  This object covers the address,
        control, and information field of I-Frames
        only.  This object is initialized to zero when
        the port is created."
    ::= { llcPortStatsEntry 10 }

llcPortStatsOctetsOut OBJECT-TYPE
    SYNTAX Counter32
    ACCESS read-only
    STATUS mandatory
    DESCRIPTION
        "This object reflects the total octets
        transmitted to adjacent link stations on this
        port.  This object covers the address,
        control, and information field of I-Frames
        only.  This object is initialized to zero when
        the port is created."
    ::= { llcPortStatsEntry 11 }

llcPortStatsProtocolErrs OBJECT-TYPE
    SYNTAX Counter32
    ACCESS read-only
    STATUS mandatory
    DESCRIPTION
        "This object reflects the total number of
        times that the link stations on this port have
        deactivated the link as a result of having
        received a protocol violation from the
        adjacent link station.  This object is
        initialized to zero when the port is created."
    ::= { llcPortStatsEntry 12 }

llcPortStatsActivityTOs OBJECT-TYPE
    SYNTAX Counter32
    ACCESS read-only
    STATUS mandatory
    DESCRIPTION
        "This object reflects the total number of
        times that the link stations on this port
        have deactivated the link as a result of no
        activity on the link.  This object is
        initialized to zero when the port is created."
    ::= { llcPortStatsEntry 13 }

llcPortStatsRetriesExps OBJECT-TYPE
    SYNTAX Counter32
    ACCESS read-only
    STATUS mandatory
    DESCRIPTION
        "This object reflects the total number of
        times that the link stations on this port
        have deactivated the link as a result of a
        retry sequence being exhausted.  This object
        is initialized to zero when the port is
        created."
    ::= { llcPortStatsEntry 14 }

llcPortStatsRetransmitsIn OBJECT-TYPE
    SYNTAX Counter32
    ACCESS read-only
    STATUS mandatory
    DESCRIPTION
        "This object reflects the total number of
        I-Frames retransmitted by remote link stations
        for all link stations on this port.  This
        object is initialized to zero when the port is
        created."
    ::= { llcPortStatsEntry 15 }

llcPortStatsRetransmitsOut OBJECT-TYPE
    SYNTAX Counter32
    ACCESS read-only
    STATUS mandatory
    DESCRIPTION
        "This object reflects the total number of
        I-Frames retransmitted by all local link
        stations on this port.  This object is
        initialized to zero when the port is created."
    ::= { llcPortStatsEntry 16 }

llcSapAdminTable OBJECT-TYPE
    SYNTAX SEQUENCE OF LlcSapAdminEntry
    ACCESS not-accessible
    STATUS mandatory
    DESCRIPTION
        "This table contains objects that can be
        changed to manage a local SAP.    Changing one
        of these parameters may take effect in the
        operating SAP immediately or may wait until the
        interface is restarted depending on the details
        of the implementation.
        
        Most of the objects in this read-write table
        have corresponding read-only objects in the
        llcSapOperTable that return the current
        operating value.
        
        The operating values may be different from
        these configured values if  a configured
        parameter was changed after the interface was
        started."
    ::= { llcSapGroup 1 }

llcSapAdminEntry OBJECT-TYPE
    SYNTAX LlcSapAdminEntry
    ACCESS not-accessible
    STATUS mandatory
    DESCRIPTION
        "A list of configured values for a local SAP."
    INDEX { ifIndex, llcSapNumber }
    ::= { llcSapAdminTable 1 }

LlcSapAdminEntry ::= SEQUENCE {
    llcSapNumber INTEGER,
    llcSapAdminState INTEGER,
    llcSapAdminMaxIPDUOctetsSend Integer32,
    llcSapAdminMaxIPDUOctetsRcv Integer32,
    llcSapAdminMaxUnackedIPDUsSend INTEGER,
    llcSapAdminMaxUnackedIPDUsRcv INTEGER,
    llcSapAdminMaxRetransmits INTEGER,
    llcSapAdminAckTimer TimeTicks,
    llcSapAdminPbitTimer TimeTicks,
    llcSapAdminRejTimer TimeTicks,
    llcSapAdminBusyTimer TimeTicks,
    llcSapAdminInactTimer TimeTicks,
    llcSapAdminDelayAckCount INTEGER,
    llcSapAdminDelayAckTimer TimeTicks
    }

llcSapNumber OBJECT-TYPE
    SYNTAX INTEGER(1..255)
    ACCESS read-write
    STATUS mandatory
    DESCRIPTION
        "The address of this local SAP."
    ::= { llcSapAdminEntry 1 }

llcSapAdminState OBJECT-TYPE
    SYNTAX INTEGER {
        disabled(1),
        enabled(2)
        }
    ACCESS read-write
    STATUS mandatory
    DESCRIPTION
        "This parameter controls the desired state of
        this local SAP."
    DEFVAL { enabled }
    ::= { llcSapAdminEntry 2 }

llcSapAdminMaxIPDUOctetsSend OBJECT-TYPE
    SYNTAX Integer32
    ACCESS read-write
    STATUS mandatory
    DESCRIPTION
        "This object denotes the default maximum I PDU
        size, in octets, that LLCs on this SAP may send
        to their remote connection component partners.
        This count is referred to as 'N1' in the IEEE
        802.2 specification [??].
        
        A zero value for this object indicates that the
        port default, llcPortAdminMaxIPDUOctetsSend,
        shall be used as the SAP default.  This SAP
        default value may be overridden by a non-zero
        value in the llcCcAdminMaxIPDUOctetsSend
        object.
        
        At connection setup, the remote LLC may send,
        using an XID frame, the maximum I PDU size
        which it is prepared to receive. If so, an
        implementation may choose to override the
        administered maximum PDU size with the
        dynamically learned value and should reflect
        this in the llcCcOperMaxIPDUOctetsSend object
        for the connection component.
        
        The I PDU size includes all octets in a frame,
        excluding framing characters, the MAC header
        and link link header."
    DEFVAL { 0 }
    ::= { llcSapAdminEntry 3 }

llcSapAdminMaxIPDUOctetsRcv OBJECT-TYPE
    SYNTAX Integer32
    ACCESS read-write
    STATUS mandatory
    DESCRIPTION
        "This object denotes the default maximum I PDU
        size, in octets, that LLCs on this SAP can
        expect to receive from their remote LLC
        partners. This count is referred to as 'N1' in
        the IEEE 802.2 specification [??]
        
        A zero value for this object indicates that the
        port default, llcPortAdminMaxIPDUOctetsRcv,
        shall be used as the SAP default.  This SAP
        default value may be overridden by a non-zero
        value in the llcCcAdminMaxIPDUOctetsRcv
        object.
        
        At connection setup, an implementation may
        choose to send this value to the remote LLC,
        using an XID frame.
        
        The I PDU size includes all octets in a frame
        with the exception of the framing characters,
        the MAC header and the link header."
    DEFVAL { 0 }
    ::= { llcSapAdminEntry 4 }

llcSapAdminMaxUnackedIPDUsSend OBJECT-TYPE
    SYNTAX INTEGER(1..127)
    ACCESS read-write
    STATUS mandatory
    DESCRIPTION
        "This object denotes the default maximum
        consequetive unacknowledged I PDU frames that
        LLCs on this SAP may send to their remote LLC
        partners. This count is referred to as 'k' in
        the IEEE 802.2 specification [??].
        
        A zero value for this object indicates that the
        port default, llcPortAdminMaxUnackedIPDUsSend,
        shall be used as the SAP default.  This SAP
        default value may be overridden by a non-zero
        value in the llcCcAdminMaxUnackedIPDUsSend
        object.
        
        At connection setup, the remote LLC may send,
        using an XID frame, the maximum number of
        unacknowledged I PDUs which it is prepared to
        receive. If so, an implementation may choose to
        override the administered maximum number of
        unacknowledged PDUs with the dynamicly learned
        value and should reflect this in the
        llcCcOperMaxUnackedIPDUsSend object for the
        connection component."
    ::= { llcSapAdminEntry 5 }

llcSapAdminMaxUnackedIPDUsRcv OBJECT-TYPE
    SYNTAX INTEGER(1..127)
    ACCESS read-write
    STATUS mandatory
    DESCRIPTION
        "This object denotes the default maximum number
        of unacknowledged I PDUs that LLCs on this SAP
        can expect to receive from their remote LLC
        partners. This count is referred to as 'k' in
        the IEEE 802.2 specification [??].
        
        A zero value for this object indicates that the
        port default, llcPortAdminMaxUnackedIPDUsRcv,
        shall be used as the SAP default.  This SAP
        default value may be overridden by a non-zero
        value in the llcCcAdminMaxUnackedIPDUsRcv
        object.
        
        At connection setup, an implementation may
        choose to send this value to the remote LLC,
        using an XID frame."
    ::= { llcSapAdminEntry 6 }

llcSapAdminMaxRetransmits OBJECT-TYPE
    SYNTAX INTEGER
    ACCESS read-write
    STATUS mandatory
    DESCRIPTION
        "This object denotes the default value for the
        maximum number of times that LLCs on this SAP
        shall retry PDUs following the expiration of
        the acknowledgement timer, the P-bit timer or
        the reject timer. When these retries are
        exhausted, thelink shall be declared inactive.
        This count is referred to as 'N2' in the IEEE
        802.2 specification [??].
        
        A zero value for this object indicates that the
        port default, llcPortAdminMaxRetransmits, shall
        be used as the SAP default.  This SAP default
        value may be overridden by a non-zero value in
        the llcCcAdminMaxRetransmits."
    DEFVAL { 0 }
    ::= { llcSapAdminEntry 7 }

llcSapAdminAckTimer OBJECT-TYPE
    SYNTAX TimeTicks
    ACCESS read-write
    STATUS mandatory
    DESCRIPTION
        "This object denotes the default value for the
        time interval during which the LLCs on this SAP
        shall expect to receive either:
        
        1) an acknowledgement to one or more
        outstanding I PDUs.  or 2) a response PDU to an
        unnumbered command PDU.
        
        The expiration of this timer shall cause the
        frame unacknowledged frames to be retransmitted
        (up to N2 times).
        
        A zero value for this object indicates that the
        port default, llcPortAdminAckTimer, shall be
        used as the SAP default.  This SAP default
        value may be overridden by a non-zero value in
        the llcCcAdminAckTimer."
    DEFVAL { 0 }
    ::= { llcSapAdminEntry 8 }

llcSapAdminPbitTimer OBJECT-TYPE
    SYNTAX TimeTicks
    ACCESS read-write
    STATUS mandatory
    DESCRIPTION
        "This object denotes the default value for the
        time interval during which the LLCs on this
        port shall expect to receive a PDU with the F
        bit set to '1' in response to a Type 2 command
        with the P bit set to '1'.
        
        The expiration of this timer shall cause the
        REJ PDU to be retransmitted (up to N2 times).
        
        A zero value for this object indicates that the
        port default, llcPortAdminPbitTimer, shall be
        used as the SAP default.  This SAP default
        value may be overridden by a non-zero value in
        the llcCcAdminPbitTimer."
    DEFVAL { 0 }
    ::= { llcSapAdminEntry 9 }

llcSapAdminRejTimer OBJECT-TYPE
    SYNTAX TimeTicks
    ACCESS read-write
    STATUS mandatory
    DESCRIPTION
        "This object denotes the default value for the
        time interval during which the LLCs on this SAP
        shall expect to receive a reply to a REJ PDU.
        
        The expiration of this timer shall cause the
        REJ PDU to be retransmitted (up to N2 times).
        
        A zero value for this object indicates that the
        port default, llcPortAdminRejTimer, shall be
        used as the SAP default.  This SAP default
        value may be overridden by a non-zero value in
        the llcCcAdminRejTimer."
    DEFVAL { 0 }
    ::= { llcSapAdminEntry 10 }

llcSapAdminBusyTimer OBJECT-TYPE
    SYNTAX TimeTicks
    ACCESS read-write
    STATUS mandatory
    DESCRIPTION
        "This object denotes the default value for the
        time interval during which the LLCs on this SAP
        shall expect to receive an indication that a
        busy condition at the remote LLC has cleared.
        
        The expiration of this timer shall cause the
        link to be declared inactive.
        
        A zero value for this object indicates that the
        port default, llcPortAdminBusyTimer, shall be
        used as the SAP default.  This SAP default
        value may be overridden by a non-zero value in
        the llcCcAdminBusyTimer."
    DEFVAL { 0 }
    ::= { llcSapAdminEntry 11 }

llcSapAdminInactTimer OBJECT-TYPE
    SYNTAX TimeTicks
    ACCESS read-write
    STATUS mandatory
    DESCRIPTION
        "This object denotes the default value for the
        time interval during which the LLCs on this SAP
        shall expect to receive any PDU from the remote
        LLC.  This function is not described in the
        IEEE 802.2 specification [??] but is widely
        implemented.
        
        The expiration of this timer shall cause the
        local LLC to send a PDU to the remote LLC with
        the P bit set to '1'.
        
        A zero value for this object indicates that the
        port default, llcPortAdminInactTimer, shall be
        used as the SAP default.  This SAP default
        value may be overridden by a non-zero value in
        the llcCcAdminInactTimer.
        
        Any value for this object less than or equal to
        the acknowledgement timer shall mean that the
        timer is not used."
    DEFVAL { 0 }
    ::= { llcSapAdminEntry 12 }

llcSapAdminDelayAckCount OBJECT-TYPE
    SYNTAX INTEGER
    ACCESS read-write
    STATUS mandatory
    DESCRIPTION
        "This object denotes the default value for the
        maximum number of consequetive I PDUs which the
        LLCs on this SAP shall receive during the
        interval defined by llcCcOperDelayTimer without
        sending an immediate acknowledgement.  This
        must be less than or equal to the value of
        llcCcOperMaxUnackIPDURcv. This function is not
        described in the IEEE 802.2 specification [??]
        but is widely implemented.
        
        A zero value for this object indicates that the
        port default, llcPortAdminDelayAck, shall be
        used as the SAP default.  This SAP default
        value may be overridden by a non-zero value in
        the llcCcAdminDelayAckCount.
        
        A value of one indicates that acknowledgments
        will be sent immediately and that the value of
        llcSapAdminDelayAckTimer shall be ignored."
    DEFVAL { 0 }
    ::= { llcSapAdminEntry 13 }

llcSapAdminDelayAckTimer OBJECT-TYPE
    SYNTAX TimeTicks
    ACCESS read-write
    STATUS mandatory
    DESCRIPTION
        "This object denotes the default value for the
        time interval during which the LLCs on this SAP
        shall delay acknowledgment of one or more I
        PDUs (up to the value of
        llcCcOperDelayAckCount). This function is not
        described in the IEEE 802.2 specification [??]
        but is widely implemented.
        
        The expiration of this timer shall cause the
        local LLC to acknowledge all unacknowledged I
        PDUs.
        
        This object is associated with the
        llcSapAdminDelayAckCount object and is only
        defined if that object has a value greater than
        one."
    DEFVAL { 0 }
    ::= { llcSapAdminEntry 14 }

llcSapOperTable OBJECT-TYPE
    SYNTAX SEQUENCE OF LlcSapOperEntry
    ACCESS not-accessible
    STATUS mandatory
    DESCRIPTION
        "This table contains objects that reflect the
        current operational parameters of a local SAP.
        
        Many of these objects in this table have
        corresponding objects in the llcSapAdminTable."
    ::= { llcSapGroup 2 }

llcSapOperEntry OBJECT-TYPE
    SYNTAX LlcSapOperEntry
    ACCESS not-accessible
    STATUS mandatory
    DESCRIPTION
        "A list of configured values for a local SAP."
    INDEX { ifIndex, llcSapNumber }
    ::= { llcSapOperTable 1 }

LlcSapOperEntry ::= SEQUENCE {
    llcSapOperStatus INTEGER
    }

llcSapOperStatus OBJECT-TYPE
    SYNTAX INTEGER {
        inactive(1),
        active(2)
        }
    ACCESS read-only
    STATUS mandatory
    DESCRIPTION
        "This parameter describes the actual state of
        this local SAP."
    ::= { llcSapOperEntry 1 }

llcSapStatsTable OBJECT-TYPE
    SYNTAX SEQUENCE OF LlcSapStatsEntry
    ACCESS not-accessible
    STATUS mandatory
    DESCRIPTION
        "This table contains objects that reflect the
        current operational parameters of a local SAP.
        
        Many of these objects in this table have
        corresponding objects in the llcSapAdminTable."
    ::= { llcSapGroup 3 }

llcSapStatsEntry OBJECT-TYPE
    SYNTAX LlcSapStatsEntry
    ACCESS not-accessible
    STATUS mandatory
    DESCRIPTION
        "A list of configured values for a local SAP."
    INDEX { ifIndex, llcSapNumber }
    ::= { llcSapStatsTable 1 }

LlcSapStatsEntry ::= SEQUENCE {
    llcSapStatsTESTsIn Counter32,
    llcSapStatsTESTsOut Counter32,
    llcSapStatsXIDsIn Counter32,
    llcSapStatsXIDsOut Counter32,
    llcSapStatsUIFramesIn Counter32,
    llcSapStatsUIFramesOut Counter32
    }

llcSapStatsTESTsIn OBJECT-TYPE
    SYNTAX Counter32
    ACCESS read-only
    STATUS mandatory
    DESCRIPTION
        "This object reflects the total number of TEST
        frames (both commands and responses) received on
        a local SAP."
    ::= { llcSapStatsEntry 1 }

llcSapStatsTESTsOut OBJECT-TYPE
    SYNTAX Counter32
    ACCESS read-only
    STATUS mandatory
    DESCRIPTION
        "This object reflects the total number of TEST
        frames (both commands and responses) sent on
        a local SAP."
    ::= { llcSapStatsEntry 2 }

llcSapStatsXIDsIn OBJECT-TYPE
    SYNTAX Counter32
    ACCESS read-only
    STATUS mandatory
    DESCRIPTION
        "This object reflects the total number of XID
        frames (both commands and responses) received on
        a local SAP."
    ::= { llcSapStatsEntry 3 }

llcSapStatsXIDsOut OBJECT-TYPE
    SYNTAX Counter32
    ACCESS read-only
    STATUS mandatory
    DESCRIPTION
        "This object reflects the total number of XID
        frames (both commands and responses) sent on
        a local SAP."
    ::= { llcSapStatsEntry 4 }

llcSapStatsUIFramesIn OBJECT-TYPE
    SYNTAX Counter32
    ACCESS read-only
    STATUS mandatory
    DESCRIPTION
        "This object reflects the total number of
        unnumbered information (UI) frames received on
        a local SAP."
    ::= { llcSapStatsEntry 5 }

llcSapStatsUIFramesOut OBJECT-TYPE
    SYNTAX Counter32
    ACCESS read-only
    STATUS mandatory
    DESCRIPTION
        "This object reflects the total number of
        unnumbered information (UI) frames sent on a
        local SAP."
    ::= { llcSapStatsEntry 6 }

llcCcAdminTable OBJECT-TYPE
    SYNTAX SEQUENCE OF LlcCcAdminEntry
    ACCESS not-accessible
    STATUS mandatory
    DESCRIPTION
        "This table contains objects that can be
        changed to manage an LLC link station.
        Changing one of these parameters may take
        effect in the operating link immediately or may
        wait until the link is restarted depending on
        the details of the implementation.
        
        The entries in llcCcAdminTable can be created
        either by an agent or a management station. The
        management station can create an entry in
        llcCcAdminTable by setting the appropriate
        value in llcCcAdminRowStatus.
        
        Most of the objects in this read-create table
        have corresponding read-only objects in the
        llcCcOperTable that reflect the current
        operating value.
        
        The operating values may be different from
        these configured values if changed by XID
        negotiation or if a configured parameter was
        changed after the link was started."
    ::= { llcCcGroup 1 }

llcCcAdminEntry OBJECT-TYPE
    SYNTAX LlcCcAdminEntry
    ACCESS not-accessible
    STATUS mandatory
    DESCRIPTION
        "A list of configured values for an LLC link
        station."
    INDEX { ifIndex, llcCcLSap, llcCcRSap, llcCcRMac, llcCcLMac }
    ::= { llcCcAdminTable 1 }

LlcCcAdminEntry ::= SEQUENCE {
    llcCcLSap INTEGER,
    llcCcRSap INTEGER,
    llcCcLMac OCTET STRING,
    llcCcRMac OCTET STRING,
    llcCcAdminState INTEGER,
    llcCcAdminMaxIPDUOctetsSend Integer32,
    llcCcAdminMaxIPDUOctetsRcv Integer32,
    llcCcAdminMaxUnackedIPDUsSend INTEGER,
    llcCcAdminMaxUnackedIPDUsRcv INTEGER,
    llcCcAdminMaxRetransmits INTEGER,
    llcCcAdminAckTimer TimeTicks,
    llcCcAdminPbitTimer TimeTicks,
    llcCcAdminRejTimer TimeTicks,
    llcCcAdminBusyTimer TimeTicks,
    llcCcAdminInactTimer TimeTicks,
    llcCcAdminDelayAckCount INTEGER,
    llcCcAdminDelayAckTimer TimeTicks,
    llcCcAdminRowStatus RowStatus
    }

llcCcLSap OBJECT-TYPE
    SYNTAX INTEGER(1..255)
    ACCESS read-write
    STATUS mandatory
    DESCRIPTION
        "This value is the address of the local SAP
        for this Connection Component."
    ::= { llcCcAdminEntry 1 }

llcCcRSap OBJECT-TYPE
    SYNTAX INTEGER(1..255)
    ACCESS read-write
    STATUS mandatory
    DESCRIPTION
        "This value is the address of the remote SAP
        for this Connection Component."
    ::= { llcCcAdminEntry 2 }

llcCcLMac OBJECT-TYPE
    SYNTAX OCTET STRING(SIZE(6))
    ACCESS read-write
    STATUS mandatory
    DESCRIPTION
        "This value is the local MAC address for this
        Connection Component."
    ::= { llcCcAdminEntry 3 }

llcCcRMac OBJECT-TYPE
    SYNTAX OCTET STRING(SIZE(6))
    ACCESS read-write
    STATUS mandatory
    DESCRIPTION
        "This value is the remote MAC address for this
        Connection Component."
    ::= { llcCcAdminEntry 4 }

llcCcAdminState OBJECT-TYPE
    SYNTAX INTEGER {
        disabled(1),
        enabled(2)
        }
    ACCESS read-write
    STATUS mandatory
    DESCRIPTION
        "This object controls the desired state of the
        LLC connection.  The managed system shall attempt
        to keep the operational state, llcCcOperState,
        consistent with this value."
    DEFVAL { enabled }
    ::= { llcCcAdminEntry 5 }

llcCcAdminMaxIPDUOctetsSend OBJECT-TYPE
    SYNTAX Integer32
    ACCESS read-write
    STATUS mandatory
    DESCRIPTION
        "This object denotes the maximum I PDU size, in
        octets, that this LLC SAP may send to its
        remote connection component partner. This count
        is referred to as 'N1' in the IEEE 802.2
        specification [??].
        
        This object contains an administrative value
        which will be applied the next time this
        connection is established.  A zero value for
        this object indicates that the SAP default,
        llcSapAdminMaxIPDUOctetsSend, shall be used.
        
        At connection setup, the remote LLC may send,
        using an XID frame, the maximum I PDU size
        which it is prepared to receive. If so, an
        implementation may choose to override the
        administered maximum PDU size with the
        dynamically learned value and should reflect
        this in the llcCcOperMaxIPDUOctetsSend object
        for the connection component.
        
        The I PDU size includes all octets in a frame,
        excluding framing characters, the MAC header
        and link link header."
    DEFVAL { 0 }
    ::= { llcCcAdminEntry 6 }

llcCcAdminMaxIPDUOctetsRcv OBJECT-TYPE
    SYNTAX Integer32
    ACCESS read-write
    STATUS mandatory
    DESCRIPTION
        "This object denotes the maximum I PDU size,in
        octets, that this LLC can expect to receive
        from its remote LLC partner. This count is
        referred to as 'N1' in the IEEE 802.2
        specification [??]
        
        This object contains an administrative value
        which will be applied the next time this
        connection is established.  A zero value for
        this object indicates that the SAP default,
        llcSapAdminMaxIPDUOctetsRcv, shall be used.
        
        At connection setup, an implementation may
        choose to send this value to the remote LLC,
        using an XID frame.
        
        The I PDU size includes all octets in a frame
        with the exception of the framing characters,
        the MAC header and the link header."
    DEFVAL { 0 }
    ::= { llcCcAdminEntry 7 }

llcCcAdminMaxUnackedIPDUsSend OBJECT-TYPE
    SYNTAX INTEGER(1..127)
    ACCESS read-write
    STATUS mandatory
    DESCRIPTION
        "This object denotes the maximum consequetive
        unacknowledged I PDU frames that this LLC may
        send to its remote LLC partner. This count is
        referred to as 'k' in the IEEE 802.2
        specification [??].
        
        This object contains an administrative value
        which will be applied the next time this
        connection is established.  A zero value for
        this object indicates that the SAP default,
        llcSapAdminMaxUnackedIPDUsSend, shall be used.
        
        At connection setup, the remote LLC may send,
        using an XID frame, the maximum number of
        unacknowledged I PDUs which it is prepared to
        receive. If so, an implementation may choose to
        override the administered maximum number of
        unacknowledged PDUs with the dynamicly learned
        value and should reflect this in the
        llcCcOperMaxUnackedIPDUsSend object for the
        connection component."
    ::= { llcCcAdminEntry 8 }

llcCcAdminMaxUnackedIPDUsRcv OBJECT-TYPE
    SYNTAX INTEGER(1..127)
    ACCESS read-write
    STATUS mandatory
    DESCRIPTION
        "This object denotes the maximum number of
        unacknowledged I PDUs that this LLC can expect
        to receive from its remote LLC partner. This
        count is referred to as 'k' in the IEEE 802.2
        specification [??].
        
        This object contains an administrative value
        which will be applied the next time this
        connection is established.  A zero value for
        this object indicates that the SAP default,
        llcSapAdminMaxUnackedIPDUsRcv, shall be used.
        
        At connection setup, an implementation may
        choose to send this value to the remote LLC,
        using an XID frame."
    ::= { llcCcAdminEntry 9 }

llcCcAdminMaxRetransmits OBJECT-TYPE
    SYNTAX INTEGER
    ACCESS read-write
    STATUS mandatory
    DESCRIPTION
        "This object denotes the value for the maximum
        number of times that this LLC shall retry PDUs
        following the expiration of the acknowledgement
        timer, the P-bit timer or the reject timer.
        When these retries are exhausted, the link
        shall be declared inactive.  This count is
        referred to as 'N2' in the IEEE 802.2
        specification [??].
        
        This object contains an administrative value
        which will be applied the next time this
        connection is established.  A zero value for
        this object indicates that the SAP default,
        llcSapAdminMaxRetransmits, shall be used."
    DEFVAL { 0 }
    ::= { llcCcAdminEntry 10 }

llcCcAdminAckTimer OBJECT-TYPE
    SYNTAX TimeTicks
    ACCESS read-write
    STATUS mandatory
    DESCRIPTION
        "This object denotes the value for the time
        interval during which this LLC shall expect to
        receive either:
        
        1) an acknowledgement to one or more
        outstanding I PDUs.  or 2) a response PDU to an
        unnumbered command PDU.
        
        The expiration of this timer shall cause the
        frame unacknowledged frames to be retransmitted
        (up to N2 times).
        
        This object contains an administrative value
        which will be applied the next time this
        connection is established.  A zero value for
        this object indicates that the SAP default,
        llcSapAdminAckTimer, shall be used."
    DEFVAL { 0 }
    ::= { llcCcAdminEntry 11 }

llcCcAdminPbitTimer OBJECT-TYPE
    SYNTAX TimeTicks
    ACCESS read-write
    STATUS mandatory
    DESCRIPTION
        "This object denotes the value for the time
        interval during which this LLC shall expect to
        receive a PDU with the F bit set to '1' in
        response to a Type 2 command with the P bit set
        to '1'.
        
        The expiration of this timer shall cause the
        REJ PDU to be retransmitted (up to N2 times).
        
        This object contains an administrative value
        which will be applied the next time this
        connection is established.  A zero value for
        this object indicates that the SAP default,
        llcSapAdminPbitTimer, shall be used."
    DEFVAL { 0 }
    ::= { llcCcAdminEntry 12 }

llcCcAdminRejTimer OBJECT-TYPE
    SYNTAX TimeTicks
    ACCESS read-write
    STATUS mandatory
    DESCRIPTION
        "This object denotes the value for the time
        interval during which this LLC shall expect to
        receive a reply to a REJ PDU.
        
        The expiration of this timer shall cause the
        REJ PDU to be retransmitted (up to N2 times).
        
        This object contains an administrative value
        which will be applied the next time this
        connection is established.  A zero value for
        this object indicates that the SAP default,
        llcSapAdminRejTimer, shall be used."
    DEFVAL { 0 }
    ::= { llcCcAdminEntry 13 }

llcCcAdminBusyTimer OBJECT-TYPE
    SYNTAX TimeTicks
    ACCESS read-write
    STATUS mandatory
    DESCRIPTION
        "This object denotes the value for the time
        interval during which this LLC shall expect to
        receive an indication that a busy condition at
        the remote LLC has cleared.
        
        The expiration of this timer shall cause the
        link to be declared inactive.
        
        This object contains an administrative value
        which will be applied the next time this
        connection is established.  A zero value for
        this object indicates that the SAP default,
        llcSapAdminBusyTimer, shall be used."
    DEFVAL { 0 }
    ::= { llcCcAdminEntry 14 }

llcCcAdminInactTimer OBJECT-TYPE
    SYNTAX TimeTicks
    ACCESS read-write
    STATUS mandatory
    DESCRIPTION
        "This object denotes the value for the time
        interval during which this LLC shall expect to
        receive any PDU from the remote LLC.  This
        function is not described in the IEEE 802.2
        specification [??] but is widely implemented.
        
        The expiration of this timer shall cause the
        local LLC to send a PDU to the remote LLC with
        the P bit set to '1'.
        
        This object contains an administrative value
        which will be applied the next time this
        connection is established.  A zero value for
        this object indicates that the SAP default,
        llcSapAdminInactTimer, shall be used.
        
        Any value for this object less than or equal to
        the acknowledgement timer shall mean that the
        timer is not used."
    DEFVAL { 0 }
    ::= { llcCcAdminEntry 15 }

llcCcAdminDelayAckCount OBJECT-TYPE
    SYNTAX INTEGER
    ACCESS read-write
    STATUS mandatory
    DESCRIPTION
        "This object denotes the value for the maximum
        number of consequetive I PDUs which this LLC
        shall receive during the interval defined by
        llcCcOperDelayTimer without sending an
        immediate acknowledgement.  This must be less
        than or equal to the value of
        llcCcOperMaxUnackIPDURcv. This function is not
        described in the IEEE 802.2 specification [??]
        but is widely implemented.
        
        This object contains an administrative value
        which will be applied the next time this
        connection is established.  A zero value for
        this object indicates that the SAP default,
        llcSapAdminDelayAck, shall be used.
        
        A value of one indicates that acknowledgments
        will be sent immediately and that the value of
        llcCcAdminDelayAckTimer shall be ignored."
    DEFVAL { 0 }
    ::= { llcCcAdminEntry 16 }

llcCcAdminDelayAckTimer OBJECT-TYPE
    SYNTAX TimeTicks
    ACCESS read-write
    STATUS mandatory
    DESCRIPTION
        "This object denotes the value for the time
        interval during which this LLC shall delay
        acknowledgment of one or more I PDUs (up to the
        value of llcCcOperDelayAckCount). This function
        is not described in the IEEE 802.2
        specification [??] but is widely implemented.
        
        The expiration of this timer shall cause the
        local LLC to acknowledge all unacknowledged I
        PDUs.
        
        This object contains an administrative value
        which will be applied the next time this
        connection is established.
        
        This object is associated with the
        llcCcAdminDelayAckCount object and is only
        defined if that object has a value greater than
        one."
    DEFVAL { 0 }
    ::= { llcCcAdminEntry 17 }

llcCcAdminRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object is used by a management station to
        create or delete the row entry in
        llcCcAdminTable following the RowStatus textual
        convention.
        
        Upon successful creation of the row, an agent
        automatically creates a corresponding entry in
        the llcCcOperTable with llcCcOperState equal to
        'discontacted (1)'."
    ::= { llcCcAdminEntry 18 }

llcCcOperTable OBJECT-TYPE
    SYNTAX SEQUENCE OF LlcCcOperEntry
    ACCESS not-accessible
    STATUS mandatory
    DESCRIPTION
        "This table contains current LLC link
        parameters.  Many of these objects have
        corresponding objects in the
        llcCcAdminTable."
    ::= { llcCcGroup 2 }

llcCcOperEntry OBJECT-TYPE
    SYNTAX LlcCcOperEntry
    ACCESS not-accessible
    STATUS mandatory
    DESCRIPTION
        "A list of status and control values for an
        LLC link station."
    INDEX { ifIndex, llcCcLSap, llcCcRSap, llcCcRMac, llcCcLMac }
    ::= { llcCcOperTable 1 }

LlcCcOperEntry ::= SEQUENCE {
    llcCcOperRole INTEGER,
    llcCcOperState INTEGER,
    llcCcOperMaxIPDUOctetsSend Integer32,
    llcCcOperMaxIPDUOctetsRcv Integer32,
    llcCcOperMaxUnackedIPDUsSend INTEGER,
    llcCcOperMaxUnackedIPDUsRcv INTEGER,
    llcCcOperMaxRetransmits INTEGER,
    llcCcOperAckTimer TimeTicks,
    llcCcOperPbitTimer TimeTicks,
    llcCcOperRejTimer TimeTicks,
    llcCcOperBusyTimer TimeTicks,
    llcCcOperInactTimer TimeTicks,
    llcCcOperDelayAckCount INTEGER,
    llcCcOperDelayAckTimer TimeTicks,
    llcCcOperCreateTime TimeTicks,
    llcCcOperLastModifyTime TimeTicks,
    llcCcOperLastFailTime TimeTicks,
    llcCcOperLastFailCause INTEGER,
    llcCcOperLastFailFRMRInfo OCTET STRING
    }

llcCcOperRole OBJECT-TYPE
    SYNTAX INTEGER {
        primary(1),
        secondary(2),
        undefined(3)
        }
    ACCESS read-only
    STATUS mandatory
    DESCRIPTION
        "This object reflects the current role that the link
         station is assuming."
    ::= { llcCcOperEntry 1 }

llcCcOperState OBJECT-TYPE
    SYNTAX INTEGER {
        discontacted(1),
        contactPending(2),
        contacted(3),
        discontactPending(4)
        }
    ACCESS read-only
    STATUS mandatory
    DESCRIPTION
        "This object describes the operational state of
        the LLC connection.  The managed system shall
        attempt to keep this value consistent with the
        administered state, llcCcAdminState"
    ::= { llcCcOperEntry 2 }

llcCcOperMaxIPDUOctetsSend OBJECT-TYPE
    SYNTAX Integer32
    ACCESS read-write
    STATUS mandatory
    DESCRIPTION
        "This object denotes the maximum I PDU size, in
        octets, that this LLC SAP may send to its
        remote connection component partner. This count
        is referred to as 'N1' in the IEEE 802.2
        specification [??].
        
        At connection setup, the remote LLC may send,
        using an XID frame, the maximum I PDU size
        which it is prepared to receive. If so, an
        implementation may choose to override the
        administered maximum PDU size with the
        dynamically learned value and should reflect
        that in this object.
        
        The I PDU size includes all octets in a frame,
        excluding framing characters, the MAC header
        and link link header."
    ::= { llcCcOperEntry 3 }

llcCcOperMaxIPDUOctetsRcv OBJECT-TYPE
    SYNTAX Integer32
    ACCESS read-write
    STATUS mandatory
    DESCRIPTION
        "This object denotes the maximum I PDU size,in
        octets, that this LLC can expect to receive
        from its remote LLC partner. This count is
        referred to as 'N1' in the IEEE 802.2
        specification [??]
        
        The I PDU size includes all octets in a frame
        with the exception of the framing characters,
        the MAC header and the link header."
    ::= { llcCcOperEntry 4 }

llcCcOperMaxUnackedIPDUsSend OBJECT-TYPE
    SYNTAX INTEGER(1..127)
    ACCESS read-write
    STATUS mandatory
    DESCRIPTION
        "This object denotes the maximum consequetive
        unacknowledged I PDU frames that this LLC may
        send to its remote LLC partner. This count is
        referred to as 'k' in the IEEE 802.2
        specification [??].
        
        At connection setup, the remote LLC may send,
        using an XID frame, the maximum number of
        unacknowledged I PDUs which it is prepared to
        receive. If so, an implementation may choose to
        override the administered maximum number of
        unacknowledged PDUs with the dynamicly learned
        value and should reflect that in this object."
    ::= { llcCcOperEntry 5 }

llcCcOperMaxUnackedIPDUsRcv OBJECT-TYPE
    SYNTAX INTEGER(1..127)
    ACCESS read-write
    STATUS mandatory
    DESCRIPTION
        "This object denotes the maximum number of
        unacknowledged I PDUs that this LLC can expect
        to receive from its remote LLC partner. This
        count is referred to as 'k' in the IEEE 802.2
        specification [??]."
    ::= { llcCcOperEntry 6 }

llcCcOperMaxRetransmits OBJECT-TYPE
    SYNTAX INTEGER
    ACCESS read-write
    STATUS mandatory
    DESCRIPTION
        "This object denotes the value for the maximum
        number of times that this LLC shall retry PDUs
        following the expiration of the acknowledgement
        timer, the P-bit timer or the reject timer.
        When these retries are exhausted, the link
        shall be declared inactive.  This count is
        referred to as 'N2' in the IEEE 802.2
        specification [??]."
    ::= { llcCcOperEntry 7 }

llcCcOperAckTimer OBJECT-TYPE
    SYNTAX TimeTicks
    ACCESS read-write
    STATUS mandatory
    DESCRIPTION
        "This object denotes the value for the time
        interval during which this LLC shall expect to
        receive either:
        
        1) an acknowledgement to one or more
        outstanding I PDUs.  or 2) a response PDU to an
        unnumbered command PDU.
        
        The expiration of this timer shall cause the
        frame unacknowledged frames to be retransmitted
        (up to N2 times)."
    ::= { llcCcOperEntry 8 }

llcCcOperPbitTimer OBJECT-TYPE
    SYNTAX TimeTicks
    ACCESS read-write
    STATUS mandatory
    DESCRIPTION
        "This object denotes the value for the time
        interval during which this LLC shall expect to
        receive a PDU with the F bit set to '1' in
        response to a Type 2 command with the P bit set
        to '1'.
        
        The expiration of this timer shall cause the
        REJ PDU to be retransmitted (up to N2 times)."
    ::= { llcCcOperEntry 9 }

llcCcOperRejTimer OBJECT-TYPE
    SYNTAX TimeTicks
    ACCESS read-write
    STATUS mandatory
    DESCRIPTION
        "This object denotes the value for the time
        interval during which this LLC shall expect to
        receive a reply to a REJ PDU.
        
        The expiration of this timer shall cause the
        REJ PDU to be retransmitted (up to N2 times)."
    ::= { llcCcOperEntry 10 }

llcCcOperBusyTimer OBJECT-TYPE
    SYNTAX TimeTicks
    ACCESS read-write
    STATUS mandatory
    DESCRIPTION
        "This object denotes the value for the time
        interval during which this LLC shall expect to
        receive an indication that a busy condition at
        the remote LLC has cleared.
        
        The expiration of this timer shall cause the
        link to be declared inactive."
    ::= { llcCcOperEntry 11 }

llcCcOperInactTimer OBJECT-TYPE
    SYNTAX TimeTicks
    ACCESS read-write
    STATUS mandatory
    DESCRIPTION
        "This object denotes the value for the time
        interval during which this LLC shall expect to
        receive any PDU from the remote LLC.  This
        function is not described in the IEEE 802.2
        specification [??] but is widely implemented.
        
        The expiration of this timer shall cause the
        local LLC to send a PDU to the remote LLC with
        the P bit set to '1'.
        
        Any value for this object less than or equal to
        the acknowledgement timer shall mean that the
        timer is not used."
    ::= { llcCcOperEntry 12 }

llcCcOperDelayAckCount OBJECT-TYPE
    SYNTAX INTEGER
    ACCESS read-write
    STATUS mandatory
    DESCRIPTION
        "This object denotes the value for the maximum
        number of consequetive I PDUs which this LLC
        shall receive during the interval defined by
        llcCcOperDelayTimer without sending an
        immediate acknowledgement.  This must be less
        than or equal to the value of
        llcCcOperMaxUnackIPDURcv. This function is not
        described in the IEEE 802.2 specification [??]
        but is widely implemented.
        
        A value of one indicates that acknowledgments
        will be sent immediately and that the value of
        llcCcOperDelayAckTimer should be ignored."
    ::= { llcCcOperEntry 13 }

llcCcOperDelayAckTimer OBJECT-TYPE
    SYNTAX TimeTicks
    ACCESS read-write
    STATUS mandatory
    DESCRIPTION
        "This object denotes the value for the time
        interval during which this LLC shall delay
        acknowledgment of one or more I PDUs (up to the
        value of llcCcOperDelayAckCount). This function
        is not described in the IEEE 802.2
        specification [??] but is widely implemented.
        
        The expiration of this timer shall cause the
        local LLC to acknowledge all unacknowledged I
        PDUs.
        
        This object is associated with the
        llcCcOperDelayAckCount object and only has
        meaning if that object has a value greater than
        one."
    ::= { llcCcOperEntry 14 }

llcCcOperCreateTime OBJECT-TYPE
    SYNTAX TimeTicks
    ACCESS read-only
    STATUS mandatory
    DESCRIPTION
        "This object describes the value of sysUpTime
         when this connection was created."
    ::= { llcCcOperEntry 15 }

llcCcOperLastModifyTime OBJECT-TYPE
    SYNTAX TimeTicks
    ACCESS read-only
    STATUS mandatory
    DESCRIPTION
        "This object describes the value of sysUpTime
         when this connection definition was last
         modified.  If the connection has not been
         modified, then this value shall be zero."
    ::= { llcCcOperEntry 16 }

llcCcOperLastFailTime OBJECT-TYPE
    SYNTAX TimeTicks
    ACCESS read-only
    STATUS mandatory
    DESCRIPTION
        "This object describes the value of sysUpTime
         when this LLC link station last failed.  If
         the link station has not failed, then this
         value shall be zero."
    ::= { llcCcOperEntry 17 }

llcCcOperLastFailCause OBJECT-TYPE
    SYNTAX INTEGER {
        undefined(1),
        rxFRMR(2),
        txFRMR(3),
        noResponse(4),
        protocolErr(5),
        noActivity(6),
        discReceived(7),
        dmReceived(8),
        retriesExpired(9)
        }
    ACCESS read-only
    STATUS mandatory
    DESCRIPTION
        "This enumerated object reflects the cause of the
        last failure of this LLC link station.  If the link
        station has not failed, then this object will have
        a value of undefined(1)."
    DEFVAL { undefined }
    ::= { llcCcOperEntry 18 }

llcCcOperLastFailFRMRInfo OBJECT-TYPE
    SYNTAX OCTET STRING(SIZE(3))
    ACCESS read-only
    STATUS mandatory
    DESCRIPTION
        "This object reflects the information field of the
        FRMR frame if the last failure for this LLC link
        station was as a result of an invalid frame.
        Otherwise, this field has no meaning."
    ::= { llcCcOperEntry 19 }

llcCcStatsTable OBJECT-TYPE
    SYNTAX SEQUENCE OF LlcCcStatsEntry
    ACCESS not-accessible
    STATUS mandatory
    DESCRIPTION
        "Each entry in this table contains statistics
        for a specific LLC link station."
    ::= { llcCcGroup 3 }

llcCcStatsEntry OBJECT-TYPE
    SYNTAX LlcCcStatsEntry
    ACCESS not-accessible
    STATUS mandatory
    DESCRIPTION
        "A list of statistics for an LLC link station."
    INDEX { ifIndex, llcCcLSap, llcCcRSap, llcCcRMac, llcCcLMac }
    ::= { llcCcStatsTable 1 }

LlcCcStatsEntry ::= SEQUENCE {
    llcCcStatsLocalBusies Counter32,
    llcCcStatsRemoteBusies Counter32,
    llcCcStatsIFramesIn Counter32,
    llcCcStatsIFramesOut Counter32,
    llcCcStatsIOctetsIn Counter32,
    llcCcStatsIOctetsOut Counter32,
    llcCcStatsREJsIn Counter32,
    llcCcStatsREJsOut Counter32,
    llcCcStatsRetransmitsIn Counter32,
    llcCcStatsRetransmitsOut Counter32,
    llcCcStatsFRMRsIn Counter32,
    llcCcStatsFRMRsOut Counter32,
    llcCcStatsDISCsIn Counter32,
    llcCcStatsDISCsOut Counter32,
    llcCcStatsUAsIn Counter32,
    llcCcStatsUAsOut Counter32,
    llcCcStatsDMsIn Counter32,
    llcCcStatsDMsOut Counter32,
    llcCcStatsSABMEsIn Counter32,
    llcCcStatsSABMEsOut Counter32,
    llcCcStatsProtocolErrs Counter32,
    llcCcStatsActivityTOs Counter32,
    llcCcStatsRetriesExps Counter32
    }

llcCcStatsLocalBusies OBJECT-TYPE
    SYNTAX Counter32
    ACCESS read-only
    STATUS mandatory
    DESCRIPTION
        "This object reflects the total number of times
        that the local LLC link station has entered a
        busy state (RNR) since link station startup.
        At link station startup time, this object must
        be initialized to zero."
    ::= { llcCcStatsEntry 1 }

llcCcStatsRemoteBusies OBJECT-TYPE
    SYNTAX Counter32
    ACCESS read-only
    STATUS mandatory
    DESCRIPTION
        "This object reflects the total number of times
        that an adjacent ( remote) LLC link station
        has entered a busy state (RNR) since link
        station startup.  At link station startup time,
        this object must be initialized to zero."
    ::= { llcCcStatsEntry 2 }

llcCcStatsIFramesIn OBJECT-TYPE
    SYNTAX Counter32
    ACCESS read-only
    STATUS mandatory
    DESCRIPTION
        "This object reflects the total I-frames
        received from an adjacent LLC link station
        since link station startup.  At link station
        startup time, this object must be initialized
        to zero."
    ::= { llcCcStatsEntry 3 }

llcCcStatsIFramesOut OBJECT-TYPE
    SYNTAX Counter32
    ACCESS read-only
    STATUS mandatory
    DESCRIPTION
        "This object reflects the total I-frames
        transmitted to an adjacent LLC link station
        since link station startup.  At link station
        startup time, this object must be initialized
        to zero."
    ::= { llcCcStatsEntry 4 }

llcCcStatsIOctetsIn OBJECT-TYPE
    SYNTAX Counter32
    ACCESS read-only
    STATUS mandatory
    DESCRIPTION
        "This object reflects the total octets
        contained in I-frames received from an adjacent
        LLC link station since link station startup.
        At link station startup time, this object must
        be initialized to zero."
    ::= { llcCcStatsEntry 5 }

llcCcStatsIOctetsOut OBJECT-TYPE
    SYNTAX Counter32
    ACCESS read-only
    STATUS mandatory
    DESCRIPTION
        "This object reflects the total octets
        contained in I-frames transmitted to an
        adjacent LLC link station since link station
        startup.  At link station startup time,
        this object must be initialized to zero."
    ::= { llcCcStatsEntry 6 }

llcCcStatsREJsIn OBJECT-TYPE
    SYNTAX Counter32
    ACCESS read-only
    STATUS mandatory
    DESCRIPTION
        "This object reflects the total REJ frames
        received from an adjacent LLC link station
        since link station startup."
    ::= { llcCcStatsEntry 7 }

llcCcStatsREJsOut OBJECT-TYPE
    SYNTAX Counter32
    ACCESS read-only
    STATUS mandatory
    DESCRIPTION
        "This object reflects the total REJ frames
        transmitted to an adjacent LLC link station
        since link station startup."
    ::= { llcCcStatsEntry 8 }

llcCcStatsRetransmitsIn OBJECT-TYPE
    SYNTAX Counter32
    ACCESS read-only
    STATUS mandatory
    DESCRIPTION
        "This object reflects the total number of information
        frames retransmitted by the remote link station
        because the N(s) received from that link station
        indicated that one or more information frames
        sent by that station were lost.  This event
        causes the first missing information frame of a
        window and all subsequent information frames to
        be retransmitted.  At link station startup time,
        this object must be initialized to zero"
    ::= { llcCcStatsEntry 9 }

llcCcStatsRetransmitsOut OBJECT-TYPE
    SYNTAX Counter32
    ACCESS read-only
    STATUS mandatory
    DESCRIPTION
        "This object reflects the total number of
        information frames retransmitted to a remote
        link station because the N(r) received from
        that link station indicated that one or more
        information frames sent to that station were
        lost. This event causes the first missing
        information frame of a window and all
        subsequent information frames to be
        retransmitted.  At link station startup time,
        this object must be initialized to zero."
    ::= { llcCcStatsEntry 10 }

llcCcStatsFRMRsIn OBJECT-TYPE
    SYNTAX Counter32
    ACCESS read-only
    STATUS mandatory
    DESCRIPTION
        "This object reflects the total frame reject
        (FRMR) frames received from an adjacent LLC
        link station since link station startup."
    ::= { llcCcStatsEntry 11 }

llcCcStatsFRMRsOut OBJECT-TYPE
    SYNTAX Counter32
    ACCESS read-only
    STATUS mandatory
    DESCRIPTION
        "This object reflects the total frame reject
        (FRMR) frames transmitted to an adjacent LLC
        link station since link station startup."
    ::= { llcCcStatsEntry 12 }

llcCcStatsDISCsIn OBJECT-TYPE
    SYNTAX Counter32
    ACCESS read-only
    STATUS mandatory
    DESCRIPTION
        "This object reflects the total number of
        disconnect (DISC) requests received from an
        adjacent link station since link station
        startup.  At link station startup time, this
        object must be initialized to zero."
    ::= { llcCcStatsEntry 13 }

llcCcStatsDISCsOut OBJECT-TYPE
    SYNTAX Counter32
    ACCESS read-only
    STATUS mandatory
    DESCRIPTION
        "This object reflects the total number of
        disconnect (DISC) requests transmited to an
        adjacent link station since link station
        startup.  At link station startup time, this
        object must be initialized to zero."
    ::= { llcCcStatsEntry 14 }

llcCcStatsUAsIn OBJECT-TYPE
    SYNTAX Counter32
    ACCESS read-only
    STATUS mandatory
    DESCRIPTION
        "This object reflects the total number of
        unnumbered acknowledgements (UA) requests
        received from an adjacent link station
        since link station startup.  At link station
        startup time, this object must be initialized
        to zero."
    ::= { llcCcStatsEntry 15 }

llcCcStatsUAsOut OBJECT-TYPE
    SYNTAX Counter32
    ACCESS read-only
    STATUS mandatory
    DESCRIPTION
        "This object reflects the total number of
        unnumbered acknowledgements (UA) requests
        transmited to an adjacent link station
        since link station startup.  At link station
        startup time, this object must be initialized
        to zero."
    ::= { llcCcStatsEntry 16 }

llcCcStatsDMsIn OBJECT-TYPE
    SYNTAX Counter32
    ACCESS read-only
    STATUS mandatory
    DESCRIPTION
        "This object reflects the total number of
        disconnect mode (DM) requests received from an
        adjacent link station since link station
        startup.  At link station startup time, this
        object must be initialized to zero."
    ::= { llcCcStatsEntry 17 }

llcCcStatsDMsOut OBJECT-TYPE
    SYNTAX Counter32
    ACCESS read-only
    STATUS mandatory
    DESCRIPTION
        "This object reflects the total number of
        disconnect mode (DM) requests transmited to an
        adjacent link station since link station
        startup.  At link station startup time, this
        object must be initialized to zero."
    ::= { llcCcStatsEntry 18 }

llcCcStatsSABMEsIn OBJECT-TYPE
    SYNTAX Counter32
    ACCESS read-only
    STATUS mandatory
    DESCRIPTION
        "This object reflects the total number of
        set normal response mode (SABME) requests
        received from an adjacent link station
        since link station startup.  At link station
        startup time, this object must be initialized
        to zero."
    ::= { llcCcStatsEntry 19 }

llcCcStatsSABMEsOut OBJECT-TYPE
    SYNTAX Counter32
    ACCESS read-only
    STATUS mandatory
    DESCRIPTION
        "This object reflects the total number of
        set normal response mode (SABME) requests
        transmited to an adjacent link station
        since link station startup.  At link station
        startup time, this object must be initialized
        to zero."
    ::= { llcCcStatsEntry 20 }

llcCcStatsProtocolErrs OBJECT-TYPE
    SYNTAX Counter32
    ACCESS read-only
    STATUS mandatory
    DESCRIPTION
        "This object reflects the total occurrences,
        since link station startup, where this LLC
        link station has inactivated the link as a
        result of receiving a frame from its adjacent
        link station which was in violation of the
        protocol.  At link station startup time, this
        object must be initialized to zero."
    ::= { llcCcStatsEntry 21 }

llcCcStatsActivityTOs OBJECT-TYPE
    SYNTAX Counter32
    ACCESS read-only
    STATUS mandatory
    DESCRIPTION
        "This object reflects the total occurrences,
        since startup, where this LLC link station has
        inactivated the link as a result of no activity
        on the link.  At link station startup time,
        this object must be initialized to zero."
    ::= { llcCcStatsEntry 22 }

llcCcStatsRetriesExps OBJECT-TYPE
    SYNTAX Counter32
    ACCESS read-only
    STATUS mandatory
    DESCRIPTION
        "This object reflects the total occurrences,
        since startup, where this LLC link station has
        inactivated the link as a result of a retry
        sequence being exhausted.  At link station
        startup time, this object must be initialized
        to zero."
    ::= { llcCcStatsEntry 23 }

llcPortStatusChange TRAP-TYPE
--?? Non-reverse mappable trap
    ENTERPRISE llcTraps
    VARIABLES {
        llcPortOperLastFailTime, llcPortOperLastFailCause }
--  Status
--    mandatory
    DESCRIPTION
        "This trap indicates that the state of an LLC port
         has transitioned to active or inactive."
    ::= 1

llcCcStatusChange TRAP-TYPE
--?? Non-reverse mappable trap
    ENTERPRISE llcTraps
    VARIABLES {
        llcCcOperState, llcCcAdminState, llcCcOperLastFailTime, 
        llcCcOperLastFailCause, llcCcOperLastFailFRMRInfo }
--  Status
--    mandatory
    DESCRIPTION
        "This trap indicates that the state of an LLC link
         station has transitioned to contacted or
         discontacted."
    ::= 2

llcCorePortAdminGroup OBJECT IDENTIFIER ::= { llcCoreGroups 1 }
-- OBJECT-GROUP
--  Status
--    mandatory
--  Descr
--    The llcCorePortAdminGroup defines objects
--    which are common to the PortAdmin group of all
--    compliant connections.
--  objects
--    llcPortAdminName

llcCorePortOperGroup OBJECT IDENTIFIER ::= { llcCoreGroups 2 }
-- OBJECT-GROUP
--  Status
--    mandatory
--  Descr
--    The llcCorePortOperGroup defines objects
--    which are common to the PortOper group of all
--    compliant connections.
--  objects
--    llcPortOperName, llcPortOperISTATUS, llcPortOperLastFailTime, 
--    llcPortOperLastFailCause

llcCorePortStatsGroup OBJECT IDENTIFIER ::= { llcCoreGroups 3 }
-- OBJECT-GROUP
--  Status
--    mandatory
--  Descr
--    The llcCorePortStatsGroup defines objects
--    which are common to the PortStats group of all
--    compliant connections.
--  objects
--    llcPortStatsPhysicalFailures

llcCoreCcAdminGroup OBJECT IDENTIFIER ::= { llcCoreGroups 4 }
-- OBJECT-GROUP
--  Status
--    mandatory
--  Descr
--    The llcCorePortAdminGroup defines objects
--    which are common to the PortAdmin group of all
--    compliant connections.
--  objects
--    llcCcAdminState, llcCcAdminRowStatus

llcCoreCcOperGroup OBJECT IDENTIFIER ::= { llcCoreGroups 5 }
-- OBJECT-GROUP
--  Status
--    mandatory
--  Descr
--    The llcCorePortOperGroup defines objects
--    which are common to the PortOper group of all
--    compliant connections.
--  objects
--    llcCcOperRole, llcCcOperState, llcCcOperLastFailTime, 
--    llcCcOperLastFailCause, llcCcOperLastFailFRMRInfo

llcCoreCcStatsGroup OBJECT IDENTIFIER ::= { llcCoreGroups 6 }
-- OBJECT-GROUP
--  Status
--    mandatory
--  Descr
--    The llcCorePortStatsGroup defines objects
--    which are common to the PortStats group of all
--    compliant connections.
--  objects
--    llcCcStatsLocalBusies, llcCcStatsRemoteBusies, 
--    llcCcStatsIFramesIn, llcCcStatsIFramesOut, 
--    llcCcStatsRetransmitsIn, llcCcStatsRetransmitsOut, 
--    llcCcStatsIOctetsIn, llcCcStatsIOctetsOut, llcCcStatsREJsIn, 
--    llcCcStatsREJsOut, llcCcStatsFRMRsIn, llcCcStatsFRMRsOut, 
--    llcCcStatsProtocolErrs, llcCcStatsRetriesExps

llcCoreCompliance OBJECT IDENTIFIER ::= { llcCompliances 1 }
-- MODULE-COMPLIANCE
--  Status
--    mandatory
--  Descr
--    The core compliance statement for all LLC nodes.
--  Module
--    >>current<<
--   MandGroup
--    llcCorePortAdminGroup
--   MandGroup
--    llcCorePortOperGroup
--   MandGroup
--    llcCorePortStatsGroup
--   MandGroup
--    llcCoreCcAdminGroup
--   MandGroup
--    llcCoreCcOperGroup
--   MandGroup
--    llcCoreCcStatsGroup


END
