-- *****************************************************************
-- CISCO-POWER-ETHERNET-CAPABILITY.my:
-- Cisco POWER-ETHERNET-MIB AGENT-CAPABILITIES
--
-- June 2004, Seth Wang
--
-- Copyright (c) 2004 by Cisco Systems, Inc.
-- All rights reserved.
-- *****************************************************************

CISCO-POWER-ETHERNET-CAPABILITY DEFINITIONS ::= BEGIN

IMPORTS
        MODULE-IDENTITY
                FROM SNMPv2-SMI
        AGENT-CAPABILITIES
                FROM SNMPv2-CONF
        TruthValue 
                FROM SNMPv2-TC
        ciscoAgentCapability
                FROM CISCO-SMI;

ciscoPowerEthernetCapability MODULE-IDENTITY
        LAST-UPDATED    "200406280000Z"
        ORGANIZATION    "Cisco Systems, Inc."
        CONTACT-INFO
                "       Cisco Systems
                        Customer Service

                Postal: 170 West Tasman Drive
                        San Jose, CA  95134
                        USA

                   Tel: +1 800 553-NETS

                E-mail: cs-lan-switch-snmp@cisco.com"
        DESCRIPTION
                "The capabilities description of
                 POWER-ETHERNET-MIB."

        REVISION        "200406280000Z"
        DESCRIPTION
                "Initial version of this MIB module."
        ::= { ciscoAgentCapability 412 }

cPowerEthernetCapCatOSV08R0401 AGENT-CAPABILITIES
    PRODUCT-RELEASE     "Cisco CatOS 8.4(1)."
    STATUS              current
    DESCRIPTION         "POWER-ETHERNET-MIB capabilities."

    SUPPORTS            POWER-ETHERNET-MIB
        INCLUDES        { pethPsePortGroup,
                          pethPsePortNotificationGroup,
                          pethNotificationControlGroup,
                          pethMainPseGroup,
                          pethMainPowerNotificationGroup }

        VARIATION       pethPsePortPowerPairsControlAbility
            SYNTAX      TruthValue { false(2) }
            DESCRIPTION "Only a limited set of enumerated values
                         is supported."

        VARIATION       pethPsePortPowerPairs
            SYNTAX      INTEGER { signal(1) }
            DESCRIPTION "Only a limited set of enumerated values
                         is supported."

        VARIATION       pethPsePortType
            ACCESS      read-only
            DESCRIPTION "Unable to set this in CatOS."

    ::= { ciscoPowerEthernetCapability 1 }

END
