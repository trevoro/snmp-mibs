--------------------------------------------------------------------
-- BDCOM-TS.my:  BDCom Terminal Service MIB file
--
-- June 2000, 
-- 
--------------------------------------------------------------------

   BDCOM-TS DEFINITIONS ::= BEGIN

               IMPORTS
			IpAddress
				FROM RFC1155-SMI
			OBJECT-TYPE
				FROM RFC-1212
			DisplayString
				FROM RFC1213-MIB
			bdlocal
				FROM BDCOM-SMI;
          
               bdlts             OBJECT IDENTIFIER ::= { bdlocal 9 }


          -- This group is present in all products which contain
          -- asynchronous terminal lines.

               bdtsLines OBJECT-TYPE
                   SYNTAX  INTEGER
                   ACCESS  read-only
                   STATUS  mandatory
                   DESCRIPTION
                           "Number of terminal lines on this device.
                           Includes virtual lines."
                   ::= { bdlts 1 }


               -- Local Terminal Service Line Table

          -- This group contains terminal service specific
          -- information on a per line basis.

               bdltsLineTable OBJECT-TYPE
                   SYNTAX  SEQUENCE OF BdLtsLineEntry
                   ACCESS  not-accessible
                   STATUS  mandatory
                   DESCRIPTION
                            "A list of terminal server line entries."
                   ::= { bdlts 2 }

               bdltsLineEntry OBJECT-TYPE
                   SYNTAX BdLtsLineEntry
                   ACCESS  not-accessible
                   STATUS  mandatory
                   DESCRIPTION
                            "A collection of per TTY objects in the
                            BDCom Terminal Server implementation."
                   INDEX { tsLineNumber }
               ::= { bdltsLineTable 1 }

               BdLtsLineEntry ::=
                   SEQUENCE {
                       bdtsLineActive
                           INTEGER,
                       bdtsLineType
                           INTEGER,
                       bdtsLineAutobaud
                           INTEGER,
                       bdtsLineSpeedin
                           INTEGER,
                       bdtsLineSpeedout
                           INTEGER,
                       bdtsLineFlow
                           INTEGER,
                       bdtsLineModem
                           INTEGER,
                       bdtsLineLoc
                           DisplayString,
                       bdtsLineTerm
                           DisplayString,
                       bdtsLineScrlen
                           INTEGER,
                       bdtsLineScrwid
                           INTEGER,
                       bdtsLineEsc
                           DisplayString,
                       bdtsLineTmo
                           INTEGER,
                       bdtsLineSestmo
                           INTEGER,
                       bdtsLineRotary
                           INTEGER,
                       bdtsLineUses
                           INTEGER,
                       bdtsLineNses
                           INTEGER,
                       bdtsLineUser
                           DisplayString,
                       bdtsLineNoise
                           INTEGER,
                       bdtsLineNumber
                           INTEGER,
                       bdtsLineTimeActive
                           INTEGER
                   }


          -- The following section describes the components of the
          -- table.

               bdtsLineActive OBJECT-TYPE
                   SYNTAX  INTEGER
                   ACCESS  read-only
                   STATUS  mandatory
                   DESCRIPTION
                           "Boolean whether this line is active or not."
                   ::= { bdltsLineEntry 1 }

               bdtsLineType OBJECT-TYPE
                   SYNTAX  INTEGER {
                        unknown(1),
                        console(2),
                        terminal(3),
                        line-printer(4),
                        virtual-terminal(5),
                        auxiliary(6)
                   }
                   ACCESS  read-only
                   STATUS  mandatory
                   DESCRIPTION
                           "Type of line."
                   ::= { bdltsLineEntry 2 }

               bdtsLineAutobaud OBJECT-TYPE
                   SYNTAX  INTEGER
                   ACCESS  read-only
                   STATUS  mandatory
                   DESCRIPTION
                           "Boolean whether line will autobaud or not."
                   ::= { bdltsLineEntry 3 }

               bdtsLineSpeedin OBJECT-TYPE
                   SYNTAX  INTEGER
                   ACCESS  read-only
                   STATUS  mandatory
                   DESCRIPTION
                           "What input speed the line is running at."
                   ::= { bdltsLineEntry 4 }

               bdtsLineSpeedout OBJECT-TYPE
                   SYNTAX  INTEGER
                   ACCESS  read-only
                   STATUS  mandatory
                   DESCRIPTION
                           "What output speed the line is running at."
                   ::= { bdltsLineEntry 5 }

               bdtsLineFlow OBJECT-TYPE
                   SYNTAX  INTEGER {
                        unknown(1),
                        none(2),
                        software-input(3),
                        software-output(4),
                        software-both(5),
                        hardware-input(6),
                        hardware-output(7),
                        hardware-both(8)
                   }
                   ACCESS  read-only
                   STATUS  mandatory
                   DESCRIPTION
                           "What kind of flow control the line is
                           using."
                   ::= { bdltsLineEntry 6 }

               bdtsLineModem OBJECT-TYPE
                   SYNTAX  INTEGER {
                        unknown(1),
                        none(2),
                        call-in(3),
                        call-out(4),
                        cts-required(5),
                        ri-is-cd(6),
                        inout(7)
                   }
                   ACCESS  read-only
                   STATUS  mandatory
                   DESCRIPTION
                           "What kind of modem control the line is
                           using."
                   ::= { bdltsLineEntry 7 }

               bdtsLineLoc OBJECT-TYPE
                   SYNTAX  DisplayString
                   ACCESS  read-only
                   STATUS  mandatory
                   DESCRIPTION
                           "Describes the line's physical location."
                   ::= { bdltsLineEntry 8 }

               bdtsLineTerm OBJECT-TYPE
                   SYNTAX  DisplayString
                   ACCESS  read-only
                   STATUS  mandatory
                   DESCRIPTION
                           "Describes the line's terminal type."
                   ::= { bdltsLineEntry 9 }

               bdtsLineScrlen OBJECT-TYPE
                   SYNTAX  INTEGER
                   ACCESS  read-only
                   STATUS  mandatory
                   DESCRIPTION
                           "Length in lines of the screen of terminal
                           attached to this line."
                   ::= { bdltsLineEntry 10 }

               bdtsLineScrwid OBJECT-TYPE
                   SYNTAX  INTEGER
                   ACCESS  read-only
                   STATUS  mandatory
                   DESCRIPTION
                           "Width in characters of the screen of
                           terminal attached to this line."
                   ::= { bdltsLineEntry 11 }

               bdtsLineEsc OBJECT-TYPE
                   SYNTAX  DisplayString
                   ACCESS  read-only
                   STATUS  mandatory
                   DESCRIPTION
                           "Escape character used to break out of active
                           sessions."
                   ::= { bdltsLineEntry 12 }

               bdtsLineTmo OBJECT-TYPE
                   SYNTAX  INTEGER
                   ACCESS  read-only
                   STATUS  mandatory
                   DESCRIPTION
                           "Line idleness timeout in seconds."
                   ::= { bdltsLineEntry 13 }

               bdtsLineSestmo OBJECT-TYPE
                   SYNTAX  INTEGER
                   ACCESS  read-only
                   STATUS  mandatory
                   DESCRIPTION
                           "Session idleness timeout in seconds."
                   ::= { bdltsLineEntry 14 }

               bdtsLineRotary OBJECT-TYPE
                   SYNTAX  INTEGER
                   ACCESS  read-only
                   STATUS  mandatory
                   DESCRIPTION
                           "Rotary group number the line belongs in."
                   ::= { bdltsLineEntry 15 }

               bdtsLineUses OBJECT-TYPE
                   SYNTAX  INTEGER
                   ACCESS  read-only
                   STATUS  mandatory
                   DESCRIPTION
                           "Number of times a connection has been made
                           to or from this line."
                   ::= { bdltsLineEntry 16 }

               bdtsLineNses OBJECT-TYPE
                   SYNTAX  INTEGER
                   ACCESS  read-only
                   STATUS  mandatory
                   DESCRIPTION
                           "Current number of sessions in use on this
                           line."
                   ::= { bdltsLineEntry 17 }

               bdtsLineUser OBJECT-TYPE
                   SYNTAX  DisplayString
                   ACCESS  read-only
                   STATUS  mandatory
                   DESCRIPTION
                           "TACACS user name, if TACACS enabled, of user
                           on this line."
                   ::= { bdltsLineEntry 18 }

               bdtsLineNoise OBJECT-TYPE
                   SYNTAX  INTEGER
                   ACCESS  read-only
                   STATUS  mandatory
                   DESCRIPTION
                           "Count of garbage characters received when
                           line inactive."
                   ::= { bdltsLineEntry 19 }

               bdtsLineNumber OBJECT-TYPE
                   SYNTAX  INTEGER
                   ACCESS  read-only
                   STATUS  mandatory
                   DESCRIPTION
                           "The line i've been talking about."
                   ::= { bdltsLineEntry 20 }

               bdtsLineTimeActive OBJECT-TYPE
                   SYNTAX  INTEGER
                   ACCESS  read-only
                   STATUS  mandatory
                   DESCRIPTION
                           "The time in seconds since line was activated."
                   ::= { bdltsLineEntry 21 }
               -- End of table

               -- Local Terminal Service Line Session Table

          -- This group contains terminal server specific
          -- information on a per line and per session basis.

               bdltsLineSessionTable OBJECT-TYPE
                   SYNTAX  SEQUENCE OF BdLtsLineSessionEntry
                   ACCESS  not-accessible
                   STATUS  mandatory
                   DESCRIPTION
                            "A list of terminal server line and session
                            entries."
                   ::= { bdlts 3 }

               bdltsLineSessionEntry OBJECT-TYPE
                   SYNTAX BdLtsLineSessionEntry
                   ACCESS  not-accessible
                   STATUS  mandatory
                   DESCRIPTION
                            "A collection of per session and per TTY
                            objects in the BDCom Terminal Server
                            implementation."
                   INDEX { bdtslineSesLine, bdtslineSesSession }
               ::= { bdltsLineSessionTable 1 }

               BdLtsLineSessionEntry ::=
                   SEQUENCE {
                       bdtslineSesType
                           INTEGER,
                       bdtslineSesDir
                           INTEGER,
                       bdtslineSesAddr
                           IpAddress,
                       bdtslineSesName
                           DisplayString,
                       bdtslineSesCur
                           INTEGER,
                       bdtslineSesIdle
                           INTEGER,
                       bdtslineSesLine
                           INTEGER,
                       bdtslineSesSession 
                           INTEGER
                   }


          -- The following section describes the components of the
          -- table.

               bdtslineSesType OBJECT-TYPE
                   SYNTAX  INTEGER {
                        unknown(1),
                        pad(2),
                        stream(3),
                        rlogin(4),
                        telnet(5),
                        tcp(6),
                        lat(7),
                        mop(8),
                        slip(9),
                        xremote(10),
			rshell(11)
                   }
                   ACCESS  read-only
                   STATUS  mandatory
                   DESCRIPTION
                           "Type of session."
                   ::= { bdltsLineSessionEntry 1 }

               bdtslineSesDir OBJECT-TYPE
                   SYNTAX  INTEGER {
                        unknown(1),
                        incoming(2),
                        outgoing(3)
                   }
                   ACCESS  read-only
                   STATUS  mandatory
                   DESCRIPTION
                           "Direction of session."
                   ::= { bdltsLineSessionEntry 2 }

               bdtslineSesAddr OBJECT-TYPE
                   SYNTAX  IpAddress
                   ACCESS  read-only
                   STATUS  mandatory
                   DESCRIPTION
                           "Remote host address of session. [What about
                           PAD connections?]"
                   ::= { bdltsLineSessionEntry 3 }

               bdtslineSesName OBJECT-TYPE
                   SYNTAX  DisplayString
                   ACCESS  read-only
                   STATUS  mandatory
                   DESCRIPTION
                           "Remote host name of session."
                   ::= { bdltsLineSessionEntry 4 }

               bdtslineSesCur OBJECT-TYPE
                   SYNTAX  INTEGER
                   ACCESS  read-only
                   STATUS  mandatory
                   DESCRIPTION
                           "Boolean whether session is the currently
                           active one."
                   ::= { bdltsLineSessionEntry 5 }

               bdtslineSesIdle OBJECT-TYPE
                   SYNTAX  INTEGER
                   ACCESS  read-only
                   STATUS  mandatory
                   DESCRIPTION
                           "Time in seconds session has been idle."
                   ::= { bdltsLineSessionEntry 6 }

               bdtslineSesLine OBJECT-TYPE
                   SYNTAX  INTEGER
                   ACCESS  read-only
                   STATUS  mandatory
                   DESCRIPTION
                           "Table index 1."
                   ::= { bdltsLineSessionEntry 7 }

               bdtslineSesSession OBJECT-TYPE
                   SYNTAX  INTEGER
                   ACCESS  read-only
                   STATUS  mandatory
                   DESCRIPTION
                           "Table index 2."
                   ::= { bdltsLineSessionEntry 8 }

               -- End of table


               bdtsMsgTtyLine OBJECT-TYPE
                   SYNTAX  INTEGER
                   ACCESS  read-write
                   STATUS  mandatory
                   DESCRIPTION
                           "tty line to send the message to. -1 will
                           send it to all tty lines"
                   ::= { bdlts 4 }

               bdtsMsgIntervaltim OBJECT-TYPE
                   SYNTAX  INTEGER
                   ACCESS  read-write
                   STATUS  mandatory
                   DESCRIPTION
                           "Interval between reissuing message in
                           milliseconds. Minimum non-zero setting is
                           10000. 0 will cause the routine to choose its
                           own intervals becoming more frequent as
                           MessageDuration gets close to expiring. 2hr,
                           1hr, 30min, 5min, 1min"
                   ::= { bdlts 5 }

               bdtsMsgDuration OBJECT-TYPE
                   SYNTAX  INTEGER
                   ACCESS  read-write
                   STATUS  mandatory
                   DESCRIPTION
                           "Length of time to reissue message in
                           milliseconds. Minimum non-zero setting is
                           10000. A setting of 0 will not repeat the
                           message."
                   ::= { bdlts 6 }

               bdtsMsgText OBJECT-TYPE
                   SYNTAX  DisplayString
                   ACCESS  read-write
                   STATUS  mandatory
                   DESCRIPTION
                           "Up to 256 characters that will make up the
                           message"
                   ::= { bdlts 7 }

               bdtsMsgTmpBanner OBJECT-TYPE
                   SYNTAX  INTEGER {
                        no(1),
                        additive(2)
                   }
                   ACCESS  read-write
                   STATUS  mandatory
                   DESCRIPTION
                           "Should the message be used as a temporary
                           banner. 1 - No. 2 - In addition to the normal
                           banner"
                   ::= { bdlts 8 }

               bdtsMsgSend OBJECT-TYPE
                   SYNTAX  INTEGER {
                        nothing(1),
                        reload(2),
                        messagedone(3),
                        abort(4)
                   }
                   ACCESS  read-write
                   STATUS  mandatory
                   DESCRIPTION
                           "Sends the message. The value determines what
                           to do after the message has completed."
                   ::= { bdlts 9 }

               bdtsClrTtyLine OBJECT-TYPE
                   SYNTAX  INTEGER
                   ACCESS  read-write
                   STATUS  mandatory
                   DESCRIPTION
                           "tty line to clear.  Read returns the last line
                           cleared.  A value of -1 indicates no lines have 
                           been cleared."
                   ::= { bdlts 10 }

END
