LUMINOUS-TC-MIB DEFINITIONS ::= BEGIN
    IMPORTS
	TEXTUAL-CONVENTION FROM SNMPv2-TC
             MODULE-IDENTITY, OBJECT-TYPE, NOTIFICATION-TYPE,
             ObjectName, Integer32, Counter32, Unsigned32
                                    FROM SNMPv2-SMI
DisplayString FROM RFC1213-MIB
			enterprises FROM RFC1155-SMI;
                

  -- IANA-registered  Luminous Network Enterprise Number of 4614

     luminous OBJECT IDENTIFIER ::= { enterprises 4614}

  -- leaving tree-space for the future products:

     lumADM   OBJECT IDENTIFIER ::= { luminous 1}


  --  This MIB module defines Shelf and Card groups.

     lumTcMIB  MODULE-IDENTITY      
        LAST-UPDATED "0106270000Z"
        ORGANIZATION "Luminous Networks"
        CONTACT-INFO 
                        "  Luminous Technical Support

                        Postal: Luminous Networks,
                                14060 Bubb Road,
                                Cupertino, CA 95014

                        Tel: +1 408 342 6400
                        Fax: +1 408 863 1100
                        E-mail: support@luminous.com"
        DESCRIPTION  "The Luminous TC MIB contains        
                    textual conventions for use in
                    Luminous Networks MIBs."
        ::= { lumADM 9 }

--
-- Textual Conventions
-- 

    LumShelfType ::= TEXTUAL-CONVENTION
        STATUS  current
        DESCRIPTION  "Type of chassis."
        SYNTAX  INTEGER { 
                        mSeries(1),
                        unused1(2),
                        unused2(3),
                        cSeries(4)
                        }
 
    LumChassisPlane ::= TEXTUAL-CONVENTION
        STATUS  current
        DESCRIPTION  "Which plane in the chassis."
        SYNTAX  INTEGER { 
                        front (1),
                        back  (2)
                        }
 
    LumSlotNum ::= TEXTUAL-CONVENTION
        STATUS  current
        DESCRIPTION  "Number of a slot within a chassis plane.
                        Note that 0 is not a valid slot and means unknown."
        SYNTAX  Integer32 (0..32)

    LumPortNum ::= TEXTUAL-CONVENTION
        STATUS  current
        DESCRIPTION  "Number of a port within a card..
                            Note that 0 is not a valid port and means unknown."
        SYNTAX  Integer32 (0..32)

    LumSimpleIndex::= TEXTUAL-CONVENTION
        STATUS       current
        DESCRIPTION "Simple abstract integer index for a table."
        SYNTAX  Integer32 (1..65535)

    LumPercent ::= TEXTUAL-CONVENTION
        STATUS       current
        DESCRIPTION "A percentage value."
        SYNTAX      Unsigned32(0..100)

    LumRingDirection ::= TEXTUAL-CONVENTION
        STATUS       current
        DESCRIPTION "Direction of a service of link from the ring point of view."
        SYNTAX      INTEGER {
                            none(1),  
                            west(2),
                            east(3)
                            }

    LumAdminStatus ::= TEXTUAL-CONVENTION
        STATUS       current
        DESCRIPTION "Administrative Status of an entity."
        SYNTAX    INTEGER {
                            up(1),  
                            down(2)
                            }

    LumOperStatus ::= TEXTUAL-CONVENTION
        STATUS       current
        DESCRIPTION "Operational Status of an entity. This is
                        based on IF-MIB ifOperStatus with the addition
                        of misMatch."
        SYNTAX    INTEGER {
                            up(1),              -- ready to pass packets
                            down(2),
                            testing(3),         -- in some test mode
                            unknown(4),         -- status can not be determined
                                                -- for some reason.
                            dormant(5),
                            notPresent(6),      -- some component is missing
                            lowerLayerDown(7),  -- down due to state of
                                                -- lower-layer interface(s)
                            misMatch(8)         -- incorrect plugin component
                            }

    LumControl ::= TEXTUAL-CONVENTION
        STATUS       current
        DESCRIPTION "Control of an entity."
        SYNTAX      INTEGER {
                            unknown(1),  
                            disabled(2),
                            enabled(3)
                            }

    LumServiceMode ::= TEXTUAL-CONVENTION
        STATUS       current
        DESCRIPTION "Service type for a port."
        SYNTAX      INTEGER {
                            none(1),  
                            wire(2),
                            routing(3),
                            policyForwarding(4)
                            }

    LumPortType ::= TEXTUAL-CONVENTION
        STATUS       current
        DESCRIPTION "What type of entity is this port."
        SYNTAX      INTEGER {
                            none(1),  
                            physical(2),
                            subPortDemux(3)
                            }

    LumPortCreateType ::= TEXTUAL-CONVENTION
        STATUS       current
        DESCRIPTION "Was this port created explicitly or implicitly
                    (e.g. chen channelizing a DS3, subports for DS1
                    are implicitly created."
        SYNTAX      INTEGER {
                            implicit(1),  
                            explicit(2)
                            }

    LumPortDemuxType ::= TEXTUAL-CONVENTION
        STATUS       current
        DESCRIPTION "What type of entity is this demux port."
        SYNTAX      INTEGER {
                            none(1),  
                            vlan(2),
                            mplsTag(3),
                            tdmChannel(4)
                            }

    LumPortDemuxId ::= TEXTUAL-CONVENTION
        STATUS       current
        DESCRIPTION "The substream identifier for this demux port."
        SYNTAX      Unsigned32(0..65535)

    LumConnectorType ::= TEXTUAL-CONVENTION
        STATUS       current
        DESCRIPTION "Connector type for a physical port."
        SYNTAX      INTEGER {
                            none(1),  
                            rj45(2),
                            scFiber(3),
                            miniCoax(4),
                            db9(5),
                            sjFiber(6),
                            stFiber(7)
                            }

    LumSignalState ::= TEXTUAL-CONVENTION
        STATUS       current
        DESCRIPTION "State of a hardware signal."
        SYNTAX      INTEGER {
                            idle(1),  
                            active(2)
                            }

    LumName ::= TEXTUAL-CONVENTION
        STATUS       current
        DESCRIPTION "Name of an entity. This should not
                        include white space characters."
        SYNTAX      DisplayString (SIZE(1..40))

    LumDescr ::= TEXTUAL-CONVENTION
        STATUS       current
        DESCRIPTION "Description of an entity."
        SYNTAX      DisplayString (SIZE(1..80))

    LumVersionString ::= TEXTUAL-CONVENTION
        STATUS       current
        DESCRIPTION "Version of an entity. "
        SYNTAX      DisplayString (SIZE(1..20))
    
    LumSerialNumString ::= TEXTUAL-CONVENTION
        STATUS       current
        DESCRIPTION "Serial number of an entity. "
        SYNTAX      DisplayString (SIZE(1..21))

    LumCleiString ::= TEXTUAL-CONVENTION
        STATUS       current
        DESCRIPTION "CLEI code of an entity. "
        SYNTAX      DisplayString (SIZE(1..17))

    LumManufactureString ::= TEXTUAL-CONVENTION
        STATUS       current
        DESCRIPTION "Manufacture date of an entity. "
        SYNTAX      DisplayString (SIZE(1..20))

    LumDateTimeString ::= TEXTUAL-CONVENTION
        STATUS       current
        DESCRIPTION "Date and Time."
        SYNTAX      DisplayString (SIZE(24))

    LumCardBaseType ::= TEXTUAL-CONVENTION
        STATUS       current
        DESCRIPTION "The base type of a card."
        SYNTAX      INTEGER {
                            none(1),
                            sysCon (2),
                            ring(3),
                            t1(4),
                            ether(5),
                            alarm(6),
                            upLink(7),
                            ringIO(8),
                            t1IO(9),
                            etherIO(10),
                            utility(11),
                            oc12(12),
                            oc12IO(13),
                            gigE(14),
                            gigEIO(15),
                            oc12IOAlarm(16),
                            etherFXIO(17),
                            wdm(18),
                            wdmIO(19),
                            ringIOLR(21),
                            ring2(22),
                            ring2IO(23),
                            ds3cc12(28),
                            ds3cc12IO(29),
                            ether24(32),
                            ether24IO(33),
                            asi(34),
                            asiIOIn(35),
                            asiIOOut(36),
                            present(38)
                            }

    LumCardType ::= TEXTUAL-CONVENTION
        STATUS       current
        DESCRIPTION "The specific type of a card."
        SYNTAX      INTEGER {
                            none(1),
                            sysCon (2),
                            ring(3),
                            t1(4),
                            ether(5),
                            alarm(6),
                            upLink(7),
                            ringIO(8),
                            t1IO(9),
                            etherIO(10),
                            utility(11),
                            oc12(12),
                            oc12IO(13),
                            gigE(14),
                            gigEIO(15),
                            oc12IOAlarm(16),
                            etherFXIO(17),
                            wdm(18),
                            wdmIO(19),
                            sysconR(20),
                            ringIOLR(21),
                            ring2(22),
                            ring2IO(23),
                            wdmBand1(24),
                            wdmBand2(25),
                            wdmBand3(26),
                            wdmBand4(27),
                            ds3cc12(28),
                            ds3cc12IO(29),
                            t3cc12(30),
                            e3cc12(31),
                            ether24(32),
                            ether24IO(33),
                            asi(34),
                            asiIOIn(35),
                            asiIOOut(36),
                            gigERouting(37),
                            present(38),
                            sysconU(39),
                            newCardType(40)                             
                            }

    LumCardAdminState ::= TEXTUAL-CONVENTION
        STATUS       current
        DESCRIPTION "The admininstrative state of a card.
                     This indicates the state transition
                        desired by the management. 
                        The actual success of transition is shown 
                        in the card operationla state.

                        active(2) - request to set a card in an
                                    active but not backed up state.
                        standby(3)- request to set a card to a
                                    standby state.
                        outOfService(4) -
                                    request to set a card to 
                                    OutOfService state, where it
                                    should respond to the 
                                    management requests but not
                                    support any traffic activity.
                        shutDown(5)-request to shut the card down
                                    completely. Deprecated. 
                        reset(6)   -request to reset the card.
                        switchover(7)- 
                                    request to replace this card,
                                    currently in lumCardOperState
                                    of active(7) with the card
                                    currently in lumCardOperState
                                    of standby(3) which slot is
                                    referenced with lumStandbySlot.
                                    On success, lumCardOperState
                                    of this card should transition
                                    to outOfService(4)."

        SYNTAX      INTEGER {
                            none(1),         
                            active(2),
                            standby(3),
                            outOfService(4),
                            shutDown(5),
                            reset(6),
                            switchover(7)                             
                            }

    LumCardOperState ::= TEXTUAL-CONVENTION
        STATUS       current
        DESCRIPTION "The operational state of a card.
                        The Operational State indicates the
                        current state of the card. It can be
                        either the result of some administrative
                        management action or internal card
                        activity.
                           
                        none(1)     -   indicates that there
                                        is no card in the slot  
                        active (2)  -   means working fine, but not
                                        backed up
                        standby(3)  -   means backing up other
                                        active(2) cards in case
                                        of a failure or management
                                        switchover requests
                        outOfService(4) - a state where the card
                                        should respond to the
                                        management requests but not
                                        support any traffic activity.
                        failure(5)  -   cannot function properly but
                                        still can respond to 
                                        management requests. 
                        down(6)     -   card in the slot can't even
                                        respond to the management
                                        request.
                        present(7)  -   card is present in the slot
                                        and not yet identified.
                        initializing(8)-card is present in the slot
                                        and is initializing."
            SYNTAX      INTEGER {
                            none(1),  
                            active (2),
                            standby(3),
                            outOfService(4), 
                            failure(5),
                            down(6),
                            present(7),
                            initializing(8)
                            }

    LumCardFailureState ::= TEXTUAL-CONVENTION
        STATUS       current
        DESCRIPTION "The failure state of a card.
                        This is usually none(1), unless
                        card operational state is equal to failure(5).
                           
                        Even if card operational state is equal to
                        failure(5), still, this can be
                        none(1), simply indicating that no
                        information about this failure state
                        is available.
 
                        Otherwise criticalFault(2) indicates that
                        the card cannot perform one of it's
                        required functions properly. The management
                        action is recommended (can be even reset
                        or, if mulfunctioning, be replace) to 
                        correct the problem. Otherwise the problem
                        will persist.

                        minorFault(3) indicates that a fault has
                        occured but does not persist. The action
                        from the management may not beneeded.

                        minorAlarm(4) indicates that no action is
                        needed."
            SYNTAX      INTEGER {
                            none (1),
                            criticalFault(2),
                            minorFault(3),
                            minorAlarm(4)
                            }

    LumOpticalWaveLength ::= TEXTUAL-CONVENTION
        STATUS  current
        DESCRIPTION  "The wavelength in nano-meters of an optical interface."
        SYNTAX  Integer32 (1..65535)

    LumOpticalFiberType ::= TEXTUAL-CONVENTION
        STATUS       current
        DESCRIPTION "The fiber type used by an optical interface."
        SYNTAX      INTEGER {
                            unknown(1),  
                            singleMode(2),
                            multiMode(3)
                            }

    LumOpticalMaxLength ::= TEXTUAL-CONVENTION
        STATUS  current
        DESCRIPTION  "The maximum fiber length in meters of an optical interface."
        SYNTAX  Integer32 (1..1000000)

    LumOpticalConnector ::= TEXTUAL-CONVENTION
        STATUS       current
        DESCRIPTION "The connector type used by an optical interface."
        SYNTAX      INTEGER {
                            unknown(1),  
                            sc(2),
                            lc(3)
                            }

    LumOpticalServiceSupport ::= TEXTUAL-CONVENTION
        STATUS       current
        DESCRIPTION "The service types supported by an optical interface."
        SYNTAX      BITS     {
                            gigE1(0),
                            gigE2(1),
                            fiberChannel1(2),
                            fiberChannel2(3),
                            oc12(4),
                            oc24(5),
                            oc48(6),
                            rpt(7),
                            rptE2(8),
                            oc3(9)
                            }

    LumOpticalService ::= TEXTUAL-CONVENTION
        STATUS       current
        DESCRIPTION "The service type active on an optical interface."
        SYNTAX      INTEGER {
                            none(1),  
                            gigE1(2),
                            gigE2(3),
                            fiberChannel1(4),
                            fiberChannel2(5),
                            oc12(6),
                            oc24(7),
                            oc48(8),
                            rpt(9),
                            rptE2(10),
                            oc3(11)
                            }

    LumTdmType ::= TEXTUAL-CONVENTION
        STATUS       current
        DESCRIPTION "The TDM port or connection type."
        SYNTAX      INTEGER {
                            unknown(1),  
                            t1(2),
                            e1(3),
                            t3(4),
                            e3(5)
                            }

    LumImageState ::= TEXTUAL-CONVENTION
        STATUS       current
        DESCRIPTION "The state of a program image in NVRAM."
        SYNTAX      INTEGER {
                        empty(1),       -- no image
                        trial(2),       -- trial copy
                        tried(3),       -- tried copy
                        accepted(4),    -- accept copy. always boot
                                        -- the latest accepted copy if
                                        -- no trial
                        unknown(5)
                        }

    LumAlarmSeverity ::= TEXTUAL-CONVENTION
        STATUS       current
        DESCRIPTION "The severity of an alarm of group of alarms."
        SYNTAX      INTEGER {
                        undefined(1),
                        critical(2),
                        major(3),
                        minor(4),
                        notAlarmed(5),
                        notReported(6)
                        }

    LumResetCmd ::= TEXTUAL-CONVENTION
        STATUS       current
        DESCRIPTION "Reset command for an entity."
        SYNTAX      INTEGER {
                        none(1),
                        reset(2)
                        }
    
END
