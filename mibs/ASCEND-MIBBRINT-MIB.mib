--			Ascend mibbrint MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBBRINT-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibbRIHostProfile  OBJECT IDENTIFIER ::= { configuration 62}

	-- The mibbRIHostProfile table
	--
	-- This table contains parameters for the mibbRIHostProfile profile
	--

    mibbRIHostProfileTable	OBJECT-TYPE
	SYNTAX		SEQUENCE OF MibbRIHostProfileEntry
	ACCESS		not-accessible
	STATUS		mandatory
	DESCRIPTION	"A list of mibbRIHostProfile profile entries."
	::= { mibbRIHostProfile 1 }

    mibbRIHostProfileEntry	OBJECT-TYPE
	SYNTAX		MibbRIHostProfileEntry
	ACCESS		not-accessible
	STATUS		mandatory
	DESCRIPTION	"A mibbRIHostProfile entry containing objects that
			 maps to the parameters of mibbRIHostProfile profile."
	INDEX		{ bRIHostProfile-Shelf-o, bRIHostProfile-Slot-o, bRIHostProfile-Item-o }
	::= { mibbRIHostProfileTable 1 }

    MibbRIHostProfileEntry ::=
	SEQUENCE {
	    bRIHostProfile-Shelf-o
		INTEGER,
	    bRIHostProfile-Slot-o
		INTEGER,
	    bRIHostProfile-Item-o
		INTEGER,
	    bRIHostProfile-ProfileNumber
		INTEGER,
	    bRIHostProfile-Name
		DisplayString,
	    bRIHostProfile-PhysicalAddress-Shelf
		INTEGER,
	    bRIHostProfile-PhysicalAddress-Slot
		INTEGER,
	    bRIHostProfile-PhysicalAddress-ItemNumber
		INTEGER,
	    bRIHostProfile-SwitchType
		INTEGER,
	    bRIHostProfile-DownStreamPriority
		INTEGER,
	    bRIHostProfile-DownStreamBriWan
		INTEGER,
	    bRIHostProfile-Action-o
		INTEGER
	}

    bRIHostProfile-Shelf-o	OBJECT-TYPE
	SYNTAX	INTEGER
	ACCESS	read-only
	STATUS	mandatory
	DESCRIPTION	""
	::= { mibbRIHostProfileEntry 1 }

    bRIHostProfile-Slot-o	OBJECT-TYPE
	SYNTAX	INTEGER
	ACCESS	read-only
	STATUS	mandatory
	DESCRIPTION	""
	::= { mibbRIHostProfileEntry 2 }

    bRIHostProfile-Item-o	OBJECT-TYPE
	SYNTAX	INTEGER
	ACCESS	read-only
	STATUS	mandatory
	DESCRIPTION	""
	::= { mibbRIHostProfileEntry 3 }

    bRIHostProfile-ProfileNumber	OBJECT-TYPE
	SYNTAX	INTEGER
	ACCESS	read-write
	STATUS	mandatory
	DESCRIPTION	"If it is a stored profile, the number of the profile (1..MAX_NETWORK_PROFILES). If it is the current profile, the number of the stored profile from which it was loaded, or zero if it has never been loaded."
	::= { mibbRIHostProfileEntry 4 }

    bRIHostProfile-Name	OBJECT-TYPE
	SYNTAX	DisplayString
	ACCESS	read-write
	STATUS	mandatory
	DESCRIPTION	"The null terminated ascii string that the user gave to this particular profile."
	::= { mibbRIHostProfileEntry 5 }

    bRIHostProfile-PhysicalAddress-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { mibbRIHostProfileEntry 6 }

    bRIHostProfile-PhysicalAddress-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { mibbRIHostProfileEntry 7 }

    bRIHostProfile-PhysicalAddress-ItemNumber	OBJECT-TYPE
	SYNTAX	INTEGER
	ACCESS	read-write
	STATUS	mandatory
	DESCRIPTION	"A number that specifies an addressable entity within the context of shelf and slot."
	::= { mibbRIHostProfileEntry 8 }

    bRIHostProfile-SwitchType	OBJECT-TYPE
	SYNTAX	INTEGER {
		    attPri (1),
		    ntiPri (2),
		    globandPri (3),
		    japanPri (4),
		    vn3Pri (5),
		    onetr6Pri (6),
		    net5Pri (7),
		    danishPri (8),
		    australPri (9),
		    natIsdn2Pri (10),
		    taiwanPri (31),
		    isdxDpnss (11),
		    islxDpnss (12),
		    mercuryDpnss (13),
		    dass2 (14),
		    btSs7 (32),
		    unknownBri (15),
		    att5essBri (16),
		    dms100Nt1Bri (17),
		    nisdn1Bri (18),
		    vn2Bri (19),
		    btnr191Bri (20),
		    net3Bri (21),
		    ptpNet3Bri (22),
		    kddBri (23),
		    belgianBri (24),
		    australBri (25),
		    swissBri (26),
		    german1tr6Bri (27),
		    dutch1tr6Bri (28),
		    switchCas (29),
		    idslPtpBri (30)
		}
	ACCESS	read-write
	STATUS	mandatory
	DESCRIPTION	"Switch type to be emulated."
	::= { mibbRIHostProfileEntry 9 }

    bRIHostProfile-DownStreamPriority	OBJECT-TYPE
	SYNTAX	INTEGER {
		    no (1),
		    yes (2)
		}
	ACCESS	read-write
	STATUS	mandatory
	DESCRIPTION	"Boolean that is TRUE to force a B channel data call to be cleared if an incoming or outgoing DownStream call is being requested."
	::= { mibbRIHostProfileEntry 10 }

    bRIHostProfile-DownStreamBriWan	OBJECT-TYPE
	SYNTAX	INTEGER {
		    aatNone (1),
		    aatOne (2),
		    aatTwo (3)
		}
	ACCESS	read-write
	STATUS	mandatory
	DESCRIPTION	"Parameters for setting up additional abstract terminals for DownStream BRI port."
	::= { mibbRIHostProfileEntry 11 }

    bRIHostProfile-Action-o	OBJECT-TYPE
	SYNTAX	INTEGER {
		    noAction (1),
		    createProfile (2),
		    deleteProfile (3)
		}
	ACCESS	read-write
	STATUS	mandatory
	DESCRIPTION	""
	::= { mibbRIHostProfileEntry 12 }


	-- The mibbRIHostProfile__line_interface table
	--
	-- This table contains parameters for the mibbRIHostProfile__line_interface profile
	--

    mibbRIHostProfile-LineInterfaceTable	OBJECT-TYPE
	SYNTAX		SEQUENCE OF MibbRIHostProfile-LineInterfaceEntry
	ACCESS		not-accessible
	STATUS		mandatory
	DESCRIPTION	"A list of mibbRIHostProfile__line_interface profile entries."
	::= { mibbRIHostProfile 2 }

    mibbRIHostProfile-LineInterfaceEntry	OBJECT-TYPE
	SYNTAX		MibbRIHostProfile-LineInterfaceEntry
	ACCESS		not-accessible
	STATUS		mandatory
	DESCRIPTION	"A mibbRIHostProfile__line_interface entry containing objects that
			 maps to the parameters of mibbRIHostProfile__line_interface profile."
	INDEX		{ bRIHostProfile-LineInterface-Shelf-o, bRIHostProfile-LineInterface-Slot-o, bRIHostProfile-LineInterface-Item-o, bRIHostProfile-LineInterface-Index-o }
	::= { mibbRIHostProfile-LineInterfaceTable 1 }

    MibbRIHostProfile-LineInterfaceEntry ::=
	SEQUENCE {
	    bRIHostProfile-LineInterface-Shelf-o
		INTEGER,
	    bRIHostProfile-LineInterface-Slot-o
		INTEGER,
	    bRIHostProfile-LineInterface-Item-o
		INTEGER,
	    bRIHostProfile-LineInterface-Index-o
		INTEGER,
	    bRIHostProfile-LineInterface-LineEnabled
		INTEGER,
	    bRIHostProfile-LineInterface-DialPlan
		INTEGER,
	    bRIHostProfile-LineInterface-AnswerNumber1
		DisplayString,
	    bRIHostProfile-LineInterface-AnswerNumber2
		DisplayString
	}

    bRIHostProfile-LineInterface-Shelf-o	OBJECT-TYPE
	SYNTAX	INTEGER
	ACCESS	read-only
	STATUS	mandatory
	DESCRIPTION	""
	::= { mibbRIHostProfile-LineInterfaceEntry 1 }

    bRIHostProfile-LineInterface-Slot-o	OBJECT-TYPE
	SYNTAX	INTEGER
	ACCESS	read-only
	STATUS	mandatory
	DESCRIPTION	""
	::= { mibbRIHostProfile-LineInterfaceEntry 2 }

    bRIHostProfile-LineInterface-Item-o	OBJECT-TYPE
	SYNTAX	INTEGER
	ACCESS	read-only
	STATUS	mandatory
	DESCRIPTION	""
	::= { mibbRIHostProfile-LineInterfaceEntry 3 }

    bRIHostProfile-LineInterface-Index-o	OBJECT-TYPE
	SYNTAX	INTEGER
	ACCESS	read-only
	STATUS	mandatory
	DESCRIPTION	""
	::= { mibbRIHostProfile-LineInterfaceEntry 4 }

    bRIHostProfile-LineInterface-LineEnabled	OBJECT-TYPE
	SYNTAX	INTEGER {
		    no (1),
		    yes (2)
		}
	ACCESS	read-write
	STATUS	mandatory
	DESCRIPTION	"Boolean that is TRUE if this interface is part of the set used for this network set, or FALSE otherwise."
	::= { mibbRIHostProfile-LineInterfaceEntry 5 }

    bRIHostProfile-LineInterface-DialPlan	OBJECT-TYPE
	SYNTAX	INTEGER
	ACCESS	read-write
	STATUS	mandatory
	DESCRIPTION	"Whether we are using the trunk-group-only or extended-dial plan."
	::= { mibbRIHostProfile-LineInterfaceEntry 6 }

    bRIHostProfile-LineInterface-AnswerNumber1	OBJECT-TYPE
	SYNTAX	DisplayString
	ACCESS	read-write
	STATUS	mandatory
	DESCRIPTION	"Phone numbers to match when routing by incoming phone number."
	::= { mibbRIHostProfile-LineInterfaceEntry 7 }

    bRIHostProfile-LineInterface-AnswerNumber2	OBJECT-TYPE
	SYNTAX	DisplayString
	ACCESS	read-write
	STATUS	mandatory
	DESCRIPTION	"Phone numbers to match when routing by incoming phone number."
	::= { mibbRIHostProfile-LineInterfaceEntry 8 }


	-- The mibbRIHostProfile__line_interface__down_stream_llink table
	--
	-- This table contains parameters for the mibbRIHostProfile__line_interface__down_stream_llink profile
	--

    mibbRIHostProfile-LineInterface-DownStreamLlinkTable	OBJECT-TYPE
	SYNTAX		SEQUENCE OF MibbRIHostProfile-LineInterface-DownStreamLlinkEntry
	ACCESS		not-accessible
	STATUS		mandatory
	DESCRIPTION	"A list of mibbRIHostProfile__line_interface__down_stream_llink profile entries."
	::= { mibbRIHostProfile 3 }

    mibbRIHostProfile-LineInterface-DownStreamLlinkEntry	OBJECT-TYPE
	SYNTAX		MibbRIHostProfile-LineInterface-DownStreamLlinkEntry
	ACCESS		not-accessible
	STATUS		mandatory
	DESCRIPTION	"A mibbRIHostProfile__line_interface__down_stream_llink entry containing objects that
			 maps to the parameters of mibbRIHostProfile__line_interface__down_stream_llink profile."
	INDEX		{ bRIHostProfile-LineInterface-DownStreamLlink-Shelf-o, bRIHostProfile-LineInterface-DownStreamLlink-Slot-o, bRIHostProfile-LineInterface-DownStreamLlink-Item-o, bRIHostProfile-LineInterface-DownStreamLlink-Index-o, bRIHostProfile-LineInterface-DownStreamLlink-Index1-o }
	::= { mibbRIHostProfile-LineInterface-DownStreamLlinkTable 1 }

    MibbRIHostProfile-LineInterface-DownStreamLlinkEntry ::=
	SEQUENCE {
	    bRIHostProfile-LineInterface-DownStreamLlink-Shelf-o
		INTEGER,
	    bRIHostProfile-LineInterface-DownStreamLlink-Slot-o
		INTEGER,
	    bRIHostProfile-LineInterface-DownStreamLlink-Item-o
		INTEGER,
	    bRIHostProfile-LineInterface-DownStreamLlink-Index-o
		INTEGER,
	    bRIHostProfile-LineInterface-DownStreamLlink-Index1-o
		INTEGER
	}

    bRIHostProfile-LineInterface-DownStreamLlink-Shelf-o	OBJECT-TYPE
	SYNTAX	INTEGER
	ACCESS	read-only
	STATUS	mandatory
	DESCRIPTION	""
	::= { mibbRIHostProfile-LineInterface-DownStreamLlinkEntry 1 }

    bRIHostProfile-LineInterface-DownStreamLlink-Slot-o	OBJECT-TYPE
	SYNTAX	INTEGER
	ACCESS	read-only
	STATUS	mandatory
	DESCRIPTION	""
	::= { mibbRIHostProfile-LineInterface-DownStreamLlinkEntry 2 }

    bRIHostProfile-LineInterface-DownStreamLlink-Item-o	OBJECT-TYPE
	SYNTAX	INTEGER
	ACCESS	read-only
	STATUS	mandatory
	DESCRIPTION	""
	::= { mibbRIHostProfile-LineInterface-DownStreamLlinkEntry 3 }

    bRIHostProfile-LineInterface-DownStreamLlink-Index-o	OBJECT-TYPE
	SYNTAX	INTEGER
	ACCESS	read-only
	STATUS	mandatory
	DESCRIPTION	""
	::= { mibbRIHostProfile-LineInterface-DownStreamLlinkEntry 4 }

    bRIHostProfile-LineInterface-DownStreamLlink-Index1-o	OBJECT-TYPE
	SYNTAX	INTEGER
	ACCESS	read-only
	STATUS	mandatory
	DESCRIPTION	""
	::= { mibbRIHostProfile-LineInterface-DownStreamLlinkEntry 5 }

END
