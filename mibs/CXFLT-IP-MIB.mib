-- Filtering and priority information for IP router.

CXFLT-IP-MIB DEFINITIONS ::= BEGIN

    IMPORTS
        IpAddress
            FROM RFC1155-SMI
        OBJECT-TYPE                     
            FROM RFC-1212
        cxFltIp               
            FROM CXProduct-SMI;


      cxFltIpAddrTable OBJECT-TYPE
        SYNTAX  SEQUENCE OF CxFltIpAddrEntry
        ACCESS  not-accessible
        STATUS  mandatory
        DESCRIPTION 
"The Ip Frame Filtering and Forwarding (FF) Address Table 
(shortcut: fltiptbl) allows you to enable/disable routing and to select 
forwarding priorities for specific IP addresses.  The table has a maximum
of 32 entries.  Table entries take effect only after a warm start
(sysmgt restart=1).

A packet's addressing information is analyzed and compared with the entry 
in the FF table and the routing module filters it or forwards it with the
specified priority.  If there is no FF information for the given address,
it will be forwarded with normal priority.

Using the FF functionality, you can restrict the amount of IP traffic being 
routed or you can prioritize the traffic according to urgency."

          ::= { cxFltIp 1 }


      cxFltIpAddrEntry OBJECT-TYPE
          SYNTAX  CxFltIpAddrEntry
          ACCESS  not-accessible
          STATUS  mandatory
          DESCRIPTION
"Provides filtering/forwarding information for a specific IP address."

          INDEX   { cxFltIpIndex }
          ::= { cxFltIpAddrTable 1 }

      CxFltIpAddrEntry ::=
          SEQUENCE {
          cxFltIpIndex
            INTEGER,        
          cxFltIpSrcAddr
              IpAddress,
           cxFltIpSrcNetMask
              IpAddress,
           cxFltIpDstAddr
              IpAddress,
           cxFltIpDstNetMask
              IpAddress,
           cxFltIpParameter
            INTEGER,        
           cxFltIpRowStatus
            INTEGER,
           cxFltIpProtType
            INTEGER,
           cxFltIpProtPortNum
            INTEGER
    
          }

      cxFltIpIndex  OBJECT-TYPE
          SYNTAX  INTEGER (1..65535)
          ACCESS  read-write
          STATUS  mandatory
          DESCRIPTION 
"Indexes the table entries.  This number provides access to all the 
filtering/forwarding information for a given source address and its 
associated destination address.  

Range of Values: 1 - 65535

Default Value: None

Configuration Changed: Administrative"

     ::= { cxFltIpAddrEntry 1 }
     
      cxFltIpSrcAddr OBJECT-TYPE
          SYNTAX  IpAddress
          ACCESS  read-write
          STATUS  mandatory
          DESCRIPTION
"Identifies the source IP address used for filtering/forwarding. This 
address corresponds to a destination address in 'cxFltIpDstAddr'. 
CxFltIpParameter determines whether data is filtered or forwarded from the
source address to the destination address.

Range of Values: 4 integers, each from 0 to 225

Default Value: None

Configuration Changed: Administrative"

          ::= { cxFltIpAddrEntry 2 }


      cxFltIpSrcNetMask OBJECT-TYPE
          SYNTAX  IpAddress
          ACCESS  read-write
          STATUS  mandatory
          DESCRIPTION
"Identifies the subnet mask associated with the source IP address. The mask
determines which part of the IP address identifies to the network and which
part identifies the host.

Range of Values: 4 integers, with the parts identifying the network set to
255 and the parts identifying the host set to 0.

Default Value: None

Configuration Changed: Administrative"

          ::= { cxFltIpAddrEntry 3 }


      cxFltIpDstAddr OBJECT-TYPE
          SYNTAX  IpAddress
          ACCESS  read-write
          STATUS  mandatory
          DESCRIPTION
"Identifies the destination IP address. This address corresponds to a
source address in cxFltIpSrcAddr. CxFltIpParameter determines whether data
is filtered or forwarded from the source address to this destination
address.

Range of Values: 4 integers, each from 0 to 255

Default Value: None

Configuration Changed: Administrative"

          ::= { cxFltIpAddrEntry 4 }


      cxFltIpDstNetMask OBJECT-TYPE
          SYNTAX  IpAddress
          ACCESS  read-write
          STATUS  mandatory
          DESCRIPTION
"Identifies the subnet mask associated with the source IP address. The mask
determines which part of the IP address identifies to the network and which
part identifies the host.

Range of Values:  4 integers, with the parts identifying the network set to
255 and the parts identifying the host set to 0.

Default Value: None

Configuration Changed: Administrative"

          ::= { cxFltIpAddrEntry 5 }


     cxFltIpParameter  OBJECT-TYPE
          SYNTAX  INTEGER {
                     discard(1),
                     forward(2),
                     priority-low(3),
                     priority-high(4)
                     
                  }
          ACCESS  read-write
          STATUS  mandatory
          DESCRIPTION 
"Identifies the parameter which provides filtering/forwarding action 
and priority processing for each address in the FF table.

Options:  
discard(1):  Do not forward the data.

forward(2):  Forward the data.

priority-low(3):  Forward with a low priority (Frame Relay only.)

priority-high(4):  Forward with a high priority (Frame Relay only.)
 
Default Value:  discard (1) 

Configuration Changed: Administrative"
        DEFVAL { discard }
     ::= { cxFltIpAddrEntry 6 }

    cxFltIpRowStatus  OBJECT-TYPE
          SYNTAX  INTEGER {
                     invalid(1),
                     valid(2) 
                  }
          ACCESS  read-write
          STATUS  mandatory
          DESCRIPTION 
"Allows you to control the status of the table entries.  If you change this
value to 1 (invalid), the corresponding table entry will be deleted when you 
restart and save the configuration by issuing the command 'sysmgt restart=1'.

Options:
invalid (1): Row is flagged. After next reset the values will be disabled
and the row will be deleted from the table.

valid (2): Values are enabled.

Default Value: (2)

Configuration changed: Administrative"
        DEFVAL { valid }
       ::= { cxFltIpAddrEntry 7 }


    cxFltIpProtType  OBJECT-TYPE
          SYNTAX  INTEGER (0..255)
          ACCESS  read-write
          STATUS  mandatory
          DESCRIPTION 
"Determines the Protocol ID type that will be filtered or prioritized.

Range of Values: 0 to 255  

Default Value: 0

Configuration Changed: Administrative "
        DEFVAL { 0 }
       ::= { cxFltIpAddrEntry 8 }


    cxFltIpProtPortNum  OBJECT-TYPE
          SYNTAX  INTEGER (0..65535)
          ACCESS  read-write
          STATUS  mandatory
          DESCRIPTION 
"Determines the Application Protocol to be prioritized/filtered. If the
value of cxFltIpProtType is 6 (for TCP) or 17 (for UDP) then this value
becomes effective.

Range of Values: 0 to 65,535 

Default Value: 0

Configuration Changed: Administrative"
        DEFVAL { 0 }
       ::= { cxFltIpAddrEntry 9 }

END
