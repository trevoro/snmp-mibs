XEDIA-SECURITY-MIB DEFINITIONS ::= BEGIN

IMPORTS 
    MODULE-IDENTITY, OBJECT-TYPE
        FROM SNMPv2-SMI
    DisplayString, RowStatus
        FROM SNMPv2-TC
    MODULE-COMPLIANCE, OBJECT-GROUP
        FROM SNMPv2-CONF
    xediaMibs
        FROM XEDIA-REG
    ;    

xediaSecurityMIB MODULE-IDENTITY
    LAST-UPDATED "9706262155Z" -- June 26, 1997
    ORGANIZATION "Xedia Corp."
    CONTACT-INFO
        "support@xedia.com"
    DESCRIPTION
        "This module defines objects for management of the 'Security'
        mechanism in Xedia devices.

        Security Model:

        In all cases, a top level, 'object-wide' security check is performed, 
        followed by the 'instantiated object' (particular instance or row) check, 
        if specified, followed by the security function (when appropriate),  
        followed by the required 'parent' security checks, in the same order." 
    ::= { xediaMibs 8 }

-- Top-level organization of the MIB

xsecurityObjects          OBJECT IDENTIFIER ::= { xediaSecurityMIB 1 }
xsecurityConformance      OBJECT IDENTIFIER ::= { xediaSecurityMIB 2 }

xsecurityGeneral         OBJECT IDENTIFIER ::= { xsecurityObjects 1 }
xsecurityObjectTables    OBJECT IDENTIFIER ::= { xsecurityObjects 2 }

--
-- Security Top Level Objects
--
xsecurityAdmin OBJECT-TYPE
    SYNTAX      INTEGER {
                    enabled(1),
                    disabled(2)
                }
    MAX-ACCESS  read-write
    STATUS      current
    DESCRIPTION
        "The administrative status of the 'Security mechanism' in the router. 
     The value 'enabled(1)' indicates that the appropriate security
     checks will be performed on all configured objects. The value 
     'disabled(2)' indicates that no security checks will be performed 
     on any objects."
    DEFVAL      { disabled }
    ::= { xsecurityGeneral 1 }

xsecurityParentDepth OBJECT-TYPE
    SYNTAX      INTEGER (2..32)
    MAX-ACCESS  read-write
    STATUS      current
    DESCRIPTION
        "The number of 'parent' nodes inwhich the security checks are 
     performed for any given object.  The security checks start at
     the endpoint (the actual object requested) and traverse upwards,
     checking the immediate parent node, then that parent's parent,
     etc., until the maximun number of parents is reached, or there
     are no more parents."
    DEFVAL      { 20 }
    ::= { xsecurityGeneral 2 }

xsecurityFunctionID OBJECT-TYPE
    SYNTAX      DisplayString
    MAX-ACCESS  read-write
    STATUS      current
    DESCRIPTION
        "The textual string ID used to determine a specific set of
     special customer security functions, when appropriate.  Only
     OS builds containing customized security functions will take
     advantage of this object."
    DEFVAL      { "" }
    ::= { xsecurityGeneral 3 }

xsecurityObjConfTable        OBJECT-TYPE
    SYNTAX      SEQUENCE OF XsecurityObjConfEntry
    MAX-ACCESS  not-accessible
    STATUS      current
    DESCRIPTION
            "A list of security object configuration entries.  The number 
        of entries is representative of the number of objects defined
            in the supported mib."
    ::= { xsecurityObjectTables 1 }
 
xsecurityObjConfEntry        OBJECT-TYPE
    SYNTAX      XsecurityObjConfEntry
    MAX-ACCESS  not-accessible
    STATUS      current
    DESCRIPTION
            "An entry containing additional management information
            applicable to a particular Rip2 interface."
    INDEX    { xsecurityObjID }
    ::= { xsecurityObjConfTable 1 }

XsecurityObjConfEntry ::=
    SEQUENCE {
        xsecurityObjID                   OBJECT IDENTIFIER,
        xsecurityObjName                 DisplayString,
        xsecurityObjInstance             DisplayString,
        xsecurityObjReadAdmin            INTEGER,
        xsecurityObjWriteAdmin           INTEGER,
        xsecurityObjReadFunctAdmin       INTEGER,
        xsecurityObjWriteFunctAdmin      INTEGER,
        xsecurityObjReadLevels           BIT STRING,
        xsecurityObjWriteLevels          BIT STRING,
        xsecurityObjRowStatus            RowStatus
    }

xsecurityObjID OBJECT-TYPE
    SYNTAX      OBJECT IDENTIFIER
    MAX-ACCESS  not-accessible
    STATUS      current
    DESCRIPTION
        "The Object Identifier of a known object, or a particular instance
    of the object.  Objects can be end nodes, which contain readable
    data, or they can be inner nodes which are only used to identify
    the end points.  The object ID can be secified by using the complete 
    OID of an object, with the exact OID digits making up the instance 
    portion of the object when needed.  In all cases, an 'end of ID'
    marker of decimal '999' will be used to separate the base objectID
    from the instance portion of the whole OID.

    When '.0' instance information is specified, the 'object-wide' security 
    levels of the object are modified.  But, when specific instance 
    information is specified, the security levels of a particular instance 
    are modifed.  Then,only requests with exactly matching instance 
    information are validated against the specified levels.
    
    The '.0' also indicates where the 'base' oid ends and the instance
    information (if any) begins.  This way, it is possible to identify
    high level nodes with specific instances matching lower level nodes.

    ie: ifEntry.1 --> ifEntry.999.1 filters out all instances of '1'.

        The '999' is necessary since ifEntry.1 looks exactly the same
        as ifIndex.

            1.3.6.1.2.1.2.2.1                  ifEntry
        1.3.6.1.2.1.2.2.1.1                ifIndex "
    ::= { xsecurityObjConfEntry 1 }

xsecurityObjName OBJECT-TYPE
    SYNTAX      DisplayString
    MAX-ACCESS  read-only     
    STATUS      current
    DESCRIPTION
        "The mib name of the specificed object."
    ::= { xsecurityObjConfEntry 2 }

xsecurityObjInstance OBJECT-TYPE
    SYNTAX      DisplayString
    MAX-ACCESS  read-only     
    STATUS      current
    DESCRIPTION
        "The instance portion of the specified object.  The
     OID digits are represented in a readable string format."
    ::= { xsecurityObjConfEntry 3 }

xsecurityObjReadAdmin OBJECT-TYPE
    SYNTAX      INTEGER {
                    enabled(1),
                    disabled(2)
                }
    MAX-ACCESS  read-create
    STATUS      current
    DESCRIPTION
        "The 'Read' administrative status of the 'Security mechanism' for 
     an individual object.  The value 'enabled(1)' indicates that the 
     appropriate security checks will be performed on all access to
     the spcified object.  The value 'disabled(2)' indicates that
         no security checks will be performed for the specified object, 
     although, all expected 'parent' security checks will still be
     performed."
    DEFVAL      { enabled  }
    ::= { xsecurityObjConfEntry 4 }

xsecurityObjWriteAdmin OBJECT-TYPE
    SYNTAX      INTEGER {
                    enabled(1),
                    disabled(2)
                }
    MAX-ACCESS  read-create
    STATUS      current
    DESCRIPTION
        "The 'Write' administrative status of the 'Security mechanism' for 
     an individual object.  The value 'enabled(1)' indicates that the 
     appropriate security checks will be performed on all access to
     the spcified object.  The value 'disabled(2)' indicates that
         no security checks will be performed for the specified object, 
     although, all expected 'parent' security checks will still be
     performed."
    DEFVAL      { enabled  }
    ::= { xsecurityObjConfEntry 5 }

xsecurityObjReadFunctAdmin OBJECT-TYPE
    SYNTAX      INTEGER {
                    enabled(1),
                    disabled(2)
                }
    MAX-ACCESS  read-create
    STATUS      current
    DESCRIPTION
        "The 'Read' administrative status of the 'Security Function mechanism' 
     for an individual object.  The value 'enabled(1)' indicates that the 
     appropriate security functions will be called on all access to
     the spcified object.  The value 'disabled(2)' indicates that
         no security functions will be called for the specified object."
    DEFVAL      { enabled  }
    ::= { xsecurityObjConfEntry 6 }

xsecurityObjWriteFunctAdmin OBJECT-TYPE
    SYNTAX      INTEGER {
                    enabled(1),
                    disabled(2)
                }
    MAX-ACCESS  read-create
    STATUS      current
    DESCRIPTION
        "The 'Write' administrative status of the 'Security Function mechanism' 
     for an individual object.  The value 'enabled(1)' indicates that the 
     appropriate security functions will be called on all access to
     the spcified object.  The value 'disabled(2)' indicates that
         no security functions will be called for the specified object."
    DEFVAL      { enabled  }
    ::= { xsecurityObjConfEntry 7 }

xsecurityObjReadLevels OBJECT-TYPE
    SYNTAX      BIT STRING {
                    s10(0),
                    s9(1),
                    s8(2),
                    s7(3),
                    s6(4),
                    s5(5),
                    s4(6),
                    s3(7),
                    s2(8),
                    s1(9)
                }
    MAX-ACCESS  read-create
    STATUS      current
    DESCRIPTION
        "The bit mask associated with a particular object for 'reading'
         and 'viewing'.  The levels of security indicate which community
         entries have read access to the variable.  The level matches
         the index, or entry number of the community table."
--    DEFVAL      { { s1, s2, s3, s4, s5, s6, s7, s8, s9, s10 } }
    ::= { xsecurityObjConfEntry 8 }
                            
xsecurityObjWriteLevels OBJECT-TYPE
    SYNTAX      BIT STRING {
                    s10(0),
                    s9(1),
                    s8(2),
                    s7(3),
                    s6(4),
                    s5(5),
                    s4(6),
                    s3(7),
                    s2(8),
                    s1(9)
                }
    MAX-ACCESS  read-create
    STATUS      current
    DESCRIPTION
        "The bit mask associated with a particular object for 'writinging'
         and 'setting'.  The levels of security indicate which community
         entries have read access to the variable.  The level matches
         the index, or entry number of the community table."
--    DEFVAL      { { s1, s2, s3, s4, s5, s6, s7, s8, s9, s10 } }
    ::= { xsecurityObjConfEntry 9 }
                                        

xsecurityObjRowStatus OBJECT-TYPE
    SYNTAX      RowStatus
    MAX-ACCESS  read-create
    STATUS      current
    DESCRIPTION
        "This object is used to add and remove entries from the
        table. It is important to note that the '.0' entry, which
    represents the 'object level' can not be added or deleted,
    they simply always exists.  However the 'instanciated' table
    rows can be added or deleted as necessary."
    REFERENCE
        "RFC1903: Textual Conventions for Version 2 of the Simple
        Network Management Protocol (SNMPv2)."
    ::= { xsecurityObjConfEntry 10 }

-- ****************************************************************
-- Conformance Information
-- ****************************************************************

xsecurityCompliances OBJECT IDENTIFIER ::= { xsecurityConformance 1 }
xsecurityGroups      OBJECT IDENTIFIER ::= { xsecurityConformance 2 }

--
-- Compliance Statements
--

xsecurityCompliance MODULE-COMPLIANCE
    STATUS      current
    DESCRIPTION
        "The compliance statement for all agents that support this
        MIB. A compliant agent implements all objects defined in this
        MIB."
    MODULE  -- this module
    MANDATORY-GROUPS {
        xsecurityAllGroup
    }
    ::= { xsecurityCompliances 1 }

--
-- Object Groups
--

xsecurityAllGroup OBJECT-GROUP
    OBJECTS {
        xsecurityAdmin,
        xsecurityParentDepth,
        xsecurityFunctionID,
        xsecurityObjName,
        xsecurityObjInstance,
        xsecurityObjReadAdmin,
        xsecurityObjWriteAdmin,
        xsecurityObjReadFunctAdmin,
        xsecurityObjWriteFunctAdmin,
        xsecurityObjReadLevels,
        xsecurityObjWriteLevels,
        xsecurityObjRowStatus
    }
    STATUS      current
    DESCRIPTION
        "The set of all accessible objects in this MIB."
    ::= { xsecurityGroups 1 }

END
