FILE-MIB DEFINITIONS ::= BEGIN

IMPORTS
	MODULE-IDENTITY, OBJECT-TYPE, 
	IpAddress, Integer32	FROM SNMPv2-SMI
	RowStatus			FROM SNMPv2-TC
	DisplayString                 FROM RFC1213-MIB
--	tiaraMib		FROM	TIARA-MIB;
	tiaraMgmt
		                      FROM TIARA-NETWORKS-SMI;


tiaraFileMib MODULE-IDENTITY
	LAST-UPDATED "9407272253Z" --to be corrected
	ORGANIZATION "Tiara Networks Inc."
	CONTACT-INFO
	    "       Tiara Networks
                    Customer Service

                    Postal: 525 Race Street, Suite 100,
                    San Jose, CA 95126
                    USA

                    Tel: +1 408-216-4700
                    Fax: +1 408-216-4701

                    E-mail: support@tiaranetworks.com"

	DESCRIPTION
		""
--	::= { tiaraMib 6 } 
	::= { tiaraMgmt 120 } 



-- fileTable definition
fileTable 	OBJECT-TYPE
	SYNTAX		SEQUENCE OF FileTableEntry
	MAX-ACCESS	not-accessible
	STATUS 		current
	DESCRIPTION
		"File Table"
	::= {tiaraFileMib 1}

fileTableEntry	OBJECT-TYPE
	SYNTAX			FileTableEntry
	MAX-ACCESS		not-accessible
	STATUS			current
	DESCRIPTION
		" An Entry in File Table"
	INDEX	{ fileOwnerString, fileSequenceNumber }
	::= {fileTable 1}

FileTableEntry ::= SEQUENCE {
	fileOwnerString			DisplayString,
	fileSequenceNumber	        Integer32,
	fileSrcFile                  DisplayString,
        fileDestFile             DisplayString,
        fileHostIpAddr               IpAddress,
        fileLocationOfFile              INTEGER, 
        fileSlotNumber                  INTEGER,
        fileUploadFileType                INTEGER, 
        filePerformAction             INTEGER, 
	fileActionStatus                INTEGER, 
        fileListData			DisplayString,
	fileRowStatus                RowStatus
	}

fileOwnerString	OBJECT-TYPE
	SYNTAX	DisplayString
	MAX-ACCESS not-accessible
	STATUS	current
	DESCRIPTION 
		" owner String: a unique name for identify the owner"
	::= { fileTableEntry 1}

fileSequenceNumber	OBJECT-TYPE
	SYNTAX	Integer32
	MAX-ACCESS not-accessible
	STATUS	current
	DESCRIPTION 
		" Whenever the Mgr has to create a Row. 
		  He has to provide a invalid Numeric Index (0XFFFF). 
                  This will result in appending the row to the table. 
                  When the row is created, a unique numeric Index for 
		  the row is internally generated. 
                  For querying any variable in the table for a 
                  particular row or to know number of rows exisiting in 
                  the table the Mgr can do a SNMP walk."
	::= { fileTableEntry 2}

fileSrcFile	OBJECT-TYPE
	SYNTAX	DisplayString
	MAX-ACCESS read-create
	STATUS	current
	DESCRIPTION 
		"Source File "
	::= { fileTableEntry 3}

fileDestFile	OBJECT-TYPE
	SYNTAX	DisplayString
	MAX-ACCESS	read-create
	STATUS	current
	DESCRIPTION 
		"Destnation File "
	::= { fileTableEntry 4}

fileHostIpAddr	OBJECT-TYPE
	SYNTAX	IpAddress
	MAX-ACCESS	read-create
	STATUS	current
	DESCRIPTION 
		" host Ip Address"
	::= { fileTableEntry 5}

-- BOTH HOST AND UPLOAD IP ADDRESSESS ARE CLUBBED TO ABOVE 
fileLocationOfFile	OBJECT-TYPE
	SYNTAX INTEGER {
		ic(1),
		ncm(2),
		none(3)
		}
	MAX-ACCESS	read-create
	STATUS	current
	DESCRIPTION 
		" Location of the File that has to be downloaded"
	::= { fileTableEntry 6}

fileSlotNumber	OBJECT-TYPE
	SYNTAX INTEGER 
	MAX-ACCESS    read-create
	STATUS  current
	DESCRIPTION
		" The Slot within  NCM or IC"
          ::={ fileTableEntry 7}		

fileUploadFileType	OBJECT-TYPE
	SYNTAX INTEGER {
		eventlog(1),
		flashfile(2),
		none(3)
		}
	MAX-ACCESS	read-create
	STATUS	current
	DESCRIPTION 
		" Name of teh file to be uploaded"
	::= { fileTableEntry 8}

filePerformAction	OBJECT-TYPE
	SYNTAX INTEGER {
			copy(1),
       			download(2),
                        format(3),
                        list(4),
                        remove(5),
                        upload(6)
		}
	MAX-ACCESS	read-create
	STATUS	current
	DESCRIPTION 
		" Action to be performed"
	::= { fileTableEntry 9}

fileActionStatus	OBJECT-TYPE
	SYNTAX INTEGER {
		success(1),
		failure(2),
		inProgress(3)
		}
	MAX-ACCESS	read-only
	STATUS	current
	DESCRIPTION 
		" Status of the action"
	::= { fileTableEntry 10}

fileListData	OBJECT-TYPE
	SYNTAX DisplayString
	MAX-ACCESS read-only
	STATUS  current
	DESCRIPTION 
		" This lists the file for a list command "
	     ::= { fileTableEntry 11}

fileRowStatus      OBJECT-TYPE
             SYNTAX  RowStatus
             MAX-ACCESS read-create
             STATUS  current
             DESCRIPTION
                     " Used to Add or Delete a row in the table"
             ::= { fileTableEntry 12}

END
