-- #condInclude "v2c.inc"
-- #condInclude "rfc2573.txt"
-- #condInclude "rfc2574.txt"
-- #condInclude "rfc2575.txt"
-- #condInclude "rfc2576.txt"
-- #condInclude "rstone-smi-mib.txt"

RIVERSTONE-SNMP-MIB DEFINITIONS ::= BEGIN

IMPORTS
        MODULE-IDENTITY, OBJECT-TYPE
            FROM SNMPv2-SMI
        MODULE-COMPLIANCE, OBJECT-GROUP
            FROM SNMPv2-CONF
        DateAndTime
            FROM SNMPv2-TC
        snmpTargetAddrEntry, snmpTargetParamsEntry
	    FROM SNMP-TARGET-MIB
        snmpNotifyEntry, snmpNotifyFilterProfileEntry,
        snmpNotifyFilterEntry
            FROM SNMP-NOTIFICATION-MIB
        usmUserEntry
            FROM SNMP-USER-BASED-SM-MIB
        vacmSecurityToGroupEntry, vacmAccessEntry,
        vacmViewTreeFamilyEntry
            FROM SNMP-VIEW-BASED-ACM-MIB
        snmpCommunityEntry
            FROM SNMP-COMMUNITY-MIB
        riverstoneMibs
            FROM RIVERSTONE-SMI-MIB;

rsSnmpMib MODULE-IDENTITY   
        LAST-UPDATED "200012040000Z"
        ORGANIZATION "Riverstone Networks, Inc"
        CONTACT-INFO
            "Riverstone Networks, Inc
             5200 Great America Parkway
             Santa Clara CA USA 95054
             PHONE:+1 408.878.6500
             EMAIL: nms-eng@riverstonenet.com
             WEB: http://www.riverstonenet.com"

        DESCRIPTION
            "This mib module defines addtional configuration and statistics
             for SNMP v3 Protocol Management as defined in RFCs 2570-2580
             Copyright (C) Riverstone Networks, Inc 2000"

        REVISION     "200012040000Z"
        DESCRIPTION
            "Initial version of of RIVERSTONE-SNMP-MIB."
	::= { riverstoneMibs 15 }  

rsSnmpObjects OBJECT IDENTIFIER ::= { rsSnmpMib 1 }

-- Global Last Change

rsSnmpV3LastChange        OBJECT-TYPE
       SYNTAX      DateAndTime
       MAX-ACCESS  read-only
       STATUS      current
       DESCRIPTION
        "The lastChange time of any of snmpV3 configuration."
       ::= { rsSnmpObjects 1 }

-- snmpTargetAddrTable 

rsSnmpTargetAddrTable OBJECT-TYPE
       SYNTAX      SEQUENCE OF RsSnmpTargetAddrEntry
       MAX-ACCESS  not-accessible
       STATUS      current
       DESCRIPTION
           "A table of to add a LastChange to the snmpTargetAddrTable."
       ::= { rsSnmpObjects 2 }

rsSnmpTargetAddrEntry OBJECT-TYPE
       SYNTAX      RsSnmpTargetAddrEntry
       MAX-ACCESS  not-accessible
       STATUS      current
       DESCRIPTION
           "Adds a LastChange to snmpTargetAddrEntry."
       AUGMENTS { snmpTargetAddrEntry }
       ::= { rsSnmpTargetAddrTable 1 }

RsSnmpTargetAddrEntry ::= SEQUENCE {
            rsSnmpTargetAddrLastChange    DateAndTime
        }

rsSnmpTargetAddrLastChange OBJECT-TYPE
        SYNTAX          DateAndTime
        MAX-ACCESS      read-only
        STATUS          current
        DESCRIPTION
            "This object specifies the date and time of
             creation / last modification of this conceptual 
             row."
        ::= { rsSnmpTargetAddrEntry 1 }

-- snmpTargetParamsTable 

rsSnmpTargetParamsTable OBJECT-TYPE
       SYNTAX      SEQUENCE OF RsSnmpTargetParamsEntry
       MAX-ACCESS  not-accessible
       STATUS      current
       DESCRIPTION
           "A table of to add a LastChange to the snmpTargetParamsTable."
       ::= { rsSnmpObjects 3 }

rsSnmpTargetParamsEntry OBJECT-TYPE
       SYNTAX      RsSnmpTargetParamsEntry
       MAX-ACCESS  not-accessible
       STATUS      current
       DESCRIPTION
           "Adds a LastChange to snmpTargetParamsEntry."
       AUGMENTS { snmpTargetParamsEntry }
       ::= { rsSnmpTargetParamsTable 1 }

RsSnmpTargetParamsEntry ::= SEQUENCE {
            rsSnmpTargetParamsLastChange    DateAndTime
        }

rsSnmpTargetParamsLastChange OBJECT-TYPE
        SYNTAX          DateAndTime
        MAX-ACCESS      read-only
        STATUS          current
        DESCRIPTION
            "This object specifies the date and time of
             creation / last modification of this conceptual 
             row."
        ::= { rsSnmpTargetParamsEntry 1 }

-- snmpNotifyTable 

rsSnmpNotifyTable OBJECT-TYPE
       SYNTAX      SEQUENCE OF RsSnmpNotifyEntry
       MAX-ACCESS  not-accessible
       STATUS      current
       DESCRIPTION
           "A table of to add a LastChange to the snmpNotifyTable."
       ::= { rsSnmpObjects 4 }

rsSnmpNotifyEntry OBJECT-TYPE
       SYNTAX      RsSnmpNotifyEntry
       MAX-ACCESS  not-accessible
       STATUS      current
       DESCRIPTION
           "Adds a LastChange to snmpNotifyEntry."
       AUGMENTS { snmpNotifyEntry }
       ::= { rsSnmpNotifyTable 1 }

RsSnmpNotifyEntry ::= SEQUENCE {
            rsSnmpNotifyLastChange    DateAndTime
        }

rsSnmpNotifyLastChange OBJECT-TYPE
        SYNTAX          DateAndTime
        MAX-ACCESS      read-only
        STATUS          current
        DESCRIPTION
            "This object specifies the date and time of
             creation / last modification of this conceptual 
             row."
        ::= { rsSnmpNotifyEntry 1 }

-- snmpNotifyFilterProfileTable 

rsSnmpNotifyFilterProfileTable OBJECT-TYPE
       SYNTAX      SEQUENCE OF RsSnmpNotifyFilterProfileEntry
       MAX-ACCESS  not-accessible
       STATUS      current
       DESCRIPTION
           "A table of to add a LastChange to the snmpNotifyFilterProfileTable."
       ::= { rsSnmpObjects 5 }

rsSnmpNotifyFilterProfileEntry OBJECT-TYPE
       SYNTAX      RsSnmpNotifyFilterProfileEntry
       MAX-ACCESS  not-accessible
       STATUS      current
       DESCRIPTION
           "Adds a LastChange to snmpNotifyFilterProfileEntry."
       AUGMENTS { snmpNotifyFilterProfileEntry }
       ::= { rsSnmpNotifyFilterProfileTable 1 }

RsSnmpNotifyFilterProfileEntry ::= SEQUENCE {
            rsSnmpNotifyFilterProfileLastChange    DateAndTime
        }

rsSnmpNotifyFilterProfileLastChange OBJECT-TYPE
        SYNTAX          DateAndTime
        MAX-ACCESS      read-only
        STATUS          current
        DESCRIPTION
            "This object specifies the date and time of
             creation / last modification of this conceptual 
             row."
        ::= { rsSnmpNotifyFilterProfileEntry 1 }

-- snmpNotifyFilterTable 

rsSnmpNotifyFilterTable OBJECT-TYPE
       SYNTAX      SEQUENCE OF RsSnmpNotifyFilterEntry
       MAX-ACCESS  not-accessible
       STATUS      current
       DESCRIPTION
           "A table of to add a LastChange to the snmpNotifyFilterTable."
       ::= { rsSnmpObjects 6 }

rsSnmpNotifyFilterEntry OBJECT-TYPE
       SYNTAX      RsSnmpNotifyFilterEntry
       MAX-ACCESS  not-accessible
       STATUS      current
       DESCRIPTION
           "Adds a LastChange to snmpNotifyFilterEntry."
       AUGMENTS { snmpNotifyFilterEntry }
       ::= { rsSnmpNotifyFilterTable 1 }

RsSnmpNotifyFilterEntry ::= SEQUENCE {
            rsSnmpNotifyFilterLastChange    DateAndTime
        }

rsSnmpNotifyFilterLastChange OBJECT-TYPE
        SYNTAX          DateAndTime
        MAX-ACCESS      read-only
        STATUS          current
        DESCRIPTION
            "This object specifies the date and time of
             creation / last modification of this conceptual 
             row."
        ::= { rsSnmpNotifyFilterEntry 1 }

-- usmUserTable 

rsUsmUserTable OBJECT-TYPE
       SYNTAX      SEQUENCE OF RsUsmUserEntry
       MAX-ACCESS  not-accessible
       STATUS      current
       DESCRIPTION
           "A table of to add a LastChange to the usmUserTable."
       ::= { rsSnmpObjects 7 }

rsUsmUserEntry OBJECT-TYPE
       SYNTAX      RsUsmUserEntry
       MAX-ACCESS  not-accessible
       STATUS      current
       DESCRIPTION
           "Adds a LastChange to usmUserEntry."
       AUGMENTS { usmUserEntry }
       ::= { rsUsmUserTable 1 }

RsUsmUserEntry ::= SEQUENCE {
            rsUsmUserLastChange    DateAndTime
        }

rsUsmUserLastChange OBJECT-TYPE
        SYNTAX          DateAndTime
        MAX-ACCESS      read-only
        STATUS          current
        DESCRIPTION
            "This object specifies the date and time of
             creation / last modification of this conceptual 
             row."
        ::= { rsUsmUserEntry 1 }

-- vacmSecurityToGroupTable 

rsVacmSecurityToGroupTable OBJECT-TYPE
       SYNTAX      SEQUENCE OF RsVacmSecurityToGroupEntry
       MAX-ACCESS  not-accessible
       STATUS      current
       DESCRIPTION
           "A table of to add a LastChange to the vacmSecurityToGroupTable."
       ::= { rsSnmpObjects 8 }

rsVacmSecurityToGroupEntry OBJECT-TYPE
       SYNTAX      RsVacmSecurityToGroupEntry
       MAX-ACCESS  not-accessible
       STATUS      current
       DESCRIPTION
           "Adds a LastChange to vacmSecurityToGroupEntry."
       AUGMENTS { vacmSecurityToGroupEntry }
       ::= { rsVacmSecurityToGroupTable 1 }

RsVacmSecurityToGroupEntry ::= SEQUENCE {
            rsVacmSecurityToGroupLastChange    DateAndTime
        }

rsVacmSecurityToGroupLastChange OBJECT-TYPE
        SYNTAX          DateAndTime
        MAX-ACCESS      read-only
        STATUS          current
        DESCRIPTION
            "This object specifies the date and time of
             creation / last modification of this conceptual 
             row."
        ::= { rsVacmSecurityToGroupEntry 1 }

-- vacmAccessTable 

rsVacmAccessTable OBJECT-TYPE
       SYNTAX      SEQUENCE OF RsVacmAccessEntry
       MAX-ACCESS  not-accessible
       STATUS      current
       DESCRIPTION
           "A table of to add a LastChange to the vacmAccessTable."
       ::= { rsSnmpObjects 9 }

rsVacmAccessEntry OBJECT-TYPE
       SYNTAX      RsVacmAccessEntry
       MAX-ACCESS  not-accessible
       STATUS      current
       DESCRIPTION
           "Adds a LastChange to vacmAccessEntry."
       AUGMENTS { vacmAccessEntry }
       ::= { rsVacmAccessTable 1 }

RsVacmAccessEntry ::= SEQUENCE {
            rsVacmAccessLastChange    DateAndTime
        }

rsVacmAccessLastChange OBJECT-TYPE
        SYNTAX          DateAndTime
        MAX-ACCESS      read-only
        STATUS          current
        DESCRIPTION
            "This object specifies the date and time of
             creation / last modification of this conceptual 
             row."
        ::= { rsVacmAccessEntry 1 }

-- vacmViewTreeFamilyTable 

rsVacmViewTreeFamilyTable OBJECT-TYPE
       SYNTAX      SEQUENCE OF RsVacmViewTreeFamilyEntry
       MAX-ACCESS  not-accessible
       STATUS      current
       DESCRIPTION
           "A table of to add a LastChange to the vacmViewTreeFamilyTable."
       ::= { rsSnmpObjects 10 }

rsVacmViewTreeFamilyEntry OBJECT-TYPE
       SYNTAX      RsVacmViewTreeFamilyEntry
       MAX-ACCESS  not-accessible
       STATUS      current
       DESCRIPTION
           "Adds a LastChange to vacmViewTreeFamilyEntry."
       AUGMENTS { vacmViewTreeFamilyEntry }
       ::= { rsVacmViewTreeFamilyTable 1 }

RsVacmViewTreeFamilyEntry ::= SEQUENCE {
            rsVacmViewTreeFamilyLastChange    DateAndTime
        }

rsVacmViewTreeFamilyLastChange OBJECT-TYPE
        SYNTAX          DateAndTime
        MAX-ACCESS      read-only
        STATUS          current
        DESCRIPTION
            "This object specifies the date and time of
             creation / last modification of this conceptual 
             row."
        ::= { rsVacmViewTreeFamilyEntry 1 }

-- snmpCommunityTable 

rsSnmpCommunityTable OBJECT-TYPE
       SYNTAX      SEQUENCE OF RsSnmpCommunityEntry
       MAX-ACCESS  not-accessible
       STATUS      current
       DESCRIPTION
           "A table of to add a LastChange to the snmpCommunityTable."
       ::= { rsSnmpObjects 11 }

rsSnmpCommunityEntry OBJECT-TYPE
       SYNTAX      RsSnmpCommunityEntry
       MAX-ACCESS  not-accessible
       STATUS      current
       DESCRIPTION
           "Adds a LastChange to snmpCommunityEntry."
       AUGMENTS { snmpCommunityEntry }
       ::= { rsSnmpCommunityTable 1 }

RsSnmpCommunityEntry ::= SEQUENCE {
            rsSnmpCommunityLastChange    DateAndTime
        }

rsSnmpCommunityLastChange OBJECT-TYPE
        SYNTAX          DateAndTime
        MAX-ACCESS      read-only
        STATUS          current
        DESCRIPTION
            "This object specifies the date and time of
             creation / last modification of this conceptual 
             row."
        ::= { rsSnmpCommunityEntry 1 }

--
--  Compliance Section
--

rsSnmpConformance OBJECT IDENTIFIER ::= { rsSnmpMib 2 }

rsSnmpGroups OBJECT IDENTIFIER ::= { rsSnmpConformance 1 }

rsSnmpCompliances OBJECT IDENTIFIER ::= { rsSnmpConformance 2 }

rsSnmpBaseGroup OBJECT-GROUP
    OBJECTS {
        rsSnmpV3LastChange,
        rsSnmpTargetAddrLastChange,
        rsSnmpTargetParamsLastChange,
        rsSnmpNotifyLastChange,
        rsSnmpNotifyFilterProfileLastChange,
        rsSnmpNotifyFilterLastChange,
        rsUsmUserLastChange,
        rsVacmSecurityToGroupLastChange,
        rsVacmAccessLastChange,
        rsVacmViewTreeFamilyLastChange,
        rsSnmpCommunityLastChange
    }
    STATUS      current
    DESCRIPTION
        "A collection of objects providing 
         configuration and monitoring capabilites of SNMP v3
         Protocol on a given device."
    ::= { rsSnmpGroups 1 }

rsSnmpMibCompliance MODULE-COMPLIANCE
    STATUS  current
    DESCRIPTION
        "The compliance statement for device support of 
        extended SNMP v3 support."

    MODULE
        MANDATORY-GROUPS { rsSnmpBaseGroup }

       ::= { rsSnmpCompliances 1 }

END
