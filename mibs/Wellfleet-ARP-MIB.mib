Wellfleet-ARP-MIB DEFINITIONS ::= BEGIN

-- Created by mdl2asn version 3.1
-- Creation date: Wed Aug 30 16:36:43 EDT 1995


    IMPORTS

      OBJECT-TYPE
        FROM RFC-1212
      wfArpGroup
        FROM Wellfleet-COMMON-MIB;


    wfArpBase	OBJECT IDENTIFIER ::= { wfArpGroup 1 }

    wfArpBaseCreate OBJECT-TYPE
        SYNTAX	INTEGER {
    		    created(1),
    		    deleted(2)
    		}
        ACCESS	read-write
        STATUS	mandatory
        DESCRIPTION
                "Create/Delete parameter. Default is created.
                Users perform a set operation on this
                object in order to create/delete ARP."
        DEFVAL	{ created }
        ::= { wfArpBase 1 }

    wfArpBaseEnable OBJECT-TYPE
        SYNTAX	INTEGER {
    		    enabled(1),
    		    disabled(2)
    		}
        ACCESS	read-write
        STATUS	mandatory
        DESCRIPTION
                "Enable/Disable Parameter indicates whether
                this ARP record is enabled or disabled."
        DEFVAL	{ enabled }
        ::= { wfArpBase 2 }

    wfArpBaseForwarding OBJECT-TYPE
        SYNTAX	INTEGER {
    		    forwarding(1),
    		    notforwarding(2)
    		}
        ACCESS	read-write
        STATUS	mandatory
        DESCRIPTION
                "Equivalent to IP Host Only. This attribute
                says that ARP should send unknown addresses to the
                bridge for further handling"
        DEFVAL	{ forwarding }
        ::= { wfArpBase 3 }

    wfArpBaseNonlocalSrc OBJECT-TYPE
        SYNTAX	INTEGER {
    		    log(1),
    		    drop(2)
    		}
        ACCESS	read-write
        STATUS	mandatory
        DESCRIPTION
                "DROP_LOG/DROP Parameter indicates whether
                or not log an invalid ARP source address
                when processing an ARP request.
                If DROP_LOG is set, log the invalid ARP source
                address; if DROP is set, do not log it.
                In both cases, the ARP request from the invalid
                source address will be droped."
        DEFVAL	{ drop }
        ::= { wfArpBase 4 }

    wfArpBaseNonlocalDest OBJECT-TYPE
        SYNTAX	INTEGER {
    		    drop(1),
    		    accept(2)
    		}
        ACCESS	read-write
        STATUS	mandatory
        DESCRIPTION
                "DEST_DROP/DEST_ACCEPT Parameter indicates
                whether or not drop/accept an ARP Request
                in which the destination address is in a
                different network/subnetwork from the
                source address.
                If DEST_DROP is set, drop the ARP Request;
                If DEST_ACCEPT is set, process the ARP Request.
                The default is DEST_DROP."
        DEFVAL	{ drop }
        ::= { wfArpBase 5 }

    wfArpIntfTable OBJECT-TYPE
        SYNTAX	SEQUENCE OF WfArpIntfEntry
        ACCESS	not-accessible
        STATUS	mandatory
        DESCRIPTION
                "List of configured ARP interfaces"
        ::= { wfArpGroup 2 }

    wfArpIntfEntry OBJECT-TYPE
        SYNTAX	WfArpIntfEntry
        ACCESS	not-accessible
        STATUS	mandatory
        DESCRIPTION
                "A description of an ARP interface"
        INDEX	{ wfArpCctno }
        ::= { wfArpIntfTable 1 }

    WfArpIntfEntry ::= SEQUENCE {
    	    wfArpCreate
    		INTEGER,
    	    wfArpEnable
    		INTEGER,
    	    wfArpCctno
    		INTEGER
        }

    wfArpCreate OBJECT-TYPE
        SYNTAX	INTEGER {
    		    created(1),
    		    deleted(2)
    		}
        ACCESS	read-write
        STATUS	mandatory
        DESCRIPTION
                "Indicates whether this ARP intf record is to be deleted or created"
        DEFVAL	{ created }
        ::= { wfArpIntfEntry 1 }

    wfArpEnable OBJECT-TYPE
        SYNTAX	INTEGER {
    		    enabled(1),
    		    disabled(2)
    		}
        ACCESS	read-write
        STATUS	mandatory
        DESCRIPTION
                "Indicates whether this ARP intf record is to be enabled or disabled"
        DEFVAL	{ enabled }
        ::= { wfArpIntfEntry 2 }

    wfArpCctno OBJECT-TYPE
        SYNTAX	INTEGER
        ACCESS	read-only
        STATUS	mandatory
        DESCRIPTION
                "Which Circuit arp should run on"
        ::= { wfArpIntfEntry 3 }

    END  -- Wellfleet-ARP-MIB
