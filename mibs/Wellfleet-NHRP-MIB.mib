Wellfleet-NHRP-MIB DEFINITIONS ::= BEGIN

IMPORTS

  Counter, IpAddress
    FROM RFC1155-SMI
  OBJECT-TYPE
    FROM RFC-1212
  DisplayString
    FROM RFC1213-MIB
  wfNhrpGroup
    FROM Wellfleet-COMMON-MIB;

wfNhrpNetTable OBJECT-TYPE
	SYNTAX	SEQUENCE OF WfNhrpNetEntry
	ACCESS	not-accessible
	STATUS	mandatory
	DESCRIPTION
		"A table containing entries for each combination of a layer 2
		network and a layer 3 protocol.
		Currently, IP over Frame Relay and IP over ATM is supported."
	::= { wfNhrpGroup 1 }

wfNhrpNetEntry OBJECT-TYPE
	SYNTAX	WfNhrpNetEntry
	ACCESS	not-accessible
	STATUS	mandatory
	DESCRIPTION
		"Information about a particular NHRP instance."
	INDEX	{ wfNhrpLayer2Type, 
		  wfNhrpLayer3Type }
	::= { wfNhrpNetTable 1 }

WfNhrpNetEntry ::= SEQUENCE {
	wfNhrpDelete
		INTEGER,
	wfNhrpLayer2Type
		INTEGER,
	wfNhrpLayer3Type
		INTEGER,
	wfNhrpNHReqPath
		INTEGER,
	wfNhrpClientDisable
		INTEGER,
        wfNhrpClientRegInterval
                INTEGER,
	wfNhrpClientHoldTime
		INTEGER,
	wfNhrpClientReqTimeout
		INTEGER,
	wfNhrpClientReqRetry
		INTEGER,
	wfNhrpClientMaxPendRequests
		INTEGER,
	wfNhrpServerDisable
		INTEGER,
	wfNhrpServerFwdDisable
		INTEGER,
	wfNhrpServerMaxNhEntries
		INTEGER,
	wfNhrpServerMaxPendRequests
		INTEGER,
	wfNhrpServerUseBgp
		INTEGER,
	wfNhrpServerUseDns
		INTEGER,
	wfNhrpServerDnsProxyPort
		INTEGER,
	wfNhrpServerOverrideNbmaAddr
		INTEGER,
	wfNhrpBogusNbmaAddr
		DisplayString,
	wfNhrpNhCacheSize
		INTEGER,
	wfNhrpQosCacheSize
		INTEGER,
	wfNhrpAddrXlateCacheSize
		INTEGER,
        wfNhrpServerLoadBalance
		INTEGER,
	wfNhrpServerNegativeCaching
		INTEGER,
	wfNhrpServerNegativeTTL
		INTEGER,
        wfNhrpDebugLevel
		INTEGER,
	wfNhrpStatReset
		INTEGER,
	wfNhrpNhCacheSequence
		INTEGER,
	wfNhrpNhCacheNumEntries
		INTEGER,
	wfNhrpQosCacheNumEntries
		INTEGER,
	wfNhrpAddrXlateCacheNumEntries
		INTEGER
 }
	
wfNhrpDelete 	OBJECT-TYPE
        SYNTAX  INTEGER {
                created(1),
                deleted(2)
        }
        ACCESS  read-write
        STATUS  mandatory
        DESCRIPTION
                "Create/Delete this NHRP instance "
        DEFVAL  { created }
        ::= { wfNhrpNetEntry 1 }

wfNhrpLayer2Type	OBJECT-TYPE
	SYNTAX	INTEGER {
		fr(1),
		atm(2)
	}
	ACCESS	read-only
        STATUS  mandatory
        DESCRIPTION
                "Type of layer 2 Network."
        ::= { wfNhrpNetEntry 2 }

wfNhrpLayer3Type	OBJECT-TYPE
	SYNTAX	INTEGER {
		ip(1)
	}
	ACCESS	read-only
        STATUS  mandatory
        DESCRIPTION
                "Type of layer 3 protocol."
        ::= { wfNhrpNetEntry 3 }

wfNhrpNHReqPath OBJECT-TYPE
        SYNTAX  INTEGER {
                routed(1),
                defNHS(2)
        }
        ACCESS  read-write
        STATUS  mandatory
        DESCRIPTION
                "Path NHC will attempt first to look-up destination.
                 In case of routed path, if dest. is not found it will
                 search Default NHS list also."
        DEFVAL  { routed }
        ::= { wfNhrpNetEntry 4 }

wfNhrpClientDisable OBJECT-TYPE
	SYNTAX	INTEGER {
		enabled(1),
		disabled(2)
	}
	ACCESS	read-write
	STATUS	mandatory
	DESCRIPTION
		" Enable/Disable NHRP client functionality. "
	DEFVAL	{ enabled }
	::= { wfNhrpNetEntry 5 }

wfNhrpClientRegInterval OBJECT-TYPE
        SYNTAX  INTEGER(10..200)
        ACCESS  read-write
        STATUS  mandatory
        DESCRIPTION
                "Client registration period. Every wfNhrpRegInterval seconds,
                 CREG gate will send registration request to refresh/update
                 NH cache. It should always be less than wfNhrpNHCacheHoldTime"
        DEFVAL  { 25 }
        ::= { wfNhrpNetEntry 6 }

wfNhrpClientHoldTime	OBJECT-TYPE
	SYNTAX	INTEGER(10..200)
	ACCESS	read-write
	STATUS	mandatory
	DESCRIPTION
		"Time (seconds) for which client info is valid."
	DEFVAL	{ 30 }
	::= { wfNhrpNetEntry 7 }

wfNhrpClientReqTimeout OBJECT-TYPE
	SYNTAX  INTEGER(1..100)
	ACCESS	read-write
	STATUS	mandatory
	DESCRIPTION
		" Client request timeout in seconds "
	DEFVAL { 10 }
	::= { wfNhrpNetEntry 8 }

wfNhrpClientReqRetry	OBJECT-TYPE
	SYNTAX	INTEGER(1..20)
	ACCESS	read-write
	STATUS	mandatory
	DESCRIPTION
		" Number of times to retry a given client request before
		  returning an error. "
	DEFVAL { 3 }
	::= { wfNhrpNetEntry 9 }

wfNhrpClientMaxPendRequests OBJECT-TYPE
	SYNTAX	INTEGER(1..100)
	ACCESS	read-write
	STATUS	mandatory
	DESCRIPTION
		"Maximum Number of pending requests for client."  
	DEFVAL	{ 100 }
	::= { wfNhrpNetEntry 10 }

wfNhrpServerDisable OBJECT-TYPE
	SYNTAX	INTEGER {
		enabled(1),
		disabled(2)
	}
	ACCESS	read-write
	STATUS	mandatory
	DESCRIPTION
		" Enable/Disable NHRP server functionality. "
	DEFVAL	{ enabled }
	::= { wfNhrpNetEntry 11 }

wfNhrpServerFwdDisable OBJECT-TYPE
	SYNTAX	INTEGER {
		enabled(1),
		disabled(2)
	}
	ACCESS	read-write
	STATUS	mandatory
	DESCRIPTION
		" Enable/Disable NHRP server request forwarding function. "
	DEFVAL	{ enabled }
	::= { wfNhrpNetEntry 12 }

wfNhrpServerMaxNhEntries OBJECT-TYPE
	SYNTAX	INTEGER(1..20)
	ACCESS	read-write
	STATUS	mandatory
	DESCRIPTION
		"maximum number of next hop entries to keep.  If the 
		 NH Resolution Reply message has more entries, last 
		 ones will be discarded."
	DEFVAL  { 5 }
	::= { wfNhrpNetEntry 13 }

wfNhrpServerMaxPendRequests OBJECT-TYPE
	SYNTAX	INTEGER(1..100)
	ACCESS	read-write
	STATUS	mandatory
	DESCRIPTION
		"Maximum Number of pending requests for servers."  
	DEFVAL	{ 100 }
	::= { wfNhrpNetEntry 14 }

wfNhrpServerUseBgp	OBJECT-TYPE
	SYNTAX	INTEGER {
		use(1),
		notuse(2)
	}
	ACCESS	read-write
	STATUS	mandatory
	DESCRIPTION
		"Use BGP to find next hop if destination address is not
		in cache."
	DEFVAL { notuse }
	::= { wfNhrpNetEntry 15 }
	
wfNhrpServerUseDns 	OBJECT-TYPE
	SYNTAX	INTEGER {
		use(1),
		notuse(2)
	}
	ACCESS	read-write
	STATUS	mandatory
	DESCRIPTION
		"Use DNS to translate addresses and find QoS for next
                 hop resolutions."
	DEFVAL 	{ notuse }
	::= { wfNhrpNetEntry 16 }

wfNhrpServerDnsProxyPort OBJECT-TYPE
	SYNTAX 	INTEGER(1..32550)
	ACCESS	read-write
	STATUS	mandatory
	DESCRIPTION
		"DNS proxy port for QOS translation queries"
	DEFVAL 	{ 500 }
	::= { wfNhrpNetEntry 17 }

wfNhrpServerOverrideNbmaAddr OBJECT-TYPE
        SYNTAX  INTEGER {
                enabled(1),
                disabled(2)
        }
        ACCESS  read-write
        STATUS  mandatory
        DESCRIPTION
                "Override NBMA addresses in client registration messages."
        DEFVAL  { disabled }
        ::= { wfNhrpNetEntry 18 }

wfNhrpBogusNbmaAddr OBJECT-TYPE
	SYNTAX	DisplayString (SIZE (0..20))
	ACCESS	read-write
	STATUS	mandatory
	DESCRIPTION
		"Value used to determine if NBMA address in client request
		is valid."
	DEFVAL 	{ "NOADDRESS" }
	::= { wfNhrpNetEntry 19 }


wfNhrpNhCacheSize OBJECT-TYPE
	SYNTAX	INTEGER(16..1024)
	ACCESS	read-write
	STATUS	mandatory
	DESCRIPTION
		"Maximum number of next hop entries to be cached"
	DEFVAL { 16 }
	::= { wfNhrpNetEntry 20 }

wfNhrpQosCacheSize OBJECT-TYPE
	SYNTAX	INTEGER(16..1024)
        ACCESS  read-write
        STATUS  mandatory
        DESCRIPTION
                "Maximum number of socketpair to filter/flow spec entries to 
		be cached"
	DEFVAL { 16 }
        ::= { wfNhrpNetEntry 21 }

wfNhrpAddrXlateCacheSize OBJECT-TYPE
	SYNTAX  INTEGER(16..1024)
        ACCESS  read-write
        STATUS  mandatory
        DESCRIPTION
                "Maximum number of L3-to-L2 address mapping entries
		to be cached"
	DEFVAL { 16 }
        ::= { wfNhrpNetEntry 22 }

wfNhrpServerLoadBalance OBJECT-TYPE
	SYNTAX  INTEGER {
                enable(1),
                disable(2)
        }
        ACCESS  read-write
        STATUS  mandatory
        DESCRIPTION
                "Enable/disable round-robin cycling of next hop
		entries to cause a load-balancing effect."
	DEFVAL { disable }
        ::= { wfNhrpNetEntry 23 }

wfNhrpServerNegativeCaching OBJECT-TYPE
	SYNTAX  INTEGER {
   		enable (1),
                disable(2)
        }
        ACCESS  read-write
        STATUS  mandatory
        DESCRIPTION
                "Enable/disable negative caching of DNS records."
	DEFVAL { enable }
        ::= { wfNhrpNetEntry 24 }

wfNhrpServerNegativeTTL OBJECT-TYPE
	SYNTAX  INTEGER(1..65535)
        ACCESS  read-write
        STATUS  mandatory
        DESCRIPTION
                "Time in seconds for negative caching of DNS 
                 records."
	DEFVAL { 10 }
        ::= { wfNhrpNetEntry 25 }

wfNhrpDebugLevel OBJECT-TYPE
	SYNTAX  INTEGER 
        ACCESS  read-write
        STATUS  mandatory
        DESCRIPTION
                "Minimum level of debug messages to log."
	DEFVAL { 0 }
        ::= { wfNhrpNetEntry 26 }

wfNhrpStatReset OBJECT-TYPE
	SYNTAX  INTEGER {
   		notreset(1),
		reset(2)
         }
        ACCESS  read-write
        STATUS  mandatory
        DESCRIPTION
                "Reset all NHRP client and server stats."
	DEFVAL { notreset }
        ::= { wfNhrpNetEntry 27 }

wfNhrpNhCacheSequence OBJECT-TYPE
	SYNTAX  INTEGER 
        ACCESS  read-only
        STATUS  mandatory
        DESCRIPTION
                "Sequence number for Next Hop Cache updates."
	DEFVAL { 0 }
        ::= { wfNhrpNetEntry 28 }

wfNhrpNhCacheNumEntries OBJECT-TYPE
	SYNTAX  INTEGER
        ACCESS  read-only
        STATUS  mandatory
        DESCRIPTION
                "Current number of Next Hop Cache entries."
	DEFVAL { 0 }
        ::= { wfNhrpNetEntry 29 }

wfNhrpQosCacheNumEntries OBJECT-TYPE
	SYNTAX  INTEGER
        ACCESS  read-only
        STATUS  mandatory
        DESCRIPTION
                "Current number of entries in QOS Cache."
	DEFVAL { 0 }
        ::= { wfNhrpNetEntry 30 }

wfNhrpAddrXlateCacheNumEntries OBJECT-TYPE
	SYNTAX  INTEGER
        ACCESS  read-only
        STATUS  mandatory
        DESCRIPTION
                "Current number of entries in Address Translation Cache."
	DEFVAL { 0 }
        ::= { wfNhrpNetEntry 31 }

wfNhrpIfTable OBJECT-TYPE
	SYNTAX	SEQUENCE OF WfNhrpIfEntry
	ACCESS	not-accessible
	STATUS	mandatory
	DESCRIPTION
		"
		  WF_NHRP_INTERFACE_Table - NHRP
		  This tabulates the interfaces within an nhrp protocol group.
		  All interfaces are indexed according to their Circuit Number.
		"
	::= { wfNhrpGroup 2 }

wfNhrpIfEntry OBJECT-TYPE
	SYNTAX	WfNhrpIfEntry
	ACCESS	not-accessible
	STATUS	mandatory
	DESCRIPTION
		" Nhrp interface entries. "
	INDEX	{ wfNhrpIfLayer2Type,
		  wfNhrpIfLayer3Type,
		  wfNhrpIfCct }
	::= { wfNhrpIfTable 1 }

WfNhrpIfEntry ::= SEQUENCE {
	wfNhrpIfDelete
		INTEGER,
	wfNhrpIfDisable
		INTEGER,
	wfNhrpIfVCType
		INTEGER,
	wfNhrpIfCct
		INTEGER,
	wfNhrpIfLayer2Type
		INTEGER,
	wfNhrpIfLayer3Type
		INTEGER,
	wfNhrpIfPktsXmt
		Counter
}

wfNhrpIfDelete OBJECT-TYPE
	SYNTAX	INTEGER {
		created(1),
		deleted(2)
	}
	ACCESS	read-write
	STATUS	mandatory
	DESCRIPTION
		" Creation and deletion flag for this record. When set, 
		  it will cause this entry to be deleted from the MIB. "
	DEFVAL	{ created }
	::= { wfNhrpIfEntry 1 }

wfNhrpIfDisable OBJECT-TYPE
	SYNTAX	INTEGER {
		enabled(1),
		disabled(2)
	}
	ACCESS	read-write
	STATUS	mandatory
	DESCRIPTION
		" Enable/Disable parameter. A disabled interface will 
		  never be selected as the active interface for a circuit. "
	DEFVAL	{ enabled }
	::= { wfNhrpIfEntry 2 }

wfNhrpIfVCType OBJECT-TYPE
        SYNTAX  INTEGER {
                pvc(1),
                svc(2)
        }
        ACCESS  read-write
        STATUS  mandatory
        DESCRIPTION
                "Type of VC, NHC will setup, if no encaps gate exist for the 
		given VCid, when needed."
        DEFVAL  { pvc }
        ::= { wfNhrpIfEntry 3 }

wfNhrpIfCct OBJECT-TYPE
	SYNTAX	INTEGER {
		minimum(1),
		maximum(1023)
	}
	ACCESS	read-only
	STATUS	mandatory
	DESCRIPTION
		"The number of the circuit to which the interface belongs."
	::= { wfNhrpIfEntry 4 }

wfNhrpIfLayer2Type        OBJECT-TYPE
        SYNTAX  INTEGER {
                fr(1),
		atm(2)
        }
        ACCESS  read-only
        STATUS  mandatory
        DESCRIPTION
                "Type of layer 2 Network for this instance."
        ::= { wfNhrpIfEntry 5 }

wfNhrpIfLayer3Type        OBJECT-TYPE
        SYNTAX  INTEGER {
                ip(1)
        }
        ACCESS  read-only
        STATUS  mandatory
        DESCRIPTION
		"Type of layer 3 Protocol for this instance."
        ::= { wfNhrpIfEntry 6 }

wfNhrpIfPktsXmt OBJECT-TYPE
	SYNTAX	Counter
	ACCESS	read-only
	STATUS	mandatory
	DESCRIPTION
		" The number of NHRP packets sent on this interface. "
	::= { wfNhrpIfEntry 7 }


wfNhrpDefNhsTable OBJECT-TYPE
	SYNTAX	SEQUENCE OF WfNhrpDefNhsEntry
	ACCESS	not-accessible
	STATUS	mandatory
	DESCRIPTION
		"A list of default NHS's to contact with request messages."
	::= { wfNhrpGroup 3 }

wfNhrpDefNhsEntry OBJECT-TYPE
	SYNTAX	WfNhrpDefNhsEntry
	ACCESS	not-accessible
	STATUS	mandatory
	DESCRIPTION
		"Information pertaining to each default NHS which a
                 client may contact. "
	INDEX	{ wfNhrpDefNhsLayer2Type,
		  wfNhrpDefNhsLayer3Type,
		  wfNhrpDefNhsIndex }
	::= { wfNhrpDefNhsTable 1 }

WfNhrpDefNhsEntry ::= SEQUENCE {
	wfNhrpDefNhsDelete
		INTEGER,
	wfNhrpDefNhsDisable
		INTEGER,
	wfNhrpDefNhsCct
		INTEGER,
	wfNhrpDefNhsVcid1
		INTEGER,
	wfNhrpDefNhsVcid2
		INTEGER,
	wfNhrpDefNhsProtoAddr
		IpAddress,
	wfNhrpDefNhsServingNetworkAddr
		IpAddress,
	wfNhrpDefNhsServingNetworkMask
		IpAddress,
	wfNhrpDefNhsNbmaAddr
		OCTET STRING,
	wfNhrpDefNhsStatus
		INTEGER,
	wfNhrpDefNhsLayer2Type
		INTEGER,
	wfNhrpDefNhsLayer3Type
		INTEGER,
	wfNhrpDefNhsIndex
		INTEGER
}

wfNhrpDefNhsDelete OBJECT-TYPE
	SYNTAX	INTEGER {
		created(1),
		deleted(2)
	}
	ACCESS	read-write
	STATUS	mandatory
	DESCRIPTION
		" Creation and deletion flag for this record. When set, 
		  it will cause this entry to be deleted from the MIB. "
	DEFVAL	{ created }
	::= { wfNhrpDefNhsEntry 1 }

wfNhrpDefNhsDisable OBJECT-TYPE
	SYNTAX	INTEGER {
		enabled(1),
		disabled(2)
	}
	ACCESS	read-write
	STATUS	mandatory
	DESCRIPTION
		" Enable/Disable parameter. A disabled NHS will 
		  never be selected for sending requests. "
	DEFVAL	{ enabled }
	::= { wfNhrpDefNhsEntry 2 }

wfNhrpDefNhsCct OBJECT-TYPE
	SYNTAX	INTEGER {
		minimum(1),
		maximum(1023)
	}
	ACCESS	read-write
	STATUS	mandatory
	DESCRIPTION
		" The identifier of the circuit on which requests are sent 
		   to NHS. "
	::= { wfNhrpDefNhsEntry 3 }

wfNhrpDefNhsVcid1 OBJECT-TYPE
	SYNTAX	INTEGER
	ACCESS	read-write
	STATUS	mandatory
	DESCRIPTION
		" The virtual circuit ID on which requests are sent to NHS.
		  Vcid1 = The Dlci number for Frame Relay, the VPI for ATM
		  Range = {0-255}"
	::= { wfNhrpDefNhsEntry 4 }

wfNhrpDefNhsVcid2 OBJECT-TYPE
	SYNTAX	INTEGER
	ACCESS	read-write
	STATUS	mandatory
	DESCRIPTION
		" The virtual circuit ID on which requests are sent to NHS. 
		  Vcid2 = The VCI for ATM, NULL for Frame Relay.
		  Range = {32-65535}"
	::= { wfNhrpDefNhsEntry 5 }

wfNhrpDefNhsProtoAddr OBJECT-TYPE
	SYNTAX	IpAddress
	ACCESS	read-write
	STATUS	mandatory
	DESCRIPTION
		"Layer 3 protocol address for this default NHS.
                 Currently only IP addresses are supported."
	::= { wfNhrpDefNhsEntry 6 }

wfNhrpDefNhsServingNetworkAddr OBJECT-TYPE
	SYNTAX	IpAddress
	ACCESS	read-write
	STATUS	mandatory
	DESCRIPTION
		"Layer 3 network address of hosts served by this default NHS.
                 Currently only IP type of network addresses are supported."
	::= { wfNhrpDefNhsEntry 7 }

wfNhrpDefNhsServingNetworkMask OBJECT-TYPE
	SYNTAX	IpAddress
	ACCESS	read-write
	STATUS	mandatory
	DESCRIPTION
		"Layer 3 network address mask for range of hosts served by 
		 this default NHS. Currently only IP net mask is supported."
	::= { wfNhrpDefNhsEntry 8 }

wfNhrpDefNhsNbmaAddr OBJECT-TYPE
	SYNTAX  OCTET STRING
	ACCESS	read-write
	STATUS	mandatory
	DESCRIPTION
		"Layer 2 NBMA address for this default NHS.
		 This will be valid only when SVCs needs to be created"
	::= { wfNhrpDefNhsEntry 9 }

wfNhrpDefNhsStatus OBJECT-TYPE
	SYNTAX	INTEGER {
		up(1),
		down(2)
	}
	ACCESS	read-only
	STATUS	mandatory
	DESCRIPTION
		"Reachability Status of this NHS . "
	::= { wfNhrpDefNhsEntry 10 }

wfNhrpDefNhsLayer2Type        OBJECT-TYPE
        SYNTAX  INTEGER {
                fr(1),
		atm(2)
        }
        ACCESS  read-only
        STATUS  mandatory
        DESCRIPTION
		"Type of layer 2 Network associated with this NHS."
        ::= { wfNhrpDefNhsEntry 11 }

wfNhrpDefNhsLayer3Type        OBJECT-TYPE
        SYNTAX  INTEGER {
                ip(1)
        }
        ACCESS  read-only
        STATUS  mandatory
        DESCRIPTION
		" Type of layer 3 Protocol associated with this NHS."
        ::= { wfNhrpDefNhsEntry 12 }

wfNhrpDefNhsIndex OBJECT-TYPE
        SYNTAX  INTEGER (1..16)
	ACCESS  read-only
        STATUS  mandatory
        DESCRIPTION
                "Index used as priority of the NHS. That is, smallest index 
                 is selected first."
	::= { wfNhrpDefNhsEntry 13 }


wfNhrpNHCacheTable OBJECT-TYPE
	SYNTAX	SEQUENCE OF WfNhrpNHCacheEntry
	ACCESS	not-accessible
	STATUS	mandatory
	DESCRIPTION
		"A list of default NHS's to contact with request messages."
	::= { wfNhrpGroup 4 }

wfNhrpNHCacheEntry OBJECT-TYPE
        SYNTAX  WfNhrpNHCacheEntry
        ACCESS  not-accessible
        STATUS  mandatory
        DESCRIPTION
                " NHRP Next Hop Cache Entry. "
        INDEX   { 
		  wfNhrpNHCacheSlot,
		  wfNhrpNHCacheLayer2Type,
                  wfNhrpNHCacheLayer3Type,
                  wfNhrpNHCacheDestAddr,
		  wfNhrpNHCacheDestAddrPrefixLen,
		  wfNhrpNHCachePrefOrder }
        ::= { wfNhrpNHCacheTable 1 }


WfNhrpNHCacheEntry ::= SEQUENCE {
        wfNhrpNHCacheSlot
		INTEGER,
        wfNhrpNHCacheLayer2Type
		INTEGER,
	wfNhrpNHCacheLayer3Type
		INTEGER,
	wfNhrpNHCacheDestAddr
		IpAddress,
	wfNhrpNHCacheDestAddrPrefixLen
		INTEGER,
	wfNhrpNHCachePrefOrder
		INTEGER,
	wfNhrpNHCacheNhProtAddr
		IpAddress,
	wfNhrpNHCacheNhNbmaAddr
		DisplayString,
	wfNhrpNHCacheHoldTime
		INTEGER,
	wfNhrpNHCacheFlags
		INTEGER,
	wfNhrpNHCachePrefValue
		INTEGER,
	wfNhrpNHCacheMtu
		INTEGER,
	wfNhrpNHCacheDelete
		INTEGER
}

wfNhrpNHCacheSlot OBJECT-TYPE
        SYNTAX  INTEGER
        ACCESS  read-only
        STATUS  mandatory
        DESCRIPTION
                "The slot number indexes the object"
	::= { wfNhrpNHCacheEntry 1 }

wfNhrpNHCacheLayer2Type OBJECT-TYPE
	SYNTAX	INTEGER {
		fr(1),
		atm(2)
	}
	ACCESS	read-only
	STATUS	mandatory
	DESCRIPTION
		"Type of layer 2 Network associated with this cache entry."
	::= { wfNhrpNHCacheEntry 2 }

wfNhrpNHCacheLayer3Type OBJECT-TYPE
        SYNTAX  INTEGER {
                ip(1)
        }
        ACCESS  read-only
        STATUS  mandatory
        DESCRIPTION
                "Type of layer 3 Protocol associated with this cache entry."
        ::= { wfNhrpNHCacheEntry 3 }

wfNhrpNHCacheDestAddr OBJECT-TYPE
        SYNTAX  IpAddress
        ACCESS  read-only
	        STATUS  mandatory
        DESCRIPTION
                "protocol address of the destination"
	::= { wfNhrpNHCacheEntry 4 }

wfNhrpNHCacheDestAddrPrefixLen OBJECT-TYPE
        SYNTAX  INTEGER (0..16)
	ACCESS  read-only
        STATUS  mandatory
        DESCRIPTION
                "destination address prifix length"
	::= { wfNhrpNHCacheEntry 5 }

wfNhrpNHCachePrefOrder OBJECT-TYPE
        SYNTAX  INTEGER
        ACCESS  read-only
        STATUS  mandatory
        DESCRIPTION
		"preference order for this entry"
	::= { wfNhrpNHCacheEntry 6 }

wfNhrpNHCacheNhProtAddr OBJECT-TYPE
        SYNTAX  IpAddress
        ACCESS  read-write
                STATUS  mandatory
        DESCRIPTION
                "protocol address of the next hop"
	::= { wfNhrpNHCacheEntry 7 }

wfNhrpNHCacheNhNbmaAddr OBJECT-TYPE
        SYNTAX  DisplayString (SIZE (0..20))
        ACCESS  read-write
        STATUS  mandatory
        DESCRIPTION
                "NBMA address of the next hop"
	::= { wfNhrpNHCacheEntry 8 }

wfNhrpNHCacheHoldTime OBJECT-TYPE
        SYNTAX  INTEGER {
                minimum(10),
                default(30),
                maximum(200)
        }
        ACCESS  read-write
        STATUS  mandatory
        DESCRIPTION
                "Time (seconds) for which client info is valid."
        DEFVAL  { default }
        ::= { wfNhrpNHCacheEntry 9 }

wfNhrpNHCacheFlags OBJECT-TYPE
        SYNTAX  INTEGER
	ACCESS  read-write
        STATUS  mandatory
        DESCRIPTION
                "entry state flags"
	::= { wfNhrpNHCacheEntry 10 }

wfNhrpNHCachePrefValue OBJECT-TYPE
        SYNTAX  INTEGER
        ACCESS  read-write
        STATUS  mandatory
        DESCRIPTION
                "next hop preference value"
	::= { wfNhrpNHCacheEntry 11 }

wfNhrpNHCacheMtu OBJECT-TYPE
        SYNTAX  INTEGER
        ACCESS  read-write
        STATUS  mandatory
        DESCRIPTION
                "Max transmission unit for next hop"
	::= { wfNhrpNHCacheEntry 12 }

wfNhrpNHCacheDelete 	OBJECT-TYPE
        SYNTAX  INTEGER {
                created(1),
                deleted(2)
        }
        ACCESS  read-write
        STATUS  mandatory
        DESCRIPTION
                "Create/Delete this NHRP NH Cache Entry "
        DEFVAL  { created }
        ::= { wfNhrpNHCacheEntry 13 }

wfNhrpTest OBJECT IDENTIFIER ::= { wfNhrpGroup 5 }

wfNhrpTestDelete OBJECT-TYPE
        SYNTAX  INTEGER {
                    created(1),
                    deleted(2)
                }
        ACCESS  read-write
        STATUS  mandatory
        DESCRIPTION
                "Create or Delete the Nhrp Test Base Record"
        DEFVAL  { created }
        ::= { wfNhrpTest 1 }

wfNhrpTestLayer2Type OBJECT-TYPE
        SYNTAX  INTEGER {
                  fr(1),
		  atm(2)
		}
        ACCESS  read-write
        STATUS  mandatory
        DESCRIPTION
                "Identifies layer 2 protocol for which next hop is desired."
        DEFVAL { fr }
        ::= { wfNhrpTest 2 }

wfNhrpTestLayer3Type OBJECT-TYPE
        SYNTAX  INTEGER {
		  ip(1)
		}
        ACCESS  read-write
        STATUS  mandatory
        DESCRIPTION
                "Identifies layer 3 protocol for which next hop is desired."
        DEFVAL { ip }
        ::= { wfNhrpTest 3 }

wfNhrpTestSlot OBJECT-TYPE
        SYNTAX  INTEGER {
		minimum(1),
		maximum(16),
		default(2)
		}
        ACCESS  read-write
        STATUS  mandatory
        DESCRIPTION
                "Slot number on which test client initiates next hop requests."
        DEFVAL { default }
        ::= { wfNhrpTest 4 }

wfNhrpTestNHRPeriod OBJECT-TYPE
        SYNTAX  INTEGER 
        ACCESS  read-write
        STATUS  mandatory
        DESCRIPTION
                "Time (msec) between next hop requests."
        DEFVAL { 5000 }
        ::= { wfNhrpTest 5 }

wfNhrpTestNHRDestAddr OBJECT-TYPE
	SYNTAX	IpAddress
	ACCESS	read-write
	STATUS	mandatory
	DESCRIPTION
	  "Protocol address of destination for which next hop is desired." 
	::= { wfNhrpTest 6 }

wfNhrpTestNHRDestPrefix OBJECT-TYPE
        SYNTAX  INTEGER
        ACCESS  read-write
        STATUS  mandatory
        DESCRIPTION
          "Prefix length of destination address for which next hop is desired."
        ::= { wfNhrpTest 7 }
 
wfNhrpTestNHRReqOpt OBJECT-TYPE
        SYNTAX  INTEGER 
        ACCESS  read-write
        STATUS  mandatory
        DESCRIPTION
               "A bit field identifying next hop request options."
        DEFVAL { 0 }
        ::= { wfNhrpTest 8 }

wfNhrpTestNHRReqQOS OBJECT-TYPE
        SYNTAX  DisplayString (SIZE (0..240))
        ACCESS  read-write
        STATUS  mandatory
        DESCRIPTION
                "QoS selector value for next hop requests."
        ::= { wfNhrpTest 9 }

wfNhrpTestLogDisable OBJECT-TYPE
        SYNTAX  INTEGER {
		  enabled(1),
		  disabled(2)
		}
        ACCESS  read-write
        STATUS  mandatory
        DESCRIPTION
                "Indicates whether reply data is written to log."
        DEFVAL { enabled }
        ::= { wfNhrpTest 10 }

wfNhrpTestRegCmd OBJECT-TYPE
        SYNTAX  INTEGER {
		  ignore(1),
		  register(2),
		  purge(3),
		  nhreq(4),
		  mpsResReq(5),
		  mpsResRply(6),
		  mpsPurgeReq(7),
		  mpsPurgeRply(8),
		  mpsAddMps(9),
		  mpsDelMps(10)
		}
        ACCESS  read-write
        STATUS  mandatory
        DESCRIPTION
                "Type of registration request to send (register or purge)."
        DEFVAL { ignore }
        ::= { wfNhrpTest 11 }

wfNhrpTestRegNhsAddr OBJECT-TYPE
	SYNTAX	IpAddress
	ACCESS	read-write
	STATUS	mandatory
	DESCRIPTION
	  "Protocol address of NHS to send registration or purge request.
           If no address is given, the request will be sent to a default
           NHS." 
	::= { wfNhrpTest 12 }

wfNhrpTestRegReqOpt OBJECT-TYPE
        SYNTAX  INTEGER 
        ACCESS  read-write
        STATUS  mandatory
        DESCRIPTION
               "A bit field identifying register/purge options."
        DEFVAL { 0 }
        ::= { wfNhrpTest 13 }

wfNhrpTestRegClientHoldTime OBJECT-TYPE
        SYNTAX  INTEGER 
        ACCESS  read-write
        STATUS  mandatory
        DESCRIPTION
               "A bit field identifying register/purge hold time (seconds)."
        DEFVAL { 0 }
        ::= { wfNhrpTest 14 }

wfNhrpTestRegClientPrefVal OBJECT-TYPE
        SYNTAX  INTEGER 
        ACCESS  read-write
        STATUS  mandatory
        DESCRIPTION
               "A bit field identifying register/purge preference value."
        DEFVAL { 0 }
        ::= { wfNhrpTest 15 }

wfNhrpTestRegClientMtu OBJECT-TYPE
        SYNTAX  INTEGER 
        ACCESS  read-write
        STATUS  mandatory
        DESCRIPTION
               "Max transmit unit size (octets) for this client."
        DEFVAL { 0 }
        ::= { wfNhrpTest 16 }

wfNhrpTestRegClientPrefix OBJECT-TYPE
        SYNTAX  INTEGER
        ACCESS  read-write
        STATUS  mandatory
        DESCRIPTION
          "Prefix length of client protocol address to register or purge."
        ::= { wfNhrpTest 17 }
 
wfNhrpTestRegClientProto OBJECT-TYPE
        SYNTAX  IpAddress
        ACCESS  read-write
        STATUS  mandatory
        DESCRIPTION
                "registered client protocol address."
        ::= { wfNhrpTest 18 }

wfNhrpTestRegClientNbma OBJECT-TYPE
        SYNTAX  DisplayString (SIZE (0..20))
        ACCESS  read-write
        STATUS  mandatory
        DESCRIPTION
                "registered client NBMA address. In case of MPS res. request
		 this will be SRC_NBMA_ADDR"
	::= { wfNhrpTest 19 }

wfNhrpTestMpsGH OBJECT-TYPE
        SYNTAX  INTEGER
        ACCESS  read-write
        STATUS  mandatory
        DESCRIPTION
                "Gate handle of MPS to be registered"
	::= { wfNhrpTest 20 }

wfNhrpTestMpsCct OBJECT-TYPE
        SYNTAX  INTEGER 
        ACCESS  read-write
        STATUS  mandatory
        DESCRIPTION
                "Circuit# of MPS to be registered."
	::= { wfNhrpTest 21 }

wfNhrpClientStatTable OBJECT-TYPE
	SYNTAX	SEQUENCE OF WfNhrpClientStatEntry
	ACCESS	not-accessible
	STATUS	mandatory
	DESCRIPTION
		"This table contains statistics collected by NHRP clients."
	::= { wfNhrpGroup 6 }

wfNhrpClientStatEntry OBJECT-TYPE
        SYNTAX  WfNhrpClientStatEntry
        ACCESS  not-accessible
        STATUS  mandatory
        DESCRIPTION
                "Statistics collected by NHRP clients. "
        INDEX   { wfNhrpClientStatL2Type, 
		  wfNhrpClientStatL3Type
	        }
        ::= { wfNhrpClientStatTable 1 }

WfNhrpClientStatEntry ::= SEQUENCE {
	wfNhrpClientStatL2Type
		INTEGER,
	wfNhrpClientStatL3Type
		INTEGER,
        wfNhrpClientStatTxResolveReq
		Counter,
        wfNhrpClientStatRxResolveReplyAck
		Counter,
        wfNhrpClientStatRxResolveReplyNak
		Counter,
        wfNhrpClientStatTxRegisterReq
		Counter,
        wfNhrpClientStatRxRegisterReplyAck
		Counter,
        wfNhrpClientStatRxRegisterReplyNak
		Counter,
        wfNhrpClientStatTxPurgeReq
		Counter,
        wfNhrpClientStatRxPurgeReplyAck
		Counter,
        wfNhrpClientStatRxPurgeReplyNak
		Counter,
        wfNhrpClientStatUnsolicitPurgeReq
		Counter,
        wfNhrpClientStatTxError
		Counter,
        wfNhrpClientStatRxError
		Counter,
	wfNhrpClientStatLocalError
		Counter,
	wfNhrpClientStatRetryReq
		Counter

}

wfNhrpClientStatL2Type OBJECT-TYPE
	SYNTAX		INTEGER {
                        fr(1),
                        atm(2)
        }
 	ACCESS		read-only
	STATUS		mandatory
	DESCRIPTION	"The NHRP client layer 2 type for these statistics."
	::= { wfNhrpClientStatEntry 1 }

wfNhrpClientStatL3Type OBJECT-TYPE
	SYNTAX		INTEGER {
                        ip(1)
        }
 	ACCESS		read-only
	STATUS		mandatory
	DESCRIPTION	"The NHRP client layer 3 type for these statistics."
	::= { wfNhrpClientStatEntry 2 }

wfNhrpClientStatTxResolveReq OBJECT-TYPE
         SYNTAX      Counter
         ACCESS  read-only
         STATUS      mandatory
         DESCRIPTION
             "The number of NHRP Resolution Requests transmitted by this
             client."
         ::= { wfNhrpClientStatEntry 3 }

wfNhrpClientStatRxResolveReplyAck OBJECT-TYPE
         SYNTAX      Counter
         ACCESS  read-only
         STATUS      mandatory
         DESCRIPTION
             "The number of positively acknowledged NHRP Resolution Replies received by this client."
         ::= { wfNhrpClientStatEntry 4 }

wfNhrpClientStatRxResolveReplyNak OBJECT-TYPE
         SYNTAX      Counter
         ACCESS  read-only
         STATUS      mandatory
         DESCRIPTION
             "The number of NAKed NHRP Resolution Replies received by this client."
         ::= { wfNhrpClientStatEntry 5 }


wfNhrpClientStatTxRegisterReq OBJECT-TYPE
         SYNTAX      Counter
         ACCESS  read-only
         STATUS      mandatory
         DESCRIPTION
             "The number of NHRP Registration Requests transmitted by this client."
         ::= { wfNhrpClientStatEntry 6 }

wfNhrpClientStatRxRegisterReplyAck OBJECT-TYPE
         SYNTAX      Counter
         ACCESS  read-only
         STATUS      mandatory
         DESCRIPTION
             "The number of positively acknowledged NHRP Registration
             Replies received by this client."
         ::= { wfNhrpClientStatEntry 7}

wfNhrpClientStatRxRegisterReplyNak OBJECT-TYPE
         SYNTAX      Counter
         ACCESS  read-only
         STATUS      mandatory
         DESCRIPTION
             "The number of NAKed NHRP Registration Replies received by
             this client."
         ::= { wfNhrpClientStatEntry 8 }

wfNhrpClientStatTxPurgeReq OBJECT-TYPE
         SYNTAX      Counter
         ACCESS  read-only
         STATUS      mandatory
         DESCRIPTION
             "The number of NHRP Purge Requests transmitted by this
             client."
         ::= { wfNhrpClientStatEntry 9 }

wfNhrpClientStatRxPurgeReplyAck OBJECT-TYPE
         SYNTAX      Counter
         ACCESS  read-only
         STATUS      mandatory
         DESCRIPTION
             "The number of positive NHRP Purge Replies received by this client."
         ::= { wfNhrpClientStatEntry 10 }

wfNhrpClientStatRxPurgeReplyNak OBJECT-TYPE
         SYNTAX      Counter
         ACCESS  read-only
         STATUS      mandatory
         DESCRIPTION
             "The number of NAKed NHRP Purge Replies received by this client."
         ::= { wfNhrpClientStatEntry 11 }

wfNhrpClientStatUnsolicitPurgeReq OBJECT-TYPE
         SYNTAX      Counter
         ACCESS  read-only
         STATUS      mandatory
         DESCRIPTION
             "The number of unsolicited purge requests rec'd by this client"
         ::= { wfNhrpClientStatEntry 12 }

wfNhrpClientStatTxError OBJECT-TYPE
         SYNTAX      Counter
         ACCESS  read-only
         STATUS      mandatory
         DESCRIPTION
             "The number of NHRP Error Indication packets transmitted by
             this client."
         ::= { wfNhrpClientStatEntry 13 }

wfNhrpClientStatRxError OBJECT-TYPE
         SYNTAX      Counter
         ACCESS  read-only
         STATUS      mandatory
         DESCRIPTION
             "The number of NHRP Error Indication packets received by
             this client."
         ::= { wfNhrpClientStatEntry 14 }

wfNhrpClientStatLocalError OBJECT-TYPE
         SYNTAX      Counter
         ACCESS  read-only
         STATUS      mandatory
         DESCRIPTION
             "The number of local errors which occured on
             this client."
         ::= { wfNhrpClientStatEntry 15 }

wfNhrpClientStatRetryReq OBJECT-TYPE
         SYNTAX      Counter
         ACCESS  read-only
         STATUS      mandatory
         DESCRIPTION
             "The number of retries made for client requests by
             this client."
         ::= { wfNhrpClientStatEntry 16 }

wfNhrpServerStatTable OBJECT-TYPE
         SYNTAX      SEQUENCE OF WfNhrpServerStatEntry
         ACCESS  not-accessible
         STATUS      mandatory
         DESCRIPTION
             "Statistics collected by Next Hop Servers."
         ::= { wfNhrpGroup 7 }

wfNhrpServerStatEntry OBJECT-TYPE
         SYNTAX      WfNhrpServerStatEntry
         ACCESS  not-accessible
         STATUS      mandatory
         DESCRIPTION
             "Statistics for a particular NHS. The statistics are broken
             into received (Rx), transmitted (Tx) and forwarded (Fw)..."
         INDEX       { wfNhrpServerStatL2Type,
		       wfNhrpServerStatL3Type
		     }
         ::= { wfNhrpServerStatTable 1 }

WfNhrpServerStatEntry ::= SEQUENCE {
	 wfNhrpServerStatL2Type			       INTEGER,
	 wfNhrpServerStatL3Type			       INTEGER,

         wfNhrpServerStatRxResolveReq                  Counter,
         wfNhrpServerStatTxResolveReplyAck             Counter,
         wfNhrpServerStatTxResolveReplyNak	       Counter,

         wfNhrpServerStatRxRegisterReq                 Counter,
         wfNhrpServerStatTxRegisterReplyAck            Counter,
         wfNhrpServerStatTxRegisterReplyNak            Counter,
  
         wfNhrpServerStatRxPurgeReq                    Counter,
         wfNhrpServerStatTxPurgeReplyAck               Counter,
         wfNhrpServerStatTxPurgeReplyNak               Counter,

         wfNhrpServerStatRxError    		       Counter,
         wfNhrpServerStatTxError     		       Counter,

         wfNhrpServerStatFwdResolveReq                 Counter,
         wfNhrpServerStatFwdResolveReply               Counter,
         wfNhrpServerStatFwdRegisterReq                Counter,
         wfNhrpServerStatFwdRegisterReply              Counter,
         wfNhrpServerStatFwdPurgeReq                   Counter,
         wfNhrpServerStatFwdPurgeReply                 Counter,
         wfNhrpServerStatFwdError                      Counter,

	 wfNhrpServerStatDropPkts		       Counter
     }

wfNhrpServerStatL2Type OBJECT-TYPE
         SYNTAX      INTEGER {
                     fr(1),
                     atm(2)
         }
         ACCESS      read-only
         STATUS      mandatory
         DESCRIPTION
             "The NHRP server layer 2 type for these statistics."
         ::= { wfNhrpServerStatEntry 1 }

wfNhrpServerStatL3Type OBJECT-TYPE
         SYNTAX      INTEGER {
                     ip(1)
         }
         ACCESS      read-only
         STATUS      mandatory
         DESCRIPTION
             "The NHRP server layer 3 type for these statistics."
         ::= { wfNhrpServerStatEntry 2 }

wfNhrpServerStatRxResolveReq OBJECT-TYPE
         SYNTAX      Counter
         ACCESS  read-only
         STATUS      mandatory
         DESCRIPTION
             "The number of NHRP Resolution Requests received by this
             server."
         ::= { wfNhrpServerStatEntry 3 }

wfNhrpServerStatTxResolveReplyAck OBJECT-TYPE
         SYNTAX      Counter
         ACCESS  read-only
         STATUS      mandatory
         DESCRIPTION
             "The number of positively acknowledged NHRP Resolution 
	      Replies transmitted by this server."
         ::= { wfNhrpServerStatEntry 4 }

wfNhrpServerStatTxResolveReplyNak OBJECT-TYPE
         SYNTAX      Counter
         ACCESS  read-only
         STATUS      mandatory
         DESCRIPTION
             "The number of NAKed NHRP Resolution Replies transmitted by
             this server."
         ::= { wfNhrpServerStatEntry 5 }

wfNhrpServerStatRxRegisterReq OBJECT-TYPE
         SYNTAX      Counter
         ACCESS  read-only
         STATUS      mandatory
         DESCRIPTION
             "The number of NHRP Registration Requests received by this
             server."
         ::= { wfNhrpServerStatEntry 6 }

wfNhrpServerStatTxRegisterReplyAck OBJECT-TYPE
         SYNTAX      Counter
         ACCESS  read-only
         STATUS      mandatory
         DESCRIPTION
             "The number of positively acknowledge NHRP Registration
             Replies transmitted by this server."
         ::= { wfNhrpServerStatEntry 7 }

wfNhrpServerStatTxRegisterReplyNak OBJECT-TYPE
         SYNTAX      Counter
         ACCESS  read-only
         STATUS      mandatory
         DESCRIPTION
             "The number of NAKed NHRP Registration Replies transmitted by this server."
         ::= { wfNhrpServerStatEntry 8 }

wfNhrpServerStatRxPurgeReq OBJECT-TYPE
         SYNTAX      Counter
         ACCESS  read-only
         STATUS      mandatory
         DESCRIPTION
             "The number of NHRP Purge Requests received by this server."
         ::= { wfNhrpServerStatEntry 9 }

wfNhrpServerStatTxPurgeReplyAck OBJECT-TYPE
         SYNTAX      Counter
         ACCESS  read-only
         STATUS      mandatory
         DESCRIPTION
             "The number of positive NHRP Purge Replies transmitted by this server."
         ::= { wfNhrpServerStatEntry 10 }

wfNhrpServerStatTxPurgeReplyNak OBJECT-TYPE
         SYNTAX      Counter
         ACCESS  read-only
         STATUS      mandatory
         DESCRIPTION
             "The number of NAKed NHRP Purge Replies transmitted by this server."
         ::= { wfNhrpServerStatEntry 11 }

wfNhrpServerStatRxError OBJECT-TYPE
         SYNTAX      Counter
         ACCESS  read-only
         STATUS      mandatory
         DESCRIPTION
             "The number of NHRP Error Indication packets received by this
             server with the error code 'Unrecognized Extension'."
         ::= { wfNhrpServerStatEntry 12 }

wfNhrpServerStatTxError OBJECT-TYPE
         SYNTAX      Counter
         ACCESS  read-only
         STATUS      mandatory
         DESCRIPTION
             "The number of NHRP Error Indication packets received by this
             server with the error code 'Subnetwork ID Mismatch'."
         ::= { wfNhrpServerStatEntry 13 }

wfNhrpServerStatFwdResolveReq OBJECT-TYPE
         SYNTAX      Counter
         ACCESS  read-only
         STATUS      mandatory
         DESCRIPTION
             "The number of NHRP Resolution Requests forwarded by this
             server acting as a transit NHS."
         ::= { wfNhrpServerStatEntry 14 }

wfNhrpServerStatFwdResolveReply OBJECT-TYPE
         SYNTAX      Counter
         ACCESS  read-only
         STATUS      mandatory
         DESCRIPTION
             "The number of NHRP Resolution Replies forwarded by this
             server acting as a transit NHS."
         ::= { wfNhrpServerStatEntry 15 }

wfNhrpServerStatFwdRegisterReq OBJECT-TYPE
         SYNTAX      Counter
         ACCESS  read-only
         STATUS      mandatory
         DESCRIPTION
             "The number of NHRP Registration Requests forwarded by this
             server acting as a transit NHS."
         ::= { wfNhrpServerStatEntry 16 }

wfNhrpServerStatFwdRegisterReply OBJECT-TYPE
         SYNTAX      Counter
         ACCESS  read-only
         STATUS      mandatory
         DESCRIPTION
             "The number of NHRP Registration Replies forwarded by this
             server acting as a transit NHS."
         ::= { wfNhrpServerStatEntry 17 }

wfNhrpServerStatFwdPurgeReq OBJECT-TYPE
         SYNTAX      Counter
         ACCESS  read-only
         STATUS      mandatory
         DESCRIPTION
             "The number of NHRP Purge Requests forwarded by this server
             acting as a transit NHS."
         ::= { wfNhrpServerStatEntry 18 }

wfNhrpServerStatFwdPurgeReply OBJECT-TYPE
         SYNTAX      Counter
         ACCESS  read-only
         STATUS      mandatory
         DESCRIPTION
             "The number of NHRP Purge Replies forwarded by this server
             acting as a transit NHS."
         ::= { wfNhrpServerStatEntry 19 }

wfNhrpServerStatFwdError OBJECT-TYPE
         SYNTAX      Counter
         ACCESS  read-only
         STATUS      mandatory
         DESCRIPTION
             "The number of NHRP Error Indication packets forwarded by this
             server acting as a transit NHS."
         ::= { wfNhrpServerStatEntry 20 }

wfNhrpServerStatDropPkts OBJECT-TYPE
         SYNTAX      Counter
         ACCESS  read-only
         STATUS      mandatory
         DESCRIPTION
             "The number of packets dropped by this NHS."
         ::= { wfNhrpServerStatEntry 21 }


END -- Wellfleet-NHRP-MIB
