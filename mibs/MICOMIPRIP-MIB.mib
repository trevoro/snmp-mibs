-- 
-- Modified as per comments from Rajesh S. Dated: 05-16-96
-- MIB Version Dated: 05-31-96
-- Modified to add Inverse ARP Table
-- Update Dated: 09-13-96
--
-- 
-- MIB Revision : 1.0 dated 1-17-97
-- Change Desc. : None. 
-- 
-- MIB Revision : 1.1 dated 3-20-97
-- Change Desc. : Specified ranges for different objects. 
--
-- MIB Revision : 1.2 dated  4/22/97
-- Change Desc. : Added access privilages to capabilities
--                field.                  -S. Gaur  
--                                        
-- 
-- MIB Revision : 1.3 dated 9-25-97
-- Change Desc. : Minor syntax corrections - B. Jafari
--
-- MIB Revision : 1.4 dated 10-8-97
-- Change Desc. : Replaced MPA with 4400 - B. Jafari. 
-- 
--
-- *** Release 3.0 ***
-- MIB Revision : 1.5 dated 6-18-98
-- Change Desc. : Added (mcm/nvm)IpRipCompatibility objects.
--                Obsoleted the mcmIpIfCntrZeroTable and 
--                mcmIpGrpCounterZero, mcmIcmpGrpCounterZero,
--                mcmTcpGrpCounterZero,mcmUdpGrpCounterZero,
--                mcmSnmpGrpCounterZero objects.
--                Replaced all instances of the "4400" string
--                with the generic term "access device"           
--                                          - S. Gaur. 
--
-- MIB Revision : 1.6 dated 8-18-98
-- Change Desc. : Added the (mcm/nvm)IPBootpRelayGroup's  as per 
--                J. Pinkney.
--                                           -S. Gaur    
-- MIB Revision : 1.7 dated 8-19-98
-- Change Desc. : (mcm/nvm)ipAddr was needed as a second index
--                for the (mcm/nvm)IpAddrTable's therefore the
--                (mcm/nvm)IpAddrTable was deprecated  and 
--                (mcm/nvm)IpAddressTable was added. 
--                The access for nvmipAddress was changed to 
--                read-only.
--    
--                                           -S. Gaur    
--
-- MIB Revision : 1.6 dated 8-18-98
-- Change Desc. : Added the mcmIpPingGroup.
--                
--                                           -M. Delmar    
-- MIB Revision : 1.6 dated 11-24-98
-- Change Desc. : Removed (commented out) items from nvmipAddressDlType
--
--
--					     -M. Delmar
-- MIB Revision : 1.7 dated 12-02-98
-- Change Desc. : Added (mcm)nvmIpAddressRowStatus
--
-- *** RELEASE 3.1 ***
-- MIB Revision : 1.8 dated 1-19-99
-- Change Desc. : Modify description of nvmipAddressRoutProtType object to
--                indicate the supported enumerations for clarification.
--                Fixed under SR10159671. - M.Ly
--
-- MIB Revision : 1.9 dated 2-12-99
-- Change Desc. : Modified the nvmipAddressIfIndex object to read-only
--                because it is a index.
--		  				-V. Xin 
-- MIB Revision : 1.10 dated 2-12-99
-- Change Desc. : Changed the nvmipAddressIfIndex object back to read-write
-- 		  and the nvmipAddress object to read-write.
--						-V. Xin

    MICOMIPRIP-MIB DEFINITIONS ::= BEGIN

    IMPORTS
         IpAddress
                 FROM RFC1155-SMI
	 micom-oscar 
	  	    FROM MICOM-OSCAR-MIB


         OBJECT-TYPE
                 FROM RFC-1212;

    --  This MIB module uses the extended OBJECT-TYPE macro as
    --  defined in [13]


    --  this is the MIB module for MICOM IP-RIP objects

   mcmIp    	OBJECT IDENTIFIER ::= { micom-oscar 5 }
   ip-control   OBJECT IDENTIFIER ::= { mcmIp 16 }


mcmIpRipEnable OBJECT-TYPE
     	SYNTAX INTEGER {
                 on (1),
                 off (2)
        }
     	ACCESS read-only
     	STATUS mandatory
	DESCRIPTION
	  "NAME = ;
	   DESC = This Parameter determines if RIP is \
                  turned ON or OFF on the access device.;
           HELP = When RIP is enabled, The access device \
                  propogates routing information to other \
                  access devices, gateways, and Hosts.;
	   CAPABILITIES = NET_CFG, VPN_CFG;"
        ::= { mcmIp 1 }

mcmIpRipDfltRtEnable OBJECT-TYPE
     	SYNTAX INTEGER {
                 on (1),
                 off (2)
        }
     	ACCESS read-only
     	STATUS mandatory
	DESCRIPTION
	  "NAME = ;
	   DESC = This value determines if this unit should \
                  act as default Router.;
           HELP = ;
	   CAPABILITIES = NET_CFG, VPN_CFG;"
        ::= { mcmIp 2 }

mcmIpRipCompatibility OBJECT-TYPE
     	SYNTAX INTEGER {
                 rip1           (1),
                 rip1Compatible (2),
                 rip2           (3)
        }
     	ACCESS read-only
     	STATUS mandatory
	DESCRIPTION
	  "NAME = ;
	   DESC = This value indicates the Routing \
                  Internet Protocol (RIP) version.\
                  rip1 indicates only RIP version 1 \
                   packets are broadcasted. \
                  rip1Compatible indicates RIP \
                   version 2 packets are broadcasted. \
                  rip2 indicates RIP version 2 packets \
                   are multicasted.;
           HELP = ;
	   CAPABILITIES = NET_CFG, VPN_CFG;"
        ::= { mcmIp 10 }

mcmIpAddrTable OBJECT-TYPE
	SYNTAX SEQUENCE OF McmIpAddrEntry
	ACCESS not-accessible
	STATUS deprecated
	DESCRIPTION
	  "NAME = ;
	   DESC = ** Note this table has been deprecated and 
                  replaced by mcmIpAddressTable below ** \

                  Information about the IP Protocol parameters \
                  on a  per interface basis.;
           HELP = ;
	   CAPABILITIES = NET_CFG, VPN_CFG;"
	::= { mcmIp 3 }

mcmIpAddrEntry OBJECT-TYPE
	SYNTAX  McmIpAddrEntry
	ACCESS  not-accessible
	STATUS  deprecated
	DESCRIPTION
	  "NAME = ;
	   DESC = IP Parameters on a per interface basic.;
           HELP = ;
	   CAPABILITIES = ;"
	INDEX 	{ 
		  mcmipIfIndex
		}
   ::= { mcmIpAddrTable 1 }

McmIpAddrEntry ::=
           SEQUENCE {
               mcmipIfIndex
                   INTEGER,
               mcmipAddr
                   IpAddress,
               mcmipKeepAlive
                   INTEGER,
               mcmipMtu
                   INTEGER,
               mcmipDlType
                   INTEGER,
               mcmipForwardBcast
                   INTEGER,
               mcmipUnumIf
                   INTEGER,
	       mcmipRoutProtType
		 INTEGER

           }

mcmipIfIndex OBJECT-TYPE
	SYNTAX  INTEGER
	ACCESS  read-only
	STATUS  deprecated
	DESCRIPTION
	  "NAME = ;
	   DESC = ** DEPRECATED **\
                  The index value which uniquely identifies \
                  the interface to which this entry is applicable.;
           HELP = The interface identified by a particular \
                      value of this index is the same interface as \
                      identified by the same value of ifIndex.;
	   CAPABILITIES = ;"
           ::= { mcmIpAddrEntry 1 }

mcmipAddr OBJECT-TYPE
	SYNTAX  IpAddress
	ACCESS  read-only
	STATUS  deprecated
	DESCRIPTION
	  "NAME = ;
	   DESC = ** DEPRECATED **\
                  The IP address to which this entry's \
                  addressing information pertains.;
           HELP = ;
	   CAPABILITIES = ;"
           ::= {mcmIpAddrEntry  2 }


mcmipMtu OBJECT-TYPE
	SYNTAX  INTEGER
	ACCESS  read-only
	STATUS  deprecated
	DESCRIPTION
	  "NAME = ;
	   DESC = ** DEPRECATED **\
                  The size of the largest datagram which \
                  can be sent/received on the interface, \
                  specified in octets.;
           HELP = For interfaces that are used for transmitting \
                  datagrams, this is the size of the largest \
                  network datagram that can be sent on the interface.;
	   CAPABILITIES = ;"
           ::= { mcmIpAddrEntry 3 }

mcmipDlType OBJECT-TYPE
	SYNTAX  INTEGER {
		csmacd(1),  -- IEEE 802.3 CSMA/CD network, LLI compatibility  
		tpb(2),	  -- IEEE 802.4 Token Passing Bus, LLI compatibility  
		tpr(3),   -- IEEE 802.5 Token Passing Ring, LLI compatibility  
		metro(4), -- IEEE 802.6 Metro Net, LLI compatibility  
		ether(5), -- Ethernet Bus, LLI compatibility  
		hdlc(6),  -- ISO HDLC protocol support, bit synchronous  
		char(7),  -- Character Synchronous protocol support, eg BISYNC  
		ctca(8),  -- IBM C h a n n e l - t o - C h a n n e l Adapter  
		fddi(9),  -- Fiber Distributed data interface  
		frameRelay(10),  --Frame Relay
		frIpOpt(11),     -- Frame Relay IP Option
		other(12),  -- Any other medium not listed above 
		invalid(13) -- Invalid
           }
	ACCESS  read-only
	STATUS  deprecated
	DESCRIPTION
	  "NAME = ;
	   DESC = ** DEPRECATED **\
                  The type of interface, distinguished \
                  according to the physical/link protocol(s) \
                  immediately `below' the network layer \
                  in the protocol stack. Note - these \
           HELP = ;
	   CAPABILITIES = ;"
           ::= { mcmIpAddrEntry 4 }

                       
mcmipKeepAlive OBJECT-TYPE
     	SYNTAX INTEGER {
                 on (1),
                 off (2)
        }
     	ACCESS read-only
     	STATUS deprecated
	DESCRIPTION
	  "NAME = ;
	   DESC = ** DEPRECATED **\
                  This value determines if keepalives \
                  are sent over this interface.;
           HELP = ;
	   CAPABILITIES = ;"
        ::= { mcmIpAddrEntry 5 }

mcmipForwardBcast OBJECT-TYPE
     	SYNTAX INTEGER {
                 on (1),
                 off (2)
        }
     	ACCESS read-only
     	STATUS deprecated
	DESCRIPTION
	  "NAME = ;
	   DESC = ** DEPRECATED **\
                  This value determines if forward Broadcast \
                  is turned ON or OFF.;
           HELP = This value determines if broadcasts \
                  are forwarded.;
	   CAPABILITIES = ;"
        ::= { mcmIpAddrEntry 6 }

mcmipUnumIf OBJECT-TYPE
     	SYNTAX INTEGER {
                 unnumbered (1),
                 numbered (2)
        }
     	ACCESS read-only
     	STATUS deprecated
	DESCRIPTION
	  "NAME = ;
           DESC = ** DEPRECATED **\
                  This value determines if Unumbered IP \
                  is supported on this interface.;
           HELP = ;
	   CAPABILITIES = ;"
        ::= { mcmIpAddrEntry 7 }

mcmipRoutProtType OBJECT-TYPE
     	SYNTAX INTEGER {
                 rip (1),
                 ospf (2),
                 passiveRip (3),
                 disable (4)
        }
     	ACCESS read-only
     	STATUS deprecated
	DESCRIPTION
	  "NAME = ;
	   DESC = ** DEPRECATED **\
                  This value determines the IP routing \
                  protocol on this interface.;
           HELP =;
	   CAPABILITIES = ;"
        ::= { mcmIpAddrEntry 8 }

-- 

mcmIpAddressTable OBJECT-TYPE
	SYNTAX SEQUENCE OF McmIpAddressEntry
	ACCESS not-accessible
	STATUS mandatory
	DESCRIPTION
	  "NAME = ;
	   DESC = Information about the IP Protocol parameters \
                  on a  per interface basis.;
           HELP = ;
	   CAPABILITIES = NET_CFG, VPN_CFG;"
	::= { mcmIp 12 }

mcmIpAddressEntry OBJECT-TYPE
	SYNTAX  McmIpAddressEntry
	ACCESS  not-accessible
	STATUS  mandatory
	DESCRIPTION
	  "NAME = ;
	   DESC = IP Parameters on a per interface basic.;
           HELP = ;
	   CAPABILITIES = ;"
	INDEX 	{ 
		  mcmipAddressIfIndex, mcmipAddress
		}
   ::= { mcmIpAddressTable 1 }

McmIpAddressEntry ::=
           SEQUENCE {
               mcmipAddressIfIndex
                   INTEGER,
               mcmipAddress
                   IpAddress,
               mcmipAddressKeepAlive
                   INTEGER,
               mcmipAddressMtu
                   INTEGER,
               mcmipAddressDlType
                   INTEGER,
               mcmipAddressForwardBcast
                   INTEGER,
               mcmipAddressUnumIf
                   INTEGER,
	       mcmipAddressRoutProtType
		   INTEGER
           }

mcmipAddressIfIndex OBJECT-TYPE
	SYNTAX  INTEGER
	ACCESS  read-only
	STATUS  mandatory
	DESCRIPTION
	  "NAME = ;
	   DESC = The index value which uniquely identifies \
                  the interface to which this entry is applicable.;
           HELP = The interface identified by a particular \
                      value of this index is the same interface as \
                      identified by the same value of ifIndex.;
	   CAPABILITIES = ;"
           ::= { mcmIpAddressEntry 1 }

mcmipAddress OBJECT-TYPE
	SYNTAX  IpAddress
	ACCESS  read-only
	STATUS  mandatory
	DESCRIPTION
	  "NAME = ;
	   DESC = The IP address to which this entry's \
                  addressing information pertains. This \
                  object is also used as the second index \
                  for this table.;
           HELP = ;
	   CAPABILITIES = ;"
           ::= {mcmIpAddressEntry  2 }


mcmipAddressMtu OBJECT-TYPE
	SYNTAX  INTEGER
	ACCESS  read-only
	STATUS  mandatory
	DESCRIPTION
	  "NAME = ;
	   DESC = The size of the largest datagram which \
                  can be sent/received on the interface, \
                  specified in octets.;
           HELP = For interfaces that are used for transmitting \
                  datagrams, this is the size of the largest \
                  network datagram that can be sent on the interface.;
	   CAPABILITIES = ;"
           ::= { mcmIpAddressEntry 3 }

mcmipAddressDlType OBJECT-TYPE
	SYNTAX  INTEGER {
--		csmacd(1),   IEEE 802.3 CSMA/CD network, LLI compatibility  
--		tpb(2),	   IEEE 802.4 Token Passing Bus, LLI compatibility  
--		tpr(3),    IEEE 802.5 Token Passing Ring, LLI compatibility  
--		metro(4),  IEEE 802.6 Metro Net, LLI compatibility  
		ether(5), -- Ethernet Bus, LLI compatibility  
--		hdlc(6),   ISO HDLC protocol support, bit synchronous  
--		char(7),   Character Synchronous protocol support, eg BISYNC  
--		ctca(8),   IBM C h a n n e l - t o - C h a n n e l Adapter  
--		fddi(9),   Fiber Distributed data interface  
		frameRelay(10),  --Frame Relay
--		frIpOpt(11),      Frame Relay IP Option
--		other(12),   Any other medium not listed above 
		invalid(13) -- Invalid
           }
	ACCESS  read-only
	STATUS  mandatory
	DESCRIPTION
	  "NAME = ;
	   DESC = The type of interface, distinguished \
                  according to the physical/link protocol(s) \
                  immediately `below' the network layer \
                  in the protocol stack. Invalid is used on releases \
		  previous to 3.0; 
           HELP = ;
	   CAPABILITIES = ;"
           ::= { mcmIpAddressEntry 4 }

                       
mcmipAddressKeepAlive OBJECT-TYPE
     	SYNTAX INTEGER {
                 on (1),
                 off (2)
        }
     	ACCESS read-only
     	STATUS mandatory
	DESCRIPTION
	  "NAME = ;
	   DESC = This value determines if keepalives \
                  are sent over this interface.;
           HELP = ;
	   CAPABILITIES = ;"
        ::= { mcmIpAddressEntry 5 }

mcmipAddressForwardBcast OBJECT-TYPE
     	SYNTAX INTEGER {
                 on (1),
                 off (2)
        }
     	ACCESS read-only
     	STATUS mandatory
	DESCRIPTION
	  "NAME = ;
	   DESC = This value determines if forward Broadcast \
                  is turned ON or OFF.;
           HELP = This value determines if broadcasts \
                  are forwarded.;
	   CAPABILITIES = ;"
        ::= { mcmIpAddressEntry 6 }

mcmipAddressUnumIf OBJECT-TYPE
     	SYNTAX INTEGER {
                 unnumbered (1),
                 numbered (2)
        }
     	ACCESS read-only
     	STATUS mandatory
	DESCRIPTION
	  "NAME = ;
           DESC = This value determines if Unumbered IP \
                  is supported on this interface.;
           HELP = ;
	   CAPABILITIES = ;"
        ::= { mcmIpAddressEntry 7 }

mcmipAddressRoutProtType OBJECT-TYPE
     	SYNTAX INTEGER {
                 rip (1),
                 ospf (2),
                 passiveRip (3),
                 disable (4)
        }
     	ACCESS read-only
     	STATUS mandatory
	DESCRIPTION
	  "NAME = ;
	   DESC = This value determines the IP routing \
                  protocol on this interface.;
           HELP =;
	   CAPABILITIES = ;"
        ::= { mcmIpAddressEntry 8 }



--  This Group provides information to configure the BOOTStrap 
--  protocol parameters. (Operational)

mcmIPBootpRelayGroup    OBJECT IDENTIFIER ::= {mcmIp 14}

mcmIPBootpRelay OBJECT-TYPE
	SYNTAX	INTEGER {
                on (1),
                off (2)
                }
	ACCESS  read-only
	STATUS  mandatory
	DESCRIPTION
	  "NAME = ;
	   DESC = The value of this object determines  \
                  if the access device will relay Bootp \
                  packets. \
		  (Operational);
	   HELP = When the Bootp Relay is on, the access \
                  device can forward Bootp requests to \
                  servers on another network.;
	   CAPABILITIES = ;"
	::= { mcmIPBootpRelayGroup 1 }


mcmIPBootpRelayServerAddr OBJECT-TYPE
	SYNTAX	IpAddress
	ACCESS  read-only
	STATUS  mandatory
	DESCRIPTION
	  "NAME = ;
	   DESC = The value of this object indicates the IP \
                  address to which Bootp relay agent will \
                  relay Bootp requests to. \
      		  (Operational);
	   HELP = ;
	   CAPABILITIES = ;"
	::= { mcmIPBootpRelayGroup 2 }

mcmIPBootpRelayHops OBJECT-TYPE
	SYNTAX	INTEGER (1..16)
	ACCESS  read-only
	STATUS  mandatory
	DESCRIPTION
	  "NAME = ;
	   DESC = The value of this object indicates the \
                  number of hops a Bootp packet is allowed \
                  to make. \
		  (Operational);
	   HELP = ;
	   CAPABILITIES = ;"
	::= { mcmIPBootpRelayGroup 3 }



nvmIpRipEnable OBJECT-TYPE
     	SYNTAX INTEGER {
                 on (1),
                 off (2)
        }
     	ACCESS read-write
     	STATUS mandatory
	DESCRIPTION
	  "NAME = ;
	   DESC = This Parameter determines if RIP is \
                  turned ON or OFF on the access device.;
           HELP = When RIP is enabled, The access \
                  device propogates routing information \
                  to other access device's,  gateways, \
                  and Hosts.;
	   CAPABILITIES = NET_CFG, VPN_CFG;"
        ::= { mcmIp 4 }

nvmIpRipDfltRtEnable OBJECT-TYPE
     	SYNTAX INTEGER {
                 on (1),
                 off (2)
        }
     	ACCESS read-write
     	STATUS mandatory
	DESCRIPTION
	  "NAME = ;
	   DESC = This value determines if this unit should \
                  act as default Router.;
           HELP = ;
	   CAPABILITIES = NET_CFG, VPN_CFG;"
        ::= { mcmIp 5 }

nvmIpAddressRipCompatibility OBJECT-TYPE
     	SYNTAX INTEGER {
                 rip1           (1),
                 rip1Compatible (2),
                 rip2           (3)
        }
     	ACCESS read-write
     	STATUS mandatory
	DESCRIPTION
	  "NAME = ;
	   DESC = This value indicates the the Routing \
                  Information Protocol (RIP) version. \
                  rip1 indicates only RIP version 1 \
                    packets are broadcasted. \
                  rip1Compatible indicates RIP \
                   version 2 packets are broadcasted. \
                  rip2 indicates RIP version 2 packets \
                   are multicasted.;
           HELP = ;
	   CAPABILITIES = NET_CFG, VPN_CFG;"
        ::= { mcmIp 11 }

-- Note that the table below has been DEPRECATED

nvmIpAddrTable OBJECT-TYPE
	SYNTAX SEQUENCE OF NvmIpAddrEntry
	ACCESS not-accessible
	STATUS deprecated
	DESCRIPTION
	  "NAME = ;
	   DESC = ** Note that this table has been deprecated \
                  and it's functionality has been replaced by \
                  nvmIpAddressTable. \

                  Information about the IP Protocol parameters \
                  on a  per interface basis.;
           HELP = ;
	   CAPABILITIES = NET_CFG, VPN_CFG;"
	::= { mcmIp 6 }

nvmIpAddrEntry OBJECT-TYPE
	SYNTAX  NvmIpAddrEntry
	ACCESS  not-accessible
	STATUS  deprecated
	DESCRIPTION
	  "NAME = ;
	   DESC = ** DEPRECATED ** \
                  IP Parameters on a per interface basis.;
	   HELP = ;
	   CAPABILITIES = ;"
	INDEX 	{ 
		  nvmipIfIndex
		}
   ::= { nvmIpAddrTable 1 }

NvmIpAddrEntry ::=
           SEQUENCE {
               nvmipIfIndex
                   INTEGER,
               nvmipAddr
                   IpAddress,
               nvmipMtu
                   INTEGER,
               nvmipDlType
                   INTEGER,
               nvmipKeepAlive
                   INTEGER,
               nvmipForwardBcast
                   INTEGER,
               nvmipUnumIf 
                   INTEGER,
               nvmipRoutProtType
                   INTEGER,
               nvmipNetMask
                   IpAddress,
               nvmipBcastAddr
                   IpAddress

           }

nvmipIfIndex OBJECT-TYPE
	SYNTAX  INTEGER(1..16)
	ACCESS  read-write
	STATUS  deprecated
	DESCRIPTION
	  "NAME = ;
	   DESC = ** DEPRECATED ** \
                  The index value which uniquely identifies \
                  the interface to which this entry is applicable.;
           HELP = The interface identified by a particular \
                  value of this index is the same interface as \
                  identified by the same value of ifIndex.;
	   CAPABILITIES = ;"
           ::= { nvmIpAddrEntry 1 }

nvmipAddr OBJECT-TYPE
	SYNTAX  IpAddress
	ACCESS  read-write
	STATUS  deprecated
	DESCRIPTION
	  "NAME = ;
	   DESC = ** DEPRECATED ** \
                  The IP address to which this entry's \
                  addressing information pertains.;
           HELP = ;
	   CAPABILITIES = ;"
           ::= {nvmIpAddrEntry  2 }


nvmipMtu OBJECT-TYPE
	SYNTAX  INTEGER
	ACCESS  read-write
	STATUS  deprecated
	DESCRIPTION
	  "NAME = ;
	   DESC = ** DEPRECATED ** \
                  The size of the largest datagram which \
                  can be sent/received on the interface, \
                  specified in octets.;
           HELP = For interfaces that are used for transmitting \
                  datagrams, this is the size of the largest \
                  network datagram that can be sent on the interface.;
	   CAPABILITIES = ;"
           ::= { nvmIpAddrEntry 3 }

nvmipDlType OBJECT-TYPE
	SYNTAX  INTEGER {
		csmacd(1),  -- IEEE 802.3 CSMA/CD network, LLI compatibility  
		tpb(2),	  -- IEEE 802.4 Token Passing Bus, LLI compatibility  
		tpr(3),   -- IEEE 802.5 Token Passing Ring, LLI compatibility  
		metro(4), -- IEEE 802.6 Metro Net, LLI compatibility  
		ether(5), -- Ethernet Bus, LLI compatibility  
		hdlc(6),  -- ISO HDLC protocol support, bit synchronous  
		char(7),  -- Character Synchronous protocol support, eg BISYNC  
		ctca(8),  -- IBM C h a n n e l - t o - C h a n n e l Adapter  
		fddi(9),  -- Fiber Distributed data interface  
		frameRelay(10), --Frame Relay
		frIpOpt(11),    -- Frame Relay IP Option
		other(12),  -- Any other medium not listed above 
		invalid(13) -- Invalid
           }
	ACCESS  read-write
	STATUS  deprecated
	DESCRIPTION
	  "NAME = ;
	   DESC = ** DEPRECATED ** \
                  The type of interface, distinguished \
                  according to the physical/link protocol(s) \
                  immediately `below' the network layer \
                  in the protocol stack.; 
           HELP = ;
	   CAPABILITIES = ;"
           ::= { nvmIpAddrEntry 4 }

                       
nvmipKeepAlive OBJECT-TYPE
     	SYNTAX INTEGER {
                 on (1),
                 off (2)
        }
     	ACCESS read-write
     	STATUS deprecated
	DESCRIPTION
	  "NAME = ;
	   DESC = ** DEPRECATED ** \
                  This value determines if keepalives \
                  are sent over this interface.;
           HELP = ;
	   CAPABILITIES = ;"
        ::= { nvmIpAddrEntry 5 }

nvmipForwardBcast OBJECT-TYPE
     	SYNTAX INTEGER {
                 on (1),
                 off (2)
        }
     	ACCESS read-write
     	STATUS deprecated
	DESCRIPTION
	  "NAME = ;
	   DESC = ** DEPRECATED ** \
                  This value determines if forward Broadcast \
                  is turned ON or OFF.;
           HELP = This value determines if broadcasts \
                  are forwarded.;
	   CAPABILITIES = ;"
        ::= { nvmIpAddrEntry 6 }

nvmipUnumIf OBJECT-TYPE
     	SYNTAX INTEGER {
                 unnumbered (1),
                 numbered (2)
        }
     	ACCESS read-write
     	STATUS deprecated
	DESCRIPTION
	  "NAME = ;
	   DESC = ** DEPRECATED ** \
                  This value determines if Unumbered IP \
                  is supported on this interface.;
           HELP = ;
	   CAPABILITIES = ;"
        ::= { nvmIpAddrEntry 7 }

nvmipRoutProtType OBJECT-TYPE
     	SYNTAX INTEGER {
                 rip (1),
                 ospf (2),
                 passiveRip (3),
                 disable (4)
        }
     	ACCESS read-write
     	STATUS deprecated
	DESCRIPTION
	  "NAME = ;
	   DESC = ** DEPRECATED ** \
                  This value determines the IP routing \
                  protocol on this interface.;
           HELP = ;
	   CAPABILITIES = ;"
        ::= { nvmIpAddrEntry 8 }

nvmipNetMask OBJECT-TYPE
	SYNTAX  IpAddress
	ACCESS  read-write
	STATUS  deprecated
	DESCRIPTION
	  "NAME = ;
	   DESC = ** DEPRECATED ** \
                  The subnet mask associated with the \
                  Ip address of this entry.;
           HELP = The value of the mask is an IP address with \
                  all the network bits set to 1 and all the \
                  hosts bits set to 0.;
	   CAPABILITIES = ;"
           ::= { nvmIpAddrEntry 9 }

nvmipBcastAddr OBJECT-TYPE
	SYNTAX  IpAddress
	ACCESS  read-write
	STATUS  deprecated
	DESCRIPTION
	  "NAME = ;
           DESC = ** DEPRECATED ** \
                  The value of the least-significant bit in the IP\
                  broadcast address used for sending datagrams on the \
                  (logical) interface associated w/ IP addr of this entry.;
           HELP = when the Internet standard all-ones broadcast \
                  address is used, the value will be \
                  1.  This value applies to both the subnet & network \
                  broadcasts addresses used by the entity on this interface.;
	   CAPABILITIES = ;"
           ::= { nvmIpAddrEntry 10 }


--

nvmIpAddressTable OBJECT-TYPE
	SYNTAX SEQUENCE OF NvmIpAddressEntry
	ACCESS not-accessible
	STATUS mandatory
	DESCRIPTION
	  "NAME = ;
	   DESC = Information about the IP Protocol parameters \
                  on a  per interface basis.;
           HELP = ;
	   CAPABILITIES = NET_CFG, VPN_CFG;"
	::= { mcmIp 13 }

nvmIpAddressEntry OBJECT-TYPE
	SYNTAX  NvmIpAddressEntry
	ACCESS  not-accessible
	STATUS  mandatory
	DESCRIPTION
	  "NAME = ;
	   DESC = IP Parameters on a per interface basis.;
	   HELP = ;
	   CAPABILITIES = ;"
	INDEX 	{ 
		  nvmipAddressIfIndex, nvmipAddress
		}
   ::= { nvmIpAddressTable 1 }

NvmIpAddressEntry ::=
           SEQUENCE {
               nvmipAddressIfIndex
                   INTEGER,
               nvmipAddress
                   IpAddress,
               nvmipAddressMtu
                   INTEGER,
               nvmipAddressDlType
                   INTEGER,
               nvmipAddressKeepAlive
                   INTEGER,
               nvmipAddressForwardBcast
                   INTEGER,
               nvmipAddressUnumIf 
                   INTEGER,
               nvmipAddressRoutProtType
                   INTEGER,
               nvmipAddressNetMask
                   IpAddress,
               nvmipAddressBcastAddr
                   IpAddress,
	       nvmipAddressRowStatus
		   INTEGER

           }

nvmipAddressIfIndex OBJECT-TYPE
	SYNTAX  INTEGER(1..16)
	ACCESS  read-write
	STATUS  mandatory
	DESCRIPTION
	  "NAME = ;
	   DESC = The index value which uniquely identifies \
                  the interface to which this entry is applicable.;
           HELP = The interface identified by a particular \
                  value of this index is the same interface as \
                  identified by the same value of ifIndex.;
	   CAPABILITIES = ;"
           ::= { nvmIpAddressEntry 1 }

nvmipAddress OBJECT-TYPE
	SYNTAX  IpAddress
	ACCESS  read-write
	STATUS  mandatory
	DESCRIPTION
	  "NAME = ;
	   DESC = The IP address to which this entry's \
                  addressing information pertains. \
                  This object is also used as the second \
                  index for this table.;
           HELP = ;
	   CAPABILITIES = ;"
           ::= {nvmIpAddressEntry  2 }


nvmipAddressMtu OBJECT-TYPE
	SYNTAX  INTEGER (64..1518)
	ACCESS  read-write
	STATUS  mandatory
	DESCRIPTION
	  "NAME = ;
	   DESC = The size of the largest datagram which \
                  can be sent/received on the interface, \
                  specified in octets.;
           HELP = For interfaces that are used for transmitting \
                  datagrams, this is the size of the largest \
                  network datagram that can be sent on the interface.;
	   CAPABILITIES = ;"
           ::= { nvmIpAddressEntry 3 }

nvmipAddressDlType OBJECT-TYPE
	SYNTAX  INTEGER {
--		csmacd(1),   IEEE 802.3 CSMA/CD network, LLI compatibility  
--		tpb(2),	   IEEE 802.4 Token Passing Bus, LLI compatibility  
--		tpr(3),    IEEE 802.5 Token Passing Ring, LLI compatibility  
--		metro(4),  IEEE 802.6 Metro Net, LLI compatibility  
		ether(5), -- Ethernet Bus, LLI compatibility  
--		hdlc(6),   ISO HDLC protocol support, bit synchronous  
--		char(7),   Character Synchronous protocol support, eg BISYNC  
--		ctca(8),   IBM C h a n n e l - t o - C h a n n e l Adapter  
--		fddi(9),   Fiber Distributed data interface  
		frameRelay(10), --Frame Relay
--		frIpOpt(11),     Frame Relay IP Option
--		other(12),   Any other medium not listed above 
		invalid(13) -- Invalid
           }
	ACCESS  read-write
	STATUS  mandatory
	DESCRIPTION
	  "NAME = ;
	   DESC = The type of interface, distinguished \
                  according to the physical/link protocol(s) \
                  immediately `below' the network layer \
                  in the protocol stack.; 
           HELP = ;
	   CAPABILITIES = ;"
           ::= { nvmIpAddressEntry 4 }

                       
nvmipAddressKeepAlive OBJECT-TYPE
     	SYNTAX INTEGER {
                 on (1),
                 off (2)
        }
     	ACCESS read-write
     	STATUS mandatory
	DESCRIPTION
	  "NAME = ;
	   DESC = This value determines if keepalives \
                  are sent over this interface.;
           HELP = ;
	   CAPABILITIES = ;"
        ::= { nvmIpAddressEntry 5 }

nvmipAddressForwardBcast OBJECT-TYPE
     	SYNTAX INTEGER {
                 on (1),
                 off (2)
        }
     	ACCESS read-write
     	STATUS mandatory
	DESCRIPTION
	  "NAME = ;
	   DESC = This value determines if forward Broadcast \
                  is turned ON or OFF.;
           HELP = This value determines if broadcasts \
                  are forwarded.;
	   CAPABILITIES = ;"
        ::= { nvmIpAddressEntry 6 }

nvmipAddressUnumIf OBJECT-TYPE
     	SYNTAX INTEGER {
                 unnumbered (1),
                 numbered (2)
        }
     	ACCESS read-write
     	STATUS mandatory
	DESCRIPTION
	  "NAME = ;
	   DESC = This value determines if Unumbered IP \
                  is supported on this interface.;
           HELP = ;
	   CAPABILITIES = ;"
        ::= { nvmIpAddressEntry 7 }

nvmipAddressRoutProtType OBJECT-TYPE
     	SYNTAX INTEGER {
                 rip (1),
                 ospf (2),
                 passiveRip (3),
                 disable (4)
        }
     	ACCESS read-write
     	STATUS mandatory
	DESCRIPTION
	  "NAME = ;
	   DESC = This value determines the IP routing \
                  protocol on this interface. \
                  This object only supported enumerations of \
                  'rip', 'passiveRip' and 'disable';
           HELP = ;
	   CAPABILITIES = ;"
        ::= { nvmIpAddressEntry 8 }

nvmipAddressNetMask OBJECT-TYPE
	SYNTAX  IpAddress
	ACCESS  read-write
	STATUS  mandatory
	DESCRIPTION
	  "NAME = ;
	   DESC = The subnet mask associated with the \
                  Ip address of this entry.;
           HELP = The value of the mask is an IP address with \
                  all the network bits set to 1 and all the \
                  hosts bits set to 0.;
	   CAPABILITIES = ;"
           ::= { nvmIpAddressEntry 9 }

nvmipAddressBcastAddr OBJECT-TYPE
	SYNTAX  IpAddress
	ACCESS  read-write
	STATUS  mandatory
	DESCRIPTION
	  "NAME = ;
           DESC = The value of the least-significant bit in the IP\
                  broadcast address used for sending datagrams on the \
                  (logical) interface associated w/ IP addr of this entry.;
           HELP = when the Internet standard all-ones broadcast \
                  address is used, the value will be \
                  1.  This value applies to both the subnet & network \
                  broadcasts addresses used by the entity on this interface.;
	   CAPABILITIES = ;"
           ::= { nvmIpAddressEntry 10 }

nvmipAddressRowStatus OBJECT-TYPE
	SYNTAX INTEGER {
		add (1),
		destroy (2),
		active (3)
	}
	ACCESS read-write
	STATUS mandatory
	DESCRIPTION
	  "NAME = ;
	   DESC = This value determines the state on \
		  which this interface is.;
	   HELP = ;
	   CAPABILITIES = ;"
	::= { nvmIpAddressEntry 11 }



--  This Group provides objects to configure the BOOTStrap 
--  protocol parameters. (Configuration)

nvmIPBootpRelayGroup    OBJECT IDENTIFIER ::= {mcmIp 15}

nvmIPBootpRelay OBJECT-TYPE
	SYNTAX	INTEGER {
                on (1),
                off (2)
                }
	ACCESS  read-write
	STATUS  mandatory
	DESCRIPTION
	  "NAME = ;
	   DESC = The value of this object determines  \
                  if the access device will relay Bootp \
                  packets. \
		  (Configuration);
	   HELP = When the Bootp Relay is on, the access \
                  device can forward Bootp requests to \
                  servers on another network.;
	   CAPABILITIES = NET_CFG, VPN_CFG;"
	::= { nvmIPBootpRelayGroup 1 }


nvmIPBootpRelayServerAddr OBJECT-TYPE
	SYNTAX	IpAddress
	ACCESS  read-write
	STATUS  mandatory
	DESCRIPTION
	  "NAME = ;
	   DESC = The value of this object indicates the IP \
                  address to which Bootp relay agent will \
                  relay Bootp requests to. \
      		  (Configuration);
	   HELP = ;
	   CAPABILITIES = NET_CFG, VPN_CFG;"
	::= { nvmIPBootpRelayGroup 2 }

nvmIPBootpRelayHops OBJECT-TYPE
	SYNTAX	INTEGER (1..16)
	ACCESS  read-write
	STATUS  mandatory
	DESCRIPTION
	  "NAME = ;
	   DESC = The value of this object indicates the \
                  number of hops a Bootp packet is allowed \
                  to make. \
		  (Configuration);
	   HELP = ;
	   CAPABILITIES = NET_CFG, VPN_CFG;"
	::= { nvmIPBootpRelayGroup 3 }


--  This Group provides objects necessary to PING an
--  IP address.

mcmIpPingGroup    OBJECT IDENTIFIER ::= {ip-control 1}

mcmIpPingAction OBJECT-TYPE
	SYNTAX	INTEGER {
                ping (1)
                }
	ACCESS  write-only
	STATUS  mandatory
	DESCRIPTION
	  "NAME = ;
	   DESC = This object invokes \
                  the ping commmand. ;
	   HELP = ;
	   CAPABILITIES = NET_CFG, VPN_CFG;"
	::= { mcmIpPingGroup 1 }

mcmIpPingAddress OBJECT-TYPE
	SYNTAX	IpAddress
	ACCESS  read-write
	STATUS  mandatory
	DESCRIPTION
	  "NAME = ;
	   DESC = The value of this object specifies   \
                  the address to be pinged. ;
	   HELP = ;
	   CAPABILITIES = NET_CFG, VPN_CFG;"
	::= { mcmIpPingGroup 2 }

mcmIpPingStatus OBJECT-TYPE
	SYNTAX	INTEGER {
                alive                  (1),
                destinationUnreachable (2),
                timeExceeded           (3)
                }
	ACCESS  read-only
	STATUS  mandatory
	DESCRIPTION
	  "NAME = ;
	   DESC = The value of this object indicates   \
                  the ping status. ;
	   HELP = ;
	   CAPABILITIES = NET_CFG, VPN_CFG;"
	::= { mcmIpPingGroup 3 }


-- The Counter Reset Group

mcmIpCntr    OBJECT IDENTIFIER ::= { mcmIp 7 }


mcmIpIfCntrZeroTable OBJECT-TYPE
	SYNTAX  SEQUENCE OF McmIpIfCntrZeroEntry
	ACCESS  not-accessible
	STATUS  obsolete
	DESCRIPTION
	  "NAME = ;
           DESC = ** NOTE:THIS TABLE IS OBSOLETE AND NO \
                  LONGER SUPPORTED IN RELEASE 3.0 AND \
                  BEYOND. \
	          A table that contains port-specific \
		  information for the MICOM Port Counter \
		  Zeroing.;
	   HELP = ;
           CAPABILITIES = NET_CFG, VPN_CFG;"
           ::= { mcmIpCntr 1 }

mcmIpIfCntrZeroEntry OBJECT-TYPE
	SYNTAX  McmIpIfCntrZeroEntry
	ACCESS  not-accessible
	STATUS  obsolete
	DESCRIPTION
	  "NAME = ;
	   DESC = A list of information maintained by \
		  every port about the MICOM E-type Filter \
		  parameters for that port.;
	   HELP = ;
           CAPABILITIES = NET_CFG, VPN_CFG;"
           INDEX   { mcmIpIfCntrZeroIndex }
           ::= { mcmIpIfCntrZeroTable 1 }

McmIpIfCntrZeroEntry ::=
           SEQUENCE {
               mcmIpIfCntrZeroIndex
                   INTEGER,
               mcmIpIfGrpCounterZero
                   INTEGER
	}


mcmIpIfCntrZeroIndex OBJECT-TYPE
	SYNTAX	INTEGER
	ACCESS	write-only
	STATUS	obsolete
	DESCRIPTION
	  "NAME = ;
	   DESC = The Index to which this entry pertains.;
	   HELP = ;
           CAPABILITIES = ;"
	::= { mcmIpIfCntrZeroEntry 1 }

mcmIpIfGrpCounterZero OBJECT-TYPE
	SYNTAX  INTEGER { reset(1), other(2) }
	ACCESS	write-only
	STATUS  obsolete
	DESCRIPTION
	  "NAME = ;
	   DESC = When set to reset, the Interfaces Group \
		  Counters should be zeroed out.;
	   HELP = ;
           CAPABILITIES = ;"
   ::= { mcmIpIfCntrZeroEntry 2 }


mcmIpCntrGrp    OBJECT IDENTIFIER ::= { mcmIpCntr 2 }

--  ** NOTE:THE OBJECTS IN THE FOLLOWING GROUP ARE
--     OBSOLETE AND NO LONGER SUPPORTED IN RELEASE
--     3.0 AND BEYOND. 


mcmIpGrpCounterZero OBJECT-TYPE
	SYNTAX  INTEGER { reset(1), other(2) }
	ACCESS	write-only
	STATUS  obsolete
	DESCRIPTION
	  "NAME = ; 
           DESC = When set to reset, the IP Counters should \
		  be zeroed out.;
	   HELP = ;
           CAPABILITIES = NET_CFG, VPN_CFG;"
  	::= { mcmIpCntrGrp 1 }

mcmIcmpGrpCounterZero OBJECT-TYPE
	SYNTAX  INTEGER { reset(1), other(2) }
	ACCESS	write-only
	STATUS  obsolete
	DESCRIPTION
	  "NAME = ;
	   DESC = When set to reset, the ICMP Counters \
		  should be zeroed out.;
	   HELP = ;
           CAPABILITIES = NET_CFG, VPN_CFG;"
  	::= { mcmIpCntrGrp 2 }

mcmTcpGrpCounterZero OBJECT-TYPE
	SYNTAX  INTEGER { reset(1), other(2) }
	ACCESS	write-only
	STATUS  obsolete
	DESCRIPTION
	  "NAME = ;
	   DESC = When set to reset, the TCP Counters \
		  should be zeroed out.;
	   HELP = ;
           CAPABILITIES = NET_CFG, VPN_CFG;"
  	::= { mcmIpCntrGrp 3 }

mcmUdpGrpCounterZero OBJECT-TYPE
	SYNTAX  INTEGER { reset(1), other(2) }
	ACCESS	write-only
	STATUS  obsolete
	DESCRIPTION
	  "NAME = ;
	   DESC = When set to reset, the UDP Counters \
                  should be zeroed out.;
           HELP = ;
	   CAPABILITIES = NET_CFG, VPN_CFG;"
  	::= { mcmIpCntrGrp 4 }

mcmSnmpGrpCounterZero OBJECT-TYPE
	SYNTAX  INTEGER { reset(1), other(2) }
	ACCESS	write-only
	STATUS  obsolete
	DESCRIPTION
	  "NAME = ;
	   DESC = When set to reset, the SNMP Counters \
		  should be zeroed out.;
	   HELP = ;
           CAPABILITIES = NET_CFG, VPN_CFG;"
  	::= { mcmIpCntrGrp 5 }

-- Inverse ARP Table

mcmInverseArpTable OBJECT-TYPE
	SYNTAX SEQUENCE OF McmInverseArpEntry
	ACCESS not-accessible
	STATUS mandatory
	DESCRIPTION
	  "NAME = ;
	   DESC = This table gives  information \
                  on the status (enable/disable) of Inverse \
                  ARP for a protocol for a specific DLCI.;
           HELP = Inverse ARP is used to get the IP Address \
                  of the Core Router from the branch \
                  OSCAR using the Frame Relay DLCI NNumber \
                  that is used to  connect to the Core Router.;
	   CAPABILITIES = NET_CFG, VPN_CFG;"
	::= { mcmIp 8 }

mcmInverseArpEntry OBJECT-TYPE
	SYNTAX  McmInverseArpEntry
	ACCESS  not-accessible
	STATUS  mandatory
	DESCRIPTION
	  "NAME = ;
	   DESC = Inverse ARP for a DLCI for a protocol.;
	   HELP = ;
           CAPABILITIES = ;"
	INDEX 	{ 
                  mcmInverseArpIfIndex,
		  mcmInverseArpProtocol
		}
   ::= { mcmInverseArpTable 1 }

McmInverseArpEntry ::=
           SEQUENCE {
               mcmInverseArpIfIndex
                   INTEGER,
               mcmInverseArpProtocol
                   INTEGER,
               mcmInverseArpStatus
                   INTEGER
           }

mcmInverseArpIfIndex OBJECT-TYPE
	SYNTAX  INTEGER (1..255)
	ACCESS  read-only
	STATUS  mandatory
	DESCRIPTION
	  "NAME = ;
            DESC = The index value which uniquely identifies \
                   the interface to which this entry is applicable.;
	   HELP =  ;
	   CAPABILITIES = ;"
           ::= {mcmInverseArpEntry  1 }

mcmInverseArpProtocol OBJECT-TYPE
       	SYNTAX  INTEGER { ip(1) }
	ACCESS  read-only
	STATUS  mandatory
	DESCRIPTION
	  "NAME = ;
	   DESC = The protocol that is used for Auto-discovery of \
                  IP address.;
	   HELP =  ;
	   CAPABILITIES = ;"
           ::= { mcmInverseArpEntry 2 }

mcmInverseArpStatus OBJECT-TYPE
	SYNTAX  INTEGER { enable(1), disable(2) }
	ACCESS  read-only
	STATUS  mandatory
	DESCRIPTION
	  "NAME = ;
	   DESC = This tells weather InversArp is enabled or not.;
           HELP =  ;
	   CAPABILITIES = ;"
           ::= { mcmInverseArpEntry 3 }

-- NVM Inverse ARP Table

nvmInverseArpTable OBJECT-TYPE
	SYNTAX SEQUENCE OF NvmInverseArpEntry
	ACCESS not-accessible
	STATUS mandatory
	DESCRIPTION
	  "NAME = ;
	   DESC = This table gives  information \
                  on the status (enable/disable) of Inverse \
                  ARP for a protocol for a specific DLCI.;
           HELP = Inverse ARP is used to get the IP Address \
                  of the Core Router from the branch \
                  OSCAR using the Frame Relay DLCI NNumber \
                  that is used to  connect to the Core Router.;
	   CAPABILITIES = NET_CFG, VPN_CFG;"
	::= { mcmIp 9 }

nvmInverseArpEntry OBJECT-TYPE
	SYNTAX  NvmInverseArpEntry
	ACCESS  not-accessible
	STATUS  mandatory
	DESCRIPTION
	  "NAME = ;
	   DESC = Inverse ARP for a DLCI for a protocol.;
	   HELP = ;
           CAPABILITIES = ;"
	INDEX 	{ 
                  nvmInverseArpIfIndex,
		  nvmInverseArpProtocol
		}
   ::= { nvmInverseArpTable 1 }

NvmInverseArpEntry ::=
           SEQUENCE {
               nvmInverseArpIfIndex
                   INTEGER,
               nvmInverseArpProtocol
                   INTEGER,
               nvmInverseArpStatus
                   INTEGER
           }

nvmInverseArpIfIndex OBJECT-TYPE
	SYNTAX  INTEGER (1..255)
	ACCESS  read-only
	STATUS  mandatory
	DESCRIPTION
	  "NAME = ;
	   DESC = The index value which uniquely identifies \
                   the interface to which this entry is applicable.;
	   HELP =  ;
	   CAPABILITIES = ;"
           ::= {nvmInverseArpEntry  1 }

nvmInverseArpProtocol OBJECT-TYPE
       	SYNTAX  INTEGER { ip(1) }
	ACCESS  read-only
	STATUS  mandatory
	DESCRIPTION
	  "NAME = ;
	   DESC = The protocol that is used for Auto-discovery of \
                  IP address.;
           HELP =  ;
	   CAPABILITIES = ;"
           ::= { nvmInverseArpEntry 2 }

nvmInverseArpStatus OBJECT-TYPE
	SYNTAX  INTEGER { enable(1), disable(2) }
	ACCESS  read-write
	STATUS  mandatory
	DESCRIPTION
	  "NAME = ;
	   DESC = This tells weather InversArp is enabled or not.;
	   HELP =  ;
	   CAPABILITIES = ;"
           ::= { nvmInverseArpEntry 3 }
END
