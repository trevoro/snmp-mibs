--			Ascend mibatmif MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBATMIF-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibatmInterfaceProfile  OBJECT IDENTIFIER ::= { configuration 40}

	-- The mibatmInterfaceProfile table
	--
	-- This table contains parameters for the mibatmInterfaceProfile profile
	--

    mibatmInterfaceProfileTable	OBJECT-TYPE
	SYNTAX		SEQUENCE OF MibatmInterfaceProfileEntry
	ACCESS		not-accessible
	STATUS		mandatory
	DESCRIPTION	"A list of mibatmInterfaceProfile profile entries."
	::= { mibatmInterfaceProfile 1 }

    mibatmInterfaceProfileEntry	OBJECT-TYPE
	SYNTAX		MibatmInterfaceProfileEntry
	ACCESS		not-accessible
	STATUS		mandatory
	DESCRIPTION	"A mibatmInterfaceProfile entry containing objects that
			 maps to the parameters of mibatmInterfaceProfile profile."
	INDEX		{ atmInterfaceProfile-Shelf-o, atmInterfaceProfile-Slot-o, atmInterfaceProfile-Item-o, atmInterfaceProfile-LogicalItem-o }
	::= { mibatmInterfaceProfileTable 1 }

    MibatmInterfaceProfileEntry ::=
	SEQUENCE {
	    atmInterfaceProfile-Shelf-o
		INTEGER,
	    atmInterfaceProfile-Slot-o
		INTEGER,
	    atmInterfaceProfile-Item-o
		INTEGER,
	    atmInterfaceProfile-LogicalItem-o
		INTEGER,
	    atmInterfaceProfile-InterfaceAddress-PhysicalAddress-Shelf
		INTEGER,
	    atmInterfaceProfile-InterfaceAddress-PhysicalAddress-Slot
		INTEGER,
	    atmInterfaceProfile-InterfaceAddress-PhysicalAddress-ItemNumber
		INTEGER,
	    atmInterfaceProfile-InterfaceAddress-LogicalItem
		INTEGER,
	    atmInterfaceProfile-Name
		DisplayString,
	    atmInterfaceProfile-SvcOptions-Enabled
		INTEGER,
	    atmInterfaceProfile-SvcOptions-AtmProtocol
		INTEGER,
	    atmInterfaceProfile-SvcOptions-AtmAddress-NumberingPlan
		INTEGER,
	    atmInterfaceProfile-SvcOptions-AtmAddress-E164NativeAddress
		DisplayString,
	    atmInterfaceProfile-SvcOptions-AtmAddress-AesaAddress-Format
		INTEGER,
	    atmInterfaceProfile-SvcOptions-AtmAddress-AesaAddress-IdpPortion-Afi
		DisplayString,
	    atmInterfaceProfile-SvcOptions-AtmAddress-AesaAddress-IdpPortion-Idi
		DisplayString,
	    atmInterfaceProfile-SvcOptions-AtmAddress-AesaAddress-DspPortion-HoDsp
		DisplayString,
	    atmInterfaceProfile-SvcOptions-AtmAddress-AesaAddress-DspPortion-Esi
		DisplayString,
	    atmInterfaceProfile-SvcOptions-AtmAddress-AesaAddress-DspPortion-Sel
		DisplayString,
	    atmInterfaceProfile-SvcOptions-InsertCallingPartyAddr
		INTEGER,
	    atmInterfaceProfile-SvcOptions-Q93bOptions-MaxRestart
		INTEGER,
	    atmInterfaceProfile-SvcOptions-Q93bOptions-MaxStatenq
		INTEGER,
	    atmInterfaceProfile-SvcOptions-Q93bOptions-T301Ms
		INTEGER,
	    atmInterfaceProfile-SvcOptions-Q93bOptions-T303Ms
		INTEGER,
	    atmInterfaceProfile-SvcOptions-Q93bOptions-T306Ms
		INTEGER,
	    atmInterfaceProfile-SvcOptions-Q93bOptions-T308Ms
		INTEGER,
	    atmInterfaceProfile-SvcOptions-Q93bOptions-T309Ms
		INTEGER,
	    atmInterfaceProfile-SvcOptions-Q93bOptions-T310Ms
		INTEGER,
	    atmInterfaceProfile-SvcOptions-Q93bOptions-T313Ms
		INTEGER,
	    atmInterfaceProfile-SvcOptions-Q93bOptions-T316Ms
		INTEGER,
	    atmInterfaceProfile-SvcOptions-Q93bOptions-T317Ms
		INTEGER,
	    atmInterfaceProfile-SvcOptions-Q93bOptions-T322Ms
		INTEGER,
	    atmInterfaceProfile-SvcOptions-Q93bOptions-T331Ms
		INTEGER,
	    atmInterfaceProfile-SvcOptions-Q93bOptions-T333Ms
		INTEGER,
	    atmInterfaceProfile-SvcOptions-Q93bOptions-T397Ms
		INTEGER,
	    atmInterfaceProfile-SvcOptions-Q93bOptions-T398Ms
		INTEGER,
	    atmInterfaceProfile-SvcOptions-Q93bOptions-T399Ms
		INTEGER,
	    atmInterfaceProfile-SvcOptions-Q93bOptions-SaalRetryMs
		INTEGER,
	    atmInterfaceProfile-SvcOptions-Q93bOptions-T303NumReties
		INTEGER,
	    atmInterfaceProfile-SvcOptions-Q93bOptions-T308NumRetries
		INTEGER,
	    atmInterfaceProfile-SvcOptions-Q93bOptions-T316NumRetries
		INTEGER,
	    atmInterfaceProfile-SvcOptions-Q93bOptions-T322NumRetries
		INTEGER,
	    atmInterfaceProfile-SvcOptions-Q93bOptions-T331NumRetries
		INTEGER,
	    atmInterfaceProfile-SvcOptions-Q93bOptions-AssignVpiVci
		INTEGER,
	    atmInterfaceProfile-SvcOptions-QsaalOptions-WindowSize
		INTEGER,
	    atmInterfaceProfile-SvcOptions-QsaalOptions-MaxCc
		INTEGER,
	    atmInterfaceProfile-SvcOptions-QsaalOptions-MaxPd
		INTEGER,
	    atmInterfaceProfile-SvcOptions-QsaalOptions-MaxStat
		INTEGER,
	    atmInterfaceProfile-SvcOptions-QsaalOptions-TccMs
		INTEGER,
	    atmInterfaceProfile-SvcOptions-QsaalOptions-TpollMs
		INTEGER,
	    atmInterfaceProfile-SvcOptions-QsaalOptions-TkeepaliveMs
		INTEGER,
	    atmInterfaceProfile-SvcOptions-QsaalOptions-TnoresponseMs
		INTEGER,
	    atmInterfaceProfile-SvcOptions-QsaalOptions-TidleMs
		INTEGER,
	    atmInterfaceProfile-SvcOptions-QsaalOptions-PollAfterRetransmission
		INTEGER,
	    atmInterfaceProfile-SvcOptions-QsaalOptions-RepeatUstat
		INTEGER,
	    atmInterfaceProfile-SvcOptions-QsaalOptions-UstatRspToPoll
		INTEGER,
	    atmInterfaceProfile-Action-o
		INTEGER
	}

    atmInterfaceProfile-Shelf-o	OBJECT-TYPE
	SYNTAX	INTEGER
	ACCESS	read-only
	STATUS	mandatory
	DESCRIPTION	""
	::= { mibatmInterfaceProfileEntry 1 }

    atmInterfaceProfile-Slot-o	OBJECT-TYPE
	SYNTAX	INTEGER
	ACCESS	read-only
	STATUS	mandatory
	DESCRIPTION	""
	::= { mibatmInterfaceProfileEntry 2 }

    atmInterfaceProfile-Item-o	OBJECT-TYPE
	SYNTAX	INTEGER
	ACCESS	read-only
	STATUS	mandatory
	DESCRIPTION	""
	::= { mibatmInterfaceProfileEntry 3 }

    atmInterfaceProfile-LogicalItem-o	OBJECT-TYPE
	SYNTAX	INTEGER
	ACCESS	read-only
	STATUS	mandatory
	DESCRIPTION	""
	::= { mibatmInterfaceProfileEntry 4 }

    atmInterfaceProfile-InterfaceAddress-PhysicalAddress-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { mibatmInterfaceProfileEntry 5 }

    atmInterfaceProfile-InterfaceAddress-PhysicalAddress-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { mibatmInterfaceProfileEntry 6 }

    atmInterfaceProfile-InterfaceAddress-PhysicalAddress-ItemNumber	OBJECT-TYPE
	SYNTAX	INTEGER
	ACCESS	read-write
	STATUS	mandatory
	DESCRIPTION	"A number that specifies an addressable entity within the context of shelf and slot."
	::= { mibatmInterfaceProfileEntry 7 }

    atmInterfaceProfile-InterfaceAddress-LogicalItem	OBJECT-TYPE
	SYNTAX	INTEGER
	ACCESS	read-write
	STATUS	mandatory
	DESCRIPTION	"A number that specifies an addressable logical entity within the context of a physical address."
	::= { mibatmInterfaceProfileEntry 8 }

    atmInterfaceProfile-Name	OBJECT-TYPE
	SYNTAX	DisplayString
	ACCESS	read-write
	STATUS	mandatory
	DESCRIPTION	"Name of ATM Interface."
	::= { mibatmInterfaceProfileEntry 9 }

    atmInterfaceProfile-SvcOptions-Enabled	OBJECT-TYPE
	SYNTAX	INTEGER {
		    no (1),
		    yes (2)
		}
	ACCESS	read-write
	STATUS	mandatory
	DESCRIPTION	"SVC signalling (Q.93b) is enabled on this link."
	::= { mibatmInterfaceProfileEntry 10 }

    atmInterfaceProfile-SvcOptions-AtmProtocol	OBJECT-TYPE
	SYNTAX	INTEGER {
		    uni30 (2),
		    uni31 (3)
		}
	ACCESS	read-write
	STATUS	mandatory
	DESCRIPTION	"ATM protocol on this link."
	::= { mibatmInterfaceProfileEntry 11 }

    atmInterfaceProfile-SvcOptions-AtmAddress-NumberingPlan	OBJECT-TYPE
	SYNTAX	INTEGER {
		    undefined (1),
		    isdn (2),
		    aesa (3),
		    unknown (5),
		    x121 (9)
		}
	ACCESS	read-write
	STATUS	mandatory
	DESCRIPTION	"Numbering plan for an SVC address"
	::= { mibatmInterfaceProfileEntry 12 }

    atmInterfaceProfile-SvcOptions-AtmAddress-E164NativeAddress	OBJECT-TYPE
	SYNTAX	DisplayString
	ACCESS	read-write
	STATUS	mandatory
	DESCRIPTION	"An SVC address in a native E.164 format."
	::= { mibatmInterfaceProfileEntry 13 }

    atmInterfaceProfile-SvcOptions-AtmAddress-AesaAddress-Format	OBJECT-TYPE
	SYNTAX	INTEGER {
		    undefined (1),
		    dccAesa (2),
		    icdAesa (6),
		    e164Aesa (4),
		    customAesa (5)
		}
	ACCESS	read-write
	STATUS	mandatory
	DESCRIPTION	"An AESA address format used to define this SVC address."
	::= { mibatmInterfaceProfileEntry 14 }

    atmInterfaceProfile-SvcOptions-AtmAddress-AesaAddress-IdpPortion-Afi	OBJECT-TYPE
	SYNTAX	DisplayString
	ACCESS	read-write
	STATUS	mandatory
	DESCRIPTION	"An Authority and Format Identifier(AFI) for AESA address. Must be defined for every AESA address."
	::= { mibatmInterfaceProfileEntry 15 }

    atmInterfaceProfile-SvcOptions-AtmAddress-AesaAddress-IdpPortion-Idi	OBJECT-TYPE
	SYNTAX	DisplayString
	ACCESS	read-write
	STATUS	mandatory
	DESCRIPTION	"An Initial Domain Identifier (IDI) portion of the AESA address."
	::= { mibatmInterfaceProfileEntry 16 }

    atmInterfaceProfile-SvcOptions-AtmAddress-AesaAddress-DspPortion-HoDsp	OBJECT-TYPE
	SYNTAX	DisplayString
	ACCESS	read-write
	STATUS	mandatory
	DESCRIPTION	"A High-Order Domain-Specific Part of AESA address. The IDP portion determine the format of the HO-DSP."
	::= { mibatmInterfaceProfileEntry 17 }

    atmInterfaceProfile-SvcOptions-AtmAddress-AesaAddress-DspPortion-Esi	OBJECT-TYPE
	SYNTAX	DisplayString
	ACCESS	read-write
	STATUS	mandatory
	DESCRIPTION	"An End System Identifier (ESI) which uniquely identifies the end system within the specified subnetwork."
	::= { mibatmInterfaceProfileEntry 18 }

    atmInterfaceProfile-SvcOptions-AtmAddress-AesaAddress-DspPortion-Sel	OBJECT-TYPE
	SYNTAX	DisplayString
	ACCESS	read-write
	STATUS	mandatory
	DESCRIPTION	"A selector (SEL) field that may be used by the end system."
	::= { mibatmInterfaceProfileEntry 19 }

    atmInterfaceProfile-SvcOptions-InsertCallingPartyAddr	OBJECT-TYPE
	SYNTAX	INTEGER {
		    no (1),
		    yes (2)
		}
	ACCESS	read-write
	STATUS	mandatory
	DESCRIPTION	"Insert ATM address of this interface in calling party address IE during call setup."
	::= { mibatmInterfaceProfileEntry 20 }

    atmInterfaceProfile-SvcOptions-Q93bOptions-MaxRestart	OBJECT-TYPE
	SYNTAX	INTEGER
	ACCESS	read-write
	STATUS	mandatory
	DESCRIPTION	"Maximum number of unacknowledged tx RESTART."
	::= { mibatmInterfaceProfileEntry 21 }

    atmInterfaceProfile-SvcOptions-Q93bOptions-MaxStatenq	OBJECT-TYPE
	SYNTAX	INTEGER
	ACCESS	read-write
	STATUS	mandatory
	DESCRIPTION	"Maximum number of unacknowledged tx STATUS ENQ."
	::= { mibatmInterfaceProfileEntry 22 }

    atmInterfaceProfile-SvcOptions-Q93bOptions-T301Ms	OBJECT-TYPE
	SYNTAX	INTEGER
	ACCESS	read-write
	STATUS	mandatory
	DESCRIPTION	"Timer (in msec) for alerting supervision function. This timer is started on receipt of ALERT in Call received/delivered state and stopped when CONNECT is received."
	::= { mibatmInterfaceProfileEntry 23 }

    atmInterfaceProfile-SvcOptions-Q93bOptions-T303Ms	OBJECT-TYPE
	SYNTAX	INTEGER
	ACCESS	read-write
	STATUS	mandatory
	DESCRIPTION	"Timer (in msec) for a response after SETUP is sent. This timer is stopped when the CONNECT, CALL PROCEEDING, or RELEASE COMPLETE is received."
	::= { mibatmInterfaceProfileEntry 24 }

    atmInterfaceProfile-SvcOptions-Q93bOptions-T306Ms	OBJECT-TYPE
	SYNTAX	INTEGER
	ACCESS	read-write
	STATUS	mandatory
	DESCRIPTION	"Timer (in msec) for a RELEASE_COMPLETE to be received after a release has been sent."
	::= { mibatmInterfaceProfileEntry 25 }

    atmInterfaceProfile-SvcOptions-Q93bOptions-T308Ms	OBJECT-TYPE
	SYNTAX	INTEGER
	ACCESS	read-write
	STATUS	mandatory
	DESCRIPTION	"Timer (in msec) for a response after RELEASE is sent. This is a release indication timer. This timer is started when the RELEASE message is sent and normally is stopped when the RELEASE or RELEASE COMPLETE is received."
	::= { mibatmInterfaceProfileEntry 26 }

    atmInterfaceProfile-SvcOptions-Q93bOptions-T309Ms	OBJECT-TYPE
	SYNTAX	INTEGER
	ACCESS	read-write
	STATUS	mandatory
	DESCRIPTION	"Timer (in msec) for Q.SAAL to reconnect. After this time, calls are dropped. When set to 0, a default value based on an ATM signaling protocol will be used."
	::= { mibatmInterfaceProfileEntry 27 }

    atmInterfaceProfile-SvcOptions-Q93bOptions-T310Ms	OBJECT-TYPE
	SYNTAX	INTEGER
	ACCESS	read-write
	STATUS	mandatory
	DESCRIPTION	"Timer (in msec) for a response after SETUP is received. Also called the CALL PROCEEDING timer."
	::= { mibatmInterfaceProfileEntry 28 }

    atmInterfaceProfile-SvcOptions-Q93bOptions-T313Ms	OBJECT-TYPE
	SYNTAX	INTEGER
	ACCESS	read-write
	STATUS	mandatory
	DESCRIPTION	"Timer (in msec) for a response after CONNECT is sent. Also called the connect request timer. It is started when the CONNECT is sent and stopped when the CONNECT ACKNOWLEDGE is recieved."
	::= { mibatmInterfaceProfileEntry 29 }

    atmInterfaceProfile-SvcOptions-Q93bOptions-T316Ms	OBJECT-TYPE
	SYNTAX	INTEGER
	ACCESS	read-write
	STATUS	mandatory
	DESCRIPTION	"Timer (in msec) for a response after RESTART is sent. Also called the restart request timer. It is started when the RESTART is sent and stopped when the RESTART ACKNOWLEDGE is recieved."
	::= { mibatmInterfaceProfileEntry 30 }

    atmInterfaceProfile-SvcOptions-Q93bOptions-T317Ms	OBJECT-TYPE
	SYNTAX	INTEGER
	ACCESS	read-write
	STATUS	mandatory
	DESCRIPTION	"Timer (in msec) for internal clearing of call references. This timer is started as a result of a restart and cleared when all the internal call references are cleared. Should be less than the the likely value of T316 of the peer."
	::= { mibatmInterfaceProfileEntry 31 }

    atmInterfaceProfile-SvcOptions-Q93bOptions-T322Ms	OBJECT-TYPE
	SYNTAX	INTEGER
	ACCESS	read-write
	STATUS	mandatory
	DESCRIPTION	"Timer (in msec) for a response after STATUS ENQ is sent."
	::= { mibatmInterfaceProfileEntry 32 }

    atmInterfaceProfile-SvcOptions-Q93bOptions-T331Ms	OBJECT-TYPE
	SYNTAX	INTEGER
	ACCESS	read-write
	STATUS	mandatory
	DESCRIPTION	"Timer (in msec) for internal clearing of call references."
	::= { mibatmInterfaceProfileEntry 33 }

    atmInterfaceProfile-SvcOptions-Q93bOptions-T333Ms	OBJECT-TYPE
	SYNTAX	INTEGER
	ACCESS	read-write
	STATUS	mandatory
	DESCRIPTION	"Timer (in msec) for internal clearing of call references."
	::= { mibatmInterfaceProfileEntry 34 }

    atmInterfaceProfile-SvcOptions-Q93bOptions-T397Ms	OBJECT-TYPE
	SYNTAX	INTEGER
	ACCESS	read-write
	STATUS	mandatory
	DESCRIPTION	"Timer (in msec) for internal clearing of call references."
	::= { mibatmInterfaceProfileEntry 35 }

    atmInterfaceProfile-SvcOptions-Q93bOptions-T398Ms	OBJECT-TYPE
	SYNTAX	INTEGER
	ACCESS	read-write
	STATUS	mandatory
	DESCRIPTION	"Timer (in msec) for receipt of a response to a DROP PARTY that was sent."
	::= { mibatmInterfaceProfileEntry 36 }

    atmInterfaceProfile-SvcOptions-Q93bOptions-T399Ms	OBJECT-TYPE
	SYNTAX	INTEGER
	ACCESS	read-write
	STATUS	mandatory
	DESCRIPTION	"Timer (in msec) for receipt of a response to an ADD PARTY that was sent."
	::= { mibatmInterfaceProfileEntry 37 }

    atmInterfaceProfile-SvcOptions-Q93bOptions-SaalRetryMs	OBJECT-TYPE
	SYNTAX	INTEGER
	ACCESS	read-write
	STATUS	mandatory
	DESCRIPTION	"Timer value for retrying AAL_ESTABLISH messages."
	::= { mibatmInterfaceProfileEntry 38 }

    atmInterfaceProfile-SvcOptions-Q93bOptions-T303NumReties	OBJECT-TYPE
	SYNTAX	INTEGER
	ACCESS	read-write
	STATUS	mandatory
	DESCRIPTION	"Number of times SETUP could be resent in case of T303 timer expiry."
	::= { mibatmInterfaceProfileEntry 39 }

    atmInterfaceProfile-SvcOptions-Q93bOptions-T308NumRetries	OBJECT-TYPE
	SYNTAX	INTEGER
	ACCESS	read-write
	STATUS	mandatory
	DESCRIPTION	"Number of times RELEASE could be sent in case of T308 timer expiry."
	::= { mibatmInterfaceProfileEntry 40 }

    atmInterfaceProfile-SvcOptions-Q93bOptions-T316NumRetries	OBJECT-TYPE
	SYNTAX	INTEGER
	ACCESS	read-write
	STATUS	mandatory
	DESCRIPTION	"Number of times RESTART could be sent in case RESTART ACK is not received withinn T316 timer expiry."
	::= { mibatmInterfaceProfileEntry 41 }

    atmInterfaceProfile-SvcOptions-Q93bOptions-T322NumRetries	OBJECT-TYPE
	SYNTAX	INTEGER
	ACCESS	read-write
	STATUS	mandatory
	DESCRIPTION	"Number of times STAT ENQ could be sent before a response is received within the T322 timer expiry."
	::= { mibatmInterfaceProfileEntry 42 }

    atmInterfaceProfile-SvcOptions-Q93bOptions-T331NumRetries	OBJECT-TYPE
	SYNTAX	INTEGER
	ACCESS	read-write
	STATUS	mandatory
	DESCRIPTION	""
	::= { mibatmInterfaceProfileEntry 43 }

    atmInterfaceProfile-SvcOptions-Q93bOptions-AssignVpiVci	OBJECT-TYPE
	SYNTAX	INTEGER {
		    no (1),
		    yes (2)
		}
	ACCESS	read-write
	STATUS	mandatory
	DESCRIPTION	"In the case of UNI4.0 and PNNI this parameter specifies who assigns the VPI/VCI. TRUE will allow the local stack and FALSE will let the partner stack to assign."
	::= { mibatmInterfaceProfileEntry 44 }

    atmInterfaceProfile-SvcOptions-QsaalOptions-WindowSize	OBJECT-TYPE
	SYNTAX	INTEGER
	ACCESS	read-write
	STATUS	mandatory
	DESCRIPTION	"Q.SAAL window size"
	::= { mibatmInterfaceProfileEntry 45 }

    atmInterfaceProfile-SvcOptions-QsaalOptions-MaxCc	OBJECT-TYPE
	SYNTAX	INTEGER
	ACCESS	read-write
	STATUS	mandatory
	DESCRIPTION	"Maximum number of control PDU (BGN, END, RESYNC) retransmissions."
	::= { mibatmInterfaceProfileEntry 46 }

    atmInterfaceProfile-SvcOptions-QsaalOptions-MaxPd	OBJECT-TYPE
	SYNTAX	INTEGER
	ACCESS	read-write
	STATUS	mandatory
	DESCRIPTION	"Maximum number of Sequenced data PDU's between poll."
	::= { mibatmInterfaceProfileEntry 47 }

    atmInterfaceProfile-SvcOptions-QsaalOptions-MaxStat	OBJECT-TYPE
	SYNTAX	INTEGER
	ACCESS	read-write
	STATUS	mandatory
	DESCRIPTION	"Maximum length of STAT PDU."
	::= { mibatmInterfaceProfileEntry 48 }

    atmInterfaceProfile-SvcOptions-QsaalOptions-TccMs	OBJECT-TYPE
	SYNTAX	INTEGER
	ACCESS	read-write
	STATUS	mandatory
	DESCRIPTION	"Retry time (in msec) for control PDU's(BGN, END, RESYNC)."
	::= { mibatmInterfaceProfileEntry 49 }

    atmInterfaceProfile-SvcOptions-QsaalOptions-TpollMs	OBJECT-TYPE
	SYNTAX	INTEGER
	ACCESS	read-write
	STATUS	mandatory
	DESCRIPTION	"Poll sent (in msec) when active. When set to 0, a default value based on an ATM signaling protocol will be used."
	::= { mibatmInterfaceProfileEntry 50 }

    atmInterfaceProfile-SvcOptions-QsaalOptions-TkeepaliveMs	OBJECT-TYPE
	SYNTAX	INTEGER
	ACCESS	read-write
	STATUS	mandatory
	DESCRIPTION	"Poll sent (in msec) when in transient state. When set to 0, a default value based on an ATM signaling protocol will be used."
	::= { mibatmInterfaceProfileEntry 51 }

    atmInterfaceProfile-SvcOptions-QsaalOptions-TnoresponseMs	OBJECT-TYPE
	SYNTAX	INTEGER
	ACCESS	read-write
	STATUS	mandatory
	DESCRIPTION	"STAT received at least this period(in msec). When set to 0, a default value based on an ATM signaling protocol will be used."
	::= { mibatmInterfaceProfileEntry 52 }

    atmInterfaceProfile-SvcOptions-QsaalOptions-TidleMs	OBJECT-TYPE
	SYNTAX	INTEGER
	ACCESS	read-write
	STATUS	mandatory
	DESCRIPTION	"Poll sent (in msec) when idle -- UNI 3.1, only."
	::= { mibatmInterfaceProfileEntry 53 }

    atmInterfaceProfile-SvcOptions-QsaalOptions-PollAfterRetransmission	OBJECT-TYPE
	SYNTAX	INTEGER {
		    no (1),
		    yes (2)
		}
	ACCESS	read-write
	STATUS	mandatory
	DESCRIPTION	"Specifies after retransmitting PDUs whether a POLL must be sent before sending any further PDUs."
	::= { mibatmInterfaceProfileEntry 54 }

    atmInterfaceProfile-SvcOptions-QsaalOptions-RepeatUstat	OBJECT-TYPE
	SYNTAX	INTEGER {
		    no (1),
		    yes (2)
		}
	ACCESS	read-write
	STATUS	mandatory
	DESCRIPTION	"Specifies whether two USTAT messages should be sent each time it is required to be sent."
	::= { mibatmInterfaceProfileEntry 55 }

    atmInterfaceProfile-SvcOptions-QsaalOptions-UstatRspToPoll	OBJECT-TYPE
	SYNTAX	INTEGER {
		    no (1),
		    yes (2)
		}
	ACCESS	read-write
	STATUS	mandatory
	DESCRIPTION	"Specifies whether a USTAT should be sent in response to a POLL indicating an out of sequence PDU."
	::= { mibatmInterfaceProfileEntry 56 }

    atmInterfaceProfile-Action-o	OBJECT-TYPE
	SYNTAX	INTEGER {
		    noAction (1),
		    createProfile (2),
		    deleteProfile (3)
		}
	ACCESS	read-write
	STATUS	mandatory
	DESCRIPTION	""
	::= { mibatmInterfaceProfileEntry 57 }

END
