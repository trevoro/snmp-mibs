-- This file is corresponding to Release 6.1.2.100 from 2001/09/26 00:00:00
-- (C)opyright 1999 BinTec Communications AG
-- $RCSfile: mibcert,v $ 
-- $Revision: 1.6 $ 

BIANCA-BRICK-CERT-MIB DEFINITIONS ::= BEGIN
        IMPORTS
            IpAddress, Counter, TimeTicks
                FROM RFC1155-SMI
 
            OBJECT-TYPE
                FROM RFC-1212;

    org          OBJECT IDENTIFIER ::= { iso 3 }
    dod          OBJECT IDENTIFIER ::= { org 6 }
    internet     OBJECT IDENTIFIER ::= { dod 1 }
    private      OBJECT IDENTIFIER ::= { internet 4 }
    enterprises  OBJECT IDENTIFIER ::= { private 1 }
    bintec       OBJECT IDENTIFIER ::= { enterprises 272 }
    bibo         OBJECT IDENTIFIER ::= { bintec 4 }

    -- Management Information for the IPSec Subsystem of the BIANCA/BRICK, 
    ipsec        OBJECT IDENTIFIER
        ::= { bibo 26 }
    

	-- textual conventions

	DisplayString ::= OCTET STRING
	    -- This data type is used to model textual information taken
	    -- from the NVT ASCII character set.  By convention, objects
	    -- with this syntax are declared as having
	    --
	    --      SIZE (0..255)

    -- Management Information for the Certificate Management Subsystem of the 
    -- BIANCA/BRICK, belongs to the IPSec Group.

	cert   OBJECT IDENTIFIER ::= { ipsec 33 }

-- Global Settings for Certificate Management

	certGlobals OBJECT IDENTIFIER  ::= { cert 1 }
	--Static table containing global settings for the certificate management


	certGlobHttpProxy OBJECT-TYPE
	    SYNTAX DisplayString
            ACCESS  read-write
            STATUS  mandatory
            DESCRIPTION
		"This object specifies the HTTP proxy server which must be used
		 to access the HTTP certificate servers defined. It takes either
		 an IP-address or a fully qualified domain name."
	::= { certGlobals 1 }


	certGlobSocksServer OBJECT-TYPE
	    SYNTAX DisplayString
            ACCESS  read-write
            STATUS  mandatory
            DESCRIPTION
		"This object specifies the SOCKS server which must be used to
		 access the HTTP and LDAP certificate servers defined. It takes
		 either an IP-address or a fully qualified domain name."
	::= { certGlobals 2 }

	certGlobMaxCacheEntries OBJECT-TYPE
	    SYNTAX INTEGER 
            ACCESS  read-write
            STATUS  mandatory
            DESCRIPTION
		"This object specifies the maximum number of certificate-cache
		 entries allowed."
	::= { certGlobals 3 }

	certGlobMaxPathLength OBJECT-TYPE
	    SYNTAX INTEGER 
            ACCESS  read-write
            STATUS  mandatory
            DESCRIPTION
		"This object specifies the maximum number of intermediate CA
		certificates between a trusted root CA and a peer certificate
		accepted."
	::= { certGlobals 4 }

	certGlobMaxRestarts OBJECT-TYPE
	    SYNTAX INTEGER 
            ACCESS  read-write
            STATUS  mandatory
            DESCRIPTION
		"This object specifies the maximum number of restarts in one
		certificate search."
	::= { certGlobals 5 }

	certGlobMaxCertValidity OBJECT-TYPE
	    SYNTAX INTEGER 
            ACCESS  read-write
            STATUS  mandatory
            DESCRIPTION
		"This object specifies the maximum validity period of a
		certificate in seconds. A certificate will not be considered
		valid for a longer period of time even if its validity
		field specifies a longer period."
--                 ( 30 days )
	::= { certGlobals 6 }

	certGlobMaxCrlValidity OBJECT-TYPE
	    SYNTAX INTEGER 
            ACCESS  read-write
            STATUS  mandatory
            DESCRIPTION
		"This object specifies the maximum validity period of a
		certificate revocation list in seconds. A crl will not be
		considered valid for a longer period of time even if its
		validity field specifies a longer period."
--                 ( 1 day )
	::= { certGlobals 7 }

	certGlobNegCachePeriod OBJECT-TYPE
	    SYNTAX INTEGER 
            ACCESS  read-write
            STATUS  mandatory
            DESCRIPTION
		"This object specifies the period in seconds a certificate or
		crl search with a negative result will be remembered. Within
		this time, no new search will be performed for the same item."
--                 ( 1 hour )
	::= { certGlobals 8 }



-- Table of Certificate Servers

	certServerTable OBJECT-TYPE
            SYNTAX  SEQUENCE OF CertServerEntry
            ACCESS  not-accessible
            STATUS  mandatory
            DESCRIPTION
		"The certServerTable contains the list of certificate servers
		 used for certificate and crl requests."
	::= { cert 2 }

	certServerEntry OBJECT-TYPE
            SYNTAX  CertServerEntry
            ACCESS  not-accessible
            STATUS  mandatory
            DESCRIPTION
		"A certificate server entry defines the name of a certificate
		 server together with the protocols used to access it."
	    INDEX   {
		certServerPreference
	    }
            ::= { certServerTable 1 }

	CertServerEntry ::=
            SEQUENCE {
		certServerName			DisplayString,
		certServerUrl			DisplayString, 
		certServerPreference		INTEGER,
		certServerType			INTEGER
            }

	certServerName OBJECT-TYPE
	    SYNTAX DisplayString 
            ACCESS  read-write
            STATUS  mandatory
            DESCRIPTION
		 "This object specifies the name of a certificate server."
	::= { certServerEntry 1 }

	certServerUrl OBJECT-TYPE
	    SYNTAX DisplayString 
            ACCESS  read-write
            STATUS  mandatory
            DESCRIPTION
		 "This object specifies the url used for accessing the
		  certificate server. Syntax:
		  [<scheme>:][//[<user>[:<password>]@]<host>[:<port>]]/[<path>]
		  example: ldap://myname:mypass@ldap.ca.com:389/  ."
	::= { certServerEntry 2 }

	certServerPreference OBJECT-TYPE
	    SYNTAX INTEGER 
            ACCESS  read-write
            STATUS  mandatory
            DESCRIPTION
		 "This object specifies the preference of this server
		  with respect to the others. Servers with lower priority 
		  are accessed prior to others."
	::= { certServerEntry 3 }

	certServerType OBJECT-TYPE
	    SYNTAX INTEGER {
	    delete(1), -- mark this entry for deletion
	    server(2)  -- directory server
	    }
            ACCESS  read-write
            STATUS  mandatory
            DESCRIPTION
		 "This object specifies the type of the entry and is used to 
		  delete it."
	::= { certServerEntry 4 }

-- End Table of Certificate Servers



-- Table of Certificates

	certTable OBJECT-TYPE
            SYNTAX  SEQUENCE OF CertEntry
            ACCESS  not-accessible
            STATUS  mandatory
            DESCRIPTION
		"The certTable contains the list of certificates,
		 including own certificates and those of the trusted
		 certificate authorities."
	::= { cert 3 }

	certEntry OBJECT-TYPE
            SYNTAX  CertEntry
            ACCESS  not-accessible
            STATUS  mandatory
            DESCRIPTION
		"A certEntry contains either a peer's certificate, an
		 own certficate or a certificate of a trusted
		 certification authority, depending on the settings of
		 the certFlags field."
	    INDEX   {
		certIndex
	    }
            ::= { certTable 1 }

	CertEntry ::=
            SEQUENCE {
	        certIndex		INTEGER, 
		certDescription		DisplayString,
		certIsCA		INTEGER,
		certForceTrusted	INTEGER,
		certNoCrls		INTEGER, 
		certSerialNumber	DisplayString,
		certSubjectName		DisplayString,
		certSubjectAltNames	DisplayString,
		certIssuerName		DisplayString,
		certIssuerAltNames	DisplayString,
		certValidity		DisplayString,
		certPubKeyInfo		DisplayString,
		certKeyId	        OCTET STRING, 
		certPrivateKey		INTEGER,
		certMD5Fingerprint	OCTET STRING,
		certSHA1Fingerprint	OCTET STRING
            }

	certIndex OBJECT-TYPE
	    SYNTAX INTEGER
	    ACCESS read-only
	    STATUS mandatory
	    DESCRIPTION
		"A unique index of this certificate entry."
	::= { certEntry 1 }

	certDescription OBJECT-TYPE
	    SYNTAX DisplayString
	    ACCESS read-write
	    STATUS mandatory
	    DESCRIPTION
		"This object specifies the name of the X.509 Certificate."
	::= { certEntry 2 }

	certIsCA OBJECT-TYPE
	    SYNTAX INTEGER {
		true(1), 	-- A certificate of a trusted root CA
		false(2) 	-- An own or peer certificate
	    }
	    ACCESS read-write
	    STATUS mandatory
	    DESCRIPTION
		"This object specifies how the certificate is treated internally.
		  Possible Values:
		   true(1), 	-- A certificate of a trusted root CA
		   false(2) 	-- An own or peer certificate."
	::= { certEntry 3 }

	certForceTrusted OBJECT-TYPE
	    SYNTAX INTEGER {
		true(1), 	-- Always trust this certificate without 
				-- considering any CAs
		false(2) 	-- trust this certificate only, if there 
				-- exists a valid trust path from a CA to it 
				-- and it is not revoked
	    }
	    ACCESS read-write
	    STATUS mandatory
	    DESCRIPTION
		"This object specifies how the certificate is treated internally.
		  Possible Values:
		   true(1), 	-- Always trust this certificate without 
				-- considering any CAs
		   false(2) 	-- trust this certificate only, if there 
				-- exists a valid trust path from a CA to it 
				-- and it is not revoked."
	::= { certEntry 4 }

	certNoCrls OBJECT-TYPE
	    SYNTAX INTEGER {
		true(1), 	-- do not check for certificate revocation 
				-- lists for this CA (no meaning for non-CA 
				-- certificates)
		false(2) 	-- check for certificate revocation 
				-- lists for this CA
	    }
	    ACCESS read-write
	    STATUS mandatory
	    DESCRIPTION
		"This object specifies how the certificate is treated internally.
		  Possible Values:
		   true(1), 	-- do not check for certificate revocation 
				-- lists for this CA (no meaning for non-CA 
				-- certificates)
		   false(2) 	-- check for certificate revocation 
				-- lists for this CA (no meaning for non-CA 
				-- certificates)."
	::= { certEntry 5 }

	certSerialNumber OBJECT-TYPE
	    SYNTAX DisplayString
	    ACCESS read-only
	    STATUS mandatory
	    DESCRIPTION
		"This object specifies the serial number of the certificate."
	::= { certEntry 6 }

	certSubjectName OBJECT-TYPE
	    SYNTAX DisplayString
	    ACCESS read-only
	    STATUS mandatory
	    DESCRIPTION
		"The subject name of the certificate."
	::= { certEntry 7 }

	certSubjectAltNames OBJECT-TYPE
	    SYNTAX DisplayString
	    ACCESS read-only
	    STATUS mandatory
	    DESCRIPTION
		"The subject alternative name of the certificate. For IPSec,
		 this field (not the subject name) is taken by default as the
		 peer id, if not otherwise specified."
	::= { certEntry 8 }

	certIssuerName OBJECT-TYPE
	    SYNTAX DisplayString
	    ACCESS read-only
	    STATUS mandatory
	    DESCRIPTION
		"The name of the certificate authority which issued this
		 certificate."
	::= { certEntry 9 }

	certIssuerAltNames OBJECT-TYPE
	    SYNTAX DisplayString
	    ACCESS read-only
	    STATUS mandatory
	    DESCRIPTION
		"The alternative names of the certificate authority which issued
		 this certificate."
	::= { certEntry 10 }

	certValidity OBJECT-TYPE
	    SYNTAX DisplayString
	    ACCESS read-only
	    STATUS mandatory
	    DESCRIPTION
		"The validity period of this certificate in human readable form."
	::= { certEntry 11 }

	certPubKeyInfo OBJECT-TYPE
	    SYNTAX DisplayString
	    ACCESS read-only
	    STATUS mandatory
	    DESCRIPTION
		"This string shows the properties of the public key certified
		 in this certificate. These are the algorithm for which the key
		 is used and its length."
	::= { certEntry 12 }

	certKeyId OBJECT-TYPE
	    SYNTAX OCTET STRING
	    ACCESS read-only
	    STATUS mandatory
	    DESCRIPTION
		"The key id as contained in the extensions of the certificate,
		 if any."
	::= { certEntry 13 }

	certPrivateKey OBJECT-TYPE
	    SYNTAX INTEGER
	    ACCESS read-write
	    STATUS mandatory
	    DESCRIPTION
		"The index of the private key from the ipsecPublicKeyTable
		 corresponding to the public key in this certificate.
		 Used only for own certificates."
	::= { certEntry 14 }

	certMD5Fingerprint OBJECT-TYPE
	    SYNTAX OCTET STRING
	    ACCESS read-only
	    STATUS mandatory
	    DESCRIPTION
		"The fingerprint of the certificate computed as an MD5
		 hash of the DER encoded binary certificate data."
	::= { certEntry 24 }

	certSHA1Fingerprint OBJECT-TYPE
	    SYNTAX OCTET STRING
	    ACCESS read-only
	    STATUS mandatory
	    DESCRIPTION
		"The fingerprint of the certificate computed as an SHA1
		 hash of the DER encoded binary certificate data."
	::= { certEntry 25 }

-- End Table of Certificates



-- Table of Certificate Revocation Lists

	certRevListTable OBJECT-TYPE
            SYNTAX  SEQUENCE OF CertRevListEntry
            ACCESS  not-accessible
            STATUS  mandatory
            DESCRIPTION
		"The certRevListTable contains the dynamic list of certificate
		 revocation lists currently cached by the system."
	::= { cert 6 }

	certRevListEntry OBJECT-TYPE
            SYNTAX  CertRevListEntry
            ACCESS  not-accessible
            STATUS  mandatory
            DESCRIPTION
		"This object describes a certificate revocation list (CRL)
		 currently in the systems dynamic CRL cache."
	    INDEX   {
		certRevListIndex
	    }
            ::= { certRevListTable 1 }

	CertRevListEntry ::=
            SEQUENCE {
		certRevListIndex		INTEGER,
		certRevListDescription		DisplayString, 
		certRevListIssuerName		DisplayString,
		certRevListIssuerAltNames	DisplayString,
		certRevListSerialNumber		DisplayString, 
		certRevListValidity		DisplayString,
		certRevListNumCerts		INTEGER
            }

	certRevListIndex OBJECT-TYPE
	    SYNTAX INTEGER
	    ACCESS read-only
	    STATUS mandatory
	    DESCRIPTION
		"A unique index of this CRL."
	::= { certRevListEntry 1 }

	certRevListDescription OBJECT-TYPE
	    SYNTAX DisplayString
	    ACCESS read-write
	    STATUS mandatory
	    DESCRIPTION
		"This object specifies the name of the certificate
		 revocation list."
	::= { certRevListEntry 2 }

	certRevListIssuerName OBJECT-TYPE
	    SYNTAX DisplayString
	    ACCESS read-only
	    STATUS mandatory
	    DESCRIPTION
		"The name of the certificate authority which issued this CRL."
	::= { certRevListEntry 3 }

	certRevListIssuerAltNames OBJECT-TYPE
	    SYNTAX DisplayString
	    ACCESS read-only
	    STATUS mandatory
	    DESCRIPTION
		"The alternative names of the certificate authority which issued
		this CRL."
	::= { certRevListEntry 4 }

	certRevListSerialNumber OBJECT-TYPE
	    SYNTAX DisplayString
	    ACCESS read-only
	    STATUS mandatory
	    DESCRIPTION
		"The serial number of the CRL."
	::= { certRevListEntry 5 }

	certRevListValidity OBJECT-TYPE
	    SYNTAX DisplayString
	    ACCESS read-only
	    STATUS mandatory
	    DESCRIPTION
		"The issuing date of this CRL and the date the issuer is willing 
		 to issue the net update in human readable form."
	::= { certRevListEntry 6 }

	certRevListNumCerts OBJECT-TYPE
	    SYNTAX INTEGER
	    ACCESS read-only
	    STATUS mandatory
	    DESCRIPTION
		"The number of certificates contained in the CRL defined by this
		entry."
	::= { certRevListEntry 7 }

-- End Table of Certificate Revocation Lists





END		-- of BIANCA-BRICK-CERT-MIB definitions
