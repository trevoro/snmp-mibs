-- *****************************************************************
-- SNMP-FRAMEWORK-CAPABILITY.my:
-- Cisco SNMP-FRAMEWORK-MIB AGENT-CAPABILITIES
--
-- September 2003, Binh Le
--
-- Copyright (c) 2003, 2006 by Cisco Systems, Inc.
-- All rights reserved.
-- *****************************************************************

CISCO-SNMP-FRAMEWORK-CAPABILITY DEFINITIONS ::= BEGIN

IMPORTS
        MODULE-IDENTITY
                FROM SNMPv2-SMI
        AGENT-CAPABILITIES
                FROM SNMPv2-CONF
        ciscoAgentCapability
                FROM CISCO-SMI;

ciscoSnmpFrameworkCapability MODULE-IDENTITY
        LAST-UPDATED    "200605270000Z"
        ORGANIZATION    "Cisco Systems, Inc."
        CONTACT-INFO
                "       Cisco Systems
                        Customer Service

                Postal: 170 West Tasman Drive
                        San Jose, CA  95134
                        USA

                   Tel: +1 800 553-NETS

                E-mail: cs-lan-switch-snmp@cisco.com,
                        cs-snmp@cisco.com"
        DESCRIPTION
                "The capabilities description of
                 SNMP-FRAMEWORK-MIB."

        REVISION        "200605270000Z"
        DESCRIPTION
                "Added capability statement 
                 cSnmpFrameworkCapACSWV03R000 for 
                 Application Control Engine (ACE)."

        REVISION        "200309030000Z"
        DESCRIPTION
                "Initial version of this MIB module."
        ::= { ciscoAgentCapability 315 }

cSnmpFrameworkCapCatOSV05R0401 AGENT-CAPABILITIES
    PRODUCT-RELEASE      "Cisco CatOS 5.4(1)."
    STATUS               current
    DESCRIPTION          "SNMP-FRAMEWORK-MIB capabilities."

    SUPPORTS             SNMP-FRAMEWORK-MIB
        INCLUDES         { snmpEngineGroup }

        VARIATION        snmpEngineMaxMessageSize
            SYNTAX       INTEGER (484..1300)
            DESCRIPTION  "Maximum message size allowed is 1300."

    ::= { ciscoSnmpFrameworkCapability 1 }

cSnmpFrameworkCapACSWV03R000 AGENT-CAPABILITIES
    PRODUCT-RELEASE      "ACSW (Application Control Software) 3.0
                          for Application Control Engine (ACE) 
                          Service Module."
    STATUS               current
    DESCRIPTION          "SNMP-FRAMEWORK-MIB capabilities."

    SUPPORTS             SNMP-FRAMEWORK-MIB
        INCLUDES         { snmpEngineGroup }

        VARIATION        snmpEngineMaxMessageSize
            SYNTAX       INTEGER (484..1500)
            DESCRIPTION  "Maximum message size allowed is 1500."

    ::= { ciscoSnmpFrameworkCapability 2 }
END
