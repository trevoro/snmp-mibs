Nortel-Magellan-Passport-ModDprsQosMIB
DEFINITIONS ::= BEGIN



IMPORTS

      OBJECT-TYPE
   FROM RFC-1212

      passportMIBs
   FROM Nortel-Magellan-Passport-UsefulDefinitionsMIB

      DisplayString,
      StorageType,
      RowStatus,
      Integer32,
      Unsigned32
   FROM Nortel-Magellan-Passport-StandardTextualConventionsMIB

      NonReplicated
   FROM Nortel-Magellan-Passport-TextualConventionsMIB

      modFrsIndex,
      modFrs
   FROM Nortel-Magellan-Passport-ModCommonMIB

      modIndex
   FROM Nortel-Magellan-Passport-ShelfMIB;




-- LAST-UPDATED   "9902010000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     ModDprsQos Enterprise MIB."

modDprsQosMIB OBJECT IDENTIFIER ::= { passportMIBs 76 }










-- Mod Frs DprsNetworking
-- DprsNetworking is used to define a number of general 
-- characteristics for all Frame Relay connections using DPRS 
-- networking. All the modules in the network should have identical 
-- DprsNetworking attributes. If these attributes are not consistent 
-- across the network, then the service may be degraded. 

modFrsDprsNet OBJECT IDENTIFIER ::= { modFrs 3 }



modFrsDprsNetRowStatusTable OBJECT-TYPE
   SYNTAX     SEQUENCE OF ModFrsDprsNetRowStatusEntry
   ACCESS     not-accessible
   STATUS     mandatory
   DESCRIPTION
     "This entry controls the addition and deletion of 
      modFrsDprsNet components."
::= { modFrsDprsNet 1 }

modFrsDprsNetRowStatusEntry OBJECT-TYPE
   SYNTAX     ModFrsDprsNetRowStatusEntry
   ACCESS     not-accessible
   STATUS     mandatory
   DESCRIPTION
     "A single entry in the table represents a single 
      modFrsDprsNet component."
   INDEX {
      modIndex,
      modFrsIndex,
      modFrsDprsNetIndex }
::= { modFrsDprsNetRowStatusTable 1 }

ModFrsDprsNetRowStatusEntry ::= SEQUENCE {
   modFrsDprsNetRowStatus
      RowStatus,
   modFrsDprsNetComponentName
      DisplayString,
   modFrsDprsNetStorageType
      StorageType,
   modFrsDprsNetIndex
      NonReplicated }

modFrsDprsNetRowStatus OBJECT-TYPE
   SYNTAX     RowStatus 
   ACCESS     read-only
   STATUS     mandatory
   DESCRIPTION
     "This variable is used as the basis for SNMP naming of
      modFrsDprsNet components.
      These components cannot be added nor deleted."
::= { modFrsDprsNetRowStatusEntry 1 }

modFrsDprsNetComponentName OBJECT-TYPE
   SYNTAX     DisplayString 
   ACCESS     read-only
   STATUS     mandatory
   DESCRIPTION
     "This variable provides the component's string name for
      use with the ASCII Console Interface"
::= { modFrsDprsNetRowStatusEntry 2 }

modFrsDprsNetStorageType OBJECT-TYPE
   SYNTAX     StorageType 
   ACCESS     read-only
   STATUS     mandatory
   DESCRIPTION
     "This variable represents the storage type value for the
      modFrsDprsNet tables."
::= { modFrsDprsNetRowStatusEntry 4 }

modFrsDprsNetIndex OBJECT-TYPE
   SYNTAX     NonReplicated 
   ACCESS     not-accessible
   STATUS     mandatory
   DESCRIPTION
     "This variable represents the index for the modFrsDprsNet tables."
::= { modFrsDprsNetRowStatusEntry 10 }


-- Mod Frs DprsNet TransferPriorityMappingDprsNet/n
-- This component represents default transfer priority mappings for 
-- Frame Relay connections using DPRS networking. 

modFrsDprsNetTpm OBJECT IDENTIFIER ::= { modFrsDprsNet 2 }



modFrsDprsNetTpmRowStatusTable OBJECT-TYPE
   SYNTAX     SEQUENCE OF ModFrsDprsNetTpmRowStatusEntry
   ACCESS     not-accessible
   STATUS     mandatory
   DESCRIPTION
     "This entry controls the addition and deletion of 
      modFrsDprsNetTpm components."
::= { modFrsDprsNetTpm 1 }

modFrsDprsNetTpmRowStatusEntry OBJECT-TYPE
   SYNTAX     ModFrsDprsNetTpmRowStatusEntry
   ACCESS     not-accessible
   STATUS     mandatory
   DESCRIPTION
     "A single entry in the table represents a single 
      modFrsDprsNetTpm component."
   INDEX {
      modIndex,
      modFrsIndex,
      modFrsDprsNetIndex,
      modFrsDprsNetTpmIndex }
::= { modFrsDprsNetTpmRowStatusTable 1 }

ModFrsDprsNetTpmRowStatusEntry ::= SEQUENCE {
   modFrsDprsNetTpmRowStatus
      RowStatus,
   modFrsDprsNetTpmComponentName
      DisplayString,
   modFrsDprsNetTpmStorageType
      StorageType,
   modFrsDprsNetTpmIndex
      Integer32 }

modFrsDprsNetTpmRowStatus OBJECT-TYPE
   SYNTAX     RowStatus 
   ACCESS     read-write
   STATUS     mandatory
   DESCRIPTION
     "This variable is used as the basis for SNMP naming of
      modFrsDprsNetTpm components.
      These components can be added."
::= { modFrsDprsNetTpmRowStatusEntry 1 }

modFrsDprsNetTpmComponentName OBJECT-TYPE
   SYNTAX     DisplayString 
   ACCESS     read-only
   STATUS     mandatory
   DESCRIPTION
     "This variable provides the component's string name for
      use with the ASCII Console Interface"
::= { modFrsDprsNetTpmRowStatusEntry 2 }

modFrsDprsNetTpmStorageType OBJECT-TYPE
   SYNTAX     StorageType 
   ACCESS     read-only
   STATUS     mandatory
   DESCRIPTION
     "This variable represents the storage type value for the
      modFrsDprsNetTpm tables."
::= { modFrsDprsNetTpmRowStatusEntry 4 }

modFrsDprsNetTpmIndex OBJECT-TYPE
   SYNTAX     Integer32 (0..15)
   ACCESS     not-accessible
   STATUS     mandatory
   DESCRIPTION
     "This variable represents the index for the modFrsDprsNetTpm tables."
::= { modFrsDprsNetTpmRowStatusEntry 10 }

modFrsDprsNetTpmProvTable OBJECT-TYPE
   SYNTAX     SEQUENCE OF ModFrsDprsNetTpmProvEntry
   ACCESS     not-accessible
   STATUS     mandatory
   DESCRIPTION
     "This group specifies the mapping from the defined transfer priority 
      to the egress emission priority and routing class of service.
      The mapping of transfer priority to egress emission priority and  
      routing class of service may be modified by the user. Any changes 
      to transfer priority mappings will immediately take effect on new  
      calls. Existing connections will not be affected by changes to  
      transfer priority mappings unless the service is reset by locking  and 
      unlocking the connection or resetting the card where the service 
      lies."
::= { modFrsDprsNetTpm 10 }

modFrsDprsNetTpmProvEntry OBJECT-TYPE
   SYNTAX     ModFrsDprsNetTpmProvEntry
   ACCESS     not-accessible
   STATUS     mandatory
   DESCRIPTION
     "An entry in the modFrsDprsNetTpmProvTable."
   INDEX {
      modIndex,
      modFrsIndex,
      modFrsDprsNetIndex,
      modFrsDprsNetTpmIndex }
::= { modFrsDprsNetTpmProvTable 1 }

ModFrsDprsNetTpmProvEntry ::= SEQUENCE {
   modFrsDprsNetTpmEmissionPriority
      Unsigned32,
   modFrsDprsNetTpmRoutingClassOfService
      INTEGER }

modFrsDprsNetTpmEmissionPriority OBJECT-TYPE
   SYNTAX     Unsigned32 (0..3)
   ACCESS     read-write
   STATUS     mandatory
   DESCRIPTION
     "This attribute specifies the egress emission priority at the Frame 
      Relay interface. A value of 3 specifies the highest priority, whereas 
      a value of 0 specifies the lowest priority."
   DEFVAL     { 0 }
::= { modFrsDprsNetTpmProvEntry 1 }

modFrsDprsNetTpmRoutingClassOfService OBJECT-TYPE
   SYNTAX     INTEGER  {
                 throughput(0),
                 delay(1),
                 multimedia(2) }
   ACCESS     read-write
   STATUS     mandatory
   DESCRIPTION
     "This attribute specifies the routing class of service value to be used 
      on a transport connection. A value of multimedia specifies the 
      highest class of service and a value of throughput specifies the 
      lowest class of service."
   DEFVAL     { throughput }
::= { modFrsDprsNetTpmProvEntry 2 }




-- 
-- Version and Compliance statements
-- 



-- Object-Group Statement:
-- A list of all current accessible leaf objects.

-- OBJECTS { modFrsDprsNetTpmRoutingClassOfService,
--           modFrsDprsNetTpmEmissionPriority,
--           modFrsDprsNetTpmComponentName,
--           modFrsDprsNetComponentName,
--           modFrsDprsNetTpmStorageType,
--           modFrsDprsNetTpmRowStatus,
--           modFrsDprsNetStorageType,
--           modFrsDprsNetRowStatus }
-- STATUS  mandatory
-- DESCRIPTION
--   "A list of all current accessible leaf objects."

modDprsQosGroup OBJECT IDENTIFIER ::= { modDprsQosMIB 1 }
modDprsQosGroupBE OBJECT IDENTIFIER ::= { modDprsQosGroup 5 }
modDprsQosGroupBE01 OBJECT IDENTIFIER ::= { modDprsQosGroupBE 2 }
modDprsQosGroupBE01A OBJECT IDENTIFIER ::= { modDprsQosGroupBE01 2 }



-- Agent-Capabilities Statement:

-- PRODUCT-RELEASE "Passport Release 7.0 ModDprsQos."
-- STATUS          mandatory
-- DESCRIPTION     "ModDprsQos MIB: MIB Version BE01A,
--                  Software Version BG00S4C."
-- SUPPORTS        Nortel-Magellan-Passport-ModDprsQosMIB
--    INCLUDES     { modDprsQosGroupBE01A }

modDprsQosCapabilities OBJECT IDENTIFIER ::= { modDprsQosMIB 3 }
modDprsQosCapabilitiesBE OBJECT IDENTIFIER ::= { modDprsQosCapabilities 5 }
modDprsQosCapabilitiesBE01 OBJECT IDENTIFIER ::= { modDprsQosCapabilitiesBE 2 }
modDprsQosCapabilitiesBE01A OBJECT IDENTIFIER ::= { modDprsQosCapabilitiesBE01 2 }





END
