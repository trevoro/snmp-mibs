--
 -- WWP-LEOS-SYSTEM-CONTROL-MIB.my
 --
 --

 WWP-LEOS-SYSTEM-CONTROL-MIB DEFINITIONS ::= BEGIN

 IMPORTS                
   OBJECT-TYPE, MODULE-IDENTITY                 
            FROM SNMPv2-SMI                     
   TruthValue, MacAddress, RowStatus, TEXTUAL-CONVENTION                        
            FROM SNMPv2-TC
   dot1dStpPort
            FROM BRIDGE-MIB                                             
   wwpModules, wwpModulesLeos                   
            FROM WWP-SMI;
        
        
 wwpLeosSysCtrlMIB MODULE-IDENTITY
            LAST-UPDATED "200603151855Z"
            ORGANIZATION "World Wide Packets, Inc"
            CONTACT-INFO
                    "   Mib Meister
                        Postal: World Wide Packets
                        P.O. Box 950
                        Veradale, WA 99037
                        USA
                        Phone:  +1 509 242 9000
                        Email:  mib.meister@worldwidepackets.com"
            DESCRIPTION
                    "The MIB module for the WWP SysCtrl specific information."
            REVISION    "200603151855Z"
            DESCRIPTION
                    "The value for wwpLeosSysCtrlLacpEnable object changed
                     to be enabled (true) by default."
            REVISION    "200104031700Z"
            DESCRIPTION
                    "Initial creation."
            ::= { wwpModulesLeos 25 }
                                                
 --
 -- Node definitions
 --
        
 wwpLeosSysCtrlMIBObjects OBJECT IDENTIFIER ::= { wwpLeosSysCtrlMIB 1 }
 wwpLeosSysCtrl OBJECT IDENTIFIER ::= { wwpLeosSysCtrlMIBObjects 1 }
 wwpLeosSysCtrlLldpExt OBJECT IDENTIFIER ::= { wwpLeosSysCtrlMIBObjects 2 }

 -- Notifications 
  
 wwpLeosSysCtrlMIBNotificationPrefix  OBJECT IDENTIFIER ::= { wwpLeosSysCtrlMIB 2 } 
 wwpLeosSysCtrlMIBNotifications    OBJECT IDENTIFIER ::=  
                       { wwpLeosSysCtrlMIBNotificationPrefix 0 }

 -- Conformance information 
 
 wwpLeosSysCtrlMIBConformance OBJECT IDENTIFIER ::= { wwpLeosSysCtrlMIB 3 } 
 wwpLeosSysCtrlMIBCompliances OBJECT IDENTIFIER ::= { wwpLeosSysCtrlMIBConformance 1 }          
 wwpLeosSysCtrlMIBGroups      OBJECT IDENTIFIER ::= { wwpLeosSysCtrlMIBConformance 2 }
                
 wwpLeosSysCtrlBridgeRstpEnable OBJECT-TYPE
     SYNTAX          TruthValue
     MAX-ACCESS      read-write
     STATUS          current
     DESCRIPTION
             "when this object is set to 'true' the rstp operation
              for the bridge is enabled. Setting this object to 'false' disable
              bridge rstp operations."
     DEFVAL { false }
     ::= { wwpLeosSysCtrl 1 }

                
 wwpLeosSysCtrlLacpEnable OBJECT-TYPE
     SYNTAX          TruthValue
     MAX-ACCESS      read-write
     STATUS          current
     DESCRIPTION
             "when this object is set to 'true' the Lacp operation
              for the device is enabled. Setting this object to 'false' disable
              the Lacp operations."
     DEFVAL { true }
     ::= { wwpLeosSysCtrl 2 }

 wwpLeosSysCtrlLldpState OBJECT-TYPE
     SYNTAX          INTEGER {
                        unknwon(1),
                        disabled(2),
                        enabled(3)
                     }
     MAX-ACCESS      read-write
     STATUS          current
     DESCRIPTION
             "Setting this object will enable or disable LLDP globally."     
     ::= { wwpLeosSysCtrl 3 }

 wwpLeosSysCtrlLldpDaMac OBJECT-TYPE
     SYNTAX          MacAddress
     MAX-ACCESS      read-write
     STATUS          current
     DESCRIPTION
             "Setting this object will set da mac for lldp."     
     ::= { wwpLeosSysCtrlLldpExt 1 }

 wwpLeosSysCtrlLldpEthType OBJECT-TYPE
     SYNTAX          INTEGER (0..65535)
     MAX-ACCESS      read-write
     STATUS          current
     DESCRIPTION
             "Setting this object will set frame type for for lldp."
     ::= { wwpLeosSysCtrlLldpExt 2 }
 END

 --
 -- WWP-SYSTEM-CONTROL-MIB
 --
