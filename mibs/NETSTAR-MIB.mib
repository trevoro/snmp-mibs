--
-- 	This document is used to define the proprietary information provided
--	by each of the NetStar products. 
--
--	NOTE: NetStar was acquired by Ascend Communications, Inc. in 1996!
--
NETSTAR-MIB	DEFINITIONS ::= BEGIN

  IMPORTS
		DisplayString FROM SNMPv2-TC
          IpAddress, OBJECT-TYPE, enterprises, Counter
                  FROM RFC1155-SMI
	  ifIndex, ifDescr, ifInOctets, ifOutOctets, snmp
		  FROM RFC1213-MIB
	  TRAP-TYPE
		  FROM RFC-1215;
--
--		NetStar, Inc.
--		10250 Valley View Road
--		Minneapolis, MN 55344
--
--		Voice: (612) 943-8990
--		FAX:   (612) 943-8939
--
--		Contact:  Duane L. Van Someren
--			  Duane.VanSomeren@ascend.com
--
--		Private MIB definitions
--

	--
	--	The NetStar enterprise OID.
	--

netstar		OBJECT IDENTIFIER ::= { enterprises 1080 }

	--
	--	The NetStar groups.
	--

netstar-products OBJECT IDENTIFIER ::= { netstar 1 }

netstar-daemons  OBJECT IDENTIFIER ::= { netstar 2 }

	--	The NetStar Products.
	
	--	The gigarouter is a high-speed IP router that supports 
	--	HIPPI, FDDI, ATM/SONET, HSSI, Ethernet, and other types 
	--	of high-speed media.

gigarouter	OBJECT IDENTIFIER ::= { netstar-products 1 }

	--	The ClusterSwitch is a 12-port HIPPI crosspoint
	--	switch, as specified in the ANSI HIPPI-SC standard.

clusterswitch	OBJECT IDENTIFIER ::= { netstar-products 2 }

	--	The GR2 is basically a Gigarouter with a hot swapable 
	--	fan tray and two hot swapable power supplies. 

gr2		OBJECT IDENTIFIER ::= { netstar-products 3 }

	--	The GRF family of high-speed IP switches support FDDI, 
	--	ATM/SONET, HSSI, Ethernet, and other types of media.

grf		OBJECT IDENTIFIER ::= { netstar-products 4 }

	-- 	The GRF product family.
	
	--	The grf400 has an integrated controller and provides 
	--	4 slots for media cards.

grf400		OBJECT IDENTIFIER ::= { grf 1 }

	--	The grf1600 has an integrated controller and provides 
	--	16 slots for media cards.

grf1600		OBJECT IDENTIFIER ::= { grf 2 }

	--	The NetStar Daemons.
	
	--	The SNMP support is distributed among multiple daemon
	--	processes. Each process requires a unique object 
	--	identifier to communicate with the SNMP agent.  This 
	--	section is used to define a set of unique OIDs for 
	--	each of these daemon processes.
	--

mib2Daemon		OBJECT IDENTIFIER ::= { netstar-daemons 1 }

frameRelayDaemon	OBJECT IDENTIFIER ::= { netstar-daemons 2 }

dynamicRoutingDaemon	OBJECT IDENTIFIER ::= { netstar-daemons 3 }

mibmgrDaemon		OBJECT IDENTIFIER ::= { netstar-daemons 4 }

atmpDaemon		OBJECT IDENTIFIER ::= { netstar-daemons 5 }

	-- GigaRouter MIB groups

	grChassis	OBJECT IDENTIFIER ::= { gigarouter 1 }

	grHIPPI		OBJECT IDENTIFIER ::= { gigarouter 2 }

	grFDDI4		OBJECT IDENTIFIER ::= { gigarouter 3 }

	grAtmV1		OBJECT IDENTIFIER ::= { gigarouter 4 }

	grAtmUNI	OBJECT IDENTIFIER ::= { gigarouter 5 }

	grThreshPoll	OBJECT IDENTIFIER ::= { gigarouter 6 }
	
	grPingLog       OBJECT IDENTIFIER ::= { gigarouter 7 }

        grAtmp          OBJECT IDENTIFIER ::= { gigarouter 8 }

	grPowerSupplyStatus OBJECT-TYPE
		SYNTAX	INTEGER
		ACCESS	read-only
		STATUS	mandatory
		DESCRIPTION
			"A sum of bits:
			  1 = Power supply A is operational
			  2 = Power supply B is operational
			  3 = Power supplies A and B are operational"
		::= { grChassis 1 }

	grTempStatus OBJECT-TYPE
		SYNTAX	INTEGER	{
			normal(1),
			over-temp(2)
		}
		ACCESS	read-only
		STATUS	mandatory
		DESCRIPTION
			"The temperature sensed by the Routing Manager Board.
			Over-temp status means that the temperature has 
			exceeded the maximum temperature threshold."
		::= { grChassis 2 }

	grFanStatus OBJECT-TYPE
		SYNTAX	INTEGER
		ACCESS	read-only
		STATUS	mandatory
		DESCRIPTION
			"A sum of bits:
			  1  = Fan tray installed
			  2  = Fan 1 operational
			  4  = Fan 2 operational
			  8  = Fan 3 operational
			  16 = Fan 4 operational
			  32 = Fan 5 operational
			  64 = Fan 6 operational

			 The expected value is based upon the actual number 
			 of fans installed and varies from chassis to chassis 
			 as shown below:
			  GR-2    = 127 (six fans)
			  GRF400  = 15  (three fans)
			  GRF1600 = 7   (two fans)

			 A value of zero indicates that the fan tray has been
			 removed."
		::= { grChassis 3 }

	grPortCardNumber OBJECT-TYPE
		SYNTAX	INTEGER (0..64)
		ACCESS	read-only
		STATUS	mandatory
		DESCRIPTION
			"The number of portcards installed in the system."
		REFERENCE
			"netgrit/grime.h: CARD_NUMBER"
		::= { grChassis 4 }

	-- The PortCard Table

	grPortCardTable OBJECT-TYPE
		SYNTAX	SEQUENCE OF GrPortCardEntry
		ACCESS	not-accessible
		STATUS	mandatory
		DESCRIPTION
			"A list of PortCard entries.  The number of entries
			shall not exceed the value of grPortCardNumber."
		::= { grChassis 5 }

	grPortCardEntry OBJECT-TYPE
		SYNTAX	GrPortCardEntry
		ACCESS	not-accessible
		STATUS	mandatory
		DESCRIPTION
			"A PortCard entry containing information common to
			a given port card."
		INDEX	{ grPortCardSlot }
		::= { grPortCardTable 1 }

	GrPortCardEntry ::=
		SEQUENCE {
			grPortCardSlot
				INTEGER,
			grPortCardHWtype
				INTEGER,
			grPortCardCurrentState
				INTEGER
	}

	grPortCardSlot	OBJECT-TYPE
		SYNTAX	INTEGER (0..63)
		ACCESS	read-only
		STATUS	mandatory
		DESCRIPTION
			"The port card slot number, starting at zero."
		::= { grPortCardEntry 1 }

	grPortCardHWtype OBJECT-TYPE
		SYNTAX	INTEGER	{
			none(0),
			hippi(3),
			fddi(4),
			rmb(6),
			atm(7),
			hssi(8),
			ibmSP(9),
			atmq-oc3(10),
			fddiq(11),
			atm-oc12(12),
			ethernet(13),
			sonet-oc3(14),
			cddi(15)
		}
		ACCESS	read-only
		STATUS	mandatory
		DESCRIPTION
			"GigaRouter Port Card hardware type."
		::= { grPortCardEntry 2 }

	grPortCardCurrentState OBJECT-TYPE
		SYNTAX	INTEGER	{
			empty(1),
			power-up(2),
			boot-requested(3),
			dumping(4),
			loading(5),
			configuring(6),
			running(7),
			not-responding(8),
			panic(9),
			held-reset(10),
			other(99)
		}
		ACCESS	read-only
		STATUS	mandatory
		DESCRIPTION
			"The instantaneous state of port card operation."
		::= { grPortCardEntry 3 }

	--  Dynamic Routing Status 

	grGatedStatus OBJECT-TYPE
		SYNTAX	INTEGER	{
			running(1),
			not-running(2)
		}
		ACCESS	read-only
		STATUS	mandatory
		DESCRIPTION
			"The instantaneous state of gated: running or 
                         not running."
		::= { grChassis 6 }

	-- The Configuration File Backup/Compare/Restore Objects

	grTransportMethod OBJECT-TYPE
		SYNTAX INTEGER {
			ftp(0),
			tftp(1)
		}
		ACCESS	read-write
		STATUS	mandatory
		DESCRIPTION
			"This defines the transport method used to
			 transfer configuration files between the
			 GRF and a ftp/tftp server"
		::= { grChassis 7 }

	grFTPUserName	OBJECT-TYPE
		SYNTAX	DisplayString( SIZE (0..255))
		ACCESS	read-write
		STATUS	mandatory
		DESCRIPTION
			"This defines the user login name.  This user 
			 login name will be used to log into the ftp 
			 server to transfer the configuration files."
		::= { grChassis 8 }

	grFTPPassword	OBJECT-TYPE
		SYNTAX	DisplayString( SIZE (0..255))
		ACCESS	read-write
		STATUS	mandatory
		DESCRIPTION
			"This defines the password for the ftp user. This 
			 password will be used to log into the ftp server 
			 to transfer the configuration files."
		::= { grChassis 9 }

	grServerName	OBJECT-TYPE
		SYNTAX	DisplayString(SIZE (0..255))
		ACCESS	read-write
		STATUS	mandatory
		DESCRIPTION
			"This defines the ftp/tftp server name to be used
			 for a Backup/Compare/Restore operation."
		::= { grChassis 10 }

	grFileName	OBJECT-TYPE
		SYNTAX DisplayString(SIZE (0..255))
		ACCESS 	read-write
		STATUS	mandatory
		DESCRIPTION
			"This defines the file name to be used for a
			 Backup/Compare/Restore operation."
		::= { grChassis 11 }

	grLastOperation	OBJECT-TYPE
		SYNTAX	DisplayString( SIZE (0..255))
		ACCESS	read-only
		STATUS	mandatory
		DESCRIPTION
			"This describes the last Backup/Compare/Restore
			 operation that was executed on the system."
		::= { grChassis 12 }

	grStatusMsg OBJECT-TYPE
		SYNTAX	DisplayString( SIZE (0..255))
		ACCESS	read-only
		STATUS	mandatory
		DESCRIPTION
			"This message contains the status information
			 associated with the last Backup/Compare/Restore 
			 operation."
		::= { grChassis 13 }

	grBackup OBJECT-TYPE
		SYNTAX INTEGER {
			no(0),
			yes(1)
		}
		ACCESS  read-write
		STATUS  mandatory
		DESCRIPTION
			"The setting of this to yes starts the configuration 
			 Backup operation."
		::= { grChassis 14 }

	grCompare OBJECT-TYPE
		SYNTAX INTEGER {
			no(0),
			yes(1)
		}
		ACCESS  read-write
		STATUS	mandatory
		DESCRIPTION
			"The setting of this to yes starts the configuration 
			 Compare operation."
		::= { grChassis 15 }

	grRestore OBJECT-TYPE
		SYNTAX INTEGER {
			no(0),
			yes(1)
		}
		ACCESS	read-write
		STATUS	mandatory
		DESCRIPTION
			"The setting of this to yes starts the configuration 
			 Restore operation."
		::= { grChassis 16 }

	-- ATM Management tables

	grAtmV1VcTable OBJECT-TYPE
		SYNTAX	SEQUENCE OF GrAtmV1VcEntry
		ACCESS	not-accessible
		STATUS	mandatory
		DESCRIPTION
			"A list of PortCard ATM Interface entries."
		REFERENCE
			"netgrit/grime.h: CARD_IF_ATM_IN_PVC_TABLE"
		::= { grAtmV1 1 }

	grAtmV1VcEntry OBJECT-TYPE
		SYNTAX	GrAtmV1VcEntry
		ACCESS	not-accessible
		STATUS	mandatory
		DESCRIPTION
			"A grAtmV1Vc entry containing attributes of an ATM
			virtual connection."
		REFERENCE
			"netgrit/grime.h: CARD_IF_ATM_IN_PVC_ENTRY"
		INDEX	{ grAtmV1VcIfIndex, grAtmV1VcVpi, grAtmV1VcVci }
		::= { grAtmV1VcTable 1 }

	GrAtmV1VcEntry ::=
		SEQUENCE {
			grAtmV1VcIfIndex
				INTEGER,
			grAtmV1VcVpi
				INTEGER,
			grAtmV1VcVci
				INTEGER,
			grAtmV1VcAal
				INTEGER,
			grAtmV1VcDestIfIndex
				INTEGER,
			grAtmV1VcDestVpi
				INTEGER,
			grAtmV1VcDestVci
				INTEGER,
			grAtmV1VcProtocol
				INTEGER,
			grAtmV1VcRateq
				INTEGER,
			grAtmV1VcType
				INTEGER
	}

	grAtmV1VcIfIndex OBJECT-TYPE
		SYNTAX	INTEGER
		ACCESS	read-write
		STATUS	mandatory
		DESCRIPTION
			"The interface on which this entry's PVC
			exists.  The interface identified by a
			particular value of this index is the same
			interface as identified by the same value of
			ifIndex."
		::= { grAtmV1VcEntry 1 }

	grAtmV1VcVpi OBJECT-TYPE
		SYNTAX	INTEGER
		ACCESS	read-write
		STATUS	mandatory
		DESCRIPTION
			"The Virtual Path Identifier (VPI) value of this 
			virtual connection."
		REFERENCE
			"netgrit/grime.h: CARD_IF_ATM_IN_PVC_VPI"
		::= { grAtmV1VcEntry 2 }

	grAtmV1VcVci OBJECT-TYPE
		SYNTAX	INTEGER
		ACCESS	read-write
		STATUS	mandatory
		DESCRIPTION
			"The Virtual Connection Identifier (VCI) value of this 
			virtual connection."
		REFERENCE
			"netgrit/grime.h: CARD_IF_ATM_IN_PVC_VCI"
		::= { grAtmV1VcEntry 3 }

	grAtmV1VcAal OBJECT-TYPE
		SYNTAX	INTEGER	{
			aal3(1),
			aal5(2),
			other(3)
		}
		ACCESS	read-write
		STATUS	mandatory
		DESCRIPTION
			"The ATM Adaptation Layer (AAL) protocol to be
			used on this virtual connection."
		REFERENCE
			"netgrit/grime.h: CARD_IF_ATM_IN_PVC_AAL"
		::= { grAtmV1VcEntry 4 }

	grAtmV1VcProtocol OBJECT-TYPE
		SYNTAX	INTEGER	{
			ip-llc(1),
			ip-null(2),
			uni(3),
			diag0(4),
			diag1(5),
			raw(6),
			other(7)
		}
		ACCESS	read-write
		STATUS	mandatory
		DESCRIPTION
			"The upper-layer protocol to be used on this virtual
			connection."
		REFERENCE
			"netgrit/grime.h: CARD_IF_ATM_IN_PVC_PRO"
		::= { grAtmV1VcEntry 5 }

	grAtmV1VcDestIfIndex OBJECT-TYPE
		SYNTAX	INTEGER
		ACCESS	read-write
		STATUS	mandatory
		DESCRIPTION
			"The IfIndex value for the interface to which this
			virtual connection is attached, if any.  This object
			is meaningful only when the grAtmV1VcProtocol value
			is diag0(4), diag1(5) or raw(6)."
		REFERENCE
			"netgrit/grime.h: CARD_IF_ATM_IN_PVC_D_INF"
		::= { grAtmV1VcEntry 6 }

	grAtmV1VcDestVpi OBJECT-TYPE
		SYNTAX	INTEGER
		ACCESS	read-write
		STATUS	mandatory
		DESCRIPTION
			"The VPI value for the Destination virtual connection
			to which this VC is attached, if any.  This object
			is meaningful only when the grAtmV1VcProtocol value
			is diag0(4), diag1(5) or raw(6)."
		REFERENCE
			"netgrit/grime.h: CARD_IF_ATM_IN_PVC_D_VPI"
		::= { grAtmV1VcEntry 7 }

	grAtmV1VcDestVci OBJECT-TYPE
		SYNTAX	INTEGER
		ACCESS	read-write
		STATUS	mandatory
		DESCRIPTION
			"The VCI value for the Destination virtual connection
			to which this VC is attached, if any.  This object
			is meaningful only when the grAtmV1VcProtocol value
			is diag0(4), diag1(5) or raw(6)."
		REFERENCE
			"netgrit/grime.h: CARD_IF_ATM_IN_PVC_D_VCI"
		::= { grAtmV1VcEntry 8 }

	grAtmV1VcRateq OBJECT-TYPE
		SYNTAX	INTEGER
		ACCESS	read-write
		STATUS	mandatory
		DESCRIPTION
			"The number of the rate queue to which this
			virtual connection is assigned."
		REFERENCE
			"netgrit/grime.h: CARD_IF_ATM_OUT_PVC_RQ"
		::= { grAtmV1VcEntry 9 }

	grAtmV1VcType OBJECT-TYPE
		SYNTAX	INTEGER	{
			other(1),
			invalid(2),
			permanent(3),
			switched(4)
		}
		ACCESS	read-write
		STATUS	mandatory
		DESCRIPTION
			"The type of virtual connection."
		REFERENCE
			"netgrit/grime.h: CARD_IF_ATM_IN_PVC_STATE"
		::= { grAtmV1VcEntry 10 }



	grAtmV1RateqTable OBJECT-TYPE
		SYNTAX	SEQUENCE OF GrAtmV1RateqEntry
		ACCESS	not-accessible
		STATUS	mandatory
		DESCRIPTION
			"A list of PortCard ATM Interface entries."
		REFERENCE
			"netgrit/grime.h: CARD_IF_ATM_RATEQ_TABLE"
		::= { grAtmV1 3 }

	grAtmV1RateqEntry OBJECT-TYPE
		SYNTAX	GrAtmV1RateqEntry
		ACCESS	not-accessible
		STATUS	mandatory
		DESCRIPTION
			"A grAtmV1Rateq entry containing attributes of an ATM
			interface."
		REFERENCE
			"netgrit/grime.h: CARD_IF_ATM_RATEQ_ENTRY"
		INDEX	{ grAtmV1RateqIfIndex, grAtmV1RateqIndex }
		::= { grAtmV1RateqTable 1 }

	GrAtmV1RateqEntry ::=
		SEQUENCE {
			grAtmV1RateqIfIndex
				INTEGER,
			grAtmV1RateqIndex
				INTEGER (0..7),
			grAtmV1RateqRate
				INTEGER,
			grAtmV1RateqState
				INTEGER
		}

	grAtmV1RateqIfIndex OBJECT-TYPE
		SYNTAX INTEGER
		ACCESS  read-write
		STATUS  mandatory
		DESCRIPTION
			"The interface on which this entry's rate
			queue exists.  The interface identified by a
			particular value of this index is the same
			interface as identified by the same value of
			ifIndex."
		::= { grAtmV1RateqEntry 1 }

	grAtmV1RateqIndex OBJECT-TYPE
		SYNTAX INTEGER (0..7)
		ACCESS  read-write
		STATUS  mandatory
		DESCRIPTION
			"A number identifying the rate queue within the
			Interface."
		REFERENCE
			"netgrit/grime.h: CARD_IF_ATM_RATEQ_Q"
		::= { grAtmV1RateqEntry 2 }

	grAtmV1RateqRate OBJECT-TYPE
		SYNTAX INTEGER
		ACCESS  read-write
		STATUS  mandatory
		DESCRIPTION
			"The maximum data rate allocated to this rate queue,
			in decimal thousands of bits per second."
		REFERENCE
			"netgrit/grime.h: CARD_IF_ATM_RATEQ_RATE"
		::= { grAtmV1RateqEntry 3 }

	grAtmV1RateqState OBJECT-TYPE
		SYNTAX INTEGER	{
			active(1),
			inactive(2)
		}
		ACCESS  read-write
		STATUS  mandatory
		DESCRIPTION
			"The operational state of the rate queue."
		REFERENCE
			"netgrit/grime.h: CARD_IF_ATM_RATEQ_STATE"
		::= { grAtmV1RateqEntry 4 }


	grAtmV1NetToVcTable OBJECT-TYPE
		SYNTAX	SEQUENCE OF GrAtmV1NetToVcEntry
		ACCESS	not-accessible
		STATUS	mandatory
		DESCRIPTION
			"A list of PortCard ATM IP address to virtual 
			channel entries."
		REFERENCE
			"netgrit/grime.h: CARD_IF_ATM_ARP_TABLE"
		::= { grAtmV1 4 }

	grAtmV1NetToVcEntry OBJECT-TYPE
		SYNTAX	GrAtmV1NetToVcEntry
		ACCESS	not-accessible
		STATUS	mandatory
		DESCRIPTION
			"A grAtmV1NetToVc entry representing a mapping from an IP
			address to an ATM virtual channel."
		REFERENCE
			"netgrit/grime.h: CARD_IF_ATM_ARP_ENTRY"
		INDEX	{ grAtmV1NetToVcIfIndex, grAtmV1NetToVcNetAddress }
		::= { grAtmV1NetToVcTable 1 }

	GrAtmV1NetToVcEntry ::=
		SEQUENCE {
			grAtmV1NetToVcIfIndex
				INTEGER,
			grAtmV1NetToVcNetAddress
				IpAddress,
			grAtmV1NetToVcVpi
				INTEGER,
			grAtmV1NetToVcVci
				INTEGER,
			grAtmV1NetToVcState
				INTEGER
	}

	grAtmV1NetToVcIfIndex OBJECT-TYPE
		SYNTAX INTEGER
		ACCESS  read-write
		STATUS  mandatory
		DESCRIPTION
			"The interface on which this entry's equivalence
			is effective.  The interface identified by a
			particular value of this index is the same
			interface as identified by the same value of
			ifIndex."
		::= { grAtmV1NetToVcEntry 1 }

	grAtmV1NetToVcNetAddress OBJECT-TYPE
		SYNTAX IpAddress
		ACCESS  read-write
		STATUS  mandatory
		DESCRIPTION
			"The IpAddress corresponding to the virtual
			channel."
		REFERENCE
			"netgrit/grime.h: CARD_IF_ATM_ARP_IP"
		::= { grAtmV1NetToVcEntry 2 }

	grAtmV1NetToVcVpi OBJECT-TYPE
		SYNTAX INTEGER
		ACCESS  read-write
		STATUS  mandatory
		DESCRIPTION
			"The Virtual Path Identifier (VCI) of this
			virtual channel."
		REFERENCE
			"netgrit/grime.h: CARD_IF_ATM_ARP_VPI"
		::= { grAtmV1NetToVcEntry 3 }

	grAtmV1NetToVcVci OBJECT-TYPE
		SYNTAX INTEGER
		ACCESS  read-write
		STATUS  mandatory
		DESCRIPTION
			"The Virtual Channel Identifier (VCI) of this
			virtual channel."
		REFERENCE
			"netgrit/grime.h: CARD_IF_ATM_ARP_VCI"
		::= { grAtmV1NetToVcEntry 4 }

	grAtmV1NetToVcState OBJECT-TYPE
		SYNTAX  INTEGER	{
			active(1),
			inactive(2)
		}
		ACCESS  read-write
		STATUS  mandatory
		DESCRIPTION
			"The operational state of this entry."
		REFERENCE
			"netgrit/grime.h: CARD_IF_ATM_ARP_STATE"
		::= { grAtmV1NetToVcEntry 5 }

-- 
--  current and previous counter objects used for the
--  Threshold Poller
--

	grThreshPollTable OBJECT-TYPE
		SYNTAX	SEQUENCE OF GrThreshPollEntry
		ACCESS	not-accessible
		STATUS	mandatory
		DESCRIPTION
			"A list of current and previous threshpoll counter
			entries."
		::= { grThreshPoll 3 }

	grThreshPollEntry OBJECT-TYPE
		SYNTAX	GrThreshPollEntry
		ACCESS	not-accessible
		STATUS	mandatory
		DESCRIPTION
			"A grThreshpoll entry containing current and
			previous threshold counters."
		INDEX	{ ifIndex }
		::= { grThreshPollTable 1 }

	GrThreshPollEntry ::=
		SEQUENCE {
			grTPCurrentCount
				Counter,
			grTPPreviousCount
				Counter,
			grTPCurrentCountUpper
				Counter,
			grTPPreviousCountUpper
				Counter
		}

	grTPCurrentCount OBJECT-TYPE
		SYNTAX  Counter 
		ACCESS  read-only
		STATUS  mandatory
		DESCRIPTION
			"The current value of a counter being polled
			 by the threshold poller."
		::= { grThreshPollEntry 1 }

	grTPPreviousCount OBJECT-TYPE
		SYNTAX  Counter
		ACCESS	read-only
		STATUS	mandatory
		DESCRIPTION
			"The previous value of a counter being polled
			 by the threshold poller."
		::= { grThreshPollEntry 2 }

	grTPCurrentCountUpper OBJECT-TYPE
		SYNTAX  Counter 
		ACCESS  read-only
		STATUS  mandatory
		DESCRIPTION
			"The upper 32 bits of the current value of a 
			 64 bit counter being polled
			 by the threshold poller."
		::= { grThreshPollEntry 3 }

	grTPPreviousCountUpper OBJECT-TYPE
		SYNTAX  Counter
		ACCESS	read-only
		STATUS	mandatory
		DESCRIPTION
			"The upper 32 bits of the previous value of a 
			 64 bit counter being polled
			 by the threshold poller."
		::= { grThreshPollEntry 4 }

-- 
--  The message that is sent in the trap by pinglog when a monitored
--  device goes down.
--

	grPingLogTable OBJECT-TYPE
		SYNTAX	SEQUENCE OF GrPingLogEntry
		ACCESS	not-accessible
		STATUS	mandatory
		DESCRIPTION
			"A list of current and previous threshpoll counter
			entries."
		::= { grPingLog 1 }

	grPingLogEntry OBJECT-TYPE
		SYNTAX	GrPingLogEntry
		ACCESS	not-accessible
		STATUS	mandatory
		DESCRIPTION
			"A grThreshpoll entry containing current and
			previous threshold counters."
		INDEX	{ ifIndex }
		::= { grPingLogTable 1 }

	GrPingLogEntry ::=
		SEQUENCE {
			grPLDevDownMsg
				DisplayString
		}

	grPLDevDownMsg OBJECT-TYPE
		SYNTAX  DisplayString (SIZE (0..255))
		ACCESS	read-only
		STATUS	mandatory
		DESCRIPTION
			"The message sent when pinglog detects a device
                         down."
		::= { grPingLogEntry 1 }


	-- Standard Traps from RFC 1215

          coldStart TRAP-TYPE
              ENTERPRISE  snmp
              DESCRIPTION
                          "A coldStart trap signifies that the sending
                          protocol entity is reinitializing itself such
                          that the agent's configuration or the protocol
                          entity implementation may be altered."
              ::= 0
  
          warmStart TRAP-TYPE
              ENTERPRISE  snmp
              DESCRIPTION
                          "A warmStart trap signifies that the sending
                          protocol entity is reinitializing itself such
                          that neither the agent configuration nor the
                          protocol entity implementation is altered."
              ::= 1
  
          linkDown TRAP-TYPE
              ENTERPRISE  snmp
              VARIABLES   { ifIndex }
              DESCRIPTION
                          "A linkDown trap signifies that the sending
                          protocol entity recognizes a failure in one of
                          the communication links represented in the
                          agent's configuration."
              ::= 2
  
          linkUp TRAP-TYPE
              ENTERPRISE  snmp
              VARIABLES   { ifIndex }
              DESCRIPTION
                          "A linkUp trap signifies that the sending
                          protocol entity recognizes that one of the
                          communication links represented in the agent's
                          configuration has come up."
              ::= 3
  
          authenticationFailure TRAP-TYPE
              ENTERPRISE  snmp
              DESCRIPTION
                          "An authenticationFailure trap signifies that
                          the sending protocol entity is the addressee
                          of a protocol message that is not properly
                          authenticated.  While implementations of the
                          SNMP must be capable of generating this trap,
                          they must also be capable of suppressing the
                          emission of such traps via an implementation-
                          specific mechanism."
              ::= 4
  
--        egpNeighborLoss TRAP-TYPE
--            ENTERPRISE  snmp
--            VARIABLES   { egpNeighAddr }
--            DESCRIPTION
--                        "An egpNeighborLoss trap signifies that an EGP
--                        neighbor for whom the sending protocol entity
--                        was an EGP peer has been marked down and the
--                        peer relationship no longer obtains."
--            ::= 5

--	   NetStar private enterprise traps:
  
          grPowerSupplyFailure TRAP-TYPE
              ENTERPRISE  gigarouter
	      VARIABLES	  { grPowerSupplyStatus }
              DESCRIPTION
                          "The trap that is issued when one of the power
                          supplies is removed from the system or fails
                          in in some way."
              ::= 1

          grOverTemp TRAP-TYPE
              ENTERPRISE  gigarouter
	      VARIABLES	  { grTempStatus }
              DESCRIPTION
                          "The trap that is issued when the system
			  temperature exceeds the maximum temperature
			  threshold."
              ::= 2

          grFanFailure TRAP-TYPE
              ENTERPRISE  gigarouter
	      VARIABLES	  { grFanStatus }
              DESCRIPTION
                          "The trap that is issued when any fan's speed
			  falls below the minimum threshold value or the
			  fan tray is removed from the system."
              ::= 3

	  grCardDown TRAP-TYPE
              ENTERPRISE  gigarouter
	      VARIABLES	  { grPortCardSlot, grPortCardCurrentState }
	      DESCRIPTION
			  "The trap that is issued when the Port Card's
			  state changes from running(7) to any other state."
	      ::= 4

	  grCardUp TRAP-TYPE
              ENTERPRISE  gigarouter
              VARIABLES   { grPortCardSlot }
              DESCRIPTION
                          "The trap that is issued when the Port Card's
                          state changes to running(7) to any other state."
              ::= 5

          grSONETLossOfFrame TRAP-TYPE
              ENTERPRISE  gigarouter
              VARIABLES   { ifIndex }
              DESCRIPTION
                          "The trap issued when the SONET receive hardware
                          detects a Loss Of Frame Failure (LOF)."
              ::= 6

          grSONETLossOfSignal TRAP-TYPE
              ENTERPRISE  gigarouter
              VARIABLES   { ifIndex }
              DESCRIPTION
                          "The trap issued when the SONET receive hardware
                          detects Loss of Signal (LOS)."
              ::= 7

          grSONETSTSPathLossOfPointer TRAP-TYPE
              ENTERPRISE  gigarouter
              VARIABLES   { ifIndex }
              DESCRIPTION
                          "The trap issued when the SONET receive hardware
                          detects STS-Path Lossof Pointer (LOP)."
              ::= 8

          grSONETVTLossOfPointer TRAP-TYPE
              ENTERPRISE  gigarouter
              VARIABLES   { ifIndex }
              DESCRIPTION
                          "The trap issued when the SONET receive hardware
                          detects VT Loss of Pointer (VT LOP)."
              ::= 9

          grSONETLineAlarmIndicationSignal TRAP-TYPE
              ENTERPRISE  gigarouter
              VARIABLES   { ifIndex }
              DESCRIPTION
                          "The trap issued when the SONET receive hardware
                          detects a Line Alarm Indication Signal (L-AIS)."
              ::= 10

          grSONETSTSPathAlarmIndicationSignal TRAP-TYPE
              ENTERPRISE  gigarouter
              VARIABLES   { ifIndex }
              DESCRIPTION
                          "The trap issued when the SONET receive hardware
                          detects an STS-Path Alarm Indication Signal (AIS)."
              ::= 11

          grSONETVTPathAlarmIndicationSignal TRAP-TYPE
              ENTERPRISE  gigarouter
              VARIABLES   { ifIndex }
              DESCRIPTION
                          "The trap issued when the SONET receive hardware
                          detects a VT-Path Alarm Indication Signal
                          (VT-Path AIS)."
              ::= 12

          grSONETLineRemoteDefectIndication TRAP-TYPE
              ENTERPRISE  gigarouter
              VARIABLES   { ifIndex }
              DESCRIPTION
                          "The trap issued when the SONET receive hardware
                          detects a Line Remote Defect Indication (RDI, 
                          also known as Line FERF)."
              ::= 13

          grSONETVTPathRemoteDefectIndication TRAP-TYPE
              ENTERPRISE  gigarouter
              VARIABLES   { ifIndex }
              DESCRIPTION
                          "The trap issued when the SONET receive hardware
                          detects a VT-Path Remote Defect Indication (VT 
                          Path RDI, also known as VT Path FERF)."
              ::= 14

          grSONETTCLossOfCellDelineation TRAP-TYPE
              ENTERPRISE  gigarouter
              VARIABLES   { ifIndex }
              DESCRIPTION
                          "The trap issued when the SONET receive hardware
                          detects Loss of Cell Delineation."
              ::= 15
    
          grAtmPVCUp TRAP-TYPE
              ENTERPRISE  gigarouter
              VARIABLES   { ifIndex, grAtmV1VcVpi, grAtmV1VcVci }
              DESCRIPTION
                          "The trap issued when an ATM Permanent Virtual
                          circuit is enabled"
              ::= 16
    
          grAtmPVCDown TRAP-TYPE
              ENTERPRISE  gigarouter
              VARIABLES   { ifIndex, grAtmV1VcVpi, grAtmV1VcVci }
              DESCRIPTION
                          "The trap issued when an ATM Permanent Virtual
                          circuit is disabled"
              ::= 17

--  
--  pinglog trap
--
	  grInterfaceDown TRAP-TYPE
	      ENTERPRISE  gigarouter
	      VARIABLES  { grPLDevDownMsg }
	      DESCRIPTION
			"The trap issued when an interface is
			 not responding to pings."
	      ::= 18

--
--  threshpoll traps
--

	 grIfInOctetsHigh  TRAP-TYPE
	      ENTERPRISE  gigarouter
	      VARIABLES   { grTPPreviousCount, grTPCurrentCount }
	      DESCRIPTION
			"The trap issued when ifInOctets is greater
			 than the configured threshold for that interface."
	      ::= 19

	 grIfInOctetsLow  TRAP-TYPE
              ENTERPRISE  gigarouter
              VARIABLES   { grTPPreviousCount, grTPCurrentCount }
              DESCRIPTION
                        "The trap issued when ifInOctets is less
			 than the configured threshold for that interface."
              ::= 20

         grIfOutOctetsHigh  TRAP-TYPE
              ENTERPRISE  gigarouter
              VARIABLES   { grTPPreviousCount, grTPCurrentCount }
              DESCRIPTION
                        "The trap issued when ifOutOctets is greater
			 than the configured threshold for that interface."
              ::= 21
 
         grIfOutOctetsLow  TRAP-TYPE
              ENTERPRISE  gigarouter
              VARIABLES   { grTPPreviousCount, grTPCurrentCount }
              DESCRIPTION
                        "The trap issued when ifOutOctets is less
			 than the configured threshold for that interface."
              ::= 22
 
	 grIfInUcastPktsHigh    TRAP-TYPE
              ENTERPRISE  gigarouter
              VARIABLES   { grTPPreviousCount, grTPCurrentCount }
              DESCRIPTION
                        "The trap issued when ifInUcastPkts is greater
			 than the configured threshold for that interface."
              ::= 23

	 grIfInUcastPktsLow  TRAP-TYPE
              ENTERPRISE  gigarouter
              VARIABLES   { grTPPreviousCount, grTPCurrentCount }
              DESCRIPTION
                        "The trap issued when ifInUcastPkts is less
			 than the configured threshold for that interface."
              ::= 24

	 grIfOutUcastPktsHigh    TRAP-TYPE
              ENTERPRISE  gigarouter
              VARIABLES   { grTPPreviousCount, grTPCurrentCount }
              DESCRIPTION
                        "The trap issued when ifOutUcastPkts is greater
			 than the configured threshold for that interface."
              ::= 25

	 grIfOutUcastPktsLow  TRAP-TYPE
              ENTERPRISE  gigarouter
              VARIABLES   { grTPPreviousCount, grTPCurrentCount }
              DESCRIPTION
                        "The trap issued when ifOutUcastPkts is less
			 than the configured threshold for that interface."
              ::= 26

	 grIfInErrorsHigh  TRAP-TYPE
              ENTERPRISE  gigarouter
              VARIABLES   { grTPPreviousCount, grTPCurrentCount }
              DESCRIPTION
                        "The trap issued when ifInErrors is greater
			 than the configured threshold for that interface."
              ::= 27

	 grIfInErrorsLow  TRAP-TYPE
              ENTERPRISE  gigarouter
              VARIABLES   { grTPPreviousCount, grTPCurrentCount }
              DESCRIPTION
                        "The trap issued when ifInErrors is less
			 than the configured threshold for that interface."
              ::= 28

	 grIfOutErrorsHigh  TRAP-TYPE
              ENTERPRISE  gigarouter
              VARIABLES   { grTPPreviousCount, grTPCurrentCount }
              DESCRIPTION
                        "The trap issued when ifOutErrors is greater
			 than the configured threshold for that interface."
              ::= 29

	 grIfOutErrorsLow  TRAP-TYPE
              ENTERPRISE  gigarouter
              VARIABLES   { grTPPreviousCount, grTPCurrentCount }
              DESCRIPTION
                        "The trap issued when ifOutErrors is less
			 than the configured threshold for that interface."
              ::= 30

	 grIfInDiscardsHigh  TRAP-TYPE
              ENTERPRISE  gigarouter
              VARIABLES   { grTPPreviousCount, grTPCurrentCount }
              DESCRIPTION
                        "The trap issued when ifInDiscards is greater
			 than the configured threshold for that interface."
              ::= 31

	 grIfInDiscardsLow  TRAP-TYPE
              ENTERPRISE  gigarouter
              VARIABLES   { grTPPreviousCount, grTPCurrentCount }
              DESCRIPTION
                        "The trap issued when ifInDiscards is less
			 than the configured threshold for that interface."
              ::= 32

	 grIfOutDiscardsHigh  TRAP-TYPE
              ENTERPRISE  gigarouter
              VARIABLES   { grTPPreviousCount, grTPCurrentCount }
              DESCRIPTION
                        "The trap issued when ifOutDiscards is greater
			 than the configured threshold for that interface."
              ::= 33

	 grIfOutDiscardsLow  TRAP-TYPE
              ENTERPRISE  gigarouter
              VARIABLES   { grTPPreviousCount, grTPCurrentCount }
              DESCRIPTION
                        "The trap issued when ifOutDiscards is less
			 than the configured threshold for that interface."
              ::= 34


	grGatedDown	TRAP-TYPE
	      ENTERPRISE  gigarouter
	      DESCRIPTION
			"The trap issued when the threshold poller
			 detects that gated is not running."
	      ::= 35

	grSnmpReset     TRAP-TYPE
              ENTERPRISE  gigarouter
              DESCRIPTION
                        "The trap issued when threshpoll detects that
                         the snmp agent has restarted."
	      ::= 36

	grIfHCInOctetsHigh  TRAP-TYPE
	      ENTERPRISE  gigarouter
              VARIABLES   { grTPPreviousCountUpper, grTPPreviousCount, 
			    grTPCurrentCountUpper, grTPCurrentCount }
 	      DESCRIPTION
			"The trap issued when ifHCInOctets is greater
			 than the configured threshold for that interface."
              ::= 37

	grIfHCInOctetsLow  TRAP-TYPE
	      ENTERPRISE  gigarouter
              VARIABLES   { grTPPreviousCountUpper, grTPPreviousCount, 
			    grTPCurrentCountUpper, grTPCurrentCount }
	      DESCRIPTION
			"The trap issued when ifHCInOctets is less
			 than the configured threshold for that interface."
	      ::= 38

	grIfHCInUcastPktsHigh  TRAP-TYPE
	      ENTERPRISE  gigarouter
              VARIABLES   { grTPPreviousCountUpper, grTPPreviousCount, 
			    grTPCurrentCountUpper, grTPCurrentCount }
	      DESCRIPTION
			"The trap issued when ifHCInUcastPkts is greater
			 than the configured threshold for that interface."
	      ::= 39

	grIfHCInUcastPktsLow  TRAP-TYPE
	      ENTERPRISE  gigarouter
              VARIABLES   { grTPPreviousCountUpper, grTPPreviousCount, 
			    grTPCurrentCountUpper, grTPCurrentCount }
	      DESCRIPTION
			"The trap issued when ifHCInUcastPkts is less
			 than the configured threshold for that interface."
	      ::= 40

	grIfHCInMulticastPktsHigh  TRAP-TYPE
	      ENTERPRISE  gigarouter
              VARIABLES   { grTPPreviousCountUpper, grTPPreviousCount, 
			    grTPCurrentCountUpper, grTPCurrentCount }
	      DESCRIPTION
			"The trap issued when ifHCInMulticastPkts is greater
			 than the configured threshold for that interface."
	      ::= 41

	grIfHCInMulticastPktsLow  TRAP-TYPE
	      ENTERPRISE  gigarouter
              VARIABLES   { grTPPreviousCountUpper, grTPPreviousCount, 
			    grTPCurrentCountUpper, grTPCurrentCount }
	      DESCRIPTION
			"The trap issued when ifHCInMulticastPkts is less
			 than the configured threshold for that interface."
	      ::= 42

	grIfHCInBroadcastPktsHigh  TRAP-TYPE
	      ENTERPRISE  gigarouter
              VARIABLES   { grTPPreviousCountUpper, grTPPreviousCount, 
			    grTPCurrentCountUpper, grTPCurrentCount }
	      DESCRIPTION
			"The trap issued when ifHCInBroadcastPkts is greater
			 than the configured threshold for that interface."
	      ::= 43

	grIfHCInBroadcastPktsLow  TRAP-TYPE
	      ENTERPRISE  gigarouter
              VARIABLES   { grTPPreviousCountUpper, grTPPreviousCount, 
			    grTPCurrentCountUpper, grTPCurrentCount }
	      DESCRIPTION
			"The trap issued when ifHCInBroadcastPkts is less
			 than the configured threshold for that interface."
	      ::= 44

	grIfHCOutOctetsHigh  TRAP-TYPE
	      ENTERPRISE  gigarouter
              VARIABLES   { grTPPreviousCountUpper, grTPPreviousCount, 
			    grTPCurrentCountUpper, grTPCurrentCount }
	      DESCRIPTION
			"The trap issued when ifHCOutOctets is greater
			 than the configured threshold for that interface."
	      ::= 45

	grIfHCOutOctetsLow  TRAP-TYPE
	      ENTERPRISE  gigarouter
              VARIABLES   { grTPPreviousCountUpper, grTPPreviousCount, 
			    grTPCurrentCountUpper, grTPCurrentCount }
	      DESCRIPTION
			"The trap issued when ifHCOutOctets is less
			 than the configured threshold for that interface."
	      ::= 46

	grIfHCOutUcastPktsHigh  TRAP-TYPE
	      ENTERPRISE  gigarouter
              VARIABLES   { grTPPreviousCountUpper, grTPPreviousCount, 
			    grTPCurrentCountUpper, grTPCurrentCount }
	      DESCRIPTION
			"The trap issued when ifHCOutUcastPkts is greater
			 than the configured threshold for that interface."
	      ::= 47

	grIfHCOutUcastPktsLow  TRAP-TYPE
	      ENTERPRISE  gigarouter
              VARIABLES   { grTPPreviousCountUpper, grTPPreviousCount, 
			    grTPCurrentCountUpper, grTPCurrentCount }
	      DESCRIPTION
			"The trap issued when ifHCOutUcastPkts is less
			 than the configured threshold for that interface."
	      ::= 48

	grIfHCOutMulticastPktsHigh  TRAP-TYPE
	      ENTERPRISE  gigarouter
              VARIABLES   { grTPPreviousCountUpper, grTPPreviousCount, 
			    grTPCurrentCountUpper, grTPCurrentCount }
	      DESCRIPTION
			"The trap issued when ifHCOutMulticastPkts is greater
			 than the configured threshold for that interface."
	      ::= 49

	grIfHCOutMulticastPktsLow  TRAP-TYPE
	      ENTERPRISE  gigarouter
              VARIABLES   { grTPPreviousCountUpper, grTPPreviousCount, 
			    grTPCurrentCountUpper, grTPCurrentCount }
	      DESCRIPTION
			"The trap issued when ifHCOutMulticastPkts is less
			 than the configured threshold for that interface."
	      ::= 50

	grIfHCOutBroadcastPktsHigh  TRAP-TYPE
	      ENTERPRISE  gigarouter
              VARIABLES   { grTPPreviousCountUpper, grTPPreviousCount, 
			    grTPCurrentCountUpper, grTPCurrentCount }
	      DESCRIPTION
			"The trap issued when ifHCOutBroadcastPkts is greater
			 than the configured threshold for that interface."
	      ::= 51

	grIfHCOutBroadcastPktsLow  TRAP-TYPE
	      ENTERPRISE  gigarouter
              VARIABLES   { grTPPreviousCountUpper, grTPPreviousCount, 
			    grTPCurrentCountUpper, grTPCurrentCount }
	      DESCRIPTION
			"The trap issued when ifHCOutBroadcastPkts is less
			 than the configured threshold for that interface."
	      ::= 52

	grBackupRestoreMessages TRAP-TYPE
	     ENTERPRISE  gigarouter
	     VARIABLES   { grStatusMsg }
	     DESCRIPTION
			"This trap is issued after a Backup/Compare/Restore 
			 operation has completed."
	     ::= 53
--
--  end of threshpoll traps
--

END
