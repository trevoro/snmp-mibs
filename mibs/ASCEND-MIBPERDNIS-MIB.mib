--			Ascend mibperdnis MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBPERDNIS-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibperDnisProfile  OBJECT IDENTIFIER ::= { configuration 100}

	-- The mibperDnisProfile table
	--
	-- This table contains parameters for the mibperDnisProfile profile
	--

    mibperDnisProfileTable	OBJECT-TYPE
	SYNTAX		SEQUENCE OF MibperDnisProfileEntry
	ACCESS		not-accessible
	STATUS		mandatory
	DESCRIPTION	"A list of mibperDnisProfile profile entries."
	::= { mibperDnisProfile 1 }

    mibperDnisProfileEntry	OBJECT-TYPE
	SYNTAX		MibperDnisProfileEntry
	ACCESS		not-accessible
	STATUS		mandatory
	DESCRIPTION	"A mibperDnisProfile entry containing objects that
			 maps to the parameters of mibperDnisProfile profile."
	INDEX		{ perDnisProfile-DialedNumber }
	::= { mibperDnisProfileTable 1 }

    MibperDnisProfileEntry ::=
	SEQUENCE {
	    perDnisProfile-DialedNumber
		DisplayString,
	    perDnisProfile-CallType
		INTEGER,
	    perDnisProfile-Action-o
		INTEGER
	}

    perDnisProfile-DialedNumber	OBJECT-TYPE
	SYNTAX	DisplayString
	ACCESS	read-only
	STATUS	mandatory
	DESCRIPTION	"The number dialed. Used to select how to initialize parameters for the incoming call."
	::= { mibperDnisProfileEntry 1 }

    perDnisProfile-CallType	OBJECT-TYPE
	SYNTAX	INTEGER {
		    digital (1),
		    voice (2)
		}
	ACCESS	read-write
	STATUS	mandatory
	DESCRIPTION	"Forces this particular call type for inband/R1/R2 incoming calls matching the DNIS of this profile."
	::= { mibperDnisProfileEntry 2 }

    perDnisProfile-Action-o	OBJECT-TYPE
	SYNTAX	INTEGER {
		    noAction (1),
		    createProfile (2),
		    deleteProfile (3)
		}
	ACCESS	read-write
	STATUS	mandatory
	DESCRIPTION	""
	::= { mibperDnisProfileEntry 3 }

END
