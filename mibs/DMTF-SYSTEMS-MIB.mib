DMTF-SYSTEMS-MIB DEFINITIONS ::= BEGIN

IMPORTS
	OBJECT-TYPE, NOTIFICATION-TYPE,
	MODULE-IDENTITY, enterprises, Counter32, Counter64, Gauge32, Integer32
		FROM SNMPv2-SMI
	Dmi-Date,Dmi-Integer64,DmiString,
	dmiEventDateTime,dmiCompId,dmiEventSeverity,
	dmiEventStateKey,dmiEventAssociatedGroup,
	dmiEventSystem,dmiEventSubSystem
		FROM DMTF-DMI-MIB;

DmiCounter		::= Counter32
DmiCounter64		::= Counter64
DmiGauge		::= Gauge32
DmiInteger		::= Integer32
DmiOctetstring		::= OCTET STRING
DmiCompId		::= INTEGER
DmiGroupId		::= INTEGER

dmtf                	OBJECT IDENTIFIER ::= { enterprises 412 }
dmtfStdMifs         	OBJECT IDENTIFIER ::= { dmtf 2 }
dmtfDynOids         	OBJECT IDENTIFIER ::= { dmtf 3 }


dmtfSystemsMIF	MODULE-IDENTITY
     LAST-UPDATED "9710221800Z"
     ORGANIZATION "Desktop Management Task Force"
     CONTACT-INFO
          "         DMTF Technical Advisory Committee

		    Mailstop JF2-53
                    2111 N.E. 25th Avenue
                    Hillsboro, OR 97124

		    Phone: +1 503 264-9300
                    Email: dmtf-info@dmtf.org
          "
     DESCRIPTION
          "This MIB is a translation of the DMTF Systems MIF
          based on the translation rules defined by the
          DMTF DMI to SNMP Mapping Standard, Version 1.0.

	  DMI-based systems running a DMI-to-SNMP Mapping
          Agent provide the ability to access DMI component
          instrumentation via SNMP protocol operations.
          "
::= { dmtfStdMifs 4 }

SdmtfBIOSCharacteristic ::= SEQUENCE {
	dmtfBIOSCharacteristicState INTEGER,
	bIOSCharacteristicIndex	DmiInteger,
	bIOSNumber	DmiInteger,
	bIOSCharacteristic	DmiInteger,
	bIOSCharacteristicDescription	DmiString
}

dmtfBIOSCharacteristicTable OBJECT-TYPE
	SYNTAX		SEQUENCE OF SdmtfBIOSCharacteristic
	MAX-ACCESS	not-accessible
	STATUS		current
	DESCRIPTION	"This group defines the characteristics of the System BIOS."
	::= { dmtfSystemsMIF 4 }

dmtfBIOSCharacteristicEntry OBJECT-TYPE
	SYNTAX		SdmtfBIOSCharacteristic
	MAX-ACCESS	not-accessible
	STATUS		current
	DESCRIPTION	"This group defines the characteristics of the System BIOS."
	INDEX		{ DmiCompId,DmiGroupId, bIOSCharacteristicIndex, bIOSNumber }
	::= { dmtfBIOSCharacteristicTable 1 }


dmtfBIOSCharacteristicState OBJECT-TYPE
	SYNTAX		INTEGER {
		active(1),
		notInService(2),
		notReady(3),
		createAndGo(4),
		createAndWait(5),
		destroy(6)
	}
	MAX-ACCESS	read-write
	STATUS		current
	REFERENCE "'DMTF|BIOS Characteristic|003' 0"
	::= { dmtfBIOSCharacteristicEntry 0 }

bIOSCharacteristicIndex OBJECT-TYPE
	SYNTAX		DmiInteger
	MAX-ACCESS	read-only
	STATUS		current
	DESCRIPTION	"This is an index into the BIOS Characteristics table."
	REFERENCE "'DMTF|BIOS Characteristic|003' 1"
	::= { dmtfBIOSCharacteristicEntry 1 }

bIOSNumber OBJECT-TYPE
	SYNTAX		DmiInteger
	MAX-ACCESS	read-only
	STATUS		current
	DESCRIPTION	"The BIOS number, which correlates to the BIOS Index attribute
in the System BIOS group."
	REFERENCE "'DMTF|BIOS Characteristic|003' 2"
	::= { dmtfBIOSCharacteristicEntry 2 }

bIOSCharacteristic OBJECT-TYPE
	SYNTAX		INTEGER {
		other(1),
		unknown(2),
		unsupported(3),
		iSASupport(4),
		mCASupport(5),
		eISASupport(6),
		pCISupport(7),
		pCMCIASupport(8),
		pnPSupport(9),
		aPMSupport(10),
		upgradeableBIOS(11),
		bIOSShadowingAllowed(12),
		vLVESASupport(13),
		eSCDSupport(14),
		lS120Support(15),
		aCPISupport(16),
		i2OBootSupport(17),
		uSBLegacySupport(18),
		aGPSupport(19),
		pCCard(20),
		iR(21),
		x1394(22),
		i2C(23),
		smartBattery(24),
		pC98(160)
	}
	MAX-ACCESS	read-only
	STATUS		current
	DESCRIPTION	"The different features supported by this version of the BIOS."
	REFERENCE "'DMTF|BIOS Characteristic|003' 3"
	::= { dmtfBIOSCharacteristicEntry 3 }

bIOSCharacteristicDescription OBJECT-TYPE
	SYNTAX		DmiString
	MAX-ACCESS	read-only
	STATUS		current
	DESCRIPTION	"An expanded description of this BIOS Characteristic."
	REFERENCE "'DMTF|BIOS Characteristic|003' 4"
	::= { dmtfBIOSCharacteristicEntry 4 }

SdmtfBusCardLocation ::= SEQUENCE {
	busType	DmiInteger,
	eISAIOAddress	DmiInteger,
	busNumber	DmiInteger,
	busLocation	DmiInteger,
	iSASlot	DmiInteger
}

dmtfBusCardLocationTable OBJECT-TYPE
	SYNTAX		SEQUENCE OF SdmtfBusCardLocation
	MAX-ACCESS	not-accessible
	STATUS		current
	DESCRIPTION	"This group specifies a logical location on an I/O expansion
bus. This group is required."
	::= { dmtfSystemsMIF 69 }

dmtfBusCardLocationEntry OBJECT-TYPE
	SYNTAX		SdmtfBusCardLocation
	MAX-ACCESS	not-accessible
	STATUS		current
	DESCRIPTION	"This group specifies a logical location on an I/O expansion
bus. This group is required."
	INDEX		{ DmiCompId,DmiGroupId }
	::= { dmtfBusCardLocationTable 1 }


busType OBJECT-TYPE
	SYNTAX		INTEGER {
		other(1),
		unknown(2),
		eISA(3),
		pCI(4),
		iSA(5),
		mCA(6),
		sCSI(7),
		iDE(8),
		uSB(9),
		x1394(10),
		i2C(11),
		pCCard(12),
		cardbus(13)
	}
	MAX-ACCESS	read-only
	STATUS		current
	DESCRIPTION	"Type of expansion bus."
	REFERENCE "'DMTF|Bus Card Location|002' 7"
	::= { dmtfBusCardLocationEntry 7 }

eISAIOAddress OBJECT-TYPE
	SYNTAX		DmiInteger
	MAX-ACCESS	read-only
	STATUS		current
	DESCRIPTION	"EISA I/O address which identifies a specific EISA slot."
	REFERENCE "'DMTF|Bus Card Location|002' 8"
	::= { dmtfBusCardLocationEntry 8 }

busNumber OBJECT-TYPE
	SYNTAX		DmiInteger
	MAX-ACCESS	read-only
	STATUS		current
	DESCRIPTION	"Number of the PCI or MCA bus containing a bus card."
	REFERENCE "'DMTF|Bus Card Location|002' 9"
	::= { dmtfBusCardLocationEntry 9 }

busLocation OBJECT-TYPE
	SYNTAX		DmiInteger
	MAX-ACCESS	read-only
	STATUS		current
	DESCRIPTION	"Configuration address specifying the location of a bus card
on a specific PCI or MCA bus."
	REFERENCE "'DMTF|Bus Card Location|002' 10"
	::= { dmtfBusCardLocationEntry 10 }

iSASlot OBJECT-TYPE
	SYNTAX		DmiInteger
	MAX-ACCESS	read-only
	STATUS		current
	DESCRIPTION	"Slot number of an ISA card inserted into an EISA or ISA bus.
This indicates a physical slot number."
	REFERENCE "'DMTF|Bus Card Location|002' 11"
	::= { dmtfBusCardLocationEntry 11 }

SdmtfBusGlobalTable ::= SEQUENCE {
	dmtfBusGlobalTableState INTEGER,
	busID	DmiInteger,
	busType	DmiInteger
}

dmtfBusGlobalTable OBJECT-TYPE
	SYNTAX		SEQUENCE OF SdmtfBusGlobalTable
	MAX-ACCESS	not-accessible
	STATUS		current
	DESCRIPTION	"This global table has one entry for each of the Buses in
this Component. The unique ID provided to each bus is the index into this
table."
	::= { dmtfSystemsMIF 64 }

dmtfBusGlobalEntry OBJECT-TYPE
	SYNTAX		SdmtfBusGlobalTable
	MAX-ACCESS	not-accessible
	STATUS		current
	DESCRIPTION	"This global table has one entry for each of the Buses in
this Component. The unique ID provided to each bus is the index into this
table."
	INDEX		{ DmiCompId,DmiGroupId, busID }
	::= { dmtfBusGlobalTable 1 }


dmtfBusGlobalTableState OBJECT-TYPE
	SYNTAX		INTEGER {
		active(1),
		notInService(2),
		notReady(3),
		createAndGo(4),
		createAndWait(5),
		destroy(6)
	}
	MAX-ACCESS	read-write
	STATUS		current
	REFERENCE "'DMTF|Bus Global Table|002' 0"
	::= { dmtfBusGlobalEntry 0 }

busID OBJECT-TYPE
	SYNTAX		DmiInteger
	MAX-ACCESS	read-only
	STATUS		current
	DESCRIPTION	"Unique index provided to each Bus in this Component and used
as a key into the Bus Global Table."
	REFERENCE "'DMTF|Bus Global Table|002' 1"
	::= { dmtfBusGlobalEntry 1 }

busType OBJECT-TYPE
	SYNTAX		INTEGER {
		other(1),
		unknown(2),
		eISA(3),
		iSA(4),
		pCI(5),
		sCSI(6),
		iDE(7),
		diagnostic(8),
		i2C(9),
		power(10),
		pCCard(11),
		cardbus(12),
		x1394(13),
		uSB(14)
	}
	MAX-ACCESS	read-only
	STATUS		current
	DESCRIPTION	"The type of the bus being described by this entry in the
Bus Global Table."
	REFERENCE "'DMTF|Bus Global Table|002' 2"
	::= { dmtfBusGlobalEntry 2 }

SdmtfBusUtilizationTable ::= SEQUENCE {
	dmtfBusUtilizationTableState INTEGER,
	busIndex	DmiInteger,
	slotIndex	DmiInteger,
	busUtilizationSampleInterval	DmiInteger,
	percentBusUtilization	DmiInteger,
	averageBusThroughputRate	DmiInteger
}

dmtfBusUtilizationTable OBJECT-TYPE
	SYNTAX		SEQUENCE OF SdmtfBusUtilizationTable
	MAX-ACCESS	not-accessible
	STATUS		current
	DESCRIPTION	"This group defines Bus Utilization."
	::= { dmtfSystemsMIF 62 }

dmtfBusUtilizationEntry OBJECT-TYPE
	SYNTAX		SdmtfBusUtilizationTable
	MAX-ACCESS	not-accessible
	STATUS		current
	DESCRIPTION	"This group defines Bus Utilization."
	INDEX		{ DmiCompId,DmiGroupId, busIndex, slotIndex }
	::= { dmtfBusUtilizationTable 1 }


dmtfBusUtilizationTableState OBJECT-TYPE
	SYNTAX		INTEGER {
		active(1),
		notInService(2),
		notReady(3),
		createAndGo(4),
		createAndWait(5),
		destroy(6)
	}
	MAX-ACCESS	read-write
	STATUS		current
	REFERENCE "'DMTF|Bus Utilization Table|001' 0"
	::= { dmtfBusUtilizationEntry 0 }

busIndex OBJECT-TYPE
	SYNTAX		DmiInteger
	MAX-ACCESS	read-only
	STATUS		current
	DESCRIPTION	"Index that uniquely identifies a bus in the system or component
for which utilization is being measured. This is an index into the Bus Global
Table."
	REFERENCE "'DMTF|Bus Utilization Table|001' 1"
	::= { dmtfBusUtilizationEntry 1 }

slotIndex OBJECT-TYPE
	SYNTAX		DmiInteger
	MAX-ACCESS	read-only
	STATUS		current
	DESCRIPTION	"Index of the slot (real or virtual) in the System Slots group
for which bus utilization is being measured. An index of 0 corresponds to
the total utilization for the bus i.e. a total for all slots."
	REFERENCE "'DMTF|Bus Utilization Table|001' 2"
	::= { dmtfBusUtilizationEntry 2 }

busUtilizationSampleInterval OBJECT-TYPE
	SYNTAX		DmiInteger
	MAX-ACCESS	read-write
	STATUS		current
	DESCRIPTION	"Length of time in millisecs over which bus utilization is
measured.  A value of 0x80000000 denotes 'unknown'."
	REFERENCE "'DMTF|Bus Utilization Table|001' 3"
	::= { dmtfBusUtilizationEntry 3 }

percentBusUtilization OBJECT-TYPE
	SYNTAX		DmiInteger
	MAX-ACCESS	read-only
	STATUS		current
	DESCRIPTION	"Percent of the time the specified bus was busy transfering
data to or from the slot specified in slot index. A value of 0x80000000 means
that the percent bus utilization is unknown."
	REFERENCE "'DMTF|Bus Utilization Table|001' 4"
	::= { dmtfBusUtilizationEntry 4 }

averageBusThroughputRate OBJECT-TYPE
	SYNTAX		DmiInteger
	MAX-ACCESS	read-only
	STATUS		current
	DESCRIPTION	"Average mega bytes transferred by the bus per second during
the sampling interval. A value of 0x80000000 means that the average bus throughp
t rate is unknown."
	REFERENCE "'DMTF|Bus Utilization Table|001' 5"
	::= { dmtfBusUtilizationEntry 5 }

SdmtfCachePerformanceTable ::= SEQUENCE {
	dmtfCachePerformanceTableState INTEGER,
	cacheIndex	DmiInteger,
	millisecondCounter	DmiCounter,
	cacheAccessCount	DmiCounter64,
	cacheHitCount	DmiCounter64,
	partialHitCount	DmiCounter64,
	hitDataSize	Dmi-Integer64,
	validUsage	DmiInteger,
	dirtyUsage	DmiInteger,
	timeOfLastDetectedFault	DmiInteger,
	lastFaultFailureDetected	DmiInteger
}

dmtfCachePerformanceTable OBJECT-TYPE
	SYNTAX		SEQUENCE OF SdmtfCachePerformanceTable
	MAX-ACCESS	not-accessible
	STATUS		current
	DESCRIPTION	"This is a table of entries for cache performance for all
components in the system that implement a cache."
	::= { dmtfSystemsMIF 61 }

dmtfCachePerformanceEntry OBJECT-TYPE
	SYNTAX		SdmtfCachePerformanceTable
	MAX-ACCESS	not-accessible
	STATUS		current
	DESCRIPTION	"This is a table of entries for cache performance for all
components in the system that implement a cache."
	INDEX		{ DmiCompId,DmiGroupId, cacheIndex }
	::= { dmtfCachePerformanceTable 1 }


dmtfCachePerformanceTableState OBJECT-TYPE
	SYNTAX		INTEGER {
		active(1),
		notInService(2),
		notReady(3),
		createAndGo(4),
		createAndWait(5),
		destroy(6)
	}
	MAX-ACCESS	read-write
	STATUS		current
	REFERENCE "'DMTF|Cache Performance Table|002' 0"
	::= { dmtfCachePerformanceEntry 0 }

cacheIndex OBJECT-TYPE
	SYNTAX		DmiInteger
	MAX-ACCESS	read-only
	STATUS		current
	DESCRIPTION	"Index into the System Cache table"
	REFERENCE "'DMTF|Cache Performance Table|002' 1"
	::= { dmtfCachePerformanceEntry 1 }

millisecondCounter OBJECT-TYPE
	SYNTAX		DmiCounter
	MAX-ACCESS	read-only
	STATUS		current
	DESCRIPTION	"32 bit counter that gets incremented every millisecond"
	REFERENCE "'DMTF|Cache Performance Table|002' 2"
	::= { dmtfCachePerformanceEntry 2 }

cacheAccessCount OBJECT-TYPE
	SYNTAX		DmiCounter64
	MAX-ACCESS	read-only
	STATUS		current
	DESCRIPTION	"64 bit counter that counts the number of times the cache
has been accessed. A value of 0x8000000000000000 denotes 'unknown'."
	REFERENCE "'DMTF|Cache Performance Table|002' 3"
	::= { dmtfCachePerformanceEntry 3 }

cacheHitCount OBJECT-TYPE
	SYNTAX		DmiCounter64
	MAX-ACCESS	read-only
	STATUS		current
	DESCRIPTION	"64 bit counter that counts the number of times there was
a cache hit. i.e. memory being accessed was in the Cache. A value of 0x800000000
000000 denotes 'unknown'."
	REFERENCE "'DMTF|Cache Performance Table|002' 4"
	::= { dmtfCachePerformanceEntry 4 }

partialHitCount OBJECT-TYPE
	SYNTAX		DmiCounter64
	MAX-ACCESS	read-only
	STATUS		current
	DESCRIPTION	"Counts the number of times there was a partial cache hit.
 A value of 0x8000000000000000 denotes 'unknown' or 'unsupported'."
	REFERENCE "'DMTF|Cache Performance Table|002' 5"
	::= { dmtfCachePerformanceEntry 5 }

hitDataSize OBJECT-TYPE
	SYNTAX		Dmi-Integer64
	MAX-ACCESS	read-only
	STATUS		current
	DESCRIPTION	"On a partial hit the number of bytes that were available
in cache.  A value of 0x8000000000000000 denotes 'unknown' or 'unsupported'."
	REFERENCE "'DMTF|Cache Performance Table|002' 6"
	::= { dmtfCachePerformanceEntry 6 }

validUsage OBJECT-TYPE
	SYNTAX		DmiInteger
	MAX-ACCESS	read-only
	STATUS		current
	DESCRIPTION	"The amount of cache currently holding valid data, in kilobytes.
A value of 0x80000000 denotes 'unknown' or 'unsupported'."
	REFERENCE "'DMTF|Cache Performance Table|002' 7"
	::= { dmtfCachePerformanceEntry 7 }

dirtyUsage OBJECT-TYPE
	SYNTAX		DmiInteger
	MAX-ACCESS	read-only
	STATUS		current
	DESCRIPTION	"The amount of cache data, in kilobytes, not yet written to
media. A value of 0x80000000 denotes 'unknown' or 'unsupported'."
	REFERENCE "'DMTF|Cache Performance Table|002' 8"
	::= { dmtfCachePerformanceEntry 8 }

timeOfLastDetectedFault OBJECT-TYPE
	SYNTAX		DmiInteger
	MAX-ACCESS	read-only
	STATUS		current
	DESCRIPTION	"The number of seconds that have passed between power on the
last detected cache fault or failure."
	REFERENCE "'DMTF|Cache Performance Table|002' 9"
	::= { dmtfCachePerformanceEntry 9 }

lastFaultFailureDetected OBJECT-TYPE
	SYNTAX		DmiInteger
	MAX-ACCESS	read-only
	STATUS		current
	DESCRIPTION	"The vendor-unique fault code associated with the most recent
fault or failure detected with this cache."
	REFERENCE "'DMTF|Cache Performance Table|002' 10"
	::= { dmtfCachePerformanceEntry 10 }

SdmtfCoolingDevice ::= SEQUENCE {
	dmtfCoolingDeviceState INTEGER,
	coolingDeviceTableIndex	DmiInteger,
	fRUGroupIndex	DmiInteger,
	operationalGroupIndex	DmiInteger,
	coolingUnitIndex	DmiInteger,
	coolingDeviceType	DmiInteger,
	temperatureProbeIndex	DmiInteger
}

dmtfCoolingDeviceTable OBJECT-TYPE
	SYNTAX		SEQUENCE OF SdmtfCoolingDevice
	MAX-ACCESS	not-accessible
	STATUS		current
	DESCRIPTION	"This group defines various attributes for cooling devices
in this system."
	::= { dmtfSystemsMIF 17 }

dmtfCoolingDeviceEntry OBJECT-TYPE
	SYNTAX		SdmtfCoolingDevice
	MAX-ACCESS	not-accessible
	STATUS		current
	DESCRIPTION	"This group defines various attributes for cooling devices
in this system."
	INDEX		{ DmiCompId,DmiGroupId, coolingDeviceTableIndex }
	::= { dmtfCoolingDeviceTable 1 }


dmtfCoolingDeviceState OBJECT-TYPE
	SYNTAX		INTEGER {
		active(1),
		notInService(2),
		notReady(3),
		createAndGo(4),
		createAndWait(5),
		destroy(6)
	}
	MAX-ACCESS	read-write
	STATUS		current
	REFERENCE "'DMTF|Cooling Device|002' 0"
	::= { dmtfCoolingDeviceEntry 0 }

coolingDeviceTableIndex OBJECT-TYPE
	SYNTAX		DmiInteger
	MAX-ACCESS	read-only
	STATUS		current
	DESCRIPTION	"An index into the cooling device table."
	REFERENCE "'DMTF|Cooling Device|002' 1"
	::= { dmtfCoolingDeviceEntry 1 }

fRUGroupIndex OBJECT-TYPE
	SYNTAX		DmiInteger
	MAX-ACCESS	read-only
	STATUS		current
	DESCRIPTION	"If this is a Field Replaceable Unit or if it is part of another
FRU, this provides an index into the FRU table; 'value = -1' indicates that
the group is not a FRU."
	REFERENCE "'DMTF|Cooling Device|002' 2"
	::= { dmtfCoolingDeviceEntry 2 }

operationalGroupIndex OBJECT-TYPE
	SYNTAX		DmiInteger
	MAX-ACCESS	read-only
	STATUS		current
	DESCRIPTION	"The index into the Operational State table for this device."
	REFERENCE "'DMTF|Cooling Device|002' 3"
	::= { dmtfCoolingDeviceEntry 3 }

coolingUnitIndex OBJECT-TYPE
	SYNTAX		DmiInteger
	MAX-ACCESS	read-only
	STATUS		current
	DESCRIPTION	"This is the ID of the Cooling Unit (logical cooling device)
of which this Cooling Device is a part. This value matches up with the Cooling
Unit Table Index attribute defined in the Cooling Unit Global Table."
	REFERENCE "'DMTF|Cooling Device|002' 4"
	::= { dmtfCoolingDeviceEntry 4 }

coolingDeviceType OBJECT-TYPE
	SYNTAX		INTEGER {
		other(1),
		unknown(2),
		fan(3),
		centrifugalBlower(4),
		chipFan(5),
		cabinetFan(6),
		powerSupplyFan(7),
		heatPipe(8),
		integratedRefrigeration(9),
		activeCooling(32),
		passiveCooling(33)
	}
	MAX-ACCESS	read-only
	STATUS		current
	DESCRIPTION	"The type of Cooling Device that this is e.g. Fan, Heat Pipe,
etc."
	REFERENCE "'DMTF|Cooling Device|002' 5"
	::= { dmtfCoolingDeviceEntry 5 }

temperatureProbeIndex OBJECT-TYPE
	SYNTAX		DmiInteger
	MAX-ACCESS	read-only
	STATUS		current
	DESCRIPTION	"Index into the Temperature Probe table identifying the temperatu
e probe monitoring this cooling device. 0 indicates no probe provided."
	REFERENCE "'DMTF|Cooling Device|002' 6"
	::= { dmtfCoolingDeviceEntry 6 }

SdmtfCoolingUnitGlobalTable ::= SEQUENCE {
	dmtfCoolingUnitGlobalTableState INTEGER,
	coolingUnitIndex	DmiInteger,
	coolingUnitStatus	DmiInteger
}

dmtfCoolingUnitGlobalTable OBJECT-TYPE
	SYNTAX		SEQUENCE OF SdmtfCoolingUnitGlobalTable
	MAX-ACCESS	not-accessible
	STATUS		current
	DESCRIPTION	"This global table describes all of the Cooling Units in this
system component.  The unique index of each Cooling Unit is a key into this
table. A Cooling Unit is composed of potentially more than one Cooling Device
in a redundant configuration.  Cooling devices are described by the 'Cooling
Device' standard group. Each cooling device described by a row in the Cooling
Device standard group will point to a corresponding Cooling Unit in this
table by using the row index of the row that describes the Coolin"
	::= { dmtfSystemsMIF 67 }

dmtfCoolingUnitGlobalEntry OBJECT-TYPE
	SYNTAX		SdmtfCoolingUnitGlobalTable
	MAX-ACCESS	not-accessible
	STATUS		current
	DESCRIPTION	"This global table describes all of the Cooling Units in this
system component.  The unique index of each Cooling Unit is a key into this
table. A Cooling Unit is composed of potentially more than one Cooling Device
in a redundant configuration.  Cooling devices are described by the 'Cooling
Device' standard group. Each cooling device described by a row in the Cooling
Device standard group will point to a corresponding Cooling Unit in this
table by using the row index of the row that describes the Coolin"
	INDEX		{ DmiCompId,DmiGroupId, coolingUnitIndex }
	::= { dmtfCoolingUnitGlobalTable 1 }


dmtfCoolingUnitGlobalTableState OBJECT-TYPE
	SYNTAX		INTEGER {
		active(1),
		notInService(2),
		notReady(3),
		createAndGo(4),
		createAndWait(5),
		destroy(6)
	}
	MAX-ACCESS	read-write
	STATUS		current
	REFERENCE "'DMTF|Cooling Unit Global Table|001' 0"
	::= { dmtfCoolingUnitGlobalEntry 0 }

coolingUnitIndex OBJECT-TYPE
	SYNTAX		DmiInteger
	MAX-ACCESS	read-only
	STATUS		current
	DESCRIPTION	"The unique index given to each Cooling Unit being described
by this table. This unique index is the key into this table."
	REFERENCE "'DMTF|Cooling Unit Global Table|001' 1"
	::= { dmtfCoolingUnitGlobalEntry 1 }

coolingUnitStatus OBJECT-TYPE
	SYNTAX		INTEGER {
		other(1),
		unknown(2),
		notApplicableUnitNotRedundant(3),
		offline(4),
		fullyRedundant(5),
		degradedRedundancy(6),
		redundancyLost(7)
	}
	MAX-ACCESS	read-only
	STATUS		current
	DESCRIPTION	"Gives the redundancy status of the Cooling Unit. 'Fully Redundan
' means that all of the configured redundancy is still available; 'Degraded
Redundancy' means that some failures have been experienced but some reduced
amount of redundancy is still available; 'Redundancy Lost' means that a sufficie
t number of failures have been experienced that no redundancy is available
and the next failure experienced within the Cooling Unit will cause overall
Cooling Unit failure. "
	REFERENCE "'DMTF|Cooling Unit Global Table|001' 2"
	::= { dmtfCoolingUnitGlobalEntry 2 }

SdmtfDMA ::= SEQUENCE {
	dmtfDMAState INTEGER,
	dMANumber	DmiInteger,
	dMAChannelAvailability	DmiInteger,
	dMABurstMode	DmiInteger,
	dMADescription	DmiString
}

dmtfDMATable OBJECT-TYPE
	SYNTAX		SEQUENCE OF SdmtfDMA
	MAX-ACCESS	not-accessible
	STATUS		current
	DESCRIPTION	"This group defines various attributes for the various DMA
channels in this system."
	::= { dmtfSystemsMIF 13 }

dmtfDMAEntry OBJECT-TYPE
	SYNTAX		SdmtfDMA
	MAX-ACCESS	not-accessible
	STATUS		current
	DESCRIPTION	"This group defines various attributes for the various DMA
channels in this system."
	INDEX		{ DmiCompId,DmiGroupId, dMANumber }
	::= { dmtfDMATable 1 }


dmtfDMAState OBJECT-TYPE
	SYNTAX		INTEGER {
		active(1),
		notInService(2),
		notReady(3),
		createAndGo(4),
		createAndWait(5),
		destroy(6)
	}
	MAX-ACCESS	read-write
	STATUS		current
	REFERENCE "'DMTF|DMA|001' 0"
	::= { dmtfDMAEntry 0 }

dMANumber OBJECT-TYPE
	SYNTAX		DmiInteger
	MAX-ACCESS	read-only
	STATUS		current
	DESCRIPTION	"The current DMA channel number."
	REFERENCE "'DMTF|DMA|001' 1"
	::= { dmtfDMAEntry 1 }

dMAChannelAvailability OBJECT-TYPE
	SYNTAX		INTEGER {
		false(0),
		true(1)
	}
	MAX-ACCESS	read-only
	STATUS		current
	DESCRIPTION	"If true, this DMA channel is available."
	REFERENCE "'DMTF|DMA|001' 2"
	::= { dmtfDMAEntry 2 }

dMABurstMode OBJECT-TYPE
	SYNTAX		INTEGER {
		false(0),
		true(1)
	}
	MAX-ACCESS	read-only
	STATUS		current
	DESCRIPTION	"If true, this DMA channel supports burst mode."
	REFERENCE "'DMTF|DMA|001' 3"
	::= { dmtfDMAEntry 3 }

dMADescription OBJECT-TYPE
	SYNTAX		DmiString
	MAX-ACCESS	read-only
	STATUS		current
	DESCRIPTION	"The name of the logical device that is currently using this
DMA channel."
	REFERENCE "'DMTF|DMA|001' 4"
	::= { dmtfDMAEntry 4 }

SdmtfDiagnosticFunctionGroup ::= SEQUENCE {
	dmtfDiagnosticFunctionGroupState INTEGER,
	diagnosticFunctionTableIndex	DmiInteger,
	diagnosticFunctionName	DmiString,
	diagnosticFunctionDescription	DmiString,
	exclusiveAccessRequired	DmiInteger,
	prerequisiteConditions	DmiInteger,
	prerequisiteDiagnosticFunction	DmiInteger
}

dmtfDiagnosticFunctionGroupTable OBJECT-TYPE
	SYNTAX		SEQUENCE OF SdmtfDiagnosticFunctionGroup
	MAX-ACCESS	not-accessible
	STATUS		current
	DESCRIPTION	"This group defines the diagnostic functions that are provided
by this component for analyzing potential failures within the component.
A diagnostic function could be an actual test run against the component,
the results of a self-test of the component, an analysis of failure information
captured during a failure of the component, or an analysis of the current
state of the component."
	::= { dmtfSystemsMIF 56 }

dmtfDiagnosticFunctionGroupEntry OBJECT-TYPE
	SYNTAX		SdmtfDiagnosticFunctionGroup
	MAX-ACCESS	not-accessible
	STATUS		current
	DESCRIPTION	"This group defines the diagnostic functions that are provided
by this component for analyzing potential failures within the component.
A diagnostic function could be an actual test run against the component,
the results of a self-test of the component, an analysis of failure information
captured during a failure of the component, or an analysis of the current
state of the component."
	INDEX		{ DmiCompId,DmiGroupId, diagnosticFunctionTableIndex }
	::= { dmtfDiagnosticFunctionGroupTable 1 }


dmtfDiagnosticFunctionGroupState OBJECT-TYPE
	SYNTAX		INTEGER {
		active(1),
		notInService(2),
		notReady(3),
		createAndGo(4),
		createAndWait(5),
		destroy(6)
	}
	MAX-ACCESS	read-write
	STATUS		current
	REFERENCE "'DMTF|Diagnostic Function Group|001' 0"
	::= { dmtfDiagnosticFunctionGroupEntry 0 }

diagnosticFunctionTableIndex OBJECT-TYPE
	SYNTAX		DmiInteger
	MAX-ACCESS	read-only
	STATUS		current
	DESCRIPTION	"A unique identifier for this specific diagnostic function."
	REFERENCE "'DMTF|Diagnostic Function Group|001' 1"
	::= { dmtfDiagnosticFunctionGroupEntry 1 }

diagnosticFunctionName OBJECT-TYPE
	SYNTAX		DmiString
	MAX-ACCESS	read-only
	STATUS		current
	DESCRIPTION	"A specific descriptive name of the diagnostic function, includin
 version information, if relevant."
	REFERENCE "'DMTF|Diagnostic Function Group|001' 2"
	::= { dmtfDiagnosticFunctionGroupEntry 2 }

diagnosticFunctionDescription OBJECT-TYPE
	SYNTAX		DmiString
	MAX-ACCESS	read-only
	STATUS		current
	DESCRIPTION	"A description of what this diagnostic function does."
	REFERENCE "'DMTF|Diagnostic Function Group|001' 3"
	::= { dmtfDiagnosticFunctionGroupEntry 3 }

exclusiveAccessRequired OBJECT-TYPE
	SYNTAX		INTEGER {
		false(0),
		true(1)
	}
	MAX-ACCESS	read-only
	STATUS		current
	DESCRIPTION	"Indicates whether this diagnostic function requires exclusive
access to the device or component, implying that the user or management applicat
on must take some action within the operating system to ensure that the device
or component cannot be used by any other function."
	REFERENCE "'DMTF|Diagnostic Function Group|001' 4"
	::= { dmtfDiagnosticFunctionGroupEntry 4 }

prerequisiteConditions OBJECT-TYPE
	SYNTAX		INTEGER {
		other(1),
		unknown(2),
		noPrerequisites(3),
		wrapPlugInstalled(4),
		noMediaInstalled(5),
		scratchMediaInstalled(6),
		testMediaInstalled(7),
		systemReferenceDisketteInstalled(8)
	}
	MAX-ACCESS	read-only
	STATUS		current
	DESCRIPTION	"Indicates what conditions must be met before this diagnostic
function can be run."
	REFERENCE "'DMTF|Diagnostic Function Group|001' 5"
	::= { dmtfDiagnosticFunctionGroupEntry 5 }

prerequisiteDiagnosticFunction OBJECT-TYPE
	SYNTAX		DmiInteger
	MAX-ACCESS	read-only
	STATUS		current
	DESCRIPTION	"If non-0, this specifies the ID of another diagnostic function
that must be run immediately prior to this one."
	REFERENCE "'DMTF|Diagnostic Function Group|001' 6"
	::= { dmtfDiagnosticFunctionGroupEntry 6 }

SdmtfDiagnosticRequestGroup ::= SEQUENCE {
	diagnosticFunctionReserveKey	DmiInteger,
	diagnosticFunctionRequest	DmiInteger,
	diagnosticFunctionResult	DmiInteger
}

dmtfDiagnosticRequestGroupTable OBJECT-TYPE
	SYNTAX		SEQUENCE OF SdmtfDiagnosticRequestGroup
	MAX-ACCESS	not-accessible
	STATUS		current
	DESCRIPTION	"This group defines the attributes which a management application
uses to request an actual diagnostic analysis."
	::= { dmtfSystemsMIF 57 }

dmtfDiagnosticRequestGroupEntry OBJECT-TYPE
	SYNTAX		SdmtfDiagnosticRequestGroup
	MAX-ACCESS	not-accessible
	STATUS		current
	DESCRIPTION	"This group defines the attributes which a management application
uses to request an actual diagnostic analysis."
	INDEX		{ DmiCompId,DmiGroupId }
	::= { dmtfDiagnosticRequestGroupTable 1 }


diagnosticFunctionReserveKey OBJECT-TYPE
	SYNTAX		DmiInteger
	MAX-ACCESS	read-write
	STATUS		current
	DESCRIPTION	"Indicates whether the interface to this component's diagnostic
functions is reserved. A zero value returned on a get indicates that a reserve
is already in effect.  A non-zero value indicates that no reserve was in
effect, and the returned value may be used as a reserve key."
	REFERENCE "'DMTF|Diagnostic Request Group|001' 1"
	::= { dmtfDiagnosticRequestGroupEntry 1 }

diagnosticFunctionRequest OBJECT-TYPE
	SYNTAX		DmiInteger
	MAX-ACCESS	read-write
	STATUS		current
	DESCRIPTION	"The ID of the specific diagnostic function which is being
requested. If the interface is reserved, a set request to this attribute
should also set the Diagnostic Function Reserve Key with the reserve key
value."
	REFERENCE "'DMTF|Diagnostic Request Group|001' 2"
	::= { dmtfDiagnosticRequestGroupEntry 2 }

diagnosticFunctionResult OBJECT-TYPE
	SYNTAX		DmiInteger
	MAX-ACCESS	read-only
	STATUS		current
	DESCRIPTION	"The integer-based result code of the last diagnostic function
run."
	REFERENCE "'DMTF|Diagnostic Request Group|001' 3"
	::= { dmtfDiagnosticRequestGroupEntry 3 }

SdmtfDiagnosticResultsFRUCall ::= SEQUENCE {
	dmtfDiagnosticResultsFRUCallState INTEGER,
	diagnosticFunctionID	DmiInteger,
	diagnosticFunctionResult	DmiInteger,
	fRUIndexPointer	DmiInteger,
	fRUProbability	DmiInteger
}

dmtfDiagnosticResultsFRUCallTable OBJECT-TYPE
	SYNTAX		SEQUENCE OF SdmtfDiagnosticResultsFRUCall
	MAX-ACCESS	not-accessible
	STATUS		current
	DESCRIPTION	"This group defines the possible FRUs (Field Replaceable Units)
implied by the diagnostic function results. This table may hold multiple
FRU entries for a given diagnostic ID and result."
	::= { dmtfSystemsMIF 59 }

dmtfDiagnosticResultsFRUCallEntry OBJECT-TYPE
	SYNTAX		SdmtfDiagnosticResultsFRUCall
	MAX-ACCESS	not-accessible
	STATUS		current
	DESCRIPTION	"This group defines the possible FRUs (Field Replaceable Units)
implied by the diagnostic function results. This table may hold multiple
FRU entries for a given diagnostic ID and result."
	INDEX		{ DmiCompId,DmiGroupId, diagnosticFunctionID, diagnosticFunctionResult, fRUIndexPointer }
	::= { dmtfDiagnosticResultsFRUCallTable 1 }


dmtfDiagnosticResultsFRUCallState OBJECT-TYPE
	SYNTAX		INTEGER {
		active(1),
		notInService(2),
		notReady(3),
		createAndGo(4),
		createAndWait(5),
		destroy(6)
	}
	MAX-ACCESS	read-write
	STATUS		current
	REFERENCE "'DMTF|Diagnostic Results FRU Call|001' 0"
	::= { dmtfDiagnosticResultsFRUCallEntry 0 }

diagnosticFunctionID OBJECT-TYPE
	SYNTAX		DmiInteger
	MAX-ACCESS	read-only
	STATUS		current
	DESCRIPTION	"The unique ID of a specific diagnostic function."
	REFERENCE "'DMTF|Diagnostic Results FRU Call|001' 1"
	::= { dmtfDiagnosticResultsFRUCallEntry 1 }

diagnosticFunctionResult OBJECT-TYPE
	SYNTAX		DmiInteger
	MAX-ACCESS	read-only
	STATUS		current
	DESCRIPTION	"An integer-based result code of the diagnostic function."
	REFERENCE "'DMTF|Diagnostic Results FRU Call|001' 2"
	::= { dmtfDiagnosticResultsFRUCallEntry 2 }

fRUIndexPointer OBJECT-TYPE
	SYNTAX		DmiInteger
	MAX-ACCESS	read-only
	STATUS		current
	DESCRIPTION	"The index in the FRU table of the implied failing FRU."
	REFERENCE "'DMTF|Diagnostic Results FRU Call|001' 3"
	::= { dmtfDiagnosticResultsFRUCallEntry 3 }

fRUProbability OBJECT-TYPE
	SYNTAX		DmiInteger
	MAX-ACCESS	read-only
	STATUS		current
	DESCRIPTION	"The probability, in percent, that this is the failing FRU.
A value of 0x80000000 means the probability is unknown; otherwise, this should
be a percentage number from 1 to 100."
	REFERENCE "'DMTF|Diagnostic Results FRU Call|001' 4"
	::= { dmtfDiagnosticResultsFRUCallEntry 4 }

SdmtfDiagnosticResultsGroup ::= SEQUENCE {
	dmtfDiagnosticResultsGroupState INTEGER,
	diagnosticFunctionID	DmiInteger,
	diagnosticFunctionResult	DmiInteger,
	diagnosticFunctionResultDescription	DmiString,
	faultIsolatedToThisComponent	DmiInteger
}

dmtfDiagnosticResultsGroupTable OBJECT-TYPE
	SYNTAX		SEQUENCE OF SdmtfDiagnosticResultsGroup
	MAX-ACCESS	not-accessible
	STATUS		current
	DESCRIPTION	"This group defines the attributes for interpreting diagnostic
function result codes."
	::= { dmtfSystemsMIF 58 }

dmtfDiagnosticResultsGroupEntry OBJECT-TYPE
	SYNTAX		SdmtfDiagnosticResultsGroup
	MAX-ACCESS	not-accessible
	STATUS		current
	DESCRIPTION	"This group defines the attributes for interpreting diagnostic
function result codes."
	INDEX		{ DmiCompId,DmiGroupId, diagnosticFunctionID, diagnosticFunctionResult }
	::= { dmtfDiagnosticResultsGroupTable 1 }


dmtfDiagnosticResultsGroupState OBJECT-TYPE
	SYNTAX		INTEGER {
		active(1),
		notInService(2),
		notReady(3),
		createAndGo(4),
		createAndWait(5),
		destroy(6)
	}
	MAX-ACCESS	read-write
	STATUS		current
	REFERENCE "'DMTF|Diagnostic Results Group|001' 0"
	::= { dmtfDiagnosticResultsGroupEntry 0 }

diagnosticFunctionID OBJECT-TYPE
	SYNTAX		DmiInteger
	MAX-ACCESS	read-only
	STATUS		current
	DESCRIPTION	"The unique ID for a specific diagnostic function."
	REFERENCE "'DMTF|Diagnostic Results Group|001' 1"
	::= { dmtfDiagnosticResultsGroupEntry 1 }

diagnosticFunctionResult OBJECT-TYPE
	SYNTAX		DmiInteger
	MAX-ACCESS	read-only
	STATUS		current
	DESCRIPTION	"An integer-based result code of the diagnostic function."
	REFERENCE "'DMTF|Diagnostic Results Group|001' 2"
	::= { dmtfDiagnosticResultsGroupEntry 2 }

diagnosticFunctionResultDescription OBJECT-TYPE
	SYNTAX		DmiString
	MAX-ACCESS	read-only
	STATUS		current
	DESCRIPTION	"A description of what this result code for this diagnostic
function means, including suggested corrective actions, where possible."
	REFERENCE "'DMTF|Diagnostic Results Group|001' 3"
	::= { dmtfDiagnosticResultsGroupEntry 3 }

faultIsolatedToThisComponent OBJECT-TYPE
	SYNTAX		INTEGER {
		false(0),
		true(1)
	}
	MAX-ACCESS	read-only
	STATUS		current
	DESCRIPTION	"An indicator of whether the fault is strictly isolated within
the bounds of this component. A False value indicates that the fault might
be caused by a failing parent component; for example, a disk test may fail
because of a faulty disk controller."
	REFERENCE "'DMTF|Diagnostic Results Group|001' 4"
	::= { dmtfDiagnosticResultsGroupEntry 4 }

SdmtfDiskController ::= SEQUENCE {
	dmtfDiskControllerState INTEGER,
	diskControllerIndex	DmiInteger,
	fRUGroupIndex	DmiInteger,
	operationalGroupIndex	DmiInteger,
	systemSlotIndex	DmiInteger,
	diskControllerIdentification	DmiString,
	controllerSoftwareRevisionLevel	DmiString,
	controllerChannelCount	DmiInteger,
	controllerMaximumDevices	DmiInteger
}

dmtfDiskControllerTable OBJECT-TYPE
	SYNTAX		SEQUENCE OF SdmtfDiskController
	MAX-ACCESS	not-accessible
	STATUS		current
	DESCRIPTION	"This group defines the disk controller in this system."
	::= { dmtfSystemsMIF 25 }

dmtfDiskControllerEntry OBJECT-TYPE
	SYNTAX		SdmtfDiskController
	MAX-ACCESS	not-accessible
	STATUS		current
	DESCRIPTION	"This group defines the disk controller in this system."
	INDEX		{ DmiCompId,DmiGroupId, diskControllerIndex }
	::= { dmtfDiskControllerTable 1 }


dmtfDiskControllerState OBJECT-TYPE
	SYNTAX		INTEGER {
		active(1),
		notInService(2),
		notReady(3),
		createAndGo(4),
		createAndWait(5),
		destroy(6)
	}
	MAX-ACCESS	read-write
	STATUS		current
	REFERENCE "'DMTF|Disk Controller|002' 0"
	::= { dmtfDiskControllerEntry 0 }

diskControllerIndex OBJECT-TYPE
	SYNTAX		DmiInteger
	MAX-ACCESS	read-only
	STATUS		current
	DESCRIPTION	"Index value used by the system to identify the disk controller."
	REFERENCE "'DMTF|Disk Controller|002' 1"
	::= { dmtfDiskControllerEntry 1 }

fRUGroupIndex OBJECT-TYPE
	SYNTAX		DmiInteger
	MAX-ACCESS	read-only
	STATUS		current
	DESCRIPTION	"If this is a Field Replaceable Unit or if it is part of another
FRU, this provides an index into the FRU table; 'value = -1' indicates that
the group is not a FRU."
	REFERENCE "'DMTF|Disk Controller|002' 2"
	::= { dmtfDiskControllerEntry 2 }

operationalGroupIndex OBJECT-TYPE
	SYNTAX		DmiInteger
	MAX-ACCESS	read-only
	STATUS		current
	DESCRIPTION	"The index into the Operational State table for this device."
	REFERENCE "'DMTF|Disk Controller|002' 3"
	::= { dmtfDiskControllerEntry 3 }

systemSlotIndex OBJECT-TYPE
	SYNTAX		DmiInteger
	MAX-ACCESS	read-only
	STATUS		current
	DESCRIPTION	"Index value in System Slot table of disk Controller. 0 =
no slot"
	REFERENCE "'DMTF|Disk Controller|002' 4"
	::= { dmtfDiskControllerEntry 4 }

diskControllerIdentification OBJECT-TYPE
	SYNTAX		DmiString
	MAX-ACCESS	read-only
	STATUS		current
	DESCRIPTION	"Name, brand and hardware revision level of the disk controller."
	REFERENCE "'DMTF|Disk Controller|002' 5"
	::= { dmtfDiskControllerEntry 5 }

controllerSoftwareRevisionLevel OBJECT-TYPE
	SYNTAX		DmiString
	MAX-ACCESS	read-only
	STATUS		current
	DESCRIPTION	"Level and version of the software associated with this controlle
."
	REFERENCE "'DMTF|Disk Controller|002' 6"
	::= { dmtfDiskControllerEntry 6 }

controllerChannelCount OBJECT-TYPE
	SYNTAX		DmiInteger
	MAX-ACCESS	read-only
	STATUS		current
	DESCRIPTION	"The number of channels supported by this controller. 0x80000000
= Unknown"
	REFERENCE "'DMTF|Disk Controller|002' 7"
	::= { dmtfDiskControllerEntry 7 }

controllerMaximumDevices OBJECT-TYPE
	SYNTAX		DmiInteger
	MAX-ACCESS	read-only
	STATUS		current
	DESCRIPTION	"The maximum number of devices for all channels which can
be controlled by this disk controller. 0x80000000 = Unknown "
	REFERENCE "'DMTF|Disk Controller|002' 8"
	::= { dmtfDiskControllerEntry 8 }

SdmtfDisksMappingTable ::= SEQUENCE {
	dmtfDisksMappingTableState INTEGER,
	storageType	DmiInteger,
	diskIndex	DmiInteger,
	partitionIndex	DmiInteger
}

dmtfDisksMappingTable OBJECT-TYPE
	SYNTAX		SEQUENCE OF SdmtfDisksMappingTable
	MAX-ACCESS	not-accessible
	STATUS		current
	DESCRIPTION	"A table relating disks to partitions. May have an instance
of a disk or partition more than once."
	::= { dmtfSystemsMIF 23 }

dmtfDisksMappingEntry OBJECT-TYPE
	SYNTAX		SdmtfDisksMappingTable
	MAX-ACCESS	not-accessible
	STATUS		current
	DESCRIPTION	"A table relating disks to partitions. May have an instance
of a disk or partition more than once."
	INDEX		{ DmiCompId,DmiGroupId, storageType, diskIndex, partitionIndex }
	::= { dmtfDisksMappingTable 1 }


dmtfDisksMappingTableState OBJECT-TYPE
	SYNTAX		INTEGER {
		active(1),
		notInService(2),
		notReady(3),
		createAndGo(4),
		createAndWait(5),
		destroy(6)
	}
	MAX-ACCESS	read-write
	STATUS		current
	REFERENCE "'DMTF|Disks Mapping Table|001' 0"
	::= { dmtfDisksMappingEntry 0 }

storageType OBJECT-TYPE
	SYNTAX		INTEGER {
		other(1),
		unknown(2),
		hardDisk(3),
		floppyDisk(4),
		opticalROM(5),
		opticalWORM(6),
		opticalRW(7),
		compactDisk(8),
		flashDisk(9),
		bernoulli(10),
		opticalFloppyDisk(11)
	}
	MAX-ACCESS	read-only
	STATUS		current
	DESCRIPTION	"The type of the mass storage device."
	REFERENCE "'DMTF|Disks Mapping Table|001' 1"
	::= { dmtfDisksMappingEntry 1 }

diskIndex OBJECT-TYPE
	SYNTAX		DmiInteger
	MAX-ACCESS	read-only
	STATUS		current
	DESCRIPTION	"An index value into the Disks table."
	REFERENCE "'DMTF|Disks Mapping Table|001' 2"
	::= { dmtfDisksMappingEntry 2 }

partitionIndex OBJECT-TYPE
	SYNTAX		DmiInteger
	MAX-ACCESS	read-only
	STATUS		current
	DESCRIPTION	"An index value into the partition table."
	REFERENCE "'DMTF|Disks Mapping Table|001' 3"
	::= { dmtfDisksMappingEntry 3 }

SdmtfDisks ::= SEQUENCE {
	dmtfDisksState INTEGER,
	storageType	DmiInteger,
	diskIndex	DmiInteger,
	storageInterfaceType	DmiInteger,
	interfaceDescription	DmiString,
	mediaLoaded	DmiInteger,
	removableDrive	DmiInteger,
	removableMedia	DmiInteger,
	deviceID	DmiInteger,
	logicalUnitNumber	DmiInteger,
	numberOfPhysicalCylinders	DmiInteger,
	numberOfPhysicalSectorsPerTrack	DmiInteger,
	numberOfPhysicalHeads	DmiInteger,
	physicalCylinderForWritePrecompensation	DmiInteger,
	physicalCylinderForLandingZone	DmiInteger,
	sectorSize	DmiInteger,
	totalPhysicalSize	DmiInteger,
	numberOfCurrentBadBlocksOrSectors	DmiInteger,
	partitions	DmiInteger,
	physicalLocation	DmiInteger,
	fRUGroupIndex	DmiInteger,
	operationalGroupIndex	DmiInteger,
	securitySettings	DmiInteger
}

dmtfDisksTable OBJECT-TYPE
	SYNTAX		SEQUENCE OF SdmtfDisks
	MAX-ACCESS	not-accessible
	STATUS		current
	DESCRIPTION	"This group defines the physical attributes of disk mass storage
devices inthis system."
	::= { dmtfSystemsMIF 22 }

dmtfDisksEntry OBJECT-TYPE
	SYNTAX		SdmtfDisks
	MAX-ACCESS	not-accessible
	STATUS		current
	DESCRIPTION	"This group defines the physical attributes of disk mass storage
devices inthis system."
	INDEX		{ DmiCompId,DmiGroupId, storageType, diskIndex }
	::= { dmtfDisksTable 1 }


dmtfDisksState OBJECT-TYPE
	SYNTAX		INTEGER {
		active(1),
		notInService(2),
		notReady(3),
		createAndGo(4),
		createAndWait(5),
		destroy(6)
	}
	MAX-ACCESS	read-write
	STATUS		current
	REFERENCE "'DMTF|Disks|002' 0"
	::= { dmtfDisksEntry 0 }

storageType OBJECT-TYPE
	SYNTAX		INTEGER {
		other(1),
		unknown(2),
		hardDisk(3),
		floppyDisk(4),
		opticalROM(5),
		opticalWORM(6),
		opticalRW(7),
		compactDisk(8),
		flashDisk(9),
		bernoulli(10),
		opticalFloppyDisk(11)
	}
	MAX-ACCESS	read-only
	STATUS		current
	DESCRIPTION	"The type of this mass storage device."
	REFERENCE "'DMTF|Disks|002' 1"
	::= { dmtfDisksEntry 1 }

diskIndex OBJECT-TYPE
	SYNTAX		DmiInteger
	MAX-ACCESS	read-only
	STATUS		current
	DESCRIPTION	"An index into the disk table."
	REFERENCE "'DMTF|Disks|002' 2"
	::= { dmtfDisksEntry 2 }

storageInterfaceType OBJECT-TYPE
	SYNTAX		INTEGER {
		other(1),
		unknown(2),
		sCSI(3),
		eSDI(4),
		iDE(5),
		cMD(6),
		iPI(7),
		sT506(8),
		dSSI(9),
		parallelPort(10),
		hIPPI(11),
		qIC2(12),
		floppyDiskInterface(13),
		pCMCIA(14),
		enhancedATAIDE(15)
	}
	MAX-ACCESS	read-only
	STATUS		current
	DESCRIPTION	"The interface used by this mass storage device."
	REFERENCE "'DMTF|Disks|002' 3"
	::= { dmtfDisksEntry 3 }

interfaceDescription OBJECT-TYPE
	SYNTAX		DmiString
	MAX-ACCESS	read-only
	STATUS		current
	DESCRIPTION	"A longer description of the mass storage interface.  For
example, SCSI2 fast wide."
	REFERENCE "'DMTF|Disks|002' 4"
	::= { dmtfDisksEntry 4 }

mediaLoaded OBJECT-TYPE
	SYNTAX		INTEGER {
		false(0),
		true(1)
	}
	MAX-ACCESS	read-only
	STATUS		current
	DESCRIPTION	"If true, the media is loaded."
	REFERENCE "'DMTF|Disks|002' 5"
	::= { dmtfDisksEntry 5 }

removableDrive OBJECT-TYPE
	SYNTAX		INTEGER {
		false(0),
		true(1)
	}
	MAX-ACCESS	read-only
	STATUS		current
	DESCRIPTION	"If true, this drive is removable."
	REFERENCE "'DMTF|Disks|002' 6"
	::= { dmtfDisksEntry 6 }

removableMedia OBJECT-TYPE
	SYNTAX		INTEGER {
		false(0),
		true(1)
	}
	MAX-ACCESS	read-only
	STATUS		current
	DESCRIPTION	"If true, the media in this drive is removable."
	REFERENCE "'DMTF|Disks|002' 7"
	::= { dmtfDisksEntry 7 }

deviceID OBJECT-TYPE
	SYNTAX		DmiInteger
	MAX-ACCESS	read-only
	STATUS		current
	DESCRIPTION	"The SCSI address of this device."
	REFERENCE "'DMTF|Disks|002' 8"
	::= { dmtfDisksEntry 8 }

logicalUnitNumber OBJECT-TYPE
	SYNTAX		DmiInteger
	MAX-ACCESS	read-only
	STATUS		current
	DESCRIPTION	"The logical unit number of this SCSI device."
	REFERENCE "'DMTF|Disks|002' 9"
	::= { dmtfDisksEntry 9 }

numberOfPhysicalCylinders OBJECT-TYPE
	SYNTAX		DmiInteger
	MAX-ACCESS	read-only
	STATUS		current
	DESCRIPTION	"The number of reported physical cylinders on this device."
	REFERENCE "'DMTF|Disks|002' 10"
	::= { dmtfDisksEntry 10 }

numberOfPhysicalSectorsPerTrack OBJECT-TYPE
	SYNTAX		DmiInteger
	MAX-ACCESS	read-only
	STATUS		current
	DESCRIPTION	"The number of reported physical sectors per track for this
device."
	REFERENCE "'DMTF|Disks|002' 11"
	::= { dmtfDisksEntry 11 }

numberOfPhysicalHeads OBJECT-TYPE
	SYNTAX		DmiInteger
	MAX-ACCESS	read-only
	STATUS		current
	DESCRIPTION	"The number of reported physical heads for this device."
	REFERENCE "'DMTF|Disks|002' 12"
	::= { dmtfDisksEntry 12 }

physicalCylinderForWritePrecompensation OBJECT-TYPE
	SYNTAX		DmiInteger
	MAX-ACCESS	read-only
	STATUS		current
	DESCRIPTION	"Specifies the physical cylinder used for write precompensation
on this device."
	REFERENCE "'DMTF|Disks|002' 13"
	::= { dmtfDisksEntry 13 }

physicalCylinderForLandingZone OBJECT-TYPE
	SYNTAX		DmiInteger
	MAX-ACCESS	read-only
	STATUS		current
	DESCRIPTION	"The physical landing zone cylinder of this device."
	REFERENCE "'DMTF|Disks|002' 14"
	::= { dmtfDisksEntry 14 }

sectorSize OBJECT-TYPE
	SYNTAX		DmiInteger
	MAX-ACCESS	read-only
	STATUS		current
	DESCRIPTION	"The size in bytes of the physical disk sector or logical
block as reported by the disk."
	REFERENCE "'DMTF|Disks|002' 15"
	::= { dmtfDisksEntry 15 }

totalPhysicalSize OBJECT-TYPE
	SYNTAX		DmiInteger
	MAX-ACCESS	read-only
	STATUS		current
	DESCRIPTION	"The total size in kilobytes (1024 bytes) of this device that
is available to users"
	REFERENCE "'DMTF|Disks|002' 16"
	::= { dmtfDisksEntry 16 }

numberOfCurrentBadBlocksOrSectors OBJECT-TYPE
	SYNTAX		DmiInteger
	MAX-ACCESS	read-only
	STATUS		current
	DESCRIPTION	"The number of current bad blocks or sectors to include total
of both factory assigned and grown defects."
	REFERENCE "'DMTF|Disks|002' 17"
	::= { dmtfDisksEntry 17 }

partitions OBJECT-TYPE
	SYNTAX		DmiInteger
	MAX-ACCESS	read-only
	STATUS		current
	DESCRIPTION	"The number of partitions on this storage unit."
	REFERENCE "'DMTF|Disks|002' 18"
	::= { dmtfDisksEntry 18 }

physicalLocation OBJECT-TYPE
	SYNTAX		INTEGER {
		other(1),
		unknown(2),
		internal(3),
		external(4)
	}
	MAX-ACCESS	read-only
	STATUS		current
	DESCRIPTION	"The physical location of this disk drive assembly relative
to the system enclosure."
	REFERENCE "'DMTF|Disks|002' 19"
	::= { dmtfDisksEntry 19 }

fRUGroupIndex OBJECT-TYPE
	SYNTAX		DmiInteger
	MAX-ACCESS	read-only
	STATUS		current
	DESCRIPTION	"If this is a Field Replaceable Unit or if it is part of another
FRU, this provides an index into the FRU table; 'value = -1' indicates that
the group is not a FRU."
	REFERENCE "'DMTF|Disks|002' 20"
	::= { dmtfDisksEntry 20 }

operationalGroupIndex OBJECT-TYPE
	SYNTAX		DmiInteger
	MAX-ACCESS	read-only
	STATUS		current
	DESCRIPTION	"The index into the Operational State table for this device."
	REFERENCE "'DMTF|Disks|002' 21"
	::= { dmtfDisksEntry 21 }

securitySettings OBJECT-TYPE
	SYNTAX		INTEGER {
		other(1),
		unknown(2),
		none(3),
		readOnly(4),
		lockoutEnabled(5),
		bootBypass(6),
		bootBypassReadOnly(7)
	}
	MAX-ACCESS	read-only
	STATUS		current
	DESCRIPTION	"Enum describing the current hardware security settings on
this device"
	REFERENCE "'DMTF|Disks|002' 22"
	::= { dmtfDisksEntry 22 }

SdmtfElectricalCurrentProbe ::= SEQUENCE {
	dmtfElectricalCurrentProbeState INTEGER,
	electricalCurrentProbeTableIndex	DmiInteger,
	electricalCurrentProbeLocation	DmiInteger,
	electricalCurrentProbeDescription	DmiString,
	electricalCurrentStatus	DmiInteger,
	electricalCurrentProbeReading	DmiInteger,
	monitoredElectricalCurrentNominalReading	DmiInteger,
	monitoredElectricalCurrentNormalMaximum	DmiInteger,
	monitoredElectricalCurrentNormalMinimum	DmiInteger,
	electricalCurrentProbeMaximum	DmiInteger,
	electricalCurrentProbeMinimum	DmiInteger,
	electricalCurrentReadingLowerThresholdNonCritical	DmiInteger,
	electricalCurrentReadingUpperThresholdNonCritical	DmiInteger,
	electricalCurrentReadingLowerThresholdCritical	DmiInteger,
	currentReadingUpperThresholdCritical	DmiInteger,
	electricalCurrentReadingLowerThresholdNonRecoverab	DmiInteger,
	electricalCurrentReadingUpperThresholdNonRecoverab	DmiInteger,
	electricalCurrentProbeResolution	DmiInteger,
	electricalCurrentProbeTolerance	DmiInteger,
	electricalCurrentProbeAccuracy	DmiInteger,
	fRUGroupIndex-1	DmiInteger,
	operationalGroupIndex-1	DmiInteger
}

dmtfElectricalCurrentProbeTable OBJECT-TYPE
	SYNTAX		SEQUENCE OF SdmtfElectricalCurrentProbe
	MAX-ACCESS	not-accessible
	STATUS		current
	DESCRIPTION	"This group defines the attributes for the current probes
in this system."
	::= { dmtfSystemsMIF 55 }

dmtfElectricalCurrentProbeEntry OBJECT-TYPE
	SYNTAX		SdmtfElectricalCurrentProbe
	MAX-ACCESS	not-accessible
	STATUS		current
	DESCRIPTION	"This group defines the attributes for the current probes
in this system."
	INDEX		{ DmiCompId,DmiGroupId, electricalCurrentProbeTableIndex }
	::= { dmtfElectricalCurrentProbeTable 1 }


dmtfElectricalCurrentProbeState OBJECT-TYPE
	SYNTAX		INTEGER {
		active(1),
		notInService(2),
		notReady(3),
		createAndGo(4),
		createAndWait(5),
		destroy(6)
	}
	MAX-ACCESS	read-write
	STATUS		current
	REFERENCE "'DMTF|Electrical Current Probe|001' 0"
	::= { dmtfElectricalCurrentProbeEntry 0 }

electricalCurrentProbeTableIndex OBJECT-TYPE
	SYNTAX		DmiInteger
	MAX-ACCESS	read-only
	STATUS		current
	DESCRIPTION	"Index into this electrical current probe table."
	REFERENCE "'DMTF|Electrical Current Probe|001' 1"
	::= { dmtfElectricalCurrentProbeEntry 1 }

electricalCurrentProbeLocation OBJECT-TYPE
	SYNTAX		INTEGER {
		other(1),
		unknown(2),
		processor(3),
		disk(4),
		peripheralBay(5),
		sMBMaster(6),
		motherboard(7),
		memoryModule(8),
		processorModule(9),
		powerUnit(10),
		addInCard(11)
	}
	MAX-ACCESS	read-only
	STATUS		current
	DESCRIPTION	"Identifies the physical location of the electrical current
probe."
	REFERENCE "'DMTF|Electrical Current Probe|001' 2"
	::= { dmtfElectricalCurrentProbeEntry 2 }

electricalCurrentProbeDescription OBJECT-TYPE
	SYNTAX		DmiString
	MAX-ACCESS	read-only
	STATUS		current
	DESCRIPTION	"Additional descriptive information about the electrical current
probe or probe's location."
	REFERENCE "'DMTF|Electrical Current Probe|001' 3"
	::= { dmtfElectricalCurrentProbeEntry 3 }

electricalCurrentStatus OBJECT-TYPE
	SYNTAX		INTEGER {
		other(1),
		unknown(2),
		oK(3),
		nonCritical(4),
		critical(5),
		nonRecoverable(6)
	}
	MAX-ACCESS	read-only
	STATUS		current
	DESCRIPTION	"Defines the status of the electrical current monitored by
this electrical current probe."
	REFERENCE "'DMTF|Electrical Current Probe|001' 4"
	::= { dmtfElectricalCurrentProbeEntry 4 }

electricalCurrentProbeReading OBJECT-TYPE
	SYNTAX		DmiInteger
	MAX-ACCESS	read-only
	STATUS		current
	DESCRIPTION	"The present electrical current reading of this probe in milliamp
. 0x8000000 denotes 'unknown'."
	REFERENCE "'DMTF|Electrical Current Probe|001' 5"
	::= { dmtfElectricalCurrentProbeEntry 5 }

monitoredElectricalCurrentNominalReading OBJECT-TYPE
	SYNTAX		DmiInteger
	MAX-ACCESS	read-only
	STATUS		current
	DESCRIPTION	"The nominal electrical current reading of the current monitored
by this probe in milliamps. 0x80000000 denotes 'unknown'."
	REFERENCE "'DMTF|Electrical Current Probe|001' 6"
	::= { dmtfElectricalCurrentProbeEntry 6 }

monitoredElectricalCurrentNormalMaximum OBJECT-TYPE
	SYNTAX		DmiInteger
	MAX-ACCESS	read-only
	STATUS		current
	DESCRIPTION	"The normal maximum electrical current reading of the current
monitored by this probe in milliamps. 0x80000000 denotes 'unknown'."
	REFERENCE "'DMTF|Electrical Current Probe|001' 7"
	::= { dmtfElectricalCurrentProbeEntry 7 }

monitoredElectricalCurrentNormalMinimum OBJECT-TYPE
	SYNTAX		DmiInteger
	MAX-ACCESS	read-only
	STATUS		current
	DESCRIPTION	"The normal minimum electrical current reading of the current
monitored by this probe in milliamps. 0x80000000 denotes 'unknown'."
	REFERENCE "'DMTF|Electrical Current Probe|001' 8"
	::= { dmtfElectricalCurrentProbeEntry 8 }

electricalCurrentProbeMaximum OBJECT-TYPE
	SYNTAX		DmiInteger
	MAX-ACCESS	read-only
	STATUS		current
	DESCRIPTION	"The maximum electrical current reading specified to be readable
by this probe in milliamps. 0x80000000 denotes 'unknown'."
	REFERENCE "'DMTF|Electrical Current Probe|001' 9"
	::= { dmtfElectricalCurrentProbeEntry 9 }

electricalCurrentProbeMinimum OBJECT-TYPE
	SYNTAX		DmiInteger
	MAX-ACCESS	read-only
	STATUS		current
	DESCRIPTION	"The minimum electrical current reading specified to be readable
by this probe in milliamps. 0x80000000 denotes 'unknown'."
	REFERENCE "'DMTF|Electrical Current Probe|001' 10"
	::= { dmtfElectricalCurrentProbeEntry 10 }

electricalCurrentReadingLowerThresholdNonCritical OBJECT-TYPE
	SYNTAX		DmiInteger
	MAX-ACCESS	read-write
	STATUS		current
	DESCRIPTION	"The lower non-critical threshold for the electrical current
reading set by the user, in milliamps. 0x80000000 denotes 'unknown'."
	REFERENCE "'DMTF|Electrical Current Probe|001' 11"
	::= { dmtfElectricalCurrentProbeEntry 11 }

electricalCurrentReadingUpperThresholdNonCritical OBJECT-TYPE
	SYNTAX		DmiInteger
	MAX-ACCESS	read-write
	STATUS		current
	DESCRIPTION	"The upper non-critical threshold for the electrical current
reading, in milliamps. 0x80000000 denotes 'unknown'."
	REFERENCE "'DMTF|Electrical Current Probe|001' 12"
	::= { dmtfElectricalCurrentProbeEntry 12 }

electricalCurrentReadingLowerThresholdCritical OBJECT-TYPE
	SYNTAX		DmiInteger
	MAX-ACCESS	read-write
	STATUS		current
	DESCRIPTION	"The lower critical threshold for the electrical current probe,
in milliamps. 0x80000000 denotes 'unknown'."
	REFERENCE "'DMTF|Electrical Current Probe|001' 13"
	::= { dmtfElectricalCurrentProbeEntry 13 }

currentReadingUpperThresholdCritical OBJECT-TYPE
	SYNTAX		DmiInteger
	MAX-ACCESS	read-write
	STATUS		current
	DESCRIPTION	"The upper critical threshold for the electrical current probe,
in milliamps. 0x80000000 denotes 'unknown'."
	REFERENCE "'DMTF|Electrical Current Probe|001' 14"
	::= { dmtfElectricalCurrentProbeEntry 14 }

electricalCurrentReadingLowerThresholdNonRecoverab OBJECT-TYPE
	SYNTAX		DmiInteger
	MAX-ACCESS	read-write
	STATUS		current
	DESCRIPTION	"The lower non-recoverable threshold for the electrical current
probe, in milliamps. 0x80000000 denotes 'unknown'."
	REFERENCE "'DMTF|Electrical Current Probe|001' 15"
	::= { dmtfElectricalCurrentProbeEntry 15 }

electricalCurrentReadingUpperThresholdNonRecoverab OBJECT-TYPE
	SYNTAX		DmiInteger
	MAX-ACCESS	read-write
	STATUS		current
	DESCRIPTION	"The upper non-recoverable threshold for the electrical current
probe, in milliamps. 0x80000000 denotes 'unknown'."
	REFERENCE "'DMTF|Electrical Current Probe|001' 16"
	::= { dmtfElectricalCurrentProbeEntry 16 }

electricalCurrentProbeResolution OBJECT-TYPE
	SYNTAX		DmiInteger
	MAX-ACCESS	read-write
	STATUS		current
	DESCRIPTION	"The resolution for the reading from this electrical current
probe, in tenths of milliamps. '0x80000000 denotes 'unknown'."
	REFERENCE "'DMTF|Electrical Current Probe|001' 17"
	::= { dmtfElectricalCurrentProbeEntry 17 }

electricalCurrentProbeTolerance OBJECT-TYPE
	SYNTAX		DmiInteger
	MAX-ACCESS	read-write
	STATUS		current
	DESCRIPTION	"The tolerance for the reading from this electrical current
probe, in plus/minus milliamps. 0x80000000 denotes 'unknown'."
	REFERENCE "'DMTF|Electrical Current Probe|001' 18"
	::= { dmtfElectricalCurrentProbeEntry 18 }

electricalCurrentProbeAccuracy OBJECT-TYPE
	SYNTAX		DmiInteger
	MAX-ACCESS	read-write
	STATUS		current
	DESCRIPTION	"The accuracy for the reading from this electrical current
probe, in plus/minus hundredths of a percent. 0x80000000 denotes 'unknown'."
	REFERENCE "'DMTF|Electrical Current Probe|001' 19"
	::= { dmtfElectricalCurrentProbeEntry 19 }

fRUGroupIndex OBJECT-TYPE
	SYNTAX		DmiInteger
	MAX-ACCESS	read-only
	STATUS		current
	DESCRIPTION	"Index into the FRU table"
	REFERENCE "'DMTF|Electrical Current Probe|001' 20"
	::= { dmtfElectricalCurrentProbeEntry 20 }

operationalGroupIndex OBJECT-TYPE
	SYNTAX		DmiInteger
	MAX-ACCESS	read-only
	STATUS		current
	DESCRIPTION	"Index into the Operational State table"
	REFERENCE "'DMTF|Electrical Current Probe|001' 21"
	::= { dmtfElectricalCurrentProbeEntry 21 }

SdmtfFRU ::= SEQUENCE {
	dmtfFRUState INTEGER,
	fRUIndex	DmiInteger,
	deviceGroupIndex	DmiInteger,
	description	DmiString,
	manufacturer	DmiString,
	model	DmiString,
	partNumber	DmiString,
	fRUSerialNumber	DmiString,
	revisionLevel	DmiString,
	warrantyStartDate	Dmi-Date,
	warrantyDuration	DmiInteger,
	supportPhoneNumber	DmiString
}

dmtfFRUTable OBJECT-TYPE
	SYNTAX		SEQUENCE OF SdmtfFRU
	MAX-ACCESS	not-accessible
	STATUS		current
	DESCRIPTION	"A Field Replaceable Unit (FRU), is defined as a hardware
component which is designed to be separately removable for replacement or
repair. For the purposes of this definition, a motherboard and a fixed hard
disk are FRUs, whereas a fixed hard disk platter or a chip fixed in place
on the motherboard are not FRUs since they are not designed to be separately
removable. Each instance within the FRU table should contain the device group
and instance data for the associated hardware component."
	::= { dmtfSystemsMIF 29 }

dmtfFRUEntry OBJECT-TYPE
	SYNTAX		SdmtfFRU
	MAX-ACCESS	not-accessible
	STATUS		current
	DESCRIPTION	"A Field Replaceable Unit (FRU), is defined as a hardware
component which is designed to be separately removable for replacement or
repair. For the purposes of this definition, a motherboard and a fixed hard
disk are FRUs, whereas a fixed hard disk platter or a chip fixed in place
on the motherboard are not FRUs since they are not designed to be separately
removable. Each instance within the FRU table should contain the device group
and instance data for the associated hardware component."
	INDEX		{ DmiCompId,DmiGroupId, fRUIndex }
	::= { dmtfFRUTable 1 }


dmtfFRUState OBJECT-TYPE
	SYNTAX		INTEGER {
		active(1),
		notInService(2),
		notReady(3),
		createAndGo(4),
		createAndWait(5),
		destroy(6)
	}
	MAX-ACCESS	read-write
	STATUS		current
	REFERENCE "'DMTF|FRU|001' 0"
	::= { dmtfFRUEntry 0 }

fRUIndex OBJECT-TYPE
	SYNTAX		DmiInteger
	MAX-ACCESS	read-only
	STATUS		current
	DESCRIPTION	"The index into the Field Replaceable Unit table."
	REFERENCE "'DMTF|FRU|001' 1"
	::= { dmtfFRUEntry 1 }

deviceGroupIndex OBJECT-TYPE
	SYNTAX		DmiInteger
	MAX-ACCESS	read-only
	STATUS		current
	DESCRIPTION	"The group ID of the group referencing this Field Replaceable
Unit instance."
	REFERENCE "'DMTF|FRU|001' 2"
	::= { dmtfFRUEntry 2 }

description OBJECT-TYPE
	SYNTAX		DmiString
	MAX-ACCESS	read-only
	STATUS		current
	DESCRIPTION	"A clear description of this Field Replaceable Unit."
	REFERENCE "'DMTF|FRU|001' 3"
	::= { dmtfFRUEntry 3 }

manufacturer OBJECT-TYPE
	SYNTAX		DmiString
	MAX-ACCESS	read-only
	STATUS		current
	DESCRIPTION	"The name of the company manufacturing or providing this Field
Replaceable Unit."
	REFERENCE "'DMTF|FRU|001' 4"
	::= { dmtfFRUEntry 4 }

model OBJECT-TYPE
	SYNTAX		DmiString
	MAX-ACCESS	read-only
	STATUS		current
	DESCRIPTION	"The manufacturer's model number for this Field Replaceable
Unit."
	REFERENCE "'DMTF|FRU|001' 5"
	::= { dmtfFRUEntry 5 }

partNumber OBJECT-TYPE
	SYNTAX		DmiString
	MAX-ACCESS	read-only
	STATUS		current
	DESCRIPTION	"A part number by which a replacement part can be ordered
for this Field Replaceable Unit."
	REFERENCE "'DMTF|FRU|001' 6"
	::= { dmtfFRUEntry 6 }

fRUSerialNumber OBJECT-TYPE
	SYNTAX		DmiString
	MAX-ACCESS	read-only
	STATUS		current
	DESCRIPTION	"The manufacturer's serial number for this Field Replaceable
Unit."
	REFERENCE "'DMTF|FRU|001' 7"
	::= { dmtfFRUEntry 7 }

revisionLevel OBJECT-TYPE
	SYNTAX		DmiString
	MAX-ACCESS	read-only
	STATUS		current
	DESCRIPTION	"The revision level of this Field Replaceable Unit."
	REFERENCE "'DMTF|FRU|001' 8"
	::= { dmtfFRUEntry 8 }

warrantyStartDate OBJECT-TYPE
	SYNTAX		Dmi-Date
	MAX-ACCESS	read-only
	STATUS		current
	DESCRIPTION	"The start date of the service warranty for this Field Replaceabl
 Unit."
	REFERENCE "'DMTF|FRU|001' 9"
	::= { dmtfFRUEntry 9 }

warrantyDuration OBJECT-TYPE
	SYNTAX		DmiInteger
	MAX-ACCESS	read-only
	STATUS		current
	DESCRIPTION	"The total duration of this Field Replaceable Unit warranty
in months."
	REFERENCE "'DMTF|FRU|001' 10"
	::= { dmtfFRUEntry 10 }

supportPhoneNumber OBJECT-TYPE
	SYNTAX		DmiString
	MAX-ACCESS	read-only
	STATUS		current
	DESCRIPTION	"The phone number(s) for support for this Field Replaceable
Unit."
	REFERENCE "'DMTF|FRU|001' 11"
	::= { dmtfFRUEntry 11 }

SdmtfGeneralInformation ::= SEQUENCE {
	systemName	DmiString,
	systemLocation	DmiString,
	systemPrimaryUserName	DmiString,
	systemPrimaryUserPhone	DmiString,
	systemBootupTime	Dmi-Date,
	systemDateTime	Dmi-Date
}

dmtfGeneralInformationTable OBJECT-TYPE
	SYNTAX		SEQUENCE OF SdmtfGeneralInformation
	MAX-ACCESS	not-accessible
	STATUS		current
	DESCRIPTION	"This group defines general information about this system."
	::= { dmtfSystemsMIF 1 }

dmtfGeneralInformationEntry OBJECT-TYPE
	SYNTAX		SdmtfGeneralInformation
	MAX-ACCESS	not-accessible
	STATUS		current
	DESCRIPTION	"This group defines general information about this system."
	INDEX		{ DmiCompId,DmiGroupId }
	::= { dmtfGeneralInformationTable 1 }


systemName OBJECT-TYPE
	SYNTAX		DmiString
	MAX-ACCESS	read-write
	STATUS		current
	DESCRIPTION	"A name to identify this system."
	REFERENCE "'DMTF|General Information|001' 1"
	::= { dmtfGeneralInformationEntry 1 }

systemLocation OBJECT-TYPE
	SYNTAX		DmiString
	MAX-ACCESS	read-write
	STATUS		current
	DESCRIPTION	"The physical location of this system."
	REFERENCE "'DMTF|General Information|001' 2"
	::= { dmtfGeneralInformationEntry 2 }

systemPrimaryUserName OBJECT-TYPE
	SYNTAX		DmiString
	MAX-ACCESS	read-write
	STATUS		current
	DESCRIPTION	"The name of the primary user or owner of this system."
	REFERENCE "'DMTF|General Information|001' 3"
	::= { dmtfGeneralInformationEntry 3 }

systemPrimaryUserPhone OBJECT-TYPE
	SYNTAX		DmiString
	MAX-ACCESS	read-write
	STATUS		current
	DESCRIPTION	"The phone number of the primary user of this system."
	REFERENCE "'DMTF|General Information|001' 4"
	::= { dmtfGeneralInformationEntry 4 }

systemBootupTime OBJECT-TYPE
	SYNTAX		Dmi-Date
	MAX-ACCESS	read-only
	STATUS		current
	DESCRIPTION	"The time at which the system was last booted."
	REFERENCE "'DMTF|General Information|001' 5"
	::= { dmtfGeneralInformationEntry 5 }

systemDateTime OBJECT-TYPE
	SYNTAX		Dmi-Date
	MAX-ACCESS	read-write
	STATUS		current
	DESCRIPTION	"The actual system date and time."
	REFERENCE "'DMTF|General Information|001' 6"
	::= { dmtfGeneralInformationEntry 6 }

SdmtfIRQ ::= SEQUENCE {
	dmtfIRQState INTEGER,
	iRQNumber	DmiInteger,
	iRQAvailability	DmiInteger,
	iRQTriggerType	DmiInteger,
	iRQShareable	DmiInteger,
	iRQDescription	DmiString
}

dmtfIRQTable OBJECT-TYPE
	SYNTAX		SEQUENCE OF SdmtfIRQ
	MAX-ACCESS	not-accessible
	STATUS		current
	DESCRIPTION	"This group defines attributes for IRQs in this system."
	::= { dmtfSystemsMIF 12 }

dmtfIRQEntry OBJECT-TYPE
	SYNTAX		SdmtfIRQ
	MAX-ACCESS	not-accessible
	STATUS		current
	DESCRIPTION	"This group defines attributes for IRQs in this system."
	INDEX		{ DmiCompId,DmiGroupId, iRQNumber }
	::= { dmtfIRQTable 1 }


dmtfIRQState OBJECT-TYPE
	SYNTAX		INTEGER {
		active(1),
		notInService(2),
		notReady(3),
		createAndGo(4),
		createAndWait(5),
		destroy(6)
	}
	MAX-ACCESS	read-write
	STATUS		current
	REFERENCE "'DMTF|IRQ|001' 0"
	::= { dmtfIRQEntry 0 }

iRQNumber OBJECT-TYPE
	SYNTAX		DmiInteger
	MAX-ACCESS	read-only
	STATUS		current
	DESCRIPTION	"The number of this IRQ."
	REFERENCE "'DMTF|IRQ|001' 1"
	::= { dmtfIRQEntry 1 }

iRQAvailability OBJECT-TYPE
	SYNTAX		INTEGER {
		other(1),
		unknown(2),
		available(3),
		inUse(4)
	}
	MAX-ACCESS	read-only
	STATUS		current
	DESCRIPTION	"Is this IRQ available or in use?"
	REFERENCE "'DMTF|IRQ|001' 2"
	::= { dmtfIRQEntry 2 }

iRQTriggerType OBJECT-TYPE
	SYNTAX		INTEGER {
		other(1),
		unknown(2),
		level(3),
		edge(4)
	}
	MAX-ACCESS	read-only
	STATUS		current
	DESCRIPTION	"The trigger type of the IRQ."
	REFERENCE "'DMTF|IRQ|001' 3"
	::= { dmtfIRQEntry 3 }

iRQShareable OBJECT-TYPE
	SYNTAX		INTEGER {
		false(0),
		true(1)
	}
	MAX-ACCESS	read-only
	STATUS		current
	DESCRIPTION	"If true, this IRQ is shareable."
	REFERENCE "'DMTF|IRQ|001' 4"
	::= { dmtfIRQEntry 4 }

iRQDescription OBJECT-TYPE
	SYNTAX		DmiString
	MAX-ACCESS	read-only
	STATUS		current
	DESCRIPTION	"The name of the logical device that is currently using this
IRQ."
	REFERENCE "'DMTF|IRQ|001' 5"
	::= { dmtfIRQEntry 5 }

SdmtfKeyboard ::= SEQUENCE {
	keyboardLayout	DmiString,
	keyboardType	DmiString,
	keyboardConnectorType	DmiInteger,
	fRUGroupIndex	DmiInteger,
	operationalGroupIndex	DmiInteger,
	securitySettings	DmiInteger
}

dmtfKeyboardTable OBJECT-TYPE
	SYNTAX		SEQUENCE OF SdmtfKeyboard
	MAX-ACCESS	not-accessible
	STATUS		current
	DESCRIPTION	"This group defines the characteristics of the system keyboard."
	::= { dmtfSystemsMIF 28 }

dmtfKeyboardEntry OBJECT-TYPE
	SYNTAX		SdmtfKeyboard
	MAX-ACCESS	not-accessible
	STATUS		current
	DESCRIPTION	"This group defines the characteristics of the system keyboard."
	INDEX		{ DmiCompId,DmiGroupId }
	::= { dmtfKeyboardTable 1 }


keyboardLayout OBJECT-TYPE
	SYNTAX		DmiString
	MAX-ACCESS	read-only
	STATUS		current
	DESCRIPTION	"A description of the layout of this keyboard."
	REFERENCE "'DMTF|Keyboard|003' 1"
	::= { dmtfKeyboardEntry 1 }

keyboardType OBJECT-TYPE
	SYNTAX		DmiString
	MAX-ACCESS	read-only
	STATUS		current
	DESCRIPTION	"The type description of this keyboard."
	REFERENCE "'DMTF|Keyboard|003' 2"
	::= { dmtfKeyboardEntry 2 }

keyboardConnectorType OBJECT-TYPE
	SYNTAX		INTEGER {
		other(1),
		unknown(2),
		miniDin(3),
		microDin(4),
		pS2(5),
		infrared(6),
		hPHIL(7),
		dB9(8),
		accessBus(9),
		pC98(160)
	}
	MAX-ACCESS	read-only
	STATUS		current
	DESCRIPTION	"The type of keyboard connector used by this keyboard."
	REFERENCE "'DMTF|Keyboard|003' 3"
	::= { dmtfKeyboardEntry 3 }

fRUGroupIndex OBJECT-TYPE
	SYNTAX		DmiInteger
	MAX-ACCESS	read-only
	STATUS		current
	DESCRIPTION	"If this is a Field Replaceable Unit or if it is part of another
FRU, this provides an index into the FRU table; 'value = -1' indicates that
the group is not a FRU."
	REFERENCE "'DMTF|Keyboard|003' 4"
	::= { dmtfKeyboardEntry 4 }

operationalGroupIndex OBJECT-TYPE
	SYNTAX		DmiInteger
	MAX-ACCESS	read-only
	STATUS		current
	DESCRIPTION	"The index into the Operational State table for this device."
	REFERENCE "'DMTF|Keyboard|003' 5"
	::= { dmtfKeyboardEntry 5 }

securitySettings OBJECT-TYPE
	SYNTAX		INTEGER {
		other(1),
		unknown(2),
		none(3),
		externalInterfaceLockedOut(4),
		externalInterfaceEnabled(5)
	}
	MAX-ACCESS	read-only
	STATUS		current
	DESCRIPTION	"Enum describing the current hardware security settings on
this device"
	REFERENCE "'DMTF|Keyboard|003' 6"
	::= { dmtfKeyboardEntry 6 }

SdmtfLogicalDrives ::= SEQUENCE {
	dmtfLogicalDrivesState INTEGER,
	logicalDriveIndex	DmiInteger,
	logicalDriveName	DmiString,
	logicalDriveType	DmiInteger,
	logicalDriveSize	DmiInteger,
	freeLogicalDriveSize	DmiInteger,
	logicalDrivePath	DmiString
}

dmtfLogicalDrivesTable OBJECT-TYPE
	SYNTAX		SEQUENCE OF SdmtfLogicalDrives
	MAX-ACCESS	not-accessible
	STATUS		current
	DESCRIPTION	"This group defines the attributes of the logical drives in
a system."
	::= { dmtfSystemsMIF 26 }

dmtfLogicalDrivesEntry OBJECT-TYPE
	SYNTAX		SdmtfLogicalDrives
	MAX-ACCESS	not-accessible
	STATUS		current
	DESCRIPTION	"This group defines the attributes of the logical drives in
a system."
	INDEX		{ DmiCompId,DmiGroupId, logicalDriveIndex }
	::= { dmtfLogicalDrivesTable 1 }


dmtfLogicalDrivesState OBJECT-TYPE
	SYNTAX		INTEGER {
		active(1),
		notInService(2),
		notReady(3),
		createAndGo(4),
		createAndWait(5),
		destroy(6)
	}
	MAX-ACCESS	read-write
	STATUS		current
	REFERENCE "'DMTF|Logical Drives|001' 0"
	::= { dmtfLogicalDrivesEntry 0 }

logicalDriveIndex OBJECT-TYPE
	SYNTAX		DmiInteger
	MAX-ACCESS	read-only
	STATUS		current
	DESCRIPTION	"An index into the Logical Drive table."
	REFERENCE "'DMTF|Logical Drives|001' 1"
	::= { dmtfLogicalDrivesEntry 1 }

logicalDriveName OBJECT-TYPE
	SYNTAX		DmiString
	MAX-ACCESS	read-only
	STATUS		current
	DESCRIPTION	"Name used by the system to identify this logical drive. For
DOS, this could be the logical drive letter (A, B, C...)."
	REFERENCE "'DMTF|Logical Drives|001' 2"
	::= { dmtfLogicalDrivesEntry 2 }

logicalDriveType OBJECT-TYPE
	SYNTAX		INTEGER {
		other(1),
		unknown(2),
		fixedDrive(3),
		removableDrive(4),
		remoteDrive(5),
		cDROM(6),
		floppyDrive(7),
		rAMDrive(8),
		driveArray(9)
	}
	MAX-ACCESS	read-only
	STATUS		current
	DESCRIPTION	"This defines the logical drive type."
	REFERENCE "'DMTF|Logical Drives|001' 3"
	::= { dmtfLogicalDrivesEntry 3 }

logicalDriveSize OBJECT-TYPE
	SYNTAX		DmiInteger
	MAX-ACCESS	read-only
	STATUS		current
	DESCRIPTION	"The size of this logical drive in kilobytes."
	REFERENCE "'DMTF|Logical Drives|001' 4"
	::= { dmtfLogicalDrivesEntry 4 }

freeLogicalDriveSize OBJECT-TYPE
	SYNTAX		DmiInteger
	MAX-ACCESS	read-only
	STATUS		current
	DESCRIPTION	"The remaining space on this logical drive in kilobytes."
	REFERENCE "'DMTF|Logical Drives|001' 5"
	::= { dmtfLogicalDrivesEntry 5 }

logicalDrivePath OBJECT-TYPE
	SYNTAX		DmiString
	MAX-ACCESS	read-only
	STATUS		current
	DESCRIPTION	"The path used to access this logical drive (for remote drives)."
	REFERENCE "'DMTF|Logical Drives|001' 6"
	::= { dmtfLogicalDrivesEntry 6 }

SdmtfLogicalMemory ::= SEQUENCE {
	baseMemorySize	DmiInteger,
	freeBaseMemorySize	DmiInteger,
	extendedMemorySize	DmiInteger,
	freeExtendedMemorySize	DmiInteger,
	extendedMemoryManagerName	DmiString,
	extendedMemoryManagerVersion	DmiString,
	expandedMemorySize	DmiInteger,
	freeExpandedMemorySize	DmiInteger,
	expandedMemoryManagerName	DmiString,
	expandedMemoryManagerVersion	DmiString,
	expandedMemoryPageFrameAddress	Dmi-Integer64,
	expandedMemoryPageFrameSize	DmiInteger,
	expandedMemoryPageSize	DmiInteger
}

dmtfLogicalMemoryTable OBJECT-TYPE
	SYNTAX		SEQUENCE OF SdmtfLogicalMemory
	MAX-ACCESS	not-accessible
	STATUS		current
	DESCRIPTION	"This group defines the logical memory attributes for system
memory and any add-on memory installed in this system."
	::= { dmtfSystemsMIF 8 }

dmtfLogicalMemoryEntry OBJECT-TYPE
	SYNTAX		SdmtfLogicalMemory
	MAX-ACCESS	not-accessible
	STATUS		current
	DESCRIPTION	"This group defines the logical memory attributes for system
memory and any add-on memory installed in this system."
	INDEX		{ DmiCompId,DmiGroupId }
	::= { dmtfLogicalMemoryTable 1 }


baseMemorySize OBJECT-TYPE
	SYNTAX		DmiInteger
	MAX-ACCESS	read-only
	STATUS		current
	DESCRIPTION	"The total size of the base memory in kilobytes."
	REFERENCE "'DMTF|Logical Memory|001' 1"
	::= { dmtfLogicalMemoryEntry 1 }

freeBaseMemorySize OBJECT-TYPE
	SYNTAX		DmiInteger
	MAX-ACCESS	read-only
	STATUS		current
	DESCRIPTION	"The size of free base memory in kilobytes."
	REFERENCE "'DMTF|Logical Memory|001' 2"
	::= { dmtfLogicalMemoryEntry 2 }

extendedMemorySize OBJECT-TYPE
	SYNTAX		DmiInteger
	MAX-ACCESS	read-only
	STATUS		current
	DESCRIPTION	"The total size of the extended memory in kilobytes."
	REFERENCE "'DMTF|Logical Memory|001' 3"
	::= { dmtfLogicalMemoryEntry 3 }

freeExtendedMemorySize OBJECT-TYPE
	SYNTAX		DmiInteger
	MAX-ACCESS	read-only
	STATUS		current
	DESCRIPTION	"The size of free extended memory in kilobytes."
	REFERENCE "'DMTF|Logical Memory|001' 4"
	::= { dmtfLogicalMemoryEntry 4 }

extendedMemoryManagerName OBJECT-TYPE
	SYNTAX		DmiString
	MAX-ACCESS	read-only
	STATUS		current
	DESCRIPTION	"The name of the extended memory manager."
	REFERENCE "'DMTF|Logical Memory|001' 5"
	::= { dmtfLogicalMemoryEntry 5 }

extendedMemoryManagerVersion OBJECT-TYPE
	SYNTAX		DmiString
	MAX-ACCESS	read-only
	STATUS		current
	DESCRIPTION	"The version information of the extended memory manager."
	REFERENCE "'DMTF|Logical Memory|001' 6"
	::= { dmtfLogicalMemoryEntry 6 }

expandedMemorySize OBJECT-TYPE
	SYNTAX		DmiInteger
	MAX-ACCESS	read-only
	STATUS		current
	DESCRIPTION	"The total size of the expanded memory in kilobytes."
	REFERENCE "'DMTF|Logical Memory|001' 7"
	::= { dmtfLogicalMemoryEntry 7 }

freeExpandedMemorySize OBJECT-TYPE
	SYNTAX		DmiInteger
	MAX-ACCESS	read-only
	STATUS		current
	DESCRIPTION	"The size of free expanded memory in kilobytes."
	REFERENCE "'DMTF|Logical Memory|001' 8"
	::= { dmtfLogicalMemoryEntry 8 }

expandedMemoryManagerName OBJECT-TYPE
	SYNTAX		DmiString
	MAX-ACCESS	read-only
	STATUS		current
	DESCRIPTION	"The name of the expanded memory manager."
	REFERENCE "'DMTF|Logical Memory|001' 9"
	::= { dmtfLogicalMemoryEntry 9 }

expandedMemoryManagerVersion OBJECT-TYPE
	SYNTAX		DmiString
	MAX-ACCESS	read-only
	STATUS		current
	DESCRIPTION	"The version information of the expanded memory manager."
	REFERENCE "'DMTF|Logical Memory|001' 10"
	::= { dmtfLogicalMemoryEntry 10 }

expandedMemoryPageFrameAddress OBJECT-TYPE
	SYNTAX		Dmi-Integer64
	MAX-ACCESS	read-only
	STATUS		current
	DESCRIPTION	"The starting physical address of the expanded memory pageframe."
	REFERENCE "'DMTF|Logical Memory|001' 11"
	::= { dmtfLogicalMemoryEntry 11 }

expandedMemoryPageFrameSize OBJECT-TYPE
	SYNTAX		DmiInteger
	MAX-ACCESS	read-only
	STATUS		current
	DESCRIPTION	"The size in kilobytes of the expanded memory page frame."
	REFERENCE "'DMTF|Logical Memory|001' 12"
	::= { dmtfLogicalMemoryEntry 12 }

expandedMemoryPageSize OBJECT-TYPE
	SYNTAX		DmiInteger
	MAX-ACCESS	read-only
	STATUS		current
	DESCRIPTION	"The size in kilobytes of an expanded memory page, as opposed
to the expanded memory page frame, which consists of a number of memory pages."
	REFERENCE "'DMTF|Logical Memory|001' 13"
	::= { dmtfLogicalMemoryEntry 13 }

SdmtfMassStoreArrayInfoTable ::= SEQUENCE {
	dmtfMassStoreArrayInfoTableState INTEGER,
	logicalDriveIndex	DmiInteger,
	driveArrayLevel	DmiInteger,
	driveArrayRedundancyStatus	DmiInteger,
	driveArrayOperationInProgress	DmiInteger
}

dmtfMassStoreArrayInfoTable OBJECT-TYPE
	SYNTAX		SEQUENCE OF SdmtfMassStoreArrayInfoTable
	MAX-ACCESS	not-accessible
	STATUS		current
	DESCRIPTION	"This table is a parallel table to the Mass Store Logical
Drives Table; it has entries keyed by the same unique index as is used for
the logical drives table. This table has one entry corresponding to each
entry in the Mass Store Logical Drives Table whose 'Drive Array' field is
set to TRUE."
	::= { dmtfSystemsMIF 46 }

dmtfMassStoreArrayInfoEntry OBJECT-TYPE
	SYNTAX		SdmtfMassStoreArrayInfoTable
	MAX-ACCESS	not-accessible
	STATUS		current
	DESCRIPTION	"This table is a parallel table to the Mass Store Logical
Drives Table; it has entries keyed by the same unique index as is used for
the logical drives table. This table has one entry corresponding to each
entry in the Mass Store Logical Drives Table whose 'Drive Array' field is
set to TRUE."
	INDEX		{ DmiCompId,DmiGroupId, logicalDriveIndex }
	::= { dmtfMassStoreArrayInfoTable 1 }


dmtfMassStoreArrayInfoTableState OBJECT-TYPE
	SYNTAX		INTEGER {
		active(1),
		notInService(2),
		notReady(3),
		createAndGo(4),
		createAndWait(5),
		destroy(6)
	}
	MAX-ACCESS	read-write
	STATUS		current
	REFERENCE "'DMTF|Mass Store Array Info Table|001' 0"
	::= { dmtfMassStoreArrayInfoEntry 0 }

logicalDriveIndex OBJECT-TYPE
	SYNTAX		DmiInteger
	MAX-ACCESS	read-only
	STATUS		current
	DESCRIPTION	"This is the same index as the 'Logical Drive Index' field
in the Mass Store Logical Drives Table. "
	REFERENCE "'DMTF|Mass Store Array Info Table|001' 1"
	::= { dmtfMassStoreArrayInfoEntry 1 }

driveArrayLevel OBJECT-TYPE
	SYNTAX		INTEGER {
		other(1),
		unknown(2),
		rAID0(3),
		rAID1(4),
		rAID2(5),
		rAID3(6),
		rAID4(7),
		rAID5(8),
		rAID7(9),
		rAID10(10)
	}
	MAX-ACCESS	read-only
	STATUS		current
	DESCRIPTION	"This attribute is an Enum of the different possible types
of drive arrays that could compose the logical drive represented by the correspo
ding entry in the Mass Store Logical Drives Table."
	REFERENCE "'DMTF|Mass Store Array Info Table|001' 2"
	::= { dmtfMassStoreArrayInfoEntry 2 }

driveArrayRedundancyStatus OBJECT-TYPE
	SYNTAX		INTEGER {
		other(1),
		unknown(2),
		fullyRedundant(3),
		degradedRedundancy(4),
		redundancyLost(5),
		notApplicableUnitNotRedundant-1(6),
		unitFailed(7)
	}
	MAX-ACCESS	read-only
	STATUS		current
	DESCRIPTION	"This attribute identifies which of the different states of
the available redundancy in the drive array currently applies."
	REFERENCE "'DMTF|Mass Store Array Info Table|001' 5"
	::= { dmtfMassStoreArrayInfoEntry 5 }

driveArrayOperationInProgress OBJECT-TYPE
	SYNTAX		INTEGER {
		other(1),
		unknown(2),
		verify(3),
		rebuild(5),
		none(6)
	}
	MAX-ACCESS	read-only
	STATUS		current
	DESCRIPTION	"This value of this attribute describes whether the drive
array is currently undergoing array operations of some sort."
	REFERENCE "'DMTF|Mass Store Array Info Table|001' 6"
	::= { dmtfMassStoreArrayInfoEntry 6 }

SdmtfMassStoreLogicalDrivesTable ::= SEQUENCE {
	dmtfMassStoreLogicalDrivesTableState INTEGER,
	logicalDriveIndex	DmiInteger,
	topOfHierarchy	DmiInteger,
	driveArray	DmiInteger,
	logicalDriveSizeInKB	DmiInteger,
	logicalDriveBlockSizeInBytes	DmiInteger,
	logicalDriveNameString	DmiString
}

dmtfMassStoreLogicalDrivesTable OBJECT-TYPE
	SYNTAX		SEQUENCE OF SdmtfMassStoreLogicalDrivesTable
	MAX-ACCESS	not-accessible
	STATUS		current
	DESCRIPTION	"This table describes the logical drives contained in this
component. Logical drives are typically composed of one or more other logical
drives or physical segments. Each entry of this table contains information
about the size of a logical drive, its string name as set by driver software,
and a boolean that describes whether this logical drive is at the top of
the logical drive hierarchy or not."
	::= { dmtfSystemsMIF 45 }

dmtfMassStoreLogicalDrivesEntry OBJECT-TYPE
	SYNTAX		SdmtfMassStoreLogicalDrivesTable
	MAX-ACCESS	not-accessible
	STATUS		current
	DESCRIPTION	"This table describes the logical drives contained in this
component. Logical drives are typically composed of one or more other logical
drives or physical segments. Each entry of this table contains information
about the size of a logical drive, its string name as set by driver software,
and a boolean that describes whether this logical drive is at the top of
the logical drive hierarchy or not."
	INDEX		{ DmiCompId,DmiGroupId, logicalDriveIndex }
	::= { dmtfMassStoreLogicalDrivesTable 1 }


dmtfMassStoreLogicalDrivesTableState OBJECT-TYPE
	SYNTAX		INTEGER {
		active(1),
		notInService(2),
		notReady(3),
		createAndGo(4),
		createAndWait(5),
		destroy(6)
	}
	MAX-ACCESS	read-write
	STATUS		current
	REFERENCE "'DMTF|Mass Store Logical Drives Table|001' 0"
	::= { dmtfMassStoreLogicalDrivesEntry 0 }

logicalDriveIndex OBJECT-TYPE
	SYNTAX		DmiInteger
	MAX-ACCESS	read-only
	STATUS		current
	DESCRIPTION	"A unique index (key) into the Mass Store Logical Drives Table."
	REFERENCE "'DMTF|Mass Store Logical Drives Table|001' 1"
	::= { dmtfMassStoreLogicalDrivesEntry 1 }

topOfHierarchy OBJECT-TYPE
	SYNTAX		INTEGER {
		false(0),
		true(1)
	}
	MAX-ACCESS	read-only
	STATUS		current
	DESCRIPTION	"This attribute identifies whether the logical drive represented
by this entry is a part of some higher order logical drive or not. If the
value of this boolean attribute is TRUE, then this means that this logical
drive is not a constituent part of any other logical drive in this component."
	REFERENCE "'DMTF|Mass Store Logical Drives Table|001' 2"
	::= { dmtfMassStoreLogicalDrivesEntry 2 }

driveArray OBJECT-TYPE
	SYNTAX		INTEGER {
		false(0),
		true(1)
	}
	MAX-ACCESS	read-only
	STATUS		current
	DESCRIPTION	"This boolean attribute identifies whether the logical drive
represented by this table entry is composed of an array of drives or not.
If the value of this attribute is TRUE, then the entry with the same index
(as this entry) in the Mass Store Array Info Table will give information
about the drive array that comprises this logical drive"
	REFERENCE "'DMTF|Mass Store Logical Drives Table|001' 3"
	::= { dmtfMassStoreLogicalDrivesEntry 3 }

logicalDriveSizeInKB OBJECT-TYPE
	SYNTAX		DmiInteger
	MAX-ACCESS	read-only
	STATUS		current
	DESCRIPTION	"This attribute holds the size of this logical drive in kilobytes"
	REFERENCE "'DMTF|Mass Store Logical Drives Table|001' 4"
	::= { dmtfMassStoreLogicalDrivesEntry 4 }

logicalDriveBlockSizeInBytes OBJECT-TYPE
	SYNTAX		DmiInteger
	MAX-ACCESS	read-only
	STATUS		current
	DESCRIPTION	"This attribute holds the size of the allocatable unit of
storage on this logical drive. The size of the allocatable unit is given
in bytes"
	REFERENCE "'DMTF|Mass Store Logical Drives Table|001' 5"
	::= { dmtfMassStoreLogicalDrivesEntry 5 }

logicalDriveNameString OBJECT-TYPE
	SYNTAX		DmiString
	MAX-ACCESS	read-write
	STATUS		current
	DESCRIPTION	"This attribute is simply a container for a string name for
the logical drive.  The instrumentation code does not assign or manipulate
this attribute. It is simply a convenience provided so that driver software
may put in this container the string name by which it refers to this logical
drive."
	REFERENCE "'DMTF|Mass Store Logical Drives Table|001' 6"
	::= { dmtfMassStoreLogicalDrivesEntry 6 }

SdmtfMassStoreMappingTable ::= SEQUENCE {
	dmtfMassStoreMappingTableState INTEGER,
	mappingIndex	DmiInteger,
	parentDrive	DmiInteger,
	childSegment	DmiInteger
}

dmtfMassStoreMappingTable OBJECT-TYPE
	SYNTAX		SEQUENCE OF SdmtfMassStoreMappingTable
	MAX-ACCESS	not-accessible
	STATUS		current
	DESCRIPTION	"This table represents mappings between logical drives and
logical or physical drive segments. Each entry in this table describes *one*
such mapping. A logical drive may be composed of one, *or more*, such mappings.
A segment may be a part of a physical or logical drive or, in the degenerate
case, the entire drive may be one segment. The table also contains two fields,
namely: (a) 'Parent Drive' a unique index into the Mass Store Logical Drives
Table describing the logical drive involved in the mapping, "
	::= { dmtfSystemsMIF 43 }

dmtfMassStoreMappingEntry OBJECT-TYPE
	SYNTAX		SdmtfMassStoreMappingTable
	MAX-ACCESS	not-accessible
	STATUS		current
	DESCRIPTION	"This table represents mappings between logical drives and
logical or physical drive segments. Each entry in this table describes *one*
such mapping. A logical drive may be composed of one, *or more*, such mappings.
A segment may be a part of a physical or logical drive or, in the degenerate
case, the entire drive may be one segment. The table also contains two fields,
namely: (a) 'Parent Drive' a unique index into the Mass Store Logical Drives
Table describing the logical drive involved in the mapping, "
	INDEX		{ DmiCompId,DmiGroupId, mappingIndex }
	::= { dmtfMassStoreMappingTable 1 }


dmtfMassStoreMappingTableState OBJECT-TYPE
	SYNTAX		INTEGER {
		active(1),
		notInService(2),
		notReady(3),
		createAndGo(4),
		createAndWait(5),
		destroy(6)
	}
	MAX-ACCESS	read-write
	STATUS		current
	REFERENCE "'DMTF|Mass Store Mapping Table|001' 0"
	::= { dmtfMassStoreMappingEntry 0 }

mappingIndex OBJECT-TYPE
	SYNTAX		DmiInteger
	MAX-ACCESS	read-only
	STATUS		current
	DESCRIPTION	"Unique index into the Mass Store Mapping Table"
	REFERENCE "'DMTF|Mass Store Mapping Table|001' 1"
	::= { dmtfMassStoreMappingEntry 1 }

parentDrive OBJECT-TYPE
	SYNTAX		DmiInteger
	MAX-ACCESS	read-only
	STATUS		current
	DESCRIPTION	"Unique index into the Mass Store Logical Drives Table of
the entry that represents the parent drive in this mapping."
	REFERENCE "'DMTF|Mass Store Mapping Table|001' 2"
	::= { dmtfMassStoreMappingEntry 2 }

childSegment OBJECT-TYPE
	SYNTAX		DmiInteger
	MAX-ACCESS	read-only
	STATUS		current
	DESCRIPTION	"This field contains the index of the logical or physical
segment that is one of the constituents of the parent logical drive referenced
by the attribute 'Parent Drive'.This index is a key into the Mass Store Segment
Table."
	REFERENCE "'DMTF|Mass Store Mapping Table|001' 3"
	::= { dmtfMassStoreMappingEntry 3 }

SdmtfMassStoreSegmentTable ::= SEQUENCE {
	dmtfMassStoreSegmentTableState INTEGER,
	segmentIndex	DmiInteger,
	segmentType	DmiInteger,
	segmentStart	DmiInteger,
	segmentLength	DmiInteger,
	segmentAllocationUnit	DmiInteger,
	segmentAllocationState	DmiInteger,
	driveKey1	DmiInteger,
	driveKey2	DmiInteger
}

dmtfMassStoreSegmentTable OBJECT-TYPE
	SYNTAX		SEQUENCE OF SdmtfMassStoreSegmentTable
	MAX-ACCESS	not-accessible
	STATUS		current
	DESCRIPTION	"This table describes the various segments on the various
physical or logical drives in the component. In some cases a segment may
represent an entire drive. In other cases there may be multiple segments
on a drive."
	::= { dmtfSystemsMIF 44 }

dmtfMassStoreSegmentEntry OBJECT-TYPE
	SYNTAX		SdmtfMassStoreSegmentTable
	MAX-ACCESS	not-accessible
	STATUS		current
	DESCRIPTION	"This table describes the various segments on the various
physical or logical drives in the component. In some cases a segment may
represent an entire drive. In other cases there may be multiple segments
on a drive."
	INDEX		{ DmiCompId,DmiGroupId, segmentIndex }
	::= { dmtfMassStoreSegmentTable 1 }


dmtfMassStoreSegmentTableState OBJECT-TYPE
	SYNTAX		INTEGER {
		active(1),
		notInService(2),
		notReady(3),
		createAndGo(4),
		createAndWait(5),
		destroy(6)
	}
	MAX-ACCESS	read-write
	STATUS		current
	REFERENCE "'DMTF|Mass Store Segment Table|001' 0"
	::= { dmtfMassStoreSegmentEntry 0 }

segmentIndex OBJECT-TYPE
	SYNTAX		DmiInteger
	MAX-ACCESS	read-only
	STATUS		current
	DESCRIPTION	"This is a unique index for this segment and is used as a
key into this table"
	REFERENCE "'DMTF|Mass Store Segment Table|001' 1"
	::= { dmtfMassStoreSegmentEntry 1 }

segmentType OBJECT-TYPE
	SYNTAX		INTEGER {
		physical(1),
		logical(2)
	}
	MAX-ACCESS	read-only
	STATUS		current
	DESCRIPTION	"Describes whether the segment is a physical segment on a
physical drive or a logical segment on a logical drive. If the value of this
attribute is 'Physical' then the physical drive is identified in the Disks
table by Drive Key 1 and Drive Key 2 attributes. If the value of this attribute
is 'Logical' then the logical drive is identified in the Mass Store Logical
Drives table by the Drive Key 2 attribute and the Drive Key 1 attribute is
irrelevant"
	REFERENCE "'DMTF|Mass Store Segment Table|001' 2"
	::= { dmtfMassStoreSegmentEntry 2 }

segmentStart OBJECT-TYPE
	SYNTAX		DmiInteger
	MAX-ACCESS	read-only
	STATUS		current
	DESCRIPTION	"This is the index of the allocation unit on the drive at
which the media extent corresponding to this segment starts."
	REFERENCE "'DMTF|Mass Store Segment Table|001' 3"
	::= { dmtfMassStoreSegmentEntry 3 }

segmentLength OBJECT-TYPE
	SYNTAX		DmiInteger
	MAX-ACCESS	read-only
	STATUS		current
	DESCRIPTION	"This is the length of the segment in allocation units inclusive
of the starting allocation unit whose index is contained in the attribute
'Segment Start'."
	REFERENCE "'DMTF|Mass Store Segment Table|001' 4"
	::= { dmtfMassStoreSegmentEntry 4 }

segmentAllocationUnit OBJECT-TYPE
	SYNTAX		INTEGER {
		other(1),
		unknown(2),
		physicalSector(3),
		logicalBlock(4)
	}
	MAX-ACCESS	read-only
	STATUS		current
	DESCRIPTION	"The value of this attribute identifies the type of unit of
space that can be allocated on the drive."
	REFERENCE "'DMTF|Mass Store Segment Table|001' 5"
	::= { dmtfMassStoreSegmentEntry 5 }

segmentAllocationState OBJECT-TYPE
	SYNTAX		INTEGER {
		other(1),
		unknown(2),
		allocated(3),
		available(4),
		defective(5),
		reserved-1(6),
		spare(7)
	}
	MAX-ACCESS	read-only
	STATUS		current
	DESCRIPTION	"The value of this attribute identifies the current allocation
state of the segment represented by this table entry. NOTE: Reserved = This
segment is reserved for vendor use (DO NOT USE this segment for other purposes);
Spare = This segment is currently in use being held in reserve for hot sparing."
	REFERENCE "'DMTF|Mass Store Segment Table|001' 6"
	::= { dmtfMassStoreSegmentEntry 6 }

driveKey1 OBJECT-TYPE
	SYNTAX		INTEGER {
		other(1),
		unknown(2),
		hardDisk(3),
		floppyDisk(4),
		opticalROM(5),
		opticalWORM(6),
		opticalRW(7),
		compactDisk(8),
		flashDisk(9),
		bernoulli(10),
		opticalFloppyDisk(11)
	}
	MAX-ACCESS	read-only
	STATUS		current
	DESCRIPTION	"If Segment Type is 'Physical' this is one of two keys used
to identify a specific disk in the Disks group. If the Segment Type is 'Logical'
this attribute is unused and its value is irrelevant."
	REFERENCE "'DMTF|Mass Store Segment Table|001' 7"
	::= { dmtfMassStoreSegmentEntry 7 }

driveKey2 OBJECT-TYPE
	SYNTAX		DmiInteger
	MAX-ACCESS	read-only
	STATUS		current
	DESCRIPTION	"(A) If the value of the attribute Segment Type is 'Physical'
then this attribute holds the second of two keys that identify the physical
drive in the Disks table group. (B) If the value of the Segment Type is 'Logical
 then this is the single integer key that identifies the logical drive in
the Mass Store Logical Drives table."
	REFERENCE "'DMTF|Mass Store Segment Table|001' 8"
	::= { dmtfMassStoreSegmentEntry 8 }

SdmtfMemoryArrayMappedAddresses ::= SEQUENCE {
	dmtfMemoryArrayMappedAddressesState INTEGER,
	memoryArrayMappedAddressesTableIndex	DmiInteger,
	memoryArrayIndex	DmiInteger,
	mappedRangeStartingAddress	DmiInteger,
	mappedRangeEndingAddress	DmiInteger,
	partitionID	DmiInteger,
	partitionWidth	DmiInteger,
	operationalGroupIndex	DmiInteger
}

dmtfMemoryArrayMappedAddressesTable OBJECT-TYPE
	SYNTAX		SEQUENCE OF SdmtfMemoryArrayMappedAddresses
	MAX-ACCESS	not-accessible
	STATUS		current
	DESCRIPTION	"This table presents ranges of physical addresses that are
mapped to a given Memory Array."
	::= { dmtfSystemsMIF 34 }

dmtfMemoryArrayMappedAddressesEntry OBJECT-TYPE
	SYNTAX		SdmtfMemoryArrayMappedAddresses
	MAX-ACCESS	not-accessible
	STATUS		current
	DESCRIPTION	"This table presents ranges of physical addresses that are
mapped to a given Memory Array."
	INDEX		{ DmiCompId,DmiGroupId, memoryArrayMappedAddressesTableIndex }
	::= { dmtfMemoryArrayMappedAddressesTable 1 }


dmtfMemoryArrayMappedAddressesState OBJECT-TYPE
	SYNTAX		INTEGER {
		active(1),
		notInService(2),
		notReady(3),
		createAndGo(4),
		createAndWait(5),
		destroy(6)
	}
	MAX-ACCESS	read-write
	STATUS		current
	REFERENCE "'DMTF|Memory Array Mapped Addresses|001' 0"
	::= { dmtfMemoryArrayMappedAddressesEntry 0 }

memoryArrayMappedAddressesTableIndex OBJECT-TYPE
	SYNTAX		DmiInteger
	MAX-ACCESS	read-only
	STATUS		current
	DESCRIPTION	"A unique number that identifies this row."
	REFERENCE "'DMTF|Memory Array Mapped Addresses|001' 1"
	::= { dmtfMemoryArrayMappedAddressesEntry 1 }

memoryArrayIndex OBJECT-TYPE
	SYNTAX		DmiInteger
	MAX-ACCESS	read-only
	STATUS		current
	DESCRIPTION	"The ID of the Memory Array that this address range is mapped
to.  Multiple address ranges may be mapped to a Memory Array."
	REFERENCE "'DMTF|Memory Array Mapped Addresses|001' 2"
	::= { dmtfMemoryArrayMappedAddressesEntry 2 }

mappedRangeStartingAddress OBJECT-TYPE
	SYNTAX		DmiInteger
	MAX-ACCESS	read-only
	STATUS		current
	DESCRIPTION	"The physical starting address, in kilobytes, of a range of
memory mapped to the specified Memory Array. 0x80000000 denotes 'unknown'."
	REFERENCE "'DMTF|Memory Array Mapped Addresses|001' 3"
	::= { dmtfMemoryArrayMappedAddressesEntry 3 }

mappedRangeEndingAddress OBJECT-TYPE
	SYNTAX		DmiInteger
	MAX-ACCESS	read-only
	STATUS		current
	DESCRIPTION	"The physical ending address of the last kilobyte of a range
of addresses mapped to the specified Memory Array. 0x80000000 denotes 'unknown'."
	REFERENCE "'DMTF|Memory Array Mapped Addresses|001' 4"
	::= { dmtfMemoryArrayMappedAddressesEntry 4 }

partitionID OBJECT-TYPE
	SYNTAX		DmiInteger
	MAX-ACCESS	read-only
	STATUS		current
	DESCRIPTION	"Identifies a Memory Partition associated with the Memory
Array specified by Memory Array Table Index. 0x80000000 denotes 'unknown'."
	REFERENCE "'DMTF|Memory Array Mapped Addresses|001' 5"
	::= { dmtfMemoryArrayMappedAddressesEntry 5 }

partitionWidth OBJECT-TYPE
	SYNTAX		DmiInteger
	MAX-ACCESS	read-only
	STATUS		current
	DESCRIPTION	"The number of Memory Devices that form a single row of memory
for the partition. 0x80000000 denotes 'unknown'."
	REFERENCE "'DMTF|Memory Array Mapped Addresses|001' 6"
	::= { dmtfMemoryArrayMappedAddressesEntry 6 }

operationalGroupIndex OBJECT-TYPE
	SYNTAX		DmiInteger
	MAX-ACCESS	read-only
	STATUS		current
	DESCRIPTION	"The index into the Operational State Table for this Memory
Range.  Generally, there will be a 1:1 correspondence between a mapped range
and a partition.  In which case, the Operational State will be for the partition
as well. In the case that there is more than one mapped range for a partion,
it will be necessary to check the Operational State entries for each range
to determine the overall status of the partition."
	REFERENCE "'DMTF|Memory Array Mapped Addresses|001' 7"
	::= { dmtfMemoryArrayMappedAddressesEntry 7 }

SdmtfMemoryDeviceMappedAddresses ::= SEQUENCE {
	dmtfMemoryDeviceMappedAddressesState INTEGER,
	memoryDeviceMappedAddressesTableIndex	DmiInteger,
	memoryDeviceSetID	DmiInteger,
	partition	DmiInteger,
	mappedRangeStartingAddress	DmiInteger,
	mappedRangeEndingAddress	DmiInteger,
	partitionRowPosition	DmiInteger,
	interleavePosition	DmiInteger,
	dataDepth	DmiInteger
}

dmtfMemoryDeviceMappedAddressesTable OBJECT-TYPE
	SYNTAX		SEQUENCE OF SdmtfMemoryDeviceMappedAddresses
	MAX-ACCESS	not-accessible
	STATUS		current
	DESCRIPTION	"This table presents ranges of physical addresses that are
mapped to a given Memory Device Set."
	::= { dmtfSystemsMIF 36 }

dmtfMemoryDeviceMappedAddressesEntry OBJECT-TYPE
	SYNTAX		SdmtfMemoryDeviceMappedAddresses
	MAX-ACCESS	not-accessible
	STATUS		current
	DESCRIPTION	"This table presents ranges of physical addresses that are
mapped to a given Memory Device Set."
	INDEX		{ DmiCompId,DmiGroupId, memoryDeviceMappedAddressesTableIndex }
	::= { dmtfMemoryDeviceMappedAddressesTable 1 }


dmtfMemoryDeviceMappedAddressesState OBJECT-TYPE
	SYNTAX		INTEGER {
		active(1),
		notInService(2),
		notReady(3),
		createAndGo(4),
		createAndWait(5),
		destroy(6)
	}
	MAX-ACCESS	read-write
	STATUS		current
	REFERENCE "'DMTF|Memory Device Mapped Addresses|001' 0"
	::= { dmtfMemoryDeviceMappedAddressesEntry 0 }

memoryDeviceMappedAddressesTableIndex OBJECT-TYPE
	SYNTAX		DmiInteger
	MAX-ACCESS	read-only
	STATUS		current
	DESCRIPTION	"A unique number that identifies this row."
	REFERENCE "'DMTF|Memory Device Mapped Addresses|001' 1"
	::= { dmtfMemoryDeviceMappedAddressesEntry 1 }

memoryDeviceSetID OBJECT-TYPE
	SYNTAX		DmiInteger
	MAX-ACCESS	read-only
	STATUS		current
	DESCRIPTION	"The row in the Memory Device table that this address range
is for.  This matches with a Memory Device Table Index. There may be multiple
rows in Memory Device Mapped addresses for a single Memory Device."
	REFERENCE "'DMTF|Memory Device Mapped Addresses|001' 2"
	::= { dmtfMemoryDeviceMappedAddressesEntry 2 }

partition OBJECT-TYPE
	SYNTAX		DmiInteger
	MAX-ACCESS	read-only
	STATUS		current
	DESCRIPTION	"Identifies the Memory partition in the Memory Array Mapped
Addresses table that this Memory Device is part of. Partition number should
be positive.  0x80000000 denotes 'unknown'."
	REFERENCE "'DMTF|Memory Device Mapped Addresses|001' 3"
	::= { dmtfMemoryDeviceMappedAddressesEntry 3 }

mappedRangeStartingAddress OBJECT-TYPE
	SYNTAX		DmiInteger
	MAX-ACCESS	read-only
	STATUS		current
	DESCRIPTION	"The physical starting address, in kilobytes, of a range of
memory mapped to the specified Memory Device set. The address is specified
relative to the bus that the device is connected to. 0x80000000 denotes 'unknown
."
	REFERENCE "'DMTF|Memory Device Mapped Addresses|001' 4"
	::= { dmtfMemoryDeviceMappedAddressesEntry 4 }

mappedRangeEndingAddress OBJECT-TYPE
	SYNTAX		DmiInteger
	MAX-ACCESS	read-only
	STATUS		current
	DESCRIPTION	"The physical ending address of the last kilobyte of a range
of addresses mapped to the specified Memory Device. The address is specified
relative to the bus that the device is connected to. 0x80000000 denotes 'unknown
."
	REFERENCE "'DMTF|Memory Device Mapped Addresses|001' 5"
	::= { dmtfMemoryDeviceMappedAddressesEntry 5 }

partitionRowPosition OBJECT-TYPE
	SYNTAX		DmiInteger
	MAX-ACCESS	read-only
	STATUS		current
	DESCRIPTION	"This specifies the position of the device in a row of the
partition. For example, if it takes two 8-bit memory devices to form a 16-bit
row, then a value of '2'in this attribute means the device is the second
device. 0 is an invalid return value.  0x80000000 denotes 'unknown'."
	REFERENCE "'DMTF|Memory Device Mapped Addresses|001' 6"
	::= { dmtfMemoryDeviceMappedAddressesEntry 6 }

interleavePosition OBJECT-TYPE
	SYNTAX		DmiInteger
	MAX-ACCESS	read-only
	STATUS		current
	DESCRIPTION	"The position of this device in an interleave. 0 indicates
non-interleaved. 1 indicates the first position 2 the second, and so on.
For example, in a 2:1 interleave, a value of '1' would indicate the device
is in the 'even' position, in a 4:1 interleave this would be the first of
four possible positions).  0x80000000 denotes 'unknown' or'unsupported'."
	REFERENCE "'DMTF|Memory Device Mapped Addresses|001' 7"
	::= { dmtfMemoryDeviceMappedAddressesEntry 7 }

dataDepth OBJECT-TYPE
	SYNTAX		DmiInteger
	MAX-ACCESS	read-only
	STATUS		current
	DESCRIPTION	"The maximum number of consecutive rows accessed from this
device in a single interleaved transfer. For example, if a device transfers
two rows each time it is read, its Interleaved Data Depth would be 2. If
that device is 2:1 interleaved and in Interleave Position '1', then the rows
mapped to that device would be rows 1,2,5,6,9,10, etc. If the device is not
part of an interleave, this value should be 0.  0x80000000 denotes 'unknown'."
	REFERENCE "'DMTF|Memory Device Mapped Addresses|001' 8"
	::= { dmtfMemoryDeviceMappedAddressesEntry 8 }

SdmtfMemoryDevice ::= SEQUENCE {
	dmtfMemoryDeviceState INTEGER,
	memoryDeviceTableIndex	DmiInteger,
	memoryArrayIndex	DmiInteger,
	deviceLocator	DmiString,
	bankLocator	DmiString,
	size	DmiInteger,
	formFactor	DmiInteger,
	totalWidth	DmiInteger,
	dataWidth	DmiInteger,
	memoryType	DmiInteger,
	typeDetail	DmiInteger,
	deviceSet	DmiInteger,
	deviceErrorType	DmiInteger,
	errorGranularity	DmiInteger,
	lastErrorUpdate	DmiInteger,
	errorOperation	DmiInteger,
	errorDataSize	DmiInteger,
	errorData	DmiOctetstring,
	vendorSyndrome	DmiOctetstring,
	deviceErrorAddress	DmiInteger,
	arrayErrorAddress	DmiInteger,
	errorResolution	DmiInteger,
	fRUGroupIndex	DmiInteger,
	operationalGroupIndex	DmiInteger
}

dmtfMemoryDeviceTable OBJECT-TYPE
	SYNTAX		SEQUENCE OF SdmtfMemoryDevice
	MAX-ACCESS	not-accessible
	STATUS		current
	DESCRIPTION	"This group presents information about individual memory devices
in the system. A memory device can be a SIMM, a SIPP, or a single chip, or
an entire card-based on the resolution to which a memory error can be determined
and whether the device is replaceable as a unit."
	::= { dmtfSystemsMIF 35 }

dmtfMemoryDeviceEntry OBJECT-TYPE
	SYNTAX		SdmtfMemoryDevice
	MAX-ACCESS	not-accessible
	STATUS		current
	DESCRIPTION	"This group presents information about individual memory devices
in the system. A memory device can be a SIMM, a SIPP, or a single chip, or
an entire card-based on the resolution to which a memory error can be determined
and whether the device is replaceable as a unit."
	INDEX		{ DmiCompId,DmiGroupId, memoryDeviceTableIndex }
	::= { dmtfMemoryDeviceTable 1 }


dmtfMemoryDeviceState OBJECT-TYPE
	SYNTAX		INTEGER {
		active(1),
		notInService(2),
		notReady(3),
		createAndGo(4),
		createAndWait(5),
		destroy(6)
	}
	MAX-ACCESS	read-write
	STATUS		current
	REFERENCE "'DMTF|Memory Device|001' 0"
	::= { dmtfMemoryDeviceEntry 0 }

memoryDeviceTableIndex OBJECT-TYPE
	SYNTAX		DmiInteger
	MAX-ACCESS	read-only
	STATUS		current
	DESCRIPTION	"A unique number that identifies this row."
	REFERENCE "'DMTF|Memory Device|001' 1"
	::= { dmtfMemoryDeviceEntry 1 }

memoryArrayIndex OBJECT-TYPE
	SYNTAX		DmiInteger
	MAX-ACCESS	read-only
	STATUS		current
	DESCRIPTION	"The ID of the Memory Array that this Memory Device is a part
of."
	REFERENCE "'DMTF|Memory Device|001' 2"
	::= { dmtfMemoryDeviceEntry 2 }

deviceLocator OBJECT-TYPE
	SYNTAX		DmiString
	MAX-ACCESS	read-only
	STATUS		current
	DESCRIPTION	"A string identifying the physically labeled socket or board
position where the memory device is located. Eg. 'SIMM 3' or 'IC12'."
	REFERENCE "'DMTF|Memory Device|001' 3"
	::= { dmtfMemoryDeviceEntry 3 }

bankLocator OBJECT-TYPE
	SYNTAX		DmiString
	MAX-ACCESS	read-only
	STATUS		current
	DESCRIPTION	"A string identifying the physically labeled bank where the
memory device is located. Eg. 'Bank 0' or 'A'."
	REFERENCE "'DMTF|Memory Device|001' 4"
	::= { dmtfMemoryDeviceEntry 4 }

size OBJECT-TYPE
	SYNTAX		DmiInteger
	MAX-ACCESS	read-only
	STATUS		current
	DESCRIPTION	"Size of this memory device, in bytes."
	REFERENCE "'DMTF|Memory Device|001' 5"
	::= { dmtfMemoryDeviceEntry 5 }

formFactor OBJECT-TYPE
	SYNTAX		INTEGER {
		other(1),
		unknown(2),
		sIMM(3),
		sIP(4),
		chip(5),
		dIP(6),
		zIP(7),
		proprietaryCard(8),
		dIMM(9),
		tSOP(10),
		rowOfChips(11)
	}
	MAX-ACCESS	read-only
	STATUS		current
	DESCRIPTION	"Implementation form factor for this memory device."
	REFERENCE "'DMTF|Memory Device|001' 6"
	::= { dmtfMemoryDeviceEntry 6 }

totalWidth OBJECT-TYPE
	SYNTAX		DmiInteger
	MAX-ACCESS	read-only
	STATUS		current
	DESCRIPTION	"Total width of this memory device, including check or error
correction bits, in bits. If there are no error correction bits, the value
in this attribute should match that specified in Data Width.  0x80000000
denotes 'unknown'."
	REFERENCE "'DMTF|Memory Device|001' 7"
	::= { dmtfMemoryDeviceEntry 7 }

dataWidth OBJECT-TYPE
	SYNTAX		DmiInteger
	MAX-ACCESS	read-only
	STATUS		current
	DESCRIPTION	"Data width of this memory device, in bits. A data width of
0 and a Total Width of 8 would indicate that the device is solely being used
to provide eight error correction bits. 0x80000000 denotes 'unknown'."
	REFERENCE "'DMTF|Memory Device|001' 8"
	::= { dmtfMemoryDeviceEntry 8 }

memoryType OBJECT-TYPE
	SYNTAX		INTEGER {
		other(1),
		unknown(2),
		dRAM(3),
		eDRAM(4),
		vRAM(5),
		sRAM(6),
		rAM(7),
		rOM(8),
		fLASH(9),
		eEPROM(10),
		fEPROM(11),
		ePROM(12)
	}
	MAX-ACCESS	read-only
	STATUS		current
	DESCRIPTION	"Type of memory used in this memory device."
	REFERENCE "'DMTF|Memory Device|001' 9"
	::= { dmtfMemoryDeviceEntry 9 }

typeDetail OBJECT-TYPE
	SYNTAX		INTEGER {
		other(1),
		unknown(2),
		fastPaged(3),
		staticColumn(4),
		pseudoStatic(5),
		rAMBUS(6),
		synchronous(7),
		cMOS(8),
		eDO(9),
		windowDRAM(10),
		cacheDRAM(11),
		nonVolatile(12)
	}
	MAX-ACCESS	read-only
	STATUS		current
	DESCRIPTION	"Additional detail on the device type."
	REFERENCE "'DMTF|Memory Device|001' 10"
	::= { dmtfMemoryDeviceEntry 10 }

deviceSet OBJECT-TYPE
	SYNTAX		DmiInteger
	MAX-ACCESS	read-only
	STATUS		current
	DESCRIPTION	"This attribute is used to identify when the Memory Device
is one of a set of Memory Devices that must be populated with all devices
of the same type and size, and which set the device belongs to.  For example,
when one SIMM belongs to a set of four. 0 indicates the Memory Device isn't
part of a set. 0x80000000 denotes 'unknown'."
	REFERENCE "'DMTF|Memory Device|001' 11"
	::= { dmtfMemoryDeviceEntry 11 }

deviceErrorType OBJECT-TYPE
	SYNTAX		INTEGER {
		other(1),
		unknown(2),
		oK(3),
		badRead(4),
		parityError(5),
		singleBitError(6),
		doubleBitError(7),
		multiBitError(8),
		nibbleError(9),
		checksumError(10),
		cRCError(11),
		correctedSingleBitError(12),
		correctedError(13),
		uncorrectableError(14)
	}
	MAX-ACCESS	read-only
	STATUS		current
	DESCRIPTION	"The type of error that is associated with the current status
reported in Operational State for this Memory Device."
	REFERENCE "'DMTF|Memory Device|001' 12"
	::= { dmtfMemoryDeviceEntry 12 }

errorGranularity OBJECT-TYPE
	SYNTAX		INTEGER {
		other(1),
		unknown(2),
		deviceLevel(3),
		memoryPartitionLevel(4)
	}
	MAX-ACCESS	read-only
	STATUS		current
	DESCRIPTION	"Specifies whether the current error's location can be resolved
to the partition or device level."
	REFERENCE "'DMTF|Memory Device|001' 13"
	::= { dmtfMemoryDeviceEntry 13 }

lastErrorUpdate OBJECT-TYPE
	SYNTAX		INTEGER {
		other(1),
		unknown(2),
		noUpdateSinceLastInstrumentationStart(3),
		updatedFromInformationObtainedPriorToInstrumentati(4),
		updatedDuringInstrumentationRunTime(5)
	}
	MAX-ACCESS	read-only
	STATUS		current
	DESCRIPTION	"System state during which the last error update was collected."
	REFERENCE "'DMTF|Memory Device|001' 14"
	::= { dmtfMemoryDeviceEntry 14 }

errorOperation OBJECT-TYPE
	SYNTAX		INTEGER {
		other(1),
		unknown(2),
		read(3),
		write(4),
		partialWrite(5)
	}
	MAX-ACCESS	read-only
	STATUS		current
	DESCRIPTION	"The memory access operation that caused the current error."
	REFERENCE "'DMTF|Memory Device|001' 15"
	::= { dmtfMemoryDeviceEntry 15 }

errorDataSize OBJECT-TYPE
	SYNTAX		DmiInteger
	MAX-ACCESS	read-only
	STATUS		current
	DESCRIPTION	"The size of the data transfer that caused the error,in bits.
Zero indicates no error, 0x80000000 denotes 'unknown'."
	REFERENCE "'DMTF|Memory Device|001' 16"
	::= { dmtfMemoryDeviceEntry 16 }

errorData OBJECT-TYPE
	SYNTAX		DmiOctetstring
	MAX-ACCESS	read-only
	STATUS		current
	DESCRIPTION	"Data captured during the erroneous Memory Array access. The
data occupies the first n bytes of the octet string required to hold 'Error
Data Size' bits of the data. Data is stored least-significant byte first."
	REFERENCE "'DMTF|Memory Device|001' 17"
	::= { dmtfMemoryDeviceEntry 17 }

vendorSyndrome OBJECT-TYPE
	SYNTAX		DmiOctetstring
	MAX-ACCESS	read-only
	STATUS		current
	DESCRIPTION	"Vendor-specific syndrome or CRC data associated with the
erroneous access."
	REFERENCE "'DMTF|Memory Device|001' 18"
	::= { dmtfMemoryDeviceEntry 18 }

deviceErrorAddress OBJECT-TYPE
	SYNTAX		DmiInteger
	MAX-ACCESS	read-only
	STATUS		current
	DESCRIPTION	"Physical address of the error relative to the start of the
device, in bytes.  0x80000000 denotes 'unknown'."
	REFERENCE "'DMTF|Memory Device|001' 19"
	::= { dmtfMemoryDeviceEntry 19 }

arrayErrorAddress OBJECT-TYPE
	SYNTAX		DmiInteger
	MAX-ACCESS	read-only
	STATUS		current
	DESCRIPTION	"Physical address of the kilobyte where the error is located,
relative to the bus for the Memory Array. 0x80000000 denotes 'unknown'."
	REFERENCE "'DMTF|Memory Device|001' 20"
	::= { dmtfMemoryDeviceEntry 20 }

errorResolution OBJECT-TYPE
	SYNTAX		DmiInteger
	MAX-ACCESS	read-only
	STATUS		current
	DESCRIPTION	"Range in bytes that the error can be determined to be within,whe
 an Error Address is given. 0x80000000 denotes 'unknown'."
	REFERENCE "'DMTF|Memory Device|001' 21"
	::= { dmtfMemoryDeviceEntry 21 }

fRUGroupIndex OBJECT-TYPE
	SYNTAX		DmiInteger
	MAX-ACCESS	read-only
	STATUS		current
	DESCRIPTION	"If this is a Field Replaceable Unit or if it is part of another
FRU, this provides an index into the FRU table; 'value = -1' indicates that
the group is not a FRU."
	REFERENCE "'DMTF|Memory Device|001' 22"
	::= { dmtfMemoryDeviceEntry 22 }

operationalGroupIndex OBJECT-TYPE
	SYNTAX		DmiInteger
	MAX-ACCESS	read-only
	STATUS		current
	DESCRIPTION	"The index into the Operational State Table for this device."
	REFERENCE "'DMTF|Memory Device|001' 23"
	::= { dmtfMemoryDeviceEntry 23 }

SdmtfMemoryMappedIO ::= SEQUENCE {
	dmtfMemoryMappedIOState INTEGER,
	memoryMappedIOStartingAddress	Dmi-Integer64,
	memoryMappedIOEndingAddress	Dmi-Integer64,
	memoryMappedIODescription	DmiString
}

dmtfMemoryMappedIOTable OBJECT-TYPE
	SYNTAX		SEQUENCE OF SdmtfMemoryMappedIO
	MAX-ACCESS	not-accessible
	STATUS		current
	DESCRIPTION	"This group defines various attributes for memory mapped I/O
on this system."
	::= { dmtfSystemsMIF 14 }

dmtfMemoryMappedIOEntry OBJECT-TYPE
	SYNTAX		SdmtfMemoryMappedIO
	MAX-ACCESS	not-accessible
	STATUS		current
	DESCRIPTION	"This group defines various attributes for memory mapped I/O
on this system."
	INDEX		{ DmiCompId,DmiGroupId, memoryMappedIOStartingAddress }
	::= { dmtfMemoryMappedIOTable 1 }


dmtfMemoryMappedIOState OBJECT-TYPE
	SYNTAX		INTEGER {
		active(1),
		notInService(2),
		notReady(3),
		createAndGo(4),
		createAndWait(5),
		destroy(6)
	}
	MAX-ACCESS	read-write
	STATUS		current
	REFERENCE "'DMTF|Memory Mapped I/O|001' 0"
	::= { dmtfMemoryMappedIOEntry 0 }

memoryMappedIOStartingAddress OBJECT-TYPE
	SYNTAX		Dmi-Integer64
	MAX-ACCESS	read-only
	STATUS		current
	DESCRIPTION	"The starting address of a contiguous System memory mapped
I/O region."
	REFERENCE "'DMTF|Memory Mapped I/O|001' 1"
	::= { dmtfMemoryMappedIOEntry 1 }

memoryMappedIOEndingAddress OBJECT-TYPE
	SYNTAX		Dmi-Integer64
	MAX-ACCESS	read-only
	STATUS		current
	DESCRIPTION	"The ending address of a contiguous System memory mapped I/O
region."
	REFERENCE "'DMTF|Memory Mapped I/O|001' 2"
	::= { dmtfMemoryMappedIOEntry 2 }

memoryMappedIODescription OBJECT-TYPE
	SYNTAX		DmiString
	MAX-ACCESS	read-only
	STATUS		current
	DESCRIPTION	"The name of the logical device currently using this Memory
Mapped I/O."
	REFERENCE "'DMTF|Memory Mapped I/O|001' 3"
	::= { dmtfMemoryMappedIOEntry 3 }

SdmtfMotherboard ::= SEQUENCE {
	numberOfExpansionSlots	DmiInteger,
	fRUGroupIndex	DmiInteger,
	operationalGroupIndex	DmiInteger
}

dmtfMotherboardTable OBJECT-TYPE
	SYNTAX		SEQUENCE OF SdmtfMotherboard
	MAX-ACCESS	not-accessible
	STATUS		current
	DESCRIPTION	"This group defines attributes for the motherboard."
	::= { dmtfSystemsMIF 6 }

dmtfMotherboardEntry OBJECT-TYPE
	SYNTAX		SdmtfMotherboard
	MAX-ACCESS	not-accessible
	STATUS		current
	DESCRIPTION	"This group defines attributes for the motherboard."
	INDEX		{ DmiCompId,DmiGroupId }
	::= { dmtfMotherboardTable 1 }


numberOfExpansionSlots OBJECT-TYPE
	SYNTAX		DmiInteger
	MAX-ACCESS	read-only
	STATUS		current
	DESCRIPTION	"The total number of expansion slots which physically exist
on the motherboard whether occupied or not (see System Slots group)."
	REFERENCE "'DMTF|Motherboard|001' 1"
	::= { dmtfMotherboardEntry 1 }

fRUGroupIndex OBJECT-TYPE
	SYNTAX		DmiInteger
	MAX-ACCESS	read-only
	STATUS		current
	DESCRIPTION	"If this is a Field Replaceable Unit or if it is part of another
FRU, this provides an index into the FRU table; 'value = -1' indicates that
the group is not a FRU."
	REFERENCE "'DMTF|Motherboard|001' 2"
	::= { dmtfMotherboardEntry 2 }

operationalGroupIndex OBJECT-TYPE
	SYNTAX		DmiInteger
	MAX-ACCESS	read-only
	STATUS		current
	DESCRIPTION	"The index into the Operational State Table for this device
if applicable."
	REFERENCE "'DMTF|Motherboard|001' 3"
	::= { dmtfMotherboardEntry 3 }

SdmtfMouse ::= SEQUENCE {
	mouseInterface	DmiInteger,
	mouseIRQ	DmiInteger,
	mouseButtons	DmiInteger,
	mousePortName	DmiString,
	mouseDriverName	DmiString,
	mouseDriverVersion	DmiString,
	fRUGroupIndex	DmiInteger,
	operationalGroupIndex	DmiInteger,
	securitySettings	DmiInteger
}

dmtfMouseTable OBJECT-TYPE
	SYNTAX		SEQUENCE OF SdmtfMouse
	MAX-ACCESS	not-accessible
	STATUS		current
	DESCRIPTION	"This group defines the characteristics of a mouse input device."
	::= { dmtfSystemsMIF 27 }

dmtfMouseEntry OBJECT-TYPE
	SYNTAX		SdmtfMouse
	MAX-ACCESS	not-accessible
	STATUS		current
	DESCRIPTION	"This group defines the characteristics of a mouse input device."
	INDEX		{ DmiCompId,DmiGroupId }
	::= { dmtfMouseTable 1 }


mouseInterface OBJECT-TYPE
	SYNTAX		INTEGER {
		other(1),
		unknown(2),
		serial(3),
		pS2(4),
		infrared(5),
		hPHIL(6),
		busMouse(7),
		aDBAppleDesktopBus(8),
		busMouseDB9(160),
		busMouseMicroDIN(161),
		uSB(162)
	}
	MAX-ACCESS	read-only
	STATUS		current
	DESCRIPTION	"The interface type of this mouse."
	REFERENCE "'DMTF|Mouse|003' 1"
	::= { dmtfMouseEntry 1 }

mouseIRQ OBJECT-TYPE
	SYNTAX		DmiInteger
	MAX-ACCESS	read-only
	STATUS		current
	DESCRIPTION	"The IRQ number used by this mouse."
	REFERENCE "'DMTF|Mouse|003' 2"
	::= { dmtfMouseEntry 2 }

mouseButtons OBJECT-TYPE
	SYNTAX		DmiInteger
	MAX-ACCESS	read-only
	STATUS		current
	DESCRIPTION	"The number of mouse buttons on this mouse."
	REFERENCE "'DMTF|Mouse|003' 3"
	::= { dmtfMouseEntry 3 }

mousePortName OBJECT-TYPE
	SYNTAX		DmiString
	MAX-ACCESS	read-only
	STATUS		current
	DESCRIPTION	"The name of the port currently being used by this mouse."
	REFERENCE "'DMTF|Mouse|003' 4"
	::= { dmtfMouseEntry 4 }

mouseDriverName OBJECT-TYPE
	SYNTAX		DmiString
	MAX-ACCESS	read-only
	STATUS		current
	DESCRIPTION	"The name of the mouse driver."
	REFERENCE "'DMTF|Mouse|003' 5"
	::= { dmtfMouseEntry 5 }

mouseDriverVersion OBJECT-TYPE
	SYNTAX		DmiString
	MAX-ACCESS	read-only
	STATUS		current
	DESCRIPTION	"The version number of the mouse driver."
	REFERENCE "'DMTF|Mouse|003' 6"
	::= { dmtfMouseEntry 6 }

fRUGroupIndex OBJECT-TYPE
	SYNTAX		DmiInteger
	MAX-ACCESS	read-only
	STATUS		current
	DESCRIPTION	"If this is a Field Replaceable Unit or if it is part of another
FRU, this provides an index into the FRU table; 'value = -1' indicates that
the group is not a FRU."
	REFERENCE "'DMTF|Mouse|003' 7"
	::= { dmtfMouseEntry 7 }

operationalGroupIndex OBJECT-TYPE
	SYNTAX		DmiInteger
	MAX-ACCESS	read-only
	STATUS		current
	DESCRIPTION	"The index into the Operational State table for this device."
	REFERENCE "'DMTF|Mouse|003' 8"
	::= { dmtfMouseEntry 8 }

securitySettings OBJECT-TYPE
	SYNTAX		INTEGER {
		other(1),
		unknown(2),
		none(3),
		externalInterfaceLockedOut(4),
		externalInterfaceEnabled(5)
	}
	MAX-ACCESS	read-only
	STATUS		current
	DESCRIPTION	"Enum describing the current hardware security settings on
this device"
	REFERENCE "'DMTF|Mouse|003' 9"
	::= { dmtfMouseEntry 9 }

SdmtfOperatingSystem ::= SEQUENCE {
	dmtfOperatingSystemState INTEGER,
	operatingSystemIndex	DmiInteger,
	operatingSystemName	DmiString,
	operatingSystemVersion	DmiString,
	primaryOperatingSystem	DmiInteger,
	operatingSystemBootDeviceStorageType	DmiInteger,
	operatingSystemBootDeviceIndex	DmiInteger,
	operatingSystemBootPartitionIndex	DmiInteger,
	operatingSystemDescription	DmiString
}

dmtfOperatingSystemTable OBJECT-TYPE
	SYNTAX		SEQUENCE OF SdmtfOperatingSystem
	MAX-ACCESS	not-accessible
	STATUS		current
	DESCRIPTION	"This group defines general information about operating systems
installed on this system."
	::= { dmtfSystemsMIF 2 }

dmtfOperatingSystemEntry OBJECT-TYPE
	SYNTAX		SdmtfOperatingSystem
	MAX-ACCESS	not-accessible
	STATUS		current
	DESCRIPTION	"This group defines general information about operating systems
installed on this system."
	INDEX		{ DmiCompId,DmiGroupId, operatingSystemIndex }
	::= { dmtfOperatingSystemTable 1 }


dmtfOperatingSystemState OBJECT-TYPE
	SYNTAX		INTEGER {
		active(1),
		notInService(2),
		notReady(3),
		createAndGo(4),
		createAndWait(5),
		destroy(6)
	}
	MAX-ACCESS	read-write
	STATUS		current
	REFERENCE "'DMTF|Operating System|001' 0"
	::= { dmtfOperatingSystemEntry 0 }

operatingSystemIndex OBJECT-TYPE
	SYNTAX		DmiInteger
	MAX-ACCESS	read-only
	STATUS		current
	DESCRIPTION	"The index into the operating system table."
	REFERENCE "'DMTF|Operating System|001' 1"
	::= { dmtfOperatingSystemEntry 1 }

operatingSystemName OBJECT-TYPE
	SYNTAX		DmiString
	MAX-ACCESS	read-only
	STATUS		current
	DESCRIPTION	"The name of this operating system."
	REFERENCE "'DMTF|Operating System|001' 2"
	::= { dmtfOperatingSystemEntry 2 }

operatingSystemVersion OBJECT-TYPE
	SYNTAX		DmiString
	MAX-ACCESS	read-only
	STATUS		current
	DESCRIPTION	"The version number of this operating system."
	REFERENCE "'DMTF|Operating System|001' 3"
	::= { dmtfOperatingSystemEntry 3 }

primaryOperatingSystem OBJECT-TYPE
	SYNTAX		INTEGER {
		false(0),
		true(1)
	}
	MAX-ACCESS	read-only
	STATUS		current
	DESCRIPTION	"If true, this is the primary operating system."
	REFERENCE "'DMTF|Operating System|001' 4"
	::= { dmtfOperatingSystemEntry 4 }

operatingSystemBootDeviceStorageType OBJECT-TYPE
	SYNTAX		INTEGER {
		other(1),
		unknown(2),
		hardDisk(3),
		floppyDisk(4),
		opticalROM(5),
		opticalWORM(6),
		opticalRW(7),
		compactDisk(8),
		flashDisk(9),
		bernoulli(10),
		opticalFloppyDisk(11)
	}
	MAX-ACCESS	read-only
	STATUS		current
	DESCRIPTION	"An index into the Disks Table to indicate the device from
which this operating system was booted. To fully access the Disks Table,
this index must be combined with the attribute Boot Device Index."
	REFERENCE "'DMTF|Operating System|001' 5"
	::= { dmtfOperatingSystemEntry 5 }

operatingSystemBootDeviceIndex OBJECT-TYPE
	SYNTAX		DmiInteger
	MAX-ACCESS	read-only
	STATUS		current
	DESCRIPTION	"An index into the Disks Table."
	REFERENCE "'DMTF|Operating System|001' 6"
	::= { dmtfOperatingSystemEntry 6 }

operatingSystemBootPartitionIndex OBJECT-TYPE
	SYNTAX		DmiInteger
	MAX-ACCESS	read-only
	STATUS		current
	DESCRIPTION	"An index into the Partition table indicating the partition
from which this operating system booted."
	REFERENCE "'DMTF|Operating System|001' 7"
	::= { dmtfOperatingSystemEntry 7 }

operatingSystemDescription OBJECT-TYPE
	SYNTAX		DmiString
	MAX-ACCESS	read-only
	STATUS		current
	DESCRIPTION	"A description of this operating system."
	REFERENCE "'DMTF|Operating System|001' 8"
	::= { dmtfOperatingSystemEntry 8 }

SdmtfOperationalState ::= SEQUENCE {
	dmtfOperationalStateState INTEGER,
	operationalStateInstanceIndex	DmiInteger,
	deviceGroupIndex	DmiInteger,
	operationalStatus	DmiInteger,
	usageState	DmiInteger,
	availabilityStatus	DmiInteger,
	administrativeState	DmiInteger,
	fatalErrorCount	DmiCounter,
	majorErrorCount	DmiCounter,
	warningErrorCount	DmiCounter,
	currentErrorStatus	DmiInteger,
	devicePredictedFailureStatus	DmiInteger
}

dmtfOperationalStateTable OBJECT-TYPE
	SYNTAX		SEQUENCE OF SdmtfOperationalState
	MAX-ACCESS	not-accessible
	STATUS		current
	DESCRIPTION	"This group provides the operational state, usage, and availabili
y status,and administrative state indicators for specific Device Group instances
"
	::= { dmtfSystemsMIF 30 }

dmtfOperationalStateEntry OBJECT-TYPE
	SYNTAX		SdmtfOperationalState
	MAX-ACCESS	not-accessible
	STATUS		current
	DESCRIPTION	"This group provides the operational state, usage, and availabili
y status,and administrative state indicators for specific Device Group instances
"
	INDEX		{ DmiCompId,DmiGroupId, operationalStateInstanceIndex }
	::= { dmtfOperationalStateTable 1 }


dmtfOperationalStateState OBJECT-TYPE
	SYNTAX		INTEGER {
		active(1),
		notInService(2),
		notReady(3),
		createAndGo(4),
		createAndWait(5),
		destroy(6)
	}
	MAX-ACCESS	read-write
	STATUS		current
	REFERENCE "'DMTF|Operational State|003' 0"
	::= { dmtfOperationalStateEntry 0 }

operationalStateInstanceIndex OBJECT-TYPE
	SYNTAX		DmiInteger
	MAX-ACCESS	read-only
	STATUS		current
	DESCRIPTION	"The Index into the Operational State table."
	REFERENCE "'DMTF|Operational State|003' 1"
	::= { dmtfOperationalStateEntry 1 }

deviceGroupIndex OBJECT-TYPE
	SYNTAX		DmiInteger
	MAX-ACCESS	read-only
	STATUS		current
	DESCRIPTION	"The group ID of the group referencing this instance."
	REFERENCE "'DMTF|Operational State|003' 2"
	::= { dmtfOperationalStateEntry 2 }

operationalStatus OBJECT-TYPE
	SYNTAX		INTEGER {
		other(1),
		unknown(2),
		enabled(3),
		disabled(4),
		notApplicable(5)
	}
	MAX-ACCESS	read-only
	STATUS		current
	DESCRIPTION	"The operational status of the Device Group instance."
	REFERENCE "'DMTF|Operational State|003' 3"
	::= { dmtfOperationalStateEntry 3 }

usageState OBJECT-TYPE
	SYNTAX		INTEGER {
		other(1),
		unknown(2),
		idle(3),
		active(4),
		busy(5),
		notApplicable(6)
	}
	MAX-ACCESS	read-only
	STATUS		current
	DESCRIPTION	"The usage state of the Device Group instance."
	REFERENCE "'DMTF|Operational State|003' 4"
	::= { dmtfOperationalStateEntry 4 }

availabilityStatus OBJECT-TYPE
	SYNTAX		INTEGER {
		other(1),
		unknown(2),
		running(3),
		warning(4),
		inTest(5),
		notApplicable(6),
		powerOff(7),
		offLine-1(8),
		offDuty(9),
		degraded(10),
		notInstalled(11),
		installError(12),
		powerSave(13)
	}
	MAX-ACCESS	read-only
	STATUS		current
	DESCRIPTION	"The availability status of the Device Group instance."
	REFERENCE "'DMTF|Operational State|003' 5"
	::= { dmtfOperationalStateEntry 5 }

administrativeState OBJECT-TYPE
	SYNTAX		INTEGER {
		other(1),
		unknown(2),
		locked(3),
		unlocked(4),
		notApplicable(5),
		shuttingDown(6)
	}
	MAX-ACCESS	read-only
	STATUS		current
	DESCRIPTION	"The administrative state of the Device Group instance."
	REFERENCE "'DMTF|Operational State|003' 6"
	::= { dmtfOperationalStateEntry 6 }

fatalErrorCount OBJECT-TYPE
	SYNTAX		DmiCounter
	MAX-ACCESS	read-only
	STATUS		current
	DESCRIPTION	"The accumulated Fatal or Non-recoverable error count for
this Device Group instance."
	REFERENCE "'DMTF|Operational State|003' 7"
	::= { dmtfOperationalStateEntry 7 }

majorErrorCount OBJECT-TYPE
	SYNTAX		DmiCounter
	MAX-ACCESS	read-only
	STATUS		current
	DESCRIPTION	"The accumulated Major or Critical error count for this Device
Group instance."
	REFERENCE "'DMTF|Operational State|003' 8"
	::= { dmtfOperationalStateEntry 8 }

warningErrorCount OBJECT-TYPE
	SYNTAX		DmiCounter
	MAX-ACCESS	read-only
	STATUS		current
	DESCRIPTION	"The accumulated Warning or Non-Critical error count for this
Device Group instance."
	REFERENCE "'DMTF|Operational State|003' 9"
	::= { dmtfOperationalStateEntry 9 }

currentErrorStatus OBJECT-TYPE
	SYNTAX		INTEGER {
		other(1),
		unknown(2),
		oK(3),
		nonCritical(4),
		critical(5),
		nonRecoverable(6)
	}
	MAX-ACCESS	read-only
	STATUS		current
	DESCRIPTION	"This attribute presents the current error status for this
Device Group instance.  The most critical error status in effect should be
presented. I.e. if a part of the Device Group instance is 'Critical', while
other status is 'Non-critical' then the status'Critical' should be reported."
	REFERENCE "'DMTF|Operational State|003' 10"
	::= { dmtfOperationalStateEntry 10 }

devicePredictedFailureStatus OBJECT-TYPE
	SYNTAX		INTEGER {
		other(1),
		unknown(2),
		notSupportedByThisDevice(3),
		noFailurePredictedByTheDevice(4),
		deviceFailurePredictedByTheDevice(5),
		mediaFailurePredictedByTheDevice(6)
	}
	MAX-ACCESS	read-only
	STATUS		current
	DESCRIPTION	"Enumeration describing the current Device Predicted Failure
Status (e.g.: the S.M.A.R.T. status of the device)."
	REFERENCE "'DMTF|Operational State|003' 11"
	::= { dmtfOperationalStateEntry 11 }

SdmtfOutOfBandRemoteAccess ::= SEQUENCE {
	outOfBandFunctionManufacturerName	DmiString,
	outOfBandFunctionDescriptionString	DmiString,
	outboundOutOfBandConnectionEnabled	DmiInteger,
	inboundOutOfBandConnectionEnabled	DmiInteger
}

dmtfOutOfBandRemoteAccessTable OBJECT-TYPE
	SYNTAX		SEQUENCE OF SdmtfOutOfBandRemoteAccess
	MAX-ACCESS	not-accessible
	STATUS		current
	DESCRIPTION	"This defines the attributes and policy settings of a special
hardware facility called Out-of-Band Remote Access, which may be used to
gain remote accessto a hardware system when the operating system is not availabl
 due to power down status, hardware failures, or boot failures."
	::= { dmtfSystemsMIF 60 }

dmtfOutOfBandRemoteAccessEntry OBJECT-TYPE
	SYNTAX		SdmtfOutOfBandRemoteAccess
	MAX-ACCESS	not-accessible
	STATUS		current
	DESCRIPTION	"This defines the attributes and policy settings of a special
hardware facility called Out-of-Band Remote Access, which may be used to
gain remote accessto a hardware system when the operating system is not availabl
 due to power down status, hardware failures, or boot failures."
	INDEX		{ DmiCompId,DmiGroupId }
	::= { dmtfOutOfBandRemoteAccessTable 1 }


outOfBandFunctionManufacturerName OBJECT-TYPE
	SYNTAX		DmiString
	MAX-ACCESS	read-only
	STATUS		current
	DESCRIPTION	"This string attribute provides the name of the manufacturer
of the out-of-band access facility in the system. This may be the name of
the system manufacturer or the name of the add-in that carries the out-of-band
function."
	REFERENCE "'DMTF|Out-of-Band Remote Access|001' 1"
	::= { dmtfOutOfBandRemoteAccessEntry 1 }

outOfBandFunctionDescriptionString OBJECT-TYPE
	SYNTAX		DmiString
	MAX-ACCESS	read-only
	STATUS		current
	DESCRIPTION	"This is a user-settable string that contains a description
of the out-of-band remote access facility in the system."
	REFERENCE "'DMTF|Out-of-Band Remote Access|001' 2"
	::= { dmtfOutOfBandRemoteAccessEntry 2 }

outboundOutOfBandConnectionEnabled OBJECT-TYPE
	SYNTAX		INTEGER {
		false(0),
		true(1),
		unknown(2)
	}
	MAX-ACCESS	read-write
	STATUS		current
	DESCRIPTION	"Defines whether the Out-of-Band Remote Access facility is
allowed to initiate outbound connections to contact an alert management facility
when critical conditions occur."
	REFERENCE "'DMTF|Out-of-Band Remote Access|001' 3"
	::= { dmtfOutOfBandRemoteAccessEntry 3 }

inboundOutOfBandConnectionEnabled OBJECT-TYPE
	SYNTAX		INTEGER {
		false(0),
		true(1),
		unknown(2)
	}
	MAX-ACCESS	read-write
	STATUS		current
	DESCRIPTION	"Defines whether the Out-of-Band Remote Access facility is
allowed to receive incoming connections for the purpose of remote operations
or problem management."
	REFERENCE "'DMTF|Out-of-Band Remote Access|001' 4"
	::= { dmtfOutOfBandRemoteAccessEntry 4 }

SdmtfParallelPorts ::= SEQUENCE {
	dmtfParallelPortsState INTEGER,
	parallelPortIndex	DmiInteger,
	parallelBaseIOAddress	Dmi-Integer64,
	iRQUsed	DmiInteger,
	logicalName	DmiString,
	connectorType	DmiInteger,
	connectorPinout	DmiInteger,
	dMASupport	DmiInteger,
	parallelPortCapabilities	DmiInteger,
	operationalGroupIndex	DmiInteger,
	parallelPortSecuritySettings	DmiInteger
}

dmtfParallelPortsTable OBJECT-TYPE
	SYNTAX		SEQUENCE OF SdmtfParallelPorts
	MAX-ACCESS	not-accessible
	STATUS		current
	DESCRIPTION	"This group defines the attributes for parallel ports in this
system."
	::= { dmtfSystemsMIF 10 }

dmtfParallelPortsEntry OBJECT-TYPE
	SYNTAX		SdmtfParallelPorts
	MAX-ACCESS	not-accessible
	STATUS		current
	DESCRIPTION	"This group defines the attributes for parallel ports in this
system."
	INDEX		{ DmiCompId,DmiGroupId, parallelPortIndex }
	::= { dmtfParallelPortsTable 1 }


dmtfParallelPortsState OBJECT-TYPE
	SYNTAX		INTEGER {
		active(1),
		notInService(2),
		notReady(3),
		createAndGo(4),
		createAndWait(5),
		destroy(6)
	}
	MAX-ACCESS	read-write
	STATUS		current
	REFERENCE "'DMTF|Parallel Ports|003' 0"
	::= { dmtfParallelPortsEntry 0 }

parallelPortIndex OBJECT-TYPE
	SYNTAX		DmiInteger
	MAX-ACCESS	read-only
	STATUS		current
	DESCRIPTION	"An index into the parallel ports table."
	REFERENCE "'DMTF|Parallel Ports|003' 1"
	::= { dmtfParallelPortsEntry 1 }

parallelBaseIOAddress OBJECT-TYPE
	SYNTAX		Dmi-Integer64
	MAX-ACCESS	read-only
	STATUS		current
	DESCRIPTION	"Base I/O address for this parallel port."
	REFERENCE "'DMTF|Parallel Ports|003' 2"
	::= { dmtfParallelPortsEntry 2 }

iRQUsed OBJECT-TYPE
	SYNTAX		DmiInteger
	MAX-ACCESS	read-only
	STATUS		current
	DESCRIPTION	"IRQ number that is being used by this parallel port."
	REFERENCE "'DMTF|Parallel Ports|003' 3"
	::= { dmtfParallelPortsEntry 3 }

logicalName OBJECT-TYPE
	SYNTAX		DmiString
	MAX-ACCESS	read-only
	STATUS		current
	DESCRIPTION	"The logical name of the I/O device on this parallel port,
under this operating environment."
	REFERENCE "'DMTF|Parallel Ports|003' 4"
	::= { dmtfParallelPortsEntry 4 }

connectorType OBJECT-TYPE
	SYNTAX		INTEGER {
		other(1),
		unknown(2),
		dB25Female(3),
		dB25Male(4),
		centronics(5),
		miniCentronics(6),
		proprietary(7),
		centronics14(160),
		dB36Female(161),
		miniCentronics20(162)
	}
	MAX-ACCESS	read-only
	STATUS		current
	DESCRIPTION	"The connector used to interface with the I/O device on this
parallel port."
	REFERENCE "'DMTF|Parallel Ports|003' 5"
	::= { dmtfParallelPortsEntry 5 }

connectorPinout OBJECT-TYPE
	SYNTAX		INTEGER {
		other(1),
		unknown(2),
		xTAT(3),
		pS2(4),
		iEEE1284(5),
		proprietary(6),
		pC98(160),
		pC98Hireso(161),
		pCH98(162),
		pC98Note(163),
		pC98Full(164)
	}
	MAX-ACCESS	read-only
	STATUS		current
	DESCRIPTION	"The pinout used by the I/O device on this parallel port."
	REFERENCE "'DMTF|Parallel Ports|003' 6"
	::= { dmtfParallelPortsEntry 6 }

dMASupport OBJECT-TYPE
	SYNTAX		INTEGER {
		false(0),
		true(1)
	}
	MAX-ACCESS	read-only
	STATUS		current
	DESCRIPTION	"If true, DMA is supported."
	REFERENCE "'DMTF|Parallel Ports|003' 7"
	::= { dmtfParallelPortsEntry 7 }

parallelPortCapabilities OBJECT-TYPE
	SYNTAX		DmiInteger
	MAX-ACCESS	read-only
	STATUS		current
	DESCRIPTION	"Capabilities of this parallel port. This is a bit field mask
with the bits defined as follows: 
 Bit 0 (2^0) set = XT/AT compatible, 

Bit 1 (2^1) set = PS/2 compatible, 
 Bit 2 (2^2) set = ECP, 
 Bit 3 (2^3)
set = EPP, 
 Bit 4 (2^4) set = PC-98, 
 Bit 5 (2^5) set = PC-98-Hireso, 

Bit 6 (2^6) set = PC-H98"
	REFERENCE "'DMTF|Parallel Ports|003' 8"
	::= { dmtfParallelPortsEntry 8 }

operationalGroupIndex OBJECT-TYPE
	SYNTAX		DmiInteger
	MAX-ACCESS	read-only
	STATUS		current
	DESCRIPTION	"The index into the Operational State Table for this device."
	REFERENCE "'DMTF|Parallel Ports|003' 9"
	::= { dmtfParallelPortsEntry 9 }

parallelPortSecuritySettings OBJECT-TYPE
	SYNTAX		INTEGER {
		other(1),
		unknown(2),
		none(3),
		externalInterfaceLockedOut(4),
		externalInterfaceEnabled(5),
		bootBypass(6)
	}
	MAX-ACCESS	read-only
	STATUS		current
	DESCRIPTION	"Attribute describing the current hardware security settings
on this device"
	REFERENCE "'DMTF|Parallel Ports|003' 10"
	::= { dmtfParallelPortsEntry 10 }

SdmtfPartition ::= SEQUENCE {
	dmtfPartitionState INTEGER,
	partitionIndex	DmiInteger,
	partitionName	DmiString,
	partitionSize	Dmi-Integer64,
	freeSpace	Dmi-Integer64,
	partitionLabel	DmiOctetstring,
	fileSystem	DmiInteger,
	compressed	DmiInteger,
	encrypted	DmiInteger,
	numberOfDisksOccupied	DmiInteger
}

dmtfPartitionTable OBJECT-TYPE
	SYNTAX		SEQUENCE OF SdmtfPartition
	MAX-ACCESS	not-accessible
	STATUS		current
	DESCRIPTION	"This group describes the partitions on particular disks."
	::= { dmtfSystemsMIF 24 }

dmtfPartitionEntry OBJECT-TYPE
	SYNTAX		SdmtfPartition
	MAX-ACCESS	not-accessible
	STATUS		current
	DESCRIPTION	"This group describes the partitions on particular disks."
	INDEX		{ DmiCompId,DmiGroupId, partitionIndex }
	::= { dmtfPartitionTable 1 }


dmtfPartitionState OBJECT-TYPE
	SYNTAX		INTEGER {
		active(1),
		notInService(2),
		notReady(3),
		createAndGo(4),
		createAndWait(5),
		destroy(6)
	}
	MAX-ACCESS	read-write
	STATUS		current
	REFERENCE "'DMTF|Partition|002' 0"
	::= { dmtfPartitionEntry 0 }

partitionIndex OBJECT-TYPE
	SYNTAX		DmiInteger
	MAX-ACCESS	read-only
	STATUS		current
	DESCRIPTION	"The index into the partition table."
	REFERENCE "'DMTF|Partition|002' 1"
	::= { dmtfPartitionEntry 1 }

partitionName OBJECT-TYPE
	SYNTAX		DmiString
	MAX-ACCESS	read-only
	STATUS		current
	DESCRIPTION	"The name used by the system to identify the partition. This
is normally the drive letter."
	REFERENCE "'DMTF|Partition|002' 2"
	::= { dmtfPartitionEntry 2 }

partitionSize OBJECT-TYPE
	SYNTAX		Dmi-Integer64
	MAX-ACCESS	read-only
	STATUS		current
	DESCRIPTION	"The size of this partition in kilobytes."
	REFERENCE "'DMTF|Partition|002' 3"
	::= { dmtfPartitionEntry 3 }

freeSpace OBJECT-TYPE
	SYNTAX		Dmi-Integer64
	MAX-ACCESS	read-only
	STATUS		current
	DESCRIPTION	"The number of free kilobytes on this partition."
	REFERENCE "'DMTF|Partition|002' 4"
	::= { dmtfPartitionEntry 4 }

partitionLabel OBJECT-TYPE
	SYNTAX		DmiOctetstring
	MAX-ACCESS	read-only
	STATUS		current
	DESCRIPTION	"The partition label or the unique volume label field for
this physical volume. (For DOS, this is the volume label plus the 32 bit
Volume ID field if available.)"
	REFERENCE "'DMTF|Partition|002' 5"
	::= { dmtfPartitionEntry 5 }

fileSystem OBJECT-TYPE
	SYNTAX		INTEGER {
		other(1),
		unknown(2),
		fAT(3),
		hPFS(4),
		nTFS(5),
		oFS(6),
		mFS(7),
		hFS(8),
		vXFS(9),
		sFS(10),
		s5(11),
		s52K(12),
		uFS(13),
		fFS(14),
		netware286(15),
		netware386(16),
		fAT32(17)
	}
	MAX-ACCESS	read-only
	STATUS		current
	DESCRIPTION	"The file system associated with this partition."
	REFERENCE "'DMTF|Partition|002' 6"
	::= { dmtfPartitionEntry 6 }

compressed OBJECT-TYPE
	SYNTAX		INTEGER {
		false(0),
		true(1)
	}
	MAX-ACCESS	read-only
	STATUS		current
	DESCRIPTION	"If true, this partition is compressed."
	REFERENCE "'DMTF|Partition|002' 7"
	::= { dmtfPartitionEntry 7 }

encrypted OBJECT-TYPE
	SYNTAX		INTEGER {
		false(0),
		true(1)
	}
	MAX-ACCESS	read-only
	STATUS		current
	DESCRIPTION	"If true, this partition is encrypted."
	REFERENCE "'DMTF|Partition|002' 8"
	::= { dmtfPartitionEntry 8 }

numberOfDisksOccupied OBJECT-TYPE
	SYNTAX		DmiInteger
	MAX-ACCESS	read-only
	STATUS		current
	DESCRIPTION	"The number of disks this partition occupies."
	REFERENCE "'DMTF|Partition|002' 9"
	::= { dmtfPartitionEntry 9 }

SdmtfPhysicalContainerGlobalTable ::= SEQUENCE {
	dmtfPhysicalContainerGlobalTableState INTEGER,
	containerOrChassisType	DmiInteger,
	assetTag	DmiString,
	chassisLockPresent	DmiInteger,
	bootupState	DmiInteger,
	powerState	DmiInteger,
	thermalState	DmiInteger,
	fRUGroupIndex	DmiInteger,
	operationalGroupIndex	DmiInteger,
	containerIndex	DmiInteger,
	containerName	DmiString,
	containerLocation	DmiString,
	containerSecurityStatus	DmiInteger
}

dmtfPhysicalContainerGlobalTable OBJECT-TYPE
	SYNTAX		SEQUENCE OF SdmtfPhysicalContainerGlobalTable
	MAX-ACCESS	not-accessible
	STATUS		current
	DESCRIPTION	"This group of attributes describes the fields in a row ofthe
Physical Container Global Table. This table lists all of the containers (e.g.
chassis, sub-chassis, etc.) included within the component whose structure
is being described"
	::= { dmtfSystemsMIF 63 }

dmtfPhysicalContainerGlobalEntry OBJECT-TYPE
	SYNTAX		SdmtfPhysicalContainerGlobalTable
	MAX-ACCESS	not-accessible
	STATUS		current
	DESCRIPTION	"This group of attributes describes the fields in a row ofthe
Physical Container Global Table. This table lists all of the containers (e.g.
chassis, sub-chassis, etc.) included within the component whose structure
is being described"
	INDEX		{ DmiCompId,DmiGroupId, containerIndex }
	::= { dmtfPhysicalContainerGlobalTable 1 }


dmtfPhysicalContainerGlobalTableState OBJECT-TYPE
	SYNTAX		INTEGER {
		active(1),
		notInService(2),
		notReady(3),
		createAndGo(4),
		createAndWait(5),
		destroy(6)
	}
	MAX-ACCESS	read-write
	STATUS		current
	REFERENCE "'DMTF|Physical Container Global Table|002' 0"
	::= { dmtfPhysicalContainerGlobalEntry 0 }

containerOrChassisType OBJECT-TYPE
	SYNTAX		INTEGER {
		other(1),
		unknown(2),
		desktop(3),
		lowProfileDesktop(4),
		pizzaBox(5),
		miniTower(6),
		tower(7),
		portable(8),
		lapTop(9),
		notebook(10),
		handHeld(11),
		dockingStation(12),
		allInOne(13),
		subNotebook(14),
		spaceSaving(15),
		lunchBox(16),
		mainSystemChassis(17),
		expansionChassis(18),
		subChassis(19),
		busExpansionChassis(20),
		peripheralChassis(21),
		rAIDChassis(22),
		rackMountChassis(23),
		sealedCasePC(24)
	}
	MAX-ACCESS	read-only
	STATUS		current
	DESCRIPTION	"The type of container or chassis."
	REFERENCE "'DMTF|Physical Container Global Table|002' 1"
	::= { dmtfPhysicalContainerGlobalEntry 1 }

assetTag OBJECT-TYPE
	SYNTAX		DmiString
	MAX-ACCESS	read-write
	STATUS		current
	DESCRIPTION	"The Container asset tag string. This asset tag string is
writeable by the system administrator."
	REFERENCE "'DMTF|Physical Container Global Table|002' 2"
	::= { dmtfPhysicalContainerGlobalEntry 2 }

chassisLockPresent OBJECT-TYPE
	SYNTAX		INTEGER {
		false(0),
		true(1)
	}
	MAX-ACCESS	read-only
	STATUS		current
	DESCRIPTION	"If true, a chassis lock is present on the Container."
	REFERENCE "'DMTF|Physical Container Global Table|002' 3"
	::= { dmtfPhysicalContainerGlobalEntry 3 }

bootupState OBJECT-TYPE
	SYNTAX		INTEGER {
		other(1),
		unknown(2),
		oK(3),
		warning(4),
		critical(5),
		nonRecoverable-1(6)
	}
	MAX-ACCESS	read-only
	STATUS		current
	DESCRIPTION	"The current state of this system when it booted."
	REFERENCE "'DMTF|Physical Container Global Table|002' 4"
	::= { dmtfPhysicalContainerGlobalEntry 4 }

powerState OBJECT-TYPE
	SYNTAX		INTEGER {
		other(1),
		unknown(2),
		oK(3),
		warning(4),
		critical(5),
		nonRecoverable(6)
	}
	MAX-ACCESS	read-only
	STATUS		current
	DESCRIPTION	"The current state of the power supply or battery(s) for this
system."
	REFERENCE "'DMTF|Physical Container Global Table|002' 5"
	::= { dmtfPhysicalContainerGlobalEntry 5 }

thermalState OBJECT-TYPE
	SYNTAX		INTEGER {
		other(1),
		unknown(2),
		oK(3),
		warning(4),
		critical(5),
		nonRecoverable(6)
	}
	MAX-ACCESS	read-only
	STATUS		current
	DESCRIPTION	"The current thermal state of this Container."
	REFERENCE "'DMTF|Physical Container Global Table|002' 6"
	::= { dmtfPhysicalContainerGlobalEntry 6 }

fRUGroupIndex OBJECT-TYPE
	SYNTAX		DmiInteger
	MAX-ACCESS	read-only
	STATUS		current
	DESCRIPTION	"If this is a Field Replaceable Unit or if it is part of another
FRU, this provides an index into the FRU table; 'value = -1' indicates that
the group is not a FRU."
	REFERENCE "'DMTF|Physical Container Global Table|002' 7"
	::= { dmtfPhysicalContainerGlobalEntry 7 }

operationalGroupIndex OBJECT-TYPE
	SYNTAX		DmiInteger
	MAX-ACCESS	read-only
	STATUS		current
	DESCRIPTION	"The index into the Operational State table for this device
if applicable."
	REFERENCE "'DMTF|Physical Container Global Table|002' 8"
	::= { dmtfPhysicalContainerGlobalEntry 8 }

containerIndex OBJECT-TYPE
	SYNTAX		DmiInteger
	MAX-ACCESS	read-only
	STATUS		current
	DESCRIPTION	"A unique index for the Physical Container in Physical Container
Global Table."
	REFERENCE "'DMTF|Physical Container Global Table|002' 9"
	::= { dmtfPhysicalContainerGlobalEntry 9 }

containerName OBJECT-TYPE
	SYNTAX		DmiString
	MAX-ACCESS	read-write
	STATUS		current
	DESCRIPTION	"This is any 64-octet long name that the user or system administr
tor wishes to give this specific physical container."
	REFERENCE "'DMTF|Physical Container Global Table|002' 10"
	::= { dmtfPhysicalContainerGlobalEntry 10 }

containerLocation OBJECT-TYPE
	SYNTAX		DmiString
	MAX-ACCESS	read-write
	STATUS		current
	DESCRIPTION	"This attribute is a string name for the location of the containe
.  This attribute is Read-Write and may be set to any appropriate value by
the user. The string may be 128 octets long."
	REFERENCE "'DMTF|Physical Container Global Table|002' 11"
	::= { dmtfPhysicalContainerGlobalEntry 11 }

containerSecurityStatus OBJECT-TYPE
	SYNTAX		INTEGER {
		other(1),
		unknown(2),
		noSecurityBreachDetected(3),
		containerSecurityBreachAttempted(4),
		containerSecurityBreached(5)
	}
	MAX-ACCESS	read-only
	STATUS		current
	DESCRIPTION	"This attribute describes whether the Container is physically
secure or not. This includes the state of the door lock, or the boot devices
or the keyboard or mouse."
	REFERENCE "'DMTF|Physical Container Global Table|002' 12"
	::= { dmtfPhysicalContainerGlobalEntry 12 }

SdmtfPhysicalExpansionSiteTable ::= SEQUENCE {
	dmtfPhysicalExpansionSiteTableState INTEGER,
	expansionSiteIndex	DmiInteger,
	expansionSiteType	DmiInteger,
	virtualExpansionSite	DmiInteger,
	expansionSiteName	DmiString,
	expansionSiteDescription	DmiString,
	expansionSiteCurrentlyOccupied	DmiInteger,
	expansionSiteInsertionProperties	DmiInteger,
	expansionSitePropertiesTableReference	DmiString
}

dmtfPhysicalExpansionSiteTable OBJECT-TYPE
	SYNTAX		SEQUENCE OF SdmtfPhysicalExpansionSiteTable
	MAX-ACCESS	not-accessible
	STATUS		current
	DESCRIPTION	"This global table describes all of the expansion sites in
this expandable component in the system.  The unique index of each expansion
site is the key into this table. Card/Bus slots, disk bays, hot-plug power
supply bays, etc., are all examples of expansion sites."
	::= { dmtfSystemsMIF 65 }

dmtfPhysicalExpansionSiteEntry OBJECT-TYPE
	SYNTAX		SdmtfPhysicalExpansionSiteTable
	MAX-ACCESS	not-accessible
	STATUS		current
	DESCRIPTION	"This global table describes all of the expansion sites in
this expandable component in the system.  The unique index of each expansion
site is the key into this table. Card/Bus slots, disk bays, hot-plug power
supply bays, etc., are all examples of expansion sites."
	INDEX		{ DmiCompId,DmiGroupId, expansionSiteIndex }
	::= { dmtfPhysicalExpansionSiteTable 1 }


dmtfPhysicalExpansionSiteTableState OBJECT-TYPE
	SYNTAX		INTEGER {
		active(1),
		notInService(2),
		notReady(3),
		createAndGo(4),
		createAndWait(5),
		destroy(6)
	}
	MAX-ACCESS	read-write
	STATUS		current
	REFERENCE "'DMTF|Physical Expansion Site Table|002' 0"
	::= { dmtfPhysicalExpansionSiteEntry 0 }

expansionSiteIndex OBJECT-TYPE
	SYNTAX		DmiInteger
	MAX-ACCESS	read-only
	STATUS		current
	DESCRIPTION	"The unique integer index into Physical Expansion Sites table."
	REFERENCE "'DMTF|Physical Expansion Site Table|002' 1"
	::= { dmtfPhysicalExpansionSiteEntry 1 }

expansionSiteType OBJECT-TYPE
	SYNTAX		INTEGER {
		other(1),
		unknown(2),
		busSlot(3),
		driveBay(4),
		powerUnitBay(5),
		subchassisSlot(6),
		pCMCIASlot(7),
		deviceBay(8)
	}
	MAX-ACCESS	read-only
	STATUS		current
	DESCRIPTION	"This attribute describes the type of expansion site that
is being defined by this entry in the Physical Expansion Sites Table."
	REFERENCE "'DMTF|Physical Expansion Site Table|002' 2"
	::= { dmtfPhysicalExpansionSiteEntry 2 }

virtualExpansionSite OBJECT-TYPE
	SYNTAX		INTEGER {
		false(0),
		true(1)
	}
	MAX-ACCESS	read-only
	STATUS		current
	DESCRIPTION	"This attribute indicates whether this is a 'virtual' expansion
site or not. A virtual expansion site is one that is permanently occupied
because of the level of integration of an expandable component. An example
of a virtual expansion site is an I/O bus load taken up by a LAN controller
that is integrated onto a motherboard."
	REFERENCE "'DMTF|Physical Expansion Site Table|002' 3"
	::= { dmtfPhysicalExpansionSiteEntry 3 }

expansionSiteName OBJECT-TYPE
	SYNTAX		DmiString
	MAX-ACCESS	read-only
	STATUS		current
	DESCRIPTION	"Name chosen by the vendor of this component to name this
particular expansion site within this component, e.g. 'Slot 6', 'DriveBay
1'."
	REFERENCE "'DMTF|Physical Expansion Site Table|002' 4"
	::= { dmtfPhysicalExpansionSiteEntry 4 }

expansionSiteDescription OBJECT-TYPE
	SYNTAX		DmiString
	MAX-ACCESS	read-only
	STATUS		current
	DESCRIPTION	"This is a vendor-settable string that describes the expandable
site in whatever way is desired."
	REFERENCE "'DMTF|Physical Expansion Site Table|002' 5"
	::= { dmtfPhysicalExpansionSiteEntry 5 }

expansionSiteCurrentlyOccupied OBJECT-TYPE
	SYNTAX		INTEGER {
		false(0),
		true(1)
	}
	MAX-ACCESS	read-only
	STATUS		current
	DESCRIPTION	"A boolean whose value indicates whether this Expansion Site
is currently occupied or not."
	REFERENCE "'DMTF|Physical Expansion Site Table|002' 6"
	::= { dmtfPhysicalExpansionSiteEntry 6 }

expansionSiteInsertionProperties OBJECT-TYPE
	SYNTAX		INTEGER {
		other(1),
		unknown(2),
		hot(3),
		warm(4),
		cold(5)
	}
	MAX-ACCESS	read-only
	STATUS		current
	DESCRIPTION	"This attribute indicates the insertion properties of this
expansion site (Hot, Warm, Cold) which describes if the site must be powered
OFF before a connection may be made.  An example of a hot insertion expansion
site would be a hot-plug power supply bay while a bus slot like PCI is a
cold insertion expansion site.  Warm insertion allows power to be ON but
no activity present."
	REFERENCE "'DMTF|Physical Expansion Site Table|002' 7"
	::= { dmtfPhysicalExpansionSiteEntry 7 }

expansionSitePropertiesTableReference OBJECT-TYPE
	SYNTAX		DmiString
	MAX-ACCESS	read-only
	STATUS		current
	DESCRIPTION	"Reference to Expansion Site Properties Table"
	REFERENCE "'DMTF|Physical Expansion Site Table|002' 8"
	::= { dmtfPhysicalExpansionSiteEntry 8 }

SdmtfPhysicalMemoryArray ::= SEQUENCE {
	dmtfPhysicalMemoryArrayState INTEGER,
	memoryArrayTableIndex	DmiInteger,
	memoryArrayLocation	DmiInteger,
	memoryArrayUse	DmiInteger,
	maximumMemoryCapacity	DmiInteger,
	numberOfMemoryDeviceSockets	DmiInteger,
	numberOfMemoryDeviceSocketsUsed	DmiInteger,
	memoryErrorCorrection	DmiInteger,
	arrayErrorType	DmiInteger,
	lastErrorUpdate	DmiInteger,
	errorOperation	DmiInteger,
	errorDataSize	DmiInteger,
	errorData	DmiOctetstring,
	vendorSyndrome	DmiOctetstring,
	errorAddress	Dmi-Integer64,
	errorResolution	DmiInteger,
	fRUGroupIndex	DmiInteger,
	operationalGroupIndex	DmiInteger
}

dmtfPhysicalMemoryArrayTable OBJECT-TYPE
	SYNTAX		SEQUENCE OF SdmtfPhysicalMemoryArray
	MAX-ACCESS	not-accessible
	STATUS		current
	DESCRIPTION	"This group represents an array of physical memory as a collectio
 of one or more Memory Devices associated in sets and partitions."
	::= { dmtfSystemsMIF 33 }

dmtfPhysicalMemoryArrayEntry OBJECT-TYPE
	SYNTAX		SdmtfPhysicalMemoryArray
	MAX-ACCESS	not-accessible
	STATUS		current
	DESCRIPTION	"This group represents an array of physical memory as a collectio
 of one or more Memory Devices associated in sets and partitions."
	INDEX		{ DmiCompId,DmiGroupId, memoryArrayTableIndex }
	::= { dmtfPhysicalMemoryArrayTable 1 }


dmtfPhysicalMemoryArrayState OBJECT-TYPE
	SYNTAX		INTEGER {
		active(1),
		notInService(2),
		notReady(3),
		createAndGo(4),
		createAndWait(5),
		destroy(6)
	}
	MAX-ACCESS	read-write
	STATUS		current
	REFERENCE "'DMTF|Physical Memory Array|001' 0"
	::= { dmtfPhysicalMemoryArrayEntry 0 }

memoryArrayTableIndex OBJECT-TYPE
	SYNTAX		DmiInteger
	MAX-ACCESS	read-only
	STATUS		current
	DESCRIPTION	"A unique number that identifies this row."
	REFERENCE "'DMTF|Physical Memory Array|001' 1"
	::= { dmtfPhysicalMemoryArrayEntry 1 }

memoryArrayLocation OBJECT-TYPE
	SYNTAX		INTEGER {
		other(1),
		unknown(2),
		systemBoardOrMotherboard(3),
		iSAAddOnCard(4),
		eISAAddOnCard(5),
		pCIAddOnCard(6),
		mCAAddOnCard(7),
		pCMCIAAddOnCard(8),
		proprietaryAddOnCard(9),
		nuBus(16),
		pC98C20AddOnCard(160),
		pC98C24AddOnCard(161),
		pC98EAddOnCard(162),
		pC98LocalBusAddOnCard(163),
		pC98CardSlotAddOnCard(164)
	}
	MAX-ACCESS	read-only
	STATUS		current
	DESCRIPTION	"The physical location of the Memory Array, whether on the
system board or an add-on board."
	REFERENCE "'DMTF|Physical Memory Array|001' 2"
	::= { dmtfPhysicalMemoryArrayEntry 2 }

memoryArrayUse OBJECT-TYPE
	SYNTAX		INTEGER {
		other(1),
		unknown(2),
		systemMemory(3),
		videoMemory(4),
		flashMemory(5),
		nonVolatileRAM(6),
		cacheMemory(7)
	}
	MAX-ACCESS	read-only
	STATUS		current
	DESCRIPTION	"What this Memory Array is used for."
	REFERENCE "'DMTF|Physical Memory Array|001' 3"
	::= { dmtfPhysicalMemoryArrayEntry 3 }

maximumMemoryCapacity OBJECT-TYPE
	SYNTAX		DmiInteger
	MAX-ACCESS	read-only
	STATUS		current
	DESCRIPTION	"The maximum memory capacity, in kilobytes, on this array.
0x80000000denotes 'unknown'."
	REFERENCE "'DMTF|Physical Memory Array|001' 4"
	::= { dmtfPhysicalMemoryArrayEntry 4 }

numberOfMemoryDeviceSockets OBJECT-TYPE
	SYNTAX		DmiInteger
	MAX-ACCESS	read-only
	STATUS		current
	DESCRIPTION	"The number of SIMM slots or sockets available for Memory
Devices in this array. 0x80000000 denotes 'unknown'. "
	REFERENCE "'DMTF|Physical Memory Array|001' 5"
	::= { dmtfPhysicalMemoryArrayEntry 5 }

numberOfMemoryDeviceSocketsUsed OBJECT-TYPE
	SYNTAX		DmiInteger
	MAX-ACCESS	read-only
	STATUS		current
	DESCRIPTION	"The number of SIMM slots or sockets in use for Memory Devices
in this array. 0x80000000 denotes 'unknown'."
	REFERENCE "'DMTF|Physical Memory Array|001' 6"
	::= { dmtfPhysicalMemoryArrayEntry 6 }

memoryErrorCorrection OBJECT-TYPE
	SYNTAX		INTEGER {
		other(1),
		unknown(2),
		none(3),
		parity(4),
		singleBitECC(5),
		multiBitECC(6),
		cRC(7)
	}
	MAX-ACCESS	read-only
	STATUS		current
	DESCRIPTION	"The main hardware error correction or detection method supported
by this Memory Array."
	REFERENCE "'DMTF|Physical Memory Array|001' 7"
	::= { dmtfPhysicalMemoryArrayEntry 7 }

arrayErrorType OBJECT-TYPE
	SYNTAX		INTEGER {
		other(1),
		unknown(2),
		oK(3),
		badRead(4),
		parityError(5),
		singleBitError(6),
		doubleBitError(7),
		multiBitError(8),
		nibbleError(9),
		checksumError(10),
		cRCError(11),
		correctedSingleBitError(12),
		correctedError(13),
		uncorrectableError(14)
	}
	MAX-ACCESS	read-only
	STATUS		current
	DESCRIPTION	"The type of error that is associated with the current status
reported in Operational State for this Memory Array."
	REFERENCE "'DMTF|Physical Memory Array|001' 8"
	::= { dmtfPhysicalMemoryArrayEntry 8 }

lastErrorUpdate OBJECT-TYPE
	SYNTAX		INTEGER {
		other(1),
		unknown(2),
		noUpdateSinceLastInstrumentationStart(3),
		updatedFromInformationObtainedPriorToInstrumentati(4),
		updatedDuringInstrumentationRunTime(5)
	}
	MAX-ACCESS	read-only
	STATUS		current
	DESCRIPTION	"System state during which last error status was collected."
	REFERENCE "'DMTF|Physical Memory Array|001' 9"
	::= { dmtfPhysicalMemoryArrayEntry 9 }

errorOperation OBJECT-TYPE
	SYNTAX		INTEGER {
		other(1),
		unknown(2),
		read(3),
		write(4),
		partialWrite(5)
	}
	MAX-ACCESS	read-only
	STATUS		current
	DESCRIPTION	"The memory access operation that caused the current error."
	REFERENCE "'DMTF|Physical Memory Array|001' 10"
	::= { dmtfPhysicalMemoryArrayEntry 10 }

errorDataSize OBJECT-TYPE
	SYNTAX		DmiInteger
	MAX-ACCESS	read-only
	STATUS		current
	DESCRIPTION	"The size of the data transfer that caused the error, in bits.
Zero indicates no error, 0x80000000 denotes 'unknown'."
	REFERENCE "'DMTF|Physical Memory Array|001' 11"
	::= { dmtfPhysicalMemoryArrayEntry 11 }

errorData OBJECT-TYPE
	SYNTAX		DmiOctetstring
	MAX-ACCESS	read-only
	STATUS		current
	DESCRIPTION	"Data captured during the erroneous Memory Array access. The
data occupy the first n bytes of the octet string required to hold 'Error
Data Size' bits of the data. Data are stored least-significant byte first."
	REFERENCE "'DMTF|Physical Memory Array|001' 12"
	::= { dmtfPhysicalMemoryArrayEntry 12 }

vendorSyndrome OBJECT-TYPE
	SYNTAX		DmiOctetstring
	MAX-ACCESS	read-only
	STATUS		current
	DESCRIPTION	"Vendor-specific syndrome or CRC data associated with the
erroneous access. "
	REFERENCE "'DMTF|Physical Memory Array|001' 13"
	::= { dmtfPhysicalMemoryArrayEntry 13 }

errorAddress OBJECT-TYPE
	SYNTAX		Dmi-Integer64
	MAX-ACCESS	read-only
	STATUS		current
	DESCRIPTION	"Physical address of the error based on the addressing of
the bus that the Memory Array is connected to. 0x8000 0000 0000 0000 denotes
'unknown'."
	REFERENCE "'DMTF|Physical Memory Array|001' 14"
	::= { dmtfPhysicalMemoryArrayEntry 14 }

errorResolution OBJECT-TYPE
	SYNTAX		DmiInteger
	MAX-ACCESS	read-only
	STATUS		current
	DESCRIPTION	"Range in bytes that the error can be determined to be within,
when an Error Address is given. 0x80000000 denotes 'unknown'."
	REFERENCE "'DMTF|Physical Memory Array|001' 15"
	::= { dmtfPhysicalMemoryArrayEntry 15 }

fRUGroupIndex OBJECT-TYPE
	SYNTAX		DmiInteger
	MAX-ACCESS	read-only
	STATUS		current
	DESCRIPTION	"If this is a Field Replaceable Unit or if it is part of another
FRU, this provides an index into the FRU table; 'value = -1' indicates that
the group is not a FRU."
	REFERENCE "'DMTF|Physical Memory Array|001' 16"
	::= { dmtfPhysicalMemoryArrayEntry 16 }

operationalGroupIndex OBJECT-TYPE
	SYNTAX		DmiInteger
	MAX-ACCESS	read-only
	STATUS		current
	DESCRIPTION	"The index into the Operational State Table for this Memory
Array. The Operational State row is used to hold the overall error count
and error status for this array."
	REFERENCE "'DMTF|Physical Memory Array|001' 17"
	::= { dmtfPhysicalMemoryArrayEntry 17 }

SdmtfPhysicalMemory ::= SEQUENCE {
	dmtfPhysicalMemoryState INTEGER,
	physicalMemoryIndex	DmiInteger,
	physicalMemoryLocation	DmiInteger,
	memoryStartingAddress	Dmi-Integer64,
	memoryEndingAddress	Dmi-Integer64,
	memoryUsage	DmiInteger,
	maximumMemoryCapacity	DmiInteger,
	numberOfSIMMSlots	DmiInteger,
	numberOfSIMMSlotsUsed	DmiInteger,
	memorySpeed	DmiInteger,
	memoryErrorCorrection	DmiInteger,
	fRUGroupIndex	DmiInteger,
	operationalGroupIndex	DmiInteger,
	maximumMemoryCapacityFractionalPart	DmiInteger
}

dmtfPhysicalMemoryTable OBJECT-TYPE
	SYNTAX		SEQUENCE OF SdmtfPhysicalMemory
	MAX-ACCESS	not-accessible
	STATUS		current
	DESCRIPTION	"The physical attributes for system memory and any add-on
memory installed in this system."
	::= { dmtfSystemsMIF 7 }

dmtfPhysicalMemoryEntry OBJECT-TYPE
	SYNTAX		SdmtfPhysicalMemory
	MAX-ACCESS	not-accessible
	STATUS		current
	DESCRIPTION	"The physical attributes for system memory and any add-on
memory installed in this system."
	INDEX		{ DmiCompId,DmiGroupId, physicalMemoryIndex }
	::= { dmtfPhysicalMemoryTable 1 }


dmtfPhysicalMemoryState OBJECT-TYPE
	SYNTAX		INTEGER {
		active(1),
		notInService(2),
		notReady(3),
		createAndGo(4),
		createAndWait(5),
		destroy(6)
	}
	MAX-ACCESS	read-write
	STATUS		current
	REFERENCE "'DMTF|Physical Memory|002' 0"
	::= { dmtfPhysicalMemoryEntry 0 }

physicalMemoryIndex OBJECT-TYPE
	SYNTAX		DmiInteger
	MAX-ACCESS	read-only
	STATUS		current
	DESCRIPTION	"An index into the physical memory table."
	REFERENCE "'DMTF|Physical Memory|002' 1"
	::= { dmtfPhysicalMemoryEntry 1 }

physicalMemoryLocation OBJECT-TYPE
	SYNTAX		INTEGER {
		other(1),
		unknown(2),
		systemBoardOrMotherboard(3),
		iSAAddOnCard(4),
		eISAAddOnCard(5),
		pCIAddOnCard(6),
		mCAAddOnCard(7),
		pCMCIAAddOnCard(8),
		proprietaryAddOnCard(9),
		nuBus(16),
		pC98C20AddOnCard(160),
		pC98C24AddOnCard(161),
		pC98EAddOnCard(162),
		pC98LocalBusAddOnCard(163),
		pC98CardSlotAddOnCard(164)
	}
	MAX-ACCESS	read-only
	STATUS		current
	DESCRIPTION	"The location of the memory modules, whether on the system
board or an add-on board."
	REFERENCE "'DMTF|Physical Memory|002' 2"
	::= { dmtfPhysicalMemoryEntry 2 }

memoryStartingAddress OBJECT-TYPE
	SYNTAX		Dmi-Integer64
	MAX-ACCESS	read-only
	STATUS		current
	DESCRIPTION	"The starting physical address mapped by this memory component."
	REFERENCE "'DMTF|Physical Memory|002' 3"
	::= { dmtfPhysicalMemoryEntry 3 }

memoryEndingAddress OBJECT-TYPE
	SYNTAX		Dmi-Integer64
	MAX-ACCESS	read-only
	STATUS		current
	DESCRIPTION	"The ending physical address mapped by this memory component."
	REFERENCE "'DMTF|Physical Memory|002' 4"
	::= { dmtfPhysicalMemoryEntry 4 }

memoryUsage OBJECT-TYPE
	SYNTAX		INTEGER {
		other(1),
		unknown(2),
		systemMemory(3),
		videoMemory(4),
		flashMemory(5),
		nonVolatileRAM(6)
	}
	MAX-ACCESS	read-only
	STATUS		current
	DESCRIPTION	"What this memory component is used for."
	REFERENCE "'DMTF|Physical Memory|002' 5"
	::= { dmtfPhysicalMemoryEntry 5 }

maximumMemoryCapacity OBJECT-TYPE
	SYNTAX		DmiInteger
	MAX-ACCESS	read-only
	STATUS		current
	DESCRIPTION	"The maximum memory capacity, in megabytes, on this device."
	REFERENCE "'DMTF|Physical Memory|002' 6"
	::= { dmtfPhysicalMemoryEntry 6 }

numberOfSIMMSlots OBJECT-TYPE
	SYNTAX		DmiInteger
	MAX-ACCESS	read-only
	STATUS		current
	DESCRIPTION	"The number of SIMM slots available for this type of memory
on this device."
	REFERENCE "'DMTF|Physical Memory|002' 7"
	::= { dmtfPhysicalMemoryEntry 7 }

numberOfSIMMSlotsUsed OBJECT-TYPE
	SYNTAX		DmiInteger
	MAX-ACCESS	read-only
	STATUS		current
	DESCRIPTION	"The number of SIMM slots in use for this type of memory on
this device."
	REFERENCE "'DMTF|Physical Memory|002' 8"
	::= { dmtfPhysicalMemoryEntry 8 }

memorySpeed OBJECT-TYPE
	SYNTAX		DmiInteger
	MAX-ACCESS	read-only
	STATUS		current
	DESCRIPTION	"The speed of this memory component in nanoseconds."
	REFERENCE "'DMTF|Physical Memory|002' 9"
	::= { dmtfPhysicalMemoryEntry 9 }

memoryErrorCorrection OBJECT-TYPE
	SYNTAX		INTEGER {
		other(1),
		unknown(2),
		none(3),
		parity(4),
		singleBitECC(5),
		multiBitECC(6)
	}
	MAX-ACCESS	read-only
	STATUS		current
	DESCRIPTION	"The main error correction scheme supported by this memory
component."
	REFERENCE "'DMTF|Physical Memory|002' 10"
	::= { dmtfPhysicalMemoryEntry 10 }

fRUGroupIndex OBJECT-TYPE
	SYNTAX		DmiInteger
	MAX-ACCESS	read-only
	STATUS		current
	DESCRIPTION	"If this is a Field Replaceable Unit or if it is part of another
FRU, this provides an index into the FRU table; 'value = -1' indicates that
the group is not a FRU."
	REFERENCE "'DMTF|Physical Memory|002' 11"
	::= { dmtfPhysicalMemoryEntry 11 }

operationalGroupIndex OBJECT-TYPE
	SYNTAX		DmiInteger
	MAX-ACCESS	read-only
	STATUS		current
	DESCRIPTION	"The index into the Operational State Table for this device."
	REFERENCE "'DMTF|Physical Memory|002' 12"
	::= { dmtfPhysicalMemoryEntry 12 }

maximumMemoryCapacityFractionalPart OBJECT-TYPE
	SYNTAX		DmiInteger
	MAX-ACCESS	read-only
	STATUS		current
	DESCRIPTION	"Maximum memory capacity fractional part in bytes. This plus
the 'Maximum Memory Capacity' attribute gives the total maximum memory capacity.
Rationale: the units for the 'Maximum Memory Capacity'attribute (i.e. megabytes)
could not be corrected to kilobytes for reasons of backward compatibility."
	REFERENCE "'DMTF|Physical Memory|002' 13"
	::= { dmtfPhysicalMemoryEntry 13 }

SdmtfPowerSupplyOutputVoltageCapabilities ::= SEQUENCE {
	dmtfPowerSupplyOutputVoltageCapabilitiesState INTEGER,
	outputVoltageCapabilitiesTableIndex	DmiInteger,
	powerSupplyIndex	DmiInteger,
	powerUnitIndex	DmiInteger,
	outputVoltageCapabilityDescription	DmiString,
	nominalOutputVoltage	DmiInteger,
	outputVoltageLow	DmiInteger,
	outputVoltageHigh	DmiInteger,
	outputHighFrequency	DmiInteger,
	outputLowFrequency	DmiInteger,
	recommendedMaximumOutputCurrent	DmiInteger,
	maximumOutputCurrent	DmiInteger,
	minimumOutputCurrent	DmiInteger,
	voltageProbeIndex	DmiInteger,
	electricalCurrentProbeIndex	DmiInteger
}

dmtfPowerSupplyOutputVoltageCapabilitiesTable OBJECT-TYPE
	SYNTAX		SEQUENCE OF SdmtfPowerSupplyOutputVoltageCapabilities
	MAX-ACCESS	not-accessible
	STATUS		current
	DESCRIPTION	"This group defines the voltage capabilities of the power
supplies."
	::= { dmtfSystemsMIF 50 }

dmtfPowerSupplyOutputVoltageCapabilitiesEntry OBJECT-TYPE
	SYNTAX		SdmtfPowerSupplyOutputVoltageCapabilities
	MAX-ACCESS	not-accessible
	STATUS		current
	DESCRIPTION	"This group defines the voltage capabilities of the power
supplies."
	INDEX		{ DmiCompId,DmiGroupId, outputVoltageCapabilitiesTableIndex, powerSupplyIndex, powerUnitIndex }
	::= { dmtfPowerSupplyOutputVoltageCapabilitiesTable 1 }


dmtfPowerSupplyOutputVoltageCapabilitiesState OBJECT-TYPE
	SYNTAX		INTEGER {
		active(1),
		notInService(2),
		notReady(3),
		createAndGo(4),
		createAndWait(5),
		destroy(6)
	}
	MAX-ACCESS	read-write
	STATUS		current
	REFERENCE "'DMTF|Power Supply Output Voltage Capabilities|001' 0"
	::= { dmtfPowerSupplyOutputVoltageCapabilitiesEntry 0 }

outputVoltageCapabilitiesTableIndex OBJECT-TYPE
	SYNTAX		DmiInteger
	MAX-ACCESS	read-only
	STATUS		current
	DESCRIPTION	"This is an index into this, the Output Voltage Capabilites
table."
	REFERENCE "'DMTF|Power Supply Output Voltage Capabilities|001' 1"
	::= { dmtfPowerSupplyOutputVoltageCapabilitiesEntry 1 }

powerSupplyIndex OBJECT-TYPE
	SYNTAX		DmiInteger
	MAX-ACCESS	read-only
	STATUS		current
	DESCRIPTION	"The Power Supply Index that identifies the physical power
supply providing this voltage. 0 indicates that the capability applies to
the Power Unit as a whole."
	REFERENCE "'DMTF|Power Supply Output Voltage Capabilities|001' 2"
	::= { dmtfPowerSupplyOutputVoltageCapabilitiesEntry 2 }

powerUnitIndex OBJECT-TYPE
	SYNTAX		DmiInteger
	MAX-ACCESS	read-only
	STATUS		current
	DESCRIPTION	"The Power Unit Index identifies the logical power subsystem
that the physical supply is a member of. This value is obtained from the
Power Unit Global Table Index attribute in the physical power supply group."
	REFERENCE "'DMTF|Power Supply Output Voltage Capabilities|001' 3"
	::= { dmtfPowerSupplyOutputVoltageCapabilitiesEntry 3 }

outputVoltageCapabilityDescription OBJECT-TYPE
	SYNTAX		DmiString
	MAX-ACCESS	read-only
	STATUS		current
	DESCRIPTION	"An expanded description of this Output Voltage Capability."
	REFERENCE "'DMTF|Power Supply Output Voltage Capabilities|001' 4"
	::= { dmtfPowerSupplyOutputVoltageCapabilitiesEntry 4 }

nominalOutputVoltage OBJECT-TYPE
	SYNTAX		DmiInteger
	MAX-ACCESS	read-only
	STATUS		current
	DESCRIPTION	"The nominal specified voltage for this output, in millivolts.
A value of 0x80000000 denotes 'unknown'."
	REFERENCE "'DMTF|Power Supply Output Voltage Capabilities|001' 5"
	::= { dmtfPowerSupplyOutputVoltageCapabilitiesEntry 5 }

outputVoltageLow OBJECT-TYPE
	SYNTAX		DmiInteger
	MAX-ACCESS	read-only
	STATUS		current
	DESCRIPTION	"The lowest specified voltage for this output, in millivolts.
A value of 0x80000000 denotes 'unknown'."
	REFERENCE "'DMTF|Power Supply Output Voltage Capabilities|001' 6"
	::= { dmtfPowerSupplyOutputVoltageCapabilitiesEntry 6 }

outputVoltageHigh OBJECT-TYPE
	SYNTAX		DmiInteger
	MAX-ACCESS	read-only
	STATUS		current
	DESCRIPTION	"The highest specified voltage for this output, in millivolts.
A value of 0x80000000 denotes 'unknown'."
	REFERENCE "'DMTF|Power Supply Output Voltage Capabilities|001' 7"
	::= { dmtfPowerSupplyOutputVoltageCapabilitiesEntry 7 }

outputHighFrequency OBJECT-TYPE
	SYNTAX		DmiInteger
	MAX-ACCESS	read-only
	STATUS		current
	DESCRIPTION	"Maximum specified frequency of this output. 0 for DC. A value
of 0x80000000 denotes 'unknown'."
	REFERENCE "'DMTF|Power Supply Output Voltage Capabilities|001' 8"
	::= { dmtfPowerSupplyOutputVoltageCapabilitiesEntry 8 }

outputLowFrequency OBJECT-TYPE
	SYNTAX		DmiInteger
	MAX-ACCESS	read-only
	STATUS		current
	DESCRIPTION	"Minimum specified frequency of this output. 0 for DC. A value
of 0x80000000 denotes 'unknown'."
	REFERENCE "'DMTF|Power Supply Output Voltage Capabilities|001' 9"
	::= { dmtfPowerSupplyOutputVoltageCapabilitiesEntry 9 }

recommendedMaximumOutputCurrent OBJECT-TYPE
	SYNTAX		DmiInteger
	MAX-ACCESS	read-only
	STATUS		current
	DESCRIPTION	"Recommended maximum output current for this output, in milliamps
 0x80000000 denotes 'unknown'."
	REFERENCE "'DMTF|Power Supply Output Voltage Capabilities|001' 10"
	::= { dmtfPowerSupplyOutputVoltageCapabilitiesEntry 10 }

maximumOutputCurrent OBJECT-TYPE
	SYNTAX		DmiInteger
	MAX-ACCESS	read-only
	STATUS		current
	DESCRIPTION	"Rated maximum output current for this output, in milliamps.
0x80000000 denotes 'unknown'."
	REFERENCE "'DMTF|Power Supply Output Voltage Capabilities|001' 11"
	::= { dmtfPowerSupplyOutputVoltageCapabilitiesEntry 11 }

minimumOutputCurrent OBJECT-TYPE
	SYNTAX		DmiInteger
	MAX-ACCESS	read-only
	STATUS		current
	DESCRIPTION	"Rated minimum output current for this output, in milliamps.
0x80000000 denotes 'unknown'."
	REFERENCE "'DMTF|Power Supply Output Voltage Capabilities|001' 12"
	::= { dmtfPowerSupplyOutputVoltageCapabilitiesEntry 12 }

voltageProbeIndex OBJECT-TYPE
	SYNTAX		DmiInteger
	MAX-ACCESS	read-only
	STATUS		current
	DESCRIPTION	"Index into the Voltage Probe table identifying the probe
monitoring this output. 0 indicates no probe provided."
	REFERENCE "'DMTF|Power Supply Output Voltage Capabilities|001' 13"
	::= { dmtfPowerSupplyOutputVoltageCapabilitiesEntry 13 }

electricalCurrentProbeIndex OBJECT-TYPE
	SYNTAX		DmiInteger
	MAX-ACCESS	read-only
	STATUS		current
	DESCRIPTION	"Index into the Electrical Current Probe table identifying
the current probe monitoring this output.  0 indicates no probe provided."
	REFERENCE "'DMTF|Power Supply Output Voltage Capabilities|001' 14"
	::= { dmtfPowerSupplyOutputVoltageCapabilitiesEntry 14 }

SdmtfPowerSupply ::= SEQUENCE {
	dmtfPowerSupplyState INTEGER,
	powerSupplyIndex	DmiInteger,
	fRUGroupIndex	DmiInteger,
	operationalGroupIndex	DmiInteger,
	powerUnitIndex	DmiInteger,
	powerSupplyType	DmiInteger,
	inputVoltageCapabilityDescription	DmiString,
	range1InputVoltageLow	DmiInteger,
	range1InputVoltageHigh	DmiInteger,
	range1VoltageProbeIndex	DmiInteger,
	range1ElectricalCurrentProbeIndex	DmiInteger,
	range2InputVoltageLow	DmiInteger,
	range2InputVoltageHigh	DmiInteger,
	range2VoltageProbeIndex	DmiInteger,
	range2CurrentProbeIndex	DmiInteger,
	activeInputVoltageRange	DmiInteger,
	inputVoltageRangeSwitching	DmiInteger,
	range1InputFrequencyLow	DmiInteger,
	range1InputFrequencyHigh	DmiInteger,
	range2InputFrequencyLow	DmiInteger,
	range2InputFrequencyHigh	DmiInteger,
	totalOutputPower	DmiInteger
}

dmtfPowerSupplyTable OBJECT-TYPE
	SYNTAX		SEQUENCE OF SdmtfPowerSupply
	MAX-ACCESS	not-accessible
	STATUS		current
	DESCRIPTION	"This group defines various attributes for power supplies
in this system."
	::= { dmtfSystemsMIF 16 }

dmtfPowerSupplyEntry OBJECT-TYPE
	SYNTAX		SdmtfPowerSupply
	MAX-ACCESS	not-accessible
	STATUS		current
	DESCRIPTION	"This group defines various attributes for power supplies
in this system."
	INDEX		{ DmiCompId,DmiGroupId, powerSupplyIndex }
	::= { dmtfPowerSupplyTable 1 }


dmtfPowerSupplyState OBJECT-TYPE
	SYNTAX		INTEGER {
		active(1),
		notInService(2),
		notReady(3),
		createAndGo(4),
		createAndWait(5),
		destroy(6)
	}
	MAX-ACCESS	read-write
	STATUS		current
	REFERENCE "'DMTF|Power Supply|002' 0"
	::= { dmtfPowerSupplyEntry 0 }

powerSupplyIndex OBJECT-TYPE
	SYNTAX		DmiInteger
	MAX-ACCESS	read-only
	STATUS		current
	DESCRIPTION	"The index number of the current power supply."
	REFERENCE "'DMTF|Power Supply|002' 1"
	::= { dmtfPowerSupplyEntry 1 }

fRUGroupIndex OBJECT-TYPE
	SYNTAX		DmiInteger
	MAX-ACCESS	read-only
	STATUS		current
	DESCRIPTION	"If this is a Field Replaceable Unit or if it is part of another
FRU, this provides an index into the FRU table; 'value = -1' indicates that
the group is not a FRU."
	REFERENCE "'DMTF|Power Supply|002' 2"
	::= { dmtfPowerSupplyEntry 2 }

operationalGroupIndex OBJECT-TYPE
	SYNTAX		DmiInteger
	MAX-ACCESS	read-only
	STATUS		current
	DESCRIPTION	"The index into the Operational State table for this device."
	REFERENCE "'DMTF|Power Supply|002' 3"
	::= { dmtfPowerSupplyEntry 3 }

powerUnitIndex OBJECT-TYPE
	SYNTAX		DmiInteger
	MAX-ACCESS	read-only
	STATUS		current
	DESCRIPTION	"This is the ID of the Power Unit (logical power supply) to
which this Power Supply belongs. This value matches up with the Power Unit
Table Index attribute defined in the Power Unit Global Table."
	REFERENCE "'DMTF|Power Supply|002' 4"
	::= { dmtfPowerSupplyEntry 4 }

powerSupplyType OBJECT-TYPE
	SYNTAX		INTEGER {
		other(1),
		unknown(2),
		linear(3),
		switching(4),
		battery(5),
		uPS(6),
		converter(7),
		regulator(8)
	}
	MAX-ACCESS	read-only
	STATUS		current
	DESCRIPTION	"This attribute describes the type of Power Supply, e.g. Linear,
Switching, Battery, etc."
	REFERENCE "'DMTF|Power Supply|002' 5"
	::= { dmtfPowerSupplyEntry 5 }

inputVoltageCapabilityDescription OBJECT-TYPE
	SYNTAX		DmiString
	MAX-ACCESS	read-only
	STATUS		current
	DESCRIPTION	"An expanded description of the Input Voltage Capability for
this Power Supply."
	REFERENCE "'DMTF|Power Supply|002' 6"
	::= { dmtfPowerSupplyEntry 6 }

range1InputVoltageLow OBJECT-TYPE
	SYNTAX		DmiInteger
	MAX-ACCESS	read-only
	STATUS		current
	DESCRIPTION	"The low voltage of Input Voltage Range 1 for this Power Supply,
in millivolts. A value of 0x80000000 denotes 'unknown'."
	REFERENCE "'DMTF|Power Supply|002' 7"
	::= { dmtfPowerSupplyEntry 7 }

range1InputVoltageHigh OBJECT-TYPE
	SYNTAX		DmiInteger
	MAX-ACCESS	read-only
	STATUS		current
	DESCRIPTION	"The high voltage of Input Voltage Range 1 for this Power
Supply, in millivolts. A value of 0x80000000 denotes 'unknown'."
	REFERENCE "'DMTF|Power Supply|002' 8"
	::= { dmtfPowerSupplyEntry 8 }

range1VoltageProbeIndex OBJECT-TYPE
	SYNTAX		DmiInteger
	MAX-ACCESS	read-only
	STATUS		current
	DESCRIPTION	"Index into the Voltage Probe table identifying the voltage
probe monitoring this input range. 0 indicates no probe provided."
	REFERENCE "'DMTF|Power Supply|002' 9"
	::= { dmtfPowerSupplyEntry 9 }

range1ElectricalCurrentProbeIndex OBJECT-TYPE
	SYNTAX		DmiInteger
	MAX-ACCESS	read-only
	STATUS		current
	DESCRIPTION	"Index into the Elelctrical Current Probe table identifying
the Electrical current probe monitoring this input range. 0 indicates no
probe provided."
	REFERENCE "'DMTF|Power Supply|002' 10"
	::= { dmtfPowerSupplyEntry 10 }

range2InputVoltageLow OBJECT-TYPE
	SYNTAX		DmiInteger
	MAX-ACCESS	read-only
	STATUS		current
	DESCRIPTION	"The low voltage of Input Voltage Range 2 for this Power Supply,
in millivolts. A value of 0x80000000 denotes 'unknown'."
	REFERENCE "'DMTF|Power Supply|002' 11"
	::= { dmtfPowerSupplyEntry 11 }

range2InputVoltageHigh OBJECT-TYPE
	SYNTAX		DmiInteger
	MAX-ACCESS	read-only
	STATUS		current
	DESCRIPTION	"The high voltage of Input Voltage Range 2 for this Power
Supply, in millivolts. A value of 0x80000000 denotes 'unknown'"
	REFERENCE "'DMTF|Power Supply|002' 12"
	::= { dmtfPowerSupplyEntry 12 }

range2VoltageProbeIndex OBJECT-TYPE
	SYNTAX		DmiInteger
	MAX-ACCESS	read-only
	STATUS		current
	DESCRIPTION	"Index into the Voltage Probe table identifying the voltage
probe monitoring this input range. 0 indicates no probe provided."
	REFERENCE "'DMTF|Power Supply|002' 13"
	::= { dmtfPowerSupplyEntry 13 }

range2CurrentProbeIndex OBJECT-TYPE
	SYNTAX		DmiInteger
	MAX-ACCESS	read-only
	STATUS		current
	DESCRIPTION	"Index into the Current Probe table identifying the current
probe monitoring this input range. 0 indicates no probe provided."
	REFERENCE "'DMTF|Power Supply|002' 14"
	::= { dmtfPowerSupplyEntry 14 }

activeInputVoltageRange OBJECT-TYPE
	SYNTAX		INTEGER {
		other(1),
		unknown(2),
		range1(3),
		range2(4),
		both(5)
	}
	MAX-ACCESS	read-only
	STATUS		current
	DESCRIPTION	"The value of this attribute indicates which input voltage
range of this Power Supply is currently active."
	REFERENCE "'DMTF|Power Supply|002' 15"
	::= { dmtfPowerSupplyEntry 15 }

inputVoltageRangeSwitching OBJECT-TYPE
	SYNTAX		INTEGER {
		other(1),
		unknown(2),
		manual(3),
		autoswitch(4),
		wideRange(5),
		notApplicable(6)
	}
	MAX-ACCESS	read-only
	STATUS		current
	DESCRIPTION	"This attribute describes the kind of input voltage range
switching that is implemented in this power supply."
	REFERENCE "'DMTF|Power Supply|002' 16"
	::= { dmtfPowerSupplyEntry 16 }

range1InputFrequencyLow OBJECT-TYPE
	SYNTAX		DmiInteger
	MAX-ACCESS	read-only
	STATUS		current
	DESCRIPTION	"The frequency at the low end of this power supply's Input
Frequency Range 1. A value of zero implies DC. A value of 0x80000000 denotes
'unknown'"
	REFERENCE "'DMTF|Power Supply|002' 17"
	::= { dmtfPowerSupplyEntry 17 }

range1InputFrequencyHigh OBJECT-TYPE
	SYNTAX		DmiInteger
	MAX-ACCESS	read-only
	STATUS		current
	DESCRIPTION	"The frequency at the high end of this power supply's Input
Frequency Range 1. A value of zero implies DC. A value of 0x80000000 denotes
'unknown'"
	REFERENCE "'DMTF|Power Supply|002' 18"
	::= { dmtfPowerSupplyEntry 18 }

range2InputFrequencyLow OBJECT-TYPE
	SYNTAX		DmiInteger
	MAX-ACCESS	read-only
	STATUS		current
	DESCRIPTION	"The frequency at the low end of this power supply's Input
Frequency Range 2. A value of zero implies DC. A value of 0x80000000 denotes
'unknown'"
	REFERENCE "'DMTF|Power Supply|002' 19"
	::= { dmtfPowerSupplyEntry 19 }

range2InputFrequencyHigh OBJECT-TYPE
	SYNTAX		DmiInteger
	MAX-ACCESS	read-only
	STATUS		current
	DESCRIPTION	"The frequency at the high end of this power supply's Input
Frequency Range 2. A value of zero implies DC. A value of 0x80000000 denotes
'unknown'"
	REFERENCE "'DMTF|Power Supply|002' 20"
	::= { dmtfPowerSupplyEntry 20 }

totalOutputPower OBJECT-TYPE
	SYNTAX		DmiInteger
	MAX-ACCESS	read-only
	STATUS		current
	DESCRIPTION	"This attribute value represents the total output power of
this power supply in milliWatts. 0x80000000 denotes 'unknown'"
	REFERENCE "'DMTF|Power Supply|002' 21"
	::= { dmtfPowerSupplyEntry 21 }

SdmtfPowerUnitGlobalTable ::= SEQUENCE {
	dmtfPowerUnitGlobalTableState INTEGER,
	powerUnitIndex	DmiInteger,
	powerUnitRedundancyStatus	DmiInteger
}

dmtfPowerUnitGlobalTable OBJECT-TYPE
	SYNTAX		SEQUENCE OF SdmtfPowerUnitGlobalTable
	MAX-ACCESS	not-accessible
	STATUS		current
	DESCRIPTION	"This global table describes all of the Power Units in this
system component. The unique index of each Power Unit is the key into this
table. A Power Unit is composed of potentially more than one Power Supply
in a redundant configuration. Individual power supplies are described in
the 'Power Supply' standard group. In that group, each individual power supply
entry will point to a Power Unit in this table by using the index of the
row in this table that describes the Power Unit. If a Power Unit is redunda"
	::= { dmtfSystemsMIF 66 }

dmtfPowerUnitGlobalEntry OBJECT-TYPE
	SYNTAX		SdmtfPowerUnitGlobalTable
	MAX-ACCESS	not-accessible
	STATUS		current
	DESCRIPTION	"This global table describes all of the Power Units in this
system component. The unique index of each Power Unit is the key into this
table. A Power Unit is composed of potentially more than one Power Supply
in a redundant configuration. Individual power supplies are described in
the 'Power Supply' standard group. In that group, each individual power supply
entry will point to a Power Unit in this table by using the index of the
row in this table that describes the Power Unit. If a Power Unit is redunda"
	INDEX		{ DmiCompId,DmiGroupId, powerUnitIndex }
	::= { dmtfPowerUnitGlobalTable 1 }


dmtfPowerUnitGlobalTableState OBJECT-TYPE
	SYNTAX		INTEGER {
		active(1),
		notInService(2),
		notReady(3),
		createAndGo(4),
		createAndWait(5),
		destroy(6)
	}
	MAX-ACCESS	read-write
	STATUS		current
	REFERENCE "'DMTF|Power Unit Global Table|001' 0"
	::= { dmtfPowerUnitGlobalEntry 0 }

powerUnitIndex OBJECT-TYPE
	SYNTAX		DmiInteger
	MAX-ACCESS	read-only
	STATUS		current
	DESCRIPTION	"The unique index given to each Power Unit being described
by this table. This unique index is the key into this table."
	REFERENCE "'DMTF|Power Unit Global Table|001' 1"
	::= { dmtfPowerUnitGlobalEntry 1 }

powerUnitRedundancyStatus OBJECT-TYPE
	SYNTAX		INTEGER {
		other(1),
		unknown(2),
		notApplicableUnitNotRedundant(3),
		offline(4),
		fullyRedundant(5),
		degradedRedundancy(6),
		redundancyLost(7)
	}
	MAX-ACCESS	read-only
	STATUS		current
	DESCRIPTION	"Gives the redundancy status of the Power Unit.  'Fully Redundant
 means that all of the configured redundancy is still available; 'Degraded
Redundancy' means that some failures have been experienced but some reduced
amount of redundancy is still available; 'Redundancy Lost' means that a sufficie
t number of failures have been experienced that no redundancy is available
and the next failure experienced within the Power Unit will cause overall
Power Unit failure. "
	REFERENCE "'DMTF|Power Unit Global Table|001' 2"
	::= { dmtfPowerUnitGlobalEntry 2 }

SdmtfProcessor ::= SEQUENCE {
	dmtfProcessorState INTEGER,
	processorIndex	DmiInteger,
	processorType	DmiInteger,
	processorFamily	DmiInteger,
	processorVersionInformation	DmiString,
	maximumSpeed	DmiInteger,
	currentSpeed	DmiInteger,
	processorUpgrade	DmiInteger,
	fRUGroupIndex	DmiInteger,
	operationalGroupIndex	DmiInteger,
	level1CacheIndex	DmiInteger,
	level2CacheIndex	DmiInteger,
	level3CacheIndex	DmiInteger
}

dmtfProcessorTable OBJECT-TYPE
	SYNTAX		SEQUENCE OF SdmtfProcessor
	MAX-ACCESS	not-accessible
	STATUS		current
	DESCRIPTION	"This group defines the attributes for each and every processor
installed in this system."
	::= { dmtfSystemsMIF 5 }

dmtfProcessorEntry OBJECT-TYPE
	SYNTAX		SdmtfProcessor
	MAX-ACCESS	not-accessible
	STATUS		current
	DESCRIPTION	"This group defines the attributes for each and every processor
installed in this system."
	INDEX		{ DmiCompId,DmiGroupId, processorIndex }
	::= { dmtfProcessorTable 1 }


dmtfProcessorState OBJECT-TYPE
	SYNTAX		INTEGER {
		active(1),
		notInService(2),
		notReady(3),
		createAndGo(4),
		createAndWait(5),
		destroy(6)
	}
	MAX-ACCESS	read-write
	STATUS		current
	REFERENCE "'DMTF|Processor|004' 0"
	::= { dmtfProcessorEntry 0 }

processorIndex OBJECT-TYPE
	SYNTAX		DmiInteger
	MAX-ACCESS	read-only
	STATUS		current
	DESCRIPTION	"An index into the processor table."
	REFERENCE "'DMTF|Processor|004' 1"
	::= { dmtfProcessorEntry 1 }

processorType OBJECT-TYPE
	SYNTAX		INTEGER {
		other(1),
		unknown(2),
		centralProcessor(3),
		mathProcessor(4),
		dSPProcessor(5),
		videoProcessor(6)
	}
	MAX-ACCESS	read-only
	STATUS		current
	DESCRIPTION	"The type of processor currently in the system."
	REFERENCE "'DMTF|Processor|004' 2"
	::= { dmtfProcessorEntry 2 }

processorFamily OBJECT-TYPE
	SYNTAX		INTEGER {
		other(1),
		unknown(2),
		x8086(3),
		x80286(4),
		x80386(5),
		x80486(6),
		x8087(7),
		x80287(8),
		x80387(9),
		x80487(10),
		pentiumFamily(11),
		pentiumPro(12),
		pentiumII(13),
		pentiumMMX(14),
		m1Family(18),
		k5Family(25),
		powerPCFamily(32),
		powerPC601(33),
		powerPC603(34),
		powerPC603-1(35),
		powerPC604(36),
		alphaFamily(48),
		mIPSFamily(64),
		sPARCFamily(80),
		x68040(96),
		x68xxxFamily(97),
		x68000(98),
		x68010(99),
		x68020(100),
		x68030(101),
		hobbitFamily(112),
		weitek(128),
		pARISCFamily(144),
		v30Family(160)
	}
	MAX-ACCESS	read-only
	STATUS		current
	DESCRIPTION	"The family of processors to which this processor belongs."
	REFERENCE "'DMTF|Processor|004' 3"
	::= { dmtfProcessorEntry 3 }

processorVersionInformation OBJECT-TYPE
	SYNTAX		DmiString
	MAX-ACCESS	read-only
	STATUS		current
	DESCRIPTION	"The version number or string for this processor."
	REFERENCE "'DMTF|Processor|004' 4"
	::= { dmtfProcessorEntry 4 }

maximumSpeed OBJECT-TYPE
	SYNTAX		DmiInteger
	MAX-ACCESS	read-only
	STATUS		current
	DESCRIPTION	"The maximum speed (in MHz) of this processor."
	REFERENCE "'DMTF|Processor|004' 5"
	::= { dmtfProcessorEntry 5 }

currentSpeed OBJECT-TYPE
	SYNTAX		DmiInteger
	MAX-ACCESS	read-only
	STATUS		current
	DESCRIPTION	"The current speed (in MHz) of this processor."
	REFERENCE "'DMTF|Processor|004' 6"
	::= { dmtfProcessorEntry 6 }

processorUpgrade OBJECT-TYPE
	SYNTAX		INTEGER {
		other(1),
		unknown(2),
		daughterBoard(3),
		zIFSocket(4),
		replacementPiggyBack(5),
		none(6),
		lIFSocket(7),
		slot1(8)
	}
	MAX-ACCESS	read-only
	STATUS		current
	DESCRIPTION	"The method by which this processor can be upgraded, if upgrades
are supported."
	REFERENCE "'DMTF|Processor|004' 7"
	::= { dmtfProcessorEntry 7 }

fRUGroupIndex OBJECT-TYPE
	SYNTAX		DmiInteger
	MAX-ACCESS	read-only
	STATUS		current
	DESCRIPTION	"If this is a Field Replaceable Unit or if it is part of another
FRU, this provides an index into the FRU table; 'value = -1' indicates that
the group is not a FRU."
	REFERENCE "'DMTF|Processor|004' 8"
	::= { dmtfProcessorEntry 8 }

operationalGroupIndex OBJECT-TYPE
	SYNTAX		DmiInteger
	MAX-ACCESS	read-only
	STATUS		current
	DESCRIPTION	"The index into the Operational State Table for this device
if applicable."
	REFERENCE "'DMTF|Processor|004' 9"
	::= { dmtfProcessorEntry 9 }

level1CacheIndex OBJECT-TYPE
	SYNTAX		DmiInteger
	MAX-ACCESS	read-only
	STATUS		current
	DESCRIPTION	"An index into the System Cache table that identifies the
entry that describes the L1 cache for this processor. If more than one processor
points to the same cache entry this means they share that cache."
	REFERENCE "'DMTF|Processor|004' 10"
	::= { dmtfProcessorEntry 10 }

level2CacheIndex OBJECT-TYPE
	SYNTAX		DmiInteger
	MAX-ACCESS	read-only
	STATUS		current
	DESCRIPTION	"An index into the System Cache table that identifies the
entry that describes the L2 cache for this processor If more than one processor
points to the same cache entry this means they share that cache."
	REFERENCE "'DMTF|Processor|004' 11"
	::= { dmtfProcessorEntry 11 }

level3CacheIndex OBJECT-TYPE
	SYNTAX		DmiInteger
	MAX-ACCESS	read-only
	STATUS		current
	DESCRIPTION	"An index into the System Cache table that identifies the
entry that describes the L3 cache for this processor. If more than one processor
points to the same cache entry this means they share that cache."
	REFERENCE "'DMTF|Processor|004' 12"
	::= { dmtfProcessorEntry 12 }


SdmtfSequentialAccessDevices ::= SEQUENCE {
	dmtfSequentialAccessDevicesState INTEGER,
	sequentialAccessIndex	DmiInteger,
	maximumSequentialMediaSize	DmiInteger,
	currentSequentialMediaSize	DmiInteger,
	sequentialMediaPresent	DmiInteger,
	sequentialMediaTechnology	DmiInteger,
	fRUGroupIndex	DmiInteger,
	operationalGroupIndex	DmiInteger
}

dmtfSequentialAccessDevicesTable OBJECT-TYPE
	SYNTAX		SEQUENCE OF SdmtfSequentialAccessDevices
	MAX-ACCESS	not-accessible
	STATUS		current
	DESCRIPTION	"This table describes each sequential access device in the
system."
	::= { dmtfSystemsMIF 47 }

dmtfSequentialAccessDevicesEntry OBJECT-TYPE
	SYNTAX		SdmtfSequentialAccessDevices
	MAX-ACCESS	not-accessible
	STATUS		current
	DESCRIPTION	"This table describes each sequential access device in the
system."
	INDEX		{ DmiCompId,DmiGroupId, sequentialAccessIndex }
	::= { dmtfSequentialAccessDevicesTable 1 }


dmtfSequentialAccessDevicesState OBJECT-TYPE
	SYNTAX		INTEGER {
		active(1),
		notInService(2),
		notReady(3),
		createAndGo(4),
		createAndWait(5),
		destroy(6)
	}
	MAX-ACCESS	read-write
	STATUS		current
	REFERENCE "'DMTF|Sequential Access Devices|001' 0"
	::= { dmtfSequentialAccessDevicesEntry 0 }

sequentialAccessIndex OBJECT-TYPE
	SYNTAX		DmiInteger
	MAX-ACCESS	read-only
	STATUS		current
	DESCRIPTION	"Unique index into the Sequential Access Devices table for
this Sequential Access Device."
	REFERENCE "'DMTF|Sequential Access Devices|001' 1"
	::= { dmtfSequentialAccessDevicesEntry 1 }

maximumSequentialMediaSize OBJECT-TYPE
	SYNTAX		DmiInteger
	MAX-ACCESS	read-only
	STATUS		current
	DESCRIPTION	"Maximum size, in KB, of media supported by this device"
	REFERENCE "'DMTF|Sequential Access Devices|001' 2"
	::= { dmtfSequentialAccessDevicesEntry 2 }

currentSequentialMediaSize OBJECT-TYPE
	SYNTAX		DmiInteger
	MAX-ACCESS	read-only
	STATUS		current
	DESCRIPTION	"Current size, in KB, of media in this drive."
	REFERENCE "'DMTF|Sequential Access Devices|001' 3"
	::= { dmtfSequentialAccessDevicesEntry 3 }

sequentialMediaPresent OBJECT-TYPE
	SYNTAX		INTEGER {
		false(0),
		true(1)
	}
	MAX-ACCESS	read-only
	STATUS		current
	DESCRIPTION	"Indicates the presence of a media in the drive."
	REFERENCE "'DMTF|Sequential Access Devices|001' 4"
	::= { dmtfSequentialAccessDevicesEntry 4 }

sequentialMediaTechnology OBJECT-TYPE
	SYNTAX		INTEGER {
		other(1),
		unknown(2),
		pEGCR(3),
		x3480Compatible(4),
		x3490ECompatible(5),
		dDS1(6),
		dDS2(7),
		dDS3(8),
		x8mm82xx(9),
		x8mm85xx(10),
		x8mmMammoth(11),
		qIC24(12),
		qIC525(13),
		qICOther(14),
		miniCartridgeQIC80(15),
		miniCartridgeOther(16),
		travan(17),
		dLT2000(18),
		dLT4000(19)
	}
	MAX-ACCESS	read-only
	STATUS		current
	DESCRIPTION	"Indicates the type of tapes supported by the drive."
	REFERENCE "'DMTF|Sequential Access Devices|001' 5"
	::= { dmtfSequentialAccessDevicesEntry 5 }

fRUGroupIndex OBJECT-TYPE
	SYNTAX		DmiInteger
	MAX-ACCESS	read-only
	STATUS		current
	DESCRIPTION	"If this is a Field Replaceable Unit or if it is part of another
FRU, this provides index into the FRU table.  A Value = -1 means that the
group is not a FRU"
	REFERENCE "'DMTF|Sequential Access Devices|001' 6"
	::= { dmtfSequentialAccessDevicesEntry 6 }

operationalGroupIndex OBJECT-TYPE
	SYNTAX		DmiInteger
	MAX-ACCESS	read-only
	STATUS		current
	DESCRIPTION	"The index into the Operational State Table for this device,
if applicable."
	REFERENCE "'DMTF|Sequential Access Devices|001' 7"
	::= { dmtfSequentialAccessDevicesEntry 7 }

SdmtfSerialPorts ::= SEQUENCE {
	dmtfSerialPortsState INTEGER,
	serialPortIndex	DmiInteger,
	serialBaseIOAddress	Dmi-Integer64,
	iRQUsed	DmiInteger,
	logicalName	DmiString,
	connectorType	DmiInteger,
	maximumSpeed	DmiInteger,
	serialPortCapabilities	DmiInteger,
	operationalGroupIndex	DmiInteger,
	serialPortSecuritySettings	DmiInteger
}

dmtfSerialPortsTable OBJECT-TYPE
	SYNTAX		SEQUENCE OF SdmtfSerialPorts
	MAX-ACCESS	not-accessible
	STATUS		current
	DESCRIPTION	"This group defines the attributes for serial ports in this
system."
	::= { dmtfSystemsMIF 11 }

dmtfSerialPortsEntry OBJECT-TYPE
	SYNTAX		SdmtfSerialPorts
	MAX-ACCESS	not-accessible
	STATUS		current
	DESCRIPTION	"This group defines the attributes for serial ports in this
system."
	INDEX		{ DmiCompId,DmiGroupId, serialPortIndex }
	::= { dmtfSerialPortsTable 1 }


dmtfSerialPortsState OBJECT-TYPE
	SYNTAX		INTEGER {
		active(1),
		notInService(2),
		notReady(3),
		createAndGo(4),
		createAndWait(5),
		destroy(6)
	}
	MAX-ACCESS	read-write
	STATUS		current
	REFERENCE "'DMTF|Serial Ports|003' 0"
	::= { dmtfSerialPortsEntry 0 }

serialPortIndex OBJECT-TYPE
	SYNTAX		DmiInteger
	MAX-ACCESS	read-only
	STATUS		current
	DESCRIPTION	"An index into the serial ports table."
	REFERENCE "'DMTF|Serial Ports|003' 1"
	::= { dmtfSerialPortsEntry 1 }

serialBaseIOAddress OBJECT-TYPE
	SYNTAX		Dmi-Integer64
	MAX-ACCESS	read-only
	STATUS		current
	DESCRIPTION	"Base I/O address for this serial port."
	REFERENCE "'DMTF|Serial Ports|003' 2"
	::= { dmtfSerialPortsEntry 2 }

iRQUsed OBJECT-TYPE
	SYNTAX		DmiInteger
	MAX-ACCESS	read-only
	STATUS		current
	DESCRIPTION	"IRQ number that is being used by this serial port."
	REFERENCE "'DMTF|Serial Ports|003' 3"
	::= { dmtfSerialPortsEntry 3 }

logicalName OBJECT-TYPE
	SYNTAX		DmiString
	MAX-ACCESS	read-only
	STATUS		current
	DESCRIPTION	"The logical name of this serial port under this operating
environment."
	REFERENCE "'DMTF|Serial Ports|003' 4"
	::= { dmtfSerialPortsEntry 4 }

connectorType OBJECT-TYPE
	SYNTAX		INTEGER {
		other(1),
		unknown(2),
		dB9PinMale(3),
		dB9PinFemale(4),
		dB25PinMale(5),
		dB25PinFemale(6),
		rJ11(7),
		rJ45(8),
		proprietary(9),
		circularDIN8Male(10),
		circularDIN8Female(11),
		miniCentronicsType14(160),
		miniCentronicsType26(161)
	}
	MAX-ACCESS	read-only
	STATUS		current
	DESCRIPTION	"The connector used to interface with the I/O device on this
serial port."
	REFERENCE "'DMTF|Serial Ports|003' 5"
	::= { dmtfSerialPortsEntry 5 }

maximumSpeed OBJECT-TYPE
	SYNTAX		DmiInteger
	MAX-ACCESS	read-only
	STATUS		current
	DESCRIPTION	"Maximum transfer speed of the device on this serial port
in bits per second."
	REFERENCE "'DMTF|Serial Ports|003' 6"
	::= { dmtfSerialPortsEntry 6 }

serialPortCapabilities OBJECT-TYPE
	SYNTAX		INTEGER {
		other(1),
		unknown(2),
		xTATCompatible(3),
		x16450Compatible(4),
		x16550Compatible(5),
		x16550ACompatible(6),
		x8251Compatible(160),
		x8251FIFOCompatible(161)
	}
	MAX-ACCESS	read-only
	STATUS		current
	DESCRIPTION	"The capabilities of this Serial port."
	REFERENCE "'DMTF|Serial Ports|003' 7"
	::= { dmtfSerialPortsEntry 7 }

operationalGroupIndex OBJECT-TYPE
	SYNTAX		DmiInteger
	MAX-ACCESS	read-only
	STATUS		current
	DESCRIPTION	"The index into the Operational State Table for this device."
	REFERENCE "'DMTF|Serial Ports|003' 8"
	::= { dmtfSerialPortsEntry 8 }

serialPortSecuritySettings OBJECT-TYPE
	SYNTAX		INTEGER {
		other(1),
		unknown(2),
		none(3),
		externalInterfaceLockedOut(4),
		externalInterfaceEnabled(5),
		bootBypass(6)
	}
	MAX-ACCESS	read-only
	STATUS		current
	DESCRIPTION	"Attribute describing the current hardware security settings
on this device"
	REFERENCE "'DMTF|Serial Ports|003' 9"
	::= { dmtfSerialPortsEntry 9 }

SdmtfStructureDependencyTable ::= SEQUENCE {
	dmtfStructureDependencyTableState INTEGER,
	dependencyIndex	DmiInteger,
	supportingElementGroupID	DmiInteger,
	supportingElementRowKey	DmiString,
	dependencyType	DmiInteger,
	dependentElementComponentID	DmiInteger,
	dependentElementGroupID	DmiInteger,
	dependentElementRowKey	DmiString
}

dmtfStructureDependencyTable OBJECT-TYPE
	SYNTAX		SEQUENCE OF SdmtfStructureDependencyTable
	MAX-ACCESS	not-accessible
	STATUS		current
	DESCRIPTION	"This group describes a table whose entries identify the structur
l dependencies of elements on other elements in the system.  The attributes
in this group form a row of the table and the row has the following structure:<d
pendency-index> <supporting-element-pointer> <dependency-type> <dependent-elemen
-pointer>.  The <dependency-index> is the index of the row in the table.
The <dependency-element-pointer> can point either to a element in the current
Component or to an external Component.  The <supportin"
	::= { dmtfSystemsMIF 68 }

dmtfStructureDependencyEntry OBJECT-TYPE
	SYNTAX		SdmtfStructureDependencyTable
	MAX-ACCESS	not-accessible
	STATUS		current
	DESCRIPTION	"This group describes a table whose entries identify the structur
l dependencies of elements on other elements in the system.  The attributes
in this group form a row of the table and the row has the following structure:<d
pendency-index> <supporting-element-pointer> <dependency-type> <dependent-elemen
-pointer>.  The <dependency-index> is the index of the row in the table.
The <dependency-element-pointer> can point either to a element in the current
Component or to an external Component.  The <supportin"
	INDEX		{ DmiCompId,DmiGroupId, dependencyIndex }
	::= { dmtfStructureDependencyTable 1 }


dmtfStructureDependencyTableState OBJECT-TYPE
	SYNTAX		INTEGER {
		active(1),
		notInService(2),
		notReady(3),
		createAndGo(4),
		createAndWait(5),
		destroy(6)
	}
	MAX-ACCESS	read-write
	STATUS		current
	REFERENCE "'DMTF|Structure Dependency Table|001' 0"
	::= { dmtfStructureDependencyEntry 0 }

dependencyIndex OBJECT-TYPE
	SYNTAX		DmiInteger
	MAX-ACCESS	read-only
	STATUS		current
	DESCRIPTION	"This is a unique index into the Structure Dependency Table."
	REFERENCE "'DMTF|Structure Dependency Table|001' 1"
	::= { dmtfStructureDependencyEntry 1 }

supportingElementGroupID OBJECT-TYPE
	SYNTAX		DmiInteger
	MAX-ACCESS	read-only
	STATUS		current
	DESCRIPTION	"This attribute holds the Group ID of the structure table
(e.g. Physical Container Global Table, etc.) or other table group within
the current expandable component that describes the supporting element. A
supporting element Component ID is not required because the supporting element
is expected to reside in the current Component that is implementing this
attribute."
	REFERENCE "'DMTF|Structure Dependency Table|001' 2"
	::= { dmtfStructureDependencyEntry 2 }

supportingElementRowKey OBJECT-TYPE
	SYNTAX		DmiString
	MAX-ACCESS	read-only
	STATUS		current
	DESCRIPTION	"This attribute holds the Row Key to the structure table or
other table group within the current expandable component that describes
the supporting element. The Row Key is a KeyList composed of Integers (or
Enums) ONLY.  It is currently represented as a string whose content is a
comma-separated list of Integers in ASCII form (i.e. the individual keys),
without any intervening spaces. If the supporting element is not described
by a table group then this attribute must be set to a null string."
	REFERENCE "'DMTF|Structure Dependency Table|001' 3"
	::= { dmtfStructureDependencyEntry 3 }

dependencyType OBJECT-TYPE
	SYNTAX		INTEGER {
		other(1),
		unknown(2),
		contains(3),
		providesPowerTo(4),
		providesCoolingTo(5),
		connectsTo(6)
	}
	MAX-ACCESS	read-only
	STATUS		current
	DESCRIPTION	"This attribute describes the type of dependency represented
by this entry in the Structure Dependency Table, e.g. 'contains', or'provides
power to', etc."
	REFERENCE "'DMTF|Structure Dependency Table|001' 4"
	::= { dmtfStructureDependencyEntry 4 }

dependentElementComponentID OBJECT-TYPE
	SYNTAX		DmiInteger
	MAX-ACCESS	read-only
	STATUS		current
	DESCRIPTION	"This is the Component ID of the dependent element in the
dependency relationship which is of the form'<supporting-element> <dependency-re
ation> <dependent-element>'.  If this attribute has a zero value then the
current component is being referenced. If it is non-zero then an external
component is being pointed to."
	REFERENCE "'DMTF|Structure Dependency Table|001' 5"
	::= { dmtfStructureDependencyEntry 5 }

dependentElementGroupID OBJECT-TYPE
	SYNTAX		DmiInteger
	MAX-ACCESS	read-only
	STATUS		current
	DESCRIPTION	"This attribute contains the Group ID of the attribute group
that describes the dependent element within the component identified by the
attribute Dependent Element Component ID."
	REFERENCE "'DMTF|Structure Dependency Table|001' 6"
	::= { dmtfStructureDependencyEntry 6 }

dependentElementRowKey OBJECT-TYPE
	SYNTAX		DmiString
	MAX-ACCESS	read-only
	STATUS		current
	DESCRIPTION	"This attribute holds the RowKey selecting the particular
row in the(table) group uniquely identified by the contents of the attribute's
Dependent Element Group ID and Dependent Element Component ID. The Row Key
is a KeyList composed of Integers (or Enums) ONLY. It is currently represented
as a string whose content is a comma-separated list of Integers in ASCII
form (i.e. the individual keys), without any intervening spaces. If the dependen
 element is not described by a table group then this attribute m"
	REFERENCE "'DMTF|Structure Dependency Table|001' 7"
	::= { dmtfStructureDependencyEntry 7 }

SdmtfSystemBIOS ::= SEQUENCE {
	dmtfSystemBIOSState INTEGER,
	bIOSIndex	DmiInteger,
	bIOSManufacturer	DmiString,
	bIOSVersion	DmiString,
	bIOSROMSize	DmiInteger,
	bIOSStartingAddress	Dmi-Integer64,
	bIOSEndingAddress	Dmi-Integer64,
	bIOSLoaderVersion	DmiString,
	bIOSReleaseDate	Dmi-Date,
	primaryBIOS	DmiInteger
}

dmtfSystemBIOSTable OBJECT-TYPE
	SYNTAX		SEQUENCE OF SdmtfSystemBIOS
	MAX-ACCESS	not-accessible
	STATUS		current
	DESCRIPTION	"This group defines the attributes for the System BIOS."
	::= { dmtfSystemsMIF 3 }

dmtfSystemBIOSEntry OBJECT-TYPE
	SYNTAX		SdmtfSystemBIOS
	MAX-ACCESS	not-accessible
	STATUS		current
	DESCRIPTION	"This group defines the attributes for the System BIOS."
	INDEX		{ DmiCompId,DmiGroupId, bIOSIndex }
	::= { dmtfSystemBIOSTable 1 }


dmtfSystemBIOSState OBJECT-TYPE
	SYNTAX		INTEGER {
		active(1),
		notInService(2),
		notReady(3),
		createAndGo(4),
		createAndWait(5),
		destroy(6)
	}
	MAX-ACCESS	read-write
	STATUS		current
	REFERENCE "'DMTF|System BIOS|001' 0"
	::= { dmtfSystemBIOSEntry 0 }

bIOSIndex OBJECT-TYPE
	SYNTAX		DmiInteger
	MAX-ACCESS	read-only
	STATUS		current
	DESCRIPTION	"The index into the system BIOS table."
	REFERENCE "'DMTF|System BIOS|001' 1"
	::= { dmtfSystemBIOSEntry 1 }

bIOSManufacturer OBJECT-TYPE
	SYNTAX		DmiString
	MAX-ACCESS	read-only
	STATUS		current
	DESCRIPTION	"The name of the company that wrote this System BIOS."
	REFERENCE "'DMTF|System BIOS|001' 2"
	::= { dmtfSystemBIOSEntry 2 }

bIOSVersion OBJECT-TYPE
	SYNTAX		DmiString
	MAX-ACCESS	read-only
	STATUS		current
	DESCRIPTION	"The version number or version string of this BIOS."
	REFERENCE "'DMTF|System BIOS|001' 3"
	::= { dmtfSystemBIOSEntry 3 }

bIOSROMSize OBJECT-TYPE
	SYNTAX		DmiInteger
	MAX-ACCESS	read-only
	STATUS		current
	DESCRIPTION	"The physical size of this BIOS ROM device in kilobytes."
	REFERENCE "'DMTF|System BIOS|001' 4"
	::= { dmtfSystemBIOSEntry 4 }

bIOSStartingAddress OBJECT-TYPE
	SYNTAX		Dmi-Integer64
	MAX-ACCESS	read-only
	STATUS		current
	DESCRIPTION	"The starting physical address for the memory which the BIOS
occupies."
	REFERENCE "'DMTF|System BIOS|001' 5"
	::= { dmtfSystemBIOSEntry 5 }

bIOSEndingAddress OBJECT-TYPE
	SYNTAX		Dmi-Integer64
	MAX-ACCESS	read-only
	STATUS		current
	DESCRIPTION	"The ending physical address for the memory which the BIOS
occupies."
	REFERENCE "'DMTF|System BIOS|001' 6"
	::= { dmtfSystemBIOSEntry 6 }

bIOSLoaderVersion OBJECT-TYPE
	SYNTAX		DmiString
	MAX-ACCESS	read-only
	STATUS		current
	DESCRIPTION	"The BIOS flash loader version number or string."
	REFERENCE "'DMTF|System BIOS|001' 7"
	::= { dmtfSystemBIOSEntry 7 }

bIOSReleaseDate OBJECT-TYPE
	SYNTAX		Dmi-Date
	MAX-ACCESS	read-only
	STATUS		current
	DESCRIPTION	"The BIOS release date."
	REFERENCE "'DMTF|System BIOS|001' 8"
	::= { dmtfSystemBIOSEntry 8 }

primaryBIOS OBJECT-TYPE
	SYNTAX		INTEGER {
		false(0),
		true(1)
	}
	MAX-ACCESS	read-only
	STATUS		current
	DESCRIPTION	"If true, this is the primary System BIOS."
	REFERENCE "'DMTF|System BIOS|001' 9"
	::= { dmtfSystemBIOSEntry 9 }

SdmtfSystemCache ::= SEQUENCE {
	dmtfSystemCacheState INTEGER,
	systemCacheIndex	DmiInteger,
	systemCacheLevel	DmiInteger,
	systemCacheSpeed	DmiInteger,
	systemCacheSize	DmiInteger,
	systemCacheWritePolicy	DmiInteger,
	systemCacheErrorCorrection	DmiInteger,
	fRUGroupIndex	DmiInteger,
	operationalGroupIndex	DmiInteger,
	systemCacheType	DmiInteger,
	lineSize	DmiInteger,
	volatility	DmiInteger,
	replacementPolicy	DmiInteger,
	readPolicy	DmiInteger,
	flushTimer	DmiInteger,
	associativity	DmiInteger
}

dmtfSystemCacheTable OBJECT-TYPE
	SYNTAX		SEQUENCE OF SdmtfSystemCache
	MAX-ACCESS	not-accessible
	STATUS		current
	DESCRIPTION	"This group defines the attributes for different System Caches
installed in this system."
	::= { dmtfSystemsMIF 9 }

dmtfSystemCacheEntry OBJECT-TYPE
	SYNTAX		SdmtfSystemCache
	MAX-ACCESS	not-accessible
	STATUS		current
	DESCRIPTION	"This group defines the attributes for different System Caches
installed in this system."
	INDEX		{ DmiCompId,DmiGroupId, systemCacheIndex }
	::= { dmtfSystemCacheTable 1 }


dmtfSystemCacheState OBJECT-TYPE
	SYNTAX		INTEGER {
		active(1),
		notInService(2),
		notReady(3),
		createAndGo(4),
		createAndWait(5),
		destroy(6)
	}
	MAX-ACCESS	read-write
	STATUS		current
	REFERENCE "'DMTF|System Cache|003' 0"
	::= { dmtfSystemCacheEntry 0 }

systemCacheIndex OBJECT-TYPE
	SYNTAX		DmiInteger
	MAX-ACCESS	read-only
	STATUS		current
	DESCRIPTION	"An index into the System Cache table."
	REFERENCE "'DMTF|System Cache|003' 1"
	::= { dmtfSystemCacheEntry 1 }

systemCacheLevel OBJECT-TYPE
	SYNTAX		INTEGER {
		other(1),
		unknown(2),
		primary(3),
		secondary(4),
		tertiary(5)
	}
	MAX-ACCESS	read-only
	STATUS		current
	DESCRIPTION	"Is this the primary System Cache, or a subsidiary cache?"
	REFERENCE "'DMTF|System Cache|003' 2"
	::= { dmtfSystemCacheEntry 2 }

systemCacheSpeed OBJECT-TYPE
	SYNTAX		DmiInteger
	MAX-ACCESS	read-only
	STATUS		current
	DESCRIPTION	"The speed of this System Cache module in nanoseconds."
	REFERENCE "'DMTF|System Cache|003' 3"
	::= { dmtfSystemCacheEntry 3 }

systemCacheSize OBJECT-TYPE
	SYNTAX		DmiInteger
	MAX-ACCESS	read-only
	STATUS		current
	DESCRIPTION	"The size of this System Cache module in kilobytes."
	REFERENCE "'DMTF|System Cache|003' 4"
	::= { dmtfSystemCacheEntry 4 }

systemCacheWritePolicy OBJECT-TYPE
	SYNTAX		INTEGER {
		other(1),
		unknown(2),
		writeBack(3),
		writeThrough(4),
		variesWithAddress(5)
	}
	MAX-ACCESS	read-only
	STATUS		current
	DESCRIPTION	"Is this a write-back or a write-through cache?"
	REFERENCE "'DMTF|System Cache|003' 5"
	::= { dmtfSystemCacheEntry 5 }

systemCacheErrorCorrection OBJECT-TYPE
	SYNTAX		INTEGER {
		other(1),
		unknown(2),
		none(3),
		parity(4),
		singleBitECC(5),
		multiBitECC(6)
	}
	MAX-ACCESS	read-only
	STATUS		current
	DESCRIPTION	"The error correction scheme supported by this cache component."
	REFERENCE "'DMTF|System Cache|003' 6"
	::= { dmtfSystemCacheEntry 6 }

fRUGroupIndex OBJECT-TYPE
	SYNTAX		DmiInteger
	MAX-ACCESS	read-only
	STATUS		current
	DESCRIPTION	"If this is a Field Replaceable Unit or if it is part of another
FRU, this provides an index into the FRU table; 'value = -1' indicates that
the group is not a FRU."
	REFERENCE "'DMTF|System Cache|003' 7"
	::= { dmtfSystemCacheEntry 7 }

operationalGroupIndex OBJECT-TYPE
	SYNTAX		DmiInteger
	MAX-ACCESS	read-only
	STATUS		current
	DESCRIPTION	"The index into the Operational State Table for this device."
	REFERENCE "'DMTF|System Cache|003' 8"
	::= { dmtfSystemCacheEntry 8 }

systemCacheType OBJECT-TYPE
	SYNTAX		INTEGER {
		other(1),
		unknown(2),
		instruction(3),
		data(4),
		unified(5)
	}
	MAX-ACCESS	read-only
	STATUS		current
	DESCRIPTION	"This defines the system cache type."
	REFERENCE "'DMTF|System Cache|003' 9"
	::= { dmtfSystemCacheEntry 9 }

lineSize OBJECT-TYPE
	SYNTAX		DmiInteger
	MAX-ACCESS	read-only
	STATUS		current
	DESCRIPTION	"The size, in bytes, of a single cache bucket or line."
	REFERENCE "'DMTF|System Cache|003' 10"
	::= { dmtfSystemCacheEntry 10 }

volatility OBJECT-TYPE
	SYNTAX		INTEGER {
		other(1),
		unknown(2),
		temporaryVolatile(3),
		volatile(4),
		permanentNonVolatile(5),
		temporaryNonVolatile(6),
		uPSNonVolatile(7)
	}
	MAX-ACCESS	read-only
	STATUS		current
	DESCRIPTION	"This defines the volatility of the cache."
	REFERENCE "'DMTF|System Cache|003' 11"
	::= { dmtfSystemCacheEntry 11 }

replacementPolicy OBJECT-TYPE
	SYNTAX		INTEGER {
		other(1),
		unknown(2),
		leastRecentlyUsedLRU(3),
		firstInFirstOutFIFO(4),
		lastInFirstOutLIFO(5),
		leastFrequentlyUsedLFU(6),
		mostFrequentlyUsedMFU(7)
	}
	MAX-ACCESS	read-only
	STATUS		current
	DESCRIPTION	"The algorithm used by the cache to determine which cache
lines or buckets should be re-used."
	REFERENCE "'DMTF|System Cache|003' 12"
	::= { dmtfSystemCacheEntry 12 }

readPolicy OBJECT-TYPE
	SYNTAX		INTEGER {
		other(1),
		unknown(2),
		read(3),
		readAhead(4),
		readAndReadAhead(5)
	}
	MAX-ACCESS	read-only
	STATUS		current
	DESCRIPTION	"The policy that shall be employed by the cache for handling
read requests."
	REFERENCE "'DMTF|System Cache|003' 13"
	::= { dmtfSystemCacheEntry 13 }

flushTimer OBJECT-TYPE
	SYNTAX		DmiInteger
	MAX-ACCESS	read-only
	STATUS		current
	DESCRIPTION	"The maximum amount of time, in seconds, dirty lines or buckets
may remain in the cache before they are flushed. A value of zero indicated
that a cache flush is not controlled by a flushing timer."
	REFERENCE "'DMTF|System Cache|003' 14"
	::= { dmtfSystemCacheEntry 14 }

associativity OBJECT-TYPE
	SYNTAX		INTEGER {
		other(1),
		unknown(2),
		directMapped(3),
		x2WaySetAssociative(4),
		x4WaySetAssociative(5),
		fullyAssociative(6)
	}
	MAX-ACCESS	read-only
	STATUS		current
	DESCRIPTION	"This defines the system cache associativity (direct-mapped,
2-way, 4-way, etc)."
	REFERENCE "'DMTF|System Cache|003' 15"
	::= { dmtfSystemCacheEntry 15 }

SdmtfSystemContactInformation ::= SEQUENCE {
	dmtfSystemContactInformationState INTEGER,
	contactIndex	DmiInteger,
	contactName	DmiString,
	contactType	DmiInteger,
	contactInformation	DmiString
}

dmtfSystemContactInformationTable OBJECT-TYPE
	SYNTAX		SEQUENCE OF SdmtfSystemContactInformation
	MAX-ACCESS	not-accessible
	STATUS		current
	DESCRIPTION	"This tabular group contains records, each of which contains
contact information for one of the administrators of this machine"
	::= { dmtfSystemsMIF 70 }

dmtfSystemContactInformationEntry OBJECT-TYPE
	SYNTAX		SdmtfSystemContactInformation
	MAX-ACCESS	not-accessible
	STATUS		current
	DESCRIPTION	"This tabular group contains records, each of which contains
contact information for one of the administrators of this machine"
	INDEX		{ DmiCompId,DmiGroupId, contactIndex }
	::= { dmtfSystemContactInformationTable 1 }


dmtfSystemContactInformationState OBJECT-TYPE
	SYNTAX		INTEGER {
		active(1),
		notInService(2),
		notReady(3),
		createAndGo(4),
		createAndWait(5),
		destroy(6)
	}
	MAX-ACCESS	read-write
	STATUS		current
	REFERENCE "'DMTF|System Contact Information|001' 0"
	::= { dmtfSystemContactInformationEntry 0 }

contactIndex OBJECT-TYPE
	SYNTAX		DmiInteger
	MAX-ACCESS	read-only
	STATUS		current
	DESCRIPTION	"Index into table of administrator contacts for this system"
	REFERENCE "'DMTF|System Contact Information|001' 1"
	::= { dmtfSystemContactInformationEntry 1 }

contactName OBJECT-TYPE
	SYNTAX		DmiString
	MAX-ACCESS	read-write
	STATUS		current
	DESCRIPTION	"Name of administrator contact for this machine"
	REFERENCE "'DMTF|System Contact Information|001' 2"
	::= { dmtfSystemContactInformationEntry 2 }

contactType OBJECT-TYPE
	SYNTAX		INTEGER {
		other(0),
		unknown(1),
		telephone(2),
		cellularTelephone(3),
		pager(4),
		alphamericPager(5),
		beeper(6),
		fAX(7),
		eMail(8),
		voiceMail(9),
		audibleAlarm(10),
		visibleAlarm(11),
		wWWURL(12)
	}
	MAX-ACCESS	read-write
	STATUS		current
	DESCRIPTION	"The type of mechanism by which this administrator can be
contacted."
	REFERENCE "'DMTF|System Contact Information|001' 3"
	::= { dmtfSystemContactInformationEntry 3 }

contactInformation OBJECT-TYPE
	SYNTAX		DmiString
	MAX-ACCESS	read-write
	STATUS		current
	DESCRIPTION	"Addressing or other information that will be used to establish
contact e.g. if Contact Type is Telephone then Contact Information would
be the telephone number."
	REFERENCE "'DMTF|System Contact Information|001' 4"
	::= { dmtfSystemContactInformationEntry 4 }

SdmtfSystemEnclosure ::= SEQUENCE {
	enclosureOrChassisType	DmiInteger,
	assetTag	DmiString,
	chassisLockPresent	DmiInteger,
	bootupState	DmiInteger,
	powerState	DmiInteger,
	thermalState	DmiInteger,
	fRUGroupIndex	DmiInteger,
	operationalGroupIndex	DmiInteger
}

dmtfSystemEnclosureTable OBJECT-TYPE
	SYNTAX		SEQUENCE OF SdmtfSystemEnclosure
	MAX-ACCESS	not-accessible
	STATUS		current
	DESCRIPTION	"This group defines the attributes for the system enclosure."
	::= { dmtfSystemsMIF 15 }

dmtfSystemEnclosureEntry OBJECT-TYPE
	SYNTAX		SdmtfSystemEnclosure
	MAX-ACCESS	not-accessible
	STATUS		current
	DESCRIPTION	"This group defines the attributes for the system enclosure."
	INDEX		{ DmiCompId,DmiGroupId }
	::= { dmtfSystemEnclosureTable 1 }


enclosureOrChassisType OBJECT-TYPE
	SYNTAX		INTEGER {
		other(1),
		unknown(2),
		desktop(3),
		lowProfileDesktop(4),
		pizzaBox(5),
		miniTower(6),
		tower(7),
		portable(8),
		lapTop(9),
		notebook(10),
		handHeld(11),
		dockingStation(12),
		allInOne(13),
		subNotebook(14),
		spaceSaving(15),
		lunchBox(16),
		mainSystemChassis(17),
		expansionChassis(18),
		subChassis(19),
		busExpansionChassis(20),
		peripheralChassis(21),
		rAIDChassis(22),
		rackMountChassis(23),
		sealedCasePC(24)
	}
	MAX-ACCESS	read-only
	STATUS		current
	DESCRIPTION	"The type of enclosure."
	REFERENCE "'DMTF|System Enclosure|003' 1"
	::= { dmtfSystemEnclosureEntry 1 }

assetTag OBJECT-TYPE
	SYNTAX		DmiString
	MAX-ACCESS	read-write
	STATUS		current
	DESCRIPTION	"The system asset tag string."
	REFERENCE "'DMTF|System Enclosure|003' 2"
	::= { dmtfSystemEnclosureEntry 2 }

chassisLockPresent OBJECT-TYPE
	SYNTAX		INTEGER {
		false(0),
		true(1)
	}
	MAX-ACCESS	read-only
	STATUS		current
	DESCRIPTION	"If true, a chassis lock is present."
	REFERENCE "'DMTF|System Enclosure|003' 3"
	::= { dmtfSystemEnclosureEntry 3 }

bootupState OBJECT-TYPE
	SYNTAX		INTEGER {
		other(1),
		unknown(2),
		oK(3),
		warning(4),
		critical(5),
		nonRecoverable(6)
	}
	MAX-ACCESS	read-only
	STATUS		current
	DESCRIPTION	"The current state of this system when it booted."
	REFERENCE "'DMTF|System Enclosure|003' 4"
	::= { dmtfSystemEnclosureEntry 4 }

powerState OBJECT-TYPE
	SYNTAX		INTEGER {
		other(1),
		unknown(2),
		oK(3),
		warning(4),
		critical(5),
		nonRecoverable(6)
	}
	MAX-ACCESS	read-only
	STATUS		current
	DESCRIPTION	"The current state of the power supply for this system."
	REFERENCE "'DMTF|System Enclosure|003' 5"
	::= { dmtfSystemEnclosureEntry 5 }

thermalState OBJECT-TYPE
	SYNTAX		INTEGER {
		other(1),
		unknown(2),
		oK(3),
		warning(4),
		critical(5),
		nonRecoverable(6)
	}
	MAX-ACCESS	read-only
	STATUS		current
	DESCRIPTION	"The current thermal state of this system."
	REFERENCE "'DMTF|System Enclosure|003' 6"
	::= { dmtfSystemEnclosureEntry 6 }

fRUGroupIndex OBJECT-TYPE
	SYNTAX		DmiInteger
	MAX-ACCESS	read-only
	STATUS		current
	DESCRIPTION	"If this is a Field Replaceable Unit or if it is part of another
FRU, this provides an index into the FRU table; 'value = -1' indicates that
the group is not a FRU."
	REFERENCE "'DMTF|System Enclosure|003' 7"
	::= { dmtfSystemEnclosureEntry 7 }

operationalGroupIndex OBJECT-TYPE
	SYNTAX		DmiInteger
	MAX-ACCESS	read-only
	STATUS		current
	DESCRIPTION	"The index into the Operational State table for this device
if applicable."
	REFERENCE "'DMTF|System Enclosure|003' 8"
	::= { dmtfSystemEnclosureEntry 8 }

SdmtfSystemHardwareSecurity ::= SEQUENCE {
	powerOnPasswordStatus	DmiInteger,
	keyboardPasswordStatus	DmiInteger,
	administratorPasswordStatis	DmiInteger,
	frontPanelResetStatus	DmiInteger
}

dmtfSystemHardwareSecurityTable OBJECT-TYPE
	SYNTAX		SEQUENCE OF SdmtfSystemHardwareSecurity
	MAX-ACCESS	not-accessible
	STATUS		current
	DESCRIPTION	"This group describes the system-wide hardware security settings."
	::= { dmtfSystemsMIF 49 }

dmtfSystemHardwareSecurityEntry OBJECT-TYPE
	SYNTAX		SdmtfSystemHardwareSecurity
	MAX-ACCESS	not-accessible
	STATUS		current
	DESCRIPTION	"This group describes the system-wide hardware security settings."
	INDEX		{ DmiCompId,DmiGroupId }
	::= { dmtfSystemHardwareSecurityTable 1 }


powerOnPasswordStatus OBJECT-TYPE
	SYNTAX		INTEGER {
		other(1),
		unknown(2),
		disabled(3),
		enabled(4),
		notImplemented(5)
	}
	MAX-ACCESS	read-only
	STATUS		current
	DESCRIPTION	"The current power-on password setting on the system."
	REFERENCE "'DMTF|System Hardware Security|001' 1"
	::= { dmtfSystemHardwareSecurityEntry 1 }

keyboardPasswordStatus OBJECT-TYPE
	SYNTAX		INTEGER {
		other(1),
		unknown(2),
		disabled(3),
		enabled(4),
		notImplemented(5)
	}
	MAX-ACCESS	read-only
	STATUS		current
	DESCRIPTION	"The current keyboard password setting on the system"
	REFERENCE "'DMTF|System Hardware Security|001' 2"
	::= { dmtfSystemHardwareSecurityEntry 2 }

administratorPasswordStatis OBJECT-TYPE
	SYNTAX		INTEGER {
		other(1),
		unknown(2),
		disabled(3),
		enabled(4),
		notImplemented(5)
	}
	MAX-ACCESS	read-only
	STATUS		current
	DESCRIPTION	"The current administrator password setting on the system.
This password is required to make hardware configuration changes to the system."
	REFERENCE "'DMTF|System Hardware Security|001' 3"
	::= { dmtfSystemHardwareSecurityEntry 3 }

frontPanelResetStatus OBJECT-TYPE
	SYNTAX		INTEGER {
		other(1),
		unknown(2),
		disabled(3),
		enabled(4),
		notImplemented(5)
	}
	MAX-ACCESS	read-only
	STATUS		current
	DESCRIPTION	"The present status of the front panel reset button capability.
If Enabled, the machine can be reset via the front panel reset button. If
Disabled, the reset button, if available, is inoperative."
	REFERENCE "'DMTF|System Hardware Security|001' 4"
	::= { dmtfSystemHardwareSecurityEntry 4 }

SdmtfSystemMemorySettings ::= SEQUENCE {
	totalPhysicalMemory	DmiInteger,
	freePhysicalMemory	DmiInteger,
	totalSizeOfPagingFiles	DmiInteger,
	totalFreeSpaceInPagingFiles	DmiInteger,
	totalVirtualMemory	DmiInteger,
	freeVirtualMemory	DmiInteger
}

dmtfSystemMemorySettingsTable OBJECT-TYPE
	SYNTAX		SEQUENCE OF SdmtfSystemMemorySettings
	MAX-ACCESS	not-accessible
	STATUS		current
	DESCRIPTION	"This group defines the current memory settings for system
memory and any add-on memory installed in the operating system."
	::= { dmtfSystemsMIF 71 }

dmtfSystemMemorySettingsEntry OBJECT-TYPE
	SYNTAX		SdmtfSystemMemorySettings
	MAX-ACCESS	not-accessible
	STATUS		current
	DESCRIPTION	"This group defines the current memory settings for system
memory and any add-on memory installed in the operating system."
	INDEX		{ DmiCompId,DmiGroupId }
	::= { dmtfSystemMemorySettingsTable 1 }


totalPhysicalMemory OBJECT-TYPE
	SYNTAX		DmiInteger
	MAX-ACCESS	read-only
	STATUS		current
	DESCRIPTION	"The total size of physical system memory in kilobytes."
	REFERENCE "'DMTF|System Memory Settings|001' 1"
	::= { dmtfSystemMemorySettingsEntry 1 }

freePhysicalMemory OBJECT-TYPE
	SYNTAX		DmiInteger
	MAX-ACCESS	read-only
	STATUS		current
	DESCRIPTION	"The amount of physical memory free in kilobytes."
	REFERENCE "'DMTF|System Memory Settings|001' 2"
	::= { dmtfSystemMemorySettingsEntry 2 }

totalSizeOfPagingFiles OBJECT-TYPE
	SYNTAX		DmiInteger
	MAX-ACCESS	read-only
	STATUS		current
	DESCRIPTION	"The total number of kilobytes that can be stored in the system
paging files."
	REFERENCE "'DMTF|System Memory Settings|001' 3"
	::= { dmtfSystemMemorySettingsEntry 3 }

totalFreeSpaceInPagingFiles OBJECT-TYPE
	SYNTAX		DmiInteger
	MAX-ACCESS	read-only
	STATUS		current
	DESCRIPTION	"The number of kilobytes available in the system paging files."
	REFERENCE "'DMTF|System Memory Settings|001' 4"
	::= { dmtfSystemMemorySettingsEntry 4 }

totalVirtualMemory OBJECT-TYPE
	SYNTAX		DmiInteger
	MAX-ACCESS	read-only
	STATUS		current
	DESCRIPTION	"Total kilobytes in the virtual address space of the operating
system."
	REFERENCE "'DMTF|System Memory Settings|001' 5"
	::= { dmtfSystemMemorySettingsEntry 5 }

freeVirtualMemory OBJECT-TYPE
	SYNTAX		DmiInteger
	MAX-ACCESS	read-only
	STATUS		current
	DESCRIPTION	"Free kilobytes in the virtual address space of the operating
system."
	REFERENCE "'DMTF|System Memory Settings|001' 6"
	::= { dmtfSystemMemorySettingsEntry 6 }

SdmtfSystemPowerControls ::= SEQUENCE {
	powerControlRequest	DmiInteger,
	timedPowerOnAvailable	DmiInteger,
	timeToNextScheduledPowerOn	DmiInteger
}

dmtfSystemPowerControlsTable OBJECT-TYPE
	SYNTAX		SEQUENCE OF SdmtfSystemPowerControls
	MAX-ACCESS	not-accessible
	STATUS		current
	DESCRIPTION	"This group defines attributes for controlling the main power
supply to the system."
	::= { dmtfSystemsMIF 51 }

dmtfSystemPowerControlsEntry OBJECT-TYPE
	SYNTAX		SdmtfSystemPowerControls
	MAX-ACCESS	not-accessible
	STATUS		current
	DESCRIPTION	"This group defines attributes for controlling the main power
supply to the system."
	INDEX		{ DmiCompId,DmiGroupId }
	::= { dmtfSystemPowerControlsTable 1 }


powerControlRequest OBJECT-TYPE
	SYNTAX		INTEGER {
		other(1),
		unknown(2),
		powerOff(3),
		powerOffThenOnAgain(4),
		enterStandbyMode(5),
		enterSuspendMode(6),
		enterHibernationMode(7)
	}
	MAX-ACCESS	read-write
	STATUS		current
	DESCRIPTION	"Reading the value of this attribute gives the value of the
last valid power control request that was written into it. Writing a valid
value into it causes the appropriate power control action to be executed
immediately. Writing an invalid or unimplemented value causes no change."
	REFERENCE "'DMTF|System Power Controls|001' 1"
	::= { dmtfSystemPowerControlsEntry 1 }

timedPowerOnAvailable OBJECT-TYPE
	SYNTAX		INTEGER {
		false(0),
		true(1),
		unknown(2)
	}
	MAX-ACCESS	read-only
	STATUS		current
	DESCRIPTION	"Defines whether a timed power-on facility is available."
	REFERENCE "'DMTF|System Power Controls|001' 2"
	::= { dmtfSystemPowerControlsEntry 2 }

timeToNextScheduledPowerOn OBJECT-TYPE
	SYNTAX		DmiInteger
	MAX-ACCESS	read-write
	STATUS		current
	DESCRIPTION	"The number of seconds until the next timed power-on is scheduled
to occur. A value of 0 means that if the system is powered off, no automatic
timed poweron will occur. A value of 0x80000000 denotes 'unknown'."
	REFERENCE "'DMTF|System Power Controls|001' 3"
	::= { dmtfSystemPowerControlsEntry 3 }

SdmtfSystemReset ::= SEQUENCE {
	automaticSystemResetCapability	DmiInteger,
	automaticSystemResetStatus	DmiInteger,
	automaticSystemResetBootOption	DmiInteger,
	automaticSystemResetCount	DmiInteger,
	automaticSystemResetLimit	DmiInteger,
	automaticSystemResetBootOptionAtLimit	DmiInteger,
	automaticSystemResetTimerInterval	DmiInteger,
	automaticSystemResetTimerInterval	DmiInteger,
	automaticSystemResetTimerReset	DmiInteger,
	systemResetTimeout	DmiInteger,
	systemResetBootOption	DmiInteger
}

dmtfSystemResetTable OBJECT-TYPE
	SYNTAX		SEQUENCE OF SdmtfSystemReset
	MAX-ACCESS	not-accessible
	STATUS		current
	DESCRIPTION	"This group defines whether Automatic System Reset functions
are available (Capability) and enabled (Status). If the system has a watchdog
Timer and the timer is not reset (Timer Reset) before the Interval elapses,
an automatic system reset will occur. The system will re-boot according to
the Boot Option. This function may repeat until the Limit is reached, at
which time the system will re-boot according to the Boot Option at Limit."
	::= { dmtfSystemsMIF 48 }

dmtfSystemResetEntry OBJECT-TYPE
	SYNTAX		SdmtfSystemReset
	MAX-ACCESS	not-accessible
	STATUS		current
	DESCRIPTION	"This group defines whether Automatic System Reset functions
are available (Capability) and enabled (Status). If the system has a watchdog
Timer and the timer is not reset (Timer Reset) before the Interval elapses,
an automatic system reset will occur. The system will re-boot according to
the Boot Option. This function may repeat until the Limit is reached, at
which time the system will re-boot according to the Boot Option at Limit."
	INDEX		{ DmiCompId,DmiGroupId }
	::= { dmtfSystemResetTable 1 }


automaticSystemResetCapability OBJECT-TYPE
	SYNTAX		INTEGER {
		other(1),
		unknown(2),
		available(3),
		notAvailable(4)
	}
	MAX-ACCESS	read-only
	STATUS		current
	DESCRIPTION	"Indicates whether Automatic System Reset Capability is available
for the current operating system."
	REFERENCE "'DMTF|System Reset|001' 1"
	::= { dmtfSystemResetEntry 1 }

automaticSystemResetStatus OBJECT-TYPE
	SYNTAX		INTEGER {
		other(1),
		unknown(2),
		enabled(3),
		disabled(4)
	}
	MAX-ACCESS	read-write
	STATUS		current
	DESCRIPTION	"Indicates whether Automatic System Reset is enabled by the
user."
	REFERENCE "'DMTF|System Reset|001' 2"
	::= { dmtfSystemResetEntry 2 }

automaticSystemResetBootOption OBJECT-TYPE
	SYNTAX		INTEGER {
		other(1),
		unknown(2),
		operatingSystem(3),
		utilities(4),
		doNotReBoot(5)
	}
	MAX-ACCESS	read-write
	STATUS		current
	DESCRIPTION	"Indicates whether Automatic System Reset will boot to the
operating system, boot to utilities, or not re-boot. This is the action to
be taken following a reset."
	REFERENCE "'DMTF|System Reset|001' 3"
	::= { dmtfSystemResetEntry 3 }

automaticSystemResetCount OBJECT-TYPE
	SYNTAX		DmiInteger
	MAX-ACCESS	read-write
	STATUS		current
	DESCRIPTION	"The number of Automatic System Resets since last intentional
reset. A value of 0x80000000 denotes 'unknown'."
	REFERENCE "'DMTF|System Reset|001' 4"
	::= { dmtfSystemResetEntry 4 }

automaticSystemResetLimit OBJECT-TYPE
	SYNTAX		DmiInteger
	MAX-ACCESS	read-write
	STATUS		current
	DESCRIPTION	"The number of consecutive times the Automatic System Reset
will be attempted. A value of 0x80000000 denotes 'unknown'."
	REFERENCE "'DMTF|System Reset|001' 5"
	::= { dmtfSystemResetEntry 5 }

automaticSystemResetBootOptionAtLimit OBJECT-TYPE
	SYNTAX		INTEGER {
		other(1),
		unknown(2),
		operatingSystem(3),
		utilities(4),
		doNotReBoot(5)
	}
	MAX-ACCESS	read-write
	STATUS		current
	DESCRIPTION	"Indicates the action to be taken when the Automatic System
Reset Limit is reached."
	REFERENCE "'DMTF|System Reset|001' 6"
	::= { dmtfSystemResetEntry 6 }

automaticSystemResetTimerPresent OBJECT-TYPE
	SYNTAX		INTEGER {
		false(0),
		true(1),
		unknown(2)
	}
	MAX-ACCESS	read-write
	STATUS		current
	DESCRIPTION	"Indicates whether this system has a watchdog timer."
	REFERENCE "'DMTF|System Reset|001' 7"
	::= { dmtfSystemResetEntry 7 }

automaticSystemResetTimerInterval OBJECT-TYPE
	SYNTAX		DmiInteger
	MAX-ACCESS	read-write
	STATUS		current
	DESCRIPTION	"The number of minutes to use for watchdog timer. If the timer
is not reset within this interval, the automatic system reset timeout will
begin. A value of 0x80000000 denotes 'unknown'."
	REFERENCE "'DMTF|System Reset|001' 8"
	::= { dmtfSystemResetEntry 8 }

automaticSystemResetTimerReset OBJECT-TYPE
	SYNTAX		INTEGER {
		false(0),
		true(1),
		unknown(2)
	}
	MAX-ACCESS	read-write
	STATUS		current
	DESCRIPTION	"Initiate the reset of the automatic system reset watchdog
timer. Setting this attribute to True will cause the watchdog timer to reset."
	REFERENCE "'DMTF|System Reset|001' 9"
	::= { dmtfSystemResetEntry 9 }

systemResetTimeout OBJECT-TYPE
	SYNTAX		DmiInteger
	MAX-ACCESS	read-write
	STATUS		current
	DESCRIPTION	"This attribute identifies the number of minutes before the
re-boot is initiated. It is used after system power cycle, system reset (local
or remote), and automatic system reset. A value of 0x80000000 denotes 'unknown'."
	REFERENCE "'DMTF|System Reset|001' 10"
	::= { dmtfSystemResetEntry 10 }

systemResetBootOption OBJECT-TYPE
	SYNTAX		INTEGER {
		other(1),
		unknown(2),
		operatingSystem(3),
		utilities(4),
		doNotReBoot(5)
	}
	MAX-ACCESS	read-write
	STATUS		current
	DESCRIPTION	"Indicates whether to boot to the operating system or the
utilities when a system reset or system power cycle is performed, either
locally or remotely."
	REFERENCE "'DMTF|System Reset|001' 11"
	::= { dmtfSystemResetEntry 11 }

SdmtfSystemResourceDMAInfo ::= SEQUENCE {
	dmtfSystemResourceDMAInfoState INTEGER,
	systemResourceDMAInfoIndex	DmiInteger,
	dMATransferWidth	DmiInteger,
	dMAAddressSize	DmiInteger,
	dMAMaximumTransferSize	DmiInteger,
	dMATransferPreference	DmiInteger,
	busMaster	DmiInteger,
	byteMode	DmiInteger,
	wordMode	DmiInteger,
	channelTiming	DmiInteger,
	typeCTiming	DmiInteger
}

dmtfSystemResourceDMAInfoTable OBJECT-TYPE
	SYNTAX		SEQUENCE OF SdmtfSystemResourceDMAInfo
	MAX-ACCESS	not-accessible
	STATUS		current
	DESCRIPTION	"This group presents additional information about DMA resources
that have been defined in the System Resources table."
	::= { dmtfSystemsMIF 42 }

dmtfSystemResourceDMAInfoEntry OBJECT-TYPE
	SYNTAX		SdmtfSystemResourceDMAInfo
	MAX-ACCESS	not-accessible
	STATUS		current
	DESCRIPTION	"This group presents additional information about DMA resources
that have been defined in the System Resources table."
	INDEX		{ DmiCompId,DmiGroupId, systemResourceDMAInfoIndex }
	::= { dmtfSystemResourceDMAInfoTable 1 }


dmtfSystemResourceDMAInfoState OBJECT-TYPE
	SYNTAX		INTEGER {
		active(1),
		notInService(2),
		notReady(3),
		createAndGo(4),
		createAndWait(5),
		destroy(6)
	}
	MAX-ACCESS	read-write
	STATUS		current
	REFERENCE "'DMTF|System Resource DMA Info|001' 0"
	::= { dmtfSystemResourceDMAInfoEntry 0 }

systemResourceDMAInfoIndex OBJECT-TYPE
	SYNTAX		DmiInteger
	MAX-ACCESS	read-only
	STATUS		current
	DESCRIPTION	"A number the uniquely identifies rows in this table."
	REFERENCE "'DMTF|System Resource DMA Info|001' 1"
	::= { dmtfSystemResourceDMAInfoEntry 1 }

dMATransferWidth OBJECT-TYPE
	SYNTAX		INTEGER {
		other(1),
		unknown(2),
		x8Bit(3),
		x8And16Bit(4),
		x16Bit(5),
		x32Bit(6),
		x64Bit(7),
		x128Bit(8)
	}
	MAX-ACCESS	read-only
	STATUS		current
	DESCRIPTION	"Width of DMA transfers supported"
	REFERENCE "'DMTF|System Resource DMA Info|001' 2"
	::= { dmtfSystemResourceDMAInfoEntry 2 }

dMAAddressSize OBJECT-TYPE
	SYNTAX		INTEGER {
		other(1),
		unknown(2),
		x8Bit(3),
		x16Bit(5),
		x32Bit(6),
		x64Bit(7)
	}
	MAX-ACCESS	read-only
	STATUS		current
	DESCRIPTION	"The width of the DMA address."
	REFERENCE "'DMTF|System Resource DMA Info|001' 3"
	::= { dmtfSystemResourceDMAInfoEntry 3 }

dMAMaximumTransferSize OBJECT-TYPE
	SYNTAX		DmiInteger
	MAX-ACCESS	read-only
	STATUS		current
	DESCRIPTION	"The maximum number of bytes that can be transferred by this
DMA Channel."
	REFERENCE "'DMTF|System Resource DMA Info|001' 4"
	::= { dmtfSystemResourceDMAInfoEntry 4 }

dMATransferPreference OBJECT-TYPE
	SYNTAX		INTEGER {
		other(1),
		unknown(2),
		x8Bit(3),
		x8And16Bit(4),
		x16Bit(5),
		x32Bit(6),
		x64Bit(7)
	}
	MAX-ACCESS	read-only
	STATUS		current
	DESCRIPTION	"DMA transfer type preference."
	REFERENCE "'DMTF|System Resource DMA Info|001' 5"
	::= { dmtfSystemResourceDMAInfoEntry 5 }

busMaster OBJECT-TYPE
	SYNTAX		INTEGER {
		other(1),
		unknown(2),
		logicalDeviceIsNotABusMaster(3),
		logicalDeviceIsABusMaster(4)
	}
	MAX-ACCESS	read-only
	STATUS		current
	DESCRIPTION	"Indicates whether the device is using DMA is a bus master."
	REFERENCE "'DMTF|System Resource DMA Info|001' 6"
	::= { dmtfSystemResourceDMAInfoEntry 6 }

byteMode OBJECT-TYPE
	SYNTAX		INTEGER {
		other(1),
		unknown(2),
		dMAMayNotExecuteInCountByByteMode(3),
		dMAMayExecuteInCountByByteMode(4)
	}
	MAX-ACCESS	read-only
	STATUS		current
	DESCRIPTION	"Indicates whether DMA may execute in 'count by byte' mode."
	REFERENCE "'DMTF|System Resource DMA Info|001' 7"
	::= { dmtfSystemResourceDMAInfoEntry 7 }

wordMode OBJECT-TYPE
	SYNTAX		INTEGER {
		other(1),
		unknown(2),
		dMAMayNotExecuteInCountByWordMode(3),
		dMAMayExecuteInCountByWordMode(4)
	}
	MAX-ACCESS	read-only
	STATUS		current
	DESCRIPTION	"Indicates whether DMA may execute in 'count by word' mode."
	REFERENCE "'DMTF|System Resource DMA Info|001' 8"
	::= { dmtfSystemResourceDMAInfoEntry 8 }

channelTiming OBJECT-TYPE
	SYNTAX		INTEGER {
		other(1),
		unknown(2),
		iSACompatible(3),
		typeA(4),
		typeB(5),
		typeF(6)
	}
	MAX-ACCESS	read-only
	STATUS		current
	DESCRIPTION	"DMA channel speed support."
	REFERENCE "'DMTF|System Resource DMA Info|001' 9"
	::= { dmtfSystemResourceDMAInfoEntry 9 }

typeCTiming OBJECT-TYPE
	SYNTAX		INTEGER {
		other(1),
		unknown(2),
		iSACompatible(3),
		cTypeTimingIsNotSupported(4),
		cTypeTimingIsSupported(5)
	}
	MAX-ACCESS	read-only
	STATUS		current
	DESCRIPTION	"Indicates whether C type (burst) timing is supported."
	REFERENCE "'DMTF|System Resource DMA Info|001' 10"
	::= { dmtfSystemResourceDMAInfoEntry 10 }

SdmtfSystemResourceDeviceInfo ::= SEQUENCE {
	dmtfSystemResourceDeviceInfoState INTEGER,
	resourceUser	DmiInteger,
	deviceID	DmiInteger,
	deviceSerialNumber	DmiInteger,
	logicalDeviceIDClassCode	DmiInteger,
	deviceFlags	DmiInteger,
	deviceNumber	DmiInteger,
	deviceNumber	DmiInteger,
	busType	DmiInteger,
	cMReserved	DmiInteger
}

dmtfSystemResourceDeviceInfoTable OBJECT-TYPE
	SYNTAX		SEQUENCE OF SdmtfSystemResourceDeviceInfo
	MAX-ACCESS	not-accessible
	STATUS		current
	DESCRIPTION	"This group describes the base level of Memory, I/O, DMA,
and INT (interrupt) resources that are used by a device in the system."
	::= { dmtfSystemsMIF 38 }

dmtfSystemResourceDeviceInfoEntry OBJECT-TYPE
	SYNTAX		SdmtfSystemResourceDeviceInfo
	MAX-ACCESS	not-accessible
	STATUS		current
	DESCRIPTION	"This group describes the base level of Memory, I/O, DMA,
and INT (interrupt) resources that are used by a device in the system."
	INDEX		{ DmiCompId,DmiGroupId, resourceUser }
	::= { dmtfSystemResourceDeviceInfoTable 1 }


dmtfSystemResourceDeviceInfoState OBJECT-TYPE
	SYNTAX		INTEGER {
		active(1),
		notInService(2),
		notReady(3),
		createAndGo(4),
		createAndWait(5),
		destroy(6)
	}
	MAX-ACCESS	read-write
	STATUS		current
	REFERENCE "'DMTF|System Resource Device Info|001' 0"
	::= { dmtfSystemResourceDeviceInfoEntry 0 }

resourceUser OBJECT-TYPE
	SYNTAX		DmiInteger
	MAX-ACCESS	read-only
	STATUS		current
	DESCRIPTION	"A number that uniquely identifies this device. This number
may be derived from the 'device number' that is assigned by 'Plug N Play',
or may be uniquely assigned by the component instrumentation."
	REFERENCE "'DMTF|System Resource Device Info|001' 1"
	::= { dmtfSystemResourceDeviceInfoEntry 1 }

deviceID OBJECT-TYPE
	SYNTAX		DmiInteger
	MAX-ACCESS	read-only
	STATUS		current
	DESCRIPTION	"Physical Device ID from Config manager info. Equal to the
CISTPL-MANFID field for PCMCIA devices. 0xFFFFFFFF = Unknown"
	REFERENCE "'DMTF|System Resource Device Info|001' 2"
	::= { dmtfSystemResourceDeviceInfoEntry 2 }

deviceSerialNumber OBJECT-TYPE
	SYNTAX		DmiInteger
	MAX-ACCESS	read-only
	STATUS		current
	DESCRIPTION	"Device Serial Number from Config manager info. 0 = Undefined"
	REFERENCE "'DMTF|System Resource Device Info|001' 3"
	::= { dmtfSystemResourceDeviceInfoEntry 3 }

logicalDeviceIDClassCode OBJECT-TYPE
	SYNTAX		DmiInteger
	MAX-ACCESS	read-only
	STATUS		current
	DESCRIPTION	"Logical device ID for PnP ISA devices, Class code for PCI
devices, CISTPL-FUNCID for PCMCIA devices. 0xFFFFFFFF = Undefined, 0 = reserved"
	REFERENCE "'DMTF|System Resource Device Info|001' 4"
	::= { dmtfSystemResourceDeviceInfoEntry 4 }

deviceFlags OBJECT-TYPE
	SYNTAX		DmiInteger
	MAX-ACCESS	read-only
	STATUS		current
	DESCRIPTION	"Device flags from config manager info. Bit 0: 1 = device
has been initialized, 
 Bit 1: 1 = device is enabled, 
 Bit 2: 1 = device
config has been locked, 
 Bit 3: 1 = device has temporary config resources
assigned, 
 Bit 4: 1 = device is reconfigurable"
	REFERENCE "'DMTF|System Resource Device Info|001' 5"
	::= { dmtfSystemResourceDeviceInfoEntry 5 }

deviceNumber OBJECT-TYPE
	SYNTAX		DmiInteger
	MAX-ACCESS	read-only
	STATUS		current
	DESCRIPTION	"Device Number for PCI Devices, Logical Device number for
PnP Devices. 0 otherwise."
	REFERENCE "'DMTF|System Resource Device Info|001' 6"
	::= { dmtfSystemResourceDeviceInfoEntry 6 }

functionNumber OBJECT-TYPE
	SYNTAX		DmiInteger
	MAX-ACCESS	read-only
	STATUS		current
	DESCRIPTION	"Function Number for PCI & EISA Devices. 0 otherwise."
	REFERENCE "'DMTF|System Resource Device Info|001' 7"
	::= { dmtfSystemResourceDeviceInfoEntry 7 }

busType OBJECT-TYPE
	SYNTAX		DmiInteger
	MAX-ACCESS	read-only
	STATUS		current
	DESCRIPTION	"Bus number (0-255) for PCI Devices, Slot number for EISA
and PnP Devices, Card logical socket number for PCMCIA devices. Zero otherwise."
	REFERENCE "'DMTF|System Resource Device Info|001' 8"
	::= { dmtfSystemResourceDeviceInfoEntry 8 }

cMReserved OBJECT-TYPE
	SYNTAX		DmiInteger
	MAX-ACCESS	read-only
	STATUS		current
	DESCRIPTION	"Data from the Reserved field of the Configuration Manager
bus access structure, or 0."
	REFERENCE "'DMTF|System Resource Device Info|001' 9"
	::= { dmtfSystemResourceDeviceInfoEntry 9 }

SdmtfSystemResourceIOInfo ::= SEQUENCE {
	dmtfSystemResourceIOInfoState INTEGER,
	systemResourceIOInfoIndex	DmiInteger,
	iODecode	DmiInteger
}

dmtfSystemResourceIOInfoTable OBJECT-TYPE
	SYNTAX		SEQUENCE OF SdmtfSystemResourceIOInfo
	MAX-ACCESS	not-accessible
	STATUS		current
	DESCRIPTION	"This group presents additional information about I/O resources
that have been defined in the System Resources table."
	::= { dmtfSystemsMIF 40 }

dmtfSystemResourceIOInfoEntry OBJECT-TYPE
	SYNTAX		SdmtfSystemResourceIOInfo
	MAX-ACCESS	not-accessible
	STATUS		current
	DESCRIPTION	"This group presents additional information about I/O resources
that have been defined in the System Resources table."
	INDEX		{ DmiCompId,DmiGroupId, systemResourceIOInfoIndex }
	::= { dmtfSystemResourceIOInfoTable 1 }


dmtfSystemResourceIOInfoState OBJECT-TYPE
	SYNTAX		INTEGER {
		active(1),
		notInService(2),
		notReady(3),
		createAndGo(4),
		createAndWait(5),
		destroy(6)
	}
	MAX-ACCESS	read-write
	STATUS		current
	REFERENCE "'DMTF|System Resource I/O Info|001' 0"
	::= { dmtfSystemResourceIOInfoEntry 0 }

systemResourceIOInfoIndex OBJECT-TYPE
	SYNTAX		DmiInteger
	MAX-ACCESS	read-only
	STATUS		current
	DESCRIPTION	"A number the uniquely identifies rows in this table."
	REFERENCE "'DMTF|System Resource I/O Info|001' 1"
	::= { dmtfSystemResourceIOInfoEntry 1 }

iODecode OBJECT-TYPE
	SYNTAX		INTEGER {
		other(1),
		unknown(2),
		x10Bits(3),
		x16Bits(4)
	}
	MAX-ACCESS	read-only
	STATUS		current
	DESCRIPTION	"Number of bits used for I/O decode"
	REFERENCE "'DMTF|System Resource I/O Info|001' 2"
	::= { dmtfSystemResourceIOInfoEntry 2 }

SdmtfSystemResourceIRQInfo ::= SEQUENCE {
	dmtfSystemResourceIRQInfoState INTEGER,
	systemResourceIRQInfoIndex	DmiInteger,
	triggerType	DmiInteger,
	triggerLevel	DmiInteger
}

dmtfSystemResourceIRQInfoTable OBJECT-TYPE
	SYNTAX		SEQUENCE OF SdmtfSystemResourceIRQInfo
	MAX-ACCESS	not-accessible
	STATUS		current
	DESCRIPTION	"This group presents additional information about I/O resources
that have been defined in the System Resources table."
	::= { dmtfSystemsMIF 41 }

dmtfSystemResourceIRQInfoEntry OBJECT-TYPE
	SYNTAX		SdmtfSystemResourceIRQInfo
	MAX-ACCESS	not-accessible
	STATUS		current
	DESCRIPTION	"This group presents additional information about I/O resources
that have been defined in the System Resources table."
	INDEX		{ DmiCompId,DmiGroupId, systemResourceIRQInfoIndex }
	::= { dmtfSystemResourceIRQInfoTable 1 }


dmtfSystemResourceIRQInfoState OBJECT-TYPE
	SYNTAX		INTEGER {
		active(1),
		notInService(2),
		notReady(3),
		createAndGo(4),
		createAndWait(5),
		destroy(6)
	}
	MAX-ACCESS	read-write
	STATUS		current
	REFERENCE "'DMTF|System Resource IRQ Info|001' 0"
	::= { dmtfSystemResourceIRQInfoEntry 0 }

systemResourceIRQInfoIndex OBJECT-TYPE
	SYNTAX		DmiInteger
	MAX-ACCESS	read-only
	STATUS		current
	DESCRIPTION	"A number the uniquely identifies rows in this table."
	REFERENCE "'DMTF|System Resource IRQ Info|001' 1"
	::= { dmtfSystemResourceIRQInfoEntry 1 }

triggerType OBJECT-TYPE
	SYNTAX		INTEGER {
		other(1),
		unknown(2),
		level(3),
		edge(4)
	}
	MAX-ACCESS	read-only
	STATUS		current
	DESCRIPTION	"The trigger type for this interrupt."
	REFERENCE "'DMTF|System Resource IRQ Info|001' 2"
	::= { dmtfSystemResourceIRQInfoEntry 2 }

triggerLevel OBJECT-TYPE
	SYNTAX		INTEGER {
		other(1),
		unknown(2),
		activeLow(3),
		activeHigh(4)
	}
	MAX-ACCESS	read-only
	STATUS		current
	DESCRIPTION	"The trigger level for this interrupt."
	REFERENCE "'DMTF|System Resource IRQ Info|001' 3"
	::= { dmtfSystemResourceIRQInfoEntry 3 }

SdmtfSystemResourceMemoryInfo ::= SEQUENCE {
	dmtfSystemResourceMemoryInfoState INTEGER,
	systemResourceMemoryInfoIndex	DmiInteger,
	iSAPCMCIARangeDescriptor	DmiInteger,
	eISARangeDescriptor	DmiInteger,
	decodeSupport	DmiInteger,
	cacheable	DmiInteger,
	cacheType	DmiInteger,
	readWrite	DmiInteger
}

dmtfSystemResourceMemoryInfoTable OBJECT-TYPE
	SYNTAX		SEQUENCE OF SdmtfSystemResourceMemoryInfo
	MAX-ACCESS	not-accessible
	STATUS		current
	DESCRIPTION	"This group presents additional information about memory resource
 that have been defined in the System Resources table."
	::= { dmtfSystemsMIF 39 }

dmtfSystemResourceMemoryInfoEntry OBJECT-TYPE
	SYNTAX		SdmtfSystemResourceMemoryInfo
	MAX-ACCESS	not-accessible
	STATUS		current
	DESCRIPTION	"This group presents additional information about memory resource
 that have been defined in the System Resources table."
	INDEX		{ DmiCompId,DmiGroupId, systemResourceMemoryInfoIndex }
	::= { dmtfSystemResourceMemoryInfoTable 1 }


dmtfSystemResourceMemoryInfoState OBJECT-TYPE
	SYNTAX		INTEGER {
		active(1),
		notInService(2),
		notReady(3),
		createAndGo(4),
		createAndWait(5),
		destroy(6)
	}
	MAX-ACCESS	read-write
	STATUS		current
	REFERENCE "'DMTF|System Resource Memory Info|001' 0"
	::= { dmtfSystemResourceMemoryInfoEntry 0 }

systemResourceMemoryInfoIndex OBJECT-TYPE
	SYNTAX		DmiInteger
	MAX-ACCESS	read-only
	STATUS		current
	DESCRIPTION	"A number the uniquely identifies rows in this table."
	REFERENCE "'DMTF|System Resource Memory Info|001' 1"
	::= { dmtfSystemResourceMemoryInfoEntry 1 }

iSAPCMCIARangeDescriptor OBJECT-TYPE
	SYNTAX		INTEGER {
		other(1),
		unknown(2),
		x8BitMemoryOnly(3),
		x16BitMemoryOnly(4),
		x8And16BitMemorySupported(5),
		x32BitMemoryOnly(6)
	}
	MAX-ACCESS	read-only
	STATUS		current
	DESCRIPTION	"For PnP ISA/PCMCIA memory range descriptor compatibility."
	REFERENCE "'DMTF|System Resource Memory Info|001' 2"
	::= { dmtfSystemResourceMemoryInfoEntry 2 }

eISARangeDescriptor OBJECT-TYPE
	SYNTAX		INTEGER {
		other(1),
		unknown(2),
		x8BitMemoryOnly(3),
		x16BitMemoryOnly(4),
		x8And16BitMemorySupported(5),
		x32BitMemoryOnly(6)
	}
	MAX-ACCESS	read-only
	STATUS		current
	DESCRIPTION	"For PnP EISA memory range descriptor compatibility."
	REFERENCE "'DMTF|System Resource Memory Info|001' 3"
	::= { dmtfSystemResourceMemoryInfoEntry 3 }

decodeSupport OBJECT-TYPE
	SYNTAX		INTEGER {
		other(1),
		unknown(2),
		decodeSupportsHighAddress(3),
		decodeSupportsRangeLength(4)
	}
	MAX-ACCESS	read-only
	STATUS		current
	DESCRIPTION	"For PnP memory range descriptor compatibility."
	REFERENCE "'DMTF|System Resource Memory Info|001' 4"
	::= { dmtfSystemResourceMemoryInfoEntry 4 }

cacheable OBJECT-TYPE
	SYNTAX		INTEGER {
		false(0),
		true(1),
		unknown(2)
	}
	MAX-ACCESS	read-only
	STATUS		current
	DESCRIPTION	"Indicates whether it is allowable for this memory range to
be cached or not."
	REFERENCE "'DMTF|System Resource Memory Info|001' 5"
	::= { dmtfSystemResourceMemoryInfoEntry 5 }

cacheType OBJECT-TYPE
	SYNTAX		INTEGER {
		other(1),
		unknown(2),
		writeBack-1(3),
		writeThrough-1(4)
	}
	MAX-ACCESS	read-only
	STATUS		current
	DESCRIPTION	"Indicates Cache Type that is compatible with this resource."
	REFERENCE "'DMTF|System Resource Memory Info|001' 6"
	::= { dmtfSystemResourceMemoryInfoEntry 6 }

readWrite OBJECT-TYPE
	SYNTAX		INTEGER {
		other(1),
		unknown(2),
		rOMReadOnly(3),
		rAMReadwrite(4)
	}
	MAX-ACCESS	read-only
	STATUS		current
	DESCRIPTION	"Indicates the read-write accessibility of this memory resource."
	REFERENCE "'DMTF|System Resource Memory Info|001' 7"
	::= { dmtfSystemResourceMemoryInfoEntry 7 }

SdmtfSystemResources2 ::= SEQUENCE {
	dmtfSystemResources2State INTEGER,
	systemResourcesIndex	DmiInteger,
	resourceUser	DmiInteger,
	resourceSet	DmiInteger,
	resourceAssignment	DmiInteger,
	resourceType	DmiInteger,
	resourceNumber	DmiInteger,
	resourceInfoID	DmiInteger,
	startAddress	Dmi-Integer64,
	endAddress	Dmi-Integer64,
	resourceSize	DmiInteger,
	baseAlignment	DmiInteger,
	shareable	DmiInteger,
	shared	DmiInteger
}

dmtfSystemResources2Table OBJECT-TYPE
	SYNTAX		SEQUENCE OF SdmtfSystemResources2
	MAX-ACCESS	not-accessible
	STATUS		current
	DESCRIPTION	"This group describes the base level of Memory, I/O, DMA,
and INT (interrupt) resources that are used by a device in the system."
	::= { dmtfSystemsMIF 37 }

dmtfSystemResources2Entry OBJECT-TYPE
	SYNTAX		SdmtfSystemResources2
	MAX-ACCESS	not-accessible
	STATUS		current
	DESCRIPTION	"This group describes the base level of Memory, I/O, DMA,
and INT (interrupt) resources that are used by a device in the system."
	INDEX		{ DmiCompId,DmiGroupId, systemResourcesIndex }
	::= { dmtfSystemResources2Table 1 }


dmtfSystemResources2State OBJECT-TYPE
	SYNTAX		INTEGER {
		active(1),
		notInService(2),
		notReady(3),
		createAndGo(4),
		createAndWait(5),
		destroy(6)
	}
	MAX-ACCESS	read-write
	STATUS		current
	REFERENCE "'DMTF|System Resources 2|001' 0"
	::= { dmtfSystemResources2Entry 0 }

systemResourcesIndex OBJECT-TYPE
	SYNTAX		DmiInteger
	MAX-ACCESS	read-only
	STATUS		current
	DESCRIPTION	"A number that uniquely identifies the rows in this table."
	REFERENCE "'DMTF|System Resources 2|001' 1"
	::= { dmtfSystemResources2Entry 1 }

resourceUser OBJECT-TYPE
	SYNTAX		DmiInteger
	MAX-ACCESS	read-only
	STATUS		current
	DESCRIPTION	"A unique number for each different 'resource user' that has
resources specified in this table."
	REFERENCE "'DMTF|System Resources 2|001' 2"
	::= { dmtfSystemResources2Entry 2 }

resourceSet OBJECT-TYPE
	SYNTAX		DmiInteger
	MAX-ACCESS	read-only
	STATUS		current
	DESCRIPTION	"A number used as the ID of a set of Memory, I/O, DMA and/or
INT resources for the resource user."
	REFERENCE "'DMTF|System Resources 2|001' 3"
	::= { dmtfSystemResources2Entry 3 }

resourceAssignment OBJECT-TYPE
	SYNTAX		INTEGER {
		other(1),
		unknown(2),
		allocated(3),
		assignable(4),
		temporaryAssignment(5)
	}
	MAX-ACCESS	read-only
	STATUS		current
	DESCRIPTION	"Describes the state of the assignment of this set of resources.
(Note: This value must be the same for all resources within a given set.)"
	REFERENCE "'DMTF|System Resources 2|001' 4"
	::= { dmtfSystemResources2Entry 4 }

resourceType OBJECT-TYPE
	SYNTAX		INTEGER {
		other(1),
		unknown(2),
		memory(3),
		iO(4),
		iRQ(5),
		dMA(6)
	}
	MAX-ACCESS	read-only
	STATUS		current
	DESCRIPTION	"The type of resource described by this row."
	REFERENCE "'DMTF|System Resources 2|001' 5"
	::= { dmtfSystemResources2Entry 5 }

resourceNumber OBJECT-TYPE
	SYNTAX		DmiInteger
	MAX-ACCESS	read-only
	STATUS		current
	DESCRIPTION	"DMA or IRQ number - 0 for Memory and I/O ranges. This is
the interrupt or DMA number relative to the bus that the interrupt is sourced
from."
	REFERENCE "'DMTF|System Resources 2|001' 6"
	::= { dmtfSystemResources2Entry 6 }

resourceInfoID OBJECT-TYPE
	SYNTAX		DmiInteger
	MAX-ACCESS	read-only
	STATUS		current
	DESCRIPTION	"ID of the row in the 'Info' table for this type of system
resource. E.g. if this Resource Type is 'I/O' then this would be an index
into the 'System Resource I/O Info' table."
	REFERENCE "'DMTF|System Resources 2|001' 7"
	::= { dmtfSystemResources2Entry 7 }

startAddress OBJECT-TYPE
	SYNTAX		Dmi-Integer64
	MAX-ACCESS	read-only
	STATUS		current
	DESCRIPTION	"Starting physical address for this memory range, or the minimum
base address if this attribute is being used to describe a programmable range.
0 for IRQ and DMA resources."
	REFERENCE "'DMTF|System Resources 2|001' 8"
	::= { dmtfSystemResources2Entry 8 }

endAddress OBJECT-TYPE
	SYNTAX		Dmi-Integer64
	MAX-ACCESS	read-only
	STATUS		current
	DESCRIPTION	"Ending physical address (address of last byte) for this memory
range, or the maximum configurable base address if this attribute is being
used to describe a programmable range. 0 for IRQ and DMA resources."
	REFERENCE "'DMTF|System Resources 2|001' 9"
	::= { dmtfSystemResources2Entry 9 }

resourceSize OBJECT-TYPE
	SYNTAX		DmiInteger
	MAX-ACCESS	read-only
	STATUS		current
	DESCRIPTION	"jNumber of consecutive bytes that a memory or I/O resource
consumes. 0 for IRQ and DMA resources."
	REFERENCE "'DMTF|System Resources 2|001' 10"
	::= { dmtfSystemResources2Entry 10 }

baseAlignment OBJECT-TYPE
	SYNTAX		DmiInteger
	MAX-ACCESS	read-only
	STATUS		current
	DESCRIPTION	"Alignment of Start Address, in bytes. Indicates the granularity
of the increments in which a programmable range can be set."
	REFERENCE "'DMTF|System Resources 2|001' 11"
	::= { dmtfSystemResources2Entry 11 }

shareable OBJECT-TYPE
	SYNTAX		INTEGER {
		false(0),
		true(1),
		unknown(2)
	}
	MAX-ACCESS	read-only
	STATUS		current
	DESCRIPTION	"Indicates whether the resource is shareable."
	REFERENCE "'DMTF|System Resources 2|001' 12"
	::= { dmtfSystemResources2Entry 12 }

shared OBJECT-TYPE
	SYNTAX		INTEGER {
		false(0),
		true(1),
		unknown(2)
	}
	MAX-ACCESS	read-only
	STATUS		current
	DESCRIPTION	"Indicates whether this resource, or a portion of this resource,
is shared with another device."
	REFERENCE "'DMTF|System Resources 2|001' 13"
	::= { dmtfSystemResources2Entry 13 }

SdmtfSystemResourcesDescription ::= SEQUENCE {
	deviceCount	DmiInteger,
	systemResourceCount	DmiInteger
}

dmtfSystemResourcesDescriptionTable OBJECT-TYPE
	SYNTAX		SEQUENCE OF SdmtfSystemResourcesDescription
	MAX-ACCESS	not-accessible
	STATUS		current
	DESCRIPTION	"The System Resources Description group describes the number
of entries in the System Resources group."
	::= { dmtfSystemsMIF 31 }

dmtfSystemResourcesDescriptionEntry OBJECT-TYPE
	SYNTAX		SdmtfSystemResourcesDescription
	MAX-ACCESS	not-accessible
	STATUS		current
	DESCRIPTION	"The System Resources Description group describes the number
of entries in the System Resources group."
	INDEX		{ DmiCompId,DmiGroupId }
	::= { dmtfSystemResourcesDescriptionTable 1 }


deviceCount OBJECT-TYPE
	SYNTAX		DmiInteger
	MAX-ACCESS	read-only
	STATUS		current
	DESCRIPTION	"A count of the number of different hardware devices represented
in the System Resources table."
	REFERENCE "'DMTF|System Resources Description|001' 1"
	::= { dmtfSystemResourcesDescriptionEntry 1 }

systemResourceCount OBJECT-TYPE
	SYNTAX		DmiInteger
	MAX-ACCESS	read-only
	STATUS		current
	DESCRIPTION	"A count of the total number of system resources on this system."
	REFERENCE "'DMTF|System Resources Description|001' 2"
	::= { dmtfSystemResourcesDescriptionEntry 2 }

SdmtfSystemResources ::= SEQUENCE {
	dmtfSystemResourcesState INTEGER,
	resourceInstance	DmiInteger,
	resourceNumber	DmiInteger,
	resourceType	DmiInteger,
	resourceBase	DmiInteger,
	resourceSize	DmiInteger,
	resourceFlags	DmiInteger,
	resourceGroupID	DmiInteger
}

dmtfSystemResourcesTable OBJECT-TYPE
	SYNTAX		SEQUENCE OF SdmtfSystemResources
	MAX-ACCESS	not-accessible
	STATUS		current
	DESCRIPTION	"The System Resources group contains hardware descriptions
which are commonly used in PC style computers such as IRQs, IO ports and
memory address ranges."
	::= { dmtfSystemsMIF 32 }

dmtfSystemResourcesEntry OBJECT-TYPE
	SYNTAX		SdmtfSystemResources
	MAX-ACCESS	not-accessible
	STATUS		current
	DESCRIPTION	"The System Resources group contains hardware descriptions
which are commonly used in PC style computers such as IRQs, IO ports and
memory address ranges."
	INDEX		{ DmiCompId,DmiGroupId, resourceInstance, resourceNumber }
	::= { dmtfSystemResourcesTable 1 }


dmtfSystemResourcesState OBJECT-TYPE
	SYNTAX		INTEGER {
		active(1),
		notInService(2),
		notReady(3),
		createAndGo(4),
		createAndWait(5),
		destroy(6)
	}
	MAX-ACCESS	read-write
	STATUS		current
	REFERENCE "'DMTF|System Resources|001' 0"
	::= { dmtfSystemResourcesEntry 0 }

resourceInstance OBJECT-TYPE
	SYNTAX		DmiInteger
	MAX-ACCESS	read-only
	STATUS		current
	DESCRIPTION	"On systems that implement a PnP-like subsystem, the device
ID should be the ID used by that subsystem. On systems that do not have inherent
device numbering, then the instrumentation supporting the system resources
group should devise a device numbering scheme. In either case, the table
will naturally group all of the resources associated with a device."
	REFERENCE "'DMTF|System Resources|001' 1"
	::= { dmtfSystemResourcesEntry 1 }

resourceNumber OBJECT-TYPE
	SYNTAX		DmiInteger
	MAX-ACCESS	read-only
	STATUS		current
	DESCRIPTION	"This attribute is the ordinal of the resource within a device.
Within the table, any device may have one or more resources."
	REFERENCE "'DMTF|System Resources|001' 2"
	::= { dmtfSystemResourcesEntry 2 }

resourceType OBJECT-TYPE
	SYNTAX		INTEGER {
		other(1),
		unknown(2),
		memoryRange(3),
		iOPort(4),
		iRQ(5),
		dMA(6)
	}
	MAX-ACCESS	read-only
	STATUS		current
	DESCRIPTION	"The type of system resource represented by this entry."
	REFERENCE "'DMTF|System Resources|001' 3"
	::= { dmtfSystemResourcesEntry 3 }

resourceBase OBJECT-TYPE
	SYNTAX		DmiInteger
	MAX-ACCESS	read-only
	STATUS		current
	DESCRIPTION	"The starting address of the system resource in the appropriate
address space."
	REFERENCE "'DMTF|System Resources|001' 4"
	::= { dmtfSystemResourcesEntry 4 }

resourceSize OBJECT-TYPE
	SYNTAX		DmiInteger
	MAX-ACCESS	read-only
	STATUS		current
	DESCRIPTION	"The size of the system resource."
	REFERENCE "'DMTF|System Resources|001' 5"
	::= { dmtfSystemResourcesEntry 5 }

resourceFlags OBJECT-TYPE
	SYNTAX		DmiInteger
	MAX-ACCESS	read-only
	STATUS		current
	DESCRIPTION	"This attribute contains fields representing the status of
this resource entry. The meaning of this field varies according to the Resource
Type field in this group."
	REFERENCE "'DMTF|System Resources|001' 6"
	::= { dmtfSystemResourcesEntry 6 }

resourceGroupID OBJECT-TYPE
	SYNTAX		DmiInteger
	MAX-ACCESS	read-only
	STATUS		current
	DESCRIPTION	"This attribute is a 'back pointer' to a group within the
system MIF, if applicable. If the back pointer is not known, either because
the device is not represented by a group, or the actual device type is not
known, then the value of this attribute will be 0."
	REFERENCE "'DMTF|System Resources|001' 7"
	::= { dmtfSystemResourcesEntry 7 }

SdmtfSystemSlot ::= SEQUENCE {
	dmtfSystemSlotState INTEGER,
	slotIndex	DmiInteger,
	slotType	Dmi-Integer64,
	slotWidth	DmiInteger,
	currentUsage	DmiInteger,
	slotDescription	DmiString,
	slotCategory	DmiInteger,
	virtualSlot	DmiInteger,
	resourceUserID	DmiInteger,
	vccMixedVoltageSupport	Dmi-Integer64,
	vppMixedVoltageSupport	Dmi-Integer64,
	slotThermalRating	DmiInteger
}

dmtfSystemSlotTable OBJECT-TYPE
	SYNTAX		SEQUENCE OF SdmtfSystemSlot
	MAX-ACCESS	not-accessible
	STATUS		current
	DESCRIPTION	"This group defines the attributes for the different system
expansion slots supported in this system."
	::= { dmtfSystemsMIF 18 }

dmtfSystemSlotEntry OBJECT-TYPE
	SYNTAX		SdmtfSystemSlot
	MAX-ACCESS	not-accessible
	STATUS		current
	DESCRIPTION	"This group defines the attributes for the different system
expansion slots supported in this system."
	INDEX		{ DmiCompId,DmiGroupId, slotIndex }
	::= { dmtfSystemSlotTable 1 }


dmtfSystemSlotState OBJECT-TYPE
	SYNTAX		INTEGER {
		active(1),
		notInService(2),
		notReady(3),
		createAndGo(4),
		createAndWait(5),
		destroy(6)
	}
	MAX-ACCESS	read-write
	STATUS		current
	REFERENCE "'DMTF|System Slot|004' 0"
	::= { dmtfSystemSlotEntry 0 }

slotIndex OBJECT-TYPE
	SYNTAX		DmiInteger
	MAX-ACCESS	read-only
	STATUS		current
	DESCRIPTION	"An index into the system slot table. This is the hardware
ID number for each expansion slot, whether it is occupied or not (starting
with 1)."
	REFERENCE "'DMTF|System Slot|004' 1"
	::= { dmtfSystemSlotEntry 1 }

slotType OBJECT-TYPE
	SYNTAX		Dmi-Integer64
	MAX-ACCESS	read-only
	STATUS		current
	DESCRIPTION	"The bus type supported in this slot. This is a bit field
with the following definitions: 
 Bit 0 (2^0), if 1, it is a long-length
card; 
     if 0, it is a short-length card, 
 Bit 1 (2^1) if set, indicates
ISA, 
 Bit 2 (2^2) indicates EISA, 
 Bit 3 (2^3) indicates MCA, 
 Bit 4 (2^4)
indicates PCI, 
 Bit 5 (2^5) indicates VL, 
 Bit 6 (2^6) indicates PCMCIA,

 Bit 7 (2^7) refers to NuBus, 
 Bit 8 (2^8) indicates PC-98/C20, 
 Bit 9
(2^9) indicates PC-98/C24, 
 Bit 10 (2^10) indicates PC-98/E, 
 Bit 11 (2^"
	REFERENCE "'DMTF|System Slot|004' 2"
	::= { dmtfSystemSlotEntry 2 }

slotWidth OBJECT-TYPE
	SYNTAX		INTEGER {
		other(1),
		unknown(2),
		x8BitCard(3),
		x16BitCard(4),
		x32BitCard(5),
		x64BitCard(6),
		x128BitCard(7)
	}
	MAX-ACCESS	read-only
	STATUS		current
	DESCRIPTION	"The maximum bus width of cards accepted in this slot."
	REFERENCE "'DMTF|System Slot|004' 3"
	::= { dmtfSystemSlotEntry 3 }

currentUsage OBJECT-TYPE
	SYNTAX		INTEGER {
		other(1),
		unknown(2),
		available(3),
		inUse(4)
	}
	MAX-ACCESS	read-only
	STATUS		current
	DESCRIPTION	"Is this slot is currently in use?"
	REFERENCE "'DMTF|System Slot|004' 4"
	::= { dmtfSystemSlotEntry 4 }

slotDescription OBJECT-TYPE
	SYNTAX		DmiString
	MAX-ACCESS	read-only
	STATUS		current
	DESCRIPTION	"The card currently occupying this slot."
	REFERENCE "'DMTF|System Slot|004' 5"
	::= { dmtfSystemSlotEntry 5 }

slotCategory OBJECT-TYPE
	SYNTAX		INTEGER {
		other(1),
		unknown(2),
		busConnector(3),
		pCMCIASlot(4),
		motherboard(5)
	}
	MAX-ACCESS	read-only
	STATUS		current
	DESCRIPTION	"The word 'slot' is used to refer to bus slots. The last case
(motherboard) refers to situations where a functional element is integrated
onto, say, a motherboard and connects to a bus without a connector. It still
takes up an expansion site on the bus but this is termed a 'virtual slot'
as opposed to a physical slot (see the attribute 'Virtual Slot'). Virtual
slots are in effect permanently occupied expansion sites. This attribute
establishes which category of physical slot this table entry is defining."
	REFERENCE "'DMTF|System Slot|004' 6"
	::= { dmtfSystemSlotEntry 6 }

virtualSlot OBJECT-TYPE
	SYNTAX		INTEGER {
		false(0),
		true(1),
		unknown(2)
	}
	MAX-ACCESS	read-only
	STATUS		current
	DESCRIPTION	"This attribute indicates whether this is a 'virtual slot'
or not. A 'virtual slot' is an expansion site that is permanently occupied
because of the level of integration of an expandable component. An example
of a virtual slot is an I/O bus position taken up by a LAN controller that
is integrated onto a motherboard. A slot with the 'Slot Category' of Motherboard
is typically a Virtual Slot."
	REFERENCE "'DMTF|System Slot|004' 7"
	::= { dmtfSystemSlotEntry 7 }

resourceUserID OBJECT-TYPE
	SYNTAX		DmiInteger
	MAX-ACCESS	read-only
	STATUS		current
	DESCRIPTION	"Value used to locate the rows in the System Resources 2 table
for the resources associated with this slot or expansion site. 0 = 'unspecified'
"
	REFERENCE "'DMTF|System Slot|004' 8"
	::= { dmtfSystemSlotEntry 8 }

vccMixedVoltageSupport OBJECT-TYPE
	SYNTAX		Dmi-Integer64
	MAX-ACCESS	read-only
	STATUS		current
	DESCRIPTION	"Device Vcc Mixed Voltage support. This is a bit field with
the following definitions: 
 Bit 0 (2^0), if set, indicates 3.3V support

 Bit 1 (2^1), if set, indicates 5V support "
	REFERENCE "'DMTF|System Slot|004' 9"
	::= { dmtfSystemSlotEntry 9 }

vppMixedVoltageSupport OBJECT-TYPE
	SYNTAX		Dmi-Integer64
	MAX-ACCESS	read-only
	STATUS		current
	DESCRIPTION	"Device Vpp Mixed Voltage support. This is a bit field with
the following definitions: 
 Bit 0 (2^0), if set, indicates 3.3V support

 Bit 1 (2^1), if set, indicates 5V support 
 Bit 2 (2^2), if set, indicates
12V support"
	REFERENCE "'DMTF|System Slot|004' 10"
	::= { dmtfSystemSlotEntry 10 }

slotThermalRating OBJECT-TYPE
	SYNTAX		DmiInteger
	MAX-ACCESS	read-only
	STATUS		current
	DESCRIPTION	"The maximum thermal dissipation of the slot in milliwatts."
	REFERENCE "'DMTF|System Slot|004' 11"
	::= { dmtfSystemSlotEntry 11 }

SdmtfTemperatureProbe ::= SEQUENCE {
	dmtfTemperatureProbeState INTEGER,
	temperatureProbeTableIndex	DmiInteger,
	temperatureProbeLocation	DmiInteger,
	temperatureProbeDescription	DmiString,
	temperatureStatus	DmiInteger,
	temperatureProbeTemperatureReading	DmiInteger,
	monitoredTemperatureNominalReading	DmiInteger,
	monitoredTemperatureNormalMaximum	DmiInteger,
	monitoredTemperatureNormalMinimum	DmiInteger,
	temperatureProbeMaximum	DmiInteger,
	temperatureProbeMinimum	DmiInteger,
	temperatureReadingLowerThresholdNonCritical	DmiInteger,
	temperatureReadingUpperThresholdNonCritical	DmiInteger,
	temperatureReadingLowerThresholdCritical	DmiInteger,
	temperatureReadingUpperThresholdCritical	DmiInteger,
	temperatureReadingLowerThresholdNonRecoverable	DmiInteger,
	temperatureReadingUpperThresholdNonRecoverable	DmiInteger,
	temperatureProbeResolution	DmiInteger,
	temperatureProbeTolerance	DmiInteger,
	temperatureProbeAccuracy	DmiInteger,
	fRUGroupIndex	DmiInteger,
	operationalGroupIndex	DmiInteger
}

dmtfTemperatureProbeTable OBJECT-TYPE
	SYNTAX		SEQUENCE OF SdmtfTemperatureProbe
	MAX-ACCESS	not-accessible
	STATUS		current
	DESCRIPTION	"This group defines the attributes for the temperature probes
in this system."
	::= { dmtfSystemsMIF 54 }

dmtfTemperatureProbeEntry OBJECT-TYPE
	SYNTAX		SdmtfTemperatureProbe
	MAX-ACCESS	not-accessible
	STATUS		current
	DESCRIPTION	"This group defines the attributes for the temperature probes
in this system."
	INDEX		{ DmiCompId,DmiGroupId, temperatureProbeTableIndex }
	::= { dmtfTemperatureProbeTable 1 }


dmtfTemperatureProbeState OBJECT-TYPE
	SYNTAX		INTEGER {
		active(1),
		notInService(2),
		notReady(3),
		createAndGo(4),
		createAndWait(5),
		destroy(6)
	}
	MAX-ACCESS	read-write
	STATUS		current
	REFERENCE "'DMTF|Temperature Probe|001' 0"
	::= { dmtfTemperatureProbeEntry 0 }

temperatureProbeTableIndex OBJECT-TYPE
	SYNTAX		DmiInteger
	MAX-ACCESS	read-only
	STATUS		current
	DESCRIPTION	"Index into this temperature probe table."
	REFERENCE "'DMTF|Temperature Probe|001' 1"
	::= { dmtfTemperatureProbeEntry 1 }

temperatureProbeLocation OBJECT-TYPE
	SYNTAX		INTEGER {
		other(1),
		unknown(2),
		processor(3),
		disk(4),
		peripheralBay(5),
		sMBMaster(6),
		motherboard(7),
		memoryModule(8),
		processorModule(9),
		powerUnit(10),
		addInCard(11)
	}
	MAX-ACCESS	read-only
	STATUS		current
	DESCRIPTION	"Identifies the physical location of the temperature probe."
	REFERENCE "'DMTF|Temperature Probe|001' 2"
	::= { dmtfTemperatureProbeEntry 2 }

temperatureProbeDescription OBJECT-TYPE
	SYNTAX		DmiString
	MAX-ACCESS	read-only
	STATUS		current
	DESCRIPTION	"Additional descriptive information about the temperature
probe or probe's location."
	REFERENCE "'DMTF|Temperature Probe|001' 3"
	::= { dmtfTemperatureProbeEntry 3 }

temperatureStatus OBJECT-TYPE
	SYNTAX		INTEGER {
		other(1),
		unknown(2),
		oK(3),
		nonCritical(4),
		critical(5),
		nonRecoverable(6)
	}
	MAX-ACCESS	read-only
	STATUS		current
	DESCRIPTION	"Defines the status of the temperature monitored by this temperat
re probe."
	REFERENCE "'DMTF|Temperature Probe|001' 4"
	::= { dmtfTemperatureProbeEntry 4 }

temperatureProbeTemperatureReading OBJECT-TYPE
	SYNTAX		DmiInteger
	MAX-ACCESS	read-only
	STATUS		current
	DESCRIPTION	"The present temperature reading of this temperature probe
in 1/10th degrees C. 0x8000000 denotes 'unknown'."
	REFERENCE "'DMTF|Temperature Probe|001' 5"
	::= { dmtfTemperatureProbeEntry 5 }

monitoredTemperatureNominalReading OBJECT-TYPE
	SYNTAX		DmiInteger
	MAX-ACCESS	read-only
	STATUS		current
	DESCRIPTION	"The nominal temperature reading of the temperature monitored
by this probe in 1/10th degrees C. 0x80000000 denotes 'unknown'."
	REFERENCE "'DMTF|Temperature Probe|001' 6"
	::= { dmtfTemperatureProbeEntry 6 }

monitoredTemperatureNormalMaximum OBJECT-TYPE
	SYNTAX		DmiInteger
	MAX-ACCESS	read-only
	STATUS		current
	DESCRIPTION	"The normal maximum temperature reading of the temperature
monitored by this probe in 1/10th degrees C. 0x80000000 denotes 'unknown'."
	REFERENCE "'DMTF|Temperature Probe|001' 7"
	::= { dmtfTemperatureProbeEntry 7 }

monitoredTemperatureNormalMinimum OBJECT-TYPE
	SYNTAX		DmiInteger
	MAX-ACCESS	read-only
	STATUS		current
	DESCRIPTION	"The normal minimum temperature reading of the temperature
monitored by this probe in 1/10th degrees C. 0x80000000 denotes 'unknown'."
	REFERENCE "'DMTF|Temperature Probe|001' 8"
	::= { dmtfTemperatureProbeEntry 8 }

temperatureProbeMaximum OBJECT-TYPE
	SYNTAX		DmiInteger
	MAX-ACCESS	read-only
	STATUS		current
	DESCRIPTION	"The maximum temperature reading specified to be readable
by this probe in 1/10th degrees C. 0x80000000 denotes 'unknown'."
	REFERENCE "'DMTF|Temperature Probe|001' 9"
	::= { dmtfTemperatureProbeEntry 9 }

temperatureProbeMinimum OBJECT-TYPE
	SYNTAX		DmiInteger
	MAX-ACCESS	read-only
	STATUS		current
	DESCRIPTION	"The minimum temperature reading specified to be readable
by this probe in 1/10th degrees C. 0x80000000 denotes 'unknown'."
	REFERENCE "'DMTF|Temperature Probe|001' 10"
	::= { dmtfTemperatureProbeEntry 10 }

temperatureReadingLowerThresholdNonCritical OBJECT-TYPE
	SYNTAX		DmiInteger
	MAX-ACCESS	read-write
	STATUS		current
	DESCRIPTION	"The lower non-critical threshold for the temperature reading
set by the user, in 1/10th degrees C. 0x80000000 denotes 'unknown'."
	REFERENCE "'DMTF|Temperature Probe|001' 11"
	::= { dmtfTemperatureProbeEntry 11 }

temperatureReadingUpperThresholdNonCritical OBJECT-TYPE
	SYNTAX		DmiInteger
	MAX-ACCESS	read-write
	STATUS		current
	DESCRIPTION	"The upper non-critical threshold for the temperature probe,
in 1/10th degrees C. 0x80000000 denotes 'unknown'."
	REFERENCE "'DMTF|Temperature Probe|001' 12"
	::= { dmtfTemperatureProbeEntry 12 }

temperatureReadingLowerThresholdCritical OBJECT-TYPE
	SYNTAX		DmiInteger
	MAX-ACCESS	read-write
	STATUS		current
	DESCRIPTION	"The lower critical threshold for the temperature probe, in
1/10 degrees C. 0x80000000 denotes 'unknown'."
	REFERENCE "'DMTF|Temperature Probe|001' 13"
	::= { dmtfTemperatureProbeEntry 13 }

temperatureReadingUpperThresholdCritical OBJECT-TYPE
	SYNTAX		DmiInteger
	MAX-ACCESS	read-write
	STATUS		current
	DESCRIPTION	"The upper critical threshold for the temperature probe, in
/10th degrees C. 0x80000000 denotes 'unknown'."
	REFERENCE "'DMTF|Temperature Probe|001' 14"
	::= { dmtfTemperatureProbeEntry 14 }

temperatureReadingLowerThresholdNonRecoverable OBJECT-TYPE
	SYNTAX		DmiInteger
	MAX-ACCESS	read-write
	STATUS		current
	DESCRIPTION	"The lower non-recoverable threshold for the temperature probe,
in 1/10th degrees C. 0x80000000 denotes 'unknown'."
	REFERENCE "'DMTF|Temperature Probe|001' 15"
	::= { dmtfTemperatureProbeEntry 15 }

temperatureReadingUpperThresholdNonRecoverable OBJECT-TYPE
	SYNTAX		DmiInteger
	MAX-ACCESS	read-write
	STATUS		current
	DESCRIPTION	"The upper non-recoverable threshold for the temperature probe,
in 1/10th degrees C. 0x80000000 denotes 'unknown'."
	REFERENCE "'DMTF|Temperature Probe|001' 16"
	::= { dmtfTemperatureProbeEntry 16 }

temperatureProbeResolution OBJECT-TYPE
	SYNTAX		DmiInteger
	MAX-ACCESS	read-write
	STATUS		current
	DESCRIPTION	"The resolution for the reading from this temperature probe,
in tenths of 1/10th degrees C. '0x80000000 denotes 'unknown'."
	REFERENCE "'DMTF|Temperature Probe|001' 17"
	::= { dmtfTemperatureProbeEntry 17 }

temperatureProbeTolerance OBJECT-TYPE
	SYNTAX		DmiInteger
	MAX-ACCESS	read-write
	STATUS		current
	DESCRIPTION	"The tolerance for the reading from this temperature probe,
in plus/minus 1/10 degrees C. 0x80000000 denotes 'unknown'."
	REFERENCE "'DMTF|Temperature Probe|001' 18"
	::= { dmtfTemperatureProbeEntry 18 }

temperatureProbeAccuracy OBJECT-TYPE
	SYNTAX		DmiInteger
	MAX-ACCESS	read-write
	STATUS		current
	DESCRIPTION	"The accuracy for the reading from this temperature probe,
in plus/minus hundredths of a percent. 0x80000000 denotes 'unknown' or'unsupport
d'."
	REFERENCE "'DMTF|Temperature Probe|001' 19"
	::= { dmtfTemperatureProbeEntry 19 }

fRUGroupIndex OBJECT-TYPE
	SYNTAX		DmiInteger
	MAX-ACCESS	read-only
	STATUS		current
	DESCRIPTION	"Index into the FRU table. A value of -1 indicates that this
device is not an FRU."
	REFERENCE "'DMTF|Temperature Probe|001' 20"
	::= { dmtfTemperatureProbeEntry 20 }

operationalGroupIndex OBJECT-TYPE
	SYNTAX		DmiInteger
	MAX-ACCESS	read-only
	STATUS		current
	DESCRIPTION	"Index into the Operational State table"
	REFERENCE "'DMTF|Temperature Probe|001' 21"
	::= { dmtfTemperatureProbeEntry 21 }

SdmtfUPSBattery ::= SEQUENCE {
	batteryStatus	DmiInteger,
	secondsOnBattery	DmiCounter,
	estimatedMinutesRemaining	DmiInteger,
	estimatedChargeRemaining	DmiGauge,
	batteryVoltage	DmiGauge,
	batteryCurrent	DmiGauge,
	temperatureProbeIndex	DmiInteger,
	fRUGroupIndex	DmiInteger,
	operationalGroupIndex	DmiInteger
}

dmtfUPSBatteryTable OBJECT-TYPE
	SYNTAX		SEQUENCE OF SdmtfUPSBattery
	MAX-ACCESS	not-accessible
	STATUS		current
	DESCRIPTION	"The UPS Battery group contains information regarding the
UPS system's battery status."
	::= { dmtfSystemsMIF 52 }

dmtfUPSBatteryEntry OBJECT-TYPE
	SYNTAX		SdmtfUPSBattery
	MAX-ACCESS	not-accessible
	STATUS		current
	DESCRIPTION	"The UPS Battery group contains information regarding the
UPS system's battery status."
	INDEX		{ DmiCompId,DmiGroupId }
	::= { dmtfUPSBatteryTable 1 }


batteryStatus OBJECT-TYPE
	SYNTAX		INTEGER {
		unknown(1),
		batteryNormal(2),
		batteryLow(3),
		batteryDepleted(4)
	}
	MAX-ACCESS	read-only
	STATUS		current
	DESCRIPTION	"The indication of the capacity remaining in the UPS system's
batteries.  A value of 'battery normal' indicates that the remaining estimated
minutes of run-time is greater than the UPS's configured 'low battery time'
(typically two minutes). A value of 'battery low' indicates that the remaining
estimated minutes of battery run-time is less than or equal to the UPS's
configured 'low battery time'.  A value of 'battery depleted' indicates that
the UPS will be unable to sustain the present load when and if "
	REFERENCE "'DMTF|UPS Battery|001' 1"
	::= { dmtfUPSBatteryEntry 1 }

secondsOnBattery OBJECT-TYPE
	SYNTAX		DmiCounter
	MAX-ACCESS	read-only
	STATUS		current
	DESCRIPTION	"If the UPS is on battery power, the elapsed time in seconds
since the UPS last switched to battery power, or the time since the UPS componen
 software was last restarted, whichever is less. Zero shall be returned if
the UPS is not on battery power."
	REFERENCE "'DMTF|UPS Battery|001' 2"
	::= { dmtfUPSBatteryEntry 2 }

estimatedMinutesRemaining OBJECT-TYPE
	SYNTAX		DmiInteger
	MAX-ACCESS	read-only
	STATUS		current
	DESCRIPTION	"An estimate in minutes of the time to battery charge depletion
under the present load conditions if the utility power is off and remains
off, or if it were to be lost and remain off."
	REFERENCE "'DMTF|UPS Battery|001' 3"
	::= { dmtfUPSBatteryEntry 3 }

estimatedChargeRemaining OBJECT-TYPE
	SYNTAX		DmiGauge
	MAX-ACCESS	read-only
	STATUS		current
	DESCRIPTION	"An estimate of the time to battery charge depletion under
the present load conditions if the utility power is off and remains off,
or if it were to be lost and remain off. The value represents a percent of
full charge."
	REFERENCE "'DMTF|UPS Battery|001' 4"
	::= { dmtfUPSBatteryEntry 4 }

batteryVoltage OBJECT-TYPE
	SYNTAX		DmiGauge
	MAX-ACCESS	read-only
	STATUS		current
	DESCRIPTION	"The magnitude of the present battery voltage in 0.1 volts
DC."
	REFERENCE "'DMTF|UPS Battery|001' 5"
	::= { dmtfUPSBatteryEntry 5 }

batteryCurrent OBJECT-TYPE
	SYNTAX		DmiGauge
	MAX-ACCESS	read-only
	STATUS		current
	DESCRIPTION	"The present battery current in 0.1 Amps DC."
	REFERENCE "'DMTF|UPS Battery|001' 6"
	::= { dmtfUPSBatteryEntry 6 }

temperatureProbeIndex OBJECT-TYPE
	SYNTAX		DmiInteger
	MAX-ACCESS	read-only
	STATUS		current
	DESCRIPTION	"Index into the Temperature Probe table. This probe indicates
the ambient temperature at or near the UPS battery casing. Zero implies no
probe is present."
	REFERENCE "'DMTF|UPS Battery|001' 7"
	::= { dmtfUPSBatteryEntry 7 }

fRUGroupIndex OBJECT-TYPE
	SYNTAX		DmiInteger
	MAX-ACCESS	read-only
	STATUS		current
	DESCRIPTION	"If this is a Field Replaceable Unit or it is part of another
FRU, this provides an index into the FRU table; 'value = -1' indicates that
the group is not a FRU."
	REFERENCE "'DMTF|UPS Battery|001' 8"
	::= { dmtfUPSBatteryEntry 8 }

operationalGroupIndex OBJECT-TYPE
	SYNTAX		DmiInteger
	MAX-ACCESS	read-only
	STATUS		current
	DESCRIPTION	"The index into the Operational State table for this device."
	REFERENCE "'DMTF|UPS Battery|001' 9"
	::= { dmtfUPSBatteryEntry 9 }

SdmtfVideoBIOSCharacteristic ::= SEQUENCE {
	dmtfVideoBIOSCharacteristicState INTEGER,
	videoBIOSCharacteristicIndex	DmiInteger,
	videoBIOSNumber	DmiInteger,
	videoBIOSCharacteristic	DmiInteger,
	videoBIOSCharacteristicDescription	DmiString
}

dmtfVideoBIOSCharacteristicTable OBJECT-TYPE
	SYNTAX		SEQUENCE OF SdmtfVideoBIOSCharacteristic
	MAX-ACCESS	not-accessible
	STATUS		current
	DESCRIPTION	"This group defines the characteristics for the Video BIOS."
	::= { dmtfSystemsMIF 21 }

dmtfVideoBIOSCharacteristicEntry OBJECT-TYPE
	SYNTAX		SdmtfVideoBIOSCharacteristic
	MAX-ACCESS	not-accessible
	STATUS		current
	DESCRIPTION	"This group defines the characteristics for the Video BIOS."
	INDEX		{ DmiCompId,DmiGroupId, videoBIOSCharacteristicIndex, videoBIOSNumber }
	::= { dmtfVideoBIOSCharacteristicTable 1 }


dmtfVideoBIOSCharacteristicState OBJECT-TYPE
	SYNTAX		INTEGER {
		active(1),
		notInService(2),
		notReady(3),
		createAndGo(4),
		createAndWait(5),
		destroy(6)
	}
	MAX-ACCESS	read-write
	STATUS		current
	REFERENCE "'DMTF|Video BIOS Characteristic|001' 0"
	::= { dmtfVideoBIOSCharacteristicEntry 0 }

videoBIOSCharacteristicIndex OBJECT-TYPE
	SYNTAX		DmiInteger
	MAX-ACCESS	read-only
	STATUS		current
	DESCRIPTION	"This is an index into the Video BIOS Characteristics table."
	REFERENCE "'DMTF|Video BIOS Characteristic|001' 1"
	::= { dmtfVideoBIOSCharacteristicEntry 1 }

videoBIOSNumber OBJECT-TYPE
	SYNTAX		DmiInteger
	MAX-ACCESS	read-only
	STATUS		current
	DESCRIPTION	"This is the Video BIOS number which correlates to the Video
BIOS Index."
	REFERENCE "'DMTF|Video BIOS Characteristic|001' 2"
	::= { dmtfVideoBIOSCharacteristicEntry 2 }

videoBIOSCharacteristic OBJECT-TYPE
	SYNTAX		INTEGER {
		other(1),
		unknown(2),
		unsupported(3),
		standardVideoBIOS(4),
		vESABIOSExtensionsSupported(5),
		vESAPowerManagementSupported(6),
		vESADisplayDataChannelSupported(7),
		videoBIOSShadowingAllowed(8),
		videoBIOSUpgradeable(9)
	}
	MAX-ACCESS	read-only
	STATUS		current
	DESCRIPTION	"The attributes and extensions supported by this version of
the Video BIOS."
	REFERENCE "'DMTF|Video BIOS Characteristic|001' 3"
	::= { dmtfVideoBIOSCharacteristicEntry 3 }

videoBIOSCharacteristicDescription OBJECT-TYPE
	SYNTAX		DmiString
	MAX-ACCESS	read-only
	STATUS		current
	DESCRIPTION	"Expanded description of this VIDEO BIOS characteristic."
	REFERENCE "'DMTF|Video BIOS Characteristic|001' 4"
	::= { dmtfVideoBIOSCharacteristicEntry 4 }

SdmtfVideoBIOS ::= SEQUENCE {
	dmtfVideoBIOSState INTEGER,
	videoBIOSIndex	DmiInteger,
	videoBIOSManufacturer	DmiString,
	videoBIOSVersion	DmiString,
	videoBIOSReleaseDate	Dmi-Date,
	videoBIOSShadowingState	DmiInteger
}

dmtfVideoBIOSTable OBJECT-TYPE
	SYNTAX		SEQUENCE OF SdmtfVideoBIOS
	MAX-ACCESS	not-accessible
	STATUS		current
	DESCRIPTION	"This group defines the attributes for the Video BIOS."
	::= { dmtfSystemsMIF 20 }

dmtfVideoBIOSEntry OBJECT-TYPE
	SYNTAX		SdmtfVideoBIOS
	MAX-ACCESS	not-accessible
	STATUS		current
	DESCRIPTION	"This group defines the attributes for the Video BIOS."
	INDEX		{ DmiCompId,DmiGroupId, videoBIOSIndex }
	::= { dmtfVideoBIOSTable 1 }


dmtfVideoBIOSState OBJECT-TYPE
	SYNTAX		INTEGER {
		active(1),
		notInService(2),
		notReady(3),
		createAndGo(4),
		createAndWait(5),
		destroy(6)
	}
	MAX-ACCESS	read-write
	STATUS		current
	REFERENCE "'DMTF|Video BIOS|001' 0"
	::= { dmtfVideoBIOSEntry 0 }

videoBIOSIndex OBJECT-TYPE
	SYNTAX		DmiInteger
	MAX-ACCESS	read-only
	STATUS		current
	DESCRIPTION	"The index into the Video BIOS table."
	REFERENCE "'DMTF|Video BIOS|001' 1"
	::= { dmtfVideoBIOSEntry 1 }

videoBIOSManufacturer OBJECT-TYPE
	SYNTAX		DmiString
	MAX-ACCESS	read-only
	STATUS		current
	DESCRIPTION	"The name of the company that wrote this Video BIOS."
	REFERENCE "'DMTF|Video BIOS|001' 2"
	::= { dmtfVideoBIOSEntry 2 }

videoBIOSVersion OBJECT-TYPE
	SYNTAX		DmiString
	MAX-ACCESS	read-only
	STATUS		current
	DESCRIPTION	"The version number or version string of this Video BIOS."
	REFERENCE "'DMTF|Video BIOS|001' 3"
	::= { dmtfVideoBIOSEntry 3 }

videoBIOSReleaseDate OBJECT-TYPE
	SYNTAX		Dmi-Date
	MAX-ACCESS	read-only
	STATUS		current
	DESCRIPTION	"The Video BIOS release date."
	REFERENCE "'DMTF|Video BIOS|001' 4"
	::= { dmtfVideoBIOSEntry 4 }

videoBIOSShadowingState OBJECT-TYPE
	SYNTAX		INTEGER {
		false(0),
		true(1)
	}
	MAX-ACCESS	read-only
	STATUS		current
	DESCRIPTION	"If true, the Video BIOS is currently being shadowed."
	REFERENCE "'DMTF|Video BIOS|001' 5"
	::= { dmtfVideoBIOSEntry 5 }

SdmtfVideo ::= SEQUENCE {
	dmtfVideoState INTEGER,
	videoIndex	DmiInteger,
	videoType	DmiInteger,
	currentVideoMode	DmiInteger,
	minimumRefreshRate	DmiInteger,
	maximumRefreshRate	DmiInteger,
	videoMemoryType	DmiInteger,
	videoRAMMemorySize	DmiInteger,
	scanMode	DmiInteger,
	videoPhysicalLocation	DmiInteger,
	currentVerticalResolution	DmiInteger,
	currentHorizontalResolution	DmiInteger,
	currentNumberOfBitsPerPixel	DmiInteger,
	currentNumberOfRows	DmiInteger,
	currentNumberOfColumns	DmiInteger,
	currentRefreshRate	DmiInteger,
	fRUGroupIndex	DmiInteger,
	operationalGroupIndex	DmiInteger
}

dmtfVideoTable OBJECT-TYPE
	SYNTAX		SEQUENCE OF SdmtfVideo
	MAX-ACCESS	not-accessible
	STATUS		current
	DESCRIPTION	"This group defines the attributes of video devices in this
system."
	::= { dmtfSystemsMIF 19 }

dmtfVideoEntry OBJECT-TYPE
	SYNTAX		SdmtfVideo
	MAX-ACCESS	not-accessible
	STATUS		current
	DESCRIPTION	"This group defines the attributes of video devices in this
system."
	INDEX		{ DmiCompId,DmiGroupId, videoIndex }
	::= { dmtfVideoTable 1 }


dmtfVideoState OBJECT-TYPE
	SYNTAX		INTEGER {
		active(1),
		notInService(2),
		notReady(3),
		createAndGo(4),
		createAndWait(5),
		destroy(6)
	}
	MAX-ACCESS	read-write
	STATUS		current
	REFERENCE "'DMTF|Video|002' 0"
	::= { dmtfVideoEntry 0 }

videoIndex OBJECT-TYPE
	SYNTAX		DmiInteger
	MAX-ACCESS	read-only
	STATUS		current
	DESCRIPTION	"An index into the video table."
	REFERENCE "'DMTF|Video|002' 1"
	::= { dmtfVideoEntry 1 }

videoType OBJECT-TYPE
	SYNTAX		INTEGER {
		other(1),
		unknown(2),
		cGA(3),
		eGA(4),
		vGA(5),
		sVGA(6),
		mDA(7),
		hGC(8),
		mCGA(9),
		x8514A(10),
		xGA(11),
		linearFrameBuffer(12),
		pC98(160)
	}
	MAX-ACCESS	read-only
	STATUS		current
	DESCRIPTION	"The architecture of the video subsystem in this system."
	REFERENCE "'DMTF|Video|002' 2"
	::= { dmtfVideoEntry 2 }

currentVideoMode OBJECT-TYPE
	SYNTAX		DmiInteger
	MAX-ACCESS	read-only
	STATUS		current
	DESCRIPTION	"The current video mode in this system."
	REFERENCE "'DMTF|Video|002' 3"
	::= { dmtfVideoEntry 3 }

minimumRefreshRate OBJECT-TYPE
	SYNTAX		DmiInteger
	MAX-ACCESS	read-only
	STATUS		current
	DESCRIPTION	"The minimum refresh rate for this video subsystem in Hz."
	REFERENCE "'DMTF|Video|002' 4"
	::= { dmtfVideoEntry 4 }

maximumRefreshRate OBJECT-TYPE
	SYNTAX		DmiInteger
	MAX-ACCESS	read-only
	STATUS		current
	DESCRIPTION	"The maximum refresh rate for this video subsystem in Hz."
	REFERENCE "'DMTF|Video|002' 5"
	::= { dmtfVideoEntry 5 }

videoMemoryType OBJECT-TYPE
	SYNTAX		INTEGER {
		other(1),
		unknown(2),
		vRAM(3),
		dRAM(4),
		sRAM(5),
		wRAM(6),
		eDORAM(7),
		burstSynchronousDRAM(8),
		pipelinedBurstSRAM(9)
	}
	MAX-ACCESS	read-only
	STATUS		current
	DESCRIPTION	"The type of video memory for this adapter."
	REFERENCE "'DMTF|Video|002' 6"
	::= { dmtfVideoEntry 6 }

videoRAMMemorySize OBJECT-TYPE
	SYNTAX		DmiInteger
	MAX-ACCESS	read-only
	STATUS		current
	DESCRIPTION	"Video adapter memory size in kilobytes."
	REFERENCE "'DMTF|Video|002' 7"
	::= { dmtfVideoEntry 7 }

scanMode OBJECT-TYPE
	SYNTAX		INTEGER {
		other(1),
		unknown(2),
		interlaced(3),
		nonInterlaced(4)
	}
	MAX-ACCESS	read-only
	STATUS		current
	DESCRIPTION	"The scan mode for this video device."
	REFERENCE "'DMTF|Video|002' 8"
	::= { dmtfVideoEntry 8 }

videoPhysicalLocation OBJECT-TYPE
	SYNTAX		INTEGER {
		other(1),
		unknown(2),
		integrated(3),
		addOnCard(4)
	}
	MAX-ACCESS	read-only
	STATUS		current
	DESCRIPTION	"The location of the video controller circuitry."
	REFERENCE "'DMTF|Video|002' 9"
	::= { dmtfVideoEntry 9 }

currentVerticalResolution OBJECT-TYPE
	SYNTAX		DmiInteger
	MAX-ACCESS	read-only
	STATUS		current
	DESCRIPTION	"The current number of vertical pixels."
	REFERENCE "'DMTF|Video|002' 10"
	::= { dmtfVideoEntry 10 }

currentHorizontalResolution OBJECT-TYPE
	SYNTAX		DmiInteger
	MAX-ACCESS	read-only
	STATUS		current
	DESCRIPTION	"The current number of horizontal pixels."
	REFERENCE "'DMTF|Video|002' 11"
	::= { dmtfVideoEntry 11 }

currentNumberOfBitsPerPixel OBJECT-TYPE
	SYNTAX		DmiInteger
	MAX-ACCESS	read-only
	STATUS		current
	DESCRIPTION	"The number of bits used to display each pixel for this video
device."
	REFERENCE "'DMTF|Video|002' 12"
	::= { dmtfVideoEntry 12 }

currentNumberOfRows OBJECT-TYPE
	SYNTAX		DmiInteger
	MAX-ACCESS	read-only
	STATUS		current
	DESCRIPTION	"The number of rows in character mode for this video device."
	REFERENCE "'DMTF|Video|002' 13"
	::= { dmtfVideoEntry 13 }

currentNumberOfColumns OBJECT-TYPE
	SYNTAX		DmiInteger
	MAX-ACCESS	read-only
	STATUS		current
	DESCRIPTION	"The number of columns in character mode for this video device."
	REFERENCE "'DMTF|Video|002' 14"
	::= { dmtfVideoEntry 14 }

currentRefreshRate OBJECT-TYPE
	SYNTAX		DmiInteger
	MAX-ACCESS	read-only
	STATUS		current
	DESCRIPTION	"The current refresh rate in Hz for this video device."
	REFERENCE "'DMTF|Video|002' 15"
	::= { dmtfVideoEntry 15 }

fRUGroupIndex OBJECT-TYPE
	SYNTAX		DmiInteger
	MAX-ACCESS	read-only
	STATUS		current
	DESCRIPTION	"If this is a Field Replaceable Unit or if it is part of another
FRU, this provides an index into the FRU table; 'value = -1' indicates that
the group is not a FRU."
	REFERENCE "'DMTF|Video|002' 16"
	::= { dmtfVideoEntry 16 }

operationalGroupIndex OBJECT-TYPE
	SYNTAX		DmiInteger
	MAX-ACCESS	read-only
	STATUS		current
	DESCRIPTION	"The index into the Operational State table for this device."
	REFERENCE "'DMTF|Video|002' 17"
	::= { dmtfVideoEntry 17 }

SdmtfVoltageProbe ::= SEQUENCE {
	dmtfVoltageProbeState INTEGER,
	voltageProbeIndex	DmiInteger,
	voltageProbeLocation	DmiInteger,
	voltageProbeDescription	DmiString,
	voltageStatus	DmiInteger,
	voltageProbeVoltageLevel	DmiInteger,
	monitoredVoltageNominalLevel	DmiInteger,
	monitoredVoltageNormalMaximum	DmiInteger,
	monitoredVoltageNormalMinimum	DmiInteger,
	voltageProbeMaximum	DmiInteger,
	voltageProbeMinimum	DmiInteger,
	voltageLevelLowerThresholdNonCritical	DmiInteger,
	voltageLevelUpperThresholdNonCritical	DmiInteger,
	voltageLevelLowerThresholdCritical	DmiInteger,
	voltageLevelUpperThresholdCritical	DmiInteger,
	voltageLevelLowerThresholdNonRecoverable	DmiInteger,
	voltageLevelUpperThresholdNonRecoverable	DmiInteger,
	voltageProbeResolution	DmiInteger,
	voltageProbeTolerance	DmiInteger,
	voltageProbeAccuracy	DmiInteger,
	fRUGroupIndex	DmiInteger,
	operationalGroupIndex	DmiInteger
}

dmtfVoltageProbeTable OBJECT-TYPE
	SYNTAX		SEQUENCE OF SdmtfVoltageProbe
	MAX-ACCESS	not-accessible
	STATUS		current
	DESCRIPTION	"This group defines the attributes for the voltage probes
in this system."
	::= { dmtfSystemsMIF 53 }

dmtfVoltageProbeEntry OBJECT-TYPE
	SYNTAX		SdmtfVoltageProbe
	MAX-ACCESS	not-accessible
	STATUS		current
	DESCRIPTION	"This group defines the attributes for the voltage probes
in this system."
	INDEX		{ DmiCompId,DmiGroupId, voltageProbeIndex }
	::= { dmtfVoltageProbeTable 1 }


dmtfVoltageProbeState OBJECT-TYPE
	SYNTAX		INTEGER {
		active(1),
		notInService(2),
		notReady(3),
		createAndGo(4),
		createAndWait(5),
		destroy(6)
	}
	MAX-ACCESS	read-write
	STATUS		current
	REFERENCE "'DMTF|Voltage Probe|001' 0"
	::= { dmtfVoltageProbeEntry 0 }

voltageProbeIndex OBJECT-TYPE
	SYNTAX		DmiInteger
	MAX-ACCESS	read-only
	STATUS		current
	DESCRIPTION	"Index into this voltage probe table."
	REFERENCE "'DMTF|Voltage Probe|001' 1"
	::= { dmtfVoltageProbeEntry 1 }

voltageProbeLocation OBJECT-TYPE
	SYNTAX		INTEGER {
		other(1),
		unknown(2),
		processor(3),
		disk(4),
		peripheralBay(5),
		systemManagementModule(6),
		motherboard(7),
		memoryModule(8),
		processorModule(9),
		powerUnit(10),
		addInCard(11)
	}
	MAX-ACCESS	read-only
	STATUS		current
	DESCRIPTION	"Identifies the physical location of the voltage probe."
	REFERENCE "'DMTF|Voltage Probe|001' 2"
	::= { dmtfVoltageProbeEntry 2 }

voltageProbeDescription OBJECT-TYPE
	SYNTAX		DmiString
	MAX-ACCESS	read-only
	STATUS		current
	DESCRIPTION	"Additional descriptive information about the voltage probe
or probe's location."
	REFERENCE "'DMTF|Voltage Probe|001' 3"
	::= { dmtfVoltageProbeEntry 3 }

voltageStatus OBJECT-TYPE
	SYNTAX		INTEGER {
		other(1),
		unknown(2),
		oK(3),
		nonCritical(4),
		critical(5),
		nonRecoverable(6)
	}
	MAX-ACCESS	read-only
	STATUS		current
	DESCRIPTION	"Defines the status of the voltage monitored by this voltage
probe."
	REFERENCE "'DMTF|Voltage Probe|001' 4"
	::= { dmtfVoltageProbeEntry 4 }

voltageProbeVoltageLevel OBJECT-TYPE
	SYNTAX		DmiInteger
	MAX-ACCESS	read-only
	STATUS		current
	DESCRIPTION	"The current voltage level of this voltage probe in millivolts.
0x8000000 denotes 'unknown'."
	REFERENCE "'DMTF|Voltage Probe|001' 5"
	::= { dmtfVoltageProbeEntry 5 }

monitoredVoltageNominalLevel OBJECT-TYPE
	SYNTAX		DmiInteger
	MAX-ACCESS	read-only
	STATUS		current
	DESCRIPTION	"The nominal voltage level of the voltage monitored by this
probe in millivolts. 0x80000000 denotes 'unknown'."
	REFERENCE "'DMTF|Voltage Probe|001' 6"
	::= { dmtfVoltageProbeEntry 6 }

monitoredVoltageNormalMaximum OBJECT-TYPE
	SYNTAX		DmiInteger
	MAX-ACCESS	read-only
	STATUS		current
	DESCRIPTION	"The normal maximum voltage level of the voltage monitored
by this probe in millivolts. 0x80000000 denotes 'unknown'."
	REFERENCE "'DMTF|Voltage Probe|001' 7"
	::= { dmtfVoltageProbeEntry 7 }

monitoredVoltageNormalMinimum OBJECT-TYPE
	SYNTAX		DmiInteger
	MAX-ACCESS	read-only
	STATUS		current
	DESCRIPTION	"The normal minimum voltage level of the voltage monitored
by this probe in millivolts. 0x80000000 denotes 'unknown'."
	REFERENCE "'DMTF|Voltage Probe|001' 8"
	::= { dmtfVoltageProbeEntry 8 }

voltageProbeMaximum OBJECT-TYPE
	SYNTAX		DmiInteger
	MAX-ACCESS	read-only
	STATUS		current
	DESCRIPTION	"The maximum voltage level specified to be readable by this
probe in millivolts. 0x80000000 denotes 'unknown'."
	REFERENCE "'DMTF|Voltage Probe|001' 9"
	::= { dmtfVoltageProbeEntry 9 }

voltageProbeMinimum OBJECT-TYPE
	SYNTAX		DmiInteger
	MAX-ACCESS	read-only
	STATUS		current
	DESCRIPTION	"The minimum voltage level specified to be readable by this
probe in millivolts. 0x80000000 denotes 'unknown'."
	REFERENCE "'DMTF|Voltage Probe|001' 10"
	::= { dmtfVoltageProbeEntry 10 }

voltageLevelLowerThresholdNonCritical OBJECT-TYPE
	SYNTAX		DmiInteger
	MAX-ACCESS	read-write
	STATUS		current
	DESCRIPTION	"The lower non-critical threshold for the voltage level set
by the user, in millivolts. 0x80000000 denotes 'unknown'."
	REFERENCE "'DMTF|Voltage Probe|001' 11"
	::= { dmtfVoltageProbeEntry 11 }

voltageLevelUpperThresholdNonCritical OBJECT-TYPE
	SYNTAX		DmiInteger
	MAX-ACCESS	read-write
	STATUS		current
	DESCRIPTION	"The upper non-critical threshold for the voltage probe, in
millivolts.  0x80000000 denotes 'unknown'."
	REFERENCE "'DMTF|Voltage Probe|001' 12"
	::= { dmtfVoltageProbeEntry 12 }

voltageLevelLowerThresholdCritical OBJECT-TYPE
	SYNTAX		DmiInteger
	MAX-ACCESS	read-write
	STATUS		current
	DESCRIPTION	"The lower critical threshold for the voltage probe, in millivolt
.  0x80000000 denotes 'unknown'."
	REFERENCE "'DMTF|Voltage Probe|001' 13"
	::= { dmtfVoltageProbeEntry 13 }

voltageLevelUpperThresholdCritical OBJECT-TYPE
	SYNTAX		DmiInteger
	MAX-ACCESS	read-write
	STATUS		current
	DESCRIPTION	"The upper critical threshold for the voltage probe, in millivolt
.  0x80000000 denotes 'unknown'."
	REFERENCE "'DMTF|Voltage Probe|001' 14"
	::= { dmtfVoltageProbeEntry 14 }

voltageLevelLowerThresholdNonRecoverable OBJECT-TYPE
	SYNTAX		DmiInteger
	MAX-ACCESS	read-write
	STATUS		current
	DESCRIPTION	"The lower non-recoverable threshold for the voltage probe,
in millivolts.  0x80000000 denotes 'unknown'."
	REFERENCE "'DMTF|Voltage Probe|001' 15"
	::= { dmtfVoltageProbeEntry 15 }

voltageLevelUpperThresholdNonRecoverable OBJECT-TYPE
	SYNTAX		DmiInteger
	MAX-ACCESS	read-write
	STATUS		current
	DESCRIPTION	"The upper non-recoverable threshold for the voltage probe,
in millivolts. 0x80000000 denotes 'unknown'."
	REFERENCE "'DMTF|Voltage Probe|001' 16"
	::= { dmtfVoltageProbeEntry 16 }

voltageProbeResolution OBJECT-TYPE
	SYNTAX		DmiInteger
	MAX-ACCESS	read-write
	STATUS		current
	DESCRIPTION	"The resolution for the reading from this voltage probe, in
tenths of millivolts. '0x80000000 denotes 'unknown'."
	REFERENCE "'DMTF|Voltage Probe|001' 17"
	::= { dmtfVoltageProbeEntry 17 }

voltageProbeTolerance OBJECT-TYPE
	SYNTAX		DmiInteger
	MAX-ACCESS	read-write
	STATUS		current
	DESCRIPTION	"The tolerance for the reading from this voltage probe, in
plus/minus millivolts. 0x80000000 denotes 'unknown'."
	REFERENCE "'DMTF|Voltage Probe|001' 18"
	::= { dmtfVoltageProbeEntry 18 }

voltageProbeAccuracy OBJECT-TYPE
	SYNTAX		DmiInteger
	MAX-ACCESS	read-write
	STATUS		current
	DESCRIPTION	"The accuracy for the reading from this voltage probe, in
plus/minus hundredths of a percent. 0x80000000 denotes 'unknown'."
	REFERENCE "'DMTF|Voltage Probe|001' 19"
	::= { dmtfVoltageProbeEntry 19 }

fRUGroupIndex OBJECT-TYPE
	SYNTAX		DmiInteger
	MAX-ACCESS	read-only
	STATUS		current
	DESCRIPTION	"Index into the FRU table"
	REFERENCE "'DMTF|Voltage Probe|001' 20"
	::= { dmtfVoltageProbeEntry 20 }

operationalGroupIndex OBJECT-TYPE
	SYNTAX		DmiInteger
	MAX-ACCESS	read-only
	STATUS		current
	DESCRIPTION	"Index into the Operational State table"
	REFERENCE "'DMTF|Voltage Probe|001' 21"
	::= { dmtfVoltageProbeEntry 21 }

dmtfCoolingDeviceTraps OBJECT IDENTIFIER ::= { dmtfCoolingDeviceTable 0 }

dmtfCoolingDeviceEvSys OBJECT-TYPE
	SYNTAX		INTEGER {
		other(0),
		unknown(1)
	}
	MAX-ACCESS	not-accessible
	STATUS		current
	DESCRIPTION	"The major functional aspect of the product causing the fault."
	::= {dmtfCoolingDeviceTable 6 }

dmtfCoolingDeviceEvSub OBJECT-TYPE
	SYNTAX		INTEGER {
		other(0),
		unknown(1)
	}
	MAX-ACCESS	not-accessible
	STATUS		current
	DESCRIPTION	"The minor functional aspect of the product causing the fault."
	::= {dmtfCoolingDeviceTable 7 }

dmtfCoolingDeviceStatusChange NOTIFICATION-TYPE
	OBJECTS {
		dmiEventDateTime,
		dmiCompId,
		dmiEventSeverity,
		dmiEventStateKey,
		dmiEventAssociatedGroup
,		dmtfCoolingDeviceEvSys
,		dmtfCoolingDeviceEvSub
		}
	STATUS current
	DESCRIPTION "A cooling device (e.g., fan) on the system 
		    has changed status according to the event
		    severity indicated.  
		    
		    Improper operation of a system cooling device 
		    can lead to over-heating and eventual breakdown 
		    of the system."
	REFERENCE "'DMTF|Cooling Device|001' 1"
	::= { dmtfCoolingDeviceTraps 1 }

dmtfCoolingDeviceTemperatureFault NOTIFICATION-TYPE
	OBJECTS {
		dmiEventDateTime,
		dmiCompId,
		dmiEventSeverity,
		dmiEventStateKey,
		dmiEventAssociatedGroup
,		dmtfCoolingDeviceEvSys
,		dmtfCoolingDeviceEvSub
		}
	STATUS current
	DESCRIPTION "A temperature fault has been detected by a cooling
		     device (e.g., fan) on the system. The system or a 
		     system component is either over-heating or too cold.
		     Probable causes include an inoperable or obstructed
		     cooling device; or insufficient ventilation around
		     the system.
		    
		     This condition can lead to eventual breakdown 
		     of the system if left unattended."
	REFERENCE "'DMTF|Cooling Device|001' 2"
	::= { dmtfCoolingDeviceTraps 2 }

dmtfDiskControllerTraps OBJECT IDENTIFIER ::= { dmtfDiskControllerTable 0 }

dmtfDiskControllerEvSys OBJECT-TYPE
	SYNTAX		INTEGER {
		other(0),
		unknown(1)
	}
	MAX-ACCESS	not-accessible
	STATUS		current
	DESCRIPTION	"The major functional aspect of the product causing the fault."
	::= {dmtfDiskControllerTable 6 }

dmtfDiskControllerEvSub OBJECT-TYPE
	SYNTAX		INTEGER {
		other(0),
		unknown(1)
	}
	MAX-ACCESS	not-accessible
	STATUS		current
	DESCRIPTION	"The minor functional aspect of the product causing the fault."
	::= {dmtfDiskControllerTable 7 }

dmtfDiskControllerInitializationFailure NOTIFICATION-TYPE
	OBJECTS {
		dmiEventDateTime,
		dmiCompId,
		dmiEventSeverity,
		dmiEventStateKey,
		dmiEventAssociatedGroup
,		dmtfDiskControllerEvSys
,		dmtfDiskControllerEvSub
		}
	STATUS current
	DESCRIPTION "A disk controller on the system failed to initialize
		    properly during system startup."
	REFERENCE "'DMTF|Disk Controller|001' 1"
	::= { dmtfDiskControllerTraps 1 }

dmtfDiskControllerConfigurationError NOTIFICATION-TYPE
	OBJECTS {
		dmiEventDateTime,
		dmiCompId,
		dmiEventSeverity,
		dmiEventStateKey,
		dmiEventAssociatedGroup
,		dmtfDiskControllerEvSys
,		dmtfDiskControllerEvSub
		}
	STATUS current
	DESCRIPTION "A disk controller on the system is not properly configured"
	REFERENCE "'DMTF|Disk Controller|001' 2"
	::= { dmtfDiskControllerTraps 2 }

dmtfDisksTraps OBJECT IDENTIFIER ::= { dmtfDisksTable 0 }

dmtfDisksEvSys OBJECT-TYPE
	SYNTAX		INTEGER {
		other(0),
		unknown(1)
	}
	MAX-ACCESS	not-accessible
	STATUS		current
	DESCRIPTION	"The major functional aspect of the product causing the fault."
	::= {dmtfDisksTable 6 }

dmtfDisksEvSub OBJECT-TYPE
	SYNTAX		INTEGER {
		other(0),
		unknown(1)
	}
	MAX-ACCESS	not-accessible
	STATUS		current
	DESCRIPTION	"The minor functional aspect of the product causing the fault."
	::= {dmtfDisksTable 7 }

dmtfDisksStatusChange NOTIFICATION-TYPE
	OBJECTS {
		dmiEventDateTime,
		dmiCompId,
		dmiEventSeverity,
		dmiEventStateKey,
		dmiEventAssociatedGroup
,		dmtfDisksEvSys
,		dmtfDisksEvSub
		}
	STATUS current
	DESCRIPTION "The operational status of a physical disk 
		    on the system has changed, as indicated by
		    the event severity."
	REFERENCE "'DMTF|Disks|001' 1"
	::= { dmtfDisksTraps 1 }

dmtfDisksInitializationError NOTIFICATION-TYPE
	OBJECTS {
		dmiEventDateTime,
		dmiCompId,
		dmiEventSeverity,
		dmiEventStateKey,
		dmiEventAssociatedGroup
,		dmtfDisksEvSys
,		dmtfDisksEvSub
		}
	STATUS current
	DESCRIPTION "A physical disk drive on the system failed 
		    to initialize properly on startup."
	REFERENCE "'DMTF|Disks|001' 2"
	::= { dmtfDisksTraps 2 }

dmtfDisksConfigurationError NOTIFICATION-TYPE
	OBJECTS {
		dmiEventDateTime,
		dmiCompId,
		dmiEventSeverity,
		dmiEventStateKey,
		dmiEventAssociatedGroup
,		dmtfDisksEvSys
,		dmtfDisksEvSub
		}
	STATUS current
	DESCRIPTION "A disk drive on the system is not properly configured"
	REFERENCE "'DMTF|Disks|001' 3"
	::= { dmtfDisksTraps 3 }

dmtfElectricalCurrentProbeTraps OBJECT IDENTIFIER ::= { dmtfElectricalCurrentProbeTable 0 }

dmtfElectricalCurrentProbeEvSys OBJECT-TYPE
	SYNTAX		INTEGER {
		other(0),
		unknown(1)
	}
	MAX-ACCESS	not-accessible
	STATUS		current
	DESCRIPTION	"The major functional aspect of the product causing the fault."
	::= {dmtfElectricalCurrentProbeTable 6 }

dmtfElectricalCurrentProbeEvSub OBJECT-TYPE
	SYNTAX		INTEGER {
		other(0),
		unknown(1)
	}
	MAX-ACCESS	not-accessible
	STATUS		current
	DESCRIPTION	"The minor functional aspect of the product causing the fault."
	::= {dmtfElectricalCurrentProbeTable 7 }

dmtfElectricalCurrentProbePowerSupplyStatusChange NOTIFICATION-TYPE
	OBJECTS {
		dmiEventDateTime,
		dmiCompId,
		dmiEventSeverity,
		dmiEventStateKey,
		dmiEventAssociatedGroup
,		dmtfElectricalCurrentProbeEvSys
,		dmtfElectricalCurrentProbeEvSub
		}
	STATUS current
	DESCRIPTION "An electrical current probe on the system has
		    detected an abnormal change in electrical current
		    from a power supply to the monitored component of
		    the system."
	REFERENCE "'DMTF|Electrical Current Probe|001' 1"
	::= { dmtfElectricalCurrentProbeTraps 1 }

dmtfElectricalCurrentProbeCoolingDeviceStatusChange NOTIFICATION-TYPE
	OBJECTS {
		dmiEventDateTime,
		dmiCompId,
		dmiEventSeverity,
		dmiEventStateKey,
		dmiEventAssociatedGroup
,		dmtfElectricalCurrentProbeEvSys
,		dmtfElectricalCurrentProbeEvSub
		}
	STATUS current
	DESCRIPTION "A cooling device (e.g., Fan) on the system has changed 
		    status due to loss of (or regained) electrical power."
	REFERENCE "'DMTF|Electrical Current Probe|001' 2"
	::= { dmtfElectricalCurrentProbeTraps 2 }

dmtfLogicalMemoryTraps OBJECT IDENTIFIER ::= { dmtfLogicalMemoryTable 0 }

dmtfLogicalMemoryEvSys OBJECT-TYPE
	SYNTAX		INTEGER {
		other(0),
		unknown(1)
	}
	MAX-ACCESS	not-accessible
	STATUS		current
	DESCRIPTION	"The major functional aspect of the product causing the fault."
	::= {dmtfLogicalMemoryTable 6 }

dmtfLogicalMemoryEvSub OBJECT-TYPE
	SYNTAX		INTEGER {
		other(0),
		unknown(1)
	}
	MAX-ACCESS	not-accessible
	STATUS		current
	DESCRIPTION	"The minor functional aspect of the product causing the fault."
	::= {dmtfLogicalMemoryTable 7 }

dmtfLogicalMemoryError NOTIFICATION-TYPE
	OBJECTS {
		dmiEventDateTime,
		dmiCompId,
		dmiEventSeverity,
		dmiEventStateKey,
		dmiEventAssociatedGroup
,		dmtfLogicalMemoryEvSys
,		dmtfLogicalMemoryEvSub
		}
	STATUS current
	DESCRIPTION "A an error has occured in the system's logical memory space."
	REFERENCE "'DMTF|Logical Memory|001' 1"
	::= { dmtfLogicalMemoryTraps 1 }

dmtfLogicalMemoryInitializationFailure NOTIFICATION-TYPE
	OBJECTS {
		dmiEventDateTime,
		dmiCompId,
		dmiEventSeverity,
		dmiEventStateKey,
		dmiEventAssociatedGroup
,		dmtfLogicalMemoryEvSys
,		dmtfLogicalMemoryEvSub
		}
	STATUS current
	DESCRIPTION "An error occured while initializing the system's memory."
	REFERENCE "'DMTF|Logical Memory|001' 2"
	::= { dmtfLogicalMemoryTraps 2 }

dmtfMassStoreLogicalDrivesTraps OBJECT IDENTIFIER ::= { dmtfMassStoreLogicalDrivesTable 0 }

dmtfMassStoreLogicalDrivesEvSys OBJECT-TYPE
	SYNTAX		INTEGER {
		other(0),
		unknown(1)
	}
	MAX-ACCESS	not-accessible
	STATUS		current
	DESCRIPTION	"The major functional aspect of the product causing the fault."
	::= {dmtfMassStoreLogicalDrivesTable 6 }

dmtfMassStoreLogicalDrivesEvSub OBJECT-TYPE
	SYNTAX		INTEGER {
		other(0),
		unknown(1)
	}
	MAX-ACCESS	not-accessible
	STATUS		current
	DESCRIPTION	"The minor functional aspect of the product causing the fault."
	::= {dmtfMassStoreLogicalDrivesTable 7 }

dmtfMassStoreLogicalDrivesPhysicalDeviceStatusChange NOTIFICATION-TYPE
	OBJECTS {
		dmiEventDateTime,
		dmiCompId,
		dmiEventSeverity,
		dmiEventStateKey,
		dmiEventAssociatedGroup
,		dmtfMassStoreLogicalDrivesEvSys
,		dmtfMassStoreLogicalDrivesEvSub
		}
	STATUS current
	DESCRIPTION "The status of a Logical Disk Drive
                    (e.g., file system volume) has changed."
	REFERENCE "'DMTF|Mass Store Logical Drives Table|001' 1"
	::= { dmtfMassStoreLogicalDrivesTraps 1 }

dmtfMassStoreLogicalDrivesHotSpareActivated NOTIFICATION-TYPE
	OBJECTS {
		dmiEventDateTime,
		dmiCompId,
		dmiEventSeverity,
		dmiEventStateKey,
		dmiEventAssociatedGroup
,		dmtfMassStoreLogicalDrivesEvSys
,		dmtfMassStoreLogicalDrivesEvSub
		}
	STATUS current
	DESCRIPTION "The 'hot-swap spare' for an inoperable
		    logical disk drive has been activated."
	REFERENCE "'DMTF|Mass Store Logical Drives Table|001' 2"
	::= { dmtfMassStoreLogicalDrivesTraps 2 }

dmtfMassStoreLogicalDrivesLogicalDeviceStatusChange NOTIFICATION-TYPE
	OBJECTS {
		dmiEventDateTime,
		dmiCompId,
		dmiEventSeverity,
		dmiEventStateKey,
		dmiEventAssociatedGroup
,		dmtfMassStoreLogicalDrivesEvSys
,		dmtfMassStoreLogicalDrivesEvSub
		}
	STATUS current
	DESCRIPTION "logicalDeviceStatusChange"
	REFERENCE "'DMTF|Mass Store Logical Drives Table|001' 3"
	::= { dmtfMassStoreLogicalDrivesTraps 3 }

dmtfMassStoreLogicalDrivesInitializationFailure NOTIFICATION-TYPE
	OBJECTS {
		dmiEventDateTime,
		dmiCompId,
		dmiEventSeverity,
		dmiEventStateKey,
		dmiEventAssociatedGroup
,		dmtfMassStoreLogicalDrivesEvSys
,		dmtfMassStoreLogicalDrivesEvSub
		}
	STATUS current
	DESCRIPTION "A logical disk drive on the system failed to
		    initialize properly during system startup."
	REFERENCE "'DMTF|Mass Store Logical Drives Table|001' 4"
	::= { dmtfMassStoreLogicalDrivesTraps 4 }

dmtfMassStoreLogicalDrivesConfigurationError NOTIFICATION-TYPE
	OBJECTS {
		dmiEventDateTime,
		dmiCompId,
		dmiEventSeverity,
		dmiEventStateKey,
		dmiEventAssociatedGroup
,		dmtfMassStoreLogicalDrivesEvSys
,		dmtfMassStoreLogicalDrivesEvSub
		}
	STATUS current
	DESCRIPTION "A logical disk drive on the system is not properly configured"
	REFERENCE "'DMTF|Mass Store Logical Drives Table|001' 5"
	::= { dmtfMassStoreLogicalDrivesTraps 5 }

dmtfMotherboardTraps OBJECT IDENTIFIER ::= { dmtfMotherboardTable 0 }

dmtfMotherboardEvSys OBJECT-TYPE
	SYNTAX		INTEGER {
		other(0),
		unknown(1)
	}
	MAX-ACCESS	not-accessible
	STATUS		current
	DESCRIPTION	"The major functional aspect of the product causing the fault."
	::= {dmtfMotherboardTable 6 }

dmtfMotherboardEvSub OBJECT-TYPE
	SYNTAX		INTEGER {
		other(0),
		unknown(1)
	}
	MAX-ACCESS	not-accessible
	STATUS		current
	DESCRIPTION	"The minor functional aspect of the product causing the fault."
	::= {dmtfMotherboardTable 7 }

dmtfMotherboardProcessorFailure NOTIFICATION-TYPE
	OBJECTS {
		dmiEventDateTime,
		dmiCompId,
		dmiEventSeverity,
		dmiEventStateKey,
		dmiEventAssociatedGroup
,		dmtfMotherboardEvSys
,		dmtfMotherboardEvSub
		}
	STATUS current
	DESCRIPTION "A processor on the system motherboard has 
		    failed or been fixed according to the event
		    severity indicated."
	REFERENCE "'DMTF|Motherboard|001' 1"
	::= { dmtfMotherboardTraps 1 }

dmtfMotherboardPhysicalDeviceStatusChange NOTIFICATION-TYPE
	OBJECTS {
		dmiEventDateTime,
		dmiCompId,
		dmiEventSeverity,
		dmiEventStateKey,
		dmiEventAssociatedGroup
,		dmtfMotherboardEvSys
,		dmtfMotherboardEvSub
		}
	STATUS current
	DESCRIPTION "The motherboard physical status has changed
		    according to the event severity indicated."
	REFERENCE "'DMTF|Motherboard|001' 2"
	::= { dmtfMotherboardTraps 2 }

dmtfMotherboardMemoryError NOTIFICATION-TYPE
	OBJECTS {
		dmiEventDateTime,
		dmiCompId,
		dmiEventSeverity,
		dmiEventStateKey,
		dmiEventAssociatedGroup
,		dmtfMotherboardEvSys
,		dmtfMotherboardEvSub
		}
	STATUS current
	DESCRIPTION "A memory module on the system's motherboard
		     has failed."
	REFERENCE "'DMTF|Motherboard|001' 3"
	::= { dmtfMotherboardTraps 3 }

dmtfMotherboardSystemUp NOTIFICATION-TYPE
	OBJECTS {
		dmiEventDateTime,
		dmiCompId,
		dmiEventSeverity,
		dmiEventStateKey,
		dmiEventAssociatedGroup
,		dmtfMotherboardEvSys
,		dmtfMotherboardEvSub
		}
	STATUS current
	DESCRIPTION "The system's motherboard reports it has
		     started-up successfully."
	REFERENCE "'DMTF|Motherboard|001' 4"
	::= { dmtfMotherboardTraps 4 }

dmtfMotherboardInitializationFailure NOTIFICATION-TYPE
	OBJECTS {
		dmiEventDateTime,
		dmiCompId,
		dmiEventSeverity,
		dmiEventStateKey,
		dmiEventAssociatedGroup
,		dmtfMotherboardEvSys
,		dmtfMotherboardEvSub
		}
	STATUS current
	DESCRIPTION "The system's motherboard has failed to
		    initialize properly during system startup."
	REFERENCE "'DMTF|Motherboard|001' 5"
	::= { dmtfMotherboardTraps 5 }

dmtfMotherboardConfigurationError NOTIFICATION-TYPE
	OBJECTS {
		dmiEventDateTime,
		dmiCompId,
		dmiEventSeverity,
		dmiEventStateKey,
		dmiEventAssociatedGroup
,		dmtfMotherboardEvSys
,		dmtfMotherboardEvSub
		}
	STATUS current
	DESCRIPTION "The system's motherboard is not properly configured"
	REFERENCE "'DMTF|Motherboard|001' 6"
	::= { dmtfMotherboardTraps 6 }

dmtfPhysicalContainerGlobalTraps OBJECT IDENTIFIER ::= { dmtfPhysicalContainerGlobalTable 0 }

dmtfPhysicalContainerGlobalEvSys OBJECT-TYPE
	SYNTAX		INTEGER {
		other(0),
		unknown(1)
	}
	MAX-ACCESS	not-accessible
	STATUS		current
	DESCRIPTION	"The major functional aspect of the product causing the fault."
	::= {dmtfPhysicalContainerGlobalTable 6 }

dmtfPhysicalContainerGlobalEvSub OBJECT-TYPE
	SYNTAX		INTEGER {
		other(0),
		unknown(1)
	}
	MAX-ACCESS	not-accessible
	STATUS		current
	DESCRIPTION	"The minor functional aspect of the product causing the fault."
	::= {dmtfPhysicalContainerGlobalTable 7 }

dmtfPhysicalContainerSecuritySettingsChange NOTIFICATION-TYPE
	OBJECTS {
		dmiEventDateTime,
		dmiCompId,
		dmiEventSeverity,
		dmiEventStateKey,
		dmiEventAssociatedGroup
,		dmtfPhysicalContainerGlobalEvSys
,		dmtfPhysicalContainerGlobalEvSub
		}
	STATUS current
	DESCRIPTION "The security settings for the system chassis or 
		     physical container in the system have been modified."
	REFERENCE "'DMTF|Physical Container Global Table|001' 1"
	::= { dmtfPhysicalContainerGlobalTraps 1 }

dmtfPhysicalContainerPowerSupplyStatusChange NOTIFICATION-TYPE
	OBJECTS {
		dmiEventDateTime,
		dmiCompId,
		dmiEventSeverity,
		dmiEventStateKey,
		dmiEventAssociatedGroup
,		dmtfPhysicalContainerGlobalEvSys
,		dmtfPhysicalContainerGlobalEvSub
		}
	STATUS current
	DESCRIPTION "The power supply for an associated system
		    chassis or physical container has changed status."
	REFERENCE "'DMTF|Physical Container Global Table|001' 2"
	::= { dmtfPhysicalContainerGlobalTraps 2 }

dmtfPhysicalContainerCoolingDeviceStatusChange NOTIFICATION-TYPE
	OBJECTS {
		dmiEventDateTime,
		dmiCompId,
		dmiEventSeverity,
		dmiEventStateKey,
		dmiEventAssociatedGroup
,		dmtfPhysicalContainerGlobalEvSys
,		dmtfPhysicalContainerGlobalEvSub
		}
	STATUS current
	DESCRIPTION "The cooling device for an associated system
		    chassis or physical container has changed status."
	REFERENCE "'DMTF|Physical Container Global Table|001' 3"
	::= { dmtfPhysicalContainerGlobalTraps 3 }

dmtfPhysicalContainerPhysicalDeviceStatusChange NOTIFICATION-TYPE
	OBJECTS {
		dmiEventDateTime,
		dmiCompId,
		dmiEventSeverity,
		dmiEventStateKey,
		dmiEventAssociatedGroup
,		dmtfPhysicalContainerGlobalEvSys
,		dmtfPhysicalContainerGlobalEvSub
		}
	STATUS current
	DESCRIPTION "physicalDeviceStatusChange"
	REFERENCE "'DMTF|Physical Container Global Table|001' 4"
	::= { dmtfPhysicalContainerGlobalTraps 4 }

dmtfPhysicalContainerLogicalDeviceStatusChange NOTIFICATION-TYPE
	OBJECTS {
		dmiEventDateTime,
		dmiCompId,
		dmiEventSeverity,
		dmiEventStateKey,
		dmiEventAssociatedGroup
,		dmtfPhysicalContainerGlobalEvSys
,		dmtfPhysicalContainerGlobalEvSub
		}
	STATUS current
	DESCRIPTION "logicalDeviceStatusChange"
	REFERENCE "'DMTF|Physical Container Global Table|001' 5"
	::= { dmtfPhysicalContainerGlobalTraps 5 }

dmtfPhysicalContainerSecurityBreach NOTIFICATION-TYPE
	OBJECTS {
		dmiEventDateTime,
		dmiCompId,
		dmiEventSeverity,
		dmiEventStateKey,
		dmiEventAssociatedGroup
,		dmtfPhysicalContainerGlobalEvSys
,		dmtfPhysicalContainerGlobalEvSub
		}
	STATUS current
	DESCRIPTION "The system chassis has been opened has 
		    been opened without poper authorization."
	REFERENCE "'DMTF|Physical Container Global Table|001' 6"
	::= { dmtfPhysicalContainerGlobalTraps 6 }

dmtfPhysicalContainerConfigurationError NOTIFICATION-TYPE
	OBJECTS {
		dmiEventDateTime,
		dmiCompId,
		dmiEventSeverity,
		dmiEventStateKey,
		dmiEventAssociatedGroup
,		dmtfPhysicalContainerGlobalEvSys
,		dmtfPhysicalContainerGlobalEvSub
		}
	STATUS current
	DESCRIPTION "A chassis or other physical container on the 
		    system is not properly configured."
	REFERENCE "'DMTF|Physical Container Global Table|001' 7"
	::= { dmtfPhysicalContainerGlobalTraps 7 }

dmtfPhysicalMemoryArrayTraps OBJECT IDENTIFIER ::= { dmtfPhysicalMemoryArrayTable 0 }

dmtfPhysicalMemoryArrayEvSys OBJECT-TYPE
	SYNTAX		INTEGER {
		other(0),
		unknown(1)
	}
	MAX-ACCESS	not-accessible
	STATUS		current
	DESCRIPTION	"The major functional aspect of the product causing the fault."
	::= {dmtfPhysicalMemoryArrayTable 6 }

dmtfPhysicalMemoryArrayEvSub OBJECT-TYPE
	SYNTAX		INTEGER {
		other(0),
		unknown(1)
	}
	MAX-ACCESS	not-accessible
	STATUS		current
	DESCRIPTION	"The minor functional aspect of the product causing the fault."
	::= {dmtfPhysicalMemoryArrayTable 7 }

dmtfPhysicalMemoryArrayError NOTIFICATION-TYPE
	OBJECTS {
		dmiEventDateTime,
		dmiCompId,
		dmiEventSeverity,
		dmiEventStateKey,
		dmiEventAssociatedGroup
,		dmtfPhysicalMemoryArrayEvSys
,		dmtfPhysicalMemoryArrayEvSub
		}
	STATUS current
	DESCRIPTION "A physical memory module in the system has failed."
	REFERENCE "'DMTF|Physical Memory Array|001' 1"
	::= { dmtfPhysicalMemoryArrayTraps 1 }

dmtfPhysicalMemoryArrayInitializationFailure NOTIFICATION-TYPE
	OBJECTS {
		dmiEventDateTime,
		dmiCompId,
		dmiEventSeverity,
		dmiEventStateKey,
		dmiEventAssociatedGroup
,		dmtfPhysicalMemoryArrayEvSys
,		dmtfPhysicalMemoryArrayEvSub
		}
	STATUS current
	DESCRIPTION "A physical memory module in the system failed
		    to initialize properly during system startup."
	REFERENCE "'DMTF|Physical Memory Array|001' 2"
	::= { dmtfPhysicalMemoryArrayTraps 2 }

dmtfPowerSupplyTraps OBJECT IDENTIFIER ::= { dmtfPowerSupplyTable 0 }

dmtfPowerSupplyEvSys OBJECT-TYPE
	SYNTAX		INTEGER {
		other(0),
		unknown(1)
	}
	MAX-ACCESS	not-accessible
	STATUS		current
	DESCRIPTION	"The major functional aspect of the product causing the fault."
	::= {dmtfPowerSupplyTable 6 }

dmtfPowerSupplyEvSub OBJECT-TYPE
	SYNTAX		INTEGER {
		other(0),
		unknown(1)
	}
	MAX-ACCESS	not-accessible
	STATUS		current
	DESCRIPTION	"The minor functional aspect of the product causing the fault."
	::= {dmtfPowerSupplyTable 7 }

dmtfPowerSupplyStatusChange NOTIFICATION-TYPE
	OBJECTS {
		dmiEventDateTime,
		dmiCompId,
		dmiEventSeverity,
		dmiEventStateKey,
		dmiEventAssociatedGroup
,		dmtfPowerSupplyEvSys
,		dmtfPowerSupplyEvSub
		}
	STATUS current
	DESCRIPTION "The operational status of a power supply
		    on the system has changed according to the
		    event severity indicated."
	REFERENCE "'DMTF|Power Supply|001' 1"
	::= { dmtfPowerSupplyTraps 1 }

dmtfPowerSupplyPowerControlRequest NOTIFICATION-TYPE
	OBJECTS {
		dmiEventDateTime,
		dmiCompId,
		dmiEventSeverity,
		dmiEventStateKey,
		dmiEventAssociatedGroup
,		dmtfPowerSupplyEvSys
,		dmtfPowerSupplyEvSub
		}
	STATUS current
	DESCRIPTION "The power control setting for a power supply
		    on the system has changed."
	REFERENCE "'DMTF|Power Supply|001' 2"
	::= { dmtfPowerSupplyTraps 2 }

dmtfProcessorTraps OBJECT IDENTIFIER ::= { dmtfProcessorTable 0 }

dmtfProcessorEvSys OBJECT-TYPE
	SYNTAX		INTEGER {
		other(0),
		unknown(1)
	}
	MAX-ACCESS	not-accessible
	STATUS		current
	DESCRIPTION	"The major functional aspect of the product causing the fault."
	::= {dmtfProcessorTable 6 }

dmtfProcessorEvSub OBJECT-TYPE
	SYNTAX		INTEGER {
		other(0),
		unknown(1)
	}
	MAX-ACCESS	not-accessible
	STATUS		current
	DESCRIPTION	"The minor functional aspect of the product causing the fault."
	::= {dmtfProcessorTable 7 }

dmtfProcessorFailure NOTIFICATION-TYPE
	OBJECTS {
		dmiEventDateTime,
		dmiCompId,
		dmiEventSeverity,
		dmiEventStateKey,
		dmiEventAssociatedGroup
,		dmtfProcessorEvSys
,		dmtfProcessorEvSub
		}
	STATUS current
	DESCRIPTION "A processor in the system has failed"
	REFERENCE "'DMTF|Processor|001' 1"
	::= { dmtfProcessorTraps 1 }

dmtfProcessorSystemUp NOTIFICATION-TYPE
	OBJECTS {
		dmiEventDateTime,
		dmiCompId,
		dmiEventSeverity,
		dmiEventStateKey,
		dmiEventAssociatedGroup
,		dmtfProcessorEvSys
,		dmtfProcessorEvSub
		}
	STATUS current
	DESCRIPTION "A system processor is now up and running."
	REFERENCE "'DMTF|Processor|001' 2"
	::= { dmtfProcessorTraps 2 }

dmtfProcessorInitializationFailure NOTIFICATION-TYPE
	OBJECTS {
		dmiEventDateTime,
		dmiCompId,
		dmiEventSeverity,
		dmiEventStateKey,
		dmiEventAssociatedGroup
,		dmtfProcessorEvSys
,		dmtfProcessorEvSub
		}
	STATUS current
	DESCRIPTION "A system processor failed to initialize 
		    properly during system startup."
	REFERENCE "'DMTF|Processor|001' 3"
	::= { dmtfProcessorTraps 3 }

dmtfProcessorConfigurationError NOTIFICATION-TYPE
	OBJECTS {
		dmiEventDateTime,
		dmiCompId,
		dmiEventSeverity,
		dmiEventStateKey,
		dmiEventAssociatedGroup
,		dmtfProcessorEvSys
,		dmtfProcessorEvSub
		}
	STATUS current
	DESCRIPTION "A system processor is not properly configured"
	REFERENCE "'DMTF|Processor|001' 4"
	::= { dmtfProcessorTraps 4 }

dmtfStructureDependencyTraps OBJECT IDENTIFIER ::= { dmtfStructureDependencyTable 0 }

dmtfStructureDependencyEvSys OBJECT-TYPE
	SYNTAX		INTEGER {
		other(0),
		unknown(1)
	}
	MAX-ACCESS	not-accessible
	STATUS		current
	DESCRIPTION	"The major functional aspect of the product causing the fault."
	::= {dmtfStructureDependencyTable 6 }

dmtfStructureDependencyEvSub OBJECT-TYPE
	SYNTAX		INTEGER {
		other(0),
		unknown(1)
	}
	MAX-ACCESS	not-accessible
	STATUS		current
	DESCRIPTION	"The minor functional aspect of the product causing the fault."
	::= {dmtfStructureDependencyTable 7 }

dmtfStructureDependencyPowerSupplyStatusChange NOTIFICATION-TYPE
	OBJECTS {
		dmiEventDateTime,
		dmiCompId,
		dmiEventSeverity,
		dmiEventStateKey,
		dmiEventAssociatedGroup
,		dmtfStructureDependencyEvSys
,		dmtfStructureDependencyEvSub
		}
	STATUS current
	DESCRIPTION "A power supply in the system has changed status."
	REFERENCE "'DMTF|Structure Dependency Table|001' 1"
	::= { dmtfStructureDependencyTraps 1 }

dmtfStructureDependencyCoolingDeviceStatusChange NOTIFICATION-TYPE
	OBJECTS {
		dmiEventDateTime,
		dmiCompId,
		dmiEventSeverity,
		dmiEventStateKey,
		dmiEventAssociatedGroup
,		dmtfStructureDependencyEvSys
,		dmtfStructureDependencyEvSub
		}
	STATUS current
	DESCRIPTION "A cooling device (e.g., fan) in the system 
		    has changed status."
	REFERENCE "'DMTF|Structure Dependency Table|001' 2"
	::= { dmtfStructureDependencyTraps 2 }

dmtfStructureDependencyPhysicalDeviceStatusChange NOTIFICATION-TYPE
	OBJECTS {
		dmiEventDateTime,
		dmiCompId,
		dmiEventSeverity,
		dmiEventStateKey,
		dmiEventAssociatedGroup
,		dmtfStructureDependencyEvSys
,		dmtfStructureDependencyEvSub
		}
	STATUS current
	DESCRIPTION "A physical device in the system has
		    changed status."
	REFERENCE "'DMTF|Structure Dependency Table|001' 3"
	::= { dmtfStructureDependencyTraps 3 }

dmtfStructureDependencyLogicalDeviceStatusChange NOTIFICATION-TYPE
	OBJECTS {
		dmiEventDateTime,
		dmiCompId,
		dmiEventSeverity,
		dmiEventStateKey,
		dmiEventAssociatedGroup
,		dmtfStructureDependencyEvSys
,		dmtfStructureDependencyEvSub
		}
	STATUS current
	DESCRIPTION "A logical device in the system has
		    changed status."
	REFERENCE "'DMTF|Structure Dependency Table|001' 4"
	::= { dmtfStructureDependencyTraps 4 }

dmtfStructureDependencySystemUp NOTIFICATION-TYPE
	OBJECTS {
		dmiEventDateTime,
		dmiCompId,
		dmiEventSeverity,
		dmiEventStateKey,
		dmiEventAssociatedGroup
,		dmtfStructureDependencyEvSys
,		dmtfStructureDependencyEvSub
		}
	STATUS current
	DESCRIPTION "An element of the system is up and running"
	REFERENCE "'DMTF|Structure Dependency Table|001' 5"
	::= { dmtfStructureDependencyTraps 5 }

dmtfStructureDependencyBatteryStatusChange NOTIFICATION-TYPE
	OBJECTS {
		dmiEventDateTime,
		dmiCompId,
		dmiEventSeverity,
		dmiEventStateKey,
		dmiEventAssociatedGroup
,		dmtfStructureDependencyEvSys
,		dmtfStructureDependencyEvSub
		}
	STATUS current
	DESCRIPTION "A battery powering the system has changed status."
	REFERENCE "'DMTF|Structure Dependency Table|001' 6"
	::= { dmtfStructureDependencyTraps 6 }

dmtfStructureDependencyContainerSecurityBreach NOTIFICATION-TYPE
	OBJECTS {
		dmiEventDateTime,
		dmiCompId,
		dmiEventSeverity,
		dmiEventStateKey,
		dmiEventAssociatedGroup
,		dmtfStructureDependencyEvSys
,		dmtfStructureDependencyEvSub
		}
	STATUS current
	DESCRIPTION "The system chassis has been opened has 
		    been opened without poper authorization."
	REFERENCE "'DMTF|Structure Dependency Table|001' 7"
	::= { dmtfStructureDependencyTraps 7 }

dmtfStructureDependencyInitializationFailure NOTIFICATION-TYPE
	OBJECTS {
		dmiEventDateTime,
		dmiCompId,
		dmiEventSeverity,
		dmiEventStateKey,
		dmiEventAssociatedGroup
,		dmtfStructureDependencyEvSys
,		dmtfStructureDependencyEvSub
		}
	STATUS current
	DESCRIPTION "An element of the system failed to initialize
		    properly during system startup."
	REFERENCE "'DMTF|Structure Dependency Table|001' 8"
	::= { dmtfStructureDependencyTraps 8 }

dmtfStructureDependencyConfigurationError NOTIFICATION-TYPE
	OBJECTS {
		dmiEventDateTime,
		dmiCompId,
		dmiEventSeverity,
		dmiEventStateKey,
		dmiEventAssociatedGroup
,		dmtfStructureDependencyEvSys
,		dmtfStructureDependencyEvSub
		}
	STATUS current
	DESCRIPTION "An element of the system is not properly configured"
	REFERENCE "'DMTF|Structure Dependency Table|001' 9"
	::= { dmtfStructureDependencyTraps 9 }

dmtfSystemCacheTraps OBJECT IDENTIFIER ::= { dmtfSystemCacheTable 0 }

dmtfSystemCacheEvSys OBJECT-TYPE
	SYNTAX		INTEGER {
		other(0),
		unknown(1)
	}
	MAX-ACCESS	not-accessible
	STATUS		current
	DESCRIPTION	"The major functional aspect of the product causing the fault."
	::= {dmtfSystemCacheTable 6 }

dmtfSystemCacheEvSub OBJECT-TYPE
	SYNTAX		INTEGER {
		other(0),
		unknown(1)
	}
	MAX-ACCESS	not-accessible
	STATUS		current
	DESCRIPTION	"The minor functional aspect of the product causing the fault."
	::= {dmtfSystemCacheTable 7 }

dmtfSystemCacheMemoryError NOTIFICATION-TYPE
	OBJECTS {
		dmiEventDateTime,
		dmiCompId,
		dmiEventSeverity,
		dmiEventStateKey,
		dmiEventAssociatedGroup
,		dmtfSystemCacheEvSys
,		dmtfSystemCacheEvSub
		}
	STATUS current
	DESCRIPTION "A memory module in the system cache failed."
	REFERENCE "'DMTF|System Cache|001' 1"
	::= { dmtfSystemCacheTraps 1 }

dmtfSystemCacheInitializationFailure NOTIFICATION-TYPE
	OBJECTS {
		dmiEventDateTime,
		dmiCompId,
		dmiEventSeverity,
		dmiEventStateKey,
		dmiEventAssociatedGroup
,		dmtfSystemCacheEvSys
,		dmtfSystemCacheEvSub
		}
	STATUS current
	DESCRIPTION "The System Cache failed to initialize properly
		     during system startup."
	REFERENCE "'DMTF|System Cache|001' 2"
	::= { dmtfSystemCacheTraps 2 }

dmtfSystemHardwareSecurityTraps OBJECT IDENTIFIER ::= { dmtfSystemHardwareSecurityTable 0 }

dmtfSystemHardwareSecurityEvSys OBJECT-TYPE
	SYNTAX		INTEGER {
		other(0),
		unknown(1)
	}
	MAX-ACCESS	not-accessible
	STATUS		current
	DESCRIPTION	"The major functional aspect of the product causing the fault."
	::= {dmtfSystemHardwareSecurityTable 6 }

dmtfSystemHardwareSecurityEvSub OBJECT-TYPE
	SYNTAX		INTEGER {
		other(0),
		unknown(1)
	}
	MAX-ACCESS	not-accessible
	STATUS		current
	DESCRIPTION	"The minor functional aspect of the product causing the fault."
	::= {dmtfSystemHardwareSecurityTable 7 }

dmtfSystemHardwareSecuritySettingsChange NOTIFICATION-TYPE
	OBJECTS {
		dmiEventDateTime,
		dmiCompId,
		dmiEventSeverity,
		dmiEventStateKey,
		dmiEventAssociatedGroup
,		dmtfSystemHardwareSecurityEvSys
,		dmtfSystemHardwareSecurityEvSub
		}
	STATUS current
	DESCRIPTION "The security settings for the system hardware have changed."
	REFERENCE "'DMTF|System Hardware Security|001' 1"
	::= { dmtfSystemHardwareSecurityTraps 1 }

dmtfSystemHardwareSecurityContainerSecurityBreach NOTIFICATION-TYPE
	OBJECTS {
		dmiEventDateTime,
		dmiCompId,
		dmiEventSeverity,
		dmiEventStateKey,
		dmiEventAssociatedGroup
,		dmtfSystemHardwareSecurityEvSys
,		dmtfSystemHardwareSecurityEvSub
		}
	STATUS current
	DESCRIPTION "A secruity breach of the system hardware has occured.
	             A secured component of the physical system has been
		     accessed without proper authorization."
	REFERENCE "'DMTF|System Hardware Security|001' 2"
	::= { dmtfSystemHardwareSecurityTraps 2 }

dmtfSystemResetTraps OBJECT IDENTIFIER ::= { dmtfSystemResetTable 0 }

dmtfSystemResetEvSys OBJECT-TYPE
	SYNTAX		INTEGER {
		other(0),
		unknown(1)
	}
	MAX-ACCESS	not-accessible
	STATUS		current
	DESCRIPTION	"The major functional aspect of the product causing the fault."
	::= {dmtfSystemResetTable 6 }

dmtfSystemResetEvSub OBJECT-TYPE
	SYNTAX		INTEGER {
		other(0),
		unknown(1)
	}
	MAX-ACCESS	not-accessible
	STATUS		current
	DESCRIPTION	"The minor functional aspect of the product causing the fault."
	::= {dmtfSystemResetTable 7 }

dmtfSystemResetSystemUp NOTIFICATION-TYPE
	OBJECTS {
		dmiEventDateTime,
		dmiCompId,
		dmiEventSeverity,
		dmiEventStateKey,
		dmiEventAssociatedGroup
,		dmtfSystemResetEvSys
,		dmtfSystemResetEvSub
		}
	STATUS current
	DESCRIPTION "The system is up and running after having 
		     automatically re-booted due to some (abnormal)
		     reset condition."
	REFERENCE "'DMTF|System Reset|001' 1"
	::= { dmtfSystemResetTraps 1 }

dmtfTemperatureProbeTraps OBJECT IDENTIFIER ::= { dmtfTemperatureProbeTable 0 }

dmtfTemperatureProbeEvSys OBJECT-TYPE
	SYNTAX		INTEGER {
		other(0),
		unknown(1)
	}
	MAX-ACCESS	not-accessible
	STATUS		current
	DESCRIPTION	"The major functional aspect of the product causing the fault."
	::= {dmtfTemperatureProbeTable 6 }

dmtfTemperatureProbeEvSub OBJECT-TYPE
	SYNTAX		INTEGER {
		other(0),
		unknown(1)
	}
	MAX-ACCESS	not-accessible
	STATUS		current
	DESCRIPTION	"The minor functional aspect of the product causing the fault."
	::= {dmtfTemperatureProbeTable 7 }

dmtfTemperatureProbeCoolingDeviceStatusChange NOTIFICATION-TYPE
	OBJECTS {
		dmiEventDateTime,
		dmiCompId,
		dmiEventSeverity,
		dmiEventStateKey,
		dmiEventAssociatedGroup
,		dmtfTemperatureProbeEvSys
,		dmtfTemperatureProbeEvSub
		}
	STATUS current
	DESCRIPTION "A temperature probe on the system has detected
		    an abnormal change in temperature of the system
		    or a system component."
	REFERENCE "'DMTF|Temperature Probe|001' 1"
	::= { dmtfTemperatureProbeTraps 1 }

dmtfUPSBatteryTraps OBJECT IDENTIFIER ::= { dmtfUPSBatteryTable 0 }

dmtfUPSBatteryEvSys OBJECT-TYPE
	SYNTAX		INTEGER {
		other(0),
		unknown(1)
	}
	MAX-ACCESS	not-accessible
	STATUS		current
	DESCRIPTION	"The major functional aspect of the product causing the fault."
	::= {dmtfUPSBatteryTable 6 }

dmtfUPSBatteryEvSub OBJECT-TYPE
	SYNTAX		INTEGER {
		other(0),
		unknown(1)
	}
	MAX-ACCESS	not-accessible
	STATUS		current
	DESCRIPTION	"The minor functional aspect of the product causing the fault."
	::= {dmtfUPSBatteryTable 7 }

dmtfUPSBatteryStatusChange NOTIFICATION-TYPE
	OBJECTS {
		dmiEventDateTime,
		dmiCompId,
		dmiEventSeverity,
		dmiEventStateKey,
		dmiEventAssociatedGroup
,		dmtfUPSBatteryEvSys
,		dmtfUPSBatteryEvSub
		}
	STATUS current
	DESCRIPTION "The UPS Battery has changed status according
		    to the event severity indicated."
	REFERENCE "'DMTF|UPS Battery|001' 1"
	::= { dmtfUPSBatteryTraps 1 }

dmtfUPSBatteryUtilityPowerLostSystemOnBattery NOTIFICATION-TYPE
	OBJECTS {
		dmiEventDateTime,
		dmiCompId,
		dmiEventSeverity,
		dmiEventStateKey,
		dmiEventAssociatedGroup
,		dmtfUPSBatteryEvSys
,		dmtfUPSBatteryEvSub
		}
	STATUS current
	DESCRIPTION "The system has lost primary power and is
		    now running on UPS Battery."
	REFERENCE "'DMTF|UPS Battery|001' 2"
	::= { dmtfUPSBatteryTraps 2 }

dmtfUPSBatteryUtilityPowerUpSystemOffBattery NOTIFICATION-TYPE
	OBJECTS {
		dmiEventDateTime,
		dmiCompId,
		dmiEventSeverity,
		dmiEventStateKey,
		dmiEventAssociatedGroup
,		dmtfUPSBatteryEvSys
,		dmtfUPSBatteryEvSub
		}
	STATUS current
	DESCRIPTION "Primary power to the system has been restored.
                    The UPS battery is no longer in use."
	REFERENCE "'DMTF|UPS Battery|001' 3"
	::= { dmtfUPSBatteryTraps 3 }

dmtfVoltageProbeTraps OBJECT IDENTIFIER ::= { dmtfVoltageProbeTable 0 }

dmtfVoltageProbeEvSys OBJECT-TYPE
	SYNTAX		INTEGER {
		other(0),
		unknown(1)
	}
	MAX-ACCESS	not-accessible
	STATUS		current
	DESCRIPTION	"The major functional aspect of the product causing the fault."
	::= {dmtfVoltageProbeTable 6 }

dmtfVoltageProbeEvSub OBJECT-TYPE
	SYNTAX		INTEGER {
		other(0),
		unknown(1)
	}
	MAX-ACCESS	not-accessible
	STATUS		current
	DESCRIPTION	"The minor functional aspect of the product causing the fault."
	::= {dmtfVoltageProbeTable 7 }

dmtfVoltageProbePowerSupplyStatusChange NOTIFICATION-TYPE
	OBJECTS {
		dmiEventDateTime,
		dmiCompId,
		dmiEventSeverity,
		dmiEventStateKey,
		dmiEventAssociatedGroup
,		dmtfVoltageProbeEvSys
,		dmtfVoltageProbeEvSub
		}
	STATUS current
	DESCRIPTION "A voltage probe on the system has detected an
		     abnormal change in voltage level from one of
		     the system's power supplies to the monitored
		     component."
	REFERENCE "'DMTF|Voltage Probe|001' 1"
	::= { dmtfVoltageProbeTraps 1 }

END
