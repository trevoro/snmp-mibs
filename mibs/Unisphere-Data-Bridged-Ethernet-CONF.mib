-- *****************************************************************************
-- Unisphere-Data-Bridged-Ethernet-CONF
--
-- SNMP Agent Capabilities definitions for the Bridged Ethernet MIB.
--
-- Copyright (c) 2001 Unisphere Networks, Inc.  All rights reserved.
-- *****************************************************************************

Unisphere-Data-Bridged-Ethernet-CONF DEFINITIONS ::= BEGIN

IMPORTS
    MODULE-IDENTITY
        FROM SNMPv2-SMI
    AGENT-CAPABILITIES
        FROM SNMPv2-CONF
    usDataAgents
        FROM Unisphere-Data-Agents
    usdBridgedEthernetGroup2
        FROM Unisphere-Data-BRIDGE-ETHERNET-MIB;

usdBridgedEthernetAgent MODULE-IDENTITY
    LAST-UPDATED "200103301645Z"  -- 30-Mar-01 11:45 AM EST
    ORGANIZATION "Unisphere Networks, Inc."
    CONTACT-INFO
        "       Unisphere Networks, Inc.
        Postal: 10 Technology Park Drive
                Westford, MA  01886
                USA
        Tel:    +1 978 589 5800
        E-mail: mib@UnisphereNetworks.com"
    DESCRIPTION
        "The agent capabilities definitions for the Bridged Ethernet component
        of the SNMP agent in the Unisphere Routing Switch family of products."
    -- Revision History
    REVISION    "200103301645Z"  -- 30-Mar-01 11:45 AM EST  - RX 3.2
    DESCRIPTION
        "The initial release of this management information module."
    ::= { usDataAgents 5 }

usdBridgedEthernetAgentV1 AGENT-CAPABILITIES
    PRODUCT-RELEASE
        "Version 1 of the Bridged Ethernet component of the Unisphere Routing
        Switch SNMP agent.  This version of the Bridged Ethernet component is
        supported in the Unisphere RX 2.0 and subsequent system releases."
    STATUS      current
    DESCRIPTION
        "The MIB supported by the SNMP agent for the Bridged Ethernet
        application in the Unisphere Routing Switch."

    SUPPORTS        Unisphere-Data-BRIDGE-ETHERNET-MIB
        INCLUDES  { usdBridgedEthernetGroup2 }

    ::= { usdBridgedEthernetAgent 1 }

END
