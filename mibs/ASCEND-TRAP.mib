--			Ascend Enterprise Traps
--
--			Ascend Communications, Inc
--			1275 Harbor Bay Pkwy
--			Alameda, CA 94502
--			+1 510 769 6001
--			info@ascend.com
--
--		Copyright (c) 1993, 1994 Ascend Communications, Inc.
--		All rights reserved.
--
-- SCCS ID:	$Id: ascend.trp,v 29.25.6.10 1999/11/09 00:47:20 jjablons Exp $
--
-- 01 Dec 93:	Initial release
-- 18 Aug 93:	Add new trap types
-- 18 May 95:	Add eventTableOverwrite.
-- 15 Apr 96:   kh Add radiusServerChange.
-- 24 Jul 96:   kh Add IpAddress to maxTelnetAttempts
-- 01 Aug 97:   rm Add power supply traps.
-- 04 Aug 97:   rm Add multiShelfState trap.
-- 04 Sep 98:   rm Add configChange trap.
-- 16 Dec 98:	kn Add suspectAccessResource trap.
-- 12 Mar 99:   ds Add watchdog trap.
-- 25 Jun 99:   Add Ip Addr to consoleStateChange trap.
-- 31 Jul 99:   am Add controllerSwitchover trap.
-- 01 Aug 99:   Add traps:callLogServChange,voipGkChange,wanLineStateChange
-- 22 Aug 99:   Add callLogDroppedPkt trap.
-- 15 Sep 99:   Added megacoLinkStatusTrap.
-- 19 Oct 99:   of Add Line Interface Module sparing trap.
-- 19 Oct 99:   of Add Trunk Port sparing trap.


ASCEND-TRAP DEFINITIONS ::= BEGIN

    IMPORTS
	ifIndex
	    FROM IF-MIB
	sysName
	    FROM RFC1213-MIB
	ascend, sysLastRestartReason
	    FROM ASCEND-MIB
	consoleIndex
	    FROM ASCEND-MIB
	slotIndex, slotStatus,
	cntrReduSwitchLastTime,
	cntrReduSwitchReason,
	cntrReduSwitchIndex,
	cntrReduCurrentIndex,
        cntrReduAvailLastTime,
        cntrReduAvailSlotIndex,
        cntrReduAvailPrevState,
        cntrReduAvailCurrState
	    FROM ASCEND-CHASSIS-MIB
        radAuthServerIndex, radAuthHostIPAddress
            FROM ASCEND-RADIUS-MIB
--      radAcctServerIndex, radAcctHostIPAddress
--          FROM ASCEND-RADIUS-MIB
        heartBeatMulticastGroupAddress, heartBeatSourceAddress,
        heartBeatSlotTimeInterval, heartBeatSlotCount, heartBeatPacketCount
	    FROM ASCEND-MCAST-MIB
        suspectLanModemSlotIndex, suspectLanModemPortIndex,
        suspectLanModemUsedCount, suspectLanModemBadCount,
        suspectLanModemLast32
	    FROM ASCEND-LANMODEM-MIB
        ssnStatusUserIPAddress
	    FROM ASCEND-SESSION-MIB
        powerSupplyState, powerSupplyOperationalState
            FROM ASCEND-POWER-SUPPLY-MIB
        multiShelfState
            FROM ASCEND-MULTI-SHELF-MIB
	atmpHNProfileName, atmpLastErrorGenerated, atmpAgentSentErrorTo,
        atmpLastErrorRecv, atmpAgentRecvErrorFrom
            FROM ASCEND-ATMP-MIB
        resourceSlotIndex, resourcePortIndex,
        resourceUsedCounts, resourceBadCounts,
        resourceLast32
	    FROM ASCEND-RESOURCES-MIB
	watchdogIndex,
	watchdogName,
	watchdogState
	    FROM ASCEND-WATCHDOG-MIB
        callLoggingDroppedPacketCount
            FROM ASCEND-CALL-LOGGING-MIB
        voipCfgGkIndex,
        voipCfgGkIpAddress
            FROM ASCEND-VOIP-MIB
        callLoggingServerIndex,
        callLoggingServerIPAddress
            FROM ASCEND-CALL-LOGGING-MIB
        wanLineIfIndex,
        wanLineUsage
            FROM ASCEND-ADVANCED-AGENT-MIB
	sysUpTime
	    FROM RFC1213-MIB
        sysConfigChange
            FROM ASCEND-MIB
	TRAP-TYPE
	    FROM RFC-1215
	fatalLogIndex, fatalLogReason, sysAbsoluteCurrentTime
	    FROM ASCEND-MIB
	mgLinkName, mgOperStatus
	    FROM ASCEND-MGSTAT-MIB
        sparingSlotPrimaryIndex,sparingSlotSparingIndex,
        sparingSlotStatus,sparingSlotLastStatusChange,
        sparingSlotLastChangeReason,
        sparingIfPrimaryIndex,sparingIfSparingIndex,
        sparingIfStatus,sparingIfLastStatusChange,
        sparingIfLastChangeReason
	    FROM ASCEND-SPARING-MIB;

	-- Ascend generates traps for important events.  The events are
	-- classified to allow traps to be enabled by class.  The trap
	-- classifications are:
	--
	--	error events
	--	port state change events
	--	security events
	--
	-- Traps may only be enabled from the user interface.
	-- Each trap contains an interface number to identify the trapping
	-- entity.  The slotIfTable can be used to translate the interface
	-- to a slot/item.

	-- error events
	--
	-- The error events reported are those defined in RFC 1215.  They
	-- are:
	--	coldStart
	--	warmStart
	--	linkDown
	--	linkUp

	-- port state change events
	--
	-- the port state change events are generated when a port changes
	-- state which is often a direct result of a call state change.

    portInactive	TRAP-TYPE
	ENTERPRISE	ascend
	VARIABLES	{ ifIndex }
	DESCRIPTION	"The host port associated with the indicated ifIndex
			 has changed to the inactive state."
	::= 0

    portDualDelay	TRAP-TYPE
	ENTERPRISE	ascend
	VARIABLES	{ ifIndex }
	DESCRIPTION	"The host port associated with the indicated ifIndex
			is delaying the dialing of a second call to avoid
			overloading devices that can not handle two calls in
			close succession."
	::= 1

    portWaitSerial	TRAP-TYPE
	ENTERPRISE	ascend
	VARIABLES	{ ifIndex }
	DESCRIPTION	"The host port associated with the indicated ifIndex
			has detected DTR when in V.25bis mode and is waiting
			for an HDLC controller to come on line.  CTS is off."
	::= 2

    portHaveSerial	TRAP-TYPE
	ENTERPRISE	ascend
	VARIABLES	{ ifIndex }
	DESCRIPTION	"The host port associated with the indicated ifIndex
			is ready to accept V.25bis commands.  CTS is on."
	::= 3

    portRinging		TRAP-TYPE
	ENTERPRISE	ascend
	VARIABLES	{ ifIndex }
	DESCRIPTION	"The host port associated with the indicated ifIndex
			is has been notified of an incoming call."
	::= 4

    portCollectDigits	TRAP-TYPE
	ENTERPRISE	ascend
	VARIABLES	{ ifIndex }
	DESCRIPTION	"The host port associated with the indicated ifIndex
			is collecting digits from the RS-366 dialing
			interface."
	::= 5

    portWaiting		TRAP-TYPE
	ENTERPRISE	ascend
	VARIABLES	{ ifIndex }
	DESCRIPTION	"The host port associated with the indicated ifIndex
			is waiting for connect notification from the network
			after dialing or answer notification has been issued."
	::= 6

    portConnected	TRAP-TYPE
	ENTERPRISE	ascend
	VARIABLES	{ ifIndex }
	DESCRIPTION	"The host port associated with the indicated ifIndex
			has connected to the far end, but end-to-end data
			flow has not yet been enabled."
	::= 7

    portCarrier	TRAP-TYPE
	ENTERPRISE	ascend
	VARIABLES	{ ifIndex }
	DESCRIPTION	"The host port associated with the indicated ifIndex
			has connected to the far end and has end-to-end data
			flow."
	::= 8

    portLoopback	TRAP-TYPE
	ENTERPRISE	ascend
	VARIABLES	{ ifIndex }
	DESCRIPTION	"The host port associated with the indicated ifIndex
			has been placed in local loopback mode."
	::= 9

    portAcrPending	TRAP-TYPE
	ENTERPRISE	ascend
	VARIABLES	{ ifIndex }
	DESCRIPTION	"The host port associated with the indicated ifIndex
			has set ACR on the RS-366 dialing interface and is
			waiting for the host device to detect the transition."
	::= 10

    portDteNotReady	TRAP-TYPE
	ENTERPRISE	ascend
	VARIABLES	{ ifIndex }
	DESCRIPTION	"The host port associated with the indicated ifIndex
			is waiting for the DTE to signal a ready condition
			when performing X.21 dialing."
	::= 11

	-- Security events are used to notify users of security problems
	-- and track access to the unit from the console.  The mib-II event
	-- 
	-- 	authenticationError
	--
	-- is a security event.  The other security events are Ascend
	-- specific.

    consoleStateChange	TRAP-TYPE
	ENTERPRISE	ascend
        VARIABLES       { consoleIndex , ssnStatusUserIPAddress }
	DESCRIPTION	"The console associated with the passed console
			index has changed state.  The console entry
			can be read to see what its current state is."
	::= 12

    portUseExceeded	TRAP-TYPE
	ENTERPRISE	ascend
	VARIABLES	{ ifIndex }
	DESCRIPTION	"The port associated with the indicated ifIndex has
			exceeded the number of DS0 minutes allocated to it."
	::= 13


    systemUseExceeded	TRAP-TYPE
	ENTERPRISE	ascend
	DESCRIPTION	"The system DS0 usage has been exceeded."
	::= 14

--  maxTelnetAttempts trap returns the objectID of the session entry and the
--  associated IP address 

    maxTelnetAttempts	TRAP-TYPE
	ENTERPRISE	ascend
        VARIABLES       { ssnStatusUserIPAddress }
	DESCRIPTION	"The maximum number of login attempts for a  telnet
                         session has been exceeded."
	::= 15	


-- Following eventTableOverwrite trap is an error event.

    eventTableOverwrite	TRAP-TYPE
	ENTERPRISE	ascend
	DESCRIPTION	"A new event has overwritten an unread event.
                         This trap is sent only for systems which
			 support Ascend's accounting MIB.
			 Once sent, additional overwrites will not
			 cause another trap to be sent until at least
			 1 table's worth of new events have occured."
	::= 16	


--      ::= 17 used for debugging - trap_lcdterm_zombie


-- radiusServer change trap returns the objectID and IP address of the new
-- current server. 

    radiusServerChange	TRAP-TYPE
	ENTERPRISE	ascend
        VARIABLES       { radAuthServerIndex, radAuthHostIPAddress }
--      OR
--      VARIABLES       { radAcctServerIndex, radAcctHostIPAddress }
	DESCRIPTION	"The current Radius server has been changed."
	::= 18	

-- multicast heartbeat monitor trap is set when fails to receive heartbeats 

    multicastHeartBeatMonitor	TRAP-TYPE
	ENTERPRISE	ascend
        VARIABLES       { heartBeatMulticastGroupAddress,
  			heartBeatSourceAddress, heartBeatSlotTimeInterval,
  			heartBeatSlotCount, heartBeatPacketCount  }
	DESCRIPTION	"This trap is sent when heartBeat fails to receive
			configured number of heartBeat packets from
			heartBeat servers"
	::= 19	

-- lan modem moved to the suspect list

    lanModemMovedToSuspectList	TRAP-TYPE
	ENTERPRISE	ascend
        VARIABLES       { suspectLanModemSlotIndex, suspectLanModemPortIndex,
                          suspectLanModemUsedCount, suspectLanModemBadCount,
                          suspectLanModemLast32  }
	DESCRIPTION	"This trap is sent to all the managers in the
                        alarm group when a lan modem (digital modem) is moved
                        to the suspect list.
                        Refer to the lanModemGroup.suspectLanModemTable
                        description."
	::= 20	

-- Didnot receive ans/sub (dirdo) addresses from Radius 

    dirdoListFailure  TRAP-TYPE
        ENTERPRISE      ascend
        VARIABLES       { sysName }
        DESCRIPTION     "This trap is sent to all the managers in the
                        alarm group when a T_ONLINE call comes in and 
                        no answer/subaddresses have been received." 
        ::= 21  

-- slot state change

    sysSlotStateChange	TRAP-TYPE
	ENTERPRISE	ascend
        VARIABLES       { slotIndex, slotStatus }
	DESCRIPTION	"This trap is sent to all the managers in the
			slot group when a slot card's SLOT-STATE profile
			is created due to slot insertion, or the current-state
			transitions into oper-state-down, oper-state-up,
			oper-state-dump, or oper-state-none states.

			Refer to the slotTable.slotIndex and
			slotTable.slotStatus descriptions."
	::= 22	


-- added in TAOS 8.0 for Stinger

    powerSupplyStateChange	TRAP-TYPE
	ENTERPRISE	ascend
        VARIABLES       { powerSupplyState }
	DESCRIPTION	"This trap is sent to all the managers in the
			alarm group when a power supply module is
                        added or removed."
	::= 23	

-- added in TAOS 8.0 for Stinger

    powerSupplyOperationalStateChange	TRAP-TYPE
	ENTERPRISE	ascend
        VARIABLES       { powerSupplyOperationalState }
	DESCRIPTION	"This trap is sent to all the managers in the
			alarm group when a power supply module incurs
                        failure(s)."
	::= 24	

    multiShelfStateChange	TRAP-TYPE
	ENTERPRISE	ascend
        VARIABLES       { multiShelfState }
	DESCRIPTION	"This trap is sent to all the managers in the
			slot group when a master shelf detects up/down
                        state changes of the peer shelf in a multi-shelf
                        configuration."
	::= 25	

    sysLastRestartReasonTrap	TRAP-TYPE
	ENTERPRISE	ascend
        VARIABLES       { sysLastRestartReason, fatalLogIndex, 
                          sysAbsoluteCurrentTime }
	DESCRIPTION	"This trap is sent to all managers having the
                        alarm condition enabled if the sysLastRestartReason
                        is not unknown (value of 0)."
	::= 26

    atmpMaxTunnelExceeded        TRAP-TYPE
        ENTERPRISE      ascend
        VARIABLES       { atmpHNProfileName }
        DESCRIPTION
                        "This is generated when the number of tunnels to a Home
                        Network exceeds the maximum tunnels.  atmpHAIpAddress is
                        the Home Agent and atmpHNProfileName is the name of the
                        connection profile."
        ::= 27

    atmpAgentErrorSentTrap  TRAP-TYPE
        ENTERPRISE      ascend
        VARIABLES       { atmpLastErrorGenerated, atmpAgentSentErrorTo }
        DESCRIPTION
                        "This trap indicates errors at the Agent level or
                        with Tunnel creation."
        ::= 28

    atmpAgentErrorRecvTrap  TRAP-TYPE
        ENTERPRISE      ascend
        VARIABLES       { atmpLastErrorRecv, atmpAgentRecvErrorFrom }
        DESCRIPTION
                        "This trap indicates errors received from a peer
                        agent."
        ::= 29

    sysConfigChangeTrap  TRAP-TYPE
        ENTERPRISE      ascend
        VARIABLES       { sysConfigChange }
        DESCRIPTION  
                        "This trap indicates a configuration change has occurred."
        ::= 30

    sdtnPrimaryListEmptyTrap  TRAP-TYPE
	ENTERPRISE      ascend
	DESCRIPTION     "This trap indicates that the Transaction Server 
			 Primary list has become empty."
	::= 31

    sdtnSecondaryListEmptyTrap  TRAP-TYPE
	ENTERPRISE      ascend
	DESCRIPTION     "This trap indicates that the Transaction Server 
			 Secondary list has become empty."
	::= 32

    systemClockDrifted     TRAP-TYPE
        ENTERPRISE      ascend
        DESCRIPTION
                        "This trap indicates system clock has drifted but
                        could not be corrected.
                        This trap sent to managers when the alarm
                        and clock drifted params are set to YES in a
                        trap profile. If the clock drifting problem
                        persists, the trap will only be sent every
                        24 hours."
        ::= 33

-- access terminating resource become suspected

   suspectAccessResource       TRAP-TYPE
	ENTERPRISE	ascend
        VARIABLES       { resourceSlotIndex, resourcePortIndex,
                          resourceUsedCounts, resourceBadCounts,
                          resourceLast32  }
	DESCRIPTION	"The access resource suspected trap is sent to  
			all the managers in the alarm group when a 
			terminating resource such as modem become suspect. 
			The suspected resource(s) are not assigned to
			terminate calls until the resource in the available
			pool exhausted."
	::= 34	

-- added in TAOS 8.0 for Stinger

     watchdogWarningTrap TRAP-TYPE
	ENTERPRISE	ascend
	VARIABLES	{ watchdogIndex, watchdogName, watchdogState, sysAbsoluteCurrentTime }
	DESCRIPTION	"This trap indicates that a watchdog warning has
                         occurred."
	::= 35

     slotCardResetTrap	TRAP-TYPE
	ENTERPRISE	ascend
        VARIABLES       { fatalLogIndex, fatalLogReason,
                          sysAbsoluteCurrentTime, slotIndex }
	DESCRIPTION	"This trap is sent to all managers having the
                         alarm condition enabled"
	::= 36

-- added in TAOS 8.0 for Stinger

     controllerSwitchoverTrap   TRAP-TYPE
	ENTERPRISE      ascend
	VARIABLES       { sysAbsoluteCurrentTime, cntrReduSwitchReason,
			  cntrReduSwitchIndex, cntrReduCurrentIndex } 
	DESCRIPTION     "System controller changed. The primary system
			 controller changed from cntrReduSwitchIndex
			 to cntrReduCurrentIndex." 
	::= 37

     callLogServChange	TRAP-TYPE
	ENTERPRISE	ascend
        VARIABLES       { callLoggingServerIndex, 
                          callLoggingServerIPAddress,
                          sysAbsoluteCurrentTime }
	DESCRIPTION	"This trap is sent to indicate that the call 
                         logging server has changed."
	::= 38

     voipGkChange	TRAP-TYPE
	ENTERPRISE	ascend
        VARIABLES       { voipCfgGkIndex,
                          voipCfgGkIpAddress,
                          sysAbsoluteCurrentTime }
	DESCRIPTION	"This trap is sent when there is a change in the 
                         gatekeeper which is registered with the gateway
                         in a VOIP configuration."
	::= 39

     wanLineStateChange	TRAP-TYPE
	ENTERPRISE	ascend
        VARIABLES       { wanLineIfIndex,
                          wanLineUsage,
                          sysAbsoluteCurrentTime }
	DESCRIPTION	"This trap is sent to indicate a change in the state
                         of a T1/E1 line : trunk, quiesced or disabled"
	::= 40

    callLogDroppedPkt    TRAP-TYPE
        ENTERPRISE       ascend
        VARIABLES        { callLoggingDroppedPacketCount }
        DESCRIPTION      "This trap indicates that a call logging packet was
                          dropped. A count value of 1 indicates the start
                          of dropping of call logging packets. A count value
                          of 0 indicates that all is well again."
	::= 41

-- added in TAOS 8.0 for TNT and APX
    megacoLinkStatusTrap TRAP-TYPE
	ENTERPRISE	ascend
	VARIABLES	{ mgLinkName, mgOperStatus }
	DESCRIPTION	"This trap indicates that operational status
			of a media gateway control link has changed."
        ::= 42

-- added in TAOS 8.0 for Stinger
    sparingSlotStatusChange	TRAP-TYPE
	ENTERPRISE	ascend
        VARIABLES       { sparingSlotPrimaryIndex,
                          sparingSlotSparingIndex,
                          sparingSlotStatus,
                          sparingSlotLastStatusChange,
                          sparingSlotLastChangeReason }
	DESCRIPTION	"This trap indicates that the slot sparing state
			 has changed at sparingSlotLastStatusChange to
                         sparingSlotStatus.
                         The slot affected is sparingSlotPrimaryIndex."
	::= 43

-- added in TAOS 8.0 for Stinger
    sparingIfStatusChange	TRAP-TYPE
	ENTERPRISE	ascend
        VARIABLES       { sparingIfPrimaryIndex,
                          sparingIfSparingIndex,
                          sparingIfStatus,
                          sparingIfLastStatusChange,
                          sparingIfLastChangeReason }
	DESCRIPTION	"This trap indicates that the interface sparing state
			 has changed at sparingIfLastStatusChange to
                         sparingIfStatus.
                         The slot affected is sparingIfPrimaryIndex."
	::= 44


     cntrReduAvailTrap   TRAP-TYPE
	ENTERPRISE       ascend
	VARIABLES        { cntrReduAvailLastTime, 
                           cntrReduAvailSlotIndex,
                           cntrReduAvailPrevState,
                           cntrReduAvailCurrState
                         } 
	DESCRIPTION      "The redundancy availability for the controller in slot
                          cntrReduAvailSlotIndex changed from cntrReduAvailPrevState
                          to cntrReduAvailCurrState at cntrReduAvailLastTime."
	::= 45

END
