Wellfleet-MPLS-LDP-MIB DEFINITIONS ::= BEGIN

IMPORTS

  OBJECT-TYPE
     FROM RFC-1212
  wfMplsLdpGroup
    FROM Wellfleet-COMMON-MIB
  IpAddress
    FROM RFC1155-SMI;




    wfMplsLdpSessCfgTable OBJECT-TYPE
    	SYNTAX SEQUENCE OF WfMplsLdpSessCfgEntry
    	ACCESS not-accessible
    	STATUS mandatory
     	DESCRIPTION
        	"MPLS LDP session table -
         	This tabulates the LDP session within an mpls protocol group.
         	All sessions are indexed according to the physical slot and
         	the associated interface circuit number and session index.
         	There can be more LDP sessions per L2 MPLS interface."
    	::= { wfMplsLdpGroup 1 }

wfMplsLdpSessCfgEntry OBJECT-TYPE
    SYNTAX WfMplsLdpSessCfgEntry
    ACCESS not-accessible
    STATUS mandatory
    DESCRIPTION
        "MPLS LDP session entries."
    INDEX { wfMplsLdpSessCfgSlot,
	    wfMplsLdpSessCfgCircuit,
            wfMplsLdpSessCfgIndex }
    ::= { wfMplsLdpSessCfgTable 1 }

WfMplsLdpSessCfgEntry ::= SEQUENCE {
    wfMplsLdpSessCfgCreate
            INTEGER,
    wfMplsLdpSessCfgEnable
            INTEGER,
    wfMplsLdpSessCfgSlot
            INTEGER,
    wfMplsLdpSessCfgIndex
            INTEGER,
    wfMplsLdpSessCfgCircuit
            INTEGER,
    wfMplsLdpSessCfgLocalIpAddress
            IpAddress,
    wfMplsLdpSessCfgLocalTcpPort
            INTEGER,
    wfMplsLdpSessCfgRemoteIpAddress
            IpAddress,
    wfMplsLdpSessCfgRemoteTcpPort
            INTEGER,
    wfMplsLdpSessCfgRoutesConfigMode
            INTEGER,
    wfMplsLdpSessCfgHoldTime
            INTEGER,
    wfMplsLdpSessCfgProto
	    INTEGER,
    wfMplsLdpSessCfgAggregation
	    INTEGER,
    wfMplsLdpSessCfgDebugLevel
            INTEGER,
    wfMplsLdpSessCfgReqBindRetryTime
            INTEGER,
    wfMplsLdpSessCfgReqBindRetries
            INTEGER
}


wfMplsLdpSessCfgCreate OBJECT-TYPE
    SYNTAX  INTEGER {
        created(1),
        deleted(2)
    }
    ACCESS read-write
    STATUS mandatory
    DESCRIPTION
        "Create/Delete parameter. Default is created. Users modify
         this object in order to create/delete MPLS LDP sessions"
    DEFVAL { created }
    ::= { wfMplsLdpSessCfgEntry 1 }

wfMplsLdpSessCfgEnable OBJECT-TYPE
    SYNTAX INTEGER {
        enabled(1),
        disabled(2)
    }
    ACCESS read-write
    STATUS mandatory
    DESCRIPTION
        "Enable/Disable parameter. Default is enabled."
    DEFVAL  { enabled }
    ::= { wfMplsLdpSessCfgEntry 2 }


wfMplsLdpSessCfgSlot OBJECT-TYPE
    SYNTAX INTEGER 
    ACCESS read-only
    STATUS mandatory
    DESCRIPTION
        "The slot number this LDP session is configured on."
    ::= { wfMplsLdpSessCfgEntry 3 }

wfMplsLdpSessCfgIndex OBJECT-TYPE
    SYNTAX INTEGER 
    ACCESS read-only
    STATUS mandatory
    DESCRIPTION
        "The Session index identifies this particular LDP session on an interface."
    ::= { wfMplsLdpSessCfgEntry 4 }

wfMplsLdpSessCfgCircuit OBJECT-TYPE
    SYNTAX INTEGER (1..1023)
    ACCESS read-only
    STATUS mandatory
    DESCRIPTION
        "The circuit number of the circuit to which the session belongs."
    ::= { wfMplsLdpSessCfgEntry 5 }


wfMplsLdpSessCfgLocalIpAddress OBJECT-TYPE
    SYNTAX IpAddress
    ACCESS read-write
    STATUS mandatory
    DESCRIPTION
        "The IP address of this MPLS device for the purpose of
         establishing the LDP peer to peer session."
    ::= { wfMplsLdpSessCfgEntry 6 }

wfMplsLdpSessCfgLocalTcpPort OBJECT-TYPE
    SYNTAX INTEGER(1..65535)
    ACCESS read-write
    STATUS mandatory
    DESCRIPTION
        "The TCP port address of this MPLS device for the purpose of
         establishing the LDP peer to peer session."
    DEFVAL { 8192 }
    ::= { wfMplsLdpSessCfgEntry 7 }

wfMplsLdpSessCfgRemoteIpAddress OBJECT-TYPE
    SYNTAX IpAddress
    ACCESS read-write
    STATUS mandatory
    DESCRIPTION 
        "The IP address of the remote MPLS device for the purpose of
         establishing the LDP peer to peer session."
    ::= { wfMplsLdpSessCfgEntry 8 }

wfMplsLdpSessCfgRemoteTcpPort OBJECT-TYPE
    SYNTAX INTEGER(1..65535)
    ACCESS read-write
    STATUS mandatory
    DESCRIPTION 
        "The TCP port of the remote MPLS device for the purpose of
         establishing the LDP peer to peer session."
    DEFVAL { 8192 }
    ::= { wfMplsLdpSessCfgEntry 9 }
    

wfMplsLdpSessCfgRoutesConfigMode  OBJECT-TYPE
        SYNTAX  INTEGER {
	        auto(1),
        	manual(2)
	}
        ACCESS      read-write
        STATUS      mandatory
        DESCRIPTION
                "Indicates whether network routes should be discovered by a 
	         routing protocol(auto) or should be Manually configured(manual), see 
		 wfMplsLdpCfgRouteTable." 
        DEFVAL  { auto }
        ::= { wfMplsLdpSessCfgEntry 10 }

wfMplsLdpSessCfgHoldTime  OBJECT-TYPE
        SYNTAX      INTEGER (1..240)
        ACCESS      read-write
        STATUS      mandatory
        DESCRIPTION
                "the Hold Time indicates the maximum time in seconds that may elapse 
	 	  between the receipt of successive PDUs from the LSR peer."
        DEFVAL  { 40 }
        ::= { wfMplsLdpSessCfgEntry 11 }

wfMplsLdpSessCfgProto OBJECT-TYPE
   SYNTAX  INTEGER {
         ospf(1),
	 rip(2),
	 hybridospf(3),
	 hybridrip(4)
                }
        ACCESS  read-write
        STATUS  mandatory
        DESCRIPTION
                "The routing protocols used by MPLS."
        DEFVAL { ospf }
        ::= { wfMplsLdpSessCfgEntry 12 }

wfMplsLdpSessCfgAggregation OBJECT-TYPE
    SYNTAX INTEGER {
        enabled(1),
        disabled(2)
    }
    ACCESS read-write
    STATUS mandatory
    DESCRIPTION
        "Enable/Disable aggregation. Default is disabled."
    DEFVAL  { disabled }
    ::= { wfMplsLdpSessCfgEntry 13 }


wfMplsLdpSessCfgDebugLevel OBJECT-TYPE
    SYNTAX INTEGER{
                  one(1),
                  two(2),
                  three(3),
                  debug(4)
                }
    ACCESS read-write
    STATUS mandatory
    DESCRIPTION
        "Debug Levels - This attribute is used to assign the 
         level of DEBUG message to be logged for each LDP session."
                        
    DEFVAL  { two }
    ::= { wfMplsLdpSessCfgEntry 14 }


wfMplsLdpSessCfgReqBindRetryTime  OBJECT-TYPE
        SYNTAX      INTEGER (1..240)
        ACCESS      read-write
        STATUS      mandatory
        DESCRIPTION
                "It indicates the maximum time in seconds that may elapse 
	 	  between two consecutive request bind in case of no reply."
        DEFVAL  { 40 }
        ::= { wfMplsLdpSessCfgEntry 15 }

wfMplsLdpSessCfgReqBindRetries  OBJECT-TYPE
        SYNTAX      INTEGER (1..240)
        ACCESS      read-write
        STATUS      mandatory
        DESCRIPTION
                "It indicates the number of retry times."
        DEFVAL  { 240 }
        ::= { wfMplsLdpSessCfgEntry 16 }



   wfMplsLdpSessActualTable OBJECT-TYPE
    	SYNTAX SEQUENCE OF WfMplsLdpSessActualEntry
    	ACCESS not-accessible
    	STATUS mandatory
     	DESCRIPTION
        	"MPLS LDP interface actual table -
		read-only table containing LDP peer status, and 
		actual LDP information."  
    	::= { wfMplsLdpGroup 2 }

wfMplsLdpSessActualEntry OBJECT-TYPE
    SYNTAX WfMplsLdpSessActualEntry
    ACCESS not-accessible
    STATUS mandatory
    DESCRIPTION
        "MPLS LDP interface entries."
    INDEX { wfMplsLdpSessActualCircuit,
            wfMplsLdpSessActualIndex }
    ::= { wfMplsLdpSessActualTable 1 }

WfMplsLdpSessActualEntry ::= SEQUENCE {
    wfMplsLdpSessActualIndex
            INTEGER,
    wfMplsLdpSessActualCircuit
            INTEGER,
    wfMplsLdpSessActualState
            INTEGER,
    wfMplsLdpSessActualPeerState
            INTEGER,
    wfMplsLdpSessActualLocalIpAddress
            IpAddress, 
    wfMplsLdpSessActualLocalTcpPort
           INTEGER,
    wfMplsLdpSessActualRemoteIpAddress
            IpAddress,
    wfMplsLdpSessActualRemoteTcpPort
            INTEGER,
    wfMplsLdpSessActualHoldTime
            INTEGER,
    wfMplsLdpSessActualRoutesConfigMode
            INTEGER,
    wfMplsLdpSessActualTCPConnectionRole
            INTEGER,
    wfMplsLdpSessActualSlot
            INTEGER

}

wfMplsLdpSessActualIndex OBJECT-TYPE
    SYNTAX INTEGER 
    ACCESS read-only
    STATUS mandatory
    DESCRIPTION
        "The Session index identifies this particular LDP session on the interface."
    ::= { wfMplsLdpSessActualEntry 1 }


wfMplsLdpSessActualCircuit OBJECT-TYPE
    SYNTAX INTEGER (1..1023)
    ACCESS read-only
    STATUS mandatory
    DESCRIPTION
        "The circuit number of the circuit to which the session belongs."
    ::= { wfMplsLdpSessActualEntry 2 }

wfMplsLdpSessActualState OBJECT-TYPE
    SYNTAX INTEGER {
        up(1),
        down(2),
	init(3),
        notpresent(4)
    }
    ACCESS read-only
    STATUS mandatory
    DESCRIPTION
        "The current state of the MPLS LDP session"
    ::= { wfMplsLdpSessActualEntry 3 }

wfMplsLdpSessActualPeerState OBJECT-TYPE
    SYNTAX INTEGER {
        initialized(1),
        opensend(2),
        openrec(3),
        operational(4)
    }
    ACCESS read-only
    STATUS mandatory
    DESCRIPTION
        "The current state of MPLS LDP session with the remote MPLS
 device"
    DEFVAL { initialized }
    ::= { wfMplsLdpSessActualEntry 4 }


wfMplsLdpSessActualLocalIpAddress OBJECT-TYPE
    SYNTAX IpAddress
    ACCESS read-only
    STATUS mandatory
    DESCRIPTION
        "The actual IP address that LDP used to
         establish the LDP peer to peer session."
    ::= { wfMplsLdpSessActualEntry 5 }

wfMplsLdpSessActualLocalTcpPort OBJECT-TYPE
    SYNTAX INTEGER(1..65535)
    ACCESS read-only
    STATUS mandatory
    DESCRIPTION
        "The actual local TCP port address that this LDP used to
         establish the LDP peer to peer session."
    ::= { wfMplsLdpSessActualEntry 6 }

wfMplsLdpSessActualRemoteIpAddress OBJECT-TYPE
    SYNTAX IpAddress
    ACCESS read-only
    STATUS mandatory
    DESCRIPTION 
        "The actual remote IP address that LDP used to
         establish the LDP peer to peer session."
    ::= { wfMplsLdpSessActualEntry 7 }

wfMplsLdpSessActualRemoteTcpPort OBJECT-TYPE
    SYNTAX INTEGER(1..65535)
    ACCESS read-only
    STATUS mandatory
    DESCRIPTION 
        "The actual TCP port that LDP used to
         establish the LDP peer to peer session."
    ::= { wfMplsLdpSessActualEntry 8 }
    
wfMplsLdpSessActualHoldTime  OBJECT-TYPE
        SYNTAX      INTEGER (1..240)
        ACCESS      read-only
        STATUS      mandatory
        DESCRIPTION
                "the actual Hold Time that LDP used to indicate the maximum 
		time in seconds that may elapse between the receipt of 
		successive PDUs from the LSR peer."
        ::= { wfMplsLdpSessActualEntry 9 }

wfMplsLdpSessActualRoutesConfigMode  OBJECT-TYPE
        SYNTAX  INTEGER {
	        auto(1),
        	manual(2)
	}
        ACCESS      read-only
        STATUS      mandatory
        DESCRIPTION
                "Indicates whether network routes are discovered by a 
	         routing protocol(auto) or are Manually configured(manual), see 
		 wfMplsLdpCfgRouteTable." 
        ::= { wfMplsLdpSessActualEntry 10 }

wfMplsLdpSessActualTCPConnectionRole OBJECT-TYPE
        SYNTAX  INTEGER {
	        active(1),
        	passive(2)
	}
        ACCESS      read-only
        STATUS      mandatory
        DESCRIPTION
                "Indicates the TCP connection roles between the peers."
        ::= { wfMplsLdpSessActualEntry 11 }

wfMplsLdpSessActualSlot OBJECT-TYPE
        SYNTAX  INTEGER 
        ACCESS  read-only
        STATUS  mandatory
        DESCRIPTION
                "Indicates the slot on which the LDP session is running." 
        ::= { wfMplsLdpSessActualEntry 12 }


wfMplsLdpCfgRouteTable OBJECT-TYPE
    SYNTAX SEQUENCE OF WfMplsLdpCfgRouteEntry
    ACCESS not-accessible
    STATUS mandatory
    DESCRIPTION
        "MPLS LDP configured route table -"
    ::= { wfMplsLdpGroup 3 }

wfMplsLdpCfgRouteEntry OBJECT-TYPE
    SYNTAX WfMplsLdpCfgRouteEntry
    ACCESS not-accessible
    STATUS mandatory
    DESCRIPTION
        "MPLS LDP configured route entries."
    INDEX { wfMplsLdpCfgRouteCct,
	    wfMplsLdpCfgRouteSessId,
            wfMplsLdpCfgRouteIndex }
    ::= { wfMplsLdpCfgRouteTable 1 }

WfMplsLdpCfgRouteEntry ::= SEQUENCE {
    wfMplsLdpCfgRouteCreate
            INTEGER,
    wfMplsLdpCfgRouteEnable
	    INTEGER,
    wfMplsLdpCfgRouteCct
	    INTEGER,
    wfMplsLdpCfgRouteSessId
	    INTEGER,
    wfMplsLdpCfgRouteIndex
	    INTEGER,
    wfMplsLdpCfgRouteDestination
	    IpAddress,
    wfMplsLdpCfgRouteMask
	    IpAddress,
    wfMplsLdpCfgRouteState
            INTEGER
}


wfMplsLdpCfgRouteCreate OBJECT-TYPE
    SYNTAX  INTEGER {
        created(1),
        deleted(2)
    }
    ACCESS read-write
    STATUS mandatory
    DESCRIPTION
        "Create/Delete parameter. Default is created. Users modify
         this object in order to create/delete MPLS LSP"
    DEFVAL { created }
    ::= { wfMplsLdpCfgRouteEntry 1 }

wfMplsLdpCfgRouteEnable OBJECT-TYPE
    SYNTAX INTEGER {
        enabled(1),
        disabled(2)
    }
    ACCESS read-write
    STATUS mandatory
    DESCRIPTION
        "Enable/Disable parameter. Default is enabled."
    DEFVAL  { enabled }
    ::= { wfMplsLdpCfgRouteEntry 2 }

wfMplsLdpCfgRouteCct OBJECT-TYPE
    SYNTAX INTEGER (1..1023)
    ACCESS read-only
    STATUS mandatory
    DESCRIPTION
        "The circuit munber to which the route associates with."
    ::= { wfMplsLdpCfgRouteEntry 3 }

wfMplsLdpCfgRouteSessId OBJECT-TYPE
    SYNTAX INTEGER (1..1023)
    ACCESS read-only
    STATUS mandatory
    DESCRIPTION
        "The session identification munber to which the route associates with."
    ::= { wfMplsLdpCfgRouteEntry 4 }

wfMplsLdpCfgRouteIndex OBJECT-TYPE
    SYNTAX INTEGER 
    ACCESS read-only
    STATUS mandatory
    DESCRIPTION
        "The index number of this route."
    ::= { wfMplsLdpCfgRouteEntry 5}

wfMplsLdpCfgRouteDestination OBJECT-TYPE
    SYNTAX IpAddress 
    ACCESS read-write
    STATUS mandatory
    DESCRIPTION
        "The netwrok prefix of this route."
    ::= { wfMplsLdpCfgRouteEntry 6 }

wfMplsLdpCfgRouteMask OBJECT-TYPE
    SYNTAX IpAddress 
    ACCESS read-write
    STATUS mandatory
    DESCRIPTION
        "The mask of this route."
    ::= { wfMplsLdpCfgRouteEntry 7 }

wfMplsLdpCfgRouteState OBJECT-TYPE
    SYNTAX INTEGER {
        up(1),
        down(2)
    }
    ACCESS read-only
    STATUS mandatory
    DESCRIPTION
        "The current state of the MPLS LDP session."
    DEFVAL { down }
    ::= { wfMplsLdpCfgRouteEntry 8 }

wfMplsLdpLibTable OBJECT-TYPE
    SYNTAX SEQUENCE OF WfMplsLdpLibEntry
    ACCESS not-accessible
    STATUS mandatory
    DESCRIPTION
        "MPLS LDP Label Information Base table which contains LSPs that have been  
	 set up."
    ::= { wfMplsLdpGroup 4 }

wfMplsLdpLibEntry OBJECT-TYPE
    SYNTAX WfMplsLdpLibEntry
    ACCESS not-accessible
    STATUS mandatory
    DESCRIPTION
        "MPLS LDP Label Information Base."
    INDEX { wfMplsLdpLibCct,
            wfMplsLdpLibSessId,
            wfMplsLdpLibDest,
	    wfMplsLdpLibMid,
	    wfMplsLdpLibIndex}
    ::= { wfMplsLdpLibTable 1 }


WfMplsLdpLibEntry ::= SEQUENCE {
    wfMplsLdpLibCct
	    INTEGER,
    wfMplsLdpLibSessId
	    INTEGER,
    wfMplsLdpLibDest
	    IpAddress,
    wfMplsLdpLibMid
	    INTEGER,
    wfMplsLdpLibLabel
	    INTEGER,
    wfMplsLdpLibEncaps
	    INTEGER,
    wfMplsLdpLibDirection
	    INTEGER,
    wfMplsLdpLibSlot
	    INTEGER,
    wfMplsLdpLibIndex
	    INTEGER
}


wfMplsLdpLibCct OBJECT-TYPE
    SYNTAX INTEGER (1..1023)
    ACCESS read-only
    STATUS mandatory
    DESCRIPTION
        "The circuit munber to which the route associates with."
    ::= { wfMplsLdpLibEntry 1}

wfMplsLdpLibSessId OBJECT-TYPE
    SYNTAX INTEGER (1..1023)
    ACCESS read-only
    STATUS mandatory
    DESCRIPTION
        "The session identification munber to which the LIB entry associates with."
    ::= { wfMplsLdpLibEntry 2}


wfMplsLdpLibDest OBJECT-TYPE
    SYNTAX IpAddress
    ACCESS read-only
    STATUS mandatory
    DESCRIPTION
        "The destnation network prefix."
    ::= { wfMplsLdpLibEntry 3 }


wfMplsLdpLibMid OBJECT-TYPE
    SYNTAX INTEGER
    ACCESS read-only
    STATUS mandatory
    DESCRIPTION
        "The merge id."
    ::= { wfMplsLdpLibEntry 4}

wfMplsLdpLibLabel  OBJECT-TYPE
    SYNTAX INTEGER
    ACCESS read-only
    STATUS mandatory
    DESCRIPTION
        "The label of the lsp that this LIB entry identifies."
    ::= { wfMplsLdpLibEntry 5}

wfMplsLdpLibEncaps OBJECT-TYPE
    SYNTAX INTEGER {
        llcsnap(1),
        null(2)
    }
    ACCESS read-only
    STATUS mandatory
    DESCRIPTION
        "The lsp encapsulation type."
    DEFVAL {llcsnap }
    ::= { wfMplsLdpLibEntry 6}

wfMplsLdpLibDirection OBJECT-TYPE
    SYNTAX INTEGER {
        inbound(1),
        outbound(2),
        bidirectional(3)
    }
    ACCESS read-only
    STATUS mandatory
    DESCRIPTION
        "MPLS VC direction."
    ::= { wfMplsLdpLibEntry 7}

wfMplsLdpLibSlot OBJECT-TYPE
    SYNTAX INTEGER 
    ACCESS read-only
    STATUS mandatory
    DESCRIPTION
        "Slot on which this LSP got created"
    ::= { wfMplsLdpLibEntry 8}

wfMplsLdpLibIndex OBJECT-TYPE
    SYNTAX INTEGER 
    ACCESS read-only
    STATUS mandatory
    DESCRIPTION
        "Index part of instance id"
    ::= { wfMplsLdpLibEntry 9}
 
END -- Wellfleet-MPLS-LDP-MIB
