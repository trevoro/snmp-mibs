Usr-Filter-MIB DEFINITIONS ::= BEGIN
        IMPORTS
          OBJECT-TYPE, MODULE-IDENTITY, Integer32
                  FROM SNMPv2-SMI
          DisplayString, common, UsrConfigStatus, UsrFilterName
                  FROM USR-DEFINITIONS-MIB;
usrFilter MODULE-IDENTITY
        LAST-UPDATED "200205022050Z"
        ORGANIZATION "CommWorks Corporation, a 3Com Company"
        CONTACT-INFO "Customer Support"
        DESCRIPTION
             "The commWorks enterprise defined MIB objects
                   for Filtering."
--      REVISION  "200205022050Z"
--      DESCRIPTION "Converted to SNMPv2."
     ::= { common 16 }
   -- textual conventions
   -- Begin managed object definitions here...
     usrFilterConfigFileName OBJECT-TYPE
         SYNTAX          DisplayString
         MAX-ACCESS      read-only
         STATUS          current
         DESCRIPTION             
            "The name of a ConfigFile to read/write permanent database
             records.  If the value of this object is an empty string, 
             then the Filter Manager process uses the default name 
             `@file://filter.cfg'. "
     ::= { usrFilter 1 }
     usrFilterCFMStatusFlag  OBJECT-TYPE
         SYNTAX      UsrConfigStatus
         MAX-ACCESS      read-write
         STATUS          current
         DESCRIPTION
            "Setting the value of this object to `save' causes the values
             of the SNMP Group to be written out to the current config
             file, which is stored in the usrFilterConfigFileName object.
             While the new ConfigFile is being written, the SNMP process
             will set the value of this flag to `saving''. Any
             attempts to set the value while it is not `normal'
             (i.e. the file is currently being written to the
             ConfigFile) will result in a badValue error being
             returned. Setting the value to `normal' will result in no
             action."
     ::= { usrFilter 2 }
     usrFilterTable OBJECT-TYPE
         SYNTAX   SEQUENCE OF UsrFilterEntry
         MAX-ACCESS   not-accessible
         STATUS       current
         DESCRIPTION
            "A table of packet filter names.  The actual filter
             information is stored in an ASCII file in flash."
     ::= { usrFilter 3 }
     usrFilterEntry OBJECT-TYPE
         SYNTAX   UsrFilterEntry
         MAX-ACCESS   not-accessible
         STATUS       current
         DESCRIPTION
                "The parameters for a packet filter."
         INDEX {usrFilterName}
     ::= { usrFilterTable 1 }
     --
     -- The row is composed of these components
     --
     UsrFilterEntry ::=
         SEQUENCE {
         usrFilterName
            UsrFilterName,
         usrFilterStatus
            INTEGER,
         usrFilterProtocols
            INTEGER,
         usrFilterVerifyError
            DisplayString
     }
     usrFilterName OBJECT-TYPE
         SYNTAX  UsrFilterName
         MAX-ACCESS  not-accessible
         STATUS      current
         DESCRIPTION
            "The character name for this filter."
     ::= { usrFilterEntry 1 }
     usrFilterStatus OBJECT-TYPE
         SYNTAX  INTEGER {
                         normal(1),
                         delete(2),
                         verify(3),
                         reading(4),       -- File reading in progress
                         verifying(5),     -- Filter verification in progress
                         compiling(6),     -- Filter compilation in progress
                         verifyFailed(7),  -- Filter verification failed
                         starting(8)       -- Filter operation starting
                         }
         MAX-ACCESS  read-write
         STATUS      current
         DESCRIPTION
            "The status of this filter entry. Valid row entries in this
             table have the status field set to normal. The settable values
             are normal and delete.  If the instance is not in the table 
             and the status is normal, this will be an add operation.  If the
             instance is in the table and the status is normal, this will be a
             modify operation.  If the instance is in the table and the 
             status is delete, this will be a delete operation.  The values 
             reading, verifying, and compiling are read-only."
         --CONFIGURABLE
     ::= { usrFilterEntry 2 }
     usrFilterProtocols OBJECT-TYPE
         SYNTAX  INTEGER {
                         bridge(1),        -- Bridge filter
                         bridge-call(2),   -- Bridge Call filter
                         ip(4),            -- IP filter
                         ip-call(8),       -- IP Call filter
                         ipx(16),          -- IPX filter
                         ipx-call(32),     -- IPX Call filter
                         atalk(64),        -- AppleTalk filter
                         atalk-call(128),  -- Appletalk Call filter
                         rip(256),         -- IP RIP filter
                         xrip(512),        -- IPX RIP filter
                         sap(1024),        -- IPX SAP filter
                         rtmp(2048),       -- AppleTalk RTMP filter
                         zip(4096),        -- Appletalk ZIP filter
                         access(8192),     -- Login Access filter
					arap(16384)       -- ARAP Zone filter 
                         }
         MAX-ACCESS  read-only
         STATUS      current
         DESCRIPTION
            "Packet filters can be created for the following protocols:
             BRIDGE, IP, IPX, AppleTalk, IP-RIP, IPX-RIP, IPX-SAP, ATALK-RTMP.
             There will be others in the future.  This object uses the 32 bit 
             integer as a bit field.  A single filter specification may contain
             one or more protocols."
     ::= { usrFilterEntry 3 }
     usrFilterVerifyError OBJECT-TYPE
         SYNTAX      DisplayString
         MAX-ACCESS  read-only
         STATUS      current
         DESCRIPTION
            "The error string returned when a filter fails its verification
             process.  Otherwise, this field is NULL."
     ::= { usrFilterEntry 4 }
 usrFilterPktLogFlag OBJECT-TYPE
         SYNTAX  INTEGER {
                         all   (1),
                         radius(2),
                         off   (3)
                         }
         MAX-ACCESS  read-write
         STATUS      current
         DESCRIPTION
            "A flag that controls the generation of syslog messages for filtered
             packets.
              all    - all filtered packets will generate a syslog message.
              radius - the radius attribute, Filter-Log-Packet will control syslog
                       message generation.
              off    - no syslog messages will be generated."
         --CONFIGURABLE
     ::= { usrFilter 4 }
usrFilterPktLogSize OBJECT-TYPE
         SYNTAX  Integer32 (0..493)
         MAX-ACCESS  read-write
         STATUS      current
         DESCRIPTION
            "The size of a filtered packet that will be included in the actual 
             syslog message.  The default value is 0.  NOTE: syslog can only 
             handle 1028 bytes of ascii text, therefore packet data must 
             converted from hex to ascii, thus reducing the maxium packet data 
             size in half. When syslog begin and end strings are added it is 
             further reduced to 493 bytes." 
         --CONFIGURABLE
     ::= { usrFilter 5 }     
usrFilterPktLogCount OBJECT-TYPE
         SYNTAX  Integer32
         MAX-ACCESS  read-only
         STATUS      current
         DESCRIPTION
            "The number of packets that were filtered and sent to syslog."
     ::= { usrFilter 6 }          
END         -- End Filter MIB definitions
