EXTREMEdot11AP-MIB DEFINITIONS ::= BEGIN 
	
	
	IMPORTS 
	MODULE-IDENTITY 	FROM SNMPv2-SMI
	OBJECT-TYPE 		FROM SNMPv2-SMI
	TruthValue 		FROM SNMPv2-TC 
	extremeAP		FROM EXTREME-BASE-MIB
	ifIndex 		FROM RFC1213-MIB
	Unsigned32		FROM SNMPv2-SMI;

-- ********************************************************************** 
-- * MODULE IDENTITY 
-- ********************************************************************** 

	extremeDot11ap MODULE-IDENTITY
	LAST-UPDATED "0211140000Z" 
	ORGANIZATION "Extreme Networks"
	CONTACT-INFO " " 

	DESCRIPTION 
	"This MIB module provides managemetn of a set of APs.  It is based
	 on the IEEE AP MIB with additions for better indexing."
    ::= { extremeAP 21 }

-- ********************************************************************** 
-- * Major sections 
-- ********************************************************************** 

-- ********************************************************************** 
-- * End of EXTREME AP MIB
-- ********************************************************************** 
END 





-- *************************************************************** --
-- 			LAC MIB					   --
--                                                                 --
-- This MIB makes reference to two new terms: wireless port and    --
-- wireless interface.  A wireless port refers to the physical     --
-- connection between a LAC and an access point, together with the --
-- access point chassis.  Thus a wireless port is the unit of mani --
-- pulation for images, version, etc.                              --
--                                                                 --
-- A wireless interface is a channel or antenna on a single wirele --
-- ss port.  There can be one or more wireless interfaces on a     --
-- wireless port.                                                  --
-- *************************************************************** --
