CT-ELS100-MIB DEFINITIONS ::= BEGIN

    --  ctELS100-mib.txt
    --  Revision: 01.00.02
    --  Part Number:
    --  Date: July 8, 1998

        --  Cabletron Systems, Inc.
        --  35 Industrial Way, P.O. Box 5005
        --  Rochester, NH 03867-0505
        --  (603) 332-9400
        --  support@ctron.com

        --  This module provides authoritative definitions for Cabletron's
        --  ELS-100 mib.
        --
        --  This module will be extended, as required.
        --

        --  Cabletron Systems reserves the right to make changes in
        --  specification and other information contained in this document
        --  without prior notice.  The reader should consult Cabletron Systems
        --  to determine whether any such changes have been made.
        --
        --  In no event shall Cabletron Systems be liable for any incidental,
        --  indirect, special, or consequential damages whatsoever (including
        --  but not limited to lost profits) arising out of or related to this
        --  document or the information contained in it, even if Cabletron
        --  Systems has been advised of, known, or should have known, the
        --  possibility of such damages.
        --
        --  Cabletron grants vendors, end-users, and other interested parties
        --  a non-exclusive license to use this Specification in connection
        --  with the management of Cabletron products.

        --  Copyright (c)1998 Cabletron Systems


IMPORTS

      OBJECT-TYPE
                FROM RFC-1212

      DisplayString, sysObjectID, ifInErrors, ifOutErrors
                FROM RFC1213-MIB

      Counter, Gauge, IpAddress, TimeTicks, enterprises
                FROM RFC1155-SMI

      TRAP-TYPE
                FROM RFC-1215;



 --  mgmt   OBJECT IDENTIFIER ::= { iso org(3) dod(6) internet(1) 
 --                                            mgmt(2) }
 --  mib    OBJECT IDENTIFIER ::= { mgmt 1 }
 --  directory     OBJECT IDENTIFIER ::= { internet 1 }
 --  experimental  OBJECT IDENTIFIER ::= { internet 3 }
 --  private       OBJECT IDENTIFIER ::= { internet 4 }
 --  enterprises   OBJECT IDENTIFIER ::= { private 1 }

 sigma             OBJECT IDENTIFIER ::= { enterprises 97 }
 sys    OBJECT IDENTIFIER ::= { sigma 1 }
 els-100    OBJECT IDENTIFIER ::= { sigma 8 }
 kxhw    OBJECT IDENTIFIER ::= { els-100 1 }
 kxsw    OBJECT IDENTIFIER ::= { els-100 2 }
 kxadmin    OBJECT IDENTIFIER ::= { els-100 3 }
 kxswdis    OBJECT IDENTIFIER ::= { els-100 4 }
 kxaddr    OBJECT IDENTIFIER ::= { els-100 5 }
 kxif    OBJECT IDENTIFIER ::= { els-100 6 }
 kxuart    OBJECT IDENTIFIER ::= { els-100 7 }
 kxproto    OBJECT IDENTIFIER ::= { els-100 8 }
 kxtrunk    OBJECT IDENTIFIER ::= { els-100 9 }
 kxworkgroup   OBJECT IDENTIFIER ::= { els-100 10 }
 kxtrapMgt   OBJECT IDENTIFIER ::= { els-100 11 }
 kxmirrorgroup   OBJECT IDENTIFIER ::= { els-100 12 }


   -- SMC MIB
   -- System group
  
 sysID OBJECT-TYPE
  SYNTAX  INTEGER {
      els-100-bridge(8)
  }
  ACCESS read-only
  STATUS mandatory
  DESCRIPTION 
  "An integer which serves to identify the type of SmartStack."
  ::= { sys 1 }

 sysReset OBJECT-TYPE
  SYNTAX  TimeTicks
  ACCESS read-write
  STATUS mandatory
  DESCRIPTION
  "The time, in centiseconds, before the device should
  reboot. A GetResponse value of zero indicates that no
  reboot time has been specified."
  ::= { sys 2 }

 sysTrapPort OBJECT-TYPE
  SYNTAX  INTEGER
  ACCESS read-write
  STATUS mandatory
  DESCRIPTION
  "Zero, or the UDP port number to which a second copy
  of SNMP traps should be sent. Valid values are zero
  through 65535."
  ::= { sys 3 }


 --  HW Configuration Group


 kxhwDiagCode OBJECT-TYPE
  SYNTAX OCTET STRING
  ACCESS read-only
  STATUS mandatory
  DESCRIPTION
  "Additional diagnostics information concerning the
  slot's module."
  ::= { kxhw 1 }

 kxhwManufData OBJECT-TYPE
  SYNTAX OCTET STRING
  ACCESS read-only
  STATUS mandatory
  DESCRIPTION 
  "A 24-byte array which contains the part number,
  serial number and hardware revision level of this
  module."
  ::= { kxhw 2 }

 kxhwPortCount OBJECT-TYPE
  SYNTAX INTEGER
  ACCESS read-only
  STATUS mandatory
  DESCRIPTION ""
  ::= { kxhw 3 }


 --  kxSW Configuration Group

 kxswNumber OBJECT-TYPE
  SYNTAX INTEGER
  ACCESS read-only
  STATUS mandatory
  DESCRIPTION 
  "The number of file sets. The default is 2."
  ::= { kxsw 1 }

 kxswFilesetTable OBJECT-TYPE
  SYNTAX SEQUENCE OF KxswFilesetEntry
  ACCESS not-accessible
  STATUS mandatory
  DESCRIPTION 
  "A list of the software file sets stored. The first
  file set refers to the one that was used when ELS-100
  last booted. The second file set refers to the one
  which will be used when ELS-100 reboots or reloads any
  hardware module."
  ::= { kxsw 2 }

 kxswFilesetEntry OBJECT-TYPE
  SYNTAX KxswFilesetEntry
  ACCESS not-accessible
  STATUS mandatory
  DESCRIPTION 
  "A set of objects for each file set."
  INDEX { kxswIndex }
  ::= { kxswFilesetTable 1 }

 KxswFilesetEntry ::= SEQUENCE {
  kxswIndex
   INTEGER,
  kxswDesc
   DisplayString,
  kxswCount
   INTEGER,
  kxswType
   OCTET STRING,
  kxswSizes
   OCTET STRING,
  kxswStarts
   OCTET STRING,
  kxswBases
   OCTET STRING,
  kxswFlashBank
   INTEGER
  }

 kxswIndex OBJECT-TYPE
  SYNTAX  INTEGER {
      currently-executing(1),
      next-boot(2)
  }
  ACCESS read-only
  STATUS mandatory
  DESCRIPTION 
  "The file set number, beginning with 1 for the first
  file set. This number always matches the instance of
  the swFiles.  For example, {swIndex 2} contains the
  value '2'."
  ::= { kxswFilesetEntry 1 }

 kxswDesc OBJECT-TYPE
  SYNTAX DisplayString
  ACCESS read-only
  STATUS mandatory
  DESCRIPTION 
  "The description (0-255 bytes) of the software file
  set."
  ::= { kxswFilesetEntry 2 }

 kxswCount OBJECT-TYPE
  SYNTAX INTEGER
  ACCESS read-only
  STATUS mandatory
  DESCRIPTION 
  "The number of files in the file set. This number may
  range from 1 to 255."
  ::= { kxswFilesetEntry 3 }

 kxswType OBJECT-TYPE
  SYNTAX OCTET STRING
  ACCESS read-only
  STATUS mandatory
  DESCRIPTION 
  "The types of the files within the file set."
  ::= { kxswFilesetEntry 4 }

 kxswSizes OBJECT-TYPE
  SYNTAX OCTET STRING
  ACCESS read-only
  STATUS mandatory
  DESCRIPTION 
  "An array (4 octets per file), containing the size of
  each of the files. Each size is encoded as a series 
  of 4 bytes, which should be converted into a 32 bit
  integer."
  ::= { kxswFilesetEntry 5 }

 kxswStarts OBJECT-TYPE
  SYNTAX OCTET STRING
  ACCESS read-only
  STATUS mandatory
  DESCRIPTION 
  "An array (4 octets per file), containing the
  software's execution starting address of each of the
  files. Each address is encoded as a series of 4 bytes,
  which should be converted into a 32 bit integer."
  ::= { kxswFilesetEntry 6 }

 kxswBases OBJECT-TYPE
  SYNTAX OCTET STRING
  ACCESS read-only
  STATUS mandatory
  DESCRIPTION 
  "An array (4 octets per file), containing the
  software's base loading address of each of the
  files. Each address is encoded as a series of 4 bytes,
  which should be converted into a 32 bit integer."
  ::= { kxswFilesetEntry 7 }

 kxswFlashBank OBJECT-TYPE
  SYNTAX  INTEGER {
      first-bank(1),
      second-bank(2)
  }
  ACCESS read-only
  STATUS mandatory
  DESCRIPTION 
  "The bank number where the software file set resides."
  ::= { kxswFilesetEntry 8 }


 -- kxADMIN Group

 kxadminFatalErr OBJECT-TYPE
  SYNTAX   OCTET STRING
  ACCESS   read-only
  STATUS   mandatory
  DESCRIPTION 
  "This is a 32 byte array which contains information 
  about the cause of the previous system reset. This
  will describe the circumstances which forced the
  system software to perform a reboot. The values in the
  first byte have the following meanings (0) Power
  failure, (1) Watchdog Timeout, (2) NMS Requested
  Shutdown, (3-255) Fatal Error (next byte contains the
  hwIndex of the module which encountered the error;
  remaining 30 bytes contain additional information)."
  ::= { kxadmin 1 }

 kxadminAnyPass  OBJECT-TYPE
  SYNTAX   OCTET STRING
  ACCESS   read-write
  STATUS   mandatory
  DESCRIPTION 
  "The authentication password (0-24 bytes) which must
  match the community name in an SNMP PDU, in order for
  the operation to be performed. A zero length password
  indicates that any community name is acceptable."
  ::= { kxadmin 2 }

 kxadminGetPass  OBJECT-TYPE
  SYNTAX   OCTET STRING
  ACCESS   read-write
  STATUS   mandatory
  DESCRIPTION 
  "The authentication password (0-24 bytes) which must
  match the community name in an SNMP Get PDU (except
  for Debug or password parameters). A zero length
  password indicates that any community name is
  acceptable. Alternatively, it is acceptable if the
  community name matches configAnyPass."
  ::= { kxadmin 3 }

 kxadminNMSIPAddr OBJECT-TYPE
  SYNTAX  IpAddress
  ACCESS  read-write
  STATUS  mandatory
  DESCRIPTION 
  "The address of the NMS to which Trap PDUs are to be
  sent.  A value of zero indicates that Trap PDUs should
  be sent to the NMS last heard from."
  ::= { kxadmin 4 }

 kxadminStorageFailure OBJECT-TYPE
  SYNTAX  INTEGER { 
      true(1),
      false(2)
  }
  ACCESS   read-only
  STATUS   mandatory
  DESCRIPTION 
  "Whether the ELS-100's storage facility for its
  configuration parameters has failed (the ELS-100 may
  not be able to reboot after such a failure)."
  ::= { kxadmin 5 }

 kxadminAuthenticationFailure OBJECT-TYPE
  SYNTAX   IpAddress
  ACCESS   read-only
  STATUS   mandatory
  DESCRIPTION 
  "All nulls, or the IP source address within the last
  SNMP PDU which caused an SNMP authentication failure."
  ::= { kxadmin 6 }

 kxadminNAMReceiveCongests  OBJECT-TYPE
  SYNTAX   Counter
  ACCESS   read-only
  STATUS   mandatory
  DESCRIPTION ""
  ::= { kxadmin 7 }
          
 kxadminArpEntries  OBJECT-TYPE
  SYNTAX   Counter
  ACCESS   read-only
  STATUS   mandatory
  DESCRIPTION 
  "The number of ARP entries for all interfaces."
  ::= { kxadmin 8 }

 kxadminArpStatics OBJECT-TYPE
  SYNTAX  Counter
  ACCESS  read-only
  STATUS  mandatory
  DESCRIPTION 
  "The number of statically defined ARP entries for all
  interfaces."
  ::= { kxadmin 9 }

 kxadminArpOverflows   OBJECT-TYPE
  SYNTAX   Counter
  ACCESS   read-only
  STATUS   mandatory
  DESCRIPTION 
  "The number of times a ARP entry could not be learned
  due to insufficient address table space."
  ::= { kxadmin 10 }

 kxadminRipPreference  OBJECT-TYPE
  SYNTAX   INTEGER
  ACCESS   read-write
  STATUS   mandatory
  DESCRIPTION 
  "The value to assign to ipRouteMetric2, when adding a
  RIP-learned entry to the IP Routing Table."
  ::= { kxadmin 11 }

 kxadminRipRouteDiscards  OBJECT-TYPE
  SYNTAX   Counter
  ACCESS   read-only
  STATUS   mandatory
  DESCRIPTION 
  "The number of times a route learned via RIP was not
  added to the IP Routing Table due to insufficient
  Routing Table space."
  ::= { kxadmin 12 }

 kxadminRebootConfig   OBJECT-TYPE
  SYNTAX  INTEGER {
      no-change(1),
      tftp-config(2),
      revert-to-defaults(3)
  }
  ACCESS  read-write
  STATUS  mandatory
  DESCRIPTION 
  "The configuration file that will be used when the
  ELS-100 reboots. This parameter is normally
  automatically set by the ELS-100; however, an NMS may
  explicitly set it to either no-change (1) or
  revert-to-defaults (3)."
  ::= { kxadmin 13 }

 kxadminDisableButton  OBJECT-TYPE
  SYNTAX  INTEGER  { 
      true(1), 
      false(2) 
  }
  ACCESS read-write
  STATUS mandatory
  DESCRIPTION ""
  ::= { kxadmin 14 }

 kxadminButtonSelection  OBJECT-TYPE
  SYNTAX  INTEGER {
      led-any-activity(1),
      led-rx-activity(2),
      led-tx-activity(3),
      led-any-collision(4),
      led-programmed(5),
      led-duplex(6),
      led-speed(7),
      led-mirror(8)
  }
  ACCESS read-write
  STATUS mandatory
  DESCRIPTION ""
  ::= { kxadmin 15}

 kxadminLEDProgramOption OBJECT-TYPE
  SYNTAX  INTEGER {
      program-led-any-error(1)
  }
  ACCESS read-write
  STATUS mandatory
  DESCRIPTION ""
  ::= { kxadmin 16}

 -- Software Distribution Group

 kxswdisDesc  OBJECT-TYPE
  SYNTAX  OCTET STRING
  ACCESS read-only
  STATUS mandatory
  DESCRIPTION
  "The description (0-32 bytes) of the software set
  currently being downloaded, or a description of the
  software set last downloaded since the ELS100-16
  booted."
  ::= { kxswdis 1 }

 kxswdisAccess OBJECT-TYPE
  SYNTAX  INTEGER {
      protected(1),
      any-software(2)
  }
  ACCESS read-write
  STATUS mandatory
  DESCRIPTION
  "The version of software that may be
  downloaded. Attempts to download other versions of
  software will be rejected. The value for swdisAccess
  is embedded within the software files that are to be
  distributed via TFTP. Its value may be derived from
  the names of the software files. The NMS operator may
  wish to use the following special values: protected
  (1)  No software downloads will be accepted
  any-software (2)  A software download of any version
  of new software will be accepted - this is the factory
  default"
  ::= { kxswdis 2 }

 kxswdisWriteStatus OBJECT-TYPE
  SYNTAX  INTEGER {
      in-progress(1),
      success(2),
      config-error(3),
      flash-error(4),
      config-and-flash-errors(5)
  }
  ACCESS read-only
  STATUS mandatory
  DESCRIPTION
  "The status of the erase/write operation."
  ::= { kxswdis 3 }

 kxswdisConfigIp OBJECT-TYPE
  SYNTAX IpAddress
  ACCESS read-write
  STATUS mandatory
  DESCRIPTION
  "The IP address of the NMS (i.e., any IP host) that is
  allowed to use TFTP to send/retrieve the configuration
  file of the ELS100-16. A value of 0.0.0.0 (which is
  the factory specified default) prevents any NMS from
  obtaining access, while a value of 255.255.255.255
  gives every NMS permission."
  ::= { kxswdis 4 }

 kxswdisConfigRetryTime OBJECT-TYPE
  SYNTAX INTEGER
  ACCESS read-write
  STATUS mandatory
  DESCRIPTION
  "The number of seconds that the ELS-100 will wait for
  an acknowledgment before it retransmits an
  unacknowledged TFTP data block. The factory specified
  default is 5 seconds."
  ::= { kxswdis 5 }

 kxswdisConfigTotalTimeout OBJECT-TYPE
  SYNTAX INTEGER
  ACCESS read-write
  STATUS mandatory
  DESCRIPTION
  "The number of seconds that the ELS-100 will wait for
  an acknowledgment to a data block before it cancels a
  TFTP session. The factory specified default is 25
  seconds."
  ::= { kxswdis 6 }

 -- Address Configuration

 kxaddrStatics OBJECT-TYPE
  SYNTAX  Counter
  ACCESS read-only
  STATUS mandatory
  DESCRIPTION 
  "The number of static addresses which are currently
  stored in the ELS100-16."
  ::= { kxaddr 1 }

 kxaddrDynamics OBJECT-TYPE
  SYNTAX Counter
  ACCESS read-only
  STATUS mandatory
  DESCRIPTION 
  "The number of learned addresses in the address table."
  ::= { kxaddr 2 }

 kxaddrDynamicMax OBJECT-TYPE
  SYNTAX Gauge
  ACCESS read-write
  STATUS mandatory
  DESCRIPTION 
  "The maximum number of spanning tree addresses which
  have been learned since the ELS100-16 was last booted
  (or this parameter was last reset by the NMS)."
  ::= { kxaddr 3 }

 kxaddrDynamicOverflows OBJECT-TYPE
  SYNTAX Counter
  ACCESS read-only
  STATUS mandatory
  DESCRIPTION 
  "The number times an address was not learned due to
  insufficient address table space."
  ::= { kxaddr 4 }

 kxaddrFlags OBJECT-TYPE
  SYNTAX INTEGER
  ACCESS read-write
  STATUS mandatory
  DESCRIPTION 
  "Flags to describe the use and control of this address
  entry.  Each bit has a different meaning. The NMS must
  always set either entry-static, entry-none, or
  entry-mesh; however, for GetRequests, the NMS will see
  either no bits set (if the entry does not exist), or
  exactly one of the following bits set:
  entry-dynamic-local = 30, entry-dynamic-remote = 29, 
  entry-static = 28, entry-other = 27, entry-none = 26, 
  entry-mesh = 25, entry-statistics = 24, Bit 31 is
  reserved.

  Any combination of the restriction bits (bits 23-21)
  may be set for any type of entry, except entry-other
  or entry-mesh: entry-no-source = 23, entry-no-multi =
  22, Bit 21 is reserved, Bits 20-18 are reserved.

  Exactly one of the special entry bits (bits 17-10)
  must be set for entry-other entries, and none of the
  bits may be set for other than entry-other entries:
  entry-all-lmas = 17, entry-any-lma = 16, entry-lma =
  15, entry-port = 14, entry-bpdu = 13, entry-reserved =
  12, Bits 11-10 are reserved for future expansion. Bits
  9-0 are reserved."
  ::= { kxaddr 5 }

 kxaddrMAC OBJECT-TYPE
  SYNTAX OCTET STRING
  ACCESS read-write
  STATUS mandatory
  DESCRIPTION 
  "The MAC address for this address definition."
  ::= { kxaddr 6 }

 kxaddrPort OBJECT-TYPE
  SYNTAX INTEGER
  ACCESS read-write
  STATUS mandatory
  DESCRIPTION 
  "The port through which this address is connected to
  the ELS100 (only valid for entry-dynamic-local,
  entry-statistics, and entry-port entries)."
  ::=  { kxaddr 7 }

 kxaddrOperation OBJECT-TYPE
  SYNTAX  INTEGER {
      read-random(1),
      read-next(2),
      update(4),
      delete(5),
      read-block(6)
  }
  ACCESS read-write
  STATUS mandatory
  DESCRIPTION 
  "The operation to be performed upon the described
  address.  The possibilities include: read-random (1), 
  read-next (2), update (4), delete (5), read-block (6)."
  ::= { kxaddr 8 }

 kxaddrIndex OBJECT-TYPE
  SYNTAX INTEGER
  ACCESS read-write
  STATUS mandatory
  DESCRIPTION 
  "The index number to be used for read-next and
  read-block operations. When the ELS-100 boots,
  addrIndex is initialized to -1."
  ::= { kxaddr 9 }

 kxaddrNext OBJECT-TYPE
  SYNTAX INTEGER
  ACCESS read-write
  STATUS mandatory
  DESCRIPTION 
  "The next value to use for addrIndex, when you use
  read-next or read-block operations to read the address
  table. When the ELS-100 boots, addrNext is initialized
  to -1."
  ::= { kxaddr 10 }

 kxaddrBlockSize OBJECT-TYPE
  SYNTAX INTEGER
  ACCESS read-write
  STATUS mandatory
  DESCRIPTION 
  "The number of addresses contained by addrBlock.  This
  parameter is only used for dumping blocks of MAC
  addresses."
  ::= { kxaddr 11 }

 kxaddrBlock OBJECT-TYPE
  SYNTAX OCTET STRING
  ACCESS read-write
  STATUS mandatory
  DESCRIPTION 
  "A series of 0-700 octets, which represents 0-100
  addresses.  Each address consists of a 6 octet MAC
  address followed by a 1 byte port number. If the port
  number is zero, then the address is that of a
  specially configured address; otherwise, the address
  is a dynamically learned address. This parameter is
  only used for dumping blocks of MAC addresses"
  ::= { kxaddr 12 }


 -- Interfaces Group


 kxifTable OBJECT-TYPE
  SYNTAX SEQUENCE OF KxifEntry
  ACCESS not-accessible
  STATUS mandatory
  DESCRIPTION 
  "A list of interface entries; one per port."
  ::= { kxif 1  }

 kxifEntry OBJECT-TYPE
  SYNTAX KxifEntry
  ACCESS not-accessible
  STATUS mandatory
  DESCRIPTION 
  "A set of objects for an interface entry."
  INDEX { kxifIndex }
  ::= { kxifTable 1 }

 KxifEntry ::= SEQUENCE {
  kxifIndex
   INTEGER,
  kxifRxCnt
   INTEGER,
  kxifTxCnt
   INTEGER,
  kxifThreshold
   INTEGER,
  kxifThresholdTime
   INTEGER,
  kxifRxQueueThresh
   INTEGER,
  kxifRxQueueThreshTime
   INTEGER,
  kxifFunction
   INTEGER,
  kxifStatisticsTime
   TimeTicks
  }

 kxifIndex OBJECT-TYPE
  SYNTAX INTEGER
  ACCESS read-only
  STATUS mandatory
  DESCRIPTION 
  "The port number, beginning with 1 for the first
  port."
  ::= { kxifEntry 1 }

 kxifRxCnt OBJECT-TYPE
  SYNTAX INTEGER
  ACCESS read-only
  STATUS mandatory
  DESCRIPTION 
  "The number of small data buffers for receiving
  packets."
  ::= { kxifEntry 2 }

 kxifTxCnt OBJECT-TYPE
  SYNTAX INTEGER
  ACCESS read-only
  STATUS mandatory
  DESCRIPTION 
  "The maximum size of the port's transmit queue, i.e.,
  the number of packets that can be in the port's
  transmit queue, waiting to be transmitted."
  ::= { kxifEntry 3 }

 kxifThreshold OBJECT-TYPE
  SYNTAX INTEGER
  ACCESS read-write
  STATUS mandatory
  DESCRIPTION 
  "Maximum number of combined receive and transmit
  packet hardware errors before an alarm should be
  generated."
  ::= { kxifEntry 4 }

 kxifThresholdTime OBJECT-TYPE
  SYNTAX INTEGER
  ACCESS read-write
  STATUS mandatory
  DESCRIPTION 
  "The time period (in seconds) to which kxifThreshold
  applies. A value of zero will disable the
  kxifThreshold alarm."
  ::= { kxifEntry 5 }

 kxifRxQueueThresh OBJECT-TYPE
  SYNTAX INTEGER
  ACCESS read-write
  STATUS mandatory
  DESCRIPTION 
  "Maximum number of receive packet queue overflow
  errors before an alarm should be generated."
  ::= { kxifEntry 6 }

 kxifRxQueueThreshTime OBJECT-TYPE
  SYNTAX INTEGER
  ACCESS read-write
  STATUS mandatory
  DESCRIPTION 
  "The time period (in seconds) to which
  kxifRxQueueThresh applies.  A value of zero will
  disable the kxifRxQueueThresh alarm."
  ::= { kxifEntry 7 }

 kxifFunction OBJECT-TYPE
  SYNTAX INTEGER 
  ACCESS read-only
  STATUS mandatory
  DESCRIPTION 
  "The current functional state (protocols which have
  been activated and are operational) of the port. The
  following values or combinations are supported:
  0x0001   NMS,       0x0002   TBRIDGE, 0x0020   UNIT_NO_BPDU 
  0x0040   UNIT_RIP,  0x0800   UNIT_ARP,0x1000   UNIT_DUPLEX_HALF 
  0x2000   UNIT_DUPLEX_AUTO,   0x8000  UNIT_AUTO
  0x10000  UNIT_TRUNKING   ,   0x40000 UNIT_SPEED_10

  These values can be configured through the protoTable."
  ::= { kxifEntry 8}

 kxifStatisticsTime OBJECT-TYPE
  SYNTAX TimeTicks
  ACCESS read-only
  STATUS mandatory
  DESCRIPTION 
  "Length of time during which statistics were collected."
  ::= { kxifEntry 9 }

 -- UART Interface Group

 kxuartTable OBJECT-TYPE
  SYNTAX SEQUENCE OF KxuartEntry
  ACCESS  not-accessible
  STATUS mandatory
  DESCRIPTION 
  "A list of interface entries; one per UART port."
  ::= { kxuart 1 }

 kxuartEntry OBJECT-TYPE
  SYNTAX KxuartEntry
  ACCESS not-accessible
  STATUS mandatory
  DESCRIPTION 
  "A set of objects for an interface entry."
  INDEX { kxuartIndex }
  ::= { kxuartTable 1 }

 KxuartEntry ::= SEQUENCE {
  kxuartIndex
   INTEGER,
  kxuartBaud
   INTEGER,
  kxuartAlignmentErrors
   Counter,
  kxuartOverrunErrors
   Counter
  }

 kxuartIndex OBJECT-TYPE
  SYNTAX INTEGER
  ACCESS read-only
  STATUS mandatory
  DESCRIPTION 
  "The ELS-100's port number of the port."
  ::= { kxuartEntry 1 }

 kxuartBaud OBJECT-TYPE
  SYNTAX  INTEGER {
      external-clock(1),
      b1200-baud(2),
      b2400-baud(3),
      b4800-baud(4),
      b9600-baud(5),
      b19200-baud(6),
      b38400-baud(7),
      b56-kilobits(8),
      b1544-kilobits(9),
      b2048-kilobits(10),
      b45-megabits(11)
  }
  ACCESS read-write
  STATUS mandatory
  DESCRIPTION 
  "This is the desired baud rate. Only 1200 baud 
  through 19,200 baud are supported by the ELS-100."
  ::= { kxuartEntry 2 }

 kxuartAlignmentErrors OBJECT-TYPE
  SYNTAX Counter
  ACCESS read-only
  STATUS mandatory
  DESCRIPTION 
  "Number of received packets with frame alignment
  errors, since the port was last enabled."
  ::= { kxuartEntry 3 }

 kxuartOverrunErrors OBJECT-TYPE
  SYNTAX Counter
  ACCESS read-only
  STATUS mandatory
  DESCRIPTION 
  "Number of received packets with data overrun errors,
  since the port was last enabled."
  ::= { kxuartEntry 4 }

 --  Protocols Group

 kxprotoTable OBJECT-TYPE
  SYNTAX  SEQUENCE OF KxprotoEntry
  ACCESS  not-accessible
  STATUS  mandatory
  DESCRIPTION
  "This table contains configuration information
  specifying the types of protocols used to bridge
  and filter frames for each port."
  ::= { kxproto 1 }

 kxprotoEntry OBJECT-TYPE
  SYNTAX  KxprotoEntry
  ACCESS  not-accessible
  STATUS  mandatory
  DESCRIPTION
  "Each entry in this table specifies which protocols are
  used by a particular port in the SmartStack."
  INDEX { kxprotoIfIndex }
  ::= { kxprotoTable 1 }

 KxprotoEntry ::= SEQUENCE { 
  kxprotoIfIndex
   INTEGER,
         kxprotoBridge
   INTEGER,
         kxprotoSuppressBpdu
   INTEGER,
         kxprotoRipListen
   INTEGER,
         kxprotoTrunking
   INTEGER
  }

 kxprotoIfIndex OBJECT-TYPE
  SYNTAX  INTEGER
  ACCESS  read-only
  STATUS  mandatory
  DESCRIPTION 
  "Identifies the interface (port) to which this entry's
  information belongs. The value of this variable
  corresponds to ifIndex, as well as most of the other
  port identification values in related MIBs."
  ::= { kxprotoEntry 1 }

 kxprotoBridge OBJECT-TYPE
  SYNTAX  INTEGER { 
      transparent(1),
      none(4)
  }
  ACCESS  read-write
  STATUS  mandatory
  DESCRIPTION 
  "Defines the bridging method to be applied to frames
  received at, or destined for, this port. Ports may be
  configured for transparent or none. The UART may only
  be configured to none." 
  ::= { kxprotoEntry 2 }

 kxprotoSuppressBpdu OBJECT-TYPE
  SYNTAX  INTEGER { 
      normal(1),
      suppressed(2)
  }
  ACCESS  read-write
  STATUS  mandatory
  DESCRIPTION 
  "Allows transmission of spanning tree protocol packets
  to be suppressed.  If normal(1), 802.1d spanning tree
  packets are transmitted as usual. If suppressed(2),
  these packets are not transmitted. This option may be
  needed for interoperability with non-802.1d spanning
  tree protocols (e.g., DEC LanBridge 100)."
  ::= { kxprotoEntry 3 }

 kxprotoRipListen OBJECT-TYPE
  SYNTAX  INTEGER {
      enabled(1),
      disabled(2)
  }
  ACCESS  read-write
  STATUS  mandatory
  DESCRIPTION 
  "Specifies whether the port should listen for internet
  Routing Information Protocol (RFC-1058) packets, in
  order to build the routing table for the unit."
  ::= { kxprotoEntry 4 }

 kxprotoTrunking OBJECT-TYPE
  SYNTAX  INTEGER {
      enabled(1),
      disabled(2)
  }
  ACCESS  read-write
  STATUS  mandatory
  DESCRIPTION 
  "Specifies whether SmartStack trunking protocol (an
  extension to the standard Spanning Tree) is to be
  used over this port."
  ::= { kxprotoEntry 5 }

 --  Trunking Group


 kxtrunkTable OBJECT-TYPE
  SYNTAX SEQUENCE OF KxtrunkEntry
  ACCESS not-accessible
  STATUS mandatory
  DESCRIPTION
  "This table describes the trunking status and attributes of
   the interfaces that are configured for bridge trunking."
  ::= { kxtrunk 1 }

 kxtrunkEntry OBJECT-TYPE
  SYNTAX KxtrunkEntry
  ACCESS not-accessible
  STATUS mandatory
  DESCRIPTION
  "An entry exists in this table for each physical interface
   (port) that is configured for trunking."
  INDEX { kxtrunkIfIndex }
  ::= { kxtrunkTable 1 }

 KxtrunkEntry ::= SEQUENCE {
  kxtrunkIfIndex
   INTEGER,
  kxtrunkState
   INTEGER,
  kxtrunkRemoteBridgeAddr
   OCTET STRING,
  kxtrunkRemoteIp
   IpAddress,
  kxtrunkLastError
   INTEGER,
  kxtrunkLinkOrdinal
   INTEGER,
  kxtrunkLinkCount
   INTEGER,
  kxtrunkLastChange
   INTEGER
  }

 kxtrunkIfIndex OBJECT-TYPE
  SYNTAX INTEGER
  ACCESS read-only
  STATUS mandatory
  DESCRIPTION
  "Identifies a physical interface (port) which is
  configured for LAN trunking. The value of this variable
  corresponds to ifIndex, as well as most of the other
  port identification values in related MIBs."
  ::= { kxtrunkEntry 1 }

 kxtrunkState OBJECT-TYPE
  SYNTAX INTEGER { 
      off(1),
      closed(2),
      oneway(3),
      joined(4),
      perturbed(5),
      helddown(6),
      disabled(7)
  }
  ACCESS read-only
  STATUS mandatory
  DESCRIPTION
  "If off(1) then this link has not been enabled for
  trunking. If closed(2) then this link has not yet
  received any Trunking PDUs. If oneway(3) then incoming
  Trunking PDUs do not indicate that our PDUs are being
  successfully received by the far end. If joined(4)
  then this link is actively participating in the trunk
  group. If perturbed(5) then this link is actively
  participating in the trunk group;  however, the
  transmission of data packets has been temporarily
  stopped due to a change in membership of the group.
  If helddown(6) then an error has been detected and the
  link is being held out-of-service until the error
  clears.  If broken(7) then this link has been
  configured for trunking, but the port is physically 
     non-operational."
  ::= { kxtrunkEntry 2 }

 kxtrunkRemoteBridgeAddr OBJECT-TYPE
  SYNTAX OCTET STRING
  ACCESS read-only
  STATUS mandatory
  DESCRIPTION
  "The MAC address portion of the bridge ID of the remote 
  bridge."
  ::= { kxtrunkEntry 3 }

 kxtrunkRemoteIp OBJECT-TYPE
  SYNTAX IpAddress
  ACCESS read-only
  STATUS mandatory
  DESCRIPTION
  "The IP address of the remote bridge, as reported by that
   bridge for administrative purposes."
  ::= { kxtrunkEntry 4 }

 kxtrunkLastError OBJECT-TYPE
  SYNTAX INTEGER { 
      none(1),
      in-bpdu(2),
      multiple-bridges(3),
      ack-lost(4),
      standby(5),
      too-many-groups(6),
      no-ack(7),
      perturbed-threshold(8),
      self-connect(9),
      port-moved(10),
      multiple-lan-types(11)
  }
  ACCESS read-only
  STATUS mandatory
  DESCRIPTION
  "The last reason for failure when the link is in closed, 
  oneway, or helddown state."
  ::= { kxtrunkEntry 5 }

 kxtrunkLinkOrdinal OBJECT-TYPE
  SYNTAX INTEGER
  ACCESS read-only
  STATUS mandatory
  DESCRIPTION
  "The position of this link within the trunk group."
  ::= { kxtrunkEntry 6 }

 kxtrunkLinkCount OBJECT-TYPE
  SYNTAX INTEGER
  ACCESS read-only
  STATUS mandatory
  DESCRIPTION
  "The number of links within the trunk group."
  ::= { kxtrunkEntry 7 }

 kxtrunkLastChange OBJECT-TYPE
  SYNTAX INTEGER
  ACCESS read-only
  STATUS mandatory
  DESCRIPTION
  "The number of seconds since kxtrunkState changed."
  ::= { kxtrunkEntry 8 }

 --  Workgroup Group

 kxWorkGroupNextNumber OBJECT-TYPE
  SYNTAX  INTEGER
  ACCESS  read-only
  STATUS  mandatory
  DESCRIPTION
  "The next available workgroup number to be used.  When
  creating a new workgroup, it is recommended to read
  the value of the variable and use it to key into the
  workgroup table."
  ::= { kxworkgroup 1 }

 kxWorkGroupCurrentCount OBJECT-TYPE
  SYNTAX  INTEGER
  ACCESS  read-only
  STATUS  mandatory
  DESCRIPTION
  "The total number of workgroups currently defined."
  ::= { kxworkgroup 2 }

 kxWorkGroupMaxCount OBJECT-TYPE
  SYNTAX  INTEGER
  ACCESS  read-only
  STATUS  mandatory
  DESCRIPTION
  "The maximum number of workgroups allowed."
  ::= { kxworkgroup 3 }

 kxWorkGroupTable OBJECT-TYPE
  SYNTAX  SEQUENCE OF KxWorkGroupEntry
  ACCESS  not-accessible
  STATUS  mandatory
  DESCRIPTION
  "This table contains work group definitions for the
  interfaces."
  ::= { kxworkgroup 4 }

 kxWorkGroupEntry OBJECT-TYPE
  SYNTAX  KxWorkGroupEntry
  ACCESS  not-accessible
  STATUS  mandatory
  DESCRIPTION
  "Each entry in this table contains a definition of a
  work group."
  INDEX   { kxWorkGroupNumber }
  ::= { kxWorkGroupTable 1 }

 KxWorkGroupEntry ::= SEQUENCE {
  kxWorkGroupNumber
   INTEGER,
  kxWorkGroupName
   DisplayString,
  kxWorkGroupPorts
   OCTET STRING,
  kxWorkGroupType
   INTEGER
  }

 kxWorkGroupNumber OBJECT-TYPE
  SYNTAX  INTEGER
  ACCESS  read-write
  STATUS  mandatory
  DESCRIPTION
  "An integer that identifies the work group, used as an
  index to this table."
  ::= { kxWorkGroupEntry 1 }

 kxWorkGroupName OBJECT-TYPE
  SYNTAX  DisplayString
  ACCESS  read-write
  STATUS  mandatory
  DESCRIPTION
  "A 1-16 character work group name."
  ::= { kxWorkGroupEntry 2 }    

 kxWorkGroupPorts OBJECT-TYPE
  SYNTAX  OCTET STRING
  ACCESS  read-write
  STATUS  mandatory
  DESCRIPTION
  "A list of all ports within the group.  The first
  octet specified ports 1-8, the second 9-16, etc."
  ::= { kxWorkGroupEntry 3 }    

 kxWorkGroupType OBJECT-TYPE
  SYNTAX  INTEGER {
      all(3), -- all broadcast packets
      invalid(4) -- to delete this group
  }
  ACCESS  read-write
  STATUS  mandatory
  DESCRIPTION
  "The type of work group: all - no additional
  information needs to be supplied."
  ::= { kxWorkGroupEntry 4 }    

 --  Trap Group

 kxtrapControlTable OBJECT-TYPE
  SYNTAX  SEQUENCE OF KxtrapControlEntry
  ACCESS  not-accessible
  STATUS  mandatory
  DESCRIPTION
  "This table contains information about the severity of
  each trap and whether the trap is currently enabled."
  ::= { kxtrapMgt 1 }         

 kxtrapControlEntry OBJECT-TYPE
  SYNTAX  KxtrapControlEntry
  ACCESS  not-accessible
  STATUS  mandatory
  DESCRIPTION ""
  INDEX   { kxtrapIndex }
  ::= { kxtrapControlTable 1 }

 KxtrapControlEntry ::= SEQUENCE {
  kxtrapIndex
   INTEGER,
  kxtrapEnabled
   INTEGER,
  kxtrapSeverity
   INTEGER,
  kxtrapText
   DisplayString
  }

 kxtrapIndex OBJECT-TYPE
  SYNTAX  INTEGER
  ACCESS  read-only
  STATUS  mandatory
  DESCRIPTION
  "The specific trap number."
  ::= { kxtrapControlEntry 1 }

 kxtrapEnabled OBJECT-TYPE
  SYNTAX  INTEGER {
      true(1),
      false(2)
  }        
  ACCESS  read-write
  STATUS  mandatory
  DESCRIPTION
  "Enable or disable the generation of this trap."
  ::= { kxtrapControlEntry 2 }

 kxtrapSeverity OBJECT-TYPE
  SYNTAX  INTEGER {
      informational(1),
      warning(2),
      minor(3),
      major(4),
      critical(5)
  }
  ACCESS  read-write
  STATUS  mandatory
  DESCRIPTION
  "A user-definable severity, indicating the importance
  of the trap."
  ::= { kxtrapControlEntry 3 }

 kxtrapText OBJECT-TYPE
  SYNTAX  DisplayString
  ACCESS  read-only
  STATUS  mandatory
  DESCRIPTION
  "A description of the trap."
  ::= { kxtrapControlEntry 4 }

 kxtrapSeverityControlTable OBJECT-TYPE
  SYNTAX  SEQUENCE OF KxtrapSeverityControlEntry
  ACCESS  not-accessible
  STATUS  mandatory
  DESCRIPTION
  "This table contains information about whether a class
  of traps of a particular severity is enabled or
  disabled."
  ::= { kxtrapMgt 2 }

 kxtrapSeverityControlEntry OBJECT-TYPE
  SYNTAX  KxtrapSeverityControlEntry
  ACCESS  not-accessible
  STATUS  mandatory
  DESCRIPTION ""
  INDEX   { kxtrapSeverity }
  ::= { kxtrapSeverityControlTable 1 }

 KxtrapSeverityControlEntry ::= SEQUENCE {
  kxtrapSeverityControlSeverity
   INTEGER,
  kxtrapSeverityEnable
   INTEGER
  }

 kxtrapSeverityControlSeverity OBJECT-TYPE
  SYNTAX  INTEGER { 
      informational(1),
      warning(2),
      minor(3),
      major(4),
      critical(5)
  }
  ACCESS  read-write
  STATUS  mandatory
  DESCRIPTION
  "A user-definable severity, indicating the importance
  of the trap."
  ::= { kxtrapSeverityControlEntry 1 }

 kxtrapSeverityEnable OBJECT-TYPE
  SYNTAX  INTEGER { 
      enabled(1),
      disabled(2)
  }
  ACCESS  read-write
  STATUS  mandatory
  DESCRIPTION
  "Enable or disable all traps of a given severity
  level."
  ::= { kxtrapSeverityControlEntry 2 }

 kxtrapIncludeText OBJECT-TYPE
  SYNTAX  INTEGER {
      true(1),
      false(2)
  }
  ACCESS  read-write
  STATUS  mandatory
  DESCRIPTION
  "Whether or not a formatted text string is included in
  the trap PDU."
  ::= { kxtrapMgt 3 }

 kxtrapTime OBJECT-TYPE
  SYNTAX  TimeTicks
  ACCESS  read-write
  STATUS  mandatory
  DESCRIPTION
  "The time, in centiseconds, which should expire
  between the sending of traps."
  -- DEFVAL { 100 }
  ::= { kxtrapMgt 4 }

 kxtrapRetry OBJECT-TYPE
  SYNTAX  INTEGER
  ACCESS  read-write
  STATUS  mandatory
  DESCRIPTION
  "The number of times any enterprise-specific trap is
  to be sent for a given event.  PDUs are retried using
  a truncated exponential backoff: 2 seconds, 4 seconds,
  8 seconds, 16 seconds, and then 32 seconds for all
  succeeding intervals."
  -- DEFVAL { 1 }
  ::= { kxtrapMgt 5 }

 kxtrapNumber OBJECT-TYPE
  SYNTAX  INTEGER
  ACCESS  read-only
  STATUS  mandatory
  DESCRIPTION
  "The number of traps that are in the kxtrapTable."
  ::= { kxtrapMgt 6 }

 kxtrapTable OBJECT-TYPE
  SYNTAX  SEQUENCE OF KxtrapEntry
  ACCESS  not-accessible
  STATUS  mandatory
  DESCRIPTION
  "This table contains the latest traps that have been
  generated."
  ::= { kxtrapMgt 7 }

 kxtrapEntry OBJECT-TYPE
  SYNTAX  KxtrapEntry
  ACCESS  not-accessible
  STATUS  mandatory
  DESCRIPTION ""
  INDEX   { kxtrapEntryIndex }
  ::= { kxtrapTable 1 }

 KxtrapEntry ::= SEQUENCE {
  kxtrapEntryIndex
   INTEGER,
  kxtrapEntryTimeStamp
   TimeTicks,
  kxtrapEntryText
   DisplayString,
  kxtrapEntryNumber
   INTEGER,
  kxtrapEntrySeverity
   INTEGER
  }

 kxtrapEntryIndex OBJECT-TYPE
  SYNTAX  INTEGER
  ACCESS  read-only
  STATUS  mandatory
  DESCRIPTION
  "A number representing the order in which the trap
  occurred in time.  This 32 bit number can wrap."
  ::= { kxtrapEntry 1 }

 kxtrapEntryTimeStamp OBJECT-TYPE
  SYNTAX  TimeTicks
  ACCESS  read-only
  STATUS  mandatory
  DESCRIPTION
  "The time at which the trap occurred."
  ::= { kxtrapEntry 2 }

 kxtrapEntryText OBJECT-TYPE
  SYNTAX  DisplayString
  ACCESS  read-only
  STATUS  mandatory
  DESCRIPTION
  "A description of the trap."
  ::= { kxtrapEntry 3 }

 kxtrapEntryNumber OBJECT-TYPE
  SYNTAX  INTEGER
  ACCESS  read-only
  STATUS  mandatory
  DESCRIPTION
  "The specific trap number, as specified in the TRAP
  PDU."
  ::= { kxtrapEntry 4 }

 kxtrapEntrySeverity OBJECT-TYPE
  SYNTAX  INTEGER { 
      informational(1),
      warning(2),
      minor(3),
      major(4),
      critical(5)
  }
  ACCESS  read-only
  STATUS  mandatory
  DESCRIPTION
  "A user-definable severity, indicating the importance
  of the trap."
  ::= { kxtrapEntry 5 }


 -- Mirror Group

 kxmirrorMode OBJECT-TYPE
  SYNTAX INTEGER { 
      off(1), 
      tx(2), 
      rx(3), 
      rxandtx (4)
  }
  ACCESS read-write
  STATUS mandatory
  DESCRIPTION
  "To turn off port mirroring, or turn on by specifying
  rx, tx, or (rxandtx) which is the type of data to be
  mirrored."
  ::= { kxmirrorgroup 1 }

 kxmirrorDiagPort OBJECT-TYPE
  SYNTAX INTEGER 
  ACCESS read-write
  STATUS mandatory
  DESCRIPTION
  "This entry identifies the diagnostic port to which
  mirrored packet will be destined."
  ::= { kxmirrorgroup 2 }

 kxmirrorTargetPortLists OBJECT-TYPE
  SYNTAX OCTET STRING
  ACCESS read-write
  STATUS mandatory
  DESCRIPTION
  "An octet string specifies the list of ports to be
  mirrored.  The first octet specifies ports 1-8 and
  the second 9-16."
  ::= { kxmirrorgroup 3 }

 -- Enterprise Specific Traps for the ELS100

 kxPortFunctionsTrap TRAP-TYPE 
  ENTERPRISE  sysObjectID
  VARIABLES   {
      kxtrapSeverity,
      kxifFunction
  }
  DESCRIPTION
  "Sent whenever the current functional state (active 
  protocols) of the port has changed."
  ::= 1

 kxRxQueuesTrap TRAP-TYPE
  ENTERPRISE  sysObjectID
  VARIABLES   {
      kxtrapSeverity,
      kxifRxQueueThreshTime 
  }
  DESCRIPTION
  "Sent whenever the number of times that the port's
  receiver has stopped receiving packets due to buffer
  space shortages has exceeded the port's limit." 
  ::= 2

 kxTxStormFlagTrap TRAP-TYPE
  ENTERPRISE  sysObjectID
  VARIABLES   {
      kxtrapSeverity 
  }
  DESCRIPTION
  "Sent whenever multicast storm protection has been
  invoked for the port."
  ::= 3

 kxTxCongestsTrap TRAP-TYPE
  ENTERPRISE  sysObjectID
  VARIABLES   {
      kxtrapSeverity,
      kxadminNAMReceiveCongests
  }
  DESCRIPTION
  "Sent whenever packets destined for the unit itself
  were discarded due to lack of buffer space."
  ::= 4

 kxTrunkStateTrap TRAP-TYPE
  ENTERPRISE sysObjectID
  VARIABLES {
      kxtrapSeverity,
      kxtrunkState
  }
  DESCRIPTION
  "A trunking state change transition has occurred. The
  possible transitions are:
     Closed-Oneway
     Oneway-Perturbed
     Perturbed-Joined
     Joined-Helddown
     Closed-Helddown
     Oneway-Helddown
     Perturbed-Helddown"
  ::= 5

 kxTrunkBridgeAddrTrap TRAP-TYPE
  ENTERPRISE sysObjectID
  VARIABLES {
      kxtrapSeverity,
      kxtrunkRemoteBridgeAddr
  }
  DESCRIPTION
  "The associated trunking MAC address of the bridge ID
  of the remote bridge has changed."
  ::= 6

 kxTrunkIPAddrTrap TRAP-TYPE
  ENTERPRISE sysObjectID
  VARIABLES {
      kxtrapSeverity,
      kxtrunkRemoteIp
  }
  DESCRIPTION
  "The associated trunking IP address of the remote
  bridge has changed."
  ::= 7

 kxTrunkErrorTrap TRAP-TYPE
  ENTERPRISE sysObjectID
  VARIABLES {
      kxtrapSeverity,
      kxtrunkLastError
  }
  DESCRIPTION
  "An error has occurred in trunking."
  ::= 8 

 kxTrunkLinkOrdinalTrap TRAP-TYPE
  ENTERPRISE sysObjectID
  VARIABLES {
      kxtrapSeverity,
      kxtrunkLinkOrdinal
  }
  DESCRIPTION
  "The port's index in the trunking group has changed."
  ::= 9 

 kxTrunkLinkCountTrap TRAP-TYPE
  ENTERPRISE sysObjectID
  VARIABLES {
      kxtrapSeverity,
      kxtrunkLinkCount
  }
  DESCRIPTION
  "The number of ports in the trunking group has
  changed."
  ::= 10

 kxDiagUnitBootedTrap TRAP-TYPE
  ENTERPRISE  sysObjectID
  VARIABLES   { 
      kxtrapSeverity,
      kxadminFatalErr
  }
  DESCRIPTION
  "The unit has booted. kxadminFatalErr contains
  information about why the unit rebooted."
  ::= 11

 kxStorageFailureTrap TRAP-TYPE
  ENTERPRISE  sysObjectID
  VARIABLES   {
      kxtrapSeverity
  }
  DESCRIPTION
  "Sent if the unit's Configuration EEPROM has
  failed. The unit will not be able to reboot, and must
  be returned to the factory."
  ::= 12

 kxIfErrorsTrap TRAP-TYPE
  ENTERPRISE  sysObjectID
  VARIABLES   {
      kxtrapSeverity,
      ifInErrors,
      ifOutErrors
  }
  DESCRIPTION
  "Sent whenever the number of hardware errors in
  received and transmitted packets has exceeded the
  port's limit." 
  ::= 13 

END
