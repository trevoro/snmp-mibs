-- 
-- Copyright 1999 by Fore Systems, Inc. 
-- Converted to SMIv2 rfc 2578,2579,2580 - STD 58
--
-- Copyright 1993-1995 by Fore Systems, Inc.

Fore-Adapter-MIB DEFINITIONS ::= BEGIN

IMPORTS
	Counter32, Gauge32,
        TimeTicks, IpAddress, Integer32,	
	OBJECT-TYPE,
	MODULE-IDENTITY				FROM SNMPv2-SMI
	DisplayString,
        RowStatus                               FROM SNMPv2-TC
	systems, SpansAddress, NsapAddr,
	EntryStatus                             FROM Fore-Common-MIB;

------------------------------------------------------------------------
-- MIB Groups

atmAdapter MODULE-IDENTITY
          LAST-UPDATED         "9911050000Z"
          ORGANIZATION         "FORE"
          CONTACT-INFO         
               "      Postal:   FORE Systems Inc.
                                 1000 FORE Drive
                                 Warrendale, PA 15086-7502
                       Tel:      +1 724 742 6900
                       Email:    nm_mibs@fore.com
                       Web:      http://www.fore.com"
          DESCRIPTION "Fore Atm Adapter MIB"
          ::= { systems 1 }

adapterGroup		OBJECT IDENTIFIER ::= { atmAdapter 1 }
phyLayerGroup		OBJECT IDENTIFIER ::= { atmAdapter 2 }
atmLayerGroup		OBJECT IDENTIFIER ::= { atmAdapter 3 }
aalGroup		OBJECT IDENTIFIER ::= { atmAdapter 4 }
connGroup		OBJECT IDENTIFIER ::= { atmAdapter 5 }
sonetGroup		OBJECT IDENTIFIER ::= { atmAdapter 6 }
sonetAdapterConfGroup	OBJECT IDENTIFIER ::= { sonetGroup 1 }
sonetAdapterStatsGroup	OBJECT IDENTIFIER ::= { sonetGroup 2 }
statsGroup		OBJECT IDENTIFIER ::= { atmAdapter 7 }
atmIpGroup		OBJECT IDENTIFIER ::= { atmAdapter 8 }
atmarpGroup		OBJECT IDENTIFIER ::= { atmIpGroup 1 }
classicalIpGroup	OBJECT IDENTIFIER ::= { atmIpGroup 2 }
ipFilterGroup           OBJECT IDENTIFIER ::= { atmIpGroup 3 }
ipFilterConfGroup       OBJECT IDENTIFIER ::= { ipFilterGroup 1 }
ipFilterStatsGroup      OBJECT IDENTIFIER ::= { ipFilterGroup 2 }

------------------------------------------------------------------------
-- The Adapter Group

adapterTable OBJECT-TYPE
	SYNTAX	SEQUENCE OF AdapterEntry
	MAX-ACCESS	not-accessible
	STATUS	current
	DESCRIPTION
		"A table of adapter information."
	::= { adapterGroup 1 }

adapterEntry OBJECT-TYPE
	SYNTAX	AdapterEntry
	MAX-ACCESS	not-accessible
	STATUS	current
	DESCRIPTION
		"A table entry containing adapter information."
	INDEX	{ adapterInterface }
	::= { adapterTable 1 }

AdapterEntry ::=
	SEQUENCE {
		adapterInterface		Integer32,
		adapterSerialNumber		Integer32,
		adapterHardwareVersion		Integer32,
		adapterHardwareSpeed		Integer32,
		adapterFirmwareVersion		Integer32,
		adapterSoftwareVersion		Integer32,
		adapterTransmitBufferSize	Integer32,
		adapterTransmitQueueLength	Gauge32,
		adapterReceiveBufferSize	Integer32,
		adapterReceiveQueueLength	Gauge32,
		adapterOperStatus		INTEGER,
		adapterCarrier			INTEGER,
		adapterAddress			SpansAddress,
		adapterUptime			TimeTicks,
		adapterPhyLayer			INTEGER,
		adapterType			INTEGER,
		adapterFirmwareVersionText	DisplayString,
		adapterSoftwareVersionText	DisplayString
	}

adapterInterface OBJECT-TYPE
	SYNTAX	Integer32
	MAX-ACCESS	read-only
	STATUS	current
	DESCRIPTION
		"The ifIndex corresponding to this ATM adapter."
	::= { adapterEntry 1 }

adapterSerialNumber OBJECT-TYPE
	SYNTAX	Integer32
	MAX-ACCESS	read-only
	STATUS	current
	DESCRIPTION
		"The serial number of the ATM adapter hardware."
	::= { adapterEntry 2 }

adapterHardwareVersion OBJECT-TYPE
	SYNTAX	Integer32
	MAX-ACCESS	read-only
	STATUS	current
	DESCRIPTION
		"The version of the ATM adapter hardware.
		The version number is encoded into 6 hex digits.
		For example, version 1.1 is encoded as 0x010100."
	::= { adapterEntry 3 }

adapterHardwareSpeed OBJECT-TYPE
	SYNTAX	Integer32
	MAX-ACCESS	read-only
	STATUS	current
	DESCRIPTION
		"The speed of the ATM adapter hardware."
	::= { adapterEntry 4 }

adapterFirmwareVersion OBJECT-TYPE
	SYNTAX	Integer32
	MAX-ACCESS	read-only
	STATUS	current
	DESCRIPTION
		"The version of the ATM adapter firmware.
		The version number is encoded into 6 hex digits.
		For example, version 1.1 is encoded as 0x010100."
	::= { adapterEntry 5 }

adapterSoftwareVersion OBJECT-TYPE
	SYNTAX	Integer32
	MAX-ACCESS	read-only
	STATUS	current
	DESCRIPTION
		"The version of the ATM adapter software.
		The version number is encoded into 6 hex digits.
		For example, version 2.2.0 is encoded as 0x020200."
	::= { adapterEntry 6 }

adapterTransmitBufferSize OBJECT-TYPE
	SYNTAX	Integer32
	MAX-ACCESS	read-only
	STATUS	current
	DESCRIPTION
		"The size of the transmit buffer, in cells."
	::= { adapterEntry 7 }

adapterTransmitQueueLength OBJECT-TYPE
	SYNTAX	Gauge32
	MAX-ACCESS	read-only
	STATUS	current
	DESCRIPTION
		"The number of cells in the transmit buffer."
	::= { adapterEntry 8 }

adapterReceiveBufferSize OBJECT-TYPE
	SYNTAX	Integer32
	MAX-ACCESS	read-only
	STATUS	current
	DESCRIPTION
		"The size of the receive buffer, in cells."
	::= { adapterEntry 9 }

adapterReceiveQueueLength OBJECT-TYPE
	SYNTAX	Gauge32
	MAX-ACCESS	read-only
	STATUS	current
	DESCRIPTION
		"The number of cells in the receive buffer."
	::= { adapterEntry 10 }

adapterOperStatus OBJECT-TYPE
	SYNTAX	INTEGER {
			other(1),
			enabled(2),
			disabled(3)
		}
	MAX-ACCESS	read-only
	STATUS	current
	DESCRIPTION
		"The current operational state of the adapter."
	::= { adapterEntry 11 }

adapterCarrier OBJECT-TYPE
	SYNTAX	INTEGER {
			carrier(1),
			noCarrier(2)
		}
	MAX-ACCESS	read-only
	STATUS	current
	DESCRIPTION
		"The presence or absence of carrier on the link."
	::= { adapterEntry 12 }

adapterAddress OBJECT-TYPE
	SYNTAX	SpansAddress
	MAX-ACCESS	read-only
	STATUS	current
	DESCRIPTION
		"The address of this ATM adapter."
	::= { adapterEntry 13 }

adapterUptime OBJECT-TYPE
	SYNTAX	TimeTicks
	MAX-ACCESS	read-only
	STATUS	current
	DESCRIPTION
		"The length of time this ATM adapter has been up,
		in hundredths of a second."
	::= { adapterEntry 14 }

adapterPhyLayer OBJECT-TYPE
	SYNTAX	INTEGER {
			phy-4B5B-MMODE-100(1),
			phy-4B5B-MMODE-140(2),
			phy-ASX-100(3),
			phy-OC3-MMODE-ST(4),
			phy-OC3-MMODE-SC(5),
			phy-4B5B-SMODE-100(6),
			phy-4B5B-SMODE-140(7),
			phy-OC3-SMODE-SHORT(8),
			phy-OC3-SMODE-LONG(9),
			phy-UTP5-SONET(10),
			phy-STP1-SONET(11)
		}
	MAX-ACCESS	read-only
	STATUS	current
	DESCRIPTION
		"The physical layer of the adapter."
	::= { adapterEntry 15 }

adapterType OBJECT-TYPE
	SYNTAX	INTEGER {
			type-SBA-100(1),
			type-GIA-100(2),
			type-TCA-100(3),
			type-NXA-100(4),
			type-ASX-100(5),
			type-SBA-200(6),
			type-VMA-200(7),
			type-ESA-200(8),
			type-MCA-200(9),	
			type-ASX-200(10),
			type-HPA-200(11),
			type-ESA-200PC(12),
			type-NBA-200(13),
			type-PCA-200(14),
			type-GIA-200(15),
			type-SBA-200e(16),
			type-ESA-200e(17),
			type-GIA-200e(18),
			type-PCA-200e(19),
			type-LANNET(20),
			type-VMA-200e(21),
			type-MCA-200e(22)
		}
	MAX-ACCESS	read-only
	STATUS	current
	DESCRIPTION
		"The hardware type of the adapter."
	::= { adapterEntry 16 }

adapterFirmwareVersionText OBJECT-TYPE
	SYNTAX	DisplayString
	MAX-ACCESS	read-only
	STATUS	current
	DESCRIPTION
		"The version of the ATM adapter firmware. This object
		provides text information about the internal software
		configuration that was used when the firmware was built."
	::= { adapterEntry 17 }

adapterSoftwareVersionText OBJECT-TYPE
	SYNTAX	DisplayString
	MAX-ACCESS	read-only
	STATUS	current
	DESCRIPTION
		"The version of the ATM adapter software. This object
		provides text information about the internal software
		configuration that was used when the ATM adapter software
		was built."
	::= { adapterEntry 18 }

------------------------------------------------------------------------
-- 
-- CASE diagrams are shown for each layer.  
-- 
-- The physical layer.
-- Other physical layers (OC-3) would be similar.
-- 
-- <Receive interrupt>
--    |
--    +==> phyLayerFramingErrors
--    |
--    +==> phyLayerHeaderCRCErrors
--    |
--    v
-- <Pass cell to ATM layer>
-- 
------------------------------------------------------------------------
-- The Physical Layer Group

phyLayerTable OBJECT-TYPE
	SYNTAX	SEQUENCE OF PhyLayerEntry
	MAX-ACCESS	not-accessible
	STATUS	current
	DESCRIPTION
		"A table of adapter physical layer information."
	::= { phyLayerGroup 1 }

phyLayerEntry OBJECT-TYPE
	SYNTAX	PhyLayerEntry
	MAX-ACCESS	not-accessible
	STATUS	current
	DESCRIPTION
		"A table entry containing adapter physical layer information."
	INDEX	{ phyLayerInterface }
	::= { phyLayerTable 1 }

PhyLayerEntry ::=
	SEQUENCE {
		phyLayerInterface		Integer32,
		phyLayerFramingErrors		Counter32,
		phyLayerHeaderCRCErrors		Counter32
	}

phyLayerInterface OBJECT-TYPE
	SYNTAX	Integer32
	MAX-ACCESS	read-only
	STATUS	current
	DESCRIPTION
		"This object identifies the ATM adapter."
	::= { phyLayerEntry 1 }

phyLayerFramingErrors OBJECT-TYPE
	SYNTAX	Counter32
	MAX-ACCESS	read-only
	STATUS	current
	DESCRIPTION
		"The number of ATM cells received
		with incorrect physical layer framing."
	::= { phyLayerEntry 2 }

phyLayerHeaderCRCErrors OBJECT-TYPE
	SYNTAX	Counter32
	MAX-ACCESS	read-only
	STATUS	current
	DESCRIPTION
		"The number of ATM cells received
		with bad header CRCs."
	::= { phyLayerEntry 3 }


--------------------------------------------------------------------------
-- 
-- The ATM layer.
-- 
-- <ATM layer: cell passed in from a physical layer>
--    |
-- atmReceivedCells
--    |
--    +==> atmOutOfRangeVPIs
--    |
--    +==> atmUnconnectedVPIs
--    |
--    +==> atmOutOfRangeVCIs
--    |
--    +==> atmUnconnectedVCIs
--    |
--    +==> <Pass cell to AAL0 layer>
--    |
--    +==> <Pass cell to AAL4-SAR sublayer>
--    |
--    +==> <Pass cell to AAL5-SAR sublayer>
-- 
------------------------------------------------------------------------
-- The ATM Layer Group

atmLayerTable OBJECT-TYPE
	SYNTAX	SEQUENCE OF AtmLayerEntry
	MAX-ACCESS	not-accessible
	STATUS	current
	DESCRIPTION
		"A table of ATM layer information."
	::= { atmLayerGroup 1 }

atmLayerEntry OBJECT-TYPE
	SYNTAX	AtmLayerEntry
	MAX-ACCESS	not-accessible
	STATUS	current
	DESCRIPTION
		"A table entry containing ATM layer information."
	INDEX	{ atmInterface }
	::= { atmLayerTable 1 }

AtmLayerEntry ::=
	SEQUENCE {
		atmInterface		Integer32,
		atmTransmittedCells	Counter32,
		atmReceivedCells	Counter32,
		atmOutOfRangeVPIs	Counter32,
		atmUnconnectedVPIs	Counter32,
		atmOutOfRangeVCIs	Counter32,
		atmUnconnectedVCIs	Counter32
	}

atmInterface OBJECT-TYPE
	SYNTAX	Integer32
	MAX-ACCESS	read-only
	STATUS	current
	DESCRIPTION
		"This object identifies the ATM interface."
	::= { atmLayerEntry 1 }

atmTransmittedCells OBJECT-TYPE
	SYNTAX	Counter32
	MAX-ACCESS	read-only
	STATUS	current
	DESCRIPTION
		"The number of ATM cells transmitted."
	::= { atmLayerEntry 2 }

atmReceivedCells OBJECT-TYPE
	SYNTAX	Counter32
	MAX-ACCESS	read-only
	STATUS	current
	DESCRIPTION
		"The number of ATM cells received."
	::= { atmLayerEntry 3 }

atmOutOfRangeVPIs OBJECT-TYPE
	SYNTAX	Counter32
	MAX-ACCESS	read-only
	STATUS	current
	DESCRIPTION
		"The number of ATM cells received
		with VPI values that were out of range."
	::= { atmLayerEntry 4 }

atmUnconnectedVPIs OBJECT-TYPE
	SYNTAX	Counter32
	MAX-ACCESS	read-only
	STATUS	current
	DESCRIPTION
		"The number of ATM cells received
		with VPI values that were in range
		but did not correspond to active connections."
	::= { atmLayerEntry 5 }

atmOutOfRangeVCIs OBJECT-TYPE
	SYNTAX	Counter32
	MAX-ACCESS	read-only
	STATUS	current
	DESCRIPTION
		"The number of ATM cells received
		with VCI values that were out of range."
	::= { atmLayerEntry 6 }

atmUnconnectedVCIs OBJECT-TYPE
	SYNTAX	Counter32
	MAX-ACCESS	read-only
	STATUS	current
	DESCRIPTION
		"The number of ATM cells received
		with VCI values that were in range
		but did not correspond to active connections."
	::= { atmLayerEntry 7 }


------------------------------------------------------------------------
-- 
-- The AAL4-SAR and AAL4-CS sublayers.
-- 
-- <AAL4-SAR sublayer: cell passed in from ATM layer>
--    |
-- aal4ReceivedCells
--    |
--    +==> aal4PayloadCRCErrors
--    |
--    +==> aal4SARProtocolErrors
--    |
--    +==> aal4CellsDiscards
--    |
--    v
-- <Pass CS-PDU to AAL4-CS sublayer>
-- 
-- 
-- <AAL4-CS sublayer: CS-PDU passed in from AAL4-SAR sublayer>
--    |
-- aal4ReceivedPDUs
--    |
--    +==> aal4CSProtocolErrors
--    |
--    +==> aal4PDUsDiscards
--    |
--    v
-- <Pass packet to receiver>
-- 

------------------------------------------------------------------------
-- The ATM Adaptation Layer Group

aal4Table OBJECT-TYPE
	SYNTAX	SEQUENCE OF Aal4Entry
	MAX-ACCESS	not-accessible
	STATUS	current
	DESCRIPTION
		"A table of ATM adaptation layer type 3/4 information."
	::= { aalGroup 1 }

aal4Entry OBJECT-TYPE
	SYNTAX	Aal4Entry
	MAX-ACCESS	not-accessible
	STATUS	current
	DESCRIPTION
		"A table entry containing ATM adaptation layer type 3/4 information."
	INDEX	{ aal4Interface }
	::= { aal4Table 1 }

Aal4Entry ::=
	SEQUENCE {
		aal4Interface		Integer32,
		aal4TransmittedCells	Counter32,
		aal4ReceivedCells	Counter32,
		aal4TransmittedPDUs	Counter32,
		aal4ReceivedPDUs	Counter32,
		aal4PayloadCRCErrors	Counter32,
		aal4SARProtocolErrors	Counter32,
		aal4CSProtocolErrors	Counter32,
		aal4CellsDiscards	Counter32,
		aal4PDUsDiscards	Counter32
	}

aal4Interface OBJECT-TYPE
	SYNTAX	Integer32
	MAX-ACCESS	read-only
	STATUS	current
	DESCRIPTION
		"This object identifies the ATM interface."
	::= { aal4Entry 1 }

aal4TransmittedCells OBJECT-TYPE
	SYNTAX	Counter32
	MAX-ACCESS	read-only
	STATUS	current
	DESCRIPTION
		"The number of AAL type 4 cells transmitted."
	::= { aal4Entry 2 }

aal4ReceivedCells OBJECT-TYPE
	SYNTAX	Counter32
	MAX-ACCESS	read-only
	STATUS	current
	DESCRIPTION
		"The number of AAL type 4 cells received."
	::= { aal4Entry 3 }

aal4TransmittedPDUs OBJECT-TYPE
	SYNTAX	Counter32
	MAX-ACCESS	read-only
	STATUS	current
	DESCRIPTION
		"The number of AAL type 4 protocol data units (PDUs) transmitted."
	::= { aal4Entry 4 }

aal4ReceivedPDUs OBJECT-TYPE
	SYNTAX	Counter32
	MAX-ACCESS	read-only
	STATUS	current
	DESCRIPTION
		"The number of AAL type 4 protocol data units (PDUs) received."
	::= { aal4Entry 5 }

aal4PayloadCRCErrors OBJECT-TYPE
	SYNTAX	Counter32
	MAX-ACCESS	read-only
	STATUS	current
	DESCRIPTION
		"The number of ATM cells received with payload CRC errors."
	::= { aal4Entry 6 }

aal4SARProtocolErrors OBJECT-TYPE
	SYNTAX	Counter32
	MAX-ACCESS	read-only
	STATUS	current
	DESCRIPTION
		"The number of ATM cells that the adaptation layer 
		rejected due to SAR layer protocol errors."
	::= { aal4Entry 7 }

aal4CSProtocolErrors OBJECT-TYPE
	SYNTAX	Counter32
	MAX-ACCESS	read-only
	STATUS	current
	DESCRIPTION
		"The number of ATM cells that the adaptation layer 
		rejected due to CS layer protocol errors."
	::= { aal4Entry 8 }

aal4CellsDiscards OBJECT-TYPE
	SYNTAX	Counter32
	MAX-ACCESS	read-only
	STATUS	current
	DESCRIPTION
		"The number of ATM cells that the adaptation layer discarded
		in the course of dropping partially reassembled PDUs."
	::= { aal4Entry 9 }

aal4PDUsDiscards OBJECT-TYPE
	SYNTAX	Counter32
	MAX-ACCESS	read-only
	STATUS	current
	DESCRIPTION
		"The number of CS-PDUs that the adaptation layer discarded
		due to queue overflows."
	::= { aal4Entry 10 }

------------------------------------------------------------------------
-- 
-- The AAL5-SAR and AAL5-CPCS sublayers.
-- 
-- <AAL5-SAR sublayer: cell passed in from ATM layer>
--    |
-- aal5ReceivedCells
--    |
--    v
-- <Pass cell to AAL5-CPCS sublayer>
-- 
-- <AAL5-CPCS sublayer: cell passed in from AAL5-SAR layer>
--    |
--    +==> aal5CellsDiscards
--    |
--    v
-- <Pass CS-PDU to AAL5-CS sublayer>
-- 
-- <AAL5-CS sublayer: CS-PDU passed in from AAL5-SAR sublayer>
--    |
-- aal5ReceivedPDUs
--    |
--    +==> aal5CSProtocolErrors
--    |
--    +==> aal5CRCErrors
--    |
--    +==> aal5PDUsDiscards
--    |
--    v
-- <Pass packet to receiver>
-- 
------------------------------------------------------------------------

aal5Table OBJECT-TYPE
	SYNTAX	SEQUENCE OF Aal5Entry
	MAX-ACCESS	not-accessible
	STATUS	current
	DESCRIPTION
		"A table of ATM adaptation layer type 5 information."
	::= { aalGroup 2 }

aal5Entry OBJECT-TYPE
	SYNTAX	Aal5Entry
	MAX-ACCESS	not-accessible
	STATUS	current
	DESCRIPTION
		"A table entry containing ATM adaptation layer type 5 information."
	INDEX	{ aal5Interface }
	::= { aal5Table 1 }

Aal5Entry ::=
	SEQUENCE {
		aal5Interface		Integer32,
		aal5TransmittedCells	Counter32,
		aal5ReceivedCells	Counter32,
		aal5TransmittedPDUs	Counter32,
		aal5ReceivedPDUs	Counter32,
		aal5CRCErrors		Counter32,
		aal5CSProtocolErrors	Counter32,
		aal5CellsDiscards	Counter32,
		aal5PDUsDiscards	Counter32
	}

aal5Interface OBJECT-TYPE
	SYNTAX	Integer32
	MAX-ACCESS	read-only
	STATUS	current
	DESCRIPTION
		"This object identifies the ATM interface."
	::= { aal5Entry 1 }

aal5TransmittedCells OBJECT-TYPE
	SYNTAX	Counter32
	MAX-ACCESS	read-only
	STATUS	current
	DESCRIPTION
		"The number of AAL type 5 cells transmitted."
	::= { aal5Entry 2 }

aal5ReceivedCells OBJECT-TYPE
	SYNTAX	Counter32
	MAX-ACCESS	read-only
	STATUS	current
	DESCRIPTION
		"The number of AAL type 5 cells received."
	::= { aal5Entry 3 }

aal5TransmittedPDUs OBJECT-TYPE
	SYNTAX	Counter32
	MAX-ACCESS	read-only
	STATUS	current
	DESCRIPTION
		"The number of AAL type 5 protocol data units (PDUs) transmitted."
	::= { aal5Entry 4 }

aal5ReceivedPDUs OBJECT-TYPE
	SYNTAX	Counter32
	MAX-ACCESS	read-only
	STATUS	current
	DESCRIPTION
		"The number of AAL type 5 protocol data units received."
	::= { aal5Entry 5 }

aal5CRCErrors OBJECT-TYPE
	SYNTAX	Counter32
	MAX-ACCESS	read-only
	STATUS	current
	DESCRIPTION
		"The number of CS-PDUs received with protocol data unit 
		CRC errors."
	::= { aal5Entry 6 }

aal5CSProtocolErrors OBJECT-TYPE
	SYNTAX	Counter32
	MAX-ACCESS	read-only
	STATUS	current
	DESCRIPTION
		"The number of CS-PDUs that the adaptation layer 
		rejected due to CS layer protocol errors."
	::= { aal5Entry 7 }

aal5CellsDiscards OBJECT-TYPE
	SYNTAX	Counter32
	MAX-ACCESS	read-only
	STATUS	current
	DESCRIPTION
		"The number of ATM cells that the adaptation layer discarded
		in the course of dropping partially reassembled PDUs."
	::= { aal5Entry 8 }

aal5PDUsDiscards OBJECT-TYPE
	SYNTAX	Counter32
	MAX-ACCESS	read-only
	STATUS	current
	DESCRIPTION
		"The number of CS-PDUs that the adaptation layer discarded."
	::= { aal5Entry 9 }

------------------------------------------------------------------------
-- 
-- The AAL0 layer.
-- 
-- <AAL0 layer: cell passed in from ATM layer>
--    |
-- aal0ReceivedCells
--    |
--    +==> aal0CellsDiscards
--    |
--    v
-- <Pass cell to receiver>
-- 
------------------------------------------------------------------------

aal0Table OBJECT-TYPE
	SYNTAX	SEQUENCE OF Aal0Entry
	MAX-ACCESS	not-accessible
	STATUS	current
	DESCRIPTION
		"A table of ATM adaptation layer type 0 (user defined
		adaptation layer) information."
	::= { aalGroup 3 }

aal0Entry OBJECT-TYPE
	SYNTAX	Aal0Entry
	MAX-ACCESS	not-accessible
	STATUS	current
	DESCRIPTION
		"A table entry containing ATM adaptation layer type 0 
		(user defined adaptation layer) information."
	INDEX	{ aal0Interface }
	::= { aal0Table 1 }

Aal0Entry ::=
	SEQUENCE {
		aal0Interface		Integer32,
		aal0TransmittedCells	Counter32,
		aal0ReceivedCells	Counter32,
		aal0CellsDiscards	Counter32
	}

aal0Interface OBJECT-TYPE
	SYNTAX	Integer32
	MAX-ACCESS	read-only
	STATUS	current
	DESCRIPTION
		"This object identifies the ATM interface."
	::= { aal0Entry 1 }

aal0TransmittedCells OBJECT-TYPE
	SYNTAX	Counter32
	MAX-ACCESS	read-only
	STATUS	current
	DESCRIPTION
		"The number of AAL type 0 cells transmitted."
	::= { aal0Entry 2 }

aal0ReceivedCells OBJECT-TYPE
	SYNTAX	Counter32
	MAX-ACCESS	read-only
	STATUS	current
	DESCRIPTION
		"The number of AAL type 0 cells received."
	::= { aal0Entry 3 }

aal0CellsDiscards OBJECT-TYPE
	SYNTAX	Counter32
	MAX-ACCESS	read-only
	STATUS	current
	DESCRIPTION
		"The number of ATM cells that the adaptation layer discarded
		in the course of dropping partially reassembled PDUs."
	::= { aal0Entry 4 }

------------------------------------------------------------------------
-- The Connection Group

connTable OBJECT-TYPE
	SYNTAX	SEQUENCE OF ConnEntry
	MAX-ACCESS	not-accessible
	STATUS	current
	DESCRIPTION
		"A table of information about ATM connections."
	::= { connGroup 1 }

connEntry OBJECT-TYPE
	SYNTAX	ConnEntry
	MAX-ACCESS	not-accessible
	STATUS	current
	DESCRIPTION
		"A table entry containing information about an ATM connection."
	INDEX	{ connInterface, connDirection, connVPI, connVCI }
	::= { connTable 1 }

ConnEntry ::=
	SEQUENCE {
		connInterface		Integer32,
		connDirection		INTEGER,
		connVPI			Integer32,
		connVCI			Integer32,
		connLocalSAP		Integer32,
		connRemoteSAP		Integer32,
		connRemoteAddress	SpansAddress,
		connPeakBandwidth	Integer32,
		connMeanBandwidth	Integer32,
		connMeanBurst		Integer32,
		connUptime		TimeTicks
	}

connInterface OBJECT-TYPE
	SYNTAX	Integer32
	MAX-ACCESS	read-only
	STATUS	current
	DESCRIPTION
		"This object identifies the ATM interface."
	::= { connEntry 1 }

connDirection OBJECT-TYPE
	SYNTAX	INTEGER {
			incoming(1),
			outgoing(2)
		}
	MAX-ACCESS	read-only
	STATUS	current
	DESCRIPTION
		"The direction of this connection."
	::= { connEntry 2 }

connVPI OBJECT-TYPE
	SYNTAX	Integer32
	MAX-ACCESS	read-only
	STATUS	current
	DESCRIPTION
		"The Virtual Path Identifier for this connection."
	::= { connEntry 3 }

connVCI OBJECT-TYPE
	SYNTAX	Integer32
	MAX-ACCESS	read-only
	STATUS	current
	DESCRIPTION
		"The Virtual Channel Identifier for this connection."
	::= { connEntry 4 }

connLocalSAP OBJECT-TYPE
	SYNTAX	Integer32
	MAX-ACCESS	read-only
	STATUS	current
	DESCRIPTION
		"The local SAP for this connection."
	::= { connEntry 5 }

connRemoteSAP OBJECT-TYPE
	SYNTAX	Integer32
	MAX-ACCESS	read-only
	STATUS	current
	DESCRIPTION
		"The remote SAP for this connection."
	::= { connEntry 6 }

connRemoteAddress OBJECT-TYPE
	SYNTAX	SpansAddress
	MAX-ACCESS	read-only
	STATUS	current
	DESCRIPTION
		"The ATM address of the remote end of this connection."
	::= { connEntry 7 }

connPeakBandwidth OBJECT-TYPE
	SYNTAX	Integer32
	MAX-ACCESS	read-only
	STATUS	current
	DESCRIPTION
		"The peak bandwidth for this connection,
		in kilobits per second."
	::= { connEntry 8 }

connMeanBandwidth OBJECT-TYPE
	SYNTAX	Integer32
	MAX-ACCESS	read-only
	STATUS	current
	DESCRIPTION
		"The mean bandwidth for this connection,
		 in kilobits per second."
	::= { connEntry 9 }

connMeanBurst OBJECT-TYPE
	SYNTAX	Integer32
	MAX-ACCESS	read-only
	STATUS	current
	DESCRIPTION
		"The mean burst length for this connection, in kilobits."
	::= { connEntry 10 }

connUptime OBJECT-TYPE
	SYNTAX	TimeTicks
	MAX-ACCESS	read-only
	STATUS	current
	DESCRIPTION
		"The length of time since this connection was created,
		in hundredths of a second."
	::= { connEntry 11 }


------------------------------------------------------------------------
-- The Sonet adapter configuration Group

-- The implementation of the sonetGroup tables is mandatory
-- for all hosts that have SONET/SDH port modules.

-- sonetAdapterConfTable OBJECT-TYPE
-- 	SYNTAX	SEQUENCE OF SonetAdapterConfEntry
-- 	ACCESS	not-accessible
-- 	STATUS	mandatory
-- 	DESCRIPTION
-- 		"A table of SONET adapter configuration information."
-- 	::= { sonetAdapterConfGroup 1 }
-- 
-- sonetAdapterConfEntry OBJECT-TYPE
-- 	SYNTAX	SonetAdapterConfEntry
-- 	ACCESS	not-accessible
-- 	STATUS	mandatory
-- 	DESCRIPTION
-- 		"A table entry containing SONET configuration information
-- 		for each port."
-- 	INDEX	{ sonetAdapterConfInterface }
-- 	::= { sonetAdapterConfTable 1 }
-- 
-- SonetAdapterConfEntry ::=
-- 	SEQUENCE {
-- 		sonetAdapterConfInterface		INTEGER,		
-- 		sonetAdapterLineType			INTEGER,		
-- 		sonetAdapterLineCoding			INTEGER,
-- 		sonetAdapterFramingStandardDefault 	INTEGER,
-- 		sonetAdapterFramingStandardOper 	INTEGER,
-- 		sonetAdapterPathWidth			INTEGER,
-- 		sonetAdapterLoopbackConfig		INTEGER,
-- 		sonetAdapterTxClockSource		INTEGER,
-- 		sonetAdapterRxScrambling		INTEGER,
-- 		sonetAdapterTxScrambling		INTEGER,
-- 		sonetAdapterSectionStatus		INTEGER,
-- 		sonetAdapterLineStatus			INTEGER,
-- 		sonetAdapterPathStatus			INTEGER,
-- 		sonetAdapterIdleUnassignedCells		INTEGER
-- 	}		
-- 
-- sonetAdapterConfInterface OBJECT-TYPE
-- 	SYNTAX	INTEGER
-- 	ACCESS	read-only
-- 	STATUS	mandatory
-- 	DESCRIPTION
-- 		"The ifIndex corresponding to this ATM adapter."
-- 	::= { sonetAdapterConfEntry 1 }
-- 
-- sonetAdapterLineType OBJECT-TYPE
-- 	SYNTAX	INTEGER {
-- 		sonetOther(1), 
-- 		sonetSingleModeShortRange(2), 
-- 		sonetSingleModeMediumRange(3), 
-- 		sonetMultiMode(4), 
-- 		sonetUTP(5), 
-- 		sonetCoax(6)
-- 		} 
-- 	ACCESS	read-only
-- 	STATUS	mandatory
-- 	DESCRIPTION
-- 		"This variable describes the line type for this interface. The line type for
-- 		optical SONET signals may be single-mode (short or long range) or multi-mode 
-- 		fiber. For electrical interfaces, the line type is Unshielded Twisted Pair (UTP) 
-- 		or coax. This variable is defined in the SONET IETF draft photonic 
-- 		table as sonetPhotonicLineType with some different values."
-- 	DEFVAL { 4 }
-- 	::= { sonetAdapterConfEntry 2 }
-- 
-- sonetAdapterLineCoding OBJECT-TYPE
-- 	SYNTAX	INTEGER {
-- 		sonetOther(1), 
-- 		sonetB3ZS(2),
-- 		sonetCMI(3),
-- 		sonetNRZ(4),
-- 		sonetRZ(5)
-- 		}
-- 	ACCESS	read-only
-- 	STATUS	mandatory
-- 	DESCRIPTION
-- 		"This variable describes the line coding for this interface. The B3ZS and CMI 
-- 		are used for electrical SONET signals (STS-1 and STS-3). The Non-Return to 
-- 		Zero (NRZ) and the Return to Zero (RZ) are used for optical SONET signals. 
-- 		This variable is defined in the SONET IETF draft photonic table as 
-- 		sonetPhotonicLineCoding."
-- 	DEFVAL { 4 }
-- 	::= { sonetAdapterConfEntry 3 }
-- 
-- sonetAdapterFramingStandardDefault OBJECT-TYPE
-- 	SYNTAX	INTEGER {
-- 		atmSONET(1), 
-- 		atmSDH(2)
-- 		}
-- 	ACCESS	read-only
-- 	STATUS	mandatory
-- 	DESCRIPTION
-- 		"This variable identify the default value of the framing standard that 
-- 		is used by this port (SONET or SDH)."
-- 	::= { sonetAdapterConfEntry 4 }
-- 
-- sonetAdapterFramingStandardOper OBJECT-TYPE
-- 	SYNTAX	INTEGER {
-- 		atmSONET(1), 
-- 		atmSDH(2)
-- 		}
-- 	ACCESS	read-write
-- 	STATUS	mandatory
-- 	DESCRIPTION
-- 		"This variable identify the operational value of the framing standard that 
-- 		is used by this port (SONET or SDH)."
-- 	::= { sonetAdapterConfEntry 5 }
-- 
-- sonetAdapterPathWidth OBJECT-TYPE
-- 	SYNTAX	INTEGER {
-- 		sts1(1),
-- 		sts3c(2),
-- 		sts9c(3),
-- 		sts12c(4),
-- 		sts24c(5),
-- 		sts48c(6)
-- 	}
-- 	ACCESS	read-only
-- 	STATUS	mandatory
-- 	DESCRIPTION
-- 		"This variable indicates the type of the SONET Path. Assigned types are the 
-- 		STS-Nc Synchronous Payload Envelopes where N=1,3,9,12,24,48. STS-1 is equal 
-- 		to 51.84Mbps, STS-3c is 155.52 Mbps, etc. The SDH transmission rates STM-1 
-- 		(155.52 Mbps), STM-4 (622.08 Mbps) and STM-16 (2488.32 Mbps) are equivalent 
-- 		to SONET rates STS-3, STS-12 and STS-48, respectively. This variable is 
-- 		defined in the SONET IETF draft path configuration table as sonetPathWidth."
-- 	DEFVAL { 2 }
-- 	::= { sonetAdapterConfEntry 6 }
-- 
-- sonetAdapterLoopbackConfig OBJECT-TYPE
-- 	SYNTAX	INTEGER {
-- 		sonetNoLoop(1), 
-- 		sonetLineLoop(2),
-- 		sonetDiagLoop(3),
-- 		sonetOtherLoop(4)
-- 		}
-- 	ACCESS	read-write
-- 	STATUS	mandatory
-- 	DESCRIPTION
-- 		"This variable represents the current loopback status of the SONET interface.
-- 		The possible values are: 
-- 		sonetNoLoop (1) means that the interface is not in a loopback state.
-- 		sonetLineLoop (2) means that the receive data and clock are connected to the 
-- 		transmit data and clock.
-- 		sonetDiagLoop (3) means that the transmit data stream and clock are looped back 
-- 		to the receiver.
-- 		sonetOtherLoop (4) means that the interface is in a loopback that is not defined 
-- 		here."
-- 	DEFVAL { 1 }
-- 	::= { sonetAdapterConfEntry 7 }
-- 
-- sonetAdapterTxClockSource OBJECT-TYPE
-- 	SYNTAX	INTEGER {
-- 		rxTiming(1), 
-- 		localTiming(2)
-- 		}
-- 	ACCESS	read-write
-- 	STATUS	mandatory
-- 	DESCRIPTION
-- 		"The source of the transmit clock."
-- 	DEFVAL { 2 }
-- 	::= { sonetAdapterConfEntry 8 }
-- 
-- sonetAdapterRxScrambling OBJECT-TYPE
-- 	SYNTAX	INTEGER {
-- 		descrambling(1),
-- 		noDescrambling(2)
-- 		}
-- 	ACCESS	read-write
-- 	STATUS	mandatory
-- 	DESCRIPTION
-- 		"This variable indicates whether the information is being descrambled 
-- 		on receiving. It should be set the same as the transmitting side." 
-- 	DEFVAL { 1 }
-- 	::= { sonetAdapterConfEntry 9 }
-- 
-- sonetAdapterTxScrambling OBJECT-TYPE
-- 	SYNTAX	INTEGER {
-- 		scrambling(1),
-- 		noScrambling(2)
-- 		}
-- 	ACCESS	read-write
-- 	STATUS	mandatory
-- 	DESCRIPTION
-- 		"This variable indicates whether the information (48 octet payload) is being 
-- 		scrambled before transmitting. It should be set the same as the receiving side."
-- 	DEFVAL { 1 }
-- 	::= { sonetAdapterConfEntry 10 }
-- 
-- sonetAdapterSectionStatus OBJECT-TYPE
-- 	SYNTAX	Integer32 (1..6)
-- 	ACCESS	read-only
-- 	STATUS	mandatory
-- 	DESCRIPTION
-- 		"This variable indicates the Section Status of the interface. It is defined in 
-- 		the SONET IETF draft section configuration table as sonetSectionStatus. The 
-- 		variable is a bit map represented as a sum, therefore, it can represent multiple 
-- 		defects simultaneously. The sonetSectionNoDefect should be set if and only if no 
-- 		other flag is set.
-- 		The various bit positions are:
-- 		  1  sonetSectionNoDefect
-- 		  2  sonetSectionLOS	Loss Of Signal was detected. LOS is declared when
-- 					20 +/- 3us of all zero patterns is detected.
-- 		  4  sonetSectionLOF	Loss Of Frame was detected. LOF is declared when
-- 					an out-of-frame condition persists for 3ms."
-- 	DEFVAL { 1 }
-- 	::= { sonetAdapterConfEntry 11 }
-- 
-- sonetAdapterLineStatus OBJECT-TYPE
-- 	SYNTAX	Integer32 (1..6)
-- 	ACCESS	read-only
-- 	STATUS	mandatory
-- 	DESCRIPTION
-- 		"This variable indicates the Line Status of the interface. A similar variable is 
-- 		defined in the SONET IETF draft line configuration table as sonetLineStatus. 
-- 		The variable is a bit map represented as a sum, therefore, it can represent 
-- 		multiple defects simultaneously. The sonetLineNoDefect should be set if and only 
-- 		if no other flag is set.
-- 		The various bit positions are:
-- 		  1  sonetLineNoDefect
-- 		  2  sonetLineAIS	Line Alarm Indication Signal was detected. Line AIS is
-- 					asserted when a 111 binary pattern is detected in bits 
-- 					6,7,8 of the K2 byte for five consecutive frames.
-- 		  4  sonetLineFERF	Line Far End Receive Failure was detected. FERF is 
-- 					asserted when a 110 binary pattern is detected in bits 
-- 					6,7,8 of the K2 byte for five consecutive frames."
-- 	DEFVAL { 1 }
-- 	::= { sonetAdapterConfEntry 12 }
-- 
-- sonetAdapterPathStatus OBJECT-TYPE
-- 	SYNTAX	Integer32 (1..14)
-- 	ACCESS	read-only
-- 	STATUS	mandatory
-- 	DESCRIPTION
-- 		"This variable indicates the Path Status of the interface. It is defined in 
-- 		the SONET IETF draft path configuration table as sonetPathStatus. The variable 
-- 		is a bit map represented as a sum, therefore, it can represent multiple 
-- 		defects simultaneously. The sonetPathNoDefect should be set if and only if no 
-- 		other flag is set.
-- 		The various bit positions are:
-- 		  1  sonetPathNoDefect
-- 		  2  sonetPathLOP	Path Loss Of Pointer was detected. Path LOP is declared 
-- 					when a 'normal pointer value' is not found for eight 
-- 					consecutive frames.
-- 		  4  sonetPathAIS	Path Alarm Indication Signal was detected. Path AIS is 
-- 					asserted when an all ones pattern is detected in the 
-- 					pointer bytes (H1 and H2) for three consecutive frames.
-- 		  8  sonetPathYellow	Path Yellow alarm has been detected. Yellow alarm is 
-- 					declared when bit 5 of the path status byte is high for 
-- 					ten consecutive frames."
-- 	DEFVAL { 1 }
-- 	::= { sonetAdapterConfEntry 13 }
-- 
-- sonetAdapterIdleUnassignedCells OBJECT-TYPE
-- 	SYNTAX	INTEGER {
-- 		unassigned(1),
-- 		idle(2)
-- 		}
-- 	ACCESS	read-write
-- 	STATUS	mandatory
-- 	DESCRIPTION
-- 		"This variable indicates the type of cells that should be sent in 
-- 		case there is no data to send. According to the ATM Forum, Unassigned
-- 		cells should be sent (octet 1-3 are 0's, octet 4 is 0000xxx0, 
-- 		where x is 'don't care'). According to the CCITT specifications,
-- 		Idle cells should be sent (everything is '0' except for the CLP 
-- 		bit which is '1'). By default, unassigned cells are transmitted
-- 		in case there is no data to send."
-- 	DEFVAL { 1 }
-- 	::= { sonetAdapterConfEntry 14 }


------------------------------------------------------------------------
-- The SONET Adapter Statistics Group

-- sonetAdapterSectionTable OBJECT-TYPE
-- 	SYNTAX	SEQUENCE OF SonetAdapterSectionEntry
-- 	ACCESS	not-accessible
-- 	STATUS	mandatory
-- 	DESCRIPTION
-- 		"A table of SONET Section statistics and errors information."
-- 	::= { sonetAdapterStatsGroup 1 }
-- 
-- sonetAdapterSectionEntry OBJECT-TYPE
-- 	SYNTAX	SonetAdapterSectionEntry
-- 	ACCESS	not-accessible
-- 	STATUS	mandatory
-- 	DESCRIPTION
-- 		"A table entry containing SONET Section statistics and errors information for 
-- 		every port."
-- 	INDEX	{ sonetAdapterSectionInterface }
-- 	::= { sonetAdapterSectionTable 1 }
-- 
-- SonetAdapterSectionEntry ::=
-- 	SEQUENCE {
-- 		sonetAdapterSectionInterface	INTEGER,
-- 		sonetAdapterSectionBIPs		Counter
-- 	}
-- 
-- sonetAdapterSectionInterface OBJECT-TYPE
-- 	SYNTAX	INTEGER
-- 	ACCESS	read-only
-- 	STATUS	mandatory
-- 	DESCRIPTION
-- 		"The ifIndex corresponding to this ATM adapter."
-- 	::= { sonetAdapterSectionEntry 1 }
-- 
-- sonetAdapterSectionBIPs OBJECT-TYPE
-- 	SYNTAX	Counter
-- 	ACCESS	read-only
-- 	STATUS	mandatory
-- 	DESCRIPTION
-- 		"The number of Section BIP-8 (Bit Interleaved Parity) errors that have been 
-- 		detected since the last time the port has been reset. The calculated BIP-8 
-- 		code is compared with the BIP-8 code extracted from the B1 byte of the 
-- 		following frame. Differences indicate that a section level bit error has 
-- 		occurred."
-- 	::= { sonetAdapterSectionEntry 2 }

------------------------------------------------------------------------

-- sonetAdapterLineTable OBJECT-TYPE
-- 	SYNTAX	SEQUENCE OF SonetAdapterLineEntry
-- 	ACCESS	not-accessible
-- 	STATUS	mandatory
-- 	DESCRIPTION
-- 		"A table of SONET Line statistics and errors information."
-- 	::= { sonetAdapterStatsGroup 2 }
-- 
-- sonetAdapterLineEntry OBJECT-TYPE
-- 	SYNTAX	SonetAdapterLineEntry
-- 	ACCESS	not-accessible
-- 	STATUS	mandatory
-- 	DESCRIPTION
-- 		"A table entry containing SONET Line statistics and errors information for 
-- 		every port."
-- 	INDEX	{ sonetAdapterLineInterface } 
-- 	::= { sonetAdapterLineTable 1 }
-- 
-- SonetAdapterLineEntry ::=
-- 	SEQUENCE {
-- 		sonetAdapterLineInterface	INTEGER,		
-- 		sonetAdapterLineBIPs		Counter,
-- 		sonetAdapterLineFEBEs		Counter
-- 	}
-- 
-- sonetAdapterLineInterface OBJECT-TYPE
-- 	SYNTAX	INTEGER
-- 	ACCESS	read-only
-- 	STATUS	mandatory
-- 	DESCRIPTION
-- 		"The ifIndex corresponding to this ATM adapter."
-- 	::= { sonetAdapterLineEntry 1 }
-- 
-- sonetAdapterLineBIPs OBJECT-TYPE
-- 	SYNTAX	Counter
-- 	ACCESS	read-only
-- 	STATUS	mandatory
-- 	DESCRIPTION
-- 		"The number of Line BIP-24 (Bit Interleaved Parity) errors that have been 
-- 		detected since the last time the port has been reset. The calculated BIP-24 
-- 		code is based on the line overhead and synchronous payload envelope (SPE) of 
-- 		the STS-3c stream. The line BIP-24 code is a bit interleaved parity calculation 
-- 		using even parity. The calculated code is compared with the BIP-24 code extracted 
-- 		from the B2 bytes of the following frame. Differences indicate that a line layer 
-- 		bit error has occurred."
-- 	::= { sonetAdapterLineEntry 2 }
-- 
-- sonetAdapterLineFEBEs OBJECT-TYPE
-- 	SYNTAX	Counter
-- 	ACCESS	read-only
-- 	STATUS	mandatory
-- 	DESCRIPTION
-- 		"The number of line Far End Block Errors (FEBE) that have been detected since 
-- 		the last time the port has been reset."
-- 	::= { sonetAdapterLineEntry 3 }

------------------------------------------------------------------------

-- sonetAdapterPathTable OBJECT-TYPE
-- 	SYNTAX	SEQUENCE OF SonetAdapterPathEntry
-- 	ACCESS	not-accessible
-- 	STATUS	mandatory
-- 	DESCRIPTION
-- 		"A table of SONET Path statistics and errors information."
-- 	::= { sonetAdapterStatsGroup 3 }
-- 
-- sonetAdapterPathEntry OBJECT-TYPE
-- 	SYNTAX	SonetAdapterPathEntry
-- 	ACCESS	not-accessible
-- 	STATUS	mandatory
-- 	DESCRIPTION
-- 		"A table entry containing SONET Path statistics and errors information for 
-- 		every port."
-- 	INDEX	{ sonetAdapterPathInterface }
-- 	::= { sonetAdapterPathTable 1 }
-- 
-- SonetAdapterPathEntry ::=
-- 	SEQUENCE {
-- 		sonetAdapterPathInterface	INTEGER,		
-- 		sonetAdapterPathBIPs		Counter,
-- 		sonetAdapterPathFEBEs		Counter
-- 	}
-- 
-- sonetAdapterPathInterface OBJECT-TYPE
-- 	SYNTAX	INTEGER
-- 	ACCESS	read-only
-- 	STATUS	mandatory
-- 	DESCRIPTION
-- 		"The ifIndex corresponding to this ATM adapter."
-- 	::= { sonetAdapterPathEntry 1 }
-- 
-- sonetAdapterPathBIPs OBJECT-TYPE
-- 	SYNTAX	Counter
-- 	ACCESS	read-only
-- 	STATUS	mandatory
-- 	DESCRIPTION
-- 		"The number of Path BIP-8 (Bit Interleaved Parity) errors that have been 
-- 		detected since the last time the port has been reset. A path BIP-8 error is 
-- 		detected by comparing the path BIP-8 byte (B3) extracted from the current 
-- 		frame, to the path BIP-8 computed for the previous frame."
-- 	::= { sonetAdapterPathEntry 2 }
-- 
-- sonetAdapterPathFEBEs OBJECT-TYPE
-- 	SYNTAX	Counter
-- 	ACCESS	read-only
-- 	STATUS	mandatory
-- 	DESCRIPTION
-- 		"The number of path Far End Block Errors (FEBE) that have been detected since 
-- 		the last time the port has been reset. FEBEs are detected by extracting the 
-- 		4-bit FEBE field from the path status byte (G1). The legal range for the 4 bit 
-- 		field is between 0000 and 1000, representing zero to eight errors. Any other 
-- 		value is interpreted as zero errors."
-- 	::= { sonetAdapterPathEntry 3 }

------------------------------------------------------------------------

-- sonetAdapterAtmTable OBJECT-TYPE
-- 	SYNTAX	SEQUENCE OF SonetAdapterAtmEntry
-- 	ACCESS	not-accessible
-- 	STATUS	mandatory
-- 	DESCRIPTION
-- 		"A table of SONET ATM layer statistics and errors information."
-- 	::= { sonetAdapterStatsGroup 4 }
-- 
-- sonetAdapterAtmEntry OBJECT-TYPE
-- 	SYNTAX	SonetAdapterAtmEntry
-- 	ACCESS	not-accessible
-- 	STATUS	mandatory
-- 	DESCRIPTION
-- 		"A table entry containing SONET ATM layer statistics and errors information 
-- 		for every port."
-- 	INDEX	{ sonetAdapterAtmInterface }
-- 	::= { sonetAdapterAtmTable 1 }
-- 
-- SonetAdapterAtmEntry ::=
-- 	SEQUENCE {
-- 		sonetAdapterAtmInterface		INTEGER,		
-- 		sonetAdapterAtmCorrectableHCSs		Counter,
-- 		sonetAdapterAtmUncorrectableHCSs	Counter
-- }
-- 
-- sonetAdapterAtmInterface OBJECT-TYPE
-- 	SYNTAX	INTEGER
-- 	ACCESS	read-only
-- 	STATUS	mandatory
-- 	DESCRIPTION
-- 		"The ifIndex corresponding to this ATM adapter."
-- 	::= { sonetAdapterAtmEntry 1 }
-- 
-- sonetAdapterAtmCorrectableHCSs OBJECT-TYPE
-- 	SYNTAX	Counter
-- 	ACCESS	read-only
-- 	STATUS	mandatory
-- 	DESCRIPTION
-- 		"The number of correctable Header Check Sequence (HCS) error events that 
-- 		occurred since the port was reset. The HCS is a CRC-8 calculation over the 
-- 		first 4 octets of the ATM cell header."
-- 	::= { sonetAdapterAtmEntry 2 }
-- 
-- sonetAdapterAtmUncorrectableHCSs OBJECT-TYPE
-- 	SYNTAX	Counter
-- 	ACCESS	read-only
-- 	STATUS	mandatory
-- 	DESCRIPTION
-- 		"The number of uncorrectable Header Check Sequence (HCS) error events that 
-- 		occurred since the port was reset. The HCS is a CRC-8 calculation over the 
-- 		first 4 octets of the ATM cell header."
-- 	::= { sonetAdapterAtmEntry 3 }

------------------------------------------------------------------------
-- The Auxiliary Statistics Group

-- This group is mandatory for SNMP agents that
-- support adapters from the 200 series.

-- statsTable OBJECT-TYPE
-- 	SYNTAX	SEQUENCE OF StatsEntry
-- 	ACCESS	not-accessible
-- 	STATUS	mandatory
-- 	DESCRIPTION
-- 		"A table of auxiliary statistics for an ATM interface."
-- 	::= { statsGroup 1 }
-- 
-- statsEntry OBJECT-TYPE
-- 	SYNTAX	StatsEntry
-- 	ACCESS	not-accessible
-- 	STATUS	mandatory
-- 	DESCRIPTION
-- 		"A table entry containing auxiliary statistics information 
-- 		about an ATM connection."
-- 	INDEX	{ statsInterface }
-- 	::= { statsTable 1 }
-- 
-- StatsEntry ::=
-- 	SEQUENCE {
-- 		statsInterface		INTEGER,
-- 		statsSmallBufType1Fails	Counter,
-- 		statsLargeBufType1Fails	Counter,
-- 		statsSmallBufType2Fails	Counter,
-- 		statsLargeBufType2Fails	Counter,
-- 		statsRxPduDescFails	Counter
-- 	}
-- 
-- statsInterface OBJECT-TYPE
-- 	SYNTAX	INTEGER
-- 	ACCESS	read-only
-- 	STATUS	mandatory
-- 	DESCRIPTION
-- 		"This object uniquely identifies the ATM interface."
-- 	::= { statsEntry 1 }
-- 
-- statsSmallBufType1Fails OBJECT-TYPE
-- 	SYNTAX	Counter
-- 	ACCESS	read-only
-- 	STATUS	mandatory
-- 	DESCRIPTION
-- 		"This object counts the number of times the ATM interface
-- 		failed to get a small buffer from the type 1 pool because 
-- 		there was none available. The type of buffers that are used 
-- 		are set by the host when the VC (Virtual Circuit) is opened."
-- 	::= { statsEntry 2 }
-- 
-- statsLargeBufType1Fails OBJECT-TYPE
-- 	SYNTAX	Counter
-- 	ACCESS	read-only
-- 	STATUS	mandatory
-- 	DESCRIPTION
-- 		"This object counts the number of times the ATM interface
-- 		failed to get a large buffer from the type 1 pool because 
-- 		there was none available. The type of buffers that are used 
-- 		are set by the host when the VC (Virtual Circuit) is opened."
-- 	::= { statsEntry 3 }
-- 
-- statsSmallBufType2Fails OBJECT-TYPE
-- 	SYNTAX	Counter
-- 	ACCESS	read-only
-- 	STATUS	mandatory
-- 	DESCRIPTION
-- 		"This object counts the number of times the ATM interface
-- 		failed to get a small buffer from the type 2 pool because 
-- 		there was none available. The type of buffers that are used 
-- 		are set by the host when the VC (Virtual Circuit) is opened."
-- 	::= { statsEntry 4 }
-- 
-- statsLargeBufType2Fails OBJECT-TYPE
-- 	SYNTAX	Counter
-- 	ACCESS	read-only
-- 	STATUS	mandatory
-- 	DESCRIPTION
-- 		"This object counts the number of times the ATM interface
-- 		failed to get a large buffer from the type 2 pool because 
-- 		there was none available. The type of buffers that are used 
-- 		are set by the host when the VC (Virtual Circuit) is opened."
-- 	::= { statsEntry 5 }
-- 
-- statsRxPduDescFails OBJECT-TYPE
-- 	SYNTAX	Counter
-- 	ACCESS	read-only
-- 	STATUS	mandatory
-- 	DESCRIPTION
-- 		"This object counts the number of times the ATM interface
-- 		failed to get a PDU descriptor because there was none available."
-- 	::= { statsEntry 6 }

------------------------------------------------------------------------
-- The ATM ARP Group

atmarpFlushTable OBJECT-TYPE
	SYNTAX	INTEGER {
		disable(1),
		enable(2)
	}
	MAX-ACCESS	read-write
	STATUS	current
	DESCRIPTION
		"A SNMP agent will flush the ATM ARP table when this
		variable is set to enable(2). After the operation is
		done, the value of this object is disable(1)."
	::= { atmarpGroup 1 }
	
atmarpTable OBJECT-TYPE
	SYNTAX	SEQUENCE OF AtmarpEntry
	MAX-ACCESS	not-accessible
	STATUS	current
	DESCRIPTION
		"A table for ATM ARP information."
	::= { atmarpGroup 2 }

atmarpEntry OBJECT-TYPE
	SYNTAX	AtmarpEntry
	MAX-ACCESS	not-accessible
	STATUS	current
	DESCRIPTION
		"A table entry containing information about an ATM ARP 
		connection."
	INDEX	{ atmarpIpAddress }
	::= { atmarpTable 1 }

AtmarpEntry ::=
	SEQUENCE {
		atmarpIpAddress		IpAddress,
		atmarpInterface		Integer32,
		atmarpSpansAddress	SpansAddress,
		atmarpNsapAddress	NsapAddr,
		atmarpVPI		Integer32,
		atmarpVCI		Integer32,
		atmarpConnType		INTEGER,
		atmarpAALType		INTEGER,
		atmarpPeakBandwidth	Integer32,
		atmarpConnDirection	INTEGER,
		atmarpEntryValidity	INTEGER,
		atmarpEntryType		INTEGER,
		atmarpEntryStatus	EntryStatus
	}

atmarpIpAddress OBJECT-TYPE
	SYNTAX	IpAddress
	MAX-ACCESS	read-only
	STATUS	current
	DESCRIPTION
		"This object identifies the remote IP address for this 
		ATM ARP entry."
	::= { atmarpEntry 1 }

atmarpInterface OBJECT-TYPE
	SYNTAX	Integer32
	MAX-ACCESS	read-write
	STATUS	current
	DESCRIPTION
		"This object identifies the ATM IP interface (ifIndex)
		 on which this mapping is effective."
	::= { atmarpEntry 2 }

atmarpSpansAddress OBJECT-TYPE
	SYNTAX	SpansAddress
	MAX-ACCESS	read-only
	STATUS	current
	DESCRIPTION
		"This object identifies the remote SPANS address for this 
		ATM ARP entry."
	::= { atmarpEntry 3 }

atmarpNsapAddress OBJECT-TYPE
	SYNTAX	NsapAddr
	MAX-ACCESS	read-write
	STATUS	current
	DESCRIPTION
		"This object identifies the remote NSAP (Network Service
		Access Point) for this ATM ARP entry. This object can be
		used for manually editing the ARP table to include IP to
		NSAP address mapping for devices that do not support
		Classical IP ARP."
	::= { atmarpEntry 4 }

atmarpVPI OBJECT-TYPE
	SYNTAX	Integer32
	MAX-ACCESS	read-write
	STATUS	current
	DESCRIPTION
		"The Virtual Path Identifier for this connection."
	::= { atmarpEntry 5 }

atmarpVCI OBJECT-TYPE
	SYNTAX	Integer32
	MAX-ACCESS	read-write
	STATUS	current
	DESCRIPTION
		"The Virtual Channel Identifier for this connection."
	::= { atmarpEntry 6 }

atmarpConnType OBJECT-TYPE
	SYNTAX	INTEGER {
			foreIpPVC(1),
			foreIpSVC(2),
			classicalIpPVC(3),
			classicalIpSVC(4)
		}
	MAX-ACCESS	read-write
	STATUS	current
	DESCRIPTION
		"The type of the connection by which the IP address 
		can be reached. The value foreIpPVC(1) indicates the 
		connection is a FORE IP Permanent Virtual Circuit, 
		foreIpSVC(2) indicates it's a FORE IP Switched Virtual 
		Circuit. The value classicalIpPVC(3) indicates the 
		connection is a Classical IP Permanent Virtual Circuit, 
		and the value classicalIpSVC(4) indicates the connection
		is a Classical IP Switched Virtual Circuit."
	::= { atmarpEntry 7 }

atmarpAALType OBJECT-TYPE
	SYNTAX	INTEGER {
			aal34(1),
			aal5(2)
		}
	MAX-ACCESS	read-write
	STATUS	current
	DESCRIPTION
		"The type of the AAL (ATM Adaptation Layer) of this connection."
	::= { atmarpEntry 8 }

atmarpPeakBandwidth OBJECT-TYPE
	SYNTAX	Integer32
	MAX-ACCESS	read-write
	STATUS	current
	DESCRIPTION
		"The peak bandwidth for this connection, in kilobits per second."
	::= { atmarpEntry 9 }

atmarpConnDirection OBJECT-TYPE
	SYNTAX	INTEGER {
			outgoing(1),
			bidirectional(2),
			pending(3)
		}
	MAX-ACCESS	read-only
	STATUS	current
	DESCRIPTION
		"The direction of this connection. The value pending(3) is
		used for an ATM ARP entry that does not have a connection
		associated with it."
	::= { atmarpEntry 10 }

atmarpEntryValidity OBJECT-TYPE
	SYNTAX	INTEGER {
			valid(1),
			invalid(2)
		}
	MAX-ACCESS	read-only
	STATUS	current
	DESCRIPTION
		"The validity of this ATM ARP entry. A Classical IP connection 
		entry may be invalid(2) if the remote end of the connection does 
		not answer ARP requests for a while. The entry still exists, but 
		the host is not allowed to send data across it when the entry is 
		in the invalid(2) state."
	::= { atmarpEntry 11 }

atmarpEntryType OBJECT-TYPE
	SYNTAX	INTEGER {
			dynamic(1),
			static(2)
		}
	MAX-ACCESS	read-only
	STATUS	current
	DESCRIPTION
		"This object indicates the type of mapping. Dynamic entries 
		are learned from Fore IP or Classical IP mechanisms. Static 
		entries are created manually."
	::= { atmarpEntry 12 }

atmarpEntryStatus OBJECT-TYPE
	SYNTAX	EntryStatus
	MAX-ACCESS	read-write
	STATUS	current
	DESCRIPTION
		"The status of this ATM ARP entry."
	::= { atmarpEntry 13 }


------------------------------------------------------------------------
-- The Classical IP Group

classicalIpArpTable OBJECT-TYPE
	SYNTAX	SEQUENCE OF ClassicalIpArpEntry
	MAX-ACCESS	not-accessible
	STATUS	current
	DESCRIPTION
		"A table for Classical IP ARP information."
	::= { classicalIpGroup 1 }

classicalIpArpEntry OBJECT-TYPE
	SYNTAX	ClassicalIpArpEntry
	MAX-ACCESS	not-accessible
	STATUS	current
	DESCRIPTION
		"A table entry containing information about Classical IP ARP 
		configuration."
	INDEX	{ classicalIpArpIfIndex, classicalIpArpServerIndex }
	::= { classicalIpArpTable 1 }

ClassicalIpArpEntry ::=
	SEQUENCE {
		classicalIpArpIfIndex			Integer32,
		classicalIpArpServerIndex		Integer32,
		classicalIpArpServer			INTEGER,
		classicalIpArpServerConfigType		INTEGER,
		classicalIpWellKnownArpServerAddr	NsapAddr,
		classicalIpManualConfigArpServerAddr	NsapAddr
	}

classicalIpArpIfIndex OBJECT-TYPE
	SYNTAX	Integer32
	MAX-ACCESS	read-only
	STATUS	current
	DESCRIPTION
		"The ifIndex corresponding to the ATM interface on which 
		the following classical IP information is configured."
	::= { classicalIpArpEntry 1 }

classicalIpArpServerIndex OBJECT-TYPE
	SYNTAX	Integer32
	MAX-ACCESS	read-only
	STATUS	current
	DESCRIPTION
		"The index of the ARP server."
	::= { classicalIpArpEntry 2 }

classicalIpArpServer OBJECT-TYPE
	SYNTAX	INTEGER {
		disable(1),
		enable(2)
	}
	MAX-ACCESS	read-write
	STATUS	current
	DESCRIPTION
		"An SNMP agent will configure this virtual interface as 
		a Classical IP ARP Server when this variable is set to 
		enable(2)."
	::= { classicalIpArpEntry 3 }
	
classicalIpArpServerConfigType OBJECT-TYPE
	SYNTAX	INTEGER {
			manualConfig(1),
			wellKnown(2)
		}
	MAX-ACCESS	read-write
	STATUS	current
	DESCRIPTION
		"This object identifies the way in which the NSAP 
		(Network Service Access Point) address of the ARP server 
		is determined. When the value of this object is wellKnown(2), 
		the NSAP address of the ARP server is taken from the 
		classicalIpWellKNownArpServerAddr object. When the value 
		of this object is set to manualConfig(1), the NSAP address 
		of the ARP server is read from the 
		classicalIpManualConfigArpServerAddr object."
	::= { classicalIpArpEntry 4 }

classicalIpWellKnownArpServerAddr OBJECT-TYPE
	SYNTAX	NsapAddr
	MAX-ACCESS	read-only
	STATUS	current
	DESCRIPTION
		"This variable holds the well known NSAP (Network Service Access
		Point) address of the ARP server for this interface."
	::= { classicalIpArpEntry 5 }

classicalIpManualConfigArpServerAddr OBJECT-TYPE
	SYNTAX	NsapAddr
	MAX-ACCESS	read-write
	STATUS	current
	DESCRIPTION
		"This variable holds the manually configured NSAP (Network 
		Service Access Point) address of the ARP server for this 
		interface. By default this object is set to all zero."
	::= { classicalIpArpEntry 6 }

-------------------------------------------------------------------

-- textual conventions
-- Ip header data
IpHeader   ::= OCTET STRING (SIZE (64))

--The Ip Filter Group
--The subgroup Ip Filter Conf Group


ipFilterTable OBJECT-TYPE
    SYNTAX    SEQUENCE OF IpFilterEntry
    MAX-ACCESS    not-accessible
    STATUS    current
    DESCRIPTION
	"A table of authorized ip addresses from which the switch can
	receive IP packets."
    ::= { ipFilterConfGroup 1 }

ipFilterEntry OBJECT-TYPE
    SYNTAX    IpFilterEntry
    MAX-ACCESS    not-accessible
    STATUS    current
    DESCRIPTION
        "A table entry containing ip filter information."
    INDEX    { ipFilterIpAddress, ipFilterMask }
    ::= { ipFilterTable 1 }

IpFilterEntry ::=
    SEQUENCE {
        ipFilterIpAddress        IpAddress,
        ipFilterMask		 IpAddress,
        ipFilterRowStatus        RowStatus
    }

ipFilterIpAddress OBJECT-TYPE
    SYNTAX    IpAddress
    MAX-ACCESS    not-accessible
    STATUS    current
    DESCRIPTION
        "The authorized IP Address, in the inbound direction."
    ::= { ipFilterEntry 1 }

ipFilterMask OBJECT-TYPE
    SYNTAX    IpAddress
    MAX-ACCESS    not-accessible
    STATUS    current
    DESCRIPTION
        "Indicates the mask to be logical-ANDed with the ipFilterIpAddress
	to find matching addresses. A mask of 0.0.0.0 is a wild card
	and matches all addresses. A valid mask is one which has
	contiguous higher order 1 bits set. That is, mask 255.255.0.128
	is not valid while 255.255.0.0 is valid. Example matches:

		IpAddress	Mask		 means
		163.26.54.6	255.255.255.255	 Allow address 163.26.54.6
		163.54.7.21     255.255.0.0      Allow addresses 163.54.*.*"
    ::= { ipFilterEntry 2 }

ipFilterRowStatus OBJECT-TYPE
    SYNTAX   RowStatus
    MAX-ACCESS   read-write
    STATUS   current
    DESCRIPTION
        "The status of this ipFilter entry."
    ::= { ipFilterEntry 3 }


ipFilterNoSSR OBJECT-TYPE
    SYNTAX    INTEGER {
        enabled( 1 ),
        disabled( 2 )
    }
    MAX-ACCESS    read-write
    STATUS    current
    DESCRIPTION
        "NoStrictSourceRoute Flag.  On implies that IP packets with Strict
         Source Routed Option set will be dropped.  Off implies that these
         packets will be allowed to pass through, provided they meet with
         all the other requirements."
    ::= { ipFilterConfGroup 2 }

ipFilterNoLSR OBJECT-TYPE
    SYNTAX    INTEGER {
        enabled( 1 ),
        disabled( 2 )
    }
    MAX-ACCESS    read-write
    STATUS    current
    DESCRIPTION
        "NoLooseSourceRoute Flag.  On implies that IP packets with Loose
         Source Routed Option set will be dropped.  Off implies that these
         packets will be allowed to pass through, provided they meet with
         all the other requirements."
    ::= { ipFilterConfGroup 3 }

ipFilterNoInBand OBJECT-TYPE
    SYNTAX    INTEGER {
        enabled( 1 ),
        disabled( 2 )
    }
    MAX-ACCESS    read-write
    STATUS    current
    DESCRIPTION
        "NoInBand Flag.  On implies that ALL IP packets from the ATM network
         will be dropped.  Off implies that these packets will be allowed to
         pass through, provided they meet with all the other requirements."
    ::= { ipFilterConfGroup 4 }

--- The subgroup ipFilterStatsGroup
--- Information about the last violation that occured

ipFilterStatsIpHeader OBJECT-TYPE
    SYNTAX    IpHeader
    MAX-ACCESS    read-only
    STATUS    current
    DESCRIPTION
        "The first 64 bytes of the IP packet which was last dropped."
    ::= { ipFilterStatsGroup 1 }

ipFilterStatsTimeOccured OBJECT-TYPE
    SYNTAX    TimeTicks
    MAX-ACCESS    read-only
    STATUS    current
    DESCRIPTION
        "The sysUptime at which the last IP packet was dropped."
    ::= { ipFilterStatsGroup 2 }

ipFilterStatsViolations OBJECT-TYPE
    SYNTAX    Counter32
    MAX-ACCESS    read-only
    STATUS    current
    DESCRIPTION
        "The number of IP packets dropped till the current time."
    ::= { ipFilterStatsGroup 3 }

ipFilterStatsVPI OBJECT-TYPE
    SYNTAX    Integer32
    MAX-ACCESS    read-only
    STATUS    current
    DESCRIPTION
        "The Virtual Path Identifier corresponding to the connection on
         which the last IP packet was dropped."
    ::= { ipFilterStatsGroup 4 }

ipFilterStatsVCI OBJECT-TYPE
    SYNTAX    Integer32
    MAX-ACCESS    read-only
    STATUS    current
    DESCRIPTION
        "The Virtual Channel Identifier corresponding to the connection on
         which the last IP packet was dropped."
    ::= { ipFilterStatsGroup 5 }

ipFilterStatsIfName OBJECT-TYPE
    SYNTAX    DisplayString
    MAX-ACCESS    read-only
    STATUS    current
    DESCRIPTION 
         "Name of the interface on which the last dropped IP packet
	  was received"
    ::= { ipFilterStatsGroup 6 }

ipFilterStatsReasonText OBJECT-TYPE
    SYNTAX    DisplayString
    MAX-ACCESS    read-only
    STATUS    current
    DESCRIPTION
         "The reason for dropping the last IP packet to be dropped"
    ::= { ipFilterStatsGroup 7 }

ipFilterStatsSrcIpAddr OBJECT-TYPE
    SYNTAX    IpAddress
    MAX-ACCESS    read-only
    STATUS    current
    DESCRIPTION
         "The IP address contained in the source field of the header of the
          last IP packet to be dropped"
    ::= { ipFilterStatsGroup 8 }

END
