-- 
-- RM2-MIB module definition  
--
-- The definitions in this module specify an initial version of 
-- resource monitor mib.
--

RM2-MIB DEFINITIONS ::= BEGIN

IMPORTS
    NetworkAddress, TimeTicks, enterprises, Counter
        FROM RFC1155-SMI
    OBJECT-TYPE
        FROM RFC-1212
    DisplayString
        FROM RFC1213-MIB
    MODULE-IDENTITY, ObjectName, Integer32, Counter32, snmpModules
        FROM SNMPv2-SMI
    TruthValue, DisplayString, TestAndIncr, TimeStamp, RowStatus
        FROM SNMPv2-TC;

	lucent		    OBJECT IDENTIFIER  ::=  {  enterprises  1751  }
	products	    OBJECT IDENTIFIER  ::=  {  lucent  1  }
	softSwitch	    OBJECT IDENTIFIER  ::=  {  products 1198  }
	resourceMonitor	OBJECT IDENTIFIER  ::=  {  softSwitch 4  }

    rm2  MODULE-IDENTITY    
        LAST-UPDATED "240701"
        ORGANIZATION "Lucent Technologies"    
        CONTACT-INFO 
                ""    
        DESCRIPTION
                "The MIB module for entities implementing the xxxx
                protocol."  

::=  {  resourceMonitor  2  }


	--
	-- The various groups in this mib
	--

	rmSystem	OBJECT IDENTIFIER  ::=  {  rm2 1 }
	rmDiskGrp	OBJECT IDENTIFIER  ::=  {  rm2 2 }
	rmCpuGrp	OBJECT IDENTIFIER  ::=  {  rm2 3 }
	rmFileGrp	OBJECT IDENTIFIER  ::=  {  rm2 4 }
    rmProcessGrp    OBJECT IDENTIFIER  ::=  {  rm2 5 }

	--
	-- the rmSystem group - contains information about the
	-- resource monitor deamon iteslf
	--

	rmDescr OBJECT-TYPE
	    SYNTAX  DisplayString
	    MAX-ACCESS  read-only
	    STATUS  current
	    DESCRIPTION
		    "A textual description of the entity.  This value
		    should include the full name and version
		    identification of the resource monitor software.
		    It is mandatory that this only contain printable 
		    ASCII characters."

	    ::= { rmSystem 1 }

	rmObjectID OBJECT-TYPE
	    SYNTAX  OBJECT IDENTIFIER
	    MAX-ACCESS  read-only
	    STATUS  current
	    DESCRIPTION
		    "An internal identification for this resource monitor."

	    ::= { rmSystem 2 }

	
	rmUpTime OBJECT-TYPE
	    SYNTAX  TimeTicks
	    MAX-ACCESS  read-only
	    STATUS  current
	    DESCRIPTION
		    "The time (in hundredths of a second) since the
		    resource monitor deamon was last re-initialized."

	    ::= { rmSystem 3 }

	rmNetAddress OBJECT-TYPE
	    SYNTAX  NetworkAddress
	    MAX-ACCESS  read-only
	    STATUS  current
	    DESCRIPTION
		    "The ip address of the host on which this deamon
		    is running."

	    ::= { rmSystem 4 }

	rmControl OBJECT-TYPE
	    SYNTAX  DisplayString
	    MAX-ACCESS  read-write
	    STATUS  current
	    DESCRIPTION
		    "This is the settable field that in turn controls 
		    some of the functioning of the resource monitor.
		    At present, this field is not used.  It has been 
		    created for future expansion."

	    ::= { rmSystem 5 }


	--
	-- the rm Disk group - contains information about the
	-- file system usage for the ones being monitored.
	--


	diskPeriod  OBJECT-TYPE 
	    SYNTAX  INTEGER ( 1..60 )
	    MAX-ACCESS  read-write 
	    STATUS  current
	    DESCRIPTION
		    "Defines disk monitoring frequency. Period in seconds.
		    It is a settable field, so user can alter how frequently
		    the file systems are checked for size limits."
	    ::=  {  rmDiskGrp  1  }


	diskUsageWarningPct OBJECT-TYPE 
	    SYNTAX  INTEGER ( 1..99 )
	    MAX-ACCESS  read-write 
	    STATUS  current
	    DESCRIPTION
		    "If disk usage exceeds this amount of percentage, 
		    a diskAttention trap will be emitted.
		    severity: MAJOR"
	    ::=  {  rmDiskGrp  2  }


	diskUsageAlarmPct OBJECT-TYPE 
	    SYNTAX  INTEGER ( 1..99 ) 
	    MAX-ACCESS  read-write 
	    STATUS  current
	    DESCRIPTION
		    "If Disk usage exceeds this mount of percentage, 
		    a diskAlarm trap will be emitted.
		    severity: CRITICAL"
	    ::=  {  rmDiskGrp  3  }

	duNumber OBJECT-TYPE
	    SYNTAX  INTEGER ( 1.. 2048 )
	    MAX-ACCESS  read-only
	    STATUS  current
	    DESCRIPTION
		    "The number of file systems being monitored.
		(indicates the number of rows in diskUsageTable)"
	    ::= { rmDiskGrp 4 }

	diskUsageTable OBJECT-TYPE
	    SYNTAX  SEQUENCE  OF  DUEntry
	    MAX-ACCESS  not-accessible
	    STATUS  current
	    DESCRIPTION
		"A list of file system entries.  The number of
		entries is given by the value of duNumber."
--          AGENTCLAUSE
--          	"
--      	FILE-COMMAND: 
--      	FILE-NAME: /export/home/lss/release/netmon/mibs/rm2-duTable.txt
--      	FILE-COMMAND-TIMEOUT: 5000"
--          END AGENTCLAUSE
 		::=  { rmDiskGrp  5 }
		

	diskUsageEntry	OBJECT-TYPE
	    SYNTAX  DUEntry
	    MAX-ACCESS  not-accessible
	    STATUS  current
        DESCRIPTION 
            ""
	    INDEX   {  duIndex  }
	    ::=  { diskUsageTable 1 }

	DUEntry ::=  
	    SEQUENCE {
		duIndex  
			INTEGER,
		duFSName  
			DisplayString,
		duSize  
			INTEGER,
		duPctUsed  
			INTEGER
	    }

	duIndex	OBJECT-TYPE 
	    SYNTAX  INTEGER ( 1..2048 )
	    MAX-ACCESS  read-only 
	    STATUS  current
	    DESCRIPTION
		"A unique value for each disk slice.  Goes from 1 to N"
	    ::=  {  diskUsageEntry  1  }

	duFSName OBJECT-TYPE 
	    SYNTAX  DisplayString 
	    MAX-ACCESS  read-only 
	    STATUS  current
	    DESCRIPTION
		    "The name of the file system being monitored"
	    ::=  {  diskUsageEntry  2  }

        duSize OBJECT-TYPE 
	    SYNTAX  INTEGER ( 1..8192 )
	    MAX-ACCESS  read-only 
	    STATUS  current
	    DESCRIPTION
		    "The size of the file system in k bytes"
	    ::=  {  diskUsageEntry  3  }

       duPctUsed OBJECT-TYPE 
	    SYNTAX  INTEGER ( 0..99 )
	    MAX-ACCESS  read-only 
	    STATUS  current
	    DESCRIPTION
		    "The percentage of the file system used up"
	    ::=  {  diskUsageEntry  4  }

	--
	-- the rm CPU group - contains information about the
	-- cpu utilization and load for the machine.
	--


	cpuPeriod  OBJECT-TYPE 
	    SYNTAX  INTEGER ( 1..15 )
	    MAX-ACCESS  read-write 
	    STATUS  current
	    DESCRIPTION
		    "Defines cpu monitoring frequency.  The CPU load 
		    and utilization are measure as per this frequency.
		    Period can be either one, ten or fifteen minutes.  
		    Setting it to any other value will cause the set 
		    to fail (the old value will stay)."
	    ::=  {  rmCpuGrp  1  }

	cpuUtilization OBJECT-TYPE 
	    SYNTAX  INTEGER ( 1..99 )
	    MAX-ACCESS  read-only 
	    STATUS  current
	    DESCRIPTION
		    "The current cpu utilization percentage."
	    ::=  {  rmCpuGrp  2  }

	cpuUtilWarningPct OBJECT-TYPE 
	    SYNTAX  INTEGER ( 1..99 )
	    MAX-ACCESS  read-write 
	    STATUS  current
	    DESCRIPTION
		    "If cpu utlization exceeds this percentage, 
		    a cpuUtilAttention trap will be emitted.
		    severity: MAJOR"
	    ::=  {  rmCpuGrp  3  }

	cpuUtilAlarmPct OBJECT-TYPE 
	    SYNTAX  INTEGER ( 1..99 )
	    MAX-ACCESS  read-write 
	    STATUS  current
	    DESCRIPTION
		    "If CPU utilization exceeds this percentage,
		    a cpuUtilAlarm trap will be emitted.
		    severity: CRITICAL"
	    ::=  {  rmCpuGrp  4  }


	cpuLoad OBJECT-TYPE 
	    SYNTAX  DisplayString 
	    MAX-ACCESS  read-only 
	    STATUS  current
	    DESCRIPTION
		    "The current value of cpu load. Note: Although
		     the syntax is DisplayString, the real semantics 
		     should be floating point value of cpu load.
		     For example: 0.3, 2.5, etc."
	    ::=  {  rmCpuGrp  5  }

	cpuLoadWarningThreshold OBJECT-TYPE 
	    SYNTAX  DisplayString
	    MAX-ACCESS  read-write 
	    STATUS  current
	    DESCRIPTION
		    "If cpu load exceeds this amount, 
		    a cpuLoadAttention trap will be emitted.
		    severity: MAJOR
		    Note: Although the syntax is DisplayString, 
		    the real semantics should be floating point value."
	    ::=  {  rmCpuGrp  6  }

	cpuLoadAlarmThreshold OBJECT-TYPE 
	    SYNTAX  DisplayString 
	    MAX-ACCESS  read-write 
	    STATUS  current
	    DESCRIPTION
		    "If cpu load exceeds this amount, 
		    a cpuLoadAlarm trap will be emitted.
		    severity: CRITICAL
		    Note: Although the syntax is DisplayString, 
		    the real semantics should be floating point value."

	    ::=  {  rmCpuGrp  7  }


	--
	-- the rm File group - contains information about the
	-- log files that are being monitored for size.
	--

	filePeriod  OBJECT-TYPE 
	    SYNTAX  INTEGER ( 1..60 )
	    MAX-ACCESS  read-write 
	    STATUS  current
	    DESCRIPTION
		    "Defines log file monitoring frequency.  This 
		    value is expressed as the number of minutes."
	    ::=  {  rmFileGrp  1  }

	fmNumber OBJECT-TYPE
	    SYNTAX  INTEGER ( 1..8192 ) 
	    MAX-ACCESS  read-only
	    STATUS  current
	    DESCRIPTION
		    "The number of files being monitored by this
		    deamon."
	    ::= { rmFileGrp 2 }

	-- the Files Monitored table
	-- Each line represents detail on the file being monitored.

	fmTable OBJECT-TYPE
	    SYNTAX  SEQUENCE OF FileEntry
	    MAX-ACCESS  not-accessible
	    STATUS  current
	    DESCRIPTION
		    "A list of files being monitored for size."
--      AGENTCLAUSE
--             "
--             FILE-COMMAND: 
--             FILE-NAME: /export/home/lss/release/netmon/mibs/rm2-fmTable.txt
--             FILE-COMMAND-TIMEOUT: 5000"
--      END AGENTCLAUSE
	    ::= { rmFileGrp 3 }

	fmEntry OBJECT-TYPE
	    SYNTAX  FileEntry
	    MAX-ACCESS  not-accessible
	    STATUS  current
	    DESCRIPTION
		    "Each entry represents one log file, and is a 
		    sequence of type FileEntry, which is explained below."
	    INDEX   { fmIndex }
	    ::= { fmTable 1 }

	FileEntry ::=
	    SEQUENCE {
		fmIndex
		    INTEGER,
		fmName
		    DisplayString,	
		fmCurSize
		    INTEGER,
		fmThreshold
		    INTEGER
	    }

	fmIndex OBJECT-TYPE
	    SYNTAX  INTEGER ( 1..8192 )
	    MAX-ACCESS  read-only
	    STATUS  current
	    DESCRIPTION
		    "A unique number for each file being monitored.
		    Goes from 1 to N"
	    ::= { fmEntry 1 }

	fmName OBJECT-TYPE
	    SYNTAX  DisplayString (SIZE (0..32))
	    MAX-ACCESS  read-only
	    STATUS  current
	    DESCRIPTION
		    "the absolute path for the file being monitored."
	    ::= { fmEntry 2 }

	fmCurSize OBJECT-TYPE
	    SYNTAX  INTEGER ( 1..8192 )
	    MAX-ACCESS  read-only
	    STATUS  current
	    DESCRIPTION
		    "The is the current size of the file."
	    ::= { fmEntry 3 }

	fmThreshold OBJECT-TYPE
	    SYNTAX  INTEGER ( 1..8192 )
	    MAX-ACCESS  read-only
	    STATUS  current
	    DESCRIPTION
		    "This is the size above which a FileSizeEvent trap
		    will be sent out.   This information is read from
		    the config directory when the RMpep is started."
	    ::= { fmEntry 4 }

	archiveDir  OBJECT-TYPE
	    SYNTAX  DisplayString
	    MAX-ACCESS  read-write
	    STATUS  current
	    DESCRIPTION
		    "This variable returns the current archive 
		     directory.
		     ResMon may be periodically asked to archive
		     log files. After detecting and reporting a
		     fileOversize event, resMon may also be told 
		     to archive the log file along with file 
		     monitoring target switch.
		     The current running policy determines the
		     archive action."
	    ::= { rmFileGrp 4 }

        processPeriod  OBJECT-TYPE
            SYNTAX  INTEGER ( 1..60 )
            MAX-ACCESS  read-write
            STATUS  current
            DESCRIPTION
                    "Defines process monitoring frequency. Period in seconds.
                    It is a settable field, so user can alter how frequently
                    the processes are checked for CPU and memory utilization"
            ::=  {  rmProcessGrp  1  }

        processNumber OBJECT-TYPE
            SYNTAX  INTEGER ( 1..8192 )
            MAX-ACCESS  read-only
            STATUS  current
            DESCRIPTION
                    "The number of processes being monitored.
                (indicates the number of rows in processTable)"
            ::= { rmProcessGrp 2 }


        processTable OBJECT-TYPE
            SYNTAX  SEQUENCE  OF  ProcessEntry
            MAX-ACCESS  not-accessible
            STATUS  current
            DESCRIPTION
                "A list of process entries.  The number of
                entries is given by the value of processNumber."
--          AGENTCLAUSE
--              "
--              FILE-COMMAND:
--              FILE-NAME: /export/home/lss/release/netmon/mibs/rm2-procTable.txt
--              FILE-COMMAND-TIMEOUT: 5000"
--          END AGENTCLAUSE
                ::=  { rmProcessGrp  3 }

        processEntry  OBJECT-TYPE
            SYNTAX  ProcessEntry
            MAX-ACCESS  not-accessible
            STATUS  current
            DESCRIPTION
                ""

            INDEX   {  processIndex  }
            ::=  { processTable 1 }


        ProcessEntry ::=
            SEQUENCE {
                processIndex
                        INTEGER,
                processID
                        INTEGER,
                processName
                        DisplayString,
                processUpTime
                        INTEGER,
                processCPUUsageWarnMark
                        INTEGER,
                processCPUUsageAlarmMark
                        INTEGER,
                processCPUUsageCurrent
                        INTEGER,
                processMemUsageAlarmMark
                        INTEGER,
                processMemUsageCurrent
                        INTEGER
            }


        processIndex OBJECT-TYPE
            SYNTAX  INTEGER ( 1..8192 )
            MAX-ACCESS  read-only
            STATUS  current
            DESCRIPTION
                "A unique value for each process.  Goes from 1 to N"
            ::=  {  processEntry  1  }


        processID OBJECT-TYPE 
            SYNTAX  INTEGER ( 1..65535 )
            MAX-ACCESS  read-only
            STATUS  current
            DESCRIPTION
                "A unique value for each process."
            ::=  {  processEntry  2  }


        processName OBJECT-TYPE
            SYNTAX  DisplayString
            MAX-ACCESS  read-only
            STATUS  current
            DESCRIPTION
                "The name of the process."
            ::=  {  processEntry  3  }


        processUpTime OBJECT-TYPE
            SYNTAX  INTEGER ( 1..65535 )
            MAX-ACCESS  read-only
            STATUS  current
            DESCRIPTION
                "The time since the process is up running."
            ::=  {  processEntry  4  }


        processCPUUsageWarnMark OBJECT-TYPE
            SYNTAX  INTEGER ( 1..99 )
            MAX-ACCESS  read-only
            STATUS  current
            DESCRIPTION
                "The threshold when resMon should generate a warning for netMon."
            ::=  {  processEntry  5  }


        processCPUUsageAlarmMark OBJECT-TYPE
            SYNTAX  INTEGER ( 1..99 )
            MAX-ACCESS  read-only
            STATUS  current
            DESCRIPTION
                "The threshold when resMon should generate a alarm for netMon."
            ::=  {  processEntry  6  }


        processCPUUsageCurrent OBJECT-TYPE
            SYNTAX  INTEGER ( 1..99 )
            MAX-ACCESS  read-only
            STATUS  current
            DESCRIPTION
                "The amount of CPU time this process used."
            ::=  {  processEntry  7  }


        processMemUsageAlarmMark OBJECT-TYPE
            SYNTAX  INTEGER ( 1..99 )
            MAX-ACCESS  read-only
            STATUS  current
            DESCRIPTION
                "The memory usage threshold when resMon should generate a memory usage alarm for netMon."
            ::=  {  processEntry  8  }


        processMemUsageCurrent OBJECT-TYPE
            SYNTAX  INTEGER  ( 1..8192 )
            MAX-ACCESS  read-only
            STATUS  current
            DESCRIPTION
                "The amount of memory this process used."
            ::=  {  processEntry  9  }


END
