-- This MIB was created by extracting information from 
-- Sun Mangement Center 3.5 for use in other applications
-- to help determine what is actually listed in the SMC snmp 
-- agent. Sun has/will not release their MIBS for this 
-- information, so I created them from all information that
-- they have released.
--
-- Most all the information should be correct, but
-- if you find a discrepency please let me know. I do not
-- have all available Sun hardware to test with, so not 
-- not all types of support hardware has been tested.
-- These MIBs have only been tested using the utilities
-- from net-snmp. They may or may not work with other
-- applications.
-- 
-- The MIBs are not detailed, they only are useful in 
-- mapping OIDs to names. At some point in time 
-- descriptions may be given.
--
-- Author: Brian T. O'Neill (btoneill@misplaced.net)
-- Date: 7-30-2003 
-- Version: 0.9
--
-- No guarantees are given regarding the accuracy of this
-- data.
--
-- Note: The naming was done in line with the published
-- MIBS from Sun Microsystems.
--
READER4U-SUNMANAGEMENTCENTER-MIB DEFINITIONS ::= BEGIN

  IMPORTS
        enterprises, NOTIFICATION-TYPE, OBJECT-TYPE, MODULE-IDENTITY
                FROM SNMPv2-SMI;

sun             OBJECT IDENTIFIER ::= { enterprises 42 }
prod            OBJECT IDENTIFIER ::= { sun 2 }
sunsymon        OBJECT IDENTIFIER ::= { prod 12 }
agent           OBJECT IDENTIFIER ::= { sunsymon 2 }
base            OBJECT IDENTIFIER ::= { agent 1 }
modules         OBJECT IDENTIFIER ::= { agent 2 }
hardware        OBJECT IDENTIFIER ::= { modules 1 }
--
--
config          OBJECT IDENTIFIER ::= { hardware 1 }
reader4u        OBJECT IDENTIFIER ::= { config 1 }
reader4udt      OBJECT IDENTIFIER ::= { config 2 }
reader4uwg      OBJECT IDENTIFIER ::= { config 3 }
reader4u1P      OBJECT IDENTIFIER ::= { config 4 }
reader4u1D      OBJECT IDENTIFIER ::= { config 5 }
reader4unt      OBJECT IDENTIFIER ::= { config 6 }
readerSerengeti OBJECT IDENTIFIER ::= { config 7 }
reader4uvh      OBJECT IDENTIFIER ::= { config 8 }
readerECP       OBJECT IDENTIFIER ::= { config 9 }
readerELP       OBJECT IDENTIFIER ::= { config 10 }


sunSmTreeProp	OBJECT IDENTIFIER ::= { peripheral-12v 1 }
sunSmNodeName	OBJECT IDENTIFIER ::= { peripheral-12v 2 }
fru	OBJECT IDENTIFIER ::= { peripheral-12v 3 }
status	OBJECT IDENTIFIER ::= { peripheral-12v 4 }
sunSmTreeProp	OBJECT IDENTIFIER ::= { networkEntry 1 }
sunSmNodeName	OBJECT IDENTIFIER ::= { networkEntry 2 }
entry-no	OBJECT IDENTIFIER ::= { networkEntry 3 }
device-type	OBJECT IDENTIFIER ::= { networkEntry 4 }
ether	OBJECT IDENTIFIER ::= { networkEntry 5 }
inet	OBJECT IDENTIFIER ::= { networkEntry 6 }
interface-name	OBJECT IDENTIFIER ::= { networkEntry 7 }
node-hierarchy	OBJECT IDENTIFIER ::= { networkEntry 8 }
symbolic-name	OBJECT IDENTIFIER ::= { networkEntry 9 }
reg	OBJECT IDENTIFIER ::= { networkEntry 10 }
boardTbl	OBJECT IDENTIFIER ::= { board 1 }
cpu-unitTbl	OBJECT IDENTIFIER ::= { cpu-unit 1 }
sunSmTreeProp	OBJECT IDENTIFIER ::= { remote-console 1 }
sunSmNodeName	OBJECT IDENTIFIER ::= { remote-console 2 }
status	OBJECT IDENTIFIER ::= { remote-console 3 }
power-supply-entry	OBJECT IDENTIFIER ::= { power-supplyTbl 1 }
sunSmTreeProp	OBJECT IDENTIFIER ::= { power-supply-entry 1 }
sunSmNodeName	OBJECT IDENTIFIER ::= { power-supply-entry 2 }
entry-no	OBJECT IDENTIFIER ::= { power-supply-entry 3 }
fru	OBJECT IDENTIFIER ::= { power-supply-entry 4 }
hpu	OBJECT IDENTIFIER ::= { power-supply-entry 5 }
status	OBJECT IDENTIFIER ::= { power-supply-entry 6 }
unit-no	OBJECT IDENTIFIER ::= { power-supply-entry 7 }
sysctrlTbl	OBJECT IDENTIFIER ::= { sysctrl 1 }
sunSmTreeProp	OBJECT IDENTIFIER ::= { simm-entry 1 }
sunSmNodeName	OBJECT IDENTIFIER ::= { simm-entry 2 }
entry-no	OBJECT IDENTIFIER ::= { simm-entry 3 }
board-reference-number	OBJECT IDENTIFIER ::= { simm-entry 4 }
fru	OBJECT IDENTIFIER ::= { simm-entry 5 }
size	OBJECT IDENTIFIER ::= { simm-entry 6 }
slot	OBJECT IDENTIFIER ::= { simm-entry 7 }
type	OBJECT IDENTIFIER ::= { simm-entry 8 }
eepromTbl	OBJECT IDENTIFIER ::= { eeprom 1 }
sram-entry	OBJECT IDENTIFIER ::= { sramTbl 1 }
sunSmTreeProp	OBJECT IDENTIFIER ::= { ac-ps 1 }
sunSmNodeName	OBJECT IDENTIFIER ::= { ac-ps 2 }
status	OBJECT IDENTIFIER ::= { ac-ps 3 }
sunSmTreeProp	OBJECT IDENTIFIER ::= { ac-entry 1 }
sunSmNodeName	OBJECT IDENTIFIER ::= { ac-entry 2 }
entry-no	OBJECT IDENTIFIER ::= { ac-entry 3 }
bank-0-status	OBJECT IDENTIFIER ::= { ac-entry 4 }
bank-1-status	OBJECT IDENTIFIER ::= { ac-entry 5 }
device-type	OBJECT IDENTIFIER ::= { ac-entry 6 }
model	OBJECT IDENTIFIER ::= { ac-entry 7 }
pv-ancestor-alarm	OBJECT IDENTIFIER ::= { ac-entry 8 }
reg	OBJECT IDENTIFIER ::= { ac-entry 9 }
version-no	OBJECT IDENTIFIER ::= { ac-entry 10 }
flashprom-entry	OBJECT IDENTIFIER ::= { flashpromTbl 1 }
slotTbl	OBJECT IDENTIFIER ::= { slot 1 }
simm-groupTbl	OBJECT IDENTIFIER ::= { simm-group 1 }
sunSmTreeProp	OBJECT IDENTIFIER ::= { io-controllerEntry 1 }
sunSmNodeName	OBJECT IDENTIFIER ::= { io-controllerEntry 2 }
entry-no	OBJECT IDENTIFIER ::= { io-controllerEntry 3 }
board-num	OBJECT IDENTIFIER ::= { io-controllerEntry 4 }
clock-frequency	OBJECT IDENTIFIER ::= { io-controllerEntry 5 }
device-type	OBJECT IDENTIFIER ::= { io-controllerEntry 6 }
instance	OBJECT IDENTIFIER ::= { io-controllerEntry 7 }
model	OBJECT IDENTIFIER ::= { io-controllerEntry 8 }
reg	OBJECT IDENTIFIER ::= { io-controllerEntry 9 }
upa-mid	OBJECT IDENTIFIER ::= { io-controllerEntry 10 }
upa-portid	OBJECT IDENTIFIER ::= { io-controllerEntry 11 }
version-no	OBJECT IDENTIFIER ::= { io-controllerEntry 12 }
sunSmTreeProp	OBJECT IDENTIFIER ::= { simmstat-entry 1 }
sunSmNodeName	OBJECT IDENTIFIER ::= { simmstat-entry 2 }
entry-no	OBJECT IDENTIFIER ::= { simmstat-entry 3 }
instance	OBJECT IDENTIFIER ::= { simmstat-entry 4 }
reg	OBJECT IDENTIFIER ::= { simmstat-entry 5 }
io-controllerEntry	OBJECT IDENTIFIER ::= { io-controllerTbl 1 }
sunSmTreeProp	OBJECT IDENTIFIER ::= { system-5v 1 }
sunSmNodeName	OBJECT IDENTIFIER ::= { system-5v 2 }
fru	OBJECT IDENTIFIER ::= { system-5v 3 }
status	OBJECT IDENTIFIER ::= { system-5v 4 }
sunwffbTbl	OBJECT IDENTIFIER ::= { sunwffb 1 }
cpu-unit-entry	OBJECT IDENTIFIER ::= { cpu-unitTbl 1 }
eeprom-entry	OBJECT IDENTIFIER ::= { eepromTbl 1 }
ledTbl	OBJECT IDENTIFIER ::= { led 1 }
simmTbl	OBJECT IDENTIFIER ::= { simm 1 }
simm-status-entry	OBJECT IDENTIFIER ::= { simm-statusTbl 1 }
sunSmTreeProp	OBJECT IDENTIFIER ::= { led-entry 1 }
sunSmNodeName	OBJECT IDENTIFIER ::= { led-entry 2 }
entry-no	OBJECT IDENTIFIER ::= { led-entry 3 }
led-num	OBJECT IDENTIFIER ::= { led-entry 4 }
state	OBJECT IDENTIFIER ::= { led-entry 5 }
tapeTbl	OBJECT IDENTIFIER ::= { tape 1 }
power-supplyTbl	OBJECT IDENTIFIER ::= { power-supply 1 }
environmentTbl	OBJECT IDENTIFIER ::= { environment 1 }
sunSmTreeProp	OBJECT IDENTIFIER ::= { io-unitEntry 1 }
sunSmNodeName	OBJECT IDENTIFIER ::= { io-unitEntry 2 }
entry-no	OBJECT IDENTIFIER ::= { io-unitEntry 3 }
board-num	OBJECT IDENTIFIER ::= { io-unitEntry 4 }
device-id	OBJECT IDENTIFIER ::= { io-unitEntry 5 }
instance	OBJECT IDENTIFIER ::= { io-unitEntry 6 }
reg	OBJECT IDENTIFIER ::= { io-unitEntry 7 }
sunSmTreeProp	OBJECT IDENTIFIER ::= { eeprom-entry 1 }
sunSmNodeName	OBJECT IDENTIFIER ::= { eeprom-entry 2 }
entry-no	OBJECT IDENTIFIER ::= { eeprom-entry 3 }
model	OBJECT IDENTIFIER ::= { eeprom-entry 4 }
reg	OBJECT IDENTIFIER ::= { eeprom-entry 5 }
sunSmTreeProp	OBJECT IDENTIFIER ::= { peripheral-12v-precharge 1 }
sunSmNodeName	OBJECT IDENTIFIER ::= { peripheral-12v-precharge 2 }
fru	OBJECT IDENTIFIER ::= { peripheral-12v-precharge 3 }
status	OBJECT IDENTIFIER ::= { peripheral-12v-precharge 4 }
sunSmTreeProp	OBJECT IDENTIFIER ::= { ffb-entry 1 }
sunSmNodeName	OBJECT IDENTIFIER ::= { ffb-entry 2 }
entry-no	OBJECT IDENTIFIER ::= { ffb-entry 3 }
buffer	OBJECT IDENTIFIER ::= { ffb-entry 4 }
device-type	OBJECT IDENTIFIER ::= { ffb-entry 5 }
model	OBJECT IDENTIFIER ::= { ffb-entry 6 }
pathname-element	OBJECT IDENTIFIER ::= { ffb-entry 7 }
ffb-entry	OBJECT IDENTIFIER ::= { ffbTbl 1 }
sunSmTreeProp	OBJECT IDENTIFIER ::= { keyswitch 1 }
sunSmNodeName	OBJECT IDENTIFIER ::= { keyswitch 2 }
position	OBJECT IDENTIFIER ::= { keyswitch 3 }
fhcTbl	OBJECT IDENTIFIER ::= { fhc 1 }
sunSmTreeProp	OBJECT IDENTIFIER ::= { environment-entry 1 }
sunSmNodeName	OBJECT IDENTIFIER ::= { environment-entry 2 }
entry-no	OBJECT IDENTIFIER ::= { environment-entry 3 }
reg	OBJECT IDENTIFIER ::= { environment-entry 4 }
reader4u	OBJECT IDENTIFIER ::= { config 1 }
simm-entry	OBJECT IDENTIFIER ::= { simmTbl 1 }
central-entry	OBJECT IDENTIFIER ::= { centralTbl 1 }
sunSmTreeProp	OBJECT IDENTIFIER ::= { system-3v-precharge 1 }
sunSmNodeName	OBJECT IDENTIFIER ::= { system-3v-precharge 2 }
fru	OBJECT IDENTIFIER ::= { system-3v-precharge 3 }
status	OBJECT IDENTIFIER ::= { system-3v-precharge 4 }
flashpromTbl	OBJECT IDENTIFIER ::= { flashprom 1 }
sunSmTreeProp	OBJECT IDENTIFIER ::= { rack-fan 1 }
sunSmNodeName	OBJECT IDENTIFIER ::= { rack-fan 2 }
status	OBJECT IDENTIFIER ::= { rack-fan 3 }
io-deviceEntry	OBJECT IDENTIFIER ::= { io-deviceTbl 1 }
peripheral-PSTbl	OBJECT IDENTIFIER ::= { peripheral-PS 1 }
memoryTbl	OBJECT IDENTIFIER ::= { memory 1 }
memory-entry	OBJECT IDENTIFIER ::= { memoryTbl 1 }
simm-statusTbl	OBJECT IDENTIFIER ::= { simm-status 1 }
environ-entry	OBJECT IDENTIFIER ::= { environTbl 1 }
simmstatTbl	OBJECT IDENTIFIER ::= { simmstat 1 }
environTbl	OBJECT IDENTIFIER ::= { environ 1 }
sunSmTreeProp	OBJECT IDENTIFIER ::= { system 1 }
sunSmNodeName	OBJECT IDENTIFIER ::= { system 2 }
os	OBJECT IDENTIFIER ::= { system 3 }
os-version	OBJECT IDENTIFIER ::= { system 4 }
system-clock-frequency	OBJECT IDENTIFIER ::= { system 5 }
architecture	OBJECT IDENTIFIER ::= { system 6 }
hostname	OBJECT IDENTIFIER ::= { system 7 }
machine	OBJECT IDENTIFIER ::= { system 8 }
platform	OBJECT IDENTIFIER ::= { system 9 }
sample	OBJECT IDENTIFIER ::= { system 10 }
serial-number	OBJECT IDENTIFIER ::= { system 11 }
timestamp	OBJECT IDENTIFIER ::= { system 12 }
timestamp-raw	OBJECT IDENTIFIER ::= { system 13 }
total-disks	OBJECT IDENTIFIER ::= { system 14 }
total-memory	OBJECT IDENTIFIER ::= { system 15 }
total-processors	OBJECT IDENTIFIER ::= { system 16 }
total-tape-devices	OBJECT IDENTIFIER ::= { system 17 }
total-model-changes	OBJECT IDENTIFIER ::= { system 18 }
total-config-changes	OBJECT IDENTIFIER ::= { system 19 }
centralTbl	OBJECT IDENTIFIER ::= { central 1 }
sunSmTreeProp	OBJECT IDENTIFIER ::= { central-entry 1 }
sunSmNodeName	OBJECT IDENTIFIER ::= { central-entry 2 }
entry-no	OBJECT IDENTIFIER ::= { central-entry 3 }
reg	OBJECT IDENTIFIER ::= { central-entry 4 }
upa-mid	OBJECT IDENTIFIER ::= { central-entry 5 }
sunSmTreeProp	OBJECT IDENTIFIER ::= { sunwffb-entry 1 }
sunSmNodeName	OBJECT IDENTIFIER ::= { sunwffb-entry 2 }
entry-no	OBJECT IDENTIFIER ::= { sunwffb-entry 3 }
dram3	OBJECT IDENTIFIER ::= { sunwffb-entry 4 }
dac	OBJECT IDENTIFIER ::= { sunwffb-entry 5 }
fbc-version	OBJECT IDENTIFIER ::= { sunwffb-entry 6 }
board-type	OBJECT IDENTIFIER ::= { sunwffb-entry 7 }
buffer	OBJECT IDENTIFIER ::= { sunwffb-entry 8 }
device-type	OBJECT IDENTIFIER ::= { sunwffb-entry 9 }
height	OBJECT IDENTIFIER ::= { sunwffb-entry 10 }
model	OBJECT IDENTIFIER ::= { sunwffb-entry 11 }
revision	OBJECT IDENTIFIER ::= { sunwffb-entry 12 }
upa-portid	OBJECT IDENTIFIER ::= { sunwffb-entry 13 }
width	OBJECT IDENTIFIER ::= { sunwffb-entry 14 }
sunSmTreeProp	OBJECT IDENTIFIER ::= { peripheral-5v 1 }
sunSmNodeName	OBJECT IDENTIFIER ::= { peripheral-5v 2 }
fru	OBJECT IDENTIFIER ::= { peripheral-5v 3 }
status	OBJECT IDENTIFIER ::= { peripheral-5v 4 }
networkEntry	OBJECT IDENTIFIER ::= { networkTbl 1 }
simmstat-entry	OBJECT IDENTIFIER ::= { simmstatTbl 1 }
sunSmTreeProp	OBJECT IDENTIFIER ::= { solt-entry 1 }
sunSmNodeName	OBJECT IDENTIFIER ::= { solt-entry 2 }
entry-no	OBJECT IDENTIFIER ::= { solt-entry 3 }
slot-num	OBJECT IDENTIFIER ::= { solt-entry 4 }
acTbl	OBJECT IDENTIFIER ::= { ac 1 }
sunSmTreeProp	OBJECT IDENTIFIER ::= { io-deviceEntry 1 }
sunSmNodeName	OBJECT IDENTIFIER ::= { io-deviceEntry 2 }
entry-no	OBJECT IDENTIFIER ::= { io-deviceEntry 3 }
device-type	OBJECT IDENTIFIER ::= { io-deviceEntry 4 }
disk-count	OBJECT IDENTIFIER ::= { io-deviceEntry 5 }
instance	OBJECT IDENTIFIER ::= { io-deviceEntry 6 }
model	OBJECT IDENTIFIER ::= { io-deviceEntry 7 }
node-hierarchy	OBJECT IDENTIFIER ::= { io-deviceEntry 8 }
network-count	OBJECT IDENTIFIER ::= { io-deviceEntry 9 }
reg	OBJECT IDENTIFIER ::= { io-deviceEntry 10 }
tape-count	OBJECT IDENTIFIER ::= { io-deviceEntry 11 }
fanTbl	OBJECT IDENTIFIER ::= { fan 1 }
solt-entry	OBJECT IDENTIFIER ::= { slotTbl 1 }
sunSmTreeProp	OBJECT IDENTIFIER ::= { system-5v-precharge 1 }
sunSmNodeName	OBJECT IDENTIFIER ::= { system-5v-precharge 2 }
fru	OBJECT IDENTIFIER ::= { system-5v-precharge 3 }
status	OBJECT IDENTIFIER ::= { system-5v-precharge 4 }
sunSmTreeProp	OBJECT IDENTIFIER ::= { cpu-unit-entry 1 }
sunSmNodeName	OBJECT IDENTIFIER ::= { cpu-unit-entry 2 }
entry-no	OBJECT IDENTIFIER ::= { cpu-unit-entry 3 }
board-hash	OBJECT IDENTIFIER ::= { cpu-unit-entry 4 }
board-num	OBJECT IDENTIFIER ::= { cpu-unit-entry 5 }
clock-frequency	OBJECT IDENTIFIER ::= { cpu-unit-entry 6 }
cpu-type	OBJECT IDENTIFIER ::= { cpu-unit-entry 7 }
dcache-size	OBJECT IDENTIFIER ::= { cpu-unit-entry 8 }
device-type	OBJECT IDENTIFIER ::= { cpu-unit-entry 9 }
ecache-size	OBJECT IDENTIFIER ::= { cpu-unit-entry 10 }
fru	OBJECT IDENTIFIER ::= { cpu-unit-entry 11 }
icache-size	OBJECT IDENTIFIER ::= { cpu-unit-entry 12 }
model	OBJECT IDENTIFIER ::= { cpu-unit-entry 13 }
pathname-element	OBJECT IDENTIFIER ::= { cpu-unit-entry 14 }
processor-id	OBJECT IDENTIFIER ::= { cpu-unit-entry 15 }
reg	OBJECT IDENTIFIER ::= { cpu-unit-entry 16 }
status	OBJECT IDENTIFIER ::= { cpu-unit-entry 17 }
unit	OBJECT IDENTIFIER ::= { cpu-unit-entry 18 }
upa-mid	OBJECT IDENTIFIER ::= { cpu-unit-entry 19 }
upa-portid	OBJECT IDENTIFIER ::= { cpu-unit-entry 20 }
io-deviceTbl	OBJECT IDENTIFIER ::= { io-device 1 }
led-entry	OBJECT IDENTIFIER ::= { ledTbl 1 }
io-controllerTbl	OBJECT IDENTIFIER ::= { io-controller 1 }
sunSmTreeProp	OBJECT IDENTIFIER ::= { hot-plug-charges 1 }
sunSmNodeName	OBJECT IDENTIFIER ::= { hot-plug-charges 2 }
fru	OBJECT IDENTIFIER ::= { hot-plug-charges 3 }
sunSmTreeProp	OBJECT IDENTIFIER ::= { tapeEntry 1 }
sunSmNodeName	OBJECT IDENTIFIER ::= { tapeEntry 2 }
entry-no	OBJECT IDENTIFIER ::= { tapeEntry 3 }
device-type	OBJECT IDENTIFIER ::= { tapeEntry 4 }
fru	OBJECT IDENTIFIER ::= { tapeEntry 5 }
instance	OBJECT IDENTIFIER ::= { tapeEntry 6 }
model	OBJECT IDENTIFIER ::= { tapeEntry 7 }
node-hierarchy	OBJECT IDENTIFIER ::= { tapeEntry 8 }
tape-name	OBJECT IDENTIFIER ::= { tapeEntry 9 }
status	OBJECT IDENTIFIER ::= { tapeEntry 10 }
target	OBJECT IDENTIFIER ::= { tapeEntry 11 }
sunSmTreeProp	OBJECT IDENTIFIER ::= { system-3v 1 }
sunSmNodeName	OBJECT IDENTIFIER ::= { system-3v 2 }
fru	OBJECT IDENTIFIER ::= { system-3v 3 }
status	OBJECT IDENTIFIER ::= { system-3v 4 }
sunSmTreeProp	OBJECT IDENTIFIER ::= { environ-entry 1 }
sunSmNodeName	OBJECT IDENTIFIER ::= { environ-entry 2 }
entry-no	OBJECT IDENTIFIER ::= { environ-entry 3 }
instance	OBJECT IDENTIFIER ::= { environ-entry 4 }
reg	OBJECT IDENTIFIER ::= { environ-entry 5 }
sunSmTreeProp	OBJECT IDENTIFIER ::= { fan-entry 1 }
sunSmNodeName	OBJECT IDENTIFIER ::= { fan-entry 2 }
entry-no	OBJECT IDENTIFIER ::= { fan-entry 3 }
status	OBJECT IDENTIFIER ::= { fan-entry 4 }
tapeEntry	OBJECT IDENTIFIER ::= { tapeTbl 1 }
io-unitEntry	OBJECT IDENTIFIER ::= { io-unitTbl 1 }
sunSmTreeProp	OBJECT IDENTIFIER ::= { diskEntry 1 }
sunSmNodeName	OBJECT IDENTIFIER ::= { diskEntry 2 }
entry-no	OBJECT IDENTIFIER ::= { diskEntry 3 }
device-type	OBJECT IDENTIFIER ::= { diskEntry 4 }
disk-name	OBJECT IDENTIFIER ::= { diskEntry 5 }
fru	OBJECT IDENTIFIER ::= { diskEntry 6 }
instance	OBJECT IDENTIFIER ::= { diskEntry 7 }
node-hierarchy	OBJECT IDENTIFIER ::= { diskEntry 8 }
target	OBJECT IDENTIFIER ::= { diskEntry 9 }
sunSmTreeProp	OBJECT IDENTIFIER ::= { memory-entry 1 }
sunSmNodeName	OBJECT IDENTIFIER ::= { memory-entry 2 }
entry-no	OBJECT IDENTIFIER ::= { memory-entry 3 }
pathname-element	OBJECT IDENTIFIER ::= { memory-entry 4 }
sunSmTreeProp	OBJECT IDENTIFIER ::= { auxiliary-5v 1 }
sunSmNodeName	OBJECT IDENTIFIER ::= { auxiliary-5v 2 }
fru	OBJECT IDENTIFIER ::= { auxiliary-5v 3 }
status	OBJECT IDENTIFIER ::= { auxiliary-5v 4 }
environment-entry	OBJECT IDENTIFIER ::= { environmentTbl 1 }
sunSmTreeProp	OBJECT IDENTIFIER ::= { board-entry 1 }
sunSmNodeName	OBJECT IDENTIFIER ::= { board-entry 2 }
entry-no	OBJECT IDENTIFIER ::= { board-entry 3 }
board-num	OBJECT IDENTIFIER ::= { board-entry 4 }
fru	OBJECT IDENTIFIER ::= { board-entry 5 }
hot-plugged	OBJECT IDENTIFIER ::= { board-entry 6 }
hpu	OBJECT IDENTIFIER ::= { board-entry 7 }
memory-size	OBJECT IDENTIFIER ::= { board-entry 8 }
state	OBJECT IDENTIFIER ::= { board-entry 9 }
temperature	OBJECT IDENTIFIER ::= { board-entry 10 }
type	OBJECT IDENTIFIER ::= { board-entry 11 }
type-int	OBJECT IDENTIFIER ::= { board-entry 12 }
upa-mid	OBJECT IDENTIFIER ::= { board-entry 13 }
sunSmTreeProp	OBJECT IDENTIFIER ::= { simm-group-entry 1 }
sunSmNodeName	OBJECT IDENTIFIER ::= { simm-group-entry 2 }
entry-no	OBJECT IDENTIFIER ::= { simm-group-entry 3 }
device-type	OBJECT IDENTIFIER ::= { simm-group-entry 4 }
group-no	OBJECT IDENTIFIER ::= { simm-group-entry 5 }
size	OBJECT IDENTIFIER ::= { simm-group-entry 6 }
status	OBJECT IDENTIFIER ::= { simm-group-entry 7 }
sunSmTreeProp	OBJECT IDENTIFIER ::= { fhc-entry 1 }
sunSmNodeName	OBJECT IDENTIFIER ::= { fhc-entry 2 }
entry-no	OBJECT IDENTIFIER ::= { fhc-entry 3 }
board-num	OBJECT IDENTIFIER ::= { fhc-entry 4 }
model	OBJECT IDENTIFIER ::= { fhc-entry 5 }
reg	OBJECT IDENTIFIER ::= { fhc-entry 6 }
upa-mid	OBJECT IDENTIFIER ::= { fhc-entry 7 }
version-no	OBJECT IDENTIFIER ::= { fhc-entry 8 }
sunSmTreeProp	OBJECT IDENTIFIER ::= { disk-fan 1 }
sunSmNodeName	OBJECT IDENTIFIER ::= { disk-fan 2 }
hpu	OBJECT IDENTIFIER ::= { disk-fan 3 }
status	OBJECT IDENTIFIER ::= { disk-fan 4 }
rpfa300	OBJECT IDENTIFIER ::= { pfa-rules 1 }
rpfa301	OBJECT IDENTIFIER ::= { pfa-rules 2 }
rpfa302	OBJECT IDENTIFIER ::= { pfa-rules 3 }
sunSmTreeProp	OBJECT IDENTIFIER ::= { peripheral-5v-precharge 1 }
sunSmNodeName	OBJECT IDENTIFIER ::= { peripheral-5v-precharge 2 }
fru	OBJECT IDENTIFIER ::= { peripheral-5v-precharge 3 }
status	OBJECT IDENTIFIER ::= { peripheral-5v-precharge 4 }
sunSmTreeProp	OBJECT IDENTIFIER ::= { clock-board 1 }
sunSmNodeName	OBJECT IDENTIFIER ::= { clock-board 2 }
ffbTbl	OBJECT IDENTIFIER ::= { ffb 1 }
diskTbl	OBJECT IDENTIFIER ::= { disk 1 }
sunSmTreeProp	OBJECT IDENTIFIER ::= { flashprom-entry 1 }
sunSmNodeName	OBJECT IDENTIFIER ::= { flashprom-entry 2 }
entry-no	OBJECT IDENTIFIER ::= { flashprom-entry 3 }
model	OBJECT IDENTIFIER ::= { flashprom-entry 4 }
reg	OBJECT IDENTIFIER ::= { flashprom-entry 5 }
system	OBJECT IDENTIFIER ::= { reader4u 1 }
system-board	OBJECT IDENTIFIER ::= { reader4u 2 }
clock-board	OBJECT IDENTIFIER ::= { reader4u 3 }
sunwUltra-1	OBJECT IDENTIFIER ::= { reader4u 4 }
sunwUltra-2	OBJECT IDENTIFIER ::= { reader4u 5 }
slot	OBJECT IDENTIFIER ::= { reader4u 6 }
board	OBJECT IDENTIFIER ::= { reader4u 7 }
cpu-unit	OBJECT IDENTIFIER ::= { reader4u 8 }
simm	OBJECT IDENTIFIER ::= { reader4u 9 }
ac-ps	OBJECT IDENTIFIER ::= { reader4u 10 }
hot-plug-charges	OBJECT IDENTIFIER ::= { reader4u 11 }
auxiliary-5v	OBJECT IDENTIFIER ::= { reader4u 12 }
peripheral-5v	OBJECT IDENTIFIER ::= { reader4u 13 }
peripheral-5v-precharge	OBJECT IDENTIFIER ::= { reader4u 14 }
peripheral-12v	OBJECT IDENTIFIER ::= { reader4u 15 }
peripheral-12v-precharge	OBJECT IDENTIFIER ::= { reader4u 16 }
system-3v	OBJECT IDENTIFIER ::= { reader4u 17 }
system-3v-precharge	OBJECT IDENTIFIER ::= { reader4u 18 }
system-5v	OBJECT IDENTIFIER ::= { reader4u 19 }
system-5v-precharge	OBJECT IDENTIFIER ::= { reader4u 20 }
keyswitch	OBJECT IDENTIFIER ::= { reader4u 21 }
peripheral-PS	OBJECT IDENTIFIER ::= { reader4u 22 }
power-supply	OBJECT IDENTIFIER ::= { reader4u 23 }
rack-fan	OBJECT IDENTIFIER ::= { reader4u 24 }
disk-fan	OBJECT IDENTIFIER ::= { reader4u 25 }
remote-console	OBJECT IDENTIFIER ::= { reader4u 26 }
fhc	OBJECT IDENTIFIER ::= { reader4u 27 }
ac	OBJECT IDENTIFIER ::= { reader4u 28 }
environment	OBJECT IDENTIFIER ::= { reader4u 29 }
environ	OBJECT IDENTIFIER ::= { reader4u 30 }
flashprom	OBJECT IDENTIFIER ::= { reader4u 31 }
simmstat	OBJECT IDENTIFIER ::= { reader4u 32 }
simm-status	OBJECT IDENTIFIER ::= { reader4u 33 }
simm-group	OBJECT IDENTIFIER ::= { reader4u 34 }
sram	OBJECT IDENTIFIER ::= { reader4u 35 }
led	OBJECT IDENTIFIER ::= { reader4u 36 }
central	OBJECT IDENTIFIER ::= { reader4u 37 }
eeprom	OBJECT IDENTIFIER ::= { reader4u 38 }
sysctrl	OBJECT IDENTIFIER ::= { reader4u 39 }
fan	OBJECT IDENTIFIER ::= { reader4u 40 }
memory	OBJECT IDENTIFIER ::= { reader4u 41 }
ffb	OBJECT IDENTIFIER ::= { reader4u 42 }
sunwffb	OBJECT IDENTIFIER ::= { reader4u 43 }
hardware-rules	OBJECT IDENTIFIER ::= { reader4u 44 }
pfa-rules	OBJECT IDENTIFIER ::= { reader4u 45 }
io-controller	OBJECT IDENTIFIER ::= { reader4u 46 }
io-device	OBJECT IDENTIFIER ::= { reader4u 47 }
disk	OBJECT IDENTIFIER ::= { reader4u 48 }
tape	OBJECT IDENTIFIER ::= { reader4u 49 }
network	OBJECT IDENTIFIER ::= { reader4u 50 }
io-unit	OBJECT IDENTIFIER ::= { reader4u 51 }
sunSmTreeProp	OBJECT IDENTIFIER ::= { sunwUltra-1 1 }
sunSmNodeName	OBJECT IDENTIFIER ::= { sunwUltra-1 2 }
ac-entry	OBJECT IDENTIFIER ::= { acTbl 1 }
sunSmTreeProp	OBJECT IDENTIFIER ::= { sunwUltra-2 1 }
sunSmNodeName	OBJECT IDENTIFIER ::= { sunwUltra-2 2 }
sunSmTreeProp	OBJECT IDENTIFIER ::= { sysctrl-entry 1 }
sunSmNodeName	OBJECT IDENTIFIER ::= { sysctrl-entry 2 }
entry-no	OBJECT IDENTIFIER ::= { sysctrl-entry 3 }
instance	OBJECT IDENTIFIER ::= { sysctrl-entry 4 }
reg	OBJECT IDENTIFIER ::= { sysctrl-entry 5 }
rcr4u208	OBJECT IDENTIFIER ::= { hardware-rules 1 }
rcr4u210	OBJECT IDENTIFIER ::= { hardware-rules 2 }
rcr4u211	OBJECT IDENTIFIER ::= { hardware-rules 3 }
rcr4u214	OBJECT IDENTIFIER ::= { hardware-rules 4 }
rcr4u216	OBJECT IDENTIFIER ::= { hardware-rules 5 }
rcr4u217	OBJECT IDENTIFIER ::= { hardware-rules 6 }
rcr4u219	OBJECT IDENTIFIER ::= { hardware-rules 7 }
rcr4u220	OBJECT IDENTIFIER ::= { hardware-rules 8 }
rcr4u213	OBJECT IDENTIFIER ::= { hardware-rules 9 }
rcr4u215	OBJECT IDENTIFIER ::= { hardware-rules 10 }
rcr4u224	OBJECT IDENTIFIER ::= { hardware-rules 11 }
rcr4u221	OBJECT IDENTIFIER ::= { hardware-rules 12 }
board-entry	OBJECT IDENTIFIER ::= { boardTbl 1 }
sunSmTreeProp	OBJECT IDENTIFIER ::= { simm-status-entry 1 }
sunSmNodeName	OBJECT IDENTIFIER ::= { simm-status-entry 2 }
entry-no	OBJECT IDENTIFIER ::= { simm-status-entry 3 }
reg	OBJECT IDENTIFIER ::= { simm-status-entry 4 }
sunSmTreeProp	OBJECT IDENTIFIER ::= { system-board 1 }
sunSmNodeName	OBJECT IDENTIFIER ::= { system-board 2 }
networkTbl	OBJECT IDENTIFIER ::= { network 1 }
io-unitTbl	OBJECT IDENTIFIER ::= { io-unit 1 }
fhc-entry	OBJECT IDENTIFIER ::= { fhcTbl 1 }
simm-group-entry	OBJECT IDENTIFIER ::= { simm-groupTbl 1 }
peripheral-PS-entry	OBJECT IDENTIFIER ::= { peripheral-PSTbl 1 }
sunSmTreeProp	OBJECT IDENTIFIER ::= { peripheral-PS-entry 1 }
sunSmNodeName	OBJECT IDENTIFIER ::= { peripheral-PS-entry 2 }
entry-no	OBJECT IDENTIFIER ::= { peripheral-PS-entry 3 }
fru	OBJECT IDENTIFIER ::= { peripheral-PS-entry 4 }
hpu	OBJECT IDENTIFIER ::= { peripheral-PS-entry 5 }
status	OBJECT IDENTIFIER ::= { peripheral-PS-entry 6 }
unit-no	OBJECT IDENTIFIER ::= { peripheral-PS-entry 7 }
sysctrl-entry	OBJECT IDENTIFIER ::= { sysctrlTbl 1 }
sunSmTreeProp	OBJECT IDENTIFIER ::= { sram-entry 1 }
sunSmNodeName	OBJECT IDENTIFIER ::= { sram-entry 2 }
entry-no	OBJECT IDENTIFIER ::= { sram-entry 3 }
reg	OBJECT IDENTIFIER ::= { sram-entry 4 }
sunwffb-entry	OBJECT IDENTIFIER ::= { sunwffbTbl 1 }
sramTbl	OBJECT IDENTIFIER ::= { sram 1 }
diskEntry	OBJECT IDENTIFIER ::= { diskTbl 1 }
fan-entry	OBJECT IDENTIFIER ::= { fanTbl 1 }

END
