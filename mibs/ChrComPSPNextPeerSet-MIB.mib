ChrComPSPNextPeerSet-MIB

--FORCE-INCLUDE	<mib.h>
--FORCE-INCLUDE	<snmpdefs.h>
--FORCE-INCLUDE	"mibhand.h"

	DEFINITIONS  ::=  BEGIN

IMPORTS
	OBJECT-TYPE, Counter32			FROM  SNMPv2-SMI
	Integer32, Unsigned32			FROM  SNMPv2-SMI
	chrComProtectSinglePath			FROM  Chromatis-MIB;

-- chrComPSPNextPeerSet Table

chrComPSPNextPeerSetTable		OBJECT-TYPE
	SYNTAX		SEQUENCE OF ChrComPSPNextPeerSetEntry
	MAX-ACCESS	not-accessible
	STATUS		current
	DESCRIPTION
	""
	::= { chrComProtectSinglePath 3}

chrComPSPNextPeerSetEntry		OBJECT-TYPE
	SYNTAX		ChrComPSPNextPeerSetEntry
	MAX-ACCESS	not-accessible
	STATUS		current
	DESCRIPTION
	""
	INDEX  {  chrComPSPNextPathPeerSetID }

--DEFAULT  get-function-async  MNIL_GetRoutine
--DEFAULT  set-function-async  MNIL_SetRoutine
--DEFAULT  next-function-async MNIL_NextRoutine
--DEFAULT  test-function-async MNIL_TestRoutine
--DEFAULT  cookie "SP_NextPeerSet"
	::= { chrComPSPNextPeerSetTable  1 }

ChrComPSPNextPeerSetEntry  ::=
	SEQUENCE  {
	chrComPSPNextPathPeerSetID	Unsigned32	(0..4294967295)
}

chrComPSPNextPathPeerSetID 	OBJECT-TYPE
	SYNTAX		Unsigned32	(0..4294967295)
	MAX-ACCESS 	read-only
	STATUS 		current
	DESCRIPTION
	"The next vacant PeerSet ID in the Path Protection PeerSet Table
This field enables the NMS to create new Path protection PeerSet
"
	::= { chrComPSPNextPeerSetEntry  1 }


END
