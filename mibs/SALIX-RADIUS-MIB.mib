SALIX-RADIUS-MIB DEFINITIONS ::= BEGIN

IMPORTS
   MODULE-IDENTITY, OBJECT-TYPE, IpAddress,
   NOTIFICATION-TYPE                         FROM SNMPv2-SMI
   MODULE-COMPLIANCE, OBJECT-GROUP           FROM SNMPv2-CONF
         TruthValue                          FROM SNMPv2-TC
         atmfM4TrapAlarmSeverity             FROM ATM-FORUM-M4-MIB
         salixGeneric                        FROM SALIX-MIB;

salixRadiusMIB MODULE-IDENTITY
     LAST-UPDATED "0004050000Z"
     ORGANIZATION "SALIX Technologies"
     CONTACT-INFO "904 Wind River Lane
                   Suite 101
                   Gaithersburg, MD  20878
                   (301)-417-0017"
     DESCRIPTION  "This MIB describes objects relating to RADIUS protocol
                   support in SALIX products that is not described 
                   in RFC 2618."
     ::= { salixGeneric 8 }
     
   salixRadiusMIBObjects OBJECT IDENTIFIER ::= { salixRadiusMIB 1 }
   salixRadiusMIBTraps   OBJECT IDENTIFIER ::= { salixRadiusMIB 2 }
   salixRadiusMIBCompliance OBJECT IDENTIFIER ::= { salixRadiusMIB 3 }       
   salixRadiusMIBTrapPrefix OBJECT IDENTIFIER ::= { salixRadiusMIBTraps 0}

    --  RADIUS Server Config Table

    -- This table provides a mechanism for configuring RADIUS 
    -- servers.  For security reasons, this table is only 
    -- accessible to authenticated users.  Since SNMP support
    -- may not be secure, this table may not be available to
    -- some SNMP network management systems.

  salixRadiusServerConfigTable OBJECT-TYPE
       SYNTAX     SEQUENCE OF    SalixRadiusServerConfigEntry
       MAX-ACCESS not-accessible
       STATUS     current
       DESCRIPTION
            "The  RADIUS server configuration table.  This table provides a
             mechanism for configuring RADIUS servers."
       ::= { salixRadiusMIBObjects 1 }

  salixRadiusServerConfigEntry OBJECT-TYPE
       SYNTAX     SalixRadiusServerConfigEntry
       MAX-ACCESS not-accessible
       STATUS     current
       DESCRIPTION
            "An entry in the salixRadiusServerConfigTable that identifies 
             the parameters necessary to download announcements to the system."
       INDEX { salixRadiusServerIndex }
       ::= { salixRadiusServerConfigTable 1 }

  SalixRadiusServerConfigEntry ::= SEQUENCE {
            salixRadiusServerIndex           INTEGER,
            salixRadiusServerIpAddress       IpAddress,
            salixRadiusServerUdpPort         INTEGER,
            salixRadiusServerSharedSecret    OCTET STRING,
            salixRadiusServerEnabled         TruthValue
       }
       
  salixRadiusServerIndex OBJECT-TYPE
       SYNTAX         INTEGER (1..5)
       MAX-ACCESS     read-only
       STATUS         current
       DESCRIPTION
            "The unique index for the RADIUS server.  Servers are queried in
             order.  E.g. the server at index 1 is tried first and
             if it times out, the server at index 2 tried."
       ::= { salixRadiusServerConfigEntry 1 }

  salixRadiusServerIpAddress OBJECT-TYPE
       SYNTAX     IpAddress
       MAX-ACCESS read-write
       STATUS     current
       DESCRIPTION
            "The IP address of the RADIUS server."
       ::= { salixRadiusServerConfigEntry 2 }

  salixRadiusServerUdpPort OBJECT-TYPE
       SYNTAX         INTEGER (1..65535)
       MAX-ACCESS     read-write
       STATUS         current
       DESCRIPTION
            "The UDP port number that the RADIUS server listens on for
             Access-Requests."
       ::= { salixRadiusServerConfigEntry 3 }

  salixRadiusServerSharedSecret OBJECT-TYPE
       SYNTAX     OCTET STRING(SIZE (1..63))
       MAX-ACCESS read-write
       STATUS     current
       DESCRIPTION
            "The shared secret that will be used when communicating with
             this server.  For security reasons, reading this field will 
             return an empty string."
       ::= { salixRadiusServerConfigEntry 4 }
     
  salixRadiusServerEnabled OBJECT-TYPE
       SYNTAX     TruthValue
       MAX-ACCESS read-write
       STATUS     current
       DESCRIPTION
            "This value indicates whether requests should be sent to 
             this server."
       ::= { salixRadiusServerConfigEntry 5 }

  -- User authentication method
  -- Used to determine how user logins are authenticated
  
  salixUserAuthenticationMethod OBJECT-TYPE
       SYNTAX         INTEGER { internal(0), 
                                radius(1),
                                tacacs(2),
                                xtacacs(3),
                                tacacsplus(4) }
       MAX-ACCESS     read-write
       STATUS         current
       DESCRIPTION
            "The user authentication method for all logins into the 
             system.  The following choices are available:
             
                  internal(0)   - The system stores the username/password pairs in
                                  its nonvolatile memory.
                  radius(1)     - Authenticate using the RADIUS protocol.  
                  tacacs(2)     - Authenticate using TACACS protocol.
                  xtacacs(3)    - Authenticate using the XTACACS protocol.
                  tacacsplus(4) - Authenticate using the TACACS+ protocol."
       DEFVAL { internal }
       ::= { salixRadiusMIBObjects 2 }
                           
        
   -- RADIUS Traps
        
   salixRadiusAccessRequestTimeout NOTIFICATION-TYPE
     OBJECTS   { salixRadiusServerIndex,
                 atmfM4TrapAlarmSeverity }
     STATUS    current
     DESCRIPTION
          "Indicates that an Access Request to the specified
           server has timed out.  The default alarm severity 
           for this alarm is 'minor'."
     ::= { salixRadiusMIBTrapPrefix 1 }

   salixRadiusAccessDenied NOTIFICATION-TYPE
     OBJECTS   { salixRadiusServerIndex,
                 atmfM4TrapAlarmSeverity }
     STATUS    current
     DESCRIPTION
          "Indicates that a login attempt was denied by the specified
           server.  This could be due to someone trying to gain
           unauthorized access or due to a misconfiguration of the
           server.  The default alarm severity for this alarm is 'minor'."
     ::= { salixRadiusMIBTrapPrefix 2 }
                     
-- Conformance Statements

salixRadiusGroups      OBJECT IDENTIFIER  ::= { salixRadiusMIBCompliance 1 }
salixRadiusCompliances OBJECT IDENTIFIER  ::= { salixRadiusMIBCompliance 2 }

   salixRadiusGroup OBJECT-GROUP
      OBJECTS {
         salixRadiusServerIndex,
         salixRadiusServerIpAddress,
         salixRadiusServerUdpPort,
         salixRadiusServerSharedSecret,
         salixRadiusServerEnabled
      }
      STATUS         current
      DESCRIPTION    "Salix RADIUS Objects Group"
      ::= { salixRadiusGroups 1}
      
-- Compliance Statements

salixRadiusCompliance MODULE-COMPLIANCE
     STATUS       current
     DESCRIPTION
                  "The basic implementation requirements for the SALIX-RADIUS-MIB."
     MODULE       -- This module
     MANDATORY-GROUPS { salixRadiusGroup }
     ::= { salixRadiusCompliances 1 }

END
