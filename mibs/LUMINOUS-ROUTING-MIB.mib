LUMINOUS-ROUTING-MIB DEFINITIONS ::= BEGIN
     IMPORTS
             MODULE-IDENTITY, OBJECT-TYPE, NOTIFICATION-TYPE,
             ObjectName, Integer32, Counter32, enterprises      
                                              FROM SNMPv2-SMI
             RowStatus, DateAndTime
                               FROM SNMPv2-TC
DisplayString FROM RFC1213-MIB;

  --                   FROM RFC1213-MIB;



  -- IANA-registered  Luminous Network Enterprise Number of 4614

     luminous OBJECT IDENTIFIER ::= { enterprises 4614}


  -- leaving tree-space for the future products:

     lumADM   OBJECT IDENTIFIER ::= { luminous 1}


  --  This MIB module defines various system configurations.

 
     lumRoutingMIB       MODULE-IDENTITY      
                         LAST-UPDATED "0006260000Z"
                         ORGANIZATION "Luminous Networks"
                         CONTACT-INFO 
                                      "  Luminous Technical Support

                                         Postal: Luminous Networks,
                                                 14060 Bubb Road,
                                                 Cupertino, CA 95014

                                            Tel: +1 408 342 6400
                                            Fax: +1 408 863 1100
                                         E-mail: support@luminousnetworks.com
                                         
                                        Authors: Edward Hu
                                            Tel: +1 408 342 6474
                                         E-mail: edward@luminousnetworks.com"
                                         
                                         

                 DESCRIPTION  "The Luminous System MIB contains        
                               information related to the   
                               Luminous system configurations and monitoring." 
                         ::= { lumADM   5}


     lumRouteCfgDownload OBJECT IDENTIFIER ::= { lumRoutingMIB 1}




--  Routing Configuration file download

--  Only single routing configuration file is supported at this stage  


       lumRouteCfgDownloadHost  OBJECT-TYPE
             SYNTAX      DisplayString (SIZE (0..16))
             MAX-ACCESS  read-write
             STATUS      current
             DESCRIPTION  "The IP address or name of the Routing configuration
                           file downloading host."  
            ::= { lumRouteCfgDownload 1 }



       lumRouteCfgDownloadUsrName  OBJECT-TYPE
             SYNTAX      DisplayString (SIZE (0..16))
             MAX-ACCESS  read-write
             STATUS      current
             DESCRIPTION  "The user logging name for accessing the routing
               config file downloading host."
            ::= { lumRouteCfgDownload 2 }


       lumRouteCfgDownloadPasswd  OBJECT-TYPE
             SYNTAX      DisplayString (SIZE (0..16))
             MAX-ACCESS  read-write
             STATUS      current
             DESCRIPTION  "The password associated with the 
                           lumRouteCfgDownloadUsrName when accessing
               the routing config file downloading host."
            ::= {lumRouteCfgDownload 3 }


        lumRouteCfgDownloadPath  OBJECT-TYPE
             SYNTAX      DisplayString (SIZE (0..64))
             MAX-ACCESS read-write
             STATUS     current
             DESCRIPTION  "The routing config file name and its directory 
                           path on the downloading host."
            ::= { lumRouteCfgDownload 4 }


        lumRouteCfgDownloadTimeOut OBJECT-TYPE
             SYNTAX    Integer32
             UNITS     "minutes"
             MAX-ACCESS read-write
             STATUS     current
             DESCRIPTION "The length of time, in minutes, that agent
                          allows the download process to continue."
             DEFVAL {10}
             ::= { lumRouteCfgDownload 5}

        lumRouteCfgDownloadCmd OBJECT-TYPE
         SYNTAX    INTEGER {
              none(1),
              download(2)
            }
             MAX-ACCESS read-write
             STATUS     current
             DESCRIPTION "Set object to download(2) to active the routing  
                          config file download process.  The image downloading
              related objects should have been properly configuered.
              The download command will be rejected if the
              the lumRouteCfgDownloadStatus has a value of 
                          download-in-progress(2)." 

            ::= { lumRouteCfgDownload 6}        


        
        lumRouteCfgDownloadStatus OBJECT-TYPE
            SYNTAX    INTEGER {
                   none(1),
                   download-in-progress(2),
                   download-succeeded(3),
                   download-failed(4)
                 }
            MAX-ACCESS read-only
            STATUS     current
            DESCRIPTION "The status of a previously issued routing config
                         file download command."
            DEFVAL {1}
            ::= { lumRouteCfgDownload 7}


        lumRouteCfgDownloadAbort OBJECT-TYPE
            SYNTAX    INTEGER {
                     none(1),
                     abort(2)
            }
            MAX-ACCESS read-write
            STATUS     current
            DESCRIPTION "Abort the software download process."
            DEFVAL {1}
            ::= { lumRouteCfgDownload 8}


END
