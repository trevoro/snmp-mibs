--
-- OptiView WAN Fiber/Copper Product MIB Module
--
-- This module contains information specific to OptiView Family WAN
-- Fiber/Copper products. (ATM/POS/FrameRelay/PPP)
--

    FNET-OPTIVIEW-WAN-MIB DEFINITIONS ::= BEGIN

        IMPORTS
            TRAP-TYPE              FROM RFC-1215
            ovTrapAgentSysName    FROM FNET-OPTIVIEW-GENERIC-MIB
            ovTrapSeverity        FROM FNET-OPTIVIEW-GENERIC-MIB
            ovTrapStatus          FROM FNET-OPTIVIEW-GENERIC-MIB
            ovTrapDescription     FROM FNET-OPTIVIEW-GENERIC-MIB
            ovTrapOffenderName    FROM FNET-OPTIVIEW-GENERIC-MIB
            ovTrapOffenderNetAddr FROM FNET-OPTIVIEW-GENERIC-MIB
            ovTrapOffenderSubId   FROM FNET-OPTIVIEW-GENERIC-MIB
            fnetOptiViewGeneric   FROM FNET-GLOBAL-REG;

        -- 
        -- Trap Definitions
        --
        -- OptiView WAN Fiber/Copper is assigned specific trap values 12000..12999
        --

        probSonetLinkDown TRAP-TYPE
            ENTERPRISE  fnetOptiViewGeneric
            VARIABLES { ovTrapAgentSysName, ovTrapSeverity,
                        ovTrapStatus, ovTrapDescription,
                        ovTrapOffenderName, ovTrapOffenderNetAddr,
                        ovTrapOffenderSubId }
            DESCRIPTION
                "Monitor the contiguous Line Unavailable or Path Unavailable 
                seconds on the Sonet link.
                
                When the count equals or exceeds the rising threshold,
                the Analyzer generates this trap with ovTrapStatus=discovered.
                Then, when the count descends back below the falling threshold
                the Analyzer generates this trap with ovTrapStatus=resolved."
                
            ::= 12000

        probSonetErrors TRAP-TYPE
            ENTERPRISE  fnetOptiViewGeneric
            VARIABLES { ovTrapAgentSysName, ovTrapSeverity,
                        ovTrapStatus, ovTrapDescription,
                        ovTrapOffenderName, ovTrapOffenderNetAddr ,
                        ovTrapOffenderSubId }
            DESCRIPTION
                "Monitor the count of contiguous Sonet Line Errored seconds 
                or Severely Errored seconds. 
                
                When the count equals or exceeds the rising threshold,
                the Analyzer generates this trap with ovTrapStatus=discovered.
                Then, when the count descends back below the falling threshold
                the Analyzer generates this trap with ovTrapStatus=resolved."

            ::= 12001
        
        probSonetAlarms TRAP-TYPE
            ENTERPRISE  fnetOptiViewGeneric
            VARIABLES { ovTrapAgentSysName, ovTrapSeverity,
                        ovTrapStatus, ovTrapDescription,
                        ovTrapOffenderName, ovTrapOffenderNetAddr ,
                        ovTrapOffenderSubId }
            DESCRIPTION
                "Monitor the presence of Sonet alarms. 
                
                When the count equals or exceeds the rising threshold,
                the Analyzer generates this trap with ovTrapStatus=discovered.
                Then, when the count descends back below the falling threshold
                the Analyzer generates this trap with ovTrapStatus=resolved."

            ::= 12002
        
        probAtmLinkDown TRAP-TYPE
            ENTERPRISE  fnetOptiViewGeneric
            VARIABLES { ovTrapAgentSysName, ovTrapSeverity,
                        ovTrapStatus, ovTrapDescription,
                        ovTrapOffenderName, ovTrapOffenderNetAddr ,
                        ovTrapOffenderSubId }
            DESCRIPTION
                "Monitor the contiguous Loss of Cell Delineation seconds
                on the ATM link.
                
                When the count equals or exceeds the rising threshold,
                the Analyzer generates this trap with ovTrapStatus=discovered.
                Then, when the count descends back below the falling threshold
                the Analyzer generates this trap with ovTrapStatus=resolved."
                
            ::= 12003

        probAtmErrors TRAP-TYPE
            ENTERPRISE  fnetOptiViewGeneric
            VARIABLES { ovTrapAgentSysName, ovTrapSeverity,
                        ovTrapStatus, ovTrapDescription,
                        ovTrapOffenderName, ovTrapOffenderNetAddr ,
                        ovTrapOffenderSubId }
            DESCRIPTION
                "Monitor the rate of the combination of correctable and 
                uncorrectable HEC errors.
                
                When the count equals or exceeds the rising threshold,
                the Analyzer generates this trap with ovTrapStatus=discovered.
                Then, when the count descends back below the falling threshold
                the Analyzer generates this trap with ovTrapStatus=resolved."

            ::= 12004

        probPDUCRCErrors TRAP-TYPE
            ENTERPRISE  fnetOptiViewGeneric
            VARIABLES { ovTrapAgentSysName, ovTrapSeverity,
                        ovTrapStatus, ovTrapDescription,
                        ovTrapOffenderName, ovTrapOffenderNetAddr ,
                        ovTrapOffenderSubId }
            DESCRIPTION
                "Monitor the rate of PDU CRC errors.
                
                When the count equals or exceeds the rising threshold,
                the Analyzer generates this trap with ovTrapStatus=discovered.
                Then, when the count descends back below the falling threshold
                the Analyzer generates this trap with ovTrapStatus=resolved."
                
            ::= 12005


        probPosLinkDown TRAP-TYPE
            ENTERPRISE  fnetOptiViewGeneric
            VARIABLES { ovTrapAgentSysName, ovTrapSeverity,
                        ovTrapStatus, ovTrapDescription,
                        ovTrapOffenderName, ovTrapOffenderNetAddr ,
                        ovTrapOffenderSubId }
            DESCRIPTION
                "Monitor the contiguous loss of HDLC framing (LOF) seconds.
                 
                When the count equals or exceeds the rising threshold,
                the Analyzer generates this trap with ovTrapStatus=discovered.
                Then, when the count descends back below the falling threshold
                the Analyzer generates this trap with ovTrapStatus=resolved."

            ::= 12006

        probPosErrorsDetected TRAP-TYPE
            ENTERPRISE  fnetOptiViewGeneric
            VARIABLES { ovTrapAgentSysName, ovTrapSeverity,
                        ovTrapStatus, ovTrapDescription,
                        ovTrapOffenderName, ovTrapOffenderNetAddr ,
                        ovTrapOffenderSubId }
            DESCRIPTION
                "Monitor the percentage of bad HDLC frames on the Pos link.
                
                When the count equals or exceeds the rising threshold,
                the Analyzer generates this trap with ovTrapStatus=discovered.
                Then, when the count descends back below the falling threshold
                the Analyzer generates this trap with ovTrapStatus=resolved."

            ::= 12007
            

        probLinkUtilization TRAP-TYPE
            ENTERPRISE  fnetOptiViewGeneric
            VARIABLES { ovTrapAgentSysName, ovTrapSeverity,
                        ovTrapStatus, ovTrapDescription,
                        ovTrapOffenderName, ovTrapOffenderNetAddr ,
                        ovTrapOffenderSubId }
            DESCRIPTION
                "Monitor the utilization of the entire pipe bandwidth.
                
                When the count equals or exceeds the rising threshold,
                the Analyzer generates this trap with ovTrapStatus=discovered.
                Then, when the count descends back below the falling threshold
                the Analyzer generates this trap with ovTrapStatus=resolved."
                
            ::= 12008

        probDNSServerNoResp TRAP-TYPE
            ENTERPRISE  fnetOptiViewGeneric
            VARIABLES { ovTrapAgentSysName, ovTrapSeverity,
                        ovTrapStatus, ovTrapDescription,
                        ovTrapOffenderName, ovTrapOffenderNetAddr ,
                        ovTrapOffenderSubId }
            DESCRIPTION
                "Monitor the status of the DNS server. When the management
                port receives no DNS reply from the server address 
                configured via DHCP, and no DNS reply from either the 
                primary or secondary servers statically configured by the
                user, and there was no reply to a broadcast message for 
                a local DNS server, a trap is generated with 
                ovTrapStatus=discovered. 

                When the user causes a DNS server to be rediscovered via
                DHCP, or configures a valid primary or secondary servier
                statically, a trap is generated with ovTrapStatus=resolved."

            ::= 12009

        probDNSServerNowUsing TRAP-TYPE
            ENTERPRISE  fnetOptiViewGeneric
            VARIABLES { ovTrapAgentSysName, ovTrapSeverity,
                        ovTrapStatus, ovTrapDescription,
                        ovTrapOffenderName, ovTrapOffenderNetAddr ,
                        ovTrapOffenderSubId }
            DESCRIPTION
                "Monitor the status of the DNS server. When the management
                port receives no DNS reply from the server address 
                configured via DHCP, and no DNS reply from either the 
                primary or secondary servers statically configured by the
                user, and there WAS a reply to a broadcast message for 
                a local DNS server, a trap is generated with 
                ovTrapStatus=discovered.

                When the user causes a DNS server to be rediscovered via
                DHCP, or statically configures a valid primary or secondary
                server, a trap is generated with ovTrapStatus=resolved."

            ::= 12010

        probLostDHCPLease TRAP-TYPE
            ENTERPRISE  fnetOptiViewGeneric
            VARIABLES { ovTrapAgentSysName, ovTrapSeverity,
                        ovTrapStatus, ovTrapDescription,
                        ovTrapOffenderName, ovTrapOffenderNetAddr ,
                        ovTrapOffenderSubId }
            DESCRIPTION
                "Monitor the status of the management port's DHCP lease.
                When the lease expires a single trap is generated with
                ovTrapStatus=discovered. When the default router resumes
                responding to the PING then a single trap is generated with
                ovTrapStatus=resolved."

            ::= 12011
                     
        probDefaultRouterNoResp TRAP-TYPE
            ENTERPRISE  fnetOptiViewGeneric
            VARIABLES { ovTrapAgentSysName, ovTrapSeverity,
                        ovTrapStatus, ovTrapDescription,
                        ovTrapOffenderName, ovTrapOffenderNetAddr ,
                        ovTrapOffenderSubId }
            DESCRIPTION
                "Monitor PING responses from the default router. When no
                response is received the proble generates a single trap 
                with ovTrapStatus=discovered. When the default router resumes
                responding to the PING then a single trap is generated with
                ovTrapStatus=resolved."

            ::= 12012

        probDiscoveryFull TRAP-TYPE
            ENTERPRISE  fnetOptiViewGeneric
            VARIABLES { ovTrapAgentSysName, ovTrapSeverity,
                        ovTrapStatus, ovTrapDescription,
                        ovTrapOffenderName, ovTrapOffenderNetAddr ,
                        ovTrapOffenderSubId }
            DESCRIPTION
                "When the discovery databases are full a single trap is 
                generated with ovTrapStatus=discovered. This indicates
                new hosts and virtual circuits.will not be added to the
                discovery database. RMON hosts, conversations, and 
                utilization history will continue to be measured.
                Perform a rerun test when desired to clear the discovery
                database."

            ::= 12013


        probClearCounts TRAP-TYPE
            ENTERPRISE  fnetOptiViewGeneric
            VARIABLES { ovTrapAgentSysName, ovTrapSeverity,
                        ovTrapStatus, ovTrapDescription,
                        ovTrapOffenderName, ovTrapOffenderNetAddr ,
                        ovTrapOffenderSubId }
            DESCRIPTION
                "When the user clears statistics for a specific measurement,
                a single trap is generated with ovTrapStatus=discovered, and
                ovTrapSeverity = inform. The type of statistic (e.g top VC) 
                is indicated in the ovTrapDescription field."

            ::= 12014

        
        -- probReset, probRerunTest, and probKeyDevNoResp : see fnetOvGeneric.mib

        probDS1LinkDown TRAP-TYPE
            ENTERPRISE  fnetOptiViewGeneric
            VARIABLES { ovTrapAgentSysName, ovTrapSeverity,
                        ovTrapStatus, ovTrapDescription,
                        ovTrapOffenderName, ovTrapOffenderNetAddr,
                        ovTrapOffenderSubId }
            DESCRIPTION
                "Monitor the T1/E1 Errors and Alarms.
                
                When the count equals or exceeds the rising threshold,
                the Analyzer generates this trap with ovTrapStatus=discovered.
                Then, when the count descends back below the falling threshold
                the Analyzer generates this trap with ovTrapStatus=resolved."
                
            ::= 12015

        probDS1Errors TRAP-TYPE
            ENTERPRISE  fnetOptiViewGeneric
            VARIABLES { ovTrapAgentSysName, ovTrapSeverity,
                        ovTrapStatus, ovTrapDescription,
                        ovTrapOffenderName, ovTrapOffenderNetAddr ,
                        ovTrapOffenderSubId }
            DESCRIPTION
                "Monitor the count of contiguous T1/E1 Errored seconds 
                or Severely Errored seconds. 
                
                When the count equals or exceeds the rising threshold,
                the Analyzer generates this trap with ovTrapStatus=discovered.
                Then, when the count descends back below the falling threshold
                the Analyzer generates this trap with ovTrapStatus=resolved."

            ::= 12016
        
        probDS1Alarms TRAP-TYPE
            ENTERPRISE  fnetOptiViewGeneric
            VARIABLES { ovTrapAgentSysName, ovTrapSeverity,
                        ovTrapStatus, ovTrapDescription,
                        ovTrapOffenderName, ovTrapOffenderNetAddr ,
                        ovTrapOffenderSubId }
            DESCRIPTION
                "Monitor the presence of T1/E1 alarms. 
                
                When the count equals or exceeds the rising threshold,
                the Analyzer generates this trap with ovTrapStatus=discovered.
                Then, when the count descends back below the falling threshold
                the Analyzer generates this trap with ovTrapStatus=resolved."

            ::= 12017

        probDS3LinkDown TRAP-TYPE
            ENTERPRISE  fnetOptiViewGeneric
            VARIABLES { ovTrapAgentSysName, ovTrapSeverity,
                        ovTrapStatus, ovTrapDescription,
                        ovTrapOffenderName, ovTrapOffenderNetAddr,
                        ovTrapOffenderSubId }
            DESCRIPTION
                "Monitor the DS1/E3 Errors and Alarms.
                
                When the count equals or exceeds the rising threshold,
                the Analyzer generates this trap with ovTrapStatus=discovered.
                Then, when the count descends back below the falling threshold
                the Analyzer generates this trap with ovTrapStatus=resolved."
                
            ::= 12018

        probDS3Errors TRAP-TYPE
            ENTERPRISE  fnetOptiViewGeneric
            VARIABLES { ovTrapAgentSysName, ovTrapSeverity,
                        ovTrapStatus, ovTrapDescription,
                        ovTrapOffenderName, ovTrapOffenderNetAddr ,
                        ovTrapOffenderSubId }
            DESCRIPTION
                "Monitor the count of contiguous DS3/E3 Errored seconds 
                or Severely Errored seconds. 
                
                When the count equals or exceeds the rising threshold,
                the Analyzer generates this trap with ovTrapStatus=discovered.
                Then, when the count descends back below the falling threshold
                the Analyzer generates this trap with ovTrapStatus=resolved."

            ::= 12019
        
        probDS3Alarms TRAP-TYPE
            ENTERPRISE  fnetOptiViewGeneric
            VARIABLES { ovTrapAgentSysName, ovTrapSeverity,
                        ovTrapStatus, ovTrapDescription,
                        ovTrapOffenderName, ovTrapOffenderNetAddr ,
                        ovTrapOffenderSubId }
            DESCRIPTION
                "Monitor the presence of DS1/E3 alarms. 
                
                When the count equals or exceeds the rising threshold,
                the Analyzer generates this trap with ovTrapStatus=discovered.
                Then, when the count descends back below the falling threshold
                the Analyzer generates this trap with ovTrapStatus=resolved."

            ::= 12020

        probFrLmiLinkDown TRAP-TYPE
            ENTERPRISE  fnetOptiViewGeneric
            VARIABLES { ovTrapAgentSysName, ovTrapSeverity,
                        ovTrapStatus, ovTrapDescription,
                        ovTrapOffenderName, ovTrapOffenderNetAddr ,
                        ovTrapOffenderSubId }
            DESCRIPTION
                "Monitor the contiguous inactive LMI seconds on the 
                 Frame Relay link.
                
                When the count equals or exceeds the rising threshold,
                the Analyzer generates this trap with ovTrapStatus=discovered.
                Then, when the count descends back below the falling threshold
                the Analyzer generates this trap with ovTrapStatus=resolved."
                
            ::= 12021

        probFrLmiErrors TRAP-TYPE
            ENTERPRISE  fnetOptiViewGeneric
            VARIABLES { ovTrapAgentSysName, ovTrapSeverity,
                        ovTrapStatus, ovTrapDescription,
                        ovTrapOffenderName, ovTrapOffenderNetAddr ,
                        ovTrapOffenderSubId }
            DESCRIPTION
                "Monitor LMI errors on the Frame Relay link.
                
                When the LMI errors exist, the Analyzer generates this trap
                with ovTrapStatus=discovered. When the LMI errors subside,
                the Analyzer generates this trap with ovTrapStatus=resolved."

            ::= 12022

        probFrErrorsDetected TRAP-TYPE
            ENTERPRISE  fnetOptiViewGeneric
            VARIABLES { ovTrapAgentSysName, ovTrapSeverity,
                        ovTrapStatus, ovTrapDescription,
                        ovTrapOffenderName, ovTrapOffenderNetAddr ,
                        ovTrapOffenderSubId }
            DESCRIPTION
                "Monitor the count of contiguous Errored Frame seconds.
                
                When the count equals or exceeds the rising threshold,
                the Analyzer generates this trap with ovTrapStatus=discovered.
                Then, when the count descends back below the falling threshold
                the Analyzer generates this trap with ovTrapStatus=resolved."

            ::= 12023

        probVcDown TRAP-TYPE
            ENTERPRISE  fnetOptiViewGeneric
            VARIABLES { ovTrapAgentSysName, ovTrapSeverity,
                        ovTrapStatus, ovTrapDescription,
                        ovTrapOffenderName, ovTrapOffenderNetAddr ,
                        ovTrapOffenderSubId }
            DESCRIPTION
                "Monitor the state of Frame Relay VCs.
                
                When the PVC status received via the local in-channel 
                signaling reports status = 'deleted' or 'inactive',
                the Analyzer generates this trap with ovTrapStatus=discovered.
                Then, when the in-channel signaling reports status = 'active'
                the Analyzer generates this trap with ovTrapStatus=resolved."
                
            ::= 12024

        probInvalidDlci TRAP-TYPE
            ENTERPRISE  fnetOptiViewGeneric
            VARIABLES { ovTrapAgentSysName, ovTrapSeverity,
                        ovTrapStatus, ovTrapDescription,
                        ovTrapOffenderName, ovTrapOffenderNetAddr ,
                        ovTrapOffenderSubId }
            DESCRIPTION
                "Monitor the state of Frame Relay DLCI for invalid.
                
                When the Analyzer receives an inactive or unknown DLCI 
                it generates this trap with ovTrapStatus=discovered.
                If the full-status LMI later reports the DLCI active,
                the Analyzer generates this trap with ovTrapStatus=resolved."
                
            ::= 12025

        probFrDEUnderCIRUtilization TRAP-TYPE
            ENTERPRISE  fnetOptiViewGeneric
            VARIABLES { ovTrapAgentSysName, ovTrapSeverity,
                        ovTrapStatus, ovTrapDescription,
                        ovTrapOffenderName, ovTrapOffenderNetAddr ,
                        ovTrapOffenderSubId }
            DESCRIPTION
                "Monitor the utilization of % DE under CIR.
                
                When the count equals or exceeds the rising threshold,
                the Analyzer generates this trap with ovTrapStatus=discovered.
                Then, when the count descends back below the falling threshold
                the Analyzer generates this trap with ovTrapStatus=resolved."
                
            ::= 12026

        probHdlcLinkDown TRAP-TYPE
            ENTERPRISE  fnetOptiViewGeneric
            VARIABLES { ovTrapAgentSysName, ovTrapSeverity,
                        ovTrapStatus, ovTrapDescription,
                        ovTrapOffenderName, ovTrapOffenderNetAddr ,
                        ovTrapOffenderSubId }
            DESCRIPTION
                "Monitor the contiguous loss of HDLC framing seconds.
                 
                When the count equals or exceeds the rising threshold,
                the Analyzer generates this trap with ovTrapStatus=discovered.
                Then, when the count descends back below the falling threshold
                the Analyzer generates this trap with ovTrapStatus=resolved."

            ::= 12027

        probHdlcErrorsDetected TRAP-TYPE
            ENTERPRISE  fnetOptiViewGeneric
            VARIABLES { ovTrapAgentSysName, ovTrapSeverity,
                        ovTrapStatus, ovTrapDescription,
                        ovTrapOffenderName, ovTrapOffenderNetAddr ,
                        ovTrapOffenderSubId }
            DESCRIPTION
                "Monitor the percentage of bad HDLC frames.
                
                When the count equals or exceeds the rising threshold,
                the Analyzer generates this trap with ovTrapStatus=discovered.
                Then, when the count descends back below the falling threshold
                the Analyzer generates this trap with ovTrapStatus=resolved."

            ::= 12028

        probFrDteDceReversed TRAP-TYPE
            ENTERPRISE  fnetOptiViewGeneric
            VARIABLES { ovTrapAgentSysName, ovTrapSeverity,
                        ovTrapStatus, ovTrapDescription,
                        ovTrapOffenderName, ovTrapOffenderNetAddr ,
                        ovTrapOffenderSubId }
            DESCRIPTION
                "WAN cable reversed from LMI discovered DTE/DCR (FR only)."

            ::= 12029

        probKeyDevPingLatency TRAP-TYPE
            ENTERPRISE  fnetOptiViewGeneric
            VARIABLES { ovTrapAgentSysName, ovTrapSeverity,
                        ovTrapStatus, ovTrapDescription,
                        ovTrapOffenderName, ovTrapOffenderNetAddr ,
                        ovTrapOffenderSubId }
            DESCRIPTION
                "Measures the roundtrip PING latency to a key device.
               
                When the count equals or exceeds the rising threshold,
                the Analyzer generates this trap with ovTrapStatus=discovered.
                Then, when the count descends back below the falling threshold
                the Analyzer generates this trap with ovTrapStatus=resolved."

            ::= 12030

    END
