-- ZyXEL Communications Corporation
-- Private Enterprise MIB definition 
  
-- This file describes the ZyXEL Communications Corporation Enterprise MIB.
-- It contains ZyXEL products OIDs, and common managed objects.

-- $Log: ZYXEL-PORT-SECURITY-MIB.mib $
-- Revision 1.4  2012/09/19 07:44:33  Kevin
-- if it's leaf node, revise the vender name from zyxel to zy
-- Revision 1.3  2012/08/22 09:47:43  Kevin
-- clean warning for SNMPc
-- Revision 1.2  2012/07/05 06:24:20  Kevin
-- 1. upgrade from SNMP to SNMPv2 
-- 2. clean warning
-- Revision 1.1  2012/05/30 07:50:26  Kevin
-- Initial revision

ZYXEL-PORT-SECURITY-MIB DEFINITIONS ::= BEGIN

    IMPORTS
	enterprises		FROM RFC1155-SMI                                
	
	OBJECT-TYPE
		FROM SNMPv2-SMI			-- RFC2578	
	RowStatus, DateAndTime, TruthValue, StorageType, MacAddress
		FROM SNMPv2-TC			-- RFC2579
	DisplayString                                          
	  	FROM RFC1213-MIB
	EnabledStatus
		FROM  P-BRIDGE-MIB
	PortList
		FROM  Q-BRIDGE-MIB
	dot1dBasePort
       	FROM BRIDGE-MIB
	InterfaceIndexOrZero			-- RFC2863
		FROM IF-MIB
	SnmpAdminString
		FROM SNMP-FRAMEWORK-MIB		-- RFC2571
	InetAddressType, InetAddress
		FROM INET-ADDRESS-MIB		-- RFC2851
	OperationResponseStatus
		FROM DISMAN-PING-MIB
    Counter, TimeTicks
        FROM RFC1155-SMI
    BridgeId, Timeout
        FROM BRIDGE-MIB  
    dot1agCfmMdIndex 
		FROM IEEE8021-CFM-MIB
	dot1agCfmMaIndex
		FROM IEEE8021-CFM-MIB	
	dot1agCfmMepIdentifier
		FROM IEEE8021-CFM-MIB   	
    IpAddress
        FROM SNMPv2-SMI
    ifIndex
    	FROM IF-MIB					-- RFC2863
    NOTIFICATION-TYPE
        FROM SNMPv2-SMI
    sysObjectID 
        FROM RFC1213-MIB 
	ospfIfIpAddress, ospfAddressLessIf, ospfAreaId, ospfNbrIpAddr, ospfNbrAddressLessIndex,
	ospfLsdbAreaId, ospfLsdbType, ospfLsdbLsid, ospfLsdbRouterId, ospfVirtIfAreaId, ospfVirtIfNeighbor
		FROM OSPF-MIB
	esMgmt			
		FROM ZYXEL-ES-SMI;


	zyxelPortSecurity MODULE-IDENTITY
		LAST-UPDATED	"201207010000Z"    
		ORGANIZATION "Enterprise Solution ZyXEL"     
		CONTACT-INFO
			""	   
		DESCRIPTION
			"The subtree for dhcp"
		::= { esMgmt 66 }
		
	zyxelPortSecuritySetup  OBJECT IDENTIFIER ::= { zyxelPortSecurity 1 }
	
	
-- *******************************************************************
-- *
-- * zyxelPortSecuritySetup
-- *
-- *******************************************************************

-- zyxelPortSecurityState
 		zyPortSecurityState OBJECT-TYPE
        SYNTAX  EnabledStatus
        MAX-ACCESS  read-write
        STATUS  current
        DESCRIPTION
			"Enable/Disable port security on the switch."
        ::= { zyxelPortSecuritySetup 1 }
        
-- zyxelPortSecurityPortTable
        zyxelPortSecurityPortTable OBJECT-TYPE
        SYNTAX	SEQUENCE OF ZyxelPortSecurityPortEntry
        MAX-ACCESS  not-accessible
        STATUS  current
        DESCRIPTION
			"The table contains port security on the specified port configuration. "
        ::= { zyxelPortSecuritySetup 2 }
        
		zyxelPortSecurityPortEntry OBJECT-TYPE
        SYNTAX	ZyxelPortSecurityPortEntry
        MAX-ACCESS	not-accessible
        STATUS	current
        DESCRIPTION    	
			"An entry contains port security on the specified port configuration. "
        INDEX          	{ dot1dBasePort }
        ::= { zyxelPortSecurityPortTable 1 }

        ZyxelPortSecurityPortEntry ::=
           SEQUENCE {
        	zyPortSecurityPortState			EnabledStatus,
			zyPortSecurityPortLearnState	EnabledStatus,
			zyPortSecurityPortMacLimit		INTEGER
           }

        zyPortSecurityPortState OBJECT-TYPE
        SYNTAX  EnabledStatus
        MAX-ACCESS  read-write
        STATUS  current
        DESCRIPTION
 			"Enable/Disable Port Security on the specified port. Enable(1) means this port only accept frames 
 			from static MAC addresses that are configured for the port,and dynamic MAC address frames up to the 
 			number specified by zyxelPortSecurityPortMacLimit object."
        ::= { zyxelPortSecurityPortEntry 1 }
        
        zyPortSecurityPortLearnState OBJECT-TYPE
        SYNTAX  EnabledStatus
        MAX-ACCESS  read-write
        STATUS  current
        DESCRIPTION
			"Enable/Disable MAC address learning on the specified port. MAC address learning reduces outgoing 
			broadcast traffic. For MAC address learning to occur on a port, the port itself must be active with 
			address learning enabled. "
        ::= { zyxelPortSecurityPortEntry 2 }
        
        zyPortSecurityPortMacLimit OBJECT-TYPE
        SYNTAX  INTEGER
        MAX-ACCESS  read-write
        STATUS  current
        DESCRIPTION
			"Set this field to limit the number of (dynamic) MAC addresses that may be learned on a port. For 
			example, if you set this field to 5 on port 2, then only the devices with these five learned MAC 
			addresses may access port 2 at any one time. A sixth device must wait until one of the five learned 
			MAC addresses ages out. "
        ::= { zyxelPortSecurityPortEntry 3 }

-- zyxelPortSecurityMacFreeze
		zyPortSecurityMacFreeze OBJECT-TYPE
        SYNTAX  PortList
        MAX-ACCESS  read-write
        STATUS  current
        DESCRIPTION
                    "This entry is used to execute MacFreeze action to port. 
					It's meaningless while reading this entry."
        ::= { zyxelPortSecuritySetup 3 }     
        
-- zyxelPortSecurityMaxNumberOfVMLs
		zyPortSecurityMaxNumberOfVMLs OBJECT-TYPE
		SYNTAX  INTEGER
        MAX-ACCESS  read-only
        STATUS  current
        DESCRIPTION
                    "The maximum number of port security VML that can be created."
        ::= { zyxelPortSecuritySetup 4 }

-- zyxelPortSecurityVMLTable     
    	zyxelPortSecurityVMLTable OBJECT-TYPE
        SYNTAX	SEQUENCE OF ZyxelPortSecurityVMLEntry
        MAX-ACCESS  not-accessible
        STATUS  current
        DESCRIPTION
                 	"The table contains VLAN MAC address limit on the specified port for the specified VLAN configuration. "
        ::= { zyxelPortSecuritySetup 5 }
        
		zyxelPortSecurityVMLEntry OBJECT-TYPE
        SYNTAX	ZyxelPortSecurityVMLEntry
        MAX-ACCESS	not-accessible
        STATUS	current
        DESCRIPTION    	
					"An entry contains VLAN MAC address limit on the specified port for the specified VLAN configuration. "
        INDEX          	{ zyPortSecurityVMLPort, zyPortSecurityVMLVID }
        ::= { zyxelPortSecurityVMLTable 1 }

        ZyxelPortSecurityVMLEntry ::=
           SEQUENCE {
        	zyPortSecurityVMLPort		INTEGER,
			zyPortSecurityVMLVID		INTEGER,
			zyPortSecurityVMLMacLimit	INTEGER,
			zyPortSecurityVMLRowStatus	RowStatus 
           }

        zyPortSecurityVMLPort OBJECT-TYPE
        SYNTAX  INTEGER
        MAX-ACCESS  not-accessible
        STATUS  current
        DESCRIPTION
                      	"The configured port number of VLAN MAC Limit."
        ::= { zyxelPortSecurityVMLEntry 1 }
        
        zyPortSecurityVMLVID OBJECT-TYPE
        SYNTAX  INTEGER
        MAX-ACCESS  not-accessible
        STATUS  current
        DESCRIPTION
                      	"The configured VLAN number of VLAN MAC Limit."
        ::= { zyxelPortSecurityVMLEntry 2 }
        
        zyPortSecurityVMLMacLimit OBJECT-TYPE
        SYNTAX  INTEGER
        MAX-ACCESS  read-write
        STATUS  current
        DESCRIPTION
			"Set this field to limit the number of (dynamic) MAC addresses that may be learned on a port in a 
			specified VLAN. For example, if you set this field to 5 on port 2 in VLAN 3, then only the devices 
			with these five learned MAC addresses may access port 2 in VLAN 3 at any one time. A sixth device 
			would have to wait until one of the five learned MAC addresses aged out. "
        ::= { zyxelPortSecurityVMLEntry 3 }   
         
        zyPortSecurityVMLRowStatus OBJECT-TYPE
        SYNTAX  RowStatus
        MAX-ACCESS  read-create
        STATUS  current
        DESCRIPTION
			"This object allows entries to be created and deleted from the portSecurityVMLTable."
        ::= { zyxelPortSecurityVMLEntry 4 }


END
