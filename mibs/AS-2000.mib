--=============================================================================
--
-- Lucent Technologies - Wireless Communications and Networking Division 
-- 260 14th Street NW Suite 400
-- Atlanta, GA 30318
-- USA
-- Tel:   +1.404.898.1764
-- Fax:   +1.404.888.1182
-- Email: dborges@lucent.com
--
--=============================================================================
--
-- Access Server 2000 Management Information Base
--
--=============================================================================
--
-- FILENAME:	as2000-yymmdd.mib (yy = year, mm = month, dd = day)
--
-- DESIGNER:	Daniel R. Borges
--
-- TITLE:		Access Server 2000 Management Information Base
--
-- USED IN:		Access Server 2000 Release 2.0 for SNMP based Management.
--
--=============================================================================
--
-- Document Version Info                             
--
--=============================================================================
--  Version  Date      Author             Description       
--=============================================================================
--   1.0               Lucent             Original Creation.       
--=============================================================================
--   2.0   6th April   Future Software 	  Added MIB objects for  IAPP and IPX,
--         2000                           CLI status,Console Port.
--=============================================================================
--   2.1   19th April  Future Software 	  Wavelan card details are put in a   
--         2000                           table with ifIndex as index column, 
--                                        to support two wavelan cards.
--                                        Serial and Telnet parameters added.
--                                        Link Test parameters added to wavelan
--                                        interface table. Password for serial 
--                                        console is removed as per Lucent.    
--                                        NOTE: Telnet parameters will be
--                                            removed if their is no support
--                                            for telnet MIB in VxWorks.
--=============================================================================
--   3.0   18th May    Future Software 	  psIappAnnRespTime made as read-only.
--         2000                           Wavelan scalar objects are retained
--                                        as it is in PL1.0.           
--                                        AS2000 BASE OID given as orinoco.3 
--                                        as per the conf call with LUCENT.     
--                                        psIpxEthernetEncapsulationFormat  
--                                        object added to IPX group.        
--                                        MIB baselined after these changes.
--=============================================================================
--   3.1   7 Sept      DRB, Lucent        Modifications to IAPP Parameters.
--         2000                           The values for the following IAPP
--                                        parameters have been modified:
--                                            psIappAnnInterval
--                                            psIappAnnRespTime
--                                            psIappHandOvrTimeOut
--                                            psIappMaxHandOvrRetries
--=============================================================================
--   3.2   8 Sept      Gopal, FS          Correction made to IAPP Parameter
--		   2000                           values.
--=============================================================================
--   3.3   11 Sept     DRB, Lucent        Added TRAPs that are present in 
--         2000                           AS-2000 R1.0 (publan.mib) and were
--                                        not present in this mib for AS-2000
--                                        R2.0.  In addition, PPP Idle Session
--                                        Timeout was included.
--=============================================================================
--   3.4   27 Sept     Ganesh, FS         Added new objects from the 1.51.03's 
--         2000                           publan.mib. The objects are 
--                                        psContactEmail & psBootROMVersion.
--                                        
--         27 Sept     Ramkumar, FS       Added psPPPIPRangeTableComment in the
--         2000                           Table psPPPIPRangeTable.
--=============================================================================
--   3.5   16 Oct      DRB, Lucent        Clean-up of unnecessary objects.
--         2000
--=============================================================================
--   3.6   30 Oct      DRB, Lucent        Traps were added in order to inform
--         2000                           what task has suspended
--=============================================================================
--   3.7   1 Nov       DRB, Lucent        The following table indexes where 
--         2000                           changed from non-accessible to 
--                                        read-only for CLI access:
--                                            psSNMPManagerIndex
--                                            psPPPMACIPTableIndex
--                                            psPPPIPRangeTableIndex
--                                            radiusServerIndex
--=============================================================================
--   3.8   6 Nov       G.Ramkumar, FS     Changed Mib variables from dhcp-relay 
--	       2000				              to dhcp-relay.  Added the value 
--                                        delete(3) to the Mib Variable 
--                                        radiusServerEnabled.  Renamed the Mib 
--                                        variables psBootROMVersion and radius 
--                                        ClientMib.  Added 
--                                        psTestSNMPReadWritePassword required 
--                                        for verification of the password.	
--					                      Removed multiple occurances of 
-- 					                      AccessServerTaskSuspended. Added 
--                                        AccessServerSuspendedTaskName.
--=============================================================================
--   3.9   10 Nov      DRB, Lucent        Added pscdTFTPFileType to agent 
--         2000                           group.  Change description for 
--                                        accessServer traps removing reference 
--                                        of wavelan and pubstation.
--=============================================================================
--   4.0   13 Nov      DRB, Lucent        Renamed psBootROMVersion to 
--         2000                           psBSPBootloaderVersion.
--=============================================================================
--   4.1   27 Nov      DRB, Lucent        Changed psIPAddressType to read-write
--         2000                           and values to static and dynamic.
--=============================================================================
--   4.2   5 Dec       DRB, Lucent        Added AS Client IPX Table and 
--         2000                           device serial number.
--=============================================================================
--   4.3   6 Dec       DRB, Lucent        Changed the bsp-bootloader file type 
--         2000                           to bspbl in order for it to be
--                                        displayed correctly in the 
--                                        AS Manager.  Changed the name from
--                                        pscdTFTPFiletype to psTFTPFileType
--                                        for consistency.
--=============================================================================
--   4.4   19 Dec      G.Ramkumar         Changed the AS Client IPX table
--         2000        FS                 parameter names. This is to ensure 
--                                        that the variables displayed 
--                                        correctly in the may not only 
--                                        restrict to IPX Clients.
--=============================================================================
--   4.5   19 Dec      C S Tewari         Changed the comment for 
--         2000        FS                 psIPAddressType.                                        
--=============================================================================
--   4.6   25 Dec      T.S. Shankar       Changed type of IPXNetworkNUmber 
--         2000        FS                 paramter from Ipaddress type to 
--                                       OCTET STRING for MR LUCin01666
--=============================================================================
--   4.7   21 Dec      DRB, Lucent        Added Link Test group for remote link
--         2000                           test function.
--                                        Suresh Included Remote Link Test Part
--                                        in the Original MIB for Development 
--                                        and Testing
--=============================================================================
--   4.8   10 Jan      Suresh T           Added oriLinkTestInterface and
--         2001        FS                 oriLinkTestRadioType in the Link Test
--                                        Group.
--=============================================================================
--   4.9   25 Jan      DRB, Lucent        Added IAPP table in order to monitor
--         2001                           IAPP enabled Access Servers in the
--                                        same subnet.  Addressed in MR 1658.
--============================================================================= 
--   5.0   29 Jan      G.Ramkumar         Modified Index Name of psWlanIfTable
--         2001        FS                 as change required by CLI.
--                                        Added new object in pliWlanIfTable
--                                        for MR LUCin01745.
--                                        Added traps for Radius Authentication
--                                        not configured & Accounting not 
--                                        configured.             
--                                        Modified the Status integer field in 
--                                        psPPPSessionIdleTimeOut for 
--                                        MRLUCin01706.  Deleted Object 
--                                        psPPPMaxNoOfUsers as it added as a 
--                                        part of pliWlanIfTable.
--                                        ServerType in RadiusTable made as 
--                                        read-only as the server type is 
--                                        determined by the Index.
--============================================================================= 
--   5.1   1 Feb      G.Ramkumar          Reverted back the MaxNoOfUsers Object
--         2001        FS                 to PPPSetup Group and removed the 
--                                        MaxNoOfUsers object from the Physical
--                                        Interface Table.
--=============================================================================
--   5.2   23 Feb	  DRB, Lucent		  Add traps to indicate that BootP 
--         2001                           has failed and/or DHCP has failed.
--=============================================================================
--   5.3   20 Mar	  G.Ramkumar		  Added psBroadcastMessage Object 
--         2001       FS                  for MR LUCin01828 
--                                        Added psPOSTVersionNumber and
--                                        psHarwareVersionNumber for MR 
--                                        LUCin01581
--                                        Added traps for MR LUCin01784 &
--                                        LUCin01807.
--                                        Added values to MibVariable 
--                                        psTFTPFileType for MR LUCin01737
--=============================================================================
--   5.4   March 21   DRB, Lucent		  Modified psTelnetStatus to 
--         2001                           psTelnetSessions in order to enable/
--                                        disable Telnet access and/or 
--                                        configure the number of active telnet
--                                        sessions.
--                                        accessServerTFTPDownloadInitiated has
--                                        been removed.
--                                        Removed the uploadall and downloadall
--                                        from the TFTP file types, and added
--                                        AllConfigFiles.
--                                        Renamed the following traps:
--                                        - accessServerIncompatibleWavelan to
--                                          accessServerWLCIncompatibleFirmware
--                                        - accessServerWavelanCardFailure to
--                                          accessServerWLCFailure
--                                        - accessServerWavelanCardRemoved to
--                                          accessServerWLCRemoval
--                                        Added the following traps:
--                                        - accessServerWLCVoltageDiscrepancy
--                                        - accessServerWLCIncompatibleVendor
--                                        - accessServerWLCFirmwareDownload-
--                                                                     Failure
--                                        Added psASClientSessionUpTime to the
--                                        AS Client Table.
--=============================================================================
--   5.5   March 23   DRB, Lucent		  Added TimeTicks to Import List. 
--         2001                           Corrected integer values to start
--                                        with lower-case characters.
--                                        Removed AS-2000 IAPP Table (commented
--                                        out). 
--=============================================================================
--   5.6   March 26   DRB, Lucent		  Change access to read-only for the  
--         2001                           following Serial Interface Objects:
--                                         - psSerialDataBits
--                                         - psSerialParity
--                                         - psSerialStopBits
--                                        Image Related Trap Group has been
--                                        added with the following traps:
--                                         - accessServerZeroSizeImage
--                                         - accessServerNonVxWorksImage
--                                         - accessServerImageTooLarge
--                                        Removed auto as a value for 
--                                        psSerialBaudRate since not supported.
--                                        Removed hardware as a value for
--                                        psSerialFlowControl since not 
--                                        supported.
--=============================================================================
--   5.7   March 29   DRB, Lucent		  Removed baud115200 value for 
--         2001                           psSerialBaudRate since not supported.
--                                        Added the following objects:
--                                         - psASClientPacketsIn
--                                         - psASClientPacketsOut
--=============================================================================
--
-- COMPILER:	MG-Soft MIB compiler
--
--=============================================================================

--=============================================================================
--					Copyright (C) 2000 Lucent Technologies
--							Lucent - PROPRIETARY
--		Disclosure to third parties or reproduction in any from
--		whatsoever, without prior written consent, is strictly forbiden.
--=============================================================================

--=============================================================================
-- Includes
--=============================================================================

--#condInclude "rfc1155.smi"
--#condInclude "rfc1212.smi"
--#condInclude "rfc1213.inc"
--#condInclude "rfc1215.smi"

--=============================================================================
-- Access Server 2000 MIBs Begin
--=============================================================================

AS-2000

DEFINITIONS ::= BEGIN

IMPORTS

    enterprises, IpAddress, Counter, TimeTicks
        FROM RFC1155-SMI

        OBJECT-TYPE
            FROM RFC-1212

        TRAP-TYPE
	        FROM RFC-1215;

        DisplayString ::=
            OCTET STRING
            -- This data type is used to model textual information taken
            -- from the NVT ASCII character set.  By convention, objects
            -- with this syntax are declared as having
            --
            --      SIZE (0..255)

        PhysAddress ::=
            OCTET STRING
            -- This data type is used to model media addresses.  For many
            -- types of media, this will be in a binary representation.
            -- For example, an ethernet address would be represented as
            -- a string of 6 octets.

--=============================================================================
-- Defining the MIB OID tree for AS-2000
--=============================================================================
 
    lucent    OBJECT IDENTIFIER ::= { enterprises 1751 }
    mibs      OBJECT IDENTIFIER ::= { lucent 2 }
    orinoco   OBJECT IDENTIFIER ::= { mibs 4 }
    as2000    OBJECT IDENTIFIER ::= { orinoco 3 }

--=============================================================================
-- Defining the Product Identification for AS-2000 (to be used for sysObjectID)
--=============================================================================

    products        OBJECT IDENTIFIER ::= { lucent 1 }
    orinocoProducts OBJECT IDENTIFIER ::= { products 4 }
    as2000Product   OBJECT IDENTIFIER ::= { orinocoProducts 4 }

--=============================================================================
-- The various groups in this agent
--=============================================================================

    orinocoInterface    OBJECT IDENTIFIER ::= { as2000 3 }
    orinocoSNMPSetup    OBJECT IDENTIFIER ::= { as2000 4 }
    orinocoPPPSetup     OBJECT IDENTIFIER ::= { as2000 5 }
    orinocoAgent        OBJECT IDENTIFIER ::= { as2000 6 } 
    radius              OBJECT IDENTIFIER ::= { as2000 7 }
    orinocoShimECPSetup OBJECT IDENTIFIER ::= { as2000 8 }
    orinocoDiagnostics  OBJECT IDENTIFIER ::= { as2000 10 }
    orinocoIAPP         OBJECT IDENTIFIER ::= { as2000 11 }
    orinocoIPX          OBJECT IDENTIFIER ::= { as2000 12 }
    orinocoLinkTest     OBJECT IDENTIFIER ::= { as2000 13 }
    accessServerTraps   OBJECT IDENTIFIER ::= { as2000 15 }

--=============================================================================
-- The sub-groups of orinocoInterface
--=============================================================================

    orinocoPHY          OBJECT IDENTIFIER ::= { orinocoInterface 2 }
    orinocoDriver       OBJECT IDENTIFIER ::= { orinocoInterface 4 }

--=============================================================================
-- The orinocoPHY sub-group of orinocoInterface
--=============================================================================

    pliSystemName OBJECT-TYPE
	    SYNTAX DisplayString
        ACCESS read-write
	    STATUS mandatory
	    DESCRIPTION				
		    "The sysName of the Access Server. This may be used for 
		    diagnostic purposes. This name will be the same as the
		    sysName of the system group of MIB II"
        ::= { orinocoPHY 1 }

    psWlanIfTable OBJECT-TYPE
	    SYNTAX SEQUENCE OF PsWlanIfEntry
	    ACCESS not-accessible
	    STATUS mandatory
	    DESCRIPTION
		    "The table contains the information about the
		    wavelan interfaces present in the Access Server."
        ::= { orinocoPHY 2 }

    psWlanIfEntry OBJECT-TYPE
	    SYNTAX PsWlanIfEntry
	    ACCESS not-accessible
	    STATUS mandatory
	    DESCRIPTION
	        "The entry in the wavelan interfac table. Described
	        next."
        INDEX { pliWlanIfIndex }
        ::= { psWlanIfTable 1 }

	PsWlanIfEntry ::=
	    SEQUENCE
	        {
	            pliWlanIfIndex                       INTEGER,
	            pliWlanIfNetworkName                 DisplayString,
	            pliWlanIfMACAddress	                 PhysAddress,
	            pliWlanIfMediumReservation           INTEGER,
	            pliWlanIfTransmitRate	             INTEGER,
	            pliWlanIfOperatingFrequency          INTEGER,
	            pliWlanIfAPDensity	                 INTEGER,
	            pliWlanIfClosedSystem 	             INTEGER,
	            pliWlanIfAllowedTransmitRates        INTEGER,
	            pliWlanIfRegulatoryDomainList        OCTET STRING,
	            pliWlanIfAllowedOperatingFrequencies INTEGER,
	            pliWlanIfCapabilityOptions           INTEGER,
	            pliWlanIfProfileCode                 INTEGER
	        }

    pliWlanIfIndex OBJECT-TYPE
        SYNTAX  INTEGER
        ACCESS  read-only
        STATUS  mandatory
        DESCRIPTION
            "A unique value for each interface. The value for
			each interface must remain constant at
            least from one re-initialization of the entity's
            network management system to the next re-
            initialization."
        ::= { psWlanIfEntry 1 }
	  
	pliWlanIfNetworkName OBJECT-TYPE
	    SYNTAX DisplayString
	    ACCESS read-write
	    STATUS mandatory
	    DESCRIPTION
		    "The network name of this wavelan interface"
	    ::= { psWlanIfEntry 2 }

	pliWlanIfMACAddress	OBJECT-TYPE
	    SYNTAX PhysAddress
	    ACCESS read-only
	    STATUS mandatory
	    DESCRIPTION
		    "The MAC address of the wavelan card present in this interface."
	    ::= { psWlanIfEntry 3 }

	pliWlanIfMediumReservation 	OBJECT-TYPE
	    SYNTAX INTEGER(0..2347)
	    ACCESS read-write
	    STATUS mandatory
	    DESCRIPTION
		    "The medium reservation value. The range is 0 - 2347.
	         Default is 2347 - means disabled.
		     Medium reservation specifies the number of octets in
		     a message above which a RTS/CTS handshake is performed."
        ::= { psWlanIfEntry 4 }

	pliWlanIfTransmitRate	OBJECT-TYPE
	    SYNTAX INTEGER
		--    {
		--        one-fixed(1),
		 --       two-fixed(2),
		--        two-autofallback(3),
		--        fixed-medium(4),
		--        fixed-high(5),
		--        auto-fallback-standard(6),
		--        auto-fallback-medium(7)
          --  }
        ACCESS read-write
	    STATUS mandatory
        DESCRIPTION
		    "The transmit rate of this interface."
        ::= { psWlanIfEntry 5 }
        
	pliWlanIfOperatingFrequency OBJECT-TYPE
	    SYNTAX INTEGER(1..14)
        ACCESS read-write
        STATUS mandatory
	    DESCRIPTION
	        "The RF channel that the Access Server is working on."
        ::= { psWlanIfEntry 6 }

	pliWlanIfAPDensity	OBJECT-TYPE
	    SYNTAX INTEGER
	   --      {
	    --	     low(1),
	    --	     medium(2),
	    --	     high(3)
	    --     }
        ACCESS read-write
	    STATUS mandatory
        DESCRIPTION
		    "The AP density in the region."
	    ::= { psWlanIfEntry 7 }

	pliWlanIfClosedSystem 	OBJECT-TYPE
	    SYNTAX INTEGER
	     --   {
	     --       closed(1),
	     --       open(2)
	     --  }
	    ACCESS read-write
	    STATUS mandatory
	    DESCRIPTION
		    "This flag identifies whether the Access Server will accept 
		    associate requests in this interface, from AS-Clients having a 
		    network name of 'ANY'. The Access Server should always be a closed 
		    station and such requests should always be rejected. This flag is 
		    provided for diagnostic purposes."
        ::= { psWlanIfEntry 8 }

	pliWlanIfAllowedTransmitRates OBJECT-TYPE
	    SYNTAX INTEGER
        ACCESS read-only
        STATUS mandatory
	    DESCRIPTION
	        "This variables reflects the transmit rates that the 
		    wavelan card supports"
        ::= { psWlanIfEntry 9 }

	pliWlanIfRegulatoryDomainList OBJECT-TYPE
	    SYNTAX OCTET STRING
        ACCESS read-only
        STATUS mandatory
	    DESCRIPTION
	        "This variables reflects the regulatory domain the  wavelan card 
		    belongs to."
        ::= { psWlanIfEntry 10 }

	pliWlanIfAllowedOperatingFrequencies OBJECT-TYPE
	    SYNTAX INTEGER
        ACCESS read-only
        STATUS mandatory
	    DESCRIPTION
	        "This variables reflects the RF channels that the
		    wavelan card supports."
        ::= { psWlanIfEntry 11 }

	pliWlanIfCapabilityOptions OBJECT-TYPE
	    SYNTAX INTEGER
        ACCESS read-only
        STATUS mandatory
	    DESCRIPTION
	        "The capabilities of the card. Indicates the support of 
		    features like WEP."
        ::= { psWlanIfEntry 12 }

	pliWlanIfProfileCode OBJECT-TYPE
	    SYNTAX INTEGER
        ACCESS read-only
        STATUS mandatory
	    DESCRIPTION
	        "The varible conprises of a vendor indication (Lucent or
		    an OEM customer) and a capability indication (eg. bronze
		    or gold)."
        ::= { psWlanIfEntry 13 }

--=============================================================================
-- The orinocoDriver sub-group of orinocoInterface
--=============================================================================

	pliDriverName	OBJECT-TYPE
	    SYNTAX DisplayString
	    ACCESS read-only
	    STATUS mandatory
	    DESCRIPTION
	        "The driver name."
        ::= { orinocoDriver 1 }

	pliDriverVersion	OBJECT-TYPE
	    SYNTAX DisplayString
	    ACCESS read-only
	    STATUS mandatory
	    DESCRIPTION
	        "The driver's version number. This is a text string
	        including the major and minor release number, and, 
	        optionally, the patch level:  'mm.nn.pp', where
                    mm = major release number
                    nn = point release number
                    pp = optional patch number."
	    ::= { orinocoDriver 2 }

--=============================================================================
-- The orinocoSNMPSetup specific management objects
--=============================================================================

	psSNMPReadPassword	OBJECT-TYPE
	    SYNTAX DisplayString
	    ACCESS write-only
	    STATUS mandatory
	    DESCRIPTION
	        "The password for reading object values from the agent."
	    ::= { orinocoSNMPSetup 1 }

	psSNMPReadWritePassword	 OBJECT-TYPE
	    SYNTAX DisplayString
	    ACCESS write-only
	    STATUS mandatory
	    DESCRIPTION
	        "The password for reading and modifying object values 
	        from the agent."
        ::= { orinocoSNMPSetup 2 }

	psSNMPTrapHostIPAddress	  OBJECT-TYPE
	    SYNTAX IpAddress
	    ACCESS read-write
	    STATUS mandatory
	    DESCRIPTION
	        "The IP address of the host to which traps should be sent."
	    ::= { orinocoSNMPSetup 3 }

	psSNMPTrapHostPassword	OBJECT-TYPE
	    SYNTAX DisplayString
	    ACCESS read-write
	    STATUS mandatory
	    DESCRIPTION
	        "The password sent with the trap to enable the management
	        station to ignore unsolicited traps."
	    ::= { orinocoSNMPSetup 4 }

	psSNMPManagerCount	OBJECT-TYPE
	    SYNTAX INTEGER
	    ACCESS read-only
	    STATUS mandatory
	    DESCRIPTION
	        "The number of management stations that have been 
	        authorised to manage this Access Server."
	    ::= { orinocoSNMPSetup 5 }

	psSNMPAccessTable OBJECT-TYPE
	    SYNTAX SEQUENCE OF PsSNMPAccessTableEntry
	    ACCESS not-accessible
	    STATUS mandatory
	    DESCRIPTION
		    "The table containing the information about the
		    managers authorised to manage this Access Server."
        ::= { orinocoSNMPSetup 6 }
	
	psSNMPAccessTableEntry OBJECT-TYPE
	    SYNTAX PsSNMPAccessTableEntry
	    ACCESS not-accessible
	    STATUS mandatory
	    DESCRIPTION
	        "The entry in the SNMP access table. Described
	        next."
        INDEX { psSNMPManagerIndex }
        ::= { psSNMPAccessTable 1 }

	PsSNMPAccessTableEntry ::=
	    SEQUENCE
	        {
	            managerIndex   INTEGER,
	            managerIPAddress IpAddress,
	            managerSubnetMask  IpAddress,
	            managerStatus  INTEGER
	        }
	  
	managerIndex	OBJECT-TYPE
	    SYNTAX INTEGER
	    ACCESS read-only
	    STATUS mandatory
	    DESCRIPTION
	        "Management station identification number.
	        Is the index for the table."
	    ::= { psSNMPAccessTableEntry 1 }

	managerIPAddress	OBJECT-TYPE
	    SYNTAX IpAddress
	    ACCESS read-write
	    STATUS mandatory
	    DESCRIPTION
	        "IP address of the management station."
	    ::= { psSNMPAccessTableEntry 2 }

	managerSubnetMask	OBJECT-TYPE
	    SYNTAX IpAddress
	    ACCESS read-write
	    STATUS mandatory
	    DESCRIPTION
		    "The IP subnet  mask. Used to grant access to a complete subnet."
        ::= { psSNMPAccessTableEntry 3 }

	managerStatus	OBJECT-TYPE
	    SYNTAX INTEGER
		    {
		        enable(1),
		        delete(2)
		    }
        ACCESS read-write
	    STATUS mandatory
	    DESCRIPTION
	        "Whether the manager is enabled or disabled.
			  Used to delete the unwanted entries."
        ::= { psSNMPAccessTableEntry 4 }

	psSNMPInBadManagers OBJECT-TYPE
	    SYNTAX Counter
	    ACCESS read-only
	    STATUS mandatory
	    DESCRIPTION
	        "The no of attempts to manage this Access Server
			  by unauthorised managers."
	    ::= { orinocoSNMPSetup 7 }

	psTestSNMPReadWritePassword	 OBJECT-TYPE
	    SYNTAX DisplayString
	    ACCESS write-only
	    STATUS mandatory
	    DESCRIPTION
	        "The password for reading and modifying object values 
	        from the agent can be verified by setting this."
        ::= { orinocoSNMPSetup 8 }

--=============================================================================
-- The orinocoPPPSetup specific management objects
--=============================================================================

	psPPPIPAddressAssignmentType  OBJECT-TYPE 
	    SYNTAX INTEGER
	      --  {
		--        apm(1),
		--        dhcp-relay(2),
		--        radius(3)
		--    }
        ACCESS read-write
	    STATUS mandatory
	    DESCRIPTION
            "This identifies whether the IP addresses assigned 
            to the AS-Clients are obtained through APM (address
            pool manager), through DHCP or through the RADIUS server."
        ::= { orinocoPPPSetup 1 }

	psPPPNoOfMACIPMappingEntries  OBJECT-TYPE
	    SYNTAX INTEGER
	    ACCESS read-only
	    STATUS mandatory
	    DESCRIPTION
	        "The number of static mapping entries."
	    ::= { orinocoPPPSetup 2 }

	psPPPMACIPMappingTable  OBJECT-TYPE
	    SYNTAX SEQUENCE OF PsPPPMACIPMappingTableEntry
	    ACCESS not-accessible
	    STATUS mandatory
	    DESCRIPTION
		    "This table contains the static mapping of		
		    MAC addresses to IP addresses."	
		::= { orinocoPPPSetup 3 }
        	
    psPPPMACIPMappingTableEntry  OBJECT-TYPE
	    SYNTAX PsPPPMACIPMappingTableEntry
	    ACCESS not-accessible
	    STATUS mandatory
        DESCRIPTION
		    "The entry of the asPPPMACIPMappingTable Described below."
        INDEX { psPPPMACIPTableIndex }
        ::= { psPPPMACIPMappingTable 1 }

	PsPPPMACIPMappingTableEntry  ::=
	    SEQUENCE
	        {
	            mACIPIndex       INTEGER,
	            mACAddress  PhysAddress,
	            iPAddress   IpAddress,
	            comment     DisplayString,
	            entryStatus INTEGER
	        }

	mACIPIndex OBJECT-TYPE
	    SYNTAX INTEGER
	    ACCESS read-only
	    STATUS mandatory
	    DESCRIPTION
	        " This is the index for the mappping table."
	    ::= { psPPPMACIPMappingTableEntry 1 }

	mACAddress OBJECT-TYPE
	    SYNTAX PhysAddress
	    ACCESS read-write
	    STATUS mandatory
	    DESCRIPTION
	        "This is the MAC address."
	    ::= { psPPPMACIPMappingTableEntry 2 }

	iPAddress  OBJECT-TYPE
	    SYNTAX IpAddress
	    ACCESS read-write
	    STATUS mandatory
	    DESCRIPTION
	        "The IP address corresponding to the MAC address."
        ::= { psPPPMACIPMappingTableEntry 3 }

	comment   OBJECT-TYPE
	    SYNTAX  DisplayString
	    ACCESS read-write
	    STATUS mandatory
	    DESCRIPTION
	        "The comment for this entry, maybe the PC's owner."
        ::= { psPPPMACIPMappingTableEntry 4 }

	entryStatus	OBJECT-TYPE
	    SYNTAX INTEGER
		    {
		        enable(1),
		     --   disable(2)
		     delete(2)
		    }
        ACCESS read-write
	    STATUS mandatory
	    DESCRIPTION
	        "Whether the entry is enabled or disabled. Used to delete 
            the unwanted entries."
        ::= { psPPPMACIPMappingTableEntry 5 }

	psPPPKeepAliveInterval  OBJECT-TYPE
	    SYNTAX INTEGER
	    ACCESS read-write
	    STATUS mandatory
	    DESCRIPTION
	        "The keep alive interval to be notified to the PPP 
	        layer."
	    ::= { orinocoPPPSetup 4 }

	psPPPNoOfKeepAliveTimeouts  OBJECT-TYPE
	    SYNTAX INTEGER
	    ACCESS read-write
	    STATUS mandatory
	    DESCRIPTION
	        "The maximum number of timeouts before the session 
	        is torn down."
        ::= { orinocoPPPSetup 5 }

	psPPPPrimaryDNSIPAddress  OBJECT-TYPE
	    SYNTAX IpAddress
	    ACCESS read-write
	    STATUS mandatory
	    DESCRIPTION
	        "The IP address of the primary DNS server in the network."
        ::= { orinocoPPPSetup 6 }

	psPPPSecondaryDNSIPAddress  OBJECT-TYPE
	    SYNTAX IpAddress
	    ACCESS read-write
	    STATUS mandatory
	    DESCRIPTION
	        "The IP address of the secondary DNS server in the network."
        ::= { orinocoPPPSetup 7 }

	psPPPMaxNoOfUsers  OBJECT-TYPE
	    SYNTAX INTEGER
	    ACCESS read-write
	    STATUS mandatory
	    DESCRIPTION
	        "The maximum no of clients permitted to connect to this	
	        Access Server."
        ::= { orinocoPPPSetup 8 }

	psPPPCHAPStatus  OBJECT-TYPE
	    SYNTAX INTEGER
		   -- {
		   --     enable(1),
		   --     disable(2)
		   -- }
	    ACCESS read-write
	    STATUS mandatory
	    DESCRIPTION
	        "This variable indicates the status of CHAP in the Access Server."
        ::= { orinocoPPPSetup 9 }

	psPPPCHAPPriority  OBJECT-TYPE
	    SYNTAX INTEGER
	    ACCESS read-write
	    STATUS mandatory
	    DESCRIPTION
	        "This variable indicates the priority of CHAP among all
                  authentictaion protocols enabled on the Access Server."
        ::= { orinocoPPPSetup 10 }

	psPPPPAPStatus  OBJECT-TYPE
	    SYNTAX INTEGER
		--    {
		--        enable(1),
		 --       disable(2)
		--    }
	    ACCESS read-write
	    STATUS mandatory
	    DESCRIPTION
	        "This variable indicates the status of PAP in the Access Server."
        ::= { orinocoPPPSetup 11 }

	psPPPPAPPriority  OBJECT-TYPE
	    SYNTAX INTEGER
	    ACCESS read-write
	    STATUS mandatory
	    DESCRIPTION
	        "This variable indicates the priority of PAP among all 
		    authentictaion protocols enabled on the Access Server."
        ::= { orinocoPPPSetup 12 }

    psPPPPrimaryNBNSIPAddress  OBJECT-TYPE
        SYNTAX IpAddress
        ACCESS read-write
        STATUS mandatory
        DESCRIPTION
            "The IP address of the Primary NBNS server in the network."
        ::= { orinocoPPPSetup 13 }

    psPPPSecondaryNBNSIPAddress  OBJECT-TYPE
        SYNTAX IpAddress
        ACCESS read-write
        STATUS mandatory
        DESCRIPTION
            "The IP address of the Secondary NBNS server in the network."
        ::= { orinocoPPPSetup 14 }

	psPPPIPRangeTable  OBJECT-TYPE
	    SYNTAX SEQUENCE OF PsPPPIPRangeTableEntry
	    ACCESS not-accessible
	    STATUS mandatory
	    DESCRIPTION
		    "This table contains the static mapping of
		    MAC addresses to IP addresses."
		::= { orinocoPPPSetup 15 }
        
	psPPPIPRangeTableEntry  OBJECT-TYPE
	    SYNTAX PsPPPIPRangeTableEntry
	    ACCESS not-accessible
	    STATUS mandatory
        DESCRIPTION
		    "The entry of the psPPPIPRangeTable.
		    Described below."
        INDEX { psPPPIPRangeTableIndex }
        ::= { psPPPIPRangeTable 1 }

	PsPPPIPRangeTableEntry  ::=
	    SEQUENCE
	        {
	            pPPIPIndex         INTEGER,
	            startIPAddress IpAddress,
	            endIPAddress   IpAddress,
	            width        INTEGER,
                iPComment      DisplayString,
	            wtatus  INTEGER
	        }

	pPPIPIndex   OBJECT-TYPE
	    SYNTAX INTEGER
	    ACCESS read-only
	    STATUS mandatory
	    DESCRIPTION
	        " This is the index for the IP range table."
	    ::= { psPPPIPRangeTableEntry 1 }

	startIPAddress OBJECT-TYPE
	    SYNTAX IpAddress
	    ACCESS read-write
	    STATUS mandatory
	    DESCRIPTION
	        "This is the staring IP address of this range."
	    ::= { psPPPIPRangeTableEntry 2 }

	endIPAddress OBJECT-TYPE
	    SYNTAX IpAddress
	    ACCESS read-write
	    STATUS mandatory
	    DESCRIPTION
	        "This is the ending IP address of this range."
	    ::= { psPPPIPRangeTableEntry 3 }

	width OBJECT-TYPE
	    SYNTAX INTEGER
	    ACCESS read-write
	    STATUS mandatory
	    DESCRIPTION
	        "This is the withd of the range (no of addresses)."
	    ::= { psPPPIPRangeTableEntry 4 }

	status   OBJECT-TYPE
	    SYNTAX  INTEGER
	        {
	            enable(1),
	          --  disable(2),
	            delete(3)
	        }
	    ACCESS read-write
	    STATUS mandatory
	    DESCRIPTION
	        "The status of the entry, whether to be used or not
		    used. Setting this to delete will remove this entry."
        ::= { psPPPIPRangeTableEntry 5 }

    iPComment OBJECT-TYPE
        SYNTAX DisplayString
        ACCESS read-write
        STATUS mandatory
        DESCRIPTION
            "The comment for this entry may be the PC owner."
        ::= { psPPPIPRangeTableEntry 6 }

    psPPPSessionIdleTimeOut  OBJECT-TYPE
        SYNTAX INTEGER (0..36000)
        ACCESS read-write
        STATUS mandatory
        DESCRIPTION
            "The varible indicates the Session Idle time out."
        ::= { orinocoPPPSetup 16 }

--=============================================================================
-- The orinoco agent specific management objects
--=============================================================================

	psVersion   OBJECT-TYPE
	    SYNTAX DisplayString
	    ACCESS read-only
	    STATUS mandatory
	    DESCRIPTION
		    "The version of the Access Server software currently execuing.
		    Would be text string including the major and minor release 
		    number, and, optionally, the patch level:  'mm.nn.pp', where
                    mm = major release number
                    nn = point release number
                    pp = optional patch number."
        ::= { orinocoAgent 1 }

	psIPAddress   OBJECT-TYPE
	    SYNTAX IpAddress
	    ACCESS read-write
	    STATUS mandatory
	    DESCRIPTION
	        "The IP address to be assigned to the Access Server (to 
	        change from factory fitted IP address)."
	    ::= { orinocoAgent 2 }

	psSubnetMask   OBJECT-TYPE
	    SYNTAX IpAddress
	    ACCESS read-write
	    STATUS mandatory
	    DESCRIPTION
		    "The subnet mask of the Access Server."
        ::= { orinocoAgent 3 }

	psDefaultGateway   OBJECT-TYPE
	    SYNTAX IpAddress
	    ACCESS read-write
	    STATUS mandatory
	    DESCRIPTION
	        "The default gateway for the Access Server."
	    ::= { orinocoAgent 4 }

	psIPAddressType   OBJECT-TYPE
	    SYNTAX  INTEGER
		 --   {
		 --       static(1),
		 --       dynamic(2)
		 --   }
	    ACCESS read-write
	    STATUS mandatory
	    DESCRIPTION
		    "This can be DHCP/BOOTP(dynamic) or assigned 
		     by User via CLI or AS Manager(static). The 
                 IP address of the Access Server will be 
                 assigned based on this."
        ::= { orinocoAgent 5 }

	psAdministrativeState   OBJECT-TYPE
	    SYNTAX  INTEGER
		 --   {
		 --       up(1),
		 --       down(2)
		  --  }
	    ACCESS read-write
	    STATUS mandatory
	    DESCRIPTION
		    "The administrative state of the substation, can 
		    be Up or Down."
        ::= { orinocoAgent 6 }

	psTFTPIPAddress   OBJECT-TYPE
	    SYNTAX IpAddress
	    ACCESS read-write
	    STATUS mandatory
	    DESCRIPTION
	        "The IP address of the TFTP server."
	    ::= { orinocoAgent 7 }

	psTFTPFilename   OBJECT-TYPE
	    SYNTAX DisplayString
	    ACCESS read-write
	    STATUS mandatory
	    DESCRIPTION
		    "The filename of the image in the TFTP server."
        ::= { orinocoAgent 8 }

	psTFTPOperation   OBJECT-TYPE
	    SYNTAX INTEGER
		--    {
		--        upload(1),
		--        download(2),
		 --       downloadAndReboot(3)
		 --   }
	    ACCESS write-only
	    STATUS mandatory
	    DESCRIPTION 
		    "The operation  to be done, can be upload or download."
        ::= { orinocoAgent 9 }

	psReboot	OBJECT-TYPE
	    SYNTAX INTEGER
	    ACCESS read-write
	    STATUS mandatory
	    DESCRIPTION
               "This variable must be set to reboot the Access Server. The
               value is the number of seconds to wait to do a reboot."
        ::= { orinocoAgent 10 }

	psSecondsToAdminDown   OBJECT-TYPE
	    SYNTAX INTEGER	
	    ACCESS read-write
	    STATUS mandatory
	    DESCRIPTION
		    "The count of seconds to go before the administrative state 
            of the Access Server is made down."
        ::= { orinocoAgent 11 }

    psContactEmail OBJECT-TYPE
        SYNTAX DisplayString (SIZE (0..255))
        ACCESS read-write
        STATUS mandatory
        DESCRIPTION
            "The textual identification of the contact person 
            for this managed node, together with information
            on how to contact this person."
        ::= { orinocoAgent 12 }

    psBSPBootloaderVersion   OBJECT-TYPE
        SYNTAX DisplayString 
        ACCESS read-only
        STATUS mandatory
        DESCRIPTION
            "This object represents the BSP/Bootloader version that is
            currently stored in the access server device.."
        ::= { orinocoAgent 13 }

-- #ifdef PL2

	psTelnetSesssions	OBJECT-TYPE
	    SYNTAX INTEGER (0..5)
	    ACCESS read-write
	    STATUS mandatory
	    DESCRIPTION
		    "This object is used to enable or disable telnet access and
		    to specify the number of active telnet sessions.  When this
		    object is set to 0, telnet access is disabled.  When this object
		    is set to something greater than 0, then it specifies the maximum
		    number of active telnet sessions."
        ::= { orinocoAgent 14 }

	psTelnetPassword	OBJECT-TYPE
	    SYNTAX DisplayString
	    ACCESS write-only
	    STATUS mandatory
	    DESCRIPTION
		    "Password to access Access Server from Telenet."
        ::= { orinocoAgent 15 }	
    
    psTelnetPort	OBJECT-TYPE
	    SYNTAX INTEGER
	    ACCESS read-write
	    STATUS mandatory
	    DESCRIPTION
		    "The TCP/IP port for Access Server Telenet daemon."
        ::= { orinocoAgent 16 }
            
    psTelnetTimeout	OBJECT-TYPE
	    SYNTAX INTEGER(1..30)
	    ACCESS read-write
	    STATUS mandatory
	    DESCRIPTION
		    "Telnet inactivity timeout in minutes. The default value
            is 15 minutes"
        ::= { orinocoAgent 17 }
    
    psTelnetLoginTimeout	OBJECT-TYPE
	    SYNTAX INTEGER(1..60)
	    ACCESS read-write
	    STATUS mandatory
	    DESCRIPTION
		    "Telnet login timeout in seconds. The default value
            is 30 seconds"
        ::= { orinocoAgent 18 }	
    
    psSerialBaudRate	OBJECT-TYPE
	    SYNTAX INTEGER 
	--        {
        --        baud2400(1),
        --        baud4800(2),
        --        baud9600(3),
        --        baud19200(4),
        --        baud38400(5),
        --        baud57600(6),
        --    }
	    ACCESS read-write
	    STATUS mandatory
	    DESCRIPTION
            "Serial interface baud rate.  The default value is 9600"
        ::= { orinocoAgent 19 }
     
    psSerialDataBits	OBJECT-TYPE
        SYNTAX INTEGER(4..8)
	    ACCESS read-only
	    STATUS mandatory
	    DESCRIPTION
            "Serial interface data bits.  The default value is 8"
        ::= { orinocoAgent 20 }	
       
    psSerialParity     OBJECT-TYPE
	    SYNTAX INTEGER 
	  --      {
          --      even(1),
          --      odd(2),
          --      none(3),
           --     mark(4),
          --      space(5) 
          --  }
	    ACCESS read-only
	    STATUS mandatory
	    DESCRIPTION
            "Serial interface Parity check.  The default value is None"
        ::= { orinocoAgent 21 }	
            
    psSerialStopBits	OBJECT-TYPE
	    SYNTAX INTEGER 
	 --       {
         --       bit1(1),
         --       bit1dot5(2),
         --       bit2(3)
         --   }
	    ACCESS read-only
	    STATUS mandatory
	    DESCRIPTION
            "Serial interface stop bits.  The default value is 1"
        ::= { orinocoAgent 22 }	
            
    psSerialFlowControl   OBJECT-TYPE
	    SYNTAX INTEGER 
	  --      {
          --      xonXoff(1),
          --      none(2)
          --  }
	    ACCESS read-write
	    STATUS mandatory
	    DESCRIPTION
            "Serial interface Flow control.  The default value is None"
        ::= { orinocoAgent 23 }

-- #endif PL2

    psTFTPFileType    OBJECT-TYPE
	    SYNTAX INTEGER
		--    {
		--        config-sys(1),
		--        psimage(2),
		--        orinoco(3),
		--        radius(4),
		--        snmpset(5),
		--        sysinfo(6),
		--        ppp(7),
		--	    upgbspbl(8)
		--	    orgbspbl(9)	
                --          allconfigfiles(10)
		--    }
	    ACCESS read-write
	    STATUS mandatory
	    DESCRIPTION 
		    "The type of the file to be uploaded or downloaded to/from the 
		    access server.  The AllConfigFiles options shall upload or 
		    download all the configuration files supported."
        ::= { orinocoAgent 24 }		    

	psDeviceSerialNumber	OBJECT-TYPE
    	SYNTAX DisplayString
    	ACCESS read-only
    	STATUS mandatory
    	DESCRIPTION
			"This parameter identifies the serial number of the system."
    	::= { orinocoAgent 25 }

    psBroadcastMessage	OBJECT-TYPE
    	SYNTAX DisplayString
    	ACCESS read-only
    	STATUS mandatory
    	DESCRIPTION
			"This parameter allows to set customized messages to be sent 
			to all connected clients."
    	::= { orinocoAgent 26 }

	psPOSTVersionNumber	OBJECT-TYPE
    	SYNTAX DisplayString
    	ACCESS read-only
    	STATUS mandatory
    	DESCRIPTION
			"This parameter identifies the POST version number of the system."
    	::= { orinocoAgent 27 }

	psHardwareVersionNumber	OBJECT-TYPE
    	SYNTAX DisplayString
    	ACCESS read-only
    	STATUS mandatory
    	DESCRIPTION
			"This parameter identifies the Hardware version number of the system."
    	::= { orinocoAgent 28 }

--=============================================================================
-- RADIUS-CLIENT-MIB DEFINITIONS ::= BEGIN		 
-- radius OBJECT IDENTIFIER
--     DESCRIPTION	 
--         "The OID assigned to RADIUS MIB work by the IANA."
--         "The OID assigned to RADIUS MIB work by orinoco."orinoco	 
--     ::= { as-2000 5 }

-- Moving this up to the common section radiusClientMIB OBJECT IDENTIFIER
--     DESCRIPTION	 
--         "The MIB module for RADIUS Client Management."
--     ::=  { radius 2 }
--=============================================================================
      
    radiusClientMIB         OBJECT IDENTIFIER ::=  { radius 2 }
	radiusClientMIBObjects  OBJECT IDENTIFIER ::=  { radiusClientMIB 1 }
	radiusClient            OBJECT IDENTIFIER ::=  { radiusClientMIBObjects 1 }

	radiusClientInvalidServerAddresses OBJECT-TYPE
	    SYNTAX Counter
	    ACCESS read-only
	    STATUS mandatory
	    DESCRIPTION
	        "The total number of RADIUS Access-Response messages 		 
	        received from unknown addresses since client start-up"
	    ::=  { radiusClient 1 }

    radiusServerTable OBJECT-TYPE
	    SYNTAX SEQUENCE OF RadiusServerEntry
	    ACCESS not-accessible
	    STATUS mandatory
	    DESCRIPTION
	        "The (conceptual) table listing the RADIUS servers with
	         which the client shares a secret."
	    ::=  { radiusClient 2 }

    radiusServerEntry OBJECT-TYPE
	    SYNTAX RadiusServerEntry
	    ACCESS not-accessible
	    STATUS mandatory
	    DESCRIPTION
	        "An entry (conceptual row) representing a RADIUS server
	         with which the client shares a secret."
	    INDEX {radiusServerIndex}
	    ::=  { radiusServerTable 1 }

    RadiusServerEntry ::= 
        SEQUENCE 
            {
	            radiusServerIndex                           INTEGER,
	            radiusServerType                            INTEGER,
	            radiusServerAddress                         IpAddress,
	            radiusServerDestPortAuth                    INTEGER,
	            radiusServerDestPortAcct                    INTEGER,
	            radiusClientAccessRequests                  Counter,
	            radiusClientAccessRetransmissions           Counter,
	            radiusClientAccessAccepts                   Counter,
	            radiusClientAccessChallenges                Counter,
	            radiusClientMalformedAccessResponses        Counter,
	            radiusClientAuthenticationBadAuthenticators Counter,
	            radiusClientAccessRejects                   Counter,
	            radiusClientTimeouts                        Counter,
	            radiusClientAccountingRequests              Counter,
	            radiusClientAccountingRetransmissions       Counter,
	            radiusClientAccountingResponses             Counter,
	            radiusClientAccountingBadAuthenticators     Counter,
	            radiusServerSharedSecret                    DisplayString,
	            radiusServerEnabled                         INTEGER,
	            radiusServerResponseTime                    INTEGER,
	            radiusServerMaximumRetransmission           INTEGER
	        }

    radiusServerIndex OBJECT-TYPE
	    SYNTAX INTEGER
	    ACCESS read-only
	    STATUS mandatory
	    DESCRIPTION
	        "The RADIUS server with whom the client interacts."
	    ::=  { radiusServerEntry 1 }

    radiusServerType OBJECT-TYPE
	    SYNTAX INTEGER 
	    --    { 
	    --        auth(1),	                      
	    --        acct(2),
	    --        both(3)	                    
	    --    }
	    ACCESS read-only
	    STATUS mandatory
	    DESCRIPTION
	        "The RADIUS server type (Authentication or Accounting or Both).
	        For creating a server entry Server Type should be set"
	    ::=  { radiusServerEntry 2 }

    radiusServerAddress OBJECT-TYPE
	    SYNTAX IpAddress
	    ACCESS read-write
	    STATUS mandatory
	    DESCRIPTION
	        "The IP address of the RADIUS server referred to in this table 
	        entry."
	    ::=  { radiusServerEntry 3 }

    radiusServerDestPortAuth OBJECT-TYPE
	    SYNTAX INTEGER
	    ACCESS read-write
	    STATUS mandatory
	    DESCRIPTION
	        " The Authentication port of the RADIUS Server."
	    ::=  { radiusServerEntry 4 }

    radiusServerDestPortAcct OBJECT-TYPE
	    SYNTAX INTEGER
	    ACCESS read-write
	    STATUS mandatory
	    DESCRIPTION
	        "The Accounting port of the RADIUS Server."
	    ::=  { radiusServerEntry 5 }

	radiusClientAccessRequests OBJECT-TYPE
	    SYNTAX Counter
	    ACCESS read-only
	    STATUS mandatory
	    DESCRIPTION
	        "The total number of RADIUS Access-Request messages sent
	        since client start-up"
	    ::=  { radiusServerEntry 6 }

    radiusClientAccessRetransmissions OBJECT-TYPE
	    SYNTAX Counter
	    ACCESS read-only
	    STATUS mandatory
	    DESCRIPTION
	        "The total number of RADIUS Access-Request messages retransmitted
	        since client start-up"
	    ::=  { radiusServerEntry 7 }

    radiusClientAccessAccepts OBJECT-TYPE
	    SYNTAX Counter
	    ACCESS read-only
	    STATUS mandatory
	    DESCRIPTION
	        "The total number of RADIUS Access-Accept messages received
	        since client start-up"
	    ::=  { radiusServerEntry 8 }

    radiusClientAccessChallenges OBJECT-TYPE
	    SYNTAX Counter
	    ACCESS read-only
	    STATUS mandatory
	    DESCRIPTION
	        "The total number of RADIUS Access-Challenge messages received
	        since client start-up"
	    ::=  { radiusServerEntry 9 }

    radiusClientMalformedAccessResponses OBJECT-TYPE
	    SYNTAX Counter
	    ACCESS read-only
	    STATUS mandatory
	    DESCRIPTION
	        "The total number of malformed RADIUS Access-Response messages 
            received since client start-up"
	    ::=  { radiusServerEntry 10 }

    radiusClientAuthenticationBadAuthenticators OBJECT-TYPE
	    SYNTAX Counter
	    ACCESS read-only
	    STATUS mandatory
	    DESCRIPTION
	        "The total number of RADIUS Access-Response messages
	        containing invalid authenticators received since client 		  
	        start-up"
	    ::=  { radiusServerEntry 11 }

    radiusClientAccessRejects OBJECT-TYPE
	    SYNTAX Counter
	    ACCESS read-only
	    STATUS mandatory
	    DESCRIPTION
	        "The total number of RADIUS Access-Reject messages sent 		  
	        since client start-up"
	    ::=  { radiusServerEntry 12 }

    radiusClientTimeouts OBJECT-TYPE
	    SYNTAX Counter
	    ACCESS read-only
	    STATUS mandatory
	    DESCRIPTION
	        "The total number of timeouts since client startup"
	    ::=  { radiusServerEntry 13 }

    radiusClientAccountingRequests OBJECT-TYPE
	    SYNTAX Counter
	    ACCESS read-only
	    STATUS mandatory
	    DESCRIPTION
	        "The total number of RADIUS Accounting-Request messages sent
	        since client start-up"
	    ::=  { radiusServerEntry 14 }

	radiusClientAccountingRetransmissions OBJECT-TYPE
	    SYNTAX Counter
	    ACCESS read-only
	    STATUS mandatory
	    DESCRIPTION
	        "The total number of RADIUS Accounting-Request messages 		  
	        retransmitted since client start-up"
	    ::=  { radiusServerEntry 15 }

    radiusClientAccountingResponses OBJECT-TYPE
	    SYNTAX Counter
	    ACCESS read-only
	    STATUS mandatory
	    DESCRIPTION
	        "The total number of RADIUS Accounting-Response messages 		  
	        received since client start-up"
	    ::=  { radiusServerEntry 16 }

    radiusClientAccountingBadAuthenticators OBJECT-TYPE
	    SYNTAX Counter
	    ACCESS read-only
	    STATUS mandatory
	    DESCRIPTION
	        "The total number of RADIUS Accounting-Response messages which
	        contained invalid  authenticators received since client 		  
	        start-up"
	    ::=  { radiusServerEntry 17 }

	radiusServerSharedSecret OBJECT-TYPE
	    SYNTAX DisplayString
	    ACCESS read-write
	    STATUS mandatory
	    DESCRIPTION
	        "The secret string which is shared between Server and Client"
	    ::=  { radiusServerEntry 18 }

	radiusServerEnabled OBJECT-TYPE
	    SYNTAX INTEGER
		 --   {
		--	    enable(1),
		--		disable(2),
		--		delete(3)
		--	}
	    ACCESS read-write
	    STATUS mandatory
	    DESCRIPTION
	        "Flag to tell whether the server is active or Inactive"
	    ::=  { radiusServerEntry 19 }

	radiusServerResponseTime OBJECT-TYPE
	    SYNTAX INTEGER(1..10)
	    ACCESS read-write
	    STATUS mandatory
	    DESCRIPTION
	        "The maximum time within which the server has to respond for a
	        request from the client"
	    ::=  { radiusServerEntry 20 }

	radiusServerMaximumRetransmission OBJECT-TYPE
	    SYNTAX INTEGER(1..4)
	    ACCESS read-write
	    STATUS mandatory
	    DESCRIPTION
	        "The allowed maximum no. of trials to be tried by a client 	
            to get response from the server for a request"
	    ::=  { radiusServerEntry 21 }

--=============================================================================
-- conformance information	 
--=============================================================================
	 
	radiusClientMIBConformance OBJECT IDENTIFIER 
	    ::=  { radiusClientMIB 2 }

	radiusClientMIBCompliances OBJECT IDENTIFIER
	    ::=  { radiusClientMIBConformance 1 }

	radiusClientMIBGroups OBJECT IDENTIFIER
	    ::=  { radiusClientMIBConformance 2 }

--=============================================================================
-- Access Server ECP Information
--=============================================================================

    psShimECPRetransmissionCount OBJECT-TYPE
        SYNTAX INTEGER
        ACCESS read-write
        STATUS mandatory
        DESCRIPTION
            "The number of retransmissions when responses are not
            received with the timeout period."
        ::= { orinocoShimECPSetup 1 }

    psShimECPRepeatResponseCount  OBJECT-TYPE
        SYNTAX INTEGER
        ACCESS read-write
        STATUS mandatory
        DESCRIPTION
            "The number of time the transmitted response can be
            retransmitted."
        ::= { orinocoShimECPSetup 2 }

     psShimECPRetransmissionTimeout  OBJECT-TYPE
        SYNTAX INTEGER
        ACCESS read-write
        STATUS mandatory
        DESCRIPTION
            "The timeout interval for a response to be received."
        ::= { orinocoShimECPSetup 3 }

-- #ifdef PL2

--=============================================================================
-- Access Server IAPP Information
--=============================================================================

	psIappStatus OBJECT-TYPE
	    SYNTAX INTEGER 
	   --     { 
	    --        enable (1),
           --     disable (2)
           -- }
	    ACCESS read-write
	    STATUS mandatory
        DESCRIPTION
	        "IAPP Status (whether IAPP feature should be enabled or diaabled)"
        ::= { orinocoIAPP 1 }

	psIappAnnReqOut OBJECT-TYPE
	    SYNTAX Counter
	    ACCESS read-only
	    STATUS mandatory
        DESCRIPTION
	        "Number of ANNOUNCE.requests sent."
        ::= { orinocoIAPP 2 }
       	
	psIappAnnReqIn OBJECT-TYPE
	    SYNTAX Counter
	    ACCESS read-only
	    STATUS mandatory
        DESCRIPTION
	        "Number of ANNOUNCE.requests received."
        ::= { orinocoIAPP 3 }
       
	psIappAnnRespOut OBJECT-TYPE
	    SYNTAX Counter
	    ACCESS read-only
	    STATUS mandatory
        DESCRIPTION
	        "Number of ANNOUNCE.responses sent."
        ::= { orinocoIAPP 4 }
       
	psIappAnnRespIn OBJECT-TYPE
	    SYNTAX Counter
	    ACCESS read-only
	    STATUS mandatory
        DESCRIPTION
	        "Number of ANNOUNCE.responses received."
        ::= { orinocoIAPP 5 }
       
	psIappHandOvrReqOut OBJECT-TYPE
	    SYNTAX Counter
	    ACCESS read-only
	    STATUS mandatory
        DESCRIPTION
	        "Number of HANDOVER.request sent."
        ::= { orinocoIAPP 6 }
       
	psIappHandOvrReqIn OBJECT-TYPE
	    SYNTAX Counter
	    ACCESS read-only
	    STATUS mandatory
        DESCRIPTION
	        "Number of HANDOVER.request received."
        ::= { orinocoIAPP 7 }
       
	psIappHandOvrRespOut OBJECT-TYPE
	    SYNTAX Counter
	    ACCESS read-only
	    STATUS mandatory
        DESCRIPTION
	        "Number of HANDOVER.responses sent."
        ::= { orinocoIAPP 8 }
       
	psIappHandOvrRespIn OBJECT-TYPE
	    SYNTAX Counter
	    ACCESS read-only
	    STATUS mandatory
        DESCRIPTION
	        "Number of HANDOVER.responses received."
        ::= { orinocoIAPP 9 }
       
	psIappEndSessOut OBJECT-TYPE
	    SYNTAX Counter
	    ACCESS read-only
	    STATUS mandatory
        DESCRIPTION
	        "Number of IAPP End-PPP session PDUs sent."
        ::= { orinocoIAPP 10 }

	psIappEndSessIn OBJECT-TYPE
	    SYNTAX Counter
	    ACCESS read-only
	    STATUS mandatory
        DESCRIPTION
	        "Number of IAPP End-PPP session PDUs received."
        ::= { orinocoIAPP 11 }

	psIappEndSessAckOut OBJECT-TYPE
	    SYNTAX Counter
	    ACCESS read-only
	    STATUS mandatory
        DESCRIPTION
	        "Number of IAPP End-PPP session acknowledgement PDUs sent."
        ::= { orinocoIAPP 12 }

	psIappEndSessAckIn OBJECT-TYPE
	    SYNTAX Counter
	    ACCESS read-only
	    STATUS mandatory
        DESCRIPTION
	        "Number of IAPP End-PPP session acknowledgement PDUs received."
        ::= { orinocoIAPP 13 }

	psIappPduDrops OBJECT-TYPE
	    SYNTAX Counter
	    ACCESS read-only
	    STATUS mandatory
        DESCRIPTION
	        "Number of IAPP PDUs dropped."
        ::= { orinocoIAPP 14 }

	psIappHandOvrReqReSent OBJECT-TYPE
	    SYNTAX Counter
	    ACCESS read-only
	    STATUS mandatory
        DESCRIPTION
	        "Number of HANDOVER requests re-transmitted.."
        ::= { orinocoIAPP 15 }
       
	psIappAnnInterval OBJECT-TYPE
        SYNTAX INTEGER
          --  {
          --      eighty(80),
	--			oneHundredTwenty(120),
	--			oneHundredSixty(160),
	--			twoHundred(200)
	--		}
	    ACCESS read-write
	    STATUS mandatory
	    DESCRIPTION
			"This parameter represents interval in seconds for performing an 
			IAPP announce operation by the device.  The units for this 
			parameter is seconds and default value should be 120 seconds."
        ::= { orinocoIAPP 16 }
       
	psIappAnnRespTime OBJECT-TYPE
	    SYNTAX INTEGER
	    ACCESS read-only
	    STATUS mandatory
	    DESCRIPTION
			"This parameter indicates the amount of time in seconds the 
			device waits to send an IAPP announce response after an announce 
			request message is sent.  This parameter is set to a default value
			of 2 seconds and is not configurable."
        ::= { orinocoIAPP 17 }
       
	psIappHandOvrTimeOut OBJECT-TYPE
	    SYNTAX INTEGER
		--	{
		--		fiveHundredTwelve(512),
		--		sixHundredFourteen(614),
		--		sevenHundredSeventeen(717),
		--		eightHundredNineteen(819)
		--	}
	    ACCESS read-write
	    STATUS mandatory
	    DESCRIPTION
			"This parameter represents the time in milliseconds the device 
			waits before it resends a handover response message.  The default 
			value for this parameter should be 512 milliseconds."
        ::= { orinocoIAPP 18 }
       
	psIappMaxHandOvrRetries OBJECT-TYPE
	    SYNTAX INTEGER(1..4)
	    ACCESS read-write
	    STATUS mandatory	
	    DESCRIPTION
			"This parameter indicates the maximum amount of retransmission sent
			by the device for a handover request message.  The default for this
			parameter should be 2."
        ::= { orinocoIAPP 19 }

	psIappRoamingClients OBJECT-TYPE
	    SYNTAX Counter
	    ACCESS read-only
	    STATUS mandatory
        DESCRIPTION
	        "Number of roaming clients currently attached to the 
	        Access Server."
        ::= { orinocoIAPP 20 }

--    psIAPPMacIpTable OBJECT-TYPE
--        SYNTAX SEQUENCE OF PsIAPPMacIpEntry
--        ACCESS not-accessible
--        STATUS mandatory
--        DESCRIPTION
--           "The (conceptual) table listing AS-2000 devices in the same subnet 
--           that have the IAPP function enabled."
--        ::= { orinocoIAPP 21 }
--
--    psIAPPMacIpEntry OBJECT-TYPE
--        SYNTAX PsIAPPMacIpEntry
--        ACCESS not-accessible
--        STATUS mandatory
--        DESCRIPTION
--           "An entry (conceptual row) representing an AS-2000 device, 
--           maintaining it's IP address and Wireless MAC Address."
--        INDEX {psIAPPMacIpIndex}
--        ::= { psIAPPMacIpTable 1 }
--
--    PsIAPPMacIpEntry ::=
--        SEQUENCE 
--            {
--                psIAPPMacIpIndex        		INTEGER,
--                psIAPPPeerSystemName    		DisplayString,
--                psIAPPPeerIPAddr        		IpAddress,
--                psIAPPPeerWlessIf1MACAddr   	PhysAddress,
--                psIAPPPeerWlessIf2MACAddr   	PhysAddress,
--                psIAPPPeerNetworkNameWlessIf1   DisplayString,
--                psIAPPPeerNetworkNameWlessIf2	DisplayString
--			}
--                
--    psIAPPMacIpIndex OBJECT-TYPE
--        SYNTAX INTEGER 
--        ACCESS read-only
--        STATUS mandatory
--        DESCRIPTION
--            "The index for the AS-200 IAPP MAC-IP table."
--        ::= { psIAPPMacIpEntry 1 }
--
--    psIAPPPeerSystemName OBJECT-TYPE
--	    SYNTAX DisplayString
--	    ACCESS read-only
--	    STATUS mandatory
--	    DESCRIPTION
--		    "The System Name of the AS-2000 peer."
--	    ::= { psIAPPMacIpEntry 2 }
--
--    psIAPPPeerIPAddr OBJECT-TYPE
--        SYNTAX IpAddress
--        ACCESS read-only
--        STATUS mandatory
--        DESCRIPTION
--            "The IP Address of the Peer AS-2000 device where IAPP 
--             is enabled."
--        ::= { psIAPPMacIpEntry 3 }
--
--    psIAPPPeerWlessIf1MACAddr OBJECT-TYPE
--        SYNTAX PhysAddress
--        ACCESS read-only
--        STATUS mandatory
--        DESCRIPTION
--            "The MAC address of the wireless interface 1 of the peer AS-2000
--            device which has IAPP enabled."
--        ::= { psIAPPMacIpEntry 4 }
--
--    psIAPPPeerWlessIf2MACAddr OBJECT-TYPE
--        SYNTAX PhysAddress
--        ACCESS read-only
--        STATUS mandatory
--        DESCRIPTION
--            "The MAC address of the wireless interface 2 of the peer AS-2000
--            device which has IAPP enabled."
--        ::= { psIAPPMacIpEntry 5 }
--
--    psIAPPPeerNetworkNameWlessIf1 OBJECT-TYPE
--	    SYNTAX DisplayString
--	    ACCESS read-only
--	    STATUS mandatory
--	    DESCRIPTION
--		    "The network name of wireless interface 1 of the peer AS-2000
--		    device which has the IAPP function enabled."
--		::= { psIAPPMacIpEntry 6 }
--		    
--    psIAPPPeerNetworkNameWlessIf2 OBJECT-TYPE
--	    SYNTAX DisplayString
--	    ACCESS read-only
--	    STATUS mandatory
--	    DESCRIPTION
--		    "The network name of wireless interface 1 of the peer AS-2000
--		    device which has the IAPP function enabled."
--        ::= { psIAPPMacIpEntry 7 }

--=============================================================================
-- IPX objects
--=============================================================================

	psIpxStatus OBJECT-TYPE
	    SYNTAX INTEGER 
	  --      {
	--	        ip(1),
          --      ipx(2),
          --      both(3)
          --  }
	    ACCESS read-write
	    STATUS mandatory
        DESCRIPTION
            "Which protocol is supported, i.e, IP or IPX or both IP and IPX."
        ::= { orinocoIPX 1 }

	psIpxDefaultRouterNodeNum OBJECT-TYPE
	    SYNTAX PhysAddress
        ACCESS read-write
	    STATUS mandatory
        DESCRIPTION
            "If the source IPX network number is not equal to the destination 
            IPX Network number in the packet from wireless side to the wired 
            side, then replace the destination Ether MAC addr with the value of 
            this object (Default IPX router node number)."
        ::= { orinocoIPX 2 }

	psIpxWiredToWlessBridged OBJECT-TYPE
	    SYNTAX Counter
        ACCESS read-only
	    STATUS mandatory
        DESCRIPTION
            "Number of packets bridged from wired side to wireless side."
        ::= { orinocoIPX 3 }

	psIpxWlessToWiredBridged OBJECT-TYPE
	    SYNTAX Counter
        ACCESS read-only
	    STATUS mandatory
        DESCRIPTION
            "Number of packets bridged from wiredless side to wired side."
        ::= { orinocoIPX 4 }

	psIpxEthernetEncapsulationFormat OBJECT-TYPE
	    SYNTAX INTEGER 
	  --      {
	  --          ethII802dot3encapsulation(1),
          --      eth802dot3withSnapHdr(2),
          --      eth802dot3woSnapHdr(3)
          --  }
        ACCESS read-write
	    STATUS mandatory
        DESCRIPTION
            "Encapsulation type to be used for the IPX packets sent in wired 
            side"
        ::= { orinocoIPX 5 }

psASClientTable OBJECT-TYPE
        SYNTAX SEQUENCE OF PsASClientEntry
        ACCESS not-accessible
        STATUS mandatory
        DESCRIPTION
           "The (conceptual) table listing the ASClients (IPX) connected to the 
           access server 2000 device."
        ::= { orinocoIPX 6 }

    psASClientEntry OBJECT-TYPE
        SYNTAX PsASClientEntry
        ACCESS not-accessible
        STATUS mandatory
        DESCRIPTION
           "An entry (conceptual row) representing a ASClient (IPX) connnected to
           the Access Server 2000 device."
        INDEX {psPPPSessionId}
        ::= { psASClientTable 1 }

    PsASClientEntry ::=
        SEQUENCE 
            {
                psPPPSessionId       INTEGER,
                psIpxClientNetworkNumber    OCTET STRING,
                psIpxClientMAC          PhysAddress,
                psIpxClientStatus			INTEGER,
                psASClientSessionUpTime		TimeTicks,
                psASClientPacketsIn			Counter,
                psASClientPacketsOut		Counter
            }

    psPPPSessionId OBJECT-TYPE
        SYNTAX INTEGER 
        ACCESS read-only
        STATUS mandatory
        DESCRIPTION
            "The PPP Session ID assigned by the AS-2000 to this 
            ASClient."
        ::= { psASClientEntry 1 }

    psIpxClientNetworkNumber OBJECT-TYPE
        SYNTAX OCTET STRING
        ACCESS read-only
        STATUS mandatory
        DESCRIPTION
            "The IPX Node Number assigned by the Novell Server to 
            this IPX client."
        ::= { psASClientEntry 2 }

    psIpxClientMAC OBJECT-TYPE
        SYNTAX PhysAddress
        ACCESS read-only
        STATUS mandatory
        DESCRIPTION
            "The Wireless MAC of this IPX Client."
        ::= { psASClientEntry 3 }

    psIpxClientStatus  OBJECT-TYPE
        SYNTAX INTEGER
            {

                 up (1),
                disable(2),
                delete(3)
            }
        ACCESS read-write
        STATUS mandatory
        DESCRIPTION
           "Flag to indicate whether the IPX Client is Active or 
            Inactive.  IPX Client status can also be 
            disabled/enabled/deleted."
        ::= { psASClientEntry 4 }

    psASClientSessionUpTime OBJECT-TYPE
        SYNTAX TimeTicks
        ACCESS read-only
        STATUS mandatory
        DESCRIPTION
            "This object represents the session up time for each AS Client
            or PPP virttual interface."
        ::= { psASClientEntry 5 }

    psASClientPacketsIn OBJECT-TYPE
        SYNTAX Counter
        ACCESS read-only
        STATUS mandatory
        DESCRIPTION
            "This object represents the number of packets (unicast and 
            non-unicast)recieved for each AS Client or PPP virttual 
            interface."
        ::= { psASClientEntry 6 }

    psASClientPacketsOut OBJECT-TYPE
        SYNTAX Counter
        ACCESS read-only
        STATUS mandatory
        DESCRIPTION
            "This object represents the number of packets (unicast and 
            non-unicast)sent for each AS Client or PPP virttual 
            interface."
        ::= { psASClientEntry 7 } 
        
-- #endif PL2

--=============================================================================
-- Access Server Link Test Group
--=============================================================================

	oriLinkTestTimeOut	OBJECT-TYPE
	    SYNTAX INTEGER
	    ACCESS read-write
	    STATUS mandatory
	    DESCRIPTION
			"The value of this parameter determines the time that a link test 
			will continue without any SNMP requests for a Link Test Table 
			entry. When the time expires the Link Test Table is cleared."
	    ::= { orinocoLinkTest 1 }

	oriLinkTestInterval    OBJECT-TYPE
	    SYNTAX INTEGER
	    ACCESS read-write
	    STATUS mandatory
	    DESCRIPTION
			"This parameter indicates the interval (in millisec) between 
			sending link test frames to a station. Default on 200 
			millisecond."
	    ::= { orinocoLinkTest 3 }

	oriLinkTestExplore    OBJECT-TYPE
	    SYNTAX INTEGER
	--		{
	--		    tabletimedout(1),
	--		    exploring(2),
	--		    exploreresultsavailable(3)
	--		}
	    ACCESS read-write
	    STATUS mandatory
	    DESCRIPTION
			"When this parameter is set to 2, the access point will send out 
			an explore request on all 802.11 interfaces and from the results 
			build the Link Test table. This table is valid only while this 
			parameter is 3."
	    ::= { orinocoLinkTest 4 }

	oriLinkTestTable    OBJECT-TYPE
	    SYNTAX SEQUENCE OF OriLinkTestTableEntry
	    ACCESS not-accessible
	    STATUS mandatory
	    DESCRIPTION
			"This table contains the information for the stations currently 
			associated with this access point."
	    ::= { orinocoLinkTest 5 }

	oriLinkTestTableEntry    OBJECT-TYPE
	    SYNTAX OriLinkTestTableEntry
    	ACCESS not-accessible
	    STATUS mandatory
	    DESCRIPTION
			"This parameter represents the entry in the Remote Link Test 
			table.This is described below."
	    INDEX { oriLinkTestTableIndex }
	    ::= { oriLinkTestTable 1 }

	OriLinkTestTableEntry ::=
		SEQUENCE
		    {
			    oriLinkTestTableIndex 				INTEGER,
			    oriLinkTestInProgress				INTEGER,
			    oriLinkTestStationName				DisplayString,
			    oriLinkTestMACAddress				PhysAddress,
			    oriLinkTestStationProfile			INTEGER,
			    oriLinkTestOurCurSignalLevel		INTEGER,
			    oriLinkTestOurCurNoiseLevel			INTEGER,
			    oriLinkTestOurCurSNR				INTEGER,
			    oriLinkTestOurMinSignalLevel		INTEGER,
			    oriLinkTestOurMinNoiseLevel			INTEGER,
			    oriLinkTestOurMinSNR				INTEGER,
			    oriLinkTestOurMaxSignalLevel		INTEGER,
			    oriLinkTestOurMaxNoiseLevel			INTEGER,
			    oriLinkTestOurMaxSNR				INTEGER,
			    oriLinkTestOurLowFrameCount			INTEGER,
			    oriLinkTestOurStandardFrameCount	INTEGER,
			    oriLinkTestOurMediumFrameCount		INTEGER,
			    oriLinkTestOurHighFrameCount		INTEGER,
			    oriLinkTestHisCurSignalLevel		INTEGER,
			    oriLinkTestHisCurNoiseLevel			INTEGER,
			    oriLinkTestHisCurSNR				INTEGER,
			    oriLinkTestHisMinSignalLevel		INTEGER,
			    oriLinkTestHisMinNoiseLevel			INTEGER,
			    oriLinkTestHisMinSNR				INTEGER,
			    oriLinkTestHisMaxSignalLevel		INTEGER,
			    oriLinkTestHisMaxNoiseLevel			INTEGER,
			    oriLinkTestHisMaxSNR				INTEGER,
		    	oriLinkTestHisLowFrameCount			INTEGER,
			    oriLinkTestHisStandardFrameCount	INTEGER,
			    oriLinkTestHisMediumFrameCount		INTEGER,
			    oriLinkTestHisHighFrameCount		INTEGER,
			    oriLinkTestInterface                INTEGER,
			    oriLinkTestRadioType                INTEGER	    
		}

	oriLinkTestTableIndex    OBJECT-TYPE
	    SYNTAX INTEGER
	    ACCESS read-only
	    STATUS mandatory
	    DESCRIPTION
			"This parameter represents a unique value for each stattion. The 
			value for each station must remain constant at least from one 
			explore to the next."
	    ::= { oriLinkTestTableEntry 1 }

	oriLinkTestInProgress    OBJECT-TYPE
	    SYNTAX INTEGER
	--	    {
	--			nolinktestinprogress(1),
	--			linktestinprogress(2)
	--	    }
	    ACCESS read-write
	    STATUS mandatory
	    DESCRIPTION
			"When this parameter is set to 2 the access point will initiate a 
			link test sequence with this station. "
	    ::= { oriLinkTestTableEntry 2 }

	oriLinkTestStationName    OBJECT-TYPE
	    SYNTAX DisplayString
	    ACCESS read-only
	    STATUS mandatory
	    DESCRIPTION
			"This parameter identifies the name of the station whom which the 
			link test is being performed."
	    ::= { oriLinkTestTableEntry 3 }

	oriLinkTestMACAddress    OBJECT-TYPE
	    SYNTAX PhysAddress
	    ACCESS read-only
	    STATUS mandatory
	    DESCRIPTION
			"This variable represents the MAC address that will be mapped to 
			the IP Address of the station."
	    ::= { oriLinkTestTableEntry 4 }

	oriLinkTestStationProfile    OBJECT-TYPE
	    SYNTAX INTEGER
	    ACCESS read-only
	    STATUS mandatory
	    DESCRIPTION
			"This parameter represents the profile/capabilities for this 
			station."
	    ::= { oriLinkTestTableEntry 5 }

	oriLinkTestOurCurSignalLevel    OBJECT-TYPE
	    SYNTAX INTEGER
	    ACCESS read-only
	    STATUS mandatory
	    DESCRIPTION
			"The current signal level (in dB)for the link test from this 
			station. This variable indicates the running average of the local 
			signal level using the algorithm (3/4*oldvalue + 1/4*newvalue)."	
	    ::= { oriLinkTestTableEntry 6 }

	oriLinkTestOurCurNoiseLevel    OBJECT-TYPE
	    SYNTAX INTEGER
	    ACCESS read-only
	    STATUS mandatory
	    DESCRIPTION
			"The current noise level (in dB)for the link test to this station. 
			This variable indicates the running average of the local noise 
			level."
	    ::= { oriLinkTestTableEntry 7}

	oriLinkTestOurCurSNR    OBJECT-TYPE
	    SYNTAX INTEGER
	    ACCESS read-only
	    STATUS mandatory
	    DESCRIPTION
			"The current signal to noise ratio for the link test to this 
			station."
	    ::= { oriLinkTestTableEntry 8 }

	oriLinkTestOurMinSignalLevel    OBJECT-TYPE
	    SYNTAX INTEGER
	    ACCESS read-only
	    STATUS mandatory
	    DESCRIPTION
			"The minimum signal level during the link test to this station."
	    ::= { oriLinkTestTableEntry 9 }

	oriLinkTestOurMinNoiseLevel    OBJECT-TYPE
	    SYNTAX INTEGER
	    ACCESS read-only
	    STATUS mandatory
	    DESCRIPTION	
			"The minimum noise level during the link test to this station."
	    ::= { oriLinkTestTableEntry 10 }

	oriLinkTestOurMinSNR    OBJECT-TYPE
	    SYNTAX INTEGER
	    ACCESS read-only
	    STATUS mandatory
	    DESCRIPTION	
			"The minimum signal to noise ratio during the link test to this 
			station."
	    ::= { oriLinkTestTableEntry 11 }

	oriLinkTestOurMaxSignalLevel    OBJECT-TYPE
	    SYNTAX INTEGER
	    ACCESS read-only
	    STATUS mandatory
	    DESCRIPTION
			"The maximum signal level during the link test to this station."
	    ::= { oriLinkTestTableEntry 12 }

	oriLinkTestOurMaxNoiseLevel    OBJECT-TYPE
	    SYNTAX INTEGER
	    ACCESS read-only
	    STATUS mandatory
	    DESCRIPTION
			"The maximum noise level during the link test to this station."
	    ::= { oriLinkTestTableEntry 13 }

	oriLinkTestOurMaxSNR    OBJECT-TYPE
	    SYNTAX INTEGER
	    ACCESS read-only
	    STATUS mandatory
	    DESCRIPTION
			"The maximum signal to noise ratio during the link test to this 
			station."
	    ::= { oriLinkTestTableEntry 14 }

	oriLinkTestOurLowFrameCount    OBJECT-TYPE
	    SYNTAX INTEGER
	    ACCESS read-only
	    STATUS mandatory
	    DESCRIPTION
			"The total number of frames sent at 1 Mbit/s speed during the link 
			test to this station."
	    ::= { oriLinkTestTableEntry 15 }

	oriLinkTestOurStandardFrameCount    OBJECT-TYPE
	    SYNTAX INTEGER
	    ACCESS read-only
	    STATUS mandatory
	    DESCRIPTION
			"The total number of frames sent at 2 Mbit/s speed during the link 
			test to this station."
	    ::= { oriLinkTestTableEntry 16 }

	oriLinkTestOurMediumFrameCount    OBJECT-TYPE
	    SYNTAX INTEGER
	    ACCESS read-only
	    STATUS mandatory
	    DESCRIPTION
			"The total number of frames sent at 5.5 Mbit/s (for Turbo-8, it is 
			5 Mbit/s) speed during the link test to this station."
	    ::= { oriLinkTestTableEntry 17 }

	oriLinkTestOurHighFrameCount    OBJECT-TYPE
	    SYNTAX INTEGER
	    ACCESS read-only
	    STATUS mandatory
	    DESCRIPTION
			"The total number of frames sent at 11 Mbit/s (for Turbo-8, it is 
			8 Mbit/s) speed during the link test to this station."
	    ::= { oriLinkTestTableEntry 18 }

	oriLinkTestHisCurSignalLevel    OBJECT-TYPE
	    SYNTAX INTEGER
	    ACCESS read-only
	    STATUS mandatory
	    DESCRIPTION
			"The current signal level for the link test to the remote station 
			or access point."
	    ::= { oriLinkTestTableEntry 19 }

	oriLinkTestHisCurNoiseLevel    OBJECT-TYPE
	    SYNTAX INTEGER
	    ACCESS read-only
	    STATUS mandatory
	    DESCRIPTION
			"The current noise level for the link test to the remote station or 
			access point."
	    ::= { oriLinkTestTableEntry 20 }

	oriLinkTestHisCurSNR    OBJECT-TYPE
	    SYNTAX INTEGER
	    ACCESS read-only
	    STATUS mandatory
	    DESCRIPTION
			"The current signal to noise ratio for the link test to the remote 
			station or access point."
	    ::= { oriLinkTestTableEntry 21 }	

	oriLinkTestHisMinSignalLevel    OBJECT-TYPE
	    SYNTAX INTEGER
	    ACCESS read-only
	    STATUS mandatory
	    DESCRIPTION
			"The minimum signal level during the link test to the remote statio
			or access point."
	    ::= { oriLinkTestTableEntry 22 }

	oriLinkTestHisMinNoiseLevel    OBJECT-TYPE
	    SYNTAX INTEGER
	    ACCESS read-only
	    STATUS mandatory
	    DESCRIPTION
			"The minimum noise level during the link test to the remote station 
			or access point."
	    ::= { oriLinkTestTableEntry 23 }

	oriLinkTestHisMinSNR    OBJECT-TYPE
	    SYNTAX INTEGER
	    ACCESS read-only
	    STATUS mandatory
	    DESCRIPTION
			"The minimum signal to noise ratio during the link test to the 
			remote station or access point."
	    ::= { oriLinkTestTableEntry 24 }	

	oriLinkTestHisMaxSignalLevel    OBJECT-TYPE
	    SYNTAX INTEGER
	    ACCESS read-only
	    STATUS mandatory
	    DESCRIPTION
			"The maximum signal level during the link test to the remote 
			station or access point."
	    ::= { oriLinkTestTableEntry 25 }

	oriLinkTestHisMaxNoiseLevel    OBJECT-TYPE
	    SYNTAX INTEGER
	    ACCESS read-only
	    STATUS mandatory
	    DESCRIPTION
			"The maximum noise level during the link test to the remote station 
			or access point."
	    ::= { oriLinkTestTableEntry 26 }

	oriLinkTestHisMaxSNR    OBJECT-TYPE
    	SYNTAX INTEGER
	    ACCESS read-only
	    STATUS mandatory
	    DESCRIPTION
			"The maximum signal to noise ratio during the link test to the 
			remote station or access point."
	    ::= { oriLinkTestTableEntry 27 }

	oriLinkTestHisLowFrameCount    OBJECT-TYPE
	    SYNTAX INTEGER
	    ACCESS read-only
	    STATUS mandatory
	    DESCRIPTION
			"The total number of frames sent at 1 Mbit/s speed during the link 
			test to the remote station or access point."
	    ::= { oriLinkTestTableEntry 28 }

	oriLinkTestHisStandardFrameCount    OBJECT-TYPE
	    SYNTAX INTEGER
	    ACCESS read-only
	    STATUS mandatory
	    DESCRIPTION
			"The total number of frames sent at 2 Mbit/s speed during the link 
			test to the remote station or access point."
	    ::= { oriLinkTestTableEntry 29 }

	oriLinkTestHisMediumFrameCount    OBJECT-TYPE
	    SYNTAX INTEGER
	    ACCESS read-only
	    STATUS mandatory
	    DESCRIPTION
			"The total number of frames sent at 5.5 Mbit/s (for Turbo-8, it is 
			5 Mbit/s) speed during the link test to the remote station or 
			access point."
	    ::= { oriLinkTestTableEntry 30 }

	oriLinkTestHisHighFrameCount    OBJECT-TYPE
	    SYNTAX INTEGER
	    ACCESS read-only
	    STATUS mandatory
	    DESCRIPTION
			"The total number of frames sent at 11 Mbit/s (for Turbo-8, it is 
			5 Mbit/s) speed during the link test to the remote station or 
			access point."
	    ::= { oriLinkTestTableEntry 31 }

	oriLinkTestInterface   OBJECT-TYPE
	    SYNTAX INTEGER
	    ACCESS read-only
	    STATUS mandatory
	    DESCRIPTION
	        "The PCMCIA Card Number to which the Client has sent the Explore 
	        Response Message."
	    ::= { oriLinkTestTableEntry 32 }

	oriLinkTestRadioType    OBJECT-TYPE
	    SYNTAX INTEGER
	    ACCESS read-only
	    STATUS mandatory
	    DESCRIPTION
			"The Wireless Standard eg. IEEE 802.11 or IEEE 802.11b used on the 
			Radio."
	    ::= { oriLinkTestTableEntry 33 }

--=============================================================================
-- Access Server Trap Variables
--=============================================================================

    accessServerTrapVariables OBJECT IDENTIFIER 
        ::= { accessServerTraps 1 }

	accessServerGenericInformationMessage OBJECT-TYPE
	    SYNTAX DisplayString
	    ACCESS not-accessible
	    STATUS mandatory
	    DESCRIPTION
		    "Any generic string information can be sent as this message."
        ::= { accessServerTrapVariables 1 }

	accessServerMacAddress OBJECT-TYPE
	    SYNTAX PhysAddress
	    ACCESS not-accessible
	    STATUS mandatory
	    DESCRIPTION
	        "The MAC address that is sent with the traps to
		    identify which Access Server has the problem "
        ::= { accessServerTrapVariables 2 }

	accessServerFailedTFTPServerAddress   OBJECT-TYPE
	    SYNTAX IpAddress
	    ACCESS not-accessible
	    STATUS mandatory
	    DESCRIPTION
	 	    "The ip address configured as the TFTP server 
		    for which the operation upload/download failed."
        ::= { accessServerTrapVariables 3 }

    accessServerFailedTFTPFilename   OBJECT-TYPE
	    SYNTAX DisplayString
	    ACCESS not-accessible
	    STATUS mandatory
	    DESCRIPTION
	 	    "The filename configured to be retrieved/sent from/to 
		    the TFTP server for which the operation upload/download
		    failed."
        ::= { accessServerTrapVariables 4 }

    accessServerFailedTFTPOperation   OBJECT-TYPE
	    SYNTAX INTEGER
		--    {
		--       upload(1),
		--       download(2)
		--    }
	    ACCESS not-accessible
	    STATUS mandatory
	    DESCRIPTION 
		    "This variable used in conjunction with the different TFTP traps (
		    TFTPInitiated, TFTPFailed, TFTPCompleted)"
        ::= { accessServerTrapVariables 5 }

    accessServerSuspendedTaskName   OBJECT-TYPE
	    SYNTAX DisplayString
        ACCESS not-accessible
	    STATUS mandatory
	    DESCRIPTION 
		    "The task that was suspended, can be several tasks executed within
		    the Access Server."
        ::= { accessServerTrapVariables 6 }

    accessServerWirelessCard   OBJECT-TYPE
	    SYNTAX INTEGER
	        {
	            pc-cardA(1),
	            pc-cardB(2)
	        }
        ACCESS not-accessible
	    STATUS mandatory
	    DESCRIPTION 
		    "This trap variable is used to determine on which Wireless Card,
		    PC Card A or PC Card B, a wireless TRAP has occured on."
		::= { accessServerTrapVariables 7 }
        
--=============================================================================
-- Access Server Flash Related Traps
--=============================================================================

	accessServerFlashRelatedTraps OBJECT IDENTIFIER 
	    ::= { accessServerTraps 2 }

	accessServerFlashEmpty TRAP-TYPE
	    ENTERPRISE accessServerFlashRelatedTraps
	    DESCRIPTION
	        "This trap is sent when the FLASH is empty."
	    ::= 1

	accessServerFlashCorrupted TRAP-TYPE
	    ENTERPRISE accessServerFlashRelatedTraps
	    DESCRIPTION
	        "This trap is sent when the data in the FLASH is corrupted."
	    ::= 2

--=============================================================================
-- Access Server Configuration Related Traps
--=============================================================================

	accessServerConfigurationRelatedTraps OBJECT IDENTIFIER
	    ::= { accessServerTraps 3 }

	accessServerInvalidKey TRAP-TYPE
	    ENTERPRISE accessServerConfigurationRelatedTraps
	    DESCRIPTION
	        "This trap is sent when an invalid key is detected at the
		    accessServer."
	    ::= 1

	accessServerAPMNotConfigured TRAP-TYPE
	    ENTERPRISE accessServerConfigurationRelatedTraps
	    DESCRIPTION
	        "This trap is sent when the APM information is not 
		    configured in the Access Server."
	    ::= 2

	accessServerWLCIncompatibleFirmware TRAP-TYPE
	    ENTERPRISE accessServerConfigurationRelatedTraps
	    DESCRIPTION
            "This trap is sent when an ORiNOCO PC Card plugged
		    in the Access Server is not compatible with the firmware
		    versions supported."
	    ::= 3

	accessServerWLCFailure TRAP-TYPE
        ENTERPRISE accessServerConfigurationRelatedTraps
        DESCRIPTION
            "This trap is sent when an ORiNOCO PC Card is not present or
            there is a failure in the ORiNOCO PC card."
        ::= 4

	accessServerWLCRemoval TRAP-TYPE
        ENTERPRISE accessServerConfigurationRelatedTraps
        DESCRIPTION
            "This trap is generated when the ORiNOCO PC Card is removed
            from the Access Server."
        ::= 5

	accessServerRadiusNotConfigured TRAP-TYPE
        ENTERPRISE accessServerConfigurationRelatedTraps
        DESCRIPTION
            "This trap is sent when the radius information is not configured
	        in the Access Server."
        ::= 6

	accessServerDNSIPNotConfigured TRAP-TYPE
        ENTERPRISE accessServerConfigurationRelatedTraps
        DESCRIPTION
            "This trap is sent when the DNS IP information is not 
		    configured in the Access Server."
        ::= 7

	accessServerNBNSIPNotConfigured TRAP-TYPE
        ENTERPRISE accessServerConfigurationRelatedTraps
        DESCRIPTION
            "This trap is sent when the NBNS IP information is not 
		    configured in the Access Server."
        ::= 8

     accessServerRadiusAuthenticationNotConfigured TRAP-TYPE
        ENTERPRISE accessServerConfigurationRelatedTraps
        DESCRIPTION
            "This trap is sent when the radius authentication information
            is not configured in the Access Server."
        ::= 9 
        
     accessServerRadiusAccountingNotConfigured TRAP-TYPE
        ENTERPRISE accessServerConfigurationRelatedTraps
        DESCRIPTION
            "This trap is sent when the radius accounting information
            is not configured in the Access Server."
        ::= 10

     accessServerDuplicateIPAddressEncountered TRAP-TYPE
        ENTERPRISE accessServerConfigurationRelatedTraps
        DESCRIPTION
            "This trap is sent when the IP Address of the Access Server
            is also used by someother device in the network."
        ::= 11

    accessServerWLCVoltageDiscrepancy TRAP-TYPE
        ENTERPRISE accessServerConfigurationRelatedTraps
        DESCRIPTION
            "This trap is sent when non 5volt card or 3.3 v card is 
            inserted in the Access Server."
        ::= 12
     
    accessServerWLCIncompatibleVendor TRAP-TYPE
        ENTERPRISE accessServerConfigurationRelatedTraps
        DESCRIPTION
            "This trap is generated when an incompatible wireless vendor
            card is inserted or present in the Access Server."
        ::= 13
        
    accessServerWLCFirmwareDownloadFailure TRAP-TYPE
        ENTERPRISE accessServerConfigurationRelatedTraps
        DESCRIPTION
            "This trap is generated when a failure occurs during the firmware
            download process."
        ::= 14
        
--=============================================================================
-- Access Server Diagnostic Traps
--=============================================================================

	accessServerDiagnosticTraps OBJECT IDENTIFIER
	    ::= { accessServerTraps 4 }

	accessServerTFTPInitiated TRAP-TYPE
	    ENTERPRISE accessServerDiagnosticTraps
	    DESCRIPTION
	        "This trap is sent when a TFTP operation happens
	        at the Access Server."
	    ::= 1

	accessServerTFTPCompleted TRAP-TYPE
	    ENTERPRISE accessServerDiagnosticTraps
	    DESCRIPTION
	        "This trap is sent when a TFTP operation failure happens
	        at the Access Server."
	    ::= 2

    accessServerTFTPFailure TRAP-TYPE
	    ENTERPRISE accessServerDiagnosticTraps
	    DESCRIPTION
	        "This trap is sent when a TFTP operation failure happens
	        at the Access Server."
	    ::= 3

	accessServerAdminStateMadeUp TRAP-TYPE
	    ENTERPRISE accessServerDiagnosticTraps
	    DESCRIPTION
	        "This trap is sent when the Access Server Admin state is made
		    'up'"
	    ::= 4

	accessServerAdminStateMadeDown TRAP-TYPE
	    ENTERPRISE accessServerDiagnosticTraps
	    DESCRIPTION
	        "This trap is sent when the Access Server Admin state is made
		    'down'"
	    ::= 5

	accessServerRebootingNow TRAP-TYPE
	    ENTERPRISE accessServerDiagnosticTraps
	    DESCRIPTION
	        "This trap is sent when the Access Server is about to reboot."
	    ::= 6

	accessServerTaskSuspended TRAP-TYPE
	    ENTERPRISE accessServerDiagnosticTraps
	    DESCRIPTION
	        "This trap is sent when a task has suspended in the Access Server."
	    ::= 7

	accessServerBootPFailed TRAP-TYPE
	    ENTERPRISE accessServerDiagnosticTraps
	    DESCRIPTION
	        "This trap is sent when the BootP protocol in the bootloader has
	        failed."
	    ::= 8

	accessServerDHCPFailed TRAP-TYPE
	    ENTERPRISE accessServerDiagnosticTraps
	    DESCRIPTION
	        "This trap is sent when the DHCP in the application software has
	        failed."
	    ::= 9

--=============================================================================
-- Access Server Image Related Traps
--=============================================================================

	accessServerImageTraps OBJECT IDENTIFIER
	    ::= { accessServerTraps 5 }

	accessServerZeroSizeImage TRAP-TYPE
	    ENTERPRISE accessServerImageTraps
	    DESCRIPTION
	        "This trap is sent when an image of size zero (0) is downloaded
	        to the access server."
	    ::= 1

	accessServerNonVxWorksImage TRAP-TYPE
	    ENTERPRISE accessServerImageTraps
	    DESCRIPTION
	        "This trap is sent when a non-VxWorks image is downloaded to the
	        access server."
	    ::= 2

	accessServerImageTooLarge TRAP-TYPE
	    ENTERPRISE accessServerImageTraps
	    DESCRIPTION
	        "This trap is sent when the image downloaded to the access server
	        exceeds the size limitation of 5 MB."
	    ::= 3
	    	    	        
END

--=============================================================================
-- Access Server 2000 MIBs End
--=============================================================================
