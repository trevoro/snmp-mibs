-- *****************************************************************************
-- Unisphere-Data-BGP-MIB
--
-- Unisphere Networks Enterprise MIB
--   Extensions for BGP Protocol Management
--
-- Copyright (c) 2001, 2002 Unisphere Networks, Inc.
-- Copyright (c) 2002 Juniper Networks, Inc.
--   All Rights Reserved.
-- *****************************************************************************

Unisphere-Data-BGP-MIB DEFINITIONS ::= BEGIN

IMPORTS
    MODULE-IDENTITY, OBJECT-TYPE, Unsigned32, IpAddress, Integer32, Counter32,
    Gauge32
        FROM SNMPv2-SMI
    DisplayString, TruthValue, RowStatus, TEXTUAL-CONVENTION
        FROM SNMPv2-TC
    MODULE-COMPLIANCE, OBJECT-GROUP
        FROM SNMPv2-CONF
    usDataMibs
        FROM Unisphere-Data-MIBs
    UsdVrfName
        FROM Unisphere-Data-TC;

usdBgpMIB  MODULE-IDENTITY
    LAST-UPDATED "200209041323Z"  -- 04-Sep-02 09:23 AM EDT
    ORGANIZATION "Juniper Networks, Inc."
    CONTACT-INFO
        "       Juniper Networks, Inc.
        Postal: 10 Technology Park Drive
                Westford, MA  01886
                USA
        Tel:    +1 978 589 5800
        Email:  mib@Juniper.net"
    DESCRIPTION
        "The BGP Protocol MIB for the Unisphere Networks enterprise."
    -- Revision History
    REVISION    "200209041323Z"  -- 04-Sep-02 09:23 AM EDT  - RX 4.0
    DESCRIPTION
        "Added support for BGP internal redistribute.
         Obsoleted usdBgpStorageInitialHistoryRoutePoolSize and
         usdBgpStorageMaxHistoryRoutePoolSize.
         Added the ability to unconfigure BGP attributes from the MIB."
    REVISION    "200203011654Z"  -- 01-Mar-02 11:54 AM EST  - RX 3.5
    DESCRIPTION
        "Added support for adding unicast BGP routes into a multicast view."
    REVISION    "200201231316Z"  -- 23-Jan-02 01:16 PM EST  - RX 3.4
    DESCRIPTION
        "Added support for peer and peer-group local-as."
    REVISION    "200112041523Z"  -- 04-Dec-01 10:23 AM EST  - RX 3.3
    DESCRIPTION
        "Replaced the route tables to add original route destination as an
        index:
          usdBgpRouteTable                  > usdBgpNewRouteTable
          usdBgpRouteFlapHistoryTable       > usdBgpNewRouteFlapHistoryTable
          usdBgpRouteCommunityTable         > usdBgpNewRouteCommunityTable
          usdBgpRouteExtendedCommunityTable > usdBgpNewRouteExtendedCommunityTable
          usdBgpRouteClusterIdTable         > usdBgpNewRouteClusterIdTable"
    REVISION    "200111302220Z"  -- 30-Nov-01 05:20 PM EST  - RX 3.2
    DESCRIPTION
        "Added support for BGP default IPv4 unicast."
    REVISION    "200106181859Z"  -- 18-Jun-01 02:59 PM EDT  - RX 3.0
    DESCRIPTION
        "Redesigned version of this MIB module."
    REVISION    "200001120000Z"  -- 12-Jan-00               - RX 1.3
    DESCRIPTION
        "Initial version of this MIB module."
    ::= { usDataMibs 29 }


-- +++++++++++++++++++++++++++++++++++++++++++++++++++++++++++++++++++++++++++++
-- Textual conventions
-- +++++++++++++++++++++++++++++++++++++++++++++++++++++++++++++++++++++++++++++
UsdBgpAfi ::= TEXTUAL-CONVENTION
    STATUS      current
    DESCRIPTION
        "Address family identifier (AFI)."
    SYNTAX      INTEGER {
                    bgpIpV4(1) }

UsdBgpSafi ::= TEXTUAL-CONVENTION
    STATUS      current
    DESCRIPTION
        "Subsequent address family identifier (SAFI)."
    SYNTAX      INTEGER {
                    bgpUnicast(1),
                    bgpMulticast(2),
                    bgpUnicastMulticast(3),
                    bgpVPNUnicast(128) }

UsdBgpStorageInteger ::= TEXTUAL-CONVENTION
    STATUS      current
    DESCRIPTION
        "Specifies an unsigned integer.  If an object with this type is set
        while BGP is created, the value will not be used until a reboot occurs."
    SYNTAX      Unsigned32

UsdBgpResetConnectionType ::= TEXTUAL-CONVENTION
    STATUS      current
    DESCRIPTION
        "Writing a value to an object of this type will cause the corresponding
        reset action to take place:
            resetTypeNoop             - no action (this value is always returned
                                        on a read)
            resetTypeHard             - causes a BGP session to be dropped and
                                        then re-established
            resetTypeSoftIn           - causes inbound policy to be re-applied
                                        to received routes
            resetTypeSoftOut          - causes outbound policy to be re-applied
                                        to sent routes
            resetTypeSoftInOut        - does both resetTypeSoftIn and
                                        resetTypeSoftOut
            resetTypeRouteFlapHistory - causes route-flap dampening history to
                                        be discarded"
    SYNTAX      INTEGER    {
                    resetTypeNoop(0),
                    resetTypeHard(1),
                    resetTypeSoftIn(2),
                    resetTypeSoftOut(3),
                    resetTypeSoftInOut(4),
                    resetTypeRouteFlapHistory(5) }


-- +++++++++++++++++++++++++++++++++++++++++++++++++++++++++++++++++++++++++++++
-- Managed objects
-- +++++++++++++++++++++++++++++++++++++++++++++++++++++++++++++++++++++++++++++
usdBgpObjects                      OBJECT IDENTIFIER ::= { usdBgpMIB 1 }

-- +++++++++++++++++++++++++++++++++++++++++++++++++++++++++++++++++++++++++++++
-- BGP General Group attributes (scalars)
-- +++++++++++++++++++++++++++++++++++++++++++++++++++++++++++++++++++++++++++++
usdBgpGeneralGroup                 OBJECT IDENTIFIER ::= { usdBgpObjects 1 }

usdBgpLocalAsNumber OBJECT-TYPE
    SYNTAX      INTEGER (0..65535)
    MAX-ACCESS  read-write
    STATUS      current
    DESCRIPTION
        "The local autonomous system number.  This object cannot be modified if
        BGP is enabled."
    DEFVAL    { 0 }
    ::= { usdBgpGeneralGroup 1 }

usdBgpEnabled OBJECT-TYPE
    SYNTAX      TruthValue
    MAX-ACCESS  read-write
    STATUS      current
    DESCRIPTION
        "Set this object to true(1) in order to have BGP router enabled."
    DEFVAL    { false }
    ::= { usdBgpGeneralGroup 2 }

usdBgpIdentifier OBJECT-TYPE
    SYNTAX      IpAddress
    MAX-ACCESS  read-write
    STATUS      current
    DESCRIPTION
        "The BGP identifier of the local system.  The identifier is the system
        router ID by default."
    ::= { usdBgpGeneralGroup 3 }

usdBgpAlwaysCompareMed OBJECT-TYPE
    SYNTAX      TruthValue
    MAX-ACCESS  read-write
    STATUS      current
    DESCRIPTION
        "Set this object to true(1) in order to compare metrics for paths from
        neighors of different ASs."
    DEFVAL    { false }
    ::= { usdBgpGeneralGroup 4 }

usdBgpDefaultLocalPreference OBJECT-TYPE
    SYNTAX      Unsigned32
    MAX-ACCESS  read-write
    STATUS      current
    DESCRIPTION
        "The default local preference."
    DEFVAL    { 100 }
    ::= { usdBgpGeneralGroup 5 }

usdBgpEqualCostLimit OBJECT-TYPE
    SYNTAX      INTEGER (0..65535)
    MAX-ACCESS  read-write
    STATUS      current
    DESCRIPTION
        "The maximum equal cost paths to store in routing table."
    DEFVAL    { 1 }
    ::= { usdBgpGeneralGroup 6 }

usdBgpClientToClientReflection OBJECT-TYPE
    SYNTAX      TruthValue
    MAX-ACCESS  read-write
    STATUS      current
    DESCRIPTION
        "Set this object to true(1) in order to have client-to-client route
        reflection enabled."
    DEFVAL    { true }
    ::= { usdBgpGeneralGroup 7 }

usdBgpClusterId OBJECT-TYPE
    SYNTAX      Unsigned32
    MAX-ACCESS  read-write
    STATUS      current
    DESCRIPTION
        "The cluster ID.  When this object is zero, the router ID will be used."
    DEFVAL    { 0 }
    ::= { usdBgpGeneralGroup 8 }

usdBgpConfederationId OBJECT-TYPE
    SYNTAX      Unsigned32
    MAX-ACCESS  read-write
    STATUS      current
    DESCRIPTION
        "The confederation ID.  When this object is zero, the router is not in a
        confederation."
    DEFVAL    { 0 }
    ::= { usdBgpGeneralGroup 9 }

usdBgpMissingAsWorst OBJECT-TYPE
    SYNTAX      TruthValue
    MAX-ACCESS  read-write
    STATUS      current
    DESCRIPTION
        "If this object is set to true(1) routes without a MED attribute are
        considered worse than routes with a MED attribute.  If this object is
        set to false(0) routes without a MED attribute are considered better
        than routes with a MED attribute."
    DEFVAL    { false }
    ::= { usdBgpGeneralGroup 10 }

usdBgpResetAllConnectionType OBJECT-TYPE
    SYNTAX      UsdBgpResetConnectionType
    MAX-ACCESS  read-write
    STATUS      current
    DESCRIPTION
        "Writing a value to this object causes all sessions to all peers to be
        cleared; the value determines what type of clear is executed (hard
        clear, soft clear in, soft clear out, etc.).  Reading this object has no
        effect and always returns resetTypeNoop."
    DEFVAL    { resetTypeNoop }
    ::= { usdBgpGeneralGroup 11 }

usdBgpAdvertiseInactive OBJECT-TYPE
    SYNTAX      TruthValue
    MAX-ACCESS  read-write
    STATUS      current
    DESCRIPTION
        "Set this object to true(1) in order to propagate received BGP routes
        which are not the best route in the IP forwarding table."
    DEFVAL    { false }
    ::= { usdBgpGeneralGroup 12 }

usdBgpEnforceFirstAs OBJECT-TYPE
    SYNTAX      TruthValue
    MAX-ACCESS  read-write
    STATUS      current
    DESCRIPTION
        "Set this object to true(1) in order to check whether the first AS
        number in the AS-path in routes from EBGP peers is consistent with the
        AS number of the peer."
    DEFVAL    { false }
    ::= { usdBgpGeneralGroup 13 }

usdBgpConfedCompareMed OBJECT-TYPE
    SYNTAX      TruthValue
    MAX-ACCESS  read-write
    STATUS      current
    DESCRIPTION
        "Set this object to true(1) in order to compare metrics for paths from
        neighors of different sub-ASs in the same confederation."
    DEFVAL    { false }
    ::= { usdBgpGeneralGroup 14 }

usdBgpGlobalRetryInterval OBJECT-TYPE
    SYNTAX      INTEGER (0..65535)
    UNITS       "seconds"
    MAX-ACCESS  read-write
    STATUS      current
    DESCRIPTION
        "The default number of seconds before BGP retries to establish an
        outgoing BGP session."
    DEFVAL    { 120 }
    ::= { usdBgpGeneralGroup 15 }

usdBgpGlobalConfigKeepAliveInterval OBJECT-TYPE
    SYNTAX      INTEGER (0..21845)
    UNITS       "seconds"
    MAX-ACCESS  read-write
    STATUS      current
    DESCRIPTION
        "Default time interval in seconds for the KeepAlive timer for all peers.
        Zero means don't send KeepAlive messages."
    DEFVAL    { 30 }
    ::= { usdBgpGeneralGroup 16 }

usdBgpGlobalConfigHoldTime OBJECT-TYPE
    SYNTAX      INTEGER (0|3..65535)
    UNITS       "seconds"
    MAX-ACCESS  read-write
    STATUS      current
    DESCRIPTION
        "Default time interval in seconds for the Hold timer for all peers.
        Zero means don't expect KeepAlive message to be received."
    DEFVAL    { 90 }
    ::= { usdBgpGeneralGroup 17 }

usdBgpGlobalAsOriginationInterval OBJECT-TYPE
    SYNTAX      INTEGER (1..65535)
    UNITS       "seconds"
    MAX-ACCESS  read-write
    STATUS      current
    DESCRIPTION
        "Default time interval in seconds for the MinASOriginationInterval timer
        for all peers."
    DEFVAL    { 10 }
    ::= { usdBgpGeneralGroup 18 }

usdBgpExternalAdvertisementInterval OBJECT-TYPE
    SYNTAX      INTEGER (0..65535)
    UNITS       "seconds"
    MAX-ACCESS  read-write
    STATUS      current
    DESCRIPTION
        "Default time interval in seconds for the MinRouteAdvertisementInterval
        timer for all external peers."
    DEFVAL    { 30 }
    ::= { usdBgpGeneralGroup 19 }

usdBgpGlobalRibOutEnabled OBJECT-TYPE
    SYNTAX      TruthValue
    MAX-ACCESS  read-write
    STATUS      current
    DESCRIPTION
        "Set this object to true(1) in order to enable RIB-out by default for
        all peers, or to false(2) to disable RIB-out by default for all peers."
    DEFVAL    { true }
    ::= { usdBgpGeneralGroup 20 }

usdBgpOverloadShutdown OBJECT-TYPE
    SYNTAX      TruthValue
    MAX-ACCESS  read-write
    STATUS      current
    DESCRIPTION
        "Set this object to true(1) for BGP to shut itself down when it runs out
        of memory.  Set this object to false(2) for BGP to continue running
        (with incomplete information) when it runs out of memory."
    DEFVAL    { false }
    ::= { usdBgpGeneralGroup 21 }

usdBgpLogNeighborChanges OBJECT-TYPE
    SYNTAX      TruthValue
    MAX-ACCESS  read-write
    STATUS      current
    DESCRIPTION
        "Set this object to true(1) for BGP log a message whenever a peer enters
        or leaves the established state."
    DEFVAL    { false }
    ::= { usdBgpGeneralGroup 22 }

usdBgpFastExternalFallover OBJECT-TYPE
    SYNTAX      TruthValue
    MAX-ACCESS  read-write
    STATUS      current
    DESCRIPTION
        "Set this object to true(1) for BGP to immediately bring down any
        directly adjacent EBGP session on a link down."
    DEFVAL    { false }
    ::= { usdBgpGeneralGroup 23 }

usdBgpInternalAdvertisementInterval OBJECT-TYPE
    SYNTAX      INTEGER (0..65535)
    UNITS       "seconds"
    MAX-ACCESS  read-write
    STATUS      current
    DESCRIPTION
        "Default time interval in seconds for the MinRouteAdvertisementInterval
        timer for all internal peers."
    DEFVAL    { 5 }
    ::= { usdBgpGeneralGroup 24 }

usdBgpMaxAsLimit OBJECT-TYPE
    SYNTAX      INTEGER (0..65535)
    MAX-ACCESS  read-write
    STATUS      current
    DESCRIPTION
        "Maximum length of received AS-path.  Received routes with an AS-path
        longer than this are not placed in the IP forwarding table and are not
        propagated to other peers.  Zero means no maximum length."
    DEFVAL    { 0 }
    ::= { usdBgpGeneralGroup 25 }

usdBgpOperationalState OBJECT-TYPE
    SYNTAX      INTEGER {
                    none(0),
                    up(1),
                    down(2),
                    overload(3) }
    MAX-ACCESS  read-only
    STATUS      current
    DESCRIPTION
        "The BGP instance operational state."
    ::= { usdBgpGeneralGroup 26 }

usdBgpPreviousOperationalState OBJECT-TYPE
    SYNTAX      INTEGER {
                    none(0),
                    up(1),
                    down(2),
                    overload(3) }
    MAX-ACCESS  read-only
    STATUS      current
    DESCRIPTION
        "The BGP instance previous operational state."
    ::= { usdBgpGeneralGroup 27 }

usdBgpAutomaticRouteTargetFilter OBJECT-TYPE
    SYNTAX      TruthValue
    MAX-ACCESS  read-write
    STATUS      current
    DESCRIPTION
        "Set this object to true(1) for BGP to enable automatic route-target
        filtering."
    DEFVAL    { false }
    ::= { usdBgpGeneralGroup 28 }

usdBgpDefaultIPv4Unicast OBJECT-TYPE
    SYNTAX      TruthValue
    MAX-ACCESS  read-write
    STATUS      current
    DESCRIPTION
        "Set this object to true(1) for BGP to automatically activate peers in
        the IPv4 unicast address family."
    DEFVAL    { false }
    ::= { usdBgpGeneralGroup 29 }

usdBgpRedistributeInternal OBJECT-TYPE
    SYNTAX      TruthValue
    MAX-ACCESS  read-write
    STATUS      current
    DESCRIPTION
        "Set this object to true(1) for BGP to automatically redistribute iBGP
        routes to IGP protocols."
    DEFVAL    { false }
    ::= { usdBgpGeneralGroup 30 }

usdBgpUnconfiguredAttributes OBJECT-TYPE
    SYNTAX      BITS {
        usdBgpLocalAsNumber(0),
        usdBgpEnabled(1),
        usdBgpIdentifier(2),
        usdBgpAlwaysCompareMed(3),
        usdBgpDefaultLocalPreference(4),
        usdBgpEqualCostLimit(5),
        usdBgpClientToClientReflection(6),
        usdBgpClusterId(7),
        usdBgpConfederationId(8),
        usdBgpMissingAsWorst(9),
        usdBgpAdvertiseInactive(10),
        usdBgpEnforceFirstAs(11),
        usdBgpConfedCompareMed(12),
        usdBgpGlobalRetryInterval(13),
        usdBgpGlobalConfigKeepAliveInterval(14),
        usdBgpGlobalConfigHoldTime(15),
        usdBgpGlobalAsOriginationInterval(16),
        usdBgpExternalAdvertisementInterval(17),
        usdBgpGlobalRibOutEnabled(18),
        usdBgpOverloadShutdown(19),
        usdBgpLogNeighborChanges(20),
        usdBgpFastExternalFallover(21),
        usdBgpInternalAdvertisementInterval(22),
        usdBgpMaxAsLimit(23),
        usdBgpAutomaticRouteTargetFilter(24),
        usdBgpDefaultIPv4Unicast(25),
        usdBgpRedistributeInternal(26) }
    MAX-ACCESS  read-write
    STATUS      current
    DESCRIPTION
        "On get each bit indicates whether the corresponding attribute is
        configured or unconfigured:
           0 = The attribute is configured (i.e. the configured value is the
               operational value).
           1 = The attribute is unconfigured (i.e. the operational value is
               inherited from the a higher level which could be the default
               value).

        Getting the attribute value itself always returns the operational value
        of that attribute regardless of whether the attribute is configured or
        unconfigured.

        On write each bit indicates wheter or not the corresponding attribute
        should be set to the unconfigured state:
           0 = No operation (i.e. do not change the state of the attribute).
           1 = Set the attribute to the unconfigured state.

        Setting an attribute to a value has the automatic side-effect of setting
        the bit with the same name to zero."
    DEFVAL    { { } }
    ::= { usdBgpGeneralGroup 33 }


-- +++++++++++++++++++++++++++++++++++++++++++++++++++++++++++++++++++++++++++++
-- BGP Route Table Statistics (scalars)
-- +++++++++++++++++++++++++++++++++++++++++++++++++++++++++++++++++++++++++++++
usdBgpRouteTableStatisticsGroup    OBJECT IDENTIFIER ::= { usdBgpObjects 2 }

usdBgpBaselineTime OBJECT-TYPE
    SYNTAX      Unsigned32
    MAX-ACCESS  read-only
    STATUS      current
    DESCRIPTION
        "The sysUpTime at which the counters were most recently baselined."
    ::= { usdBgpRouteTableStatisticsGroup 1 }

usdBgpDestinationCount OBJECT-TYPE
    SYNTAX      Gauge32
    MAX-ACCESS  read-only
    STATUS      current
    DESCRIPTION
        "Number of distinct destinations in the local RIB."
    ::= { usdBgpRouteTableStatisticsGroup 2 }

usdBgpDestinationMemoryUsed OBJECT-TYPE
    SYNTAX      Gauge32
    UNITS       "bytes"
    MAX-ACCESS  read-only
    STATUS      current
    DESCRIPTION
        "Memory used by distinct destinations in the local RIB."
    ::= { usdBgpRouteTableStatisticsGroup 3 }

usdBgpRouteCount OBJECT-TYPE
    SYNTAX      Gauge32
    MAX-ACCESS  read-only
    STATUS      current
    DESCRIPTION
        "Number of routes in the local RIB."
    ::= { usdBgpRouteTableStatisticsGroup 4 }

usdBgpRouteMemoryUsed OBJECT-TYPE
    SYNTAX      Gauge32
    UNITS       "bytes"
    MAX-ACCESS  read-only
    STATUS      current
    DESCRIPTION
        "Memory used by routes in the local RIB."
    ::= { usdBgpRouteTableStatisticsGroup 5 }

usdBgpSelectedRouteCount OBJECT-TYPE
    SYNTAX      Gauge32
    MAX-ACCESS  read-only
    STATUS      current
    DESCRIPTION
        "Number of routes selected for route table installation."
    ::= { usdBgpRouteTableStatisticsGroup 6 }

usdBgpPathAttributeCount OBJECT-TYPE
    SYNTAX      Gauge32
    MAX-ACCESS  read-only
    STATUS      current
    DESCRIPTION
        "Number of entries in the path attribute database."
    ::= { usdBgpRouteTableStatisticsGroup 8 }

usdBgpPathAttributeMemoryUsed OBJECT-TYPE
    SYNTAX      Gauge32
    UNITS       "bytes"
    MAX-ACCESS  read-only
    STATUS      current
    DESCRIPTION
        "Memory used by entries in the path attribute database."
    ::= { usdBgpRouteTableStatisticsGroup 9 }

usdBgpRouteFlapHistoryCount OBJECT-TYPE
    SYNTAX      Gauge32
    MAX-ACCESS  read-only
    STATUS      current
    DESCRIPTION
        "Number of routes with active route flap histories."
    ::= { usdBgpRouteTableStatisticsGroup 10 }

usdBgpRouteFlapHistoryMemoryUsed OBJECT-TYPE
    SYNTAX      Gauge32
    UNITS       "bytes"
    MAX-ACCESS  read-only
    STATUS      current
    DESCRIPTION
        "Memory used by routes with active route flap histories."
    ::= { usdBgpRouteTableStatisticsGroup 11 }

usdBgpSuppressedRouteCount OBJECT-TYPE
    SYNTAX      Gauge32
    MAX-ACCESS  read-only
    STATUS      current
    DESCRIPTION
        "Number of routes suppressed due to route flap."
    ::= { usdBgpRouteTableStatisticsGroup 12 }


-- +++++++++++++++++++++++++++++++++++++++++++++++++++++++++++++++++++++++++++++
-- BGP Confederation Peer attributes
-- +++++++++++++++++++++++++++++++++++++++++++++++++++++++++++++++++++++++++++++
--
--  BGP ConfederationPeer Table
--
usdBgpConfederationPeerTable OBJECT-TYPE
    SYNTAX      SEQUENCE OF UsdBgpConfederationPeerEntry
    MAX-ACCESS  not-accessible
    STATUS      current
    DESCRIPTION
        "The Unisphere BGP Confederation Peer Table describes the BGP-specific
        characteristics of confederation peers."
  ::= { usdBgpObjects 3 }

usdBgpConfederationPeerEntry OBJECT-TYPE
    SYNTAX      UsdBgpConfederationPeerEntry
    MAX-ACCESS  not-accessible
    STATUS      current
    DESCRIPTION
        "The BGP Confederation Peer Entry describes BGP-specific characteristics
        of one confederation peer."
    INDEX     { usdBgpConfederationPeerAsNumber }
    ::= { usdBgpConfederationPeerTable 1 }

UsdBgpConfederationPeerEntry ::= SEQUENCE {
    usdBgpConfederationPeerAsNumber     INTEGER,
    usdBgpConfederationPeerRowStatus    RowStatus }

usdBgpConfederationPeerAsNumber OBJECT-TYPE
    SYNTAX      INTEGER (1..65535)
    MAX-ACCESS  not-accessible
    STATUS      current
    DESCRIPTION
        "The AsNumber of this confederation peer."
    ::= { usdBgpConfederationPeerEntry 1 }

usdBgpConfederationPeerRowStatus OBJECT-TYPE
    SYNTAX      RowStatus
    MAX-ACCESS  read-create
    STATUS      current
    DESCRIPTION
        "Controls creation/deletion of entries in this table according to the
        RowStatus textual convention, constrained to support the following
        values only:
            createAndGo
            destroy "
    ::= { usdBgpConfederationPeerEntry 2 }


-- +++++++++++++++++++++++++++++++++++++++++++++++++++++++++++++++++++++++++++++
-- BGP Peer attributes
-- +++++++++++++++++++++++++++++++++++++++++++++++++++++++++++++++++++++++++++++
--
--  BGP Peer Table
--
usdBgpPeerTable OBJECT-TYPE
    SYNTAX      SEQUENCE OF UsdBgpPeerEntry
    MAX-ACCESS  not-accessible
    STATUS      current
    DESCRIPTION
        "The Unisphere BGP Peer Table describes the BGP-specific characteristics
        of peers."
    ::= { usdBgpObjects 4 }

usdBgpPeerEntry OBJECT-TYPE
    SYNTAX      UsdBgpPeerEntry
    MAX-ACCESS  not-accessible
    STATUS      current
    DESCRIPTION
        "The BGP Peer Entry describes BGP-specific characteristics of one peer."
    INDEX     { usdBgpPeerVrfName,
                usdBgpPeerRemoteAddress }
    ::= { usdBgpPeerTable 1 }

UsdBgpPeerEntry ::= SEQUENCE {
    usdBgpPeerVrfName                       UsdVrfName,
    usdBgpPeerRemoteAddress                 IpAddress,
    usdBgpPeerAdminStatus                   INTEGER,
    usdBgpPeerState                         INTEGER,
    usdBgpPeerNegotiatedVersion             Integer32,
    usdBgpPeerLocalAddress                  IpAddress,
    usdBgpPeerLocalAddressMask              IpAddress,
    usdBgpPeerLocalPort                     INTEGER,
    usdBgpPeerRemoteAsNumber                INTEGER,
    usdBgpPeerRemotePort                    INTEGER,
    usdBgpPeerInUpdates                     Counter32,
    usdBgpPeerOutUpdates                    Counter32,
    usdBgpPeerInTotalMessages               Counter32,
    usdBgpPeerOutTotalMessages              Counter32,
    usdBgpPeerLastErrorCode                 OCTET STRING,
    usdBgpPeerLastResetReason               DisplayString,
    usdBgpPeerFsmEstablishedTransitions     Counter32,
    usdBgpPeerFsmEstablishedTime            Gauge32,
    usdBgpPeerRetryInterval                 INTEGER,
    usdBgpPeerHoldTime                      INTEGER,
    usdBgpPeerKeepAliveInterval             INTEGER,
    usdBgpPeerConfigHoldTime                INTEGER,
    usdBgpPeerConfigKeepAliveInterval       INTEGER,
    usdBgpPeerAsOriginationInterval         INTEGER,
    usdBgpPeerAdvertisementInterval         INTEGER,
    usdBgpPeerInUpdateElapsedTime           Gauge32,
    usdBgpPeerDescription                   DisplayString,
    usdBgpPeerRemoteIdentifier              IpAddress,
    usdBgpPeerWeight                        Unsigned32,
    usdBgpPeerEbgpMultihop                  TruthValue,
    usdBgpPeerEbgpMultihopTtl               INTEGER,
    usdBgpPeerUpdateSource                  IpAddress,
    usdBgpPeerMd5Password                   OCTET STRING,
    usdBgpPeerMaxUpdateSize                 Unsigned32,
    usdBgpPeerType                          INTEGER,
    usdBgpPeerSupportsCapabilityNegotiation TruthValue,
    usdBgpPeerCapabilityMultiProtocol       TruthValue,
    usdBgpPeerCapabilityRouteRefresh        TruthValue,
    usdBgpPeerCapabilityRouteRefreshCiscoProprietary TruthValue,
    usdBgpPeerResetConnectionType           UsdBgpResetConnectionType,
    usdBgpPeerRowStatus                     RowStatus,
    usdBgpPeerLocalAsNumber                 INTEGER,
    usdBgpPeerUnconfiguredAttributes        BITS }

usdBgpPeerVrfName OBJECT-TYPE
    SYNTAX      UsdVrfName
    MAX-ACCESS  not-accessible
    STATUS      current
    DESCRIPTION
        "The name of the VPN Routing Forwarding (VRF) instance in which this
        peer is configured.  The empty string indicates that this peer is not in
        a VRF."
    ::= { usdBgpPeerEntry 1 }

usdBgpPeerRemoteAddress OBJECT-TYPE
    SYNTAX      IpAddress
    MAX-ACCESS  not-accessible
    STATUS      current
    DESCRIPTION
        "The remote IP address of this entry's BGP peer."
    ::= { usdBgpPeerEntry 2 }

usdBgpPeerAdminStatus OBJECT-TYPE
    SYNTAX      INTEGER {
                    stop(1),
                    start(2) }
    MAX-ACCESS  read-create
    STATUS      current
    DESCRIPTION
        "The desired state of the BGP connection.  A transition from 'stop' to
        'start' will cause the BGP Start Event to be generated.  A transition
        from 'start' to 'stop' will cause the BGP Stop Event to be generated.
        This parameter can be used to restart BGP peer connections.  Care should
        be used in providing write access to this object without adequate
        authentication."
    ::= { usdBgpPeerEntry 3 }

usdBgpPeerState OBJECT-TYPE
    SYNTAX      INTEGER {
                    stop(0),
                    idle(1),
                    connect(2),
                    active(3),
                    opensent(4),
                    openconfirm(5),
                    established(6),
                    removing(7) }
    MAX-ACCESS  read-only
    STATUS      current
    DESCRIPTION
        "The BGP peer connection state."
    ::= { usdBgpPeerEntry 4 }

usdBgpPeerNegotiatedVersion OBJECT-TYPE
    SYNTAX      Integer32
    MAX-ACCESS  read-only
    STATUS      current
    DESCRIPTION
        "The negotiated version of BGP running between the two peers."
    ::= { usdBgpPeerEntry 5 }

usdBgpPeerLocalAddress OBJECT-TYPE
    SYNTAX      IpAddress
    MAX-ACCESS  read-only
    STATUS      current
    DESCRIPTION
        "The local IP address of this entry's BGP connection."
    ::= { usdBgpPeerEntry 6 }

usdBgpPeerLocalAddressMask OBJECT-TYPE
    SYNTAX      IpAddress
    MAX-ACCESS  read-only
    STATUS      current
    DESCRIPTION
        "The local IP address mask of this entry's BGP connection."
    ::= { usdBgpPeerEntry 7 }

usdBgpPeerLocalPort OBJECT-TYPE
    SYNTAX      INTEGER (0..65535)
    MAX-ACCESS  read-only
    STATUS      current
    DESCRIPTION
        "The local port for the TCP connection between the BGP peers."
    ::= { usdBgpPeerEntry 8 }

usdBgpPeerRemoteAsNumber OBJECT-TYPE
    SYNTAX      INTEGER (0..65535)
    MAX-ACCESS  read-create
    STATUS      current
    DESCRIPTION
        "The peer's autonomous system number."
    DEFVAL    { 0 }
    ::= { usdBgpPeerEntry 9 }

usdBgpPeerRemotePort OBJECT-TYPE
    SYNTAX      INTEGER (0..65535)
    MAX-ACCESS  read-only
    STATUS      current
    DESCRIPTION
        "The remote port for the TCP connection between the BGP peers.  Note
        that the objects bgpPeerLocalAddr, bgpPeerLocalPort, bgpPeerRemoteAddr
        and bgpPeerRemotePort provide the appropriate reference to the standard
        MIB TCP connection table."
    ::= { usdBgpPeerEntry 10 }

usdBgpPeerInUpdates OBJECT-TYPE
    SYNTAX      Counter32
    MAX-ACCESS  read-only
    STATUS      current
    DESCRIPTION
        "The number of BGP UPDATE messages received on this connection.  This
        object should be initialized to zero (0) when the connection is
        established."
    ::= { usdBgpPeerEntry 11 }

usdBgpPeerOutUpdates OBJECT-TYPE
    SYNTAX      Counter32
    MAX-ACCESS  read-only
    STATUS      current
    DESCRIPTION
        "The number of BGP UPDATE messages transmitted on this connection.  This
        object should be initialized to zero (0) when the connection is
        established."
    ::= { usdBgpPeerEntry 12 }

usdBgpPeerInTotalMessages OBJECT-TYPE
    SYNTAX      Counter32
    MAX-ACCESS  read-only
    STATUS      current
    DESCRIPTION
        "The total number of messages received from the remote peer on this
        connection.  This object should be initialized to zero when the
        connection is established."
    ::= { usdBgpPeerEntry 13 }

usdBgpPeerOutTotalMessages OBJECT-TYPE
    SYNTAX      Counter32
    MAX-ACCESS  read-only
    STATUS      current
    DESCRIPTION
        "The total number of messages transmitted to the remote peer on this
        connection.  This object should be initialized to zero when the
        connection is established."
    ::= { usdBgpPeerEntry 14 }

usdBgpPeerLastErrorCode OBJECT-TYPE
    SYNTAX      OCTET STRING (SIZE(2))
    MAX-ACCESS  read-only
    STATUS      current
    DESCRIPTION
        "The last error code and subcode seen by this peer on this connection.
        If no error has occurred, this field is zero.  Otherwise, the first byte
        of this two byte OCTET STRING contains the error code, and the second
        byte contains the subcode."
    ::= { usdBgpPeerEntry 15 }

usdBgpPeerLastResetReason OBJECT-TYPE
    SYNTAX      DisplayString
    MAX-ACCESS  read-only
    STATUS      current
    DESCRIPTION
        "The string representing the last error code seen by this peer on this
        connection.  If no error has occurred, this string is null."
    ::= { usdBgpPeerEntry 16 }

usdBgpPeerFsmEstablishedTransitions OBJECT-TYPE
    SYNTAX      Counter32
    MAX-ACCESS  read-only
    STATUS      current
    DESCRIPTION
        "The total number of times the BGP FSM transitioned into the established
        state."
    ::= { usdBgpPeerEntry 17 }

usdBgpPeerFsmEstablishedTime OBJECT-TYPE
    SYNTAX      Gauge32
    UNITS       "seconds"
    MAX-ACCESS  read-only
    STATUS      current
    DESCRIPTION
        "This timer indicates how long (in seconds) this peer has been in the
        Established state or how long since this peer was last in the
        Established state.  It is set to zero when a new peer is configured or
        the router is booted."
    ::= { usdBgpPeerEntry 18 }

usdBgpPeerRetryInterval OBJECT-TYPE
    SYNTAX      INTEGER (1..65535)
    UNITS       "seconds"
    MAX-ACCESS  read-create
    STATUS      current
    DESCRIPTION
        "Time interval in seconds for the ConnectRetry timer.  The suggested
        value for this timer is 120 seconds."
    DEFVAL    { 120 }
    ::= { usdBgpPeerEntry 19 }

usdBgpPeerHoldTime OBJECT-TYPE
    SYNTAX      INTEGER (0|3..65535)
    UNITS       "seconds"
    MAX-ACCESS  read-only
    STATUS      current
    DESCRIPTION
        "Time interval in seconds for the Hold Timer established with the peer.
        The value of this object is calculated by this BGP speaker by using the
        smaller of the value in bgpPeerHoldTimeConfigured and the Hold Time
        received in the OPEN message.  This value must be at lease three seconds
        if it is not zero (0) in which case the Hold Timer has not been
        established with the peer, or, the value of bgpPeerHoldTimeConfigured is
        zero (0)."
    ::= { usdBgpPeerEntry 20 }

usdBgpPeerKeepAliveInterval OBJECT-TYPE
    SYNTAX      INTEGER (0..21845)
    UNITS       "seconds"
    MAX-ACCESS  read-only
    STATUS      current
    DESCRIPTION
        "Time interval in seconds for the KeepAlive timer established with the
        peer.  The value of this object is calculated by this BGP speaker such
        that, when compared with bgpPeerHoldTime, it has the same proportion as
        what bgpPeerKeepAliveConfigured has when compared with
        bgpPeerHoldTimeConfigured.  If the value of this object is zero (0), it
        indicates that the KeepAlive timer has not been established with the
        peer, or, the value of bgpPeerKeepAliveConfigured is zero (0)."
    ::= { usdBgpPeerEntry 21 }

usdBgpPeerConfigHoldTime OBJECT-TYPE
    SYNTAX      INTEGER (0|3..65535)
    UNITS       "seconds"
    MAX-ACCESS  read-create
    STATUS      current
    DESCRIPTION
        "Time interval in seconds for the Hold Time configured for this BGP
        speaker with this peer.  This value is placed in an OPEN message sent to
        this peer by this BGP speaker, and is compared with the Hold Time field
        in an OPEN message received from the peer when determining the Hold Time
        (bgpPeerHoldTime) with the peer.  This value must not be less than three
        seconds if it is not zero (0) in which case the Hold Time is NOT to be
        established with the peer.  The suggested value for this timer is 90
        seconds."
    DEFVAL    { 90 }
    ::= { usdBgpPeerEntry 22 }

usdBgpPeerConfigKeepAliveInterval OBJECT-TYPE
    SYNTAX      INTEGER (0..21845)
    UNITS       "seconds"
    MAX-ACCESS  read-create
    STATUS      current
    DESCRIPTION
        "Time interval in seconds for the KeepAlive timer configured for this
        BGP speaker with this peer.  The value of this object will only
        determine the KEEPALIVE messages' frequency relative to the value
        specified in bgpPeerHoldTimeConfigured; the actual time interval for the
        KEEPALIVE messages is indicated by bgpPeerKeepAlive.  A reasonable
        maximum value for this timer would be configured to be one third of that
        of bgpPeerHoldTimeConfigured.  If the value of this object is zero (0),
        no periodical KEEPALIVE messages are sent to the peer after the BGP
        connection has been established.  The suggested value for this timer is
        30 seconds."
    DEFVAL    { 30 }
    ::= { usdBgpPeerEntry 23 }

usdBgpPeerAsOriginationInterval OBJECT-TYPE
    SYNTAX      INTEGER (1..65535)
    UNITS       "seconds"
    MAX-ACCESS  read-create
    STATUS      current
    DESCRIPTION
        "Time interval in seconds for the MinASOriginationInterval timer.  The
        suggested value for this timer is 10 seconds."
    DEFVAL    { 10 }
    ::= { usdBgpPeerEntry 24 }

usdBgpPeerAdvertisementInterval OBJECT-TYPE
    SYNTAX      INTEGER (1..65535)
    UNITS       "seconds"
    MAX-ACCESS  read-create
    STATUS      current
    DESCRIPTION
        "Time interval in seconds for the MinRouteAdvertisementInterval timer.
        The suggested value for this timer is 30 seconds."
    DEFVAL    { 30 }
    ::= { usdBgpPeerEntry 25 }

usdBgpPeerInUpdateElapsedTime OBJECT-TYPE
    SYNTAX      Gauge32
    UNITS       "seconds"
    MAX-ACCESS  read-only
    STATUS      current
    DESCRIPTION
        "Elapsed time in seconds since the last BGP UPDATE message was received
        from the peer.  Each time bgpPeerInUpdates is incremented, the value of
        this object is set to zero (0)."
    ::= { usdBgpPeerEntry 26 }

usdBgpPeerDescription OBJECT-TYPE
    SYNTAX      DisplayString (SIZE(0..80))
    MAX-ACCESS  read-create
    STATUS      current
    DESCRIPTION
        "Peer textual description."
    DEFVAL    { "" }
    ::= { usdBgpPeerEntry 27 }

usdBgpPeerRemoteIdentifier OBJECT-TYPE
    SYNTAX      IpAddress
    MAX-ACCESS  read-only
    STATUS      current
    DESCRIPTION
        "Peer's remote router ID."
    ::= { usdBgpPeerEntry 28 }

usdBgpPeerWeight OBJECT-TYPE
    SYNTAX      Unsigned32
    MAX-ACCESS  read-create
    STATUS      current
    DESCRIPTION
        "The weight assigned to routes learned from peer."
    DEFVAL    { 0 }
    ::= { usdBgpPeerEntry 29 }

usdBgpPeerEbgpMultihop OBJECT-TYPE
    SYNTAX      TruthValue
    MAX-ACCESS  read-create
    STATUS      current
    DESCRIPTION
        "The EBGP multihop is enabled."
    DEFVAL    { false }
    ::= { usdBgpPeerEntry 30 }

usdBgpPeerEbgpMultihopTtl OBJECT-TYPE
    SYNTAX      INTEGER (1..255)
    MAX-ACCESS  read-create
    STATUS      current
    DESCRIPTION
        "Maximum number of hops to the external peer (only relevant if EBGP
        multihop turned on)."
    DEFVAL    { 255 }
    ::= { usdBgpPeerEntry 31 }

usdBgpPeerUpdateSource OBJECT-TYPE
    SYNTAX      IpAddress
    MAX-ACCESS  read-create
    STATUS      current
    DESCRIPTION
        "The source IP address for peer connections."
    DEFVAL    { 0 }
    ::= { usdBgpPeerEntry 32 }

usdBgpPeerMd5Password OBJECT-TYPE
    SYNTAX      OCTET STRING (SIZE(0..32))
    MAX-ACCESS  read-create
    STATUS      current
    DESCRIPTION
        "The password for MD5 authentication.  Reading this object always
        results in an OCTET STRING of length zero."
    DEFVAL    { "" }
    ::= { usdBgpPeerEntry 33 }

usdBgpPeerMaxUpdateSize OBJECT-TYPE
    SYNTAX      Unsigned32
    UNITS       "bytes"
    MAX-ACCESS  read-create
    STATUS      current
    DESCRIPTION
        "The maximum size in bytes of transmitted UPDATE messages."
    DEFVAL    { 4096 }
    ::= { usdBgpPeerEntry 34 }

usdBgpPeerType OBJECT-TYPE
    SYNTAX      INTEGER {
                    peerTypeInternal(1),
                    peerTypeExternal(2),
                    peerTypeConfederation(3),
                    peerTypeUnknown(4) }
    MAX-ACCESS  read-only
    STATUS      current
    DESCRIPTION
        "The type of peer."
    ::= { usdBgpPeerEntry 35 }

usdBgpPeerSupportsCapabilityNegotiation OBJECT-TYPE
    SYNTAX      TruthValue
    MAX-ACCESS  read-only
    STATUS      current
    DESCRIPTION
        "The peer supports capability negotiation."
    ::= { usdBgpPeerEntry 36 }

usdBgpPeerCapabilityMultiProtocol OBJECT-TYPE
    SYNTAX      TruthValue
    MAX-ACCESS  read-only
    STATUS      current
    DESCRIPTION
        "The peer supports the multi-protocol capablity."
    ::= { usdBgpPeerEntry 37 }

usdBgpPeerCapabilityRouteRefresh OBJECT-TYPE
    SYNTAX      TruthValue
    MAX-ACCESS  read-only
    STATUS      current
    DESCRIPTION
        "The peer supports the route-refresh capability."
    ::= { usdBgpPeerEntry 38 }

usdBgpPeerCapabilityRouteRefreshCiscoProprietary OBJECT-TYPE
    SYNTAX      TruthValue
    MAX-ACCESS  read-only
    STATUS      current
    DESCRIPTION
        "The peer supports the route-refresh-cisco capability."
    ::= { usdBgpPeerEntry 39 }

usdBgpPeerResetConnectionType OBJECT-TYPE
    SYNTAX      UsdBgpResetConnectionType
    MAX-ACCESS  read-create
    STATUS      current
    DESCRIPTION
        "Writing a value to this object causes the session to the peer to be
        cleared; the value determines what type of clear is executed (hard
        clear, soft clear in, soft clear out, etc.).  Reading this object has no
        effect and always returns resetTypeNoop."
    DEFVAL    { resetTypeNoop }
    ::= { usdBgpPeerEntry 40 }

usdBgpPeerRowStatus OBJECT-TYPE
    SYNTAX      RowStatus
    MAX-ACCESS  read-create
    STATUS      current
    DESCRIPTION
        "Controls creation/deletion of entries in this table according to the
        RowStatus textual convention, constrained to support the following
        values only:
            createAndGo
            destroy

        To create an entry in this table, the following entry objects MUST be
        explicitly configured:
            usdBgpPeerRemoteAs "
    ::= { usdBgpPeerEntry 41 }

usdBgpPeerLocalAsNumber OBJECT-TYPE
    SYNTAX      INTEGER (0..65535)
    MAX-ACCESS  read-create
    STATUS      current
    DESCRIPTION
        "The local autonomous system number to be used for this peer.  Value
        zero (0) means that the global local automous system number (as
        specified in the object usdBgpLocalAsNumber) is used."
    DEFVAL    { 0 }
    ::= { usdBgpPeerEntry 42 }

usdBgpPeerUnconfiguredAttributes OBJECT-TYPE
    SYNTAX      BITS {
        usdBgpPeerAdminStatus(0),
        usdBgpPeerRemoteAsNumber(1),
        usdBgpPeerRetryInterval(2),
        usdBgpPeerConfigHoldTime(3),
        usdBgpPeerConfigKeepAliveInterval(4),
        usdBgpPeerAsOriginationInterval(5),
        usdBgpPeerAdvertisementInterval(6),
        usdBgpPeerDescription(7),
        usdBgpPeerWeight(8),
        usdBgpPeerEbgpMultihop(9),
        usdBgpPeerEbgpMultihopTtl(10),
        usdBgpPeerUpdateSource(11),
        usdBgpPeerMd5Password(12),
        usdBgpPeerMaxUpdateSize(13),
        usdBgpPeerLocalAsNumber(14) }
    MAX-ACCESS  read-create
    STATUS      current
    DESCRIPTION
        "On get each bit indicates whether the corresponding attribute is
        configured or unconfigured:
           0 = The attribute is configured (i.e. the configured value is the
               operational value).
           1 = The attribute is unconfigured (i.e. the operational value is
               inherited from the a higher level which could be the default
               value).

        Getting the attribute value itself always returns the operational value
        of that attribute regardless of whether the attribute is configured or
        unconfigured.

        On write each bit indicates wheter or not the corresponding attribute
        should be set to the unconfigured state:
           0 = No operation (i.e. do not change the state of the attribute).
           1 = Set the attribute to the unconfigured state.

        Setting an attribute to a value has the automatic side-effect of setting
        the bit with the same name to zero."
    DEFVAL    { { } }
    ::= { usdBgpPeerEntry 60 }


-- +++++++++++++++++++++++++++++++++++++++++++++++++++++++++++++++++++++++++++++
-- BGP Peer Proposed AFI/SAFI peer attributes
-- +++++++++++++++++++++++++++++++++++++++++++++++++++++++++++++++++++++++++++++
--
--  BGP PeerProposedAfiSafiPeer Table
--
usdBgpPeerProposedAfiSafiPeerTable OBJECT-TYPE
    SYNTAX      SEQUENCE OF UsdBgpPeerProposedAfiSafiPeerEntry
    MAX-ACCESS  not-accessible
    STATUS      current
    DESCRIPTION
        "The Unisphere BGP PeerProposedAfiSafi Peer Table describes the
        BGP-specific AFI and SAFIs a peer proposed."
    ::= { usdBgpObjects 5 }

usdBgpPeerProposedAfiSafiPeerEntry OBJECT-TYPE
    SYNTAX      UsdBgpPeerProposedAfiSafiPeerEntry
    MAX-ACCESS  not-accessible
    STATUS      current
    DESCRIPTION
        "The BGP PeerProposedAfiSafi Peer Entry describes a BGP-specific
        AFI/SAFIs proposed by one peer."
    INDEX     { usdBgpPeerProposedAfiSafiPeerVrfName,
                usdBgpPeerProposedAfiSafiPeerRemoteAddr,
                usdBgpPeerProposedAfiSafiPeerAfi,
                usdBgpPeerProposedAfiSafiPeerSafi }
    ::= { usdBgpPeerProposedAfiSafiPeerTable 1 }

UsdBgpPeerProposedAfiSafiPeerEntry ::= SEQUENCE {
    usdBgpPeerProposedAfiSafiPeerVrfName    UsdVrfName,
    usdBgpPeerProposedAfiSafiPeerRemoteAddr IpAddress,
    usdBgpPeerProposedAfiSafiPeerAfi        UsdBgpAfi,
    usdBgpPeerProposedAfiSafiPeerSafi       UsdBgpSafi,
    usdBgpPeerProposedAfiSafiPeerRowStatus  RowStatus }

usdBgpPeerProposedAfiSafiPeerVrfName OBJECT-TYPE
    SYNTAX      UsdVrfName
    MAX-ACCESS  not-accessible
    STATUS      current
    DESCRIPTION
        "The name of the VPN Routing Forwarding (VRF) instance in which this
        peer is configured.  The empty string indicates that this peer is not in
        a VRF."
    ::= { usdBgpPeerProposedAfiSafiPeerEntry 1 }

usdBgpPeerProposedAfiSafiPeerRemoteAddr OBJECT-TYPE
    SYNTAX      IpAddress
    MAX-ACCESS  not-accessible
    STATUS      current
    DESCRIPTION
        "The remote IP address of this entry's BGP peer."
    ::= { usdBgpPeerProposedAfiSafiPeerEntry 2 }

usdBgpPeerProposedAfiSafiPeerAfi OBJECT-TYPE
    SYNTAX      UsdBgpAfi
    MAX-ACCESS  not-accessible
    STATUS      current
    DESCRIPTION
        "The AFI proposed by this peer to us."
    ::= { usdBgpPeerProposedAfiSafiPeerEntry 3}

usdBgpPeerProposedAfiSafiPeerSafi OBJECT-TYPE
    SYNTAX      UsdBgpSafi
    MAX-ACCESS  not-accessible
    STATUS      current
    DESCRIPTION
        "The SAFI proposed by this peer to us."
    ::= { usdBgpPeerProposedAfiSafiPeerEntry 4 }

usdBgpPeerProposedAfiSafiPeerRowStatus OBJECT-TYPE
    SYNTAX      RowStatus
    MAX-ACCESS  read-only
    STATUS      current
    DESCRIPTION
        "Should always be active according to the Row Status convention."
    ::= { usdBgpPeerProposedAfiSafiPeerEntry 5 }

-- +++++++++++++++++++++++++++++++++++++++++++++++++++++++++++++++++++++++++++++
-- BGP Local Proposed AFI/SAFI peer attributes
-- +++++++++++++++++++++++++++++++++++++++++++++++++++++++++++++++++++++++++++++
--
--  BGP LocalProposedAfiSafiPeer Table
--
usdBgpLocalProposedAfiSafiPeerTable OBJECT-TYPE
    SYNTAX      SEQUENCE OF UsdBgpLocalProposedAfiSafiPeerEntry
    MAX-ACCESS  not-accessible
    STATUS      current
    DESCRIPTION
        "The Unisphere BGP LocalProposedAfiSafi Peer Table describes the
        BGP-specific AFI and SAFIs proposed to the peer."
    ::= { usdBgpObjects 6 }

usdBgpLocalProposedAfiSafiPeerEntry OBJECT-TYPE
    SYNTAX      UsdBgpLocalProposedAfiSafiPeerEntry
    MAX-ACCESS  not-accessible
    STATUS      current
    DESCRIPTION
        "The BGP LocalProposedAfiSafi Peer Entry describes a BGP-specific
        AFI/SAFIs proposed to one peer."
    INDEX     { usdBgpLocalProposedAfiSafiPeerVrfName,
                usdBgpLocalProposedAfiSafiPeerRemoteAddr,
                usdBgpLocalProposedAfiSafiPeerAfi,
                usdBgpLocalProposedAfiSafiPeerSafi }
    ::= { usdBgpLocalProposedAfiSafiPeerTable 1 }

UsdBgpLocalProposedAfiSafiPeerEntry ::= SEQUENCE {
    usdBgpLocalProposedAfiSafiPeerVrfName       UsdVrfName,
    usdBgpLocalProposedAfiSafiPeerRemoteAddr    IpAddress,
    usdBgpLocalProposedAfiSafiPeerAfi           UsdBgpAfi,
    usdBgpLocalProposedAfiSafiPeerSafi          UsdBgpSafi,
    usdBgpLocalProposedAfiSafiPeerRowStatus     RowStatus }

usdBgpLocalProposedAfiSafiPeerVrfName OBJECT-TYPE
    SYNTAX      UsdVrfName
    MAX-ACCESS  not-accessible
    STATUS      current
    DESCRIPTION
        "The name of the VPN Routing Forwarding (VRF) instance in which this
        peer is configured.  The empty string indicates that this peer is not in
        a VRF."
    ::= { usdBgpLocalProposedAfiSafiPeerEntry 1 }

usdBgpLocalProposedAfiSafiPeerRemoteAddr OBJECT-TYPE
    SYNTAX      IpAddress
    MAX-ACCESS  not-accessible
    STATUS      current
    DESCRIPTION
        "The remote IP address of this entry's BGP peer."
    ::= { usdBgpLocalProposedAfiSafiPeerEntry 2 }

usdBgpLocalProposedAfiSafiPeerAfi OBJECT-TYPE
    SYNTAX      UsdBgpAfi
    MAX-ACCESS  not-accessible
    STATUS      current
    DESCRIPTION
        "The AFI we proposed to this peer."
    ::= { usdBgpLocalProposedAfiSafiPeerEntry 3}

usdBgpLocalProposedAfiSafiPeerSafi OBJECT-TYPE
    SYNTAX      UsdBgpSafi
    MAX-ACCESS  not-accessible
    STATUS      current
    DESCRIPTION
        "The SAFI we proposed to this peer."
    ::= { usdBgpLocalProposedAfiSafiPeerEntry 4 }

usdBgpLocalProposedAfiSafiPeerRowStatus OBJECT-TYPE
    SYNTAX      RowStatus
    MAX-ACCESS  read-only
    STATUS      current
    DESCRIPTION
        "Should always be active according to the Row Status convention."
    ::= { usdBgpLocalProposedAfiSafiPeerEntry 5 }


-- +++++++++++++++++++++++++++++++++++++++++++++++++++++++++++++++++++++++++++++
-- BGP Exchanged AFI/SAFI peer attributes
-- +++++++++++++++++++++++++++++++++++++++++++++++++++++++++++++++++++++++++++++
--
--  BGP ExchangedAfiSafiPeer Table
--
usdBgpExchangedAfiSafiPeerTable OBJECT-TYPE
    SYNTAX      SEQUENCE OF UsdBgpExchangedAfiSafiPeerEntry
    MAX-ACCESS  not-accessible
    STATUS      current
    DESCRIPTION
        "The Unisphere BGP PeerExchangedAfiSafi Peer Table describes the
        BGP-specific AFI and SAFIs a peer exchanged."
    ::= { usdBgpObjects 7 }

usdBgpExchangedAfiSafiPeerEntry OBJECT-TYPE
    SYNTAX      UsdBgpExchangedAfiSafiPeerEntry
    MAX-ACCESS  not-accessible
    STATUS      current
    DESCRIPTION
        "The BGP ExchangedAfiSafi Peer Entry describes a BGP-specific AFI/SAFIs
        exchanged by one peer."
    INDEX     { usdBgpExchangedAfiSafiPeerVrfName,
                usdBgpExchangedAfiSafiPeerRemoteAddr,
                usdBgpExchangedAfiSafiPeerAfi,
                usdBgpExchangedAfiSafiPeerSafi }
    ::= { usdBgpExchangedAfiSafiPeerTable 1 }

UsdBgpExchangedAfiSafiPeerEntry ::= SEQUENCE {
    usdBgpExchangedAfiSafiPeerVrfName       UsdVrfName,
    usdBgpExchangedAfiSafiPeerRemoteAddr    IpAddress,
    usdBgpExchangedAfiSafiPeerAfi           UsdBgpAfi,
    usdBgpExchangedAfiSafiPeerSafi          UsdBgpSafi,
    usdBgpExchangedAfiSafiPeerRowStatus     RowStatus }

usdBgpExchangedAfiSafiPeerVrfName OBJECT-TYPE
    SYNTAX      UsdVrfName
    MAX-ACCESS  not-accessible
    STATUS      current
    DESCRIPTION
        "The name of the VPN Routing Forwarding (VRF) instance in which this
        peer is configured.  The empty string indicates that this peer is not in
        a VRF."
    ::= { usdBgpExchangedAfiSafiPeerEntry 1 }

usdBgpExchangedAfiSafiPeerRemoteAddr OBJECT-TYPE
    SYNTAX      IpAddress
    MAX-ACCESS  not-accessible
    STATUS      current
    DESCRIPTION
        "The remote IP address of this entry's BGP peer."
    ::= { usdBgpExchangedAfiSafiPeerEntry 2 }

usdBgpExchangedAfiSafiPeerAfi OBJECT-TYPE
    SYNTAX      UsdBgpAfi
    MAX-ACCESS  not-accessible
    STATUS      current
    DESCRIPTION
        "The AFI which we exchange with this peer."
    ::= { usdBgpExchangedAfiSafiPeerEntry 3}

usdBgpExchangedAfiSafiPeerSafi OBJECT-TYPE
    SYNTAX      UsdBgpSafi
    MAX-ACCESS  not-accessible
    STATUS      current
    DESCRIPTION
        "The SAFI which we exchange with this peer."
    ::= { usdBgpExchangedAfiSafiPeerEntry 4 }

usdBgpExchangedAfiSafiPeerRowStatus OBJECT-TYPE
    SYNTAX      RowStatus
    MAX-ACCESS  read-only
    STATUS      current
    DESCRIPTION
        "Should always be active according to the Row Status convention."
    ::= { usdBgpExchangedAfiSafiPeerEntry 5 }


-- +++++++++++++++++++++++++++++++++++++++++++++++++++++++++++++++++++++++++++++
-- BGP Peer Address Family attributes
-- +++++++++++++++++++++++++++++++++++++++++++++++++++++++++++++++++++++++++++++
--
--  BGP Peer Address Family Table
--
usdBgpPeerAddressFamilyTable OBJECT-TYPE
    SYNTAX      SEQUENCE OF UsdBgpPeerAddressFamilyEntry
    MAX-ACCESS  not-accessible
    STATUS      current
    DESCRIPTION
        "The Unisphere BGP Peer Address Family Table describes the BGP-specific
        attributes of an Address Family for a peer."
    ::= { usdBgpObjects 8 }

usdBgpPeerAddressFamilyEntry OBJECT-TYPE
    SYNTAX      UsdBgpPeerAddressFamilyEntry
    MAX-ACCESS  not-accessible
    STATUS      current
    DESCRIPTION
        "The BGP ExchangedAfiSafi Peer Entry describes a BGP-specific AFI/SAFIs
        exchanged by one peer."
    INDEX     { usdBgpPeerAddressFamilyVrfName,
                usdBgpPeerAddressFamilyAfi,
                usdBgpPeerAddressFamilySafi,
                usdBgpPeerAddressFamilyRemoteAddress }
    ::= { usdBgpPeerAddressFamilyTable 1 }

UsdBgpPeerAddressFamilyEntry ::= SEQUENCE {
    usdBgpPeerAddressFamilyVrfName                 UsdVrfName,
    usdBgpPeerAddressFamilyAfi                     UsdBgpAfi,
    usdBgpPeerAddressFamilySafi                    UsdBgpSafi,
    usdBgpPeerAddressFamilyRemoteAddress           IpAddress,
    usdBgpPeerAddressFamilyPeerGroup               DisplayString,
    usdBgpPeerAddressFamilyDefaultOriginate        TruthValue,
    usdBgpPeerAddressFamilyNextHopSelf             TruthValue,
    usdBgpPeerAddressFamilySendCommunity           TruthValue,
    usdBgpPeerAddressFamilyDistributeListIn        DisplayString,
    usdBgpPeerAddressFamilyDistributeListOut       DisplayString,
    usdBgpPeerAddressFamilyPrefixListIn            DisplayString,
    usdBgpPeerAddressFamilyPrefixListOut           DisplayString,
    usdBgpPeerAddressFamilyPrefixTreeIn            DisplayString,
    usdBgpPeerAddressFamilyPrefixTreeOut           DisplayString,
    usdBgpPeerAddressFamilyFilterListIn            DisplayString,
    usdBgpPeerAddressFamilyFilterListOut           DisplayString,
    usdBgpPeerAddressFamilyFilterListWeight        DisplayString,
    usdBgpPeerAddressFamilyFilterListWeightValue   Unsigned32,
    usdBgpPeerAddressFamilyRouteMapIn              DisplayString,
    usdBgpPeerAddressFamilyRouteMapOut             DisplayString,
    usdBgpPeerAddressFamilyRouteReflectorClient    TruthValue,
    usdBgpPeerAddressFamilyRouteLimitWarn          Unsigned32,
    usdBgpPeerAddressFamilyRouteLimitReset         Unsigned32,
    usdBgpPeerAddressFamilyRouteLimitWarnOnly      TruthValue,
    usdBgpPeerAddressFamilyRemovePrivateAs         TruthValue,
    usdBgpPeerAddressFamilyUnsuppressMap           DisplayString,
    usdBgpPeerAddressFamilyInboundSoftReconfig     TruthValue,
    usdBgpPeerAddressFamilyResetConnectionType     UsdBgpResetConnectionType,
    usdBgpPeerAddressFamilyRowStatus               RowStatus,
    usdBgpPeerAddressFamilyAsOverride              TruthValue,
    usdBgpPeerAddressFamilyAllowAsIn               INTEGER,
    usdBgpPeerAddressFamilySendExtendedCommunity   TruthValue,
    usdBgpPeerAddressFamilyUnconfiguredAttributes  BITS }

usdBgpPeerAddressFamilyVrfName OBJECT-TYPE
    SYNTAX      UsdVrfName
    MAX-ACCESS  not-accessible
    STATUS      current
    DESCRIPTION
        "The name of the VPN Routing Forwarding (VRF) instance in which this
        peer is configured.  The empty string indicates that this peer is not in
        a VRF."
    ::= { usdBgpPeerAddressFamilyEntry 1 }

usdBgpPeerAddressFamilyAfi OBJECT-TYPE
    SYNTAX      UsdBgpAfi
    MAX-ACCESS  not-accessible
    STATUS      current
    DESCRIPTION
        "The AFI of the address-family in which this peer is configured."
    ::= { usdBgpPeerAddressFamilyEntry 2 }

usdBgpPeerAddressFamilySafi OBJECT-TYPE
    SYNTAX      UsdBgpSafi
    MAX-ACCESS  not-accessible
    STATUS      current
    DESCRIPTION
        "The SAFI of the address-family in which this peer is configured."
    ::= { usdBgpPeerAddressFamilyEntry 3 }

usdBgpPeerAddressFamilyRemoteAddress OBJECT-TYPE
    SYNTAX      IpAddress
    MAX-ACCESS  not-accessible
    STATUS      current
    DESCRIPTION
        "The remote IP address of this entry's BGP peer."
    ::= { usdBgpPeerAddressFamilyEntry 4 }

usdBgpPeerAddressFamilyPeerGroup OBJECT-TYPE
    SYNTAX      DisplayString (SIZE(0..32))
    MAX-ACCESS  read-create
    STATUS      current
    DESCRIPTION
        "Peer group membership (null if none)."
    DEFVAL    { "" }
    ::= { usdBgpPeerAddressFamilyEntry 5 }

usdBgpPeerAddressFamilyDefaultOriginate OBJECT-TYPE
    SYNTAX      TruthValue
    MAX-ACCESS  read-create
    STATUS      current
    DESCRIPTION
        "Set this object to true(1) in order to advertise a default route to
        this peer, if present."
    DEFVAL    { false }
    ::= { usdBgpPeerAddressFamilyEntry 6 }

usdBgpPeerAddressFamilyNextHopSelf OBJECT-TYPE
    SYNTAX      TruthValue
    MAX-ACCESS  read-create
    STATUS      current
    DESCRIPTION
        "Set this object to true(1) in order to always advertise this router as
        the next hop."
    DEFVAL    { false }
    ::= { usdBgpPeerAddressFamilyEntry 7 }

usdBgpPeerAddressFamilySendCommunity OBJECT-TYPE
    SYNTAX      TruthValue
    MAX-ACCESS  read-create
    STATUS      current
    DESCRIPTION
        "Set this object to true(1) in order to send COMMUNITIES attributes in
        updates."
    DEFVAL    { false }
    ::= { usdBgpPeerAddressFamilyEntry 8 }

usdBgpPeerAddressFamilyDistributeListIn OBJECT-TYPE
    SYNTAX      DisplayString
    MAX-ACCESS  read-create
    STATUS      current
    DESCRIPTION
        "The inbound distribute IP access list name."
    DEFVAL    { "" }
    ::= { usdBgpPeerAddressFamilyEntry 9 }

usdBgpPeerAddressFamilyDistributeListOut OBJECT-TYPE
    SYNTAX      DisplayString
    MAX-ACCESS  read-create
    STATUS      current
    DESCRIPTION
        "The outbound distribute IP access list name."
    DEFVAL    { "" }
    ::= { usdBgpPeerAddressFamilyEntry 10 }

usdBgpPeerAddressFamilyPrefixListIn OBJECT-TYPE
    SYNTAX      DisplayString
    MAX-ACCESS  read-create
    STATUS      current
    DESCRIPTION
        "The inbound IP prefix list name."
    DEFVAL    { "" }
    ::= { usdBgpPeerAddressFamilyEntry 11 }

usdBgpPeerAddressFamilyPrefixListOut OBJECT-TYPE
    SYNTAX      DisplayString
    MAX-ACCESS  read-create
    STATUS      current
    DESCRIPTION
        "The outbound IP prefix list name."
    DEFVAL    { "" }
    ::= { usdBgpPeerAddressFamilyEntry 12 }

usdBgpPeerAddressFamilyPrefixTreeIn OBJECT-TYPE
    SYNTAX      DisplayString
    MAX-ACCESS  read-create
    STATUS      current
    DESCRIPTION
        "The inbound IP prefix tree name."
    DEFVAL    { "" }
    ::= { usdBgpPeerAddressFamilyEntry 13 }

usdBgpPeerAddressFamilyPrefixTreeOut OBJECT-TYPE
    SYNTAX      DisplayString
    MAX-ACCESS  read-create
    STATUS      current
    DESCRIPTION
        "The outbound IP prefix tree name."
    DEFVAL    { "" }
    ::= { usdBgpPeerAddressFamilyEntry 14 }

usdBgpPeerAddressFamilyFilterListIn OBJECT-TYPE
    SYNTAX      DisplayString
    MAX-ACCESS  read-create
    STATUS      current
    DESCRIPTION
        "The inbound filter AS path list name."
    DEFVAL    { "" }
    ::= { usdBgpPeerAddressFamilyEntry 15 }

usdBgpPeerAddressFamilyFilterListOut OBJECT-TYPE
    SYNTAX      DisplayString
    MAX-ACCESS  read-create
    STATUS      current
    DESCRIPTION
        "The outbound filter AS path list name."
    DEFVAL    { "" }
    ::= { usdBgpPeerAddressFamilyEntry 16 }

usdBgpPeerAddressFamilyFilterListWeight OBJECT-TYPE
    SYNTAX      DisplayString
    MAX-ACCESS  read-create
    STATUS      current
    DESCRIPTION
        "The weight filter AS path list name."
    DEFVAL    { "" }
    ::= { usdBgpPeerAddressFamilyEntry 17 }

usdBgpPeerAddressFamilyFilterListWeightValue OBJECT-TYPE
    SYNTAX      Unsigned32
    MAX-ACCESS  read-create
    STATUS      current
    DESCRIPTION
        "The weight to apply on weight filter list matches."
    DEFVAL    { 0 }
    ::= { usdBgpPeerAddressFamilyEntry 18 }

usdBgpPeerAddressFamilyRouteMapIn OBJECT-TYPE
    SYNTAX      DisplayString (SIZE(0..32))
    MAX-ACCESS  read-create
    STATUS      current
    DESCRIPTION
        "The inbound route-map name.  An empty string means no inbound
        route-map."
    DEFVAL    { "" }
    ::= { usdBgpPeerAddressFamilyEntry 19 }

usdBgpPeerAddressFamilyRouteMapOut OBJECT-TYPE
    SYNTAX      DisplayString (SIZE(0..32))
    MAX-ACCESS  read-create
    STATUS      current
    DESCRIPTION
        "The outbound route-map name.  An empty string means no outbound
        route-map."
    DEFVAL    { "" }
    ::= { usdBgpPeerAddressFamilyEntry 20 }

usdBgpPeerAddressFamilyRouteReflectorClient OBJECT-TYPE
    SYNTAX      TruthValue
    MAX-ACCESS  read-create
    STATUS      current
    DESCRIPTION
        "The peer is a route reflector client."
    DEFVAL    { false }
    ::= { usdBgpPeerAddressFamilyEntry 21 }

usdBgpPeerAddressFamilyRouteLimitWarn OBJECT-TYPE
    SYNTAX      Unsigned32
    MAX-ACCESS  read-create
    STATUS      current
    DESCRIPTION
        "Log a warning if pathCount exceeds this value."
    DEFVAL    { 1000000 }
    ::= { usdBgpPeerAddressFamilyEntry 22 }

usdBgpPeerAddressFamilyRouteLimitReset OBJECT-TYPE
    SYNTAX      Unsigned32
    MAX-ACCESS  read-create
    STATUS      current
    DESCRIPTION
        "Reset connection is pathCount exceeds this value."
    DEFVAL    { 10000000 }
    ::= { usdBgpPeerAddressFamilyEntry 23 }

usdBgpPeerAddressFamilyRouteLimitWarnOnly OBJECT-TYPE
    SYNTAX      TruthValue
    MAX-ACCESS  read-create
    STATUS      current
    DESCRIPTION
        "Warn, but do not reset, if the path limit is exceeded."
    DEFVAL    { false }
    ::= { usdBgpPeerAddressFamilyEntry 24 }

usdBgpPeerAddressFamilyRemovePrivateAs OBJECT-TYPE
    SYNTAX      TruthValue
    MAX-ACCESS  read-create
    STATUS      current
    DESCRIPTION
        "Remove private AS numbers from AS paths."
    DEFVAL    { false }
    ::= { usdBgpPeerAddressFamilyEntry 25 }

usdBgpPeerAddressFamilyUnsuppressMap OBJECT-TYPE
    SYNTAX      DisplayString (SIZE(0..32))
    MAX-ACCESS  read-create
    STATUS      current
    DESCRIPTION
        "The unsuppress route-map name.  Routes which are sent to this peer and
        which match this route-map are not subject to suppression by
        summary-only aggregates.  An empty string means no unsuppress
        route-map."
    DEFVAL    { "" }
    ::= { usdBgpPeerAddressFamilyEntry 26 }

usdBgpPeerAddressFamilyInboundSoftReconfig OBJECT-TYPE
    SYNTAX      TruthValue
    MAX-ACCESS  read-create
    STATUS      current
    DESCRIPTION
        "Inbound soft-reconfiguration is enabled.  If inbound
        soft-reconfiguration is enabled we keep a copy of each received route
        before inbound policy was applied."
    DEFVAL    { false }
    ::= { usdBgpPeerAddressFamilyEntry 27 }

usdBgpPeerAddressFamilyResetConnectionType OBJECT-TYPE
    SYNTAX      UsdBgpResetConnectionType
    MAX-ACCESS  read-create
    STATUS      current
    DESCRIPTION
        "Writing a value to this object causes one individual address family
        within the session to the peer to be cleared; the value determines what
        type of clear is executed (hard clear, soft clear in, soft clear out,
        etc.).  Note that hard clearing an address family within a session will
        bounce the session and thus also affect the other address families in
        the session.  Reading this object has no effect and always returns
        resetTypeNoop."
    DEFVAL    { resetTypeNoop }
    ::= { usdBgpPeerAddressFamilyEntry 28 }

usdBgpPeerAddressFamilyRowStatus OBJECT-TYPE
    SYNTAX      RowStatus
    MAX-ACCESS  read-create
    STATUS      current
    DESCRIPTION
        "Controls creation/deletion of entries in this table according to the
        RowStatus textual convention, constrained to support the following
        values only:
            createAndGo
            destroy

        To create an entry in this table, the following entry objects MUST be
        explicitly configured:
            usdBgpPeerRemoteAs "
    ::= { usdBgpPeerAddressFamilyEntry 29 }

usdBgpPeerAddressFamilyAsOverride OBJECT-TYPE
    SYNTAX      TruthValue
    MAX-ACCESS  read-create
    STATUS      current
    DESCRIPTION
        "Replace the AS number of the peer by our own AS number in the AS-path
        attribute in UPDATEs sent to this peer."
    DEFVAL    { false }
    ::= { usdBgpPeerAddressFamilyEntry 30 }

usdBgpPeerAddressFamilyAllowAsIn OBJECT-TYPE
    SYNTAX      INTEGER (0..10)
    MAX-ACCESS  read-create
    STATUS      current
    DESCRIPTION
        "The maximum number of times our own AS number is allowed to occur in a
        received AS-path before that received route is considered to be a loop
        and therefore rejected."
    DEFVAL    { 0 }
    ::= { usdBgpPeerAddressFamilyEntry 31 }

usdBgpPeerAddressFamilySendExtendedCommunity OBJECT-TYPE
    SYNTAX      TruthValue
    MAX-ACCESS  read-create
    STATUS      current
    DESCRIPTION
        "Set this object to true(1) in order to send EXTENDED-COMMUNITIES
        attributes in updates."
    DEFVAL    { false }
    ::= { usdBgpPeerAddressFamilyEntry 32 }

usdBgpPeerAddressFamilyUnconfiguredAttributes OBJECT-TYPE
    SYNTAX      BITS {
        usdBgpPeerAddressFamilyPeerGroup(0),
        usdBgpPeerAddressFamilyDefaultOriginate(1),
        usdBgpPeerAddressFamilyNextHopSelf(2),
        usdBgpPeerAddressFamilySendCommunity(3),
        usdBgpPeerAddressFamilyDistributeListIn(4),
        usdBgpPeerAddressFamilyDistributeListOut(5),
        usdBgpPeerAddressFamilyPrefixListIn(6),
        usdBgpPeerAddressFamilyPrefixListOut(7),
        usdBgpPeerAddressFamilyPrefixTreeIn(8),
        usdBgpPeerAddressFamilyPrefixTreeOut(9),
        usdBgpPeerAddressFamilyFilterListIn(10),
        usdBgpPeerAddressFamilyFilterListOut(11),
        usdBgpPeerAddressFamilyFilterListWeight(12),
        usdBgpPeerAddressFamilyFilterListWeightValue(13),
        usdBgpPeerAddressFamilyRouteMapIn(14),
        usdBgpPeerAddressFamilyRouteMapOut(15),
        usdBgpPeerAddressFamilyRouteReflectorClient(16),
        usdBgpPeerAddressFamilyRouteLimitWarn(17),
        usdBgpPeerAddressFamilyRouteLimitReset(18),
        usdBgpPeerAddressFamilyRouteLimitWarnOnly(19),
        usdBgpPeerAddressFamilyRemovePrivateAs(20),
        usdBgpPeerAddressFamilyUnsuppressMap(21),
        usdBgpPeerAddressFamilyInboundSoftReconfig(22),
        usdBgpPeerAddressFamilyAsOverride(23),
        usdBgpPeerAddressFamilyAllowAsIn(24),
        usdBgpPeerAddressFamilySendExtendedCommunity(25) }
    MAX-ACCESS  read-create
    STATUS      current
    DESCRIPTION
        "On get each bit indicates whether the corresponding attribute is
        configured or unconfigured:
           0 = The attribute is configured (i.e. the configured value is the
               operational value).
           1 = The attribute is unconfigured (i.e. the operational value is
               inherited from the a higher level which could be the default
               value).

        Getting the attribute value itself always returns the operational value
        of that attribute regardless of whether the attribute is configured or
        unconfigured.

        On write each bit indicates wheter or not the corresponding attribute
        should be set to the unconfigured state:
           0 = No operation (i.e. do not change the state of the attribute).
           1 = Set the attribute to the unconfigured state.

        Setting an attribute to a value has the automatic side-effect of setting
        the bit with the same name to zero."
    DEFVAL    { { } }
    ::= { usdBgpPeerAddressFamilyEntry 44 }


-- +++++++++++++++++++++++++++++++++++++++++++++++++++++++++++++++++++++++++++++
-- BGP Peer Group attributes
-- +++++++++++++++++++++++++++++++++++++++++++++++++++++++++++++++++++++++++++++
--
--  BGP Peer Group Table
--
usdBgpPeerGroupTable OBJECT-TYPE
    SYNTAX      SEQUENCE OF UsdBgpPeerGroupEntry
    MAX-ACCESS  not-accessible
    STATUS      current
    DESCRIPTION
        "The Unisphere BGP Peer Group Table describes the BGP-specific
        characteristics of peer groups."
    ::= { usdBgpObjects 9 }

usdBgpPeerGroupEntry OBJECT-TYPE
    SYNTAX      UsdBgpPeerGroupEntry
    MAX-ACCESS  not-accessible
    STATUS      current
    DESCRIPTION
        "The BGP Peer Group Entry describes BGP-specific characteristics of one
        peer group."
    INDEX     { usdBgpPeerGroupVrfName,
                usdBgpPeerGroupGroupName }
    ::= { usdBgpPeerGroupTable 1 }

UsdBgpPeerGroupEntry ::= SEQUENCE {
    usdBgpPeerGroupVrfName                  UsdVrfName,
    usdBgpPeerGroupGroupName                DisplayString,
    usdBgpPeerGroupAdminStatus              INTEGER,
    usdBgpPeerGroupRemoteAsNumber           INTEGER,
    usdBgpPeerGroupRetryInterval            INTEGER,
    usdBgpPeerGroupConfigHoldTime           INTEGER,
    usdBgpPeerGroupConfigKeepAliveInterval  INTEGER,
    usdBgpPeerGroupAsOriginationInterval    INTEGER,
    usdBgpPeerGroupAdvertisementInterval    INTEGER,
    usdBgpPeerGroupDescription              DisplayString,
    usdBgpPeerGroupWeight                   Unsigned32,
    usdBgpPeerGroupEbgpMultihop             TruthValue,
    usdBgpPeerGroupEbgpMultihopTtl          INTEGER,
    usdBgpPeerGroupUpdateSource             IpAddress,
    usdBgpPeerGroupMd5Password              OCTET STRING,
    usdBgpPeerGroupMaxUpdateSize            Unsigned32,
    usdBgpPeerGroupResetConnectionType      UsdBgpResetConnectionType,
    usdBgpPeerGroupRowStatus                RowStatus,
    usdBgpPeerGroupLocalAsNumber            INTEGER,
    usdBgpPeerGroupUnconfiguredAttributes   BITS }

usdBgpPeerGroupVrfName OBJECT-TYPE
    SYNTAX      UsdVrfName
    MAX-ACCESS  not-accessible
    STATUS      current
    DESCRIPTION
        "The name of the VPN Routing Forwarding (VRF) instance in which this
        peer-group is configured.  The empty string indicates that this
        peer-group is not in a VRF."
    ::= { usdBgpPeerGroupEntry 1 }

usdBgpPeerGroupGroupName OBJECT-TYPE
    SYNTAX      DisplayString (SIZE(0..32))
    MAX-ACCESS  not-accessible
    STATUS      current
    DESCRIPTION
        "The name of the Peer group this instance configures."
    ::= { usdBgpPeerGroupEntry 2 }

usdBgpPeerGroupAdminStatus OBJECT-TYPE
    SYNTAX      INTEGER {
                    stop(1),
                    start(2) }
    MAX-ACCESS  read-create
    STATUS      current
    DESCRIPTION
        "The desired state of the BGP connection.  A transition from 'stop' to
        'start' will cause the BGP Start Event to be generated.  A transition
        from 'start' to 'stop' will cause the BGP Stop Event to be generated.
        This parameter can be used to restart BGP peer connections.  Care should
        be used in providing write access to this object without adequate
        authentication."
    ::= { usdBgpPeerGroupEntry 3 }

usdBgpPeerGroupRemoteAsNumber OBJECT-TYPE
    SYNTAX      INTEGER (0..65535)
    MAX-ACCESS  read-create
    STATUS      current
    DESCRIPTION
        "The peer's autonomous system number.
        This object can only be set at row creation."
    DEFVAL    { 0 }
    ::= { usdBgpPeerGroupEntry 4 }

usdBgpPeerGroupRetryInterval OBJECT-TYPE
    SYNTAX      INTEGER (1..65535)
    UNITS       "seconds"
    MAX-ACCESS  read-create
    STATUS      current
    DESCRIPTION
        "Time interval in seconds for the ConnectRetry timer.  The suggested
        value for this timer is 120 seconds."
    DEFVAL    { 120 }
    ::= { usdBgpPeerGroupEntry 5 }

usdBgpPeerGroupConfigHoldTime OBJECT-TYPE
    SYNTAX      INTEGER (0|3..65535)
    UNITS       "seconds"
    MAX-ACCESS  read-create
    STATUS      current
    DESCRIPTION
        "Time interval in seconds for the Hold Time configured for this BGP
        speaker with this peer.  This value is placed in an OPEN message sent to
        this peer by this BGP speaker, and is compared with the Hold Time field
        in an OPEN message received from the peer when determining the Hold Time
        (bgpPeerHoldTime) with the peer.  This value must not be less than three
        seconds if it is not zero (0) in which case the Hold Time is NOT to be
        established with the peer.  The suggested value for this timer is 90
        seconds."
    DEFVAL    { 90 }
    ::= { usdBgpPeerGroupEntry 6 }

usdBgpPeerGroupConfigKeepAliveInterval OBJECT-TYPE
    SYNTAX      INTEGER (0..21845)
    UNITS       "seconds"
    MAX-ACCESS  read-create
    STATUS      current
    DESCRIPTION
        "Time interval in seconds for the KeepAlive timer configured for this
        BGP speaker with this peer.  The value of this object will only
        determine the KEEPALIVE messages' frequency relative to the value
        specified in bgpPeerHoldTimeConfigured; the actual time interval for the
        KEEPALIVE messages is indicated by bgpPeerKeepAlive.  A reasonable
        maximum value for this timer would be configured to be one third of that
        of bgpPeerHoldTimeConfigured.  If the value of this object is zero (0),
        no periodical KEEPALIVE messages are sent to the peer after the BGP
        connection has been established.  The suggested value for this timer is
        30 seconds."
    DEFVAL    { 30 }
    ::= { usdBgpPeerGroupEntry 7 }

usdBgpPeerGroupAsOriginationInterval OBJECT-TYPE
    SYNTAX      INTEGER (1..65535)
    UNITS       "seconds"
    MAX-ACCESS  read-create
    STATUS      current
    DESCRIPTION
        "Time interval in seconds for the MinASOriginationInterval timer.  The
        suggested value for this timer is 10 seconds."
    DEFVAL    { 10 }
    ::= { usdBgpPeerGroupEntry 8 }

usdBgpPeerGroupAdvertisementInterval OBJECT-TYPE
    SYNTAX      INTEGER (1..65535)
    UNITS       "seconds"
    MAX-ACCESS  read-create
    STATUS      current
    DESCRIPTION
        "Time interval in seconds for the MinRouteAdvertisementInterval timer.
        The suggested value for this timer is 30 seconds."
    DEFVAL    { 30 }
    ::= { usdBgpPeerGroupEntry 9 }

usdBgpPeerGroupDescription OBJECT-TYPE
    SYNTAX      DisplayString (SIZE(0..80))
    MAX-ACCESS  read-create
    STATUS      current
    DESCRIPTION
        "Peer textual description."
    DEFVAL    { "" }
    ::= { usdBgpPeerGroupEntry 10 }

usdBgpPeerGroupWeight OBJECT-TYPE
    SYNTAX      Unsigned32
    MAX-ACCESS  read-create
    STATUS      current
    DESCRIPTION
        "The weight assigned to routes learned from peer."
    DEFVAL    { 0 }
    ::= { usdBgpPeerGroupEntry 11 }

usdBgpPeerGroupEbgpMultihop OBJECT-TYPE
    SYNTAX      TruthValue
    MAX-ACCESS  read-create
    STATUS      current
    DESCRIPTION
        "The EBGP multihop is enabled."
    DEFVAL    { false }
    ::= { usdBgpPeerGroupEntry 12 }

usdBgpPeerGroupEbgpMultihopTtl OBJECT-TYPE
    SYNTAX      INTEGER (1..255)
    MAX-ACCESS  read-create
    STATUS      current
    DESCRIPTION
        "Maximum number of hops to the external peer (only relevant if EBGP
        multihop turned on)."
    DEFVAL    { 255 }
    ::= { usdBgpPeerGroupEntry 13 }

usdBgpPeerGroupUpdateSource OBJECT-TYPE
    SYNTAX      IpAddress
    MAX-ACCESS  read-create
    STATUS      current
    DESCRIPTION
        "The source IP address for peer connections."
    DEFVAL    { 0 }
    ::= { usdBgpPeerGroupEntry 14 }

usdBgpPeerGroupMd5Password OBJECT-TYPE
    SYNTAX      OCTET STRING (SIZE(0..32))
    MAX-ACCESS  read-create
    STATUS      current
    DESCRIPTION
        "The password for MD5 authentication.  Reading this object always
        results in an OCTET STRING of length zero."
    DEFVAL    { "" }
    ::= { usdBgpPeerGroupEntry 15 }

usdBgpPeerGroupMaxUpdateSize OBJECT-TYPE
    SYNTAX      Unsigned32
    UNITS       "bytes"
    MAX-ACCESS  read-create
    STATUS      current
    DESCRIPTION
        "The maximum size in bytes of transmitted UPDATE messages."
    DEFVAL    { 4096 }
    ::= { usdBgpPeerGroupEntry 16 }

usdBgpPeerGroupResetConnectionType OBJECT-TYPE
    SYNTAX      UsdBgpResetConnectionType
    MAX-ACCESS  read-create
    STATUS      current
    DESCRIPTION
        "Writing a value to this object causes the sessions to all peers in the
        peer-group to be cleared; the value determines what type of clear is
        executed (hard clear, soft clear in, soft clear out, etc.).  Reading
        this object has no effect and always returns resetTypeNoop."
    DEFVAL    { resetTypeNoop }
    ::= { usdBgpPeerGroupEntry 17 }

usdBgpPeerGroupRowStatus OBJECT-TYPE
    SYNTAX      RowStatus
    MAX-ACCESS  read-create
    STATUS      current
    DESCRIPTION
        "Controls creation/deletion of entries in this table according to the
        RowStatus textual convention, constrained to support the following
        values only:
            createAndGo
            destroy

        To create an entry in this table, the following entry objects MUST be
        explicitly configured:
            usdBgpPeerGroupRemoteAs "
    ::= { usdBgpPeerGroupEntry 18 }

usdBgpPeerGroupLocalAsNumber OBJECT-TYPE
    SYNTAX      INTEGER (0..65535)
    MAX-ACCESS  read-create
    STATUS      current
    DESCRIPTION
        "The local autonomous system number to be used for members of this
        peer-group.  Value zero (0) means that the global local automous system
        number (as specified in the object usdBgpLocalAsNumber) is used."
    DEFVAL    { 0 }
    ::= { usdBgpPeerGroupEntry 19 }

usdBgpPeerGroupUnconfiguredAttributes OBJECT-TYPE
    SYNTAX      BITS {
        usdBgpPeerGroupAdminStatus(0),
        usdBgpPeerGroupRemoteAsNumber(1),
        usdBgpPeerGroupRetryInterval(2),
        usdBgpPeerGroupConfigHoldTime(3),
        usdBgpPeerGroupConfigKeepAliveInterval(4),
        usdBgpPeerGroupAsOriginationInterval(5),
        usdBgpPeerGroupAdvertisementInterval(6),
        usdBgpPeerGroupDescription(7),
        usdBgpPeerGroupWeight(8),
        usdBgpPeerGroupEbgpMultihop(9),
        usdBgpPeerGroupEbgpMultihopTtl(10),
        usdBgpPeerGroupUpdateSource(11),
        usdBgpPeerGroupMd5Password(12),
        usdBgpPeerGroupMaxUpdateSize(13),
        usdBgpPeerGroupLocalAsNumber(14) }
    MAX-ACCESS  read-create
    STATUS      current
    DESCRIPTION
        "On get each bit indicates whether the corresponding attribute is
        configured or unconfigured:
           0 = The attribute is configured (i.e. the configured value is the
               operational value).
           1 = The attribute is unconfigured (i.e. the operational value is
               inherited from the a higher level which could be the default
               value).

        Getting the attribute value itself always returns the operational value
        of that attribute regardless of whether the attribute is configured or
        unconfigured.

        On write each bit indicates wheter or not the corresponding attribute
        should be set to the unconfigured state:
           0 = No operation (i.e. do not change the state of the attribute).
           1 = Set the attribute to the unconfigured state.

        Setting an attribute to a value has the automatic side-effect of setting
        the bit with the same name to zero."
    DEFVAL    { { } }
    ::= { usdBgpPeerGroupEntry 27 }


-- +++++++++++++++++++++++++++++++++++++++++++++++++++++++++++++++++++++++++++++
-- BGP Peer Group Address Family attributes
-- +++++++++++++++++++++++++++++++++++++++++++++++++++++++++++++++++++++++++++++
--
--  BGP Peer Group Address Family Table
--
usdBgpPeerGroupAddressFamilyTable OBJECT-TYPE
    SYNTAX      SEQUENCE OF UsdBgpPeerGroupAddressFamilyEntry
    MAX-ACCESS  not-accessible
    STATUS      current
    DESCRIPTION
        "The Unisphere BGP Peer Group Address Family Table describes the
        BGP-specific attributes of an Address Family for a peer group."
    ::= { usdBgpObjects 10 }

usdBgpPeerGroupAddressFamilyEntry OBJECT-TYPE
    SYNTAX      UsdBgpPeerGroupAddressFamilyEntry
    MAX-ACCESS  not-accessible
    STATUS      current
    DESCRIPTION
        "The BGP Peer Group Address Family Entry describes."
    INDEX     { usdBgpPeerGroupAddressFamilyVrfName,
                usdBgpPeerGroupAddressFamilyAfi,
                usdBgpPeerGroupAddressFamilySafi,
                usdBgpPeerGroupGroupAddressFamilyGroupName }
    ::= { usdBgpPeerGroupAddressFamilyTable 1 }

UsdBgpPeerGroupAddressFamilyEntry ::= SEQUENCE {
    usdBgpPeerGroupAddressFamilyVrfName             UsdVrfName,
    usdBgpPeerGroupAddressFamilyAfi                 UsdBgpAfi,
    usdBgpPeerGroupAddressFamilySafi                UsdBgpSafi,
    usdBgpPeerGroupGroupAddressFamilyGroupName      DisplayString,
    usdBgpPeerGroupAddressFamilyDefaultOriginate    TruthValue,
    usdBgpPeerGroupAddressFamilyNextHopSelf         TruthValue,
    usdBgpPeerGroupAddressFamilySendCommunity       TruthValue,
    usdBgpPeerGroupAddressFamilyDistributeListIn    DisplayString,
    usdBgpPeerGroupAddressFamilyDistributeListOut   DisplayString,
    usdBgpPeerGroupAddressFamilyPrefixListIn        DisplayString,
    usdBgpPeerGroupAddressFamilyPrefixListOut       DisplayString,
    usdBgpPeerGroupAddressFamilyPrefixTreeIn        DisplayString,
    usdBgpPeerGroupAddressFamilyPrefixTreeOut       DisplayString,
    usdBgpPeerGroupAddressFamilyFilterListIn        DisplayString,
    usdBgpPeerGroupAddressFamilyFilterListOut       DisplayString,
    usdBgpPeerGroupAddressFamilyFilterListWeight    DisplayString,
    usdBgpPeerGroupAddressFamilyFilterListWeightValue   Unsigned32,
    usdBgpPeerGroupAddressFamilyRouteMapIn          DisplayString,
    usdBgpPeerGroupAddressFamilyRouteMapOut         DisplayString,
    usdBgpPeerGroupAddressFamilyRouteReflectorClient    TruthValue,
    usdBgpPeerGroupAddressFamilyRouteLimitWarn      Unsigned32,
    usdBgpPeerGroupAddressFamilyRouteLimitReset     Unsigned32,
    usdBgpPeerGroupAddressFamilyRouteLimitWarnOnly  TruthValue,
    usdBgpPeerGroupAddressFamilyRemovePrivateAs     TruthValue,
    usdBgpPeerGroupAddressFamilyUnsuppressMap       DisplayString,
    usdBgpPeerGroupAddressFamilyInboundSoftReconfig TruthValue,
    usdBgpPeerGroupAddressFamilyResetConnectionType UsdBgpResetConnectionType,
    usdBgpPeerGroupAddressFamilyRowStatus           RowStatus,
    usdBgpPeerGroupAddressFamilyAsOverride          TruthValue,
    usdBgpPeerGroupAddressFamilyAllowAsIn           INTEGER,
    usdBgpPeerGroupAddressFamilySendExtendedCommunity   TruthValue,
    usdBgpPeerGroupAddressFamilyUnconfiguredAttributes  BITS }

usdBgpPeerGroupAddressFamilyVrfName OBJECT-TYPE
    SYNTAX      UsdVrfName
    MAX-ACCESS  not-accessible
    STATUS      current
    DESCRIPTION
        "The name of the VPN Routing Forwarding (VRF) instance in which this
        peer-group is configured.  The empty string indicates that this
        peer-group is not in a VRF."
    ::= { usdBgpPeerGroupAddressFamilyEntry 1 }

usdBgpPeerGroupAddressFamilyAfi OBJECT-TYPE
    SYNTAX      UsdBgpAfi
    MAX-ACCESS  not-accessible
    STATUS      current
    DESCRIPTION
        "The AFI of the address-family in which this peer-group is configured."
    ::= { usdBgpPeerGroupAddressFamilyEntry 2 }

usdBgpPeerGroupAddressFamilySafi OBJECT-TYPE
    SYNTAX      UsdBgpSafi
    MAX-ACCESS  not-accessible
    STATUS      current
    DESCRIPTION
        "The SAFI of the address-family in which this peer-group is configured."
    ::= { usdBgpPeerGroupAddressFamilyEntry 3 }

usdBgpPeerGroupGroupAddressFamilyGroupName OBJECT-TYPE
    SYNTAX      DisplayString (SIZE(0..32))
    MAX-ACCESS  not-accessible
    STATUS      current
    DESCRIPTION
        "The name of the Peer group this instance configures."
    ::= { usdBgpPeerGroupAddressFamilyEntry 4 }

usdBgpPeerGroupAddressFamilyDefaultOriginate OBJECT-TYPE
    SYNTAX      TruthValue
    MAX-ACCESS  read-create
    STATUS      current
    DESCRIPTION
        "Set this object to true(1) in order to advertise a default route to
        this peer, if present."
    DEFVAL    { false }
    ::= { usdBgpPeerGroupAddressFamilyEntry 5 }

usdBgpPeerGroupAddressFamilyNextHopSelf OBJECT-TYPE
    SYNTAX      TruthValue
    MAX-ACCESS  read-create
    STATUS      current
    DESCRIPTION
        "Set this object to true(1) in order to always advertise this router as
        the next hop."
    DEFVAL    { false }
    ::= { usdBgpPeerGroupAddressFamilyEntry 6 }

usdBgpPeerGroupAddressFamilySendCommunity OBJECT-TYPE
    SYNTAX      TruthValue
    MAX-ACCESS  read-create
    STATUS      current
    DESCRIPTION
        "Set this object to true(1) in order to send COMMUNITIES attributes in
        updates."
    DEFVAL    { false }
    ::= { usdBgpPeerGroupAddressFamilyEntry 7 }

usdBgpPeerGroupAddressFamilyDistributeListIn OBJECT-TYPE
    SYNTAX      DisplayString (SIZE(0..32))
    MAX-ACCESS  read-create
    STATUS      current
    DESCRIPTION
        "The inbound distribute IP access list name."
    DEFVAL    { "" }
    ::= { usdBgpPeerGroupAddressFamilyEntry 8 }

usdBgpPeerGroupAddressFamilyDistributeListOut OBJECT-TYPE
    SYNTAX      DisplayString (SIZE(0..32))
    MAX-ACCESS  read-create
    STATUS      current
    DESCRIPTION
        "The outbound distribute IP access list name."
    DEFVAL    { "" }
    ::= { usdBgpPeerGroupAddressFamilyEntry 9 }

usdBgpPeerGroupAddressFamilyPrefixListIn OBJECT-TYPE
    SYNTAX      DisplayString (SIZE(0..32))
    MAX-ACCESS  read-create
    STATUS      current
    DESCRIPTION
        "The inbound IP prefix list name."
    DEFVAL    { "" }
    ::= { usdBgpPeerGroupAddressFamilyEntry 10 }

usdBgpPeerGroupAddressFamilyPrefixListOut OBJECT-TYPE
    SYNTAX      DisplayString (SIZE(0..32))
    MAX-ACCESS  read-create
    STATUS      current
    DESCRIPTION
        "The outbound IP prefix list name."
    DEFVAL    { "" }
    ::= { usdBgpPeerGroupAddressFamilyEntry 11 }

usdBgpPeerGroupAddressFamilyPrefixTreeIn OBJECT-TYPE
    SYNTAX      DisplayString (SIZE(0..32))
    MAX-ACCESS  read-create
    STATUS      current
    DESCRIPTION
        "The inbound IP prefix tree name."
    DEFVAL    { "" }
    ::= { usdBgpPeerGroupAddressFamilyEntry 12 }

usdBgpPeerGroupAddressFamilyPrefixTreeOut OBJECT-TYPE
    SYNTAX      DisplayString (SIZE(0..32))
    MAX-ACCESS  read-create
    STATUS      current
    DESCRIPTION
        "The outbound IP prefix tree name."
    DEFVAL    { "" }
    ::= { usdBgpPeerGroupAddressFamilyEntry 13 }

usdBgpPeerGroupAddressFamilyFilterListIn OBJECT-TYPE
    SYNTAX      DisplayString (SIZE(0..32))
    MAX-ACCESS  read-create
    STATUS      current
    DESCRIPTION
        "The inbound filter AS path list name."
    DEFVAL    { "" }
    ::= { usdBgpPeerGroupAddressFamilyEntry 14 }

usdBgpPeerGroupAddressFamilyFilterListOut OBJECT-TYPE
    SYNTAX      DisplayString (SIZE(0..32))
    MAX-ACCESS  read-create
    STATUS      current
    DESCRIPTION
        "The outbound filter AS path list name."
    DEFVAL    { "" }
    ::= { usdBgpPeerGroupAddressFamilyEntry 15 }

usdBgpPeerGroupAddressFamilyFilterListWeight OBJECT-TYPE
    SYNTAX      DisplayString (SIZE(0..32))
    MAX-ACCESS  read-create
    STATUS      current
    DESCRIPTION
        "The weight filter AS path list name."
    DEFVAL    { "" }
    ::= { usdBgpPeerGroupAddressFamilyEntry 16 }

usdBgpPeerGroupAddressFamilyFilterListWeightValue OBJECT-TYPE
    SYNTAX      Unsigned32
    MAX-ACCESS  read-create
    STATUS      current
    DESCRIPTION
        "The weight to apply on weight filter list matches."
    DEFVAL    { 0 }
    ::= { usdBgpPeerGroupAddressFamilyEntry 17 }

usdBgpPeerGroupAddressFamilyRouteMapIn OBJECT-TYPE
    SYNTAX      DisplayString (SIZE(0..32))
    MAX-ACCESS  read-create
    STATUS      current
    DESCRIPTION
        "The inbound route-map name.
         An empty string means no inbound route-map."
    DEFVAL    { "" }
    ::= { usdBgpPeerGroupAddressFamilyEntry 18 }

usdBgpPeerGroupAddressFamilyRouteMapOut OBJECT-TYPE
    SYNTAX      DisplayString (SIZE(0..32))
    MAX-ACCESS  read-create
    STATUS      current
    DESCRIPTION
        "The outbound route-map name.
         An empty string means no outbound route-map."
    DEFVAL    { "" }
    ::= { usdBgpPeerGroupAddressFamilyEntry 19 }

usdBgpPeerGroupAddressFamilyRouteReflectorClient OBJECT-TYPE
    SYNTAX      TruthValue
    MAX-ACCESS  read-create
    STATUS      current
    DESCRIPTION
        "The peer is a route reflector client."
    DEFVAL    { false }
    ::= { usdBgpPeerGroupAddressFamilyEntry 20 }

usdBgpPeerGroupAddressFamilyRouteLimitWarn OBJECT-TYPE
    SYNTAX      Unsigned32
    MAX-ACCESS  read-create
    STATUS      current
    DESCRIPTION
        "Log a warning if pathCount exceeds this value."
    DEFVAL    { 0 }
    ::= { usdBgpPeerGroupAddressFamilyEntry 21 }

usdBgpPeerGroupAddressFamilyRouteLimitReset OBJECT-TYPE
    SYNTAX      Unsigned32
    MAX-ACCESS  read-create
    STATUS      current
    DESCRIPTION
        "Reset connection is pathCount exceeds this value."
    DEFVAL    { 0 }
    ::= { usdBgpPeerGroupAddressFamilyEntry 22 }

usdBgpPeerGroupAddressFamilyRouteLimitWarnOnly OBJECT-TYPE
    SYNTAX      TruthValue
    MAX-ACCESS  read-create
    STATUS      current
    DESCRIPTION
        "Warn, but do not reset, if the path limit is exceeded."
    DEFVAL    { false }
    ::= { usdBgpPeerGroupAddressFamilyEntry 23 }

usdBgpPeerGroupAddressFamilyRemovePrivateAs OBJECT-TYPE
    SYNTAX      TruthValue
    MAX-ACCESS  read-create
    STATUS      current
    DESCRIPTION
        "Remove private AS numbers from AS paths."
    DEFVAL    { false }
    ::= { usdBgpPeerGroupAddressFamilyEntry 24 }

usdBgpPeerGroupAddressFamilyUnsuppressMap OBJECT-TYPE
    SYNTAX      DisplayString (SIZE(0..32))
    MAX-ACCESS  read-create
    STATUS      current
    DESCRIPTION
        "The unsuppress route-map name.  Routes which are sent to this peer and
        which match this route-map are not subject to suppression by
        summary-only aggregates.  An empty string means no unsuppress
        route-map."
    DEFVAL    { "" }
    ::= { usdBgpPeerGroupAddressFamilyEntry 25 }

usdBgpPeerGroupAddressFamilyInboundSoftReconfig OBJECT-TYPE
    SYNTAX      TruthValue
    MAX-ACCESS  read-create
    STATUS      current
    DESCRIPTION
        "Inbound soft-reconfiguration is enabled.  If inbound
        soft-reconfiguration is enabled we keep a copy of each received route
        before inbound policy was applied."
    DEFVAL    { false }
    ::= { usdBgpPeerGroupAddressFamilyEntry 26 }

usdBgpPeerGroupAddressFamilyResetConnectionType OBJECT-TYPE
    SYNTAX      UsdBgpResetConnectionType
    MAX-ACCESS  read-create
    STATUS      current
    DESCRIPTION
        "Writing a value to this object causes one individual address family
        within the sessions to all peers in the peer-group to be cleared; the
        value determines what type of clear is executed (hard clear, soft clear
        in, soft clear out, etc.).  Note that hard clearing an address family
        within a session will bounce the session and thus also affect the other
        address families in the session.  Reading this object has no effect and
        always returns resetTypeNoop."
    DEFVAL    { resetTypeNoop }
    ::= { usdBgpPeerGroupAddressFamilyEntry 27 }

usdBgpPeerGroupAddressFamilyRowStatus OBJECT-TYPE
    SYNTAX      RowStatus
    MAX-ACCESS  read-create
    STATUS      current
    DESCRIPTION
        "Controls creation/deletion of entries in this table according to the
        RowStatus textual convention, constrained to support the following
        values only:
            createAndGo
            destroy

        To create an entry in this table, the following entry objects MUST be
        explicitly configured:
            usdBgpPeerGroupRemoteAs "
    ::= { usdBgpPeerGroupAddressFamilyEntry 28 }

usdBgpPeerGroupAddressFamilyAsOverride OBJECT-TYPE
    SYNTAX      TruthValue
    MAX-ACCESS  read-create
    STATUS      current
    DESCRIPTION
        "Replace the AS number of the peer by our own AS number in the AS-path
        attribute in UPDATEs sent to this peer-group."
    DEFVAL    { false }
    ::= { usdBgpPeerGroupAddressFamilyEntry 29 }

usdBgpPeerGroupAddressFamilyAllowAsIn OBJECT-TYPE
    SYNTAX      INTEGER (0..10)
    MAX-ACCESS  read-create
    STATUS      current
    DESCRIPTION
        "The maximum number of times our own AS number is allowed to occur in a
        received AS-path before that received route is considered to be a loop
        and therefore rejected."
    DEFVAL    { 0 }
    ::= { usdBgpPeerGroupAddressFamilyEntry 30 }

usdBgpPeerGroupAddressFamilySendExtendedCommunity OBJECT-TYPE
    SYNTAX      TruthValue
    MAX-ACCESS  read-create
    STATUS      current
    DESCRIPTION
        "Set this object to true(1) in order to send EXTENDED-COMMUNITIES
        attributes in updates."
    DEFVAL    { false }
    ::= { usdBgpPeerGroupAddressFamilyEntry 31 }

usdBgpPeerGroupAddressFamilyUnconfiguredAttributes OBJECT-TYPE
    SYNTAX      BITS {
        usdBgpPeerGroupAddressFamilyDefaultOriginate(0),
        usdBgpPeerGroupAddressFamilyNextHopSelf(1),
        usdBgpPeerGroupAddressFamilySendCommunity(2),
        usdBgpPeerGroupAddressFamilyDistributeListIn(3),
        usdBgpPeerGroupAddressFamilyDistributeListOut(4),
        usdBgpPeerGroupAddressFamilyPrefixListIn(5),
        usdBgpPeerGroupAddressFamilyPrefixListOut(6),
        usdBgpPeerGroupAddressFamilyPrefixTreeIn(7),
        usdBgpPeerGroupAddressFamilyPrefixTreeOut(8),
        usdBgpPeerGroupAddressFamilyFilterListIn(9),
        usdBgpPeerGroupAddressFamilyFilterListOut(10),
        usdBgpPeerGroupAddressFamilyFilterListWeight(11),
        usdBgpPeerGroupAddressFamilyFilterListWeightValue(12),
        usdBgpPeerGroupAddressFamilyRouteMapIn(13),
        usdBgpPeerGroupAddressFamilyRouteMapOut(14),
        usdBgpPeerGroupAddressFamilyRouteReflectorClient(15),
        usdBgpPeerGroupAddressFamilyRouteLimitWarn(16),
        usdBgpPeerGroupAddressFamilyRouteLimitReset(17),
        usdBgpPeerGroupAddressFamilyRouteLimitWarnOnly(18),
        usdBgpPeerGroupAddressFamilyRemovePrivateAs(19),
        usdBgpPeerGroupAddressFamilyUnsuppressMap(20),
        usdBgpPeerGroupAddressFamilyInboundSoftReconfig(21),
        usdBgpPeerGroupAddressFamilyAsOverride(22),
        usdBgpPeerGroupAddressFamilyAllowAsIn(23),
        usdBgpPeerGroupAddressFamilySendExtendedCommunity(24) }
    MAX-ACCESS  read-create
    STATUS      current
    DESCRIPTION
        "On get each bit indicates whether the corresponding attribute is
        configured or unconfigured:
           0 = The attribute is configured (i.e. the configured value is the
               operational value).
           1 = The attribute is unconfigured (i.e. the operational value is
               inherited from the a higher level which could be the default
               value).

        Getting the attribute value itself always returns the operational value
        of that attribute regardless of whether the attribute is configured or
        unconfigured.

        On write each bit indicates wheter or not the corresponding attribute
        should be set to the unconfigured state:
           0 = No operation (i.e. do not change the state of the attribute).
           1 = Set the attribute to the unconfigured state.

        Setting an attribute to a value has the automatic side-effect of setting
        the bit with the same name to zero."
    DEFVAL    { { } }
    ::= { usdBgpPeerGroupAddressFamilyEntry 35 }


-- +++++++++++++++++++++++++++++++++++++++++++++++++++++++++++++++++++++++++++++
-- BGP Network attributes
-- +++++++++++++++++++++++++++++++++++++++++++++++++++++++++++++++++++++++++++++
--
--  BGP Network Table
--
usdBgpNetworkTable OBJECT-TYPE
    SYNTAX      SEQUENCE OF UsdBgpNetworkEntry
    MAX-ACCESS  not-accessible
    STATUS      current
    DESCRIPTION
        "The BGP Network Table controls what networks are originated by this BGP
        router."
    ::= { usdBgpObjects 16 }

usdBgpNetworkEntry OBJECT-TYPE
    SYNTAX      UsdBgpNetworkEntry
    MAX-ACCESS  not-accessible
    STATUS      current
    DESCRIPTION
        "An instance in the list of networks originated by this BGP router."
    INDEX     { usdBgpNetworkVrfName,
                usdBgpNetworkAfi,
                usdBgpNetworkSafi,
                usdBgpNetworkIpAddrPrefix,
                usdBgpNetworkIpAddrPrefixLen }
    ::= { usdBgpNetworkTable 1 }

UsdBgpNetworkEntry ::= SEQUENCE {
    usdBgpNetworkVrfName                   UsdVrfName,
    usdBgpNetworkAfi                       UsdBgpAfi,
    usdBgpNetworkSafi                      UsdBgpSafi,
    usdBgpNetworkIpAddrPrefix              IpAddress,
    usdBgpNetworkIpAddrPrefixLen           INTEGER,
    usdBgpNetworkBackdoor                  TruthValue,
    usdBgpNetworkRowStatus                 RowStatus,
    usdBgpNetworkWeightSpecified           TruthValue,
    usdBgpNetworkWeight                    INTEGER,
    usdBgpNetworkRouteMap                  DisplayString,
    usdBgpNetworkUnconfiguredAttributes    BITS }

usdBgpNetworkVrfName OBJECT-TYPE
    SYNTAX      UsdVrfName
    MAX-ACCESS  not-accessible
    STATUS      current
    DESCRIPTION
        "The name of the VPN Routing Forwarding (VRF) instance in which this
        network is configured.  The empty string indicates that this network is
        not in a VRF."
    ::= { usdBgpNetworkEntry 1 }

usdBgpNetworkAfi OBJECT-TYPE
    SYNTAX      UsdBgpAfi
    MAX-ACCESS  not-accessible
    STATUS      current
    DESCRIPTION
        "The AFI of the address-family in which this network is configured."
    ::= { usdBgpNetworkEntry 2 }

usdBgpNetworkSafi OBJECT-TYPE
    SYNTAX      UsdBgpSafi
    MAX-ACCESS  not-accessible
    STATUS      current
    DESCRIPTION
        "The SAFI of the address-family in which this network is configured."
    ::= { usdBgpNetworkEntry 3 }

usdBgpNetworkIpAddrPrefix OBJECT-TYPE
    SYNTAX      IpAddress
    MAX-ACCESS  not-accessible
    STATUS      current
    DESCRIPTION
        "An IP address prefix in the Network Layer Reachability Information
        field.  This object is an IP address containing the prefix with length
        specified by bgpRouteIpAddrPrefixLen.  Any bits beyond the length
        specified by bgpRouteIpAddrPrefixLen are zeroed."
    ::= { usdBgpNetworkEntry 4 }

usdBgpNetworkIpAddrPrefixLen OBJECT-TYPE
    SYNTAX      INTEGER (0..32)
    MAX-ACCESS  not-accessible
    STATUS      current
    DESCRIPTION
        "Length in bits of the IP address prefix in the Network Layer
        Reachability Information field."
    ::= { usdBgpNetworkEntry 5 }

usdBgpNetworkBackdoor OBJECT-TYPE
    SYNTAX      TruthValue
    MAX-ACCESS  read-create
    STATUS      current
    DESCRIPTION
        "Set this object to true(1) in order to enable BGP backdoor in this
        network.  This object can only be set at row creation."
    DEFVAL    { false }
    ::= { usdBgpNetworkEntry 6 }

usdBgpNetworkRowStatus OBJECT-TYPE
    SYNTAX      RowStatus
    MAX-ACCESS  read-create
    STATUS      current
    DESCRIPTION
        "Controls creation/deletion of entries in this table according to the
        RowStatus textual convention, constrained to support the following
        values only:
            createAndGo
            destroy "
    ::= { usdBgpNetworkEntry 7 }

usdBgpNetworkWeightSpecified OBJECT-TYPE
    SYNTAX      TruthValue
    MAX-ACCESS  read-create
    STATUS      current
    DESCRIPTION
        "If this object is set to true(1) then the BGP weight of this network is
        set to the value specified in usdBgpNetworkWeightValue.  This object can
        only be set at row creation."
    DEFVAL    { false }
    ::= { usdBgpNetworkEntry 8 }

usdBgpNetworkWeight OBJECT-TYPE
    SYNTAX      INTEGER (0..65535)
    MAX-ACCESS  read-create
    STATUS      current
    DESCRIPTION
        "If usdBgpNetworkWeight specified is set to true(1) then this object
        specifies the weight of the network.  Otherwise the weight of the
        network is determined by the IGP metric of the prefix.  This object can
        only be set at row creation."
    DEFVAL    { 32768 }
    ::= { usdBgpNetworkEntry 9 }

usdBgpNetworkRouteMap OBJECT-TYPE
    SYNTAX      DisplayString (SIZE(0..32))
    MAX-ACCESS  read-create
    STATUS      current
    DESCRIPTION
        "The name of the route-map used to set the path attributes of this
        network.  A zero length route-map name means don't use a route-map for
        this.  This object can only be set at row creation."
    DEFVAL    { "" }
    ::= { usdBgpNetworkEntry 10 }

usdBgpNetworkUnconfiguredAttributes OBJECT-TYPE
    SYNTAX      BITS {
        usdBgpNetworkBackdoor(0),
        usdBgpNetworkWeight(1),
        usdBgpNetworkRouteMap(2) }
    MAX-ACCESS  read-create
    STATUS      current
    DESCRIPTION
        "On get each bit indicates whether the corresponding attribute is
        configured or unconfigured:
           0 = The attribute is configured (i.e. the configured value is the
               operational value).
           1 = The attribute is unconfigured (i.e. the operational value is
               inherited from the a higher level which could be the default
               value).

        Getting the attribute value itself always returns the operational value
        of that attribute regardless of whether the attribute is configured or
        unconfigured.

        On write each bit indicates wheter or not the corresponding attribute
        should be set to the unconfigured state:
           0 = No operation (i.e. do not change the state of the attribute).
           1 = Set the attribute to the unconfigured state.

        Setting an attribute to a value has the automatic side-effect of setting
        the bit with the same name to zero."
    DEFVAL    { { } }
    ::= { usdBgpNetworkEntry 11 }


-- +++++++++++++++++++++++++++++++++++++++++++++++++++++++++++++++++++++++++++++
-- BGP Aggregate attributes
-- +++++++++++++++++++++++++++++++++++++++++++++++++++++++++++++++++++++++++++++
--
--  BGP Aggregate Table
--
usdBgpAggregateTable OBJECT-TYPE
    SYNTAX      SEQUENCE OF UsdBgpAggregateEntry
    MAX-ACCESS  not-accessible
    STATUS      current
    DESCRIPTION
        "The BGP Aggregate Table controls the consolidation of route
        information."
    ::= { usdBgpObjects 17 }

usdBgpAggregateEntry OBJECT-TYPE
    SYNTAX      UsdBgpAggregateEntry
    MAX-ACCESS  not-accessible
    STATUS      current
    DESCRIPTION
        "An instance in the list of route aggregation."
    INDEX     { usdBgpAggregateVrfName,
                usdBgpAggregateAfi,
                usdBgpAggregateSafi,
                usdBgpAggregateIpAddrPrefix,
                usdBgpAggregateIpAddrPrefixLen }
    ::= { usdBgpAggregateTable 1 }

UsdBgpAggregateEntry ::= SEQUENCE {
    usdBgpAggregateVrfName                 UsdVrfName,
    usdBgpAggregateAfi                     UsdBgpAfi,
    usdBgpAggregateSafi                    UsdBgpSafi,
    usdBgpAggregateIpAddrPrefix            IpAddress,
    usdBgpAggregateIpAddrPrefixLen         INTEGER,
    usdBgpAggregateAsSet                   TruthValue,
    usdBgpAggregateSummaryOnly             TruthValue,
    usdBgpAggregateAttributeMap            DisplayString,
    usdBgpAggregateAdvertiseMap            DisplayString,
    usdBgpAggregateRowStatus               RowStatus,
    usdBgpAggregateSuppressMap             DisplayString,
    usdBgpAggregateUnconfiguredAttributes  BITS }

usdBgpAggregateVrfName OBJECT-TYPE
    SYNTAX      UsdVrfName
    MAX-ACCESS  not-accessible
    STATUS      current
    DESCRIPTION
        "The name of the VPN Routing Forwarding (VRF) instance in which this
        aggregate is configured.  The empty string indicates that this aggregate
        is not in a VRF."
    ::= { usdBgpAggregateEntry 1 }

usdBgpAggregateAfi OBJECT-TYPE
    SYNTAX      UsdBgpAfi
    MAX-ACCESS  not-accessible
    STATUS      current
    DESCRIPTION
        "The AFI of the address-family in which this aggregate is configured."
    ::= { usdBgpAggregateEntry 2 }

usdBgpAggregateSafi OBJECT-TYPE
    SYNTAX      UsdBgpSafi
    MAX-ACCESS  not-accessible
    STATUS      current
    DESCRIPTION
        "The SAFI of the address-family in which this aggregate is configured."
    ::= { usdBgpAggregateEntry 3 }

usdBgpAggregateIpAddrPrefix OBJECT-TYPE
    SYNTAX      IpAddress
    MAX-ACCESS  not-accessible
    STATUS      current
    DESCRIPTION
        "An IP address prefix in the Network Layer Reachability Information
        field.  This object is an IP address containing the prefix with length
        specified by bgpRouteIpAddrPrefixLen.  Any bits beyond the length
        specified by bgpRouteIpAddrPrefixLen are zeroed."
    ::= { usdBgpAggregateEntry 4 }

usdBgpAggregateIpAddrPrefixLen OBJECT-TYPE
    SYNTAX      INTEGER (0..32)
    MAX-ACCESS  not-accessible
    STATUS      current
    DESCRIPTION
        "Length in bits of the IP address prefix in the Network Layer
        Reachability Information field."
    ::= { usdBgpAggregateEntry 5 }

usdBgpAggregateAsSet OBJECT-TYPE
    SYNTAX      TruthValue
    MAX-ACCESS  read-create
    STATUS      current
    DESCRIPTION
        "Set this object to true(1) in order to generate AS_set path information
        by creating an aggregate entry that consists of all elements contained
        in all paths that are being summarized.  This object can only be set at
        row creation."
    DEFVAL    { false }
    ::= { usdBgpAggregateEntry 6 }

usdBgpAggregateSummaryOnly OBJECT-TYPE
    SYNTAX      TruthValue
    MAX-ACCESS  read-create
    STATUS      current
    DESCRIPTION
        "Set this object to true(1) in order to filter specific routes from
        updates.  By doing that, advertisements of more specific routes will be
        suppressed to all neighbors.  This object can only be set at row
        creation."
    DEFVAL    { false }
    ::= { usdBgpAggregateEntry 7 }

usdBgpAggregateAttributeMap OBJECT-TYPE
    SYNTAX      DisplayString (SIZE(0..32))
    MAX-ACCESS  read-create
    STATUS      current
    DESCRIPTION
        "The name of the route-map used to set the attributes of the aggregate
        An empty string means no route-map for this purpose."
    DEFVAL    { "" }
    ::= { usdBgpAggregateEntry 8 }

usdBgpAggregateAdvertiseMap OBJECT-TYPE
    SYNTAX      DisplayString (SIZE(0..32))
    MAX-ACCESS  read-create
    STATUS      current
    DESCRIPTION
        "The name of the route-map used to select routes covered by the
        aggregate (for as-set aggregates the path attributes of the aggregate
        route are created by summarizing the path attributes of the covered
        routes).  An empty string means no route-map for this purpose."
    DEFVAL    { "" }
    ::= { usdBgpAggregateEntry 9 }

usdBgpAggregateRowStatus OBJECT-TYPE
    SYNTAX      RowStatus
    MAX-ACCESS  read-create
    STATUS      current
    DESCRIPTION
        "Controls creation/deletion of entries in this table according to the
        RowStatus textual convention, constrained to support the following
        values only:
            createAndGo
            destroy "
    ::= { usdBgpAggregateEntry 10 }

usdBgpAggregateSuppressMap OBJECT-TYPE
    SYNTAX      DisplayString (SIZE(0..32))
    MAX-ACCESS  read-create
    STATUS      current
    DESCRIPTION
        "The suppress route-map name.  If a suppress route-map has been
        specified, all routes which are covered by the aggregate and which match
        the suppress route-map are suppressed.  An empty string means no inbound
        route-map."
    DEFVAL    { "" }
    ::= { usdBgpAggregateEntry 11 }

usdBgpAggregateUnconfiguredAttributes OBJECT-TYPE
    SYNTAX      BITS {
        usdBgpAggregateAsSet(0),
        usdBgpAggregateSummaryOnly(1),
        usdBgpAggregateAttributeMap(2),
        usdBgpAggregateAdvertiseMap(3),
        usdBgpAggregateSuppressMap(4) }
    MAX-ACCESS  read-create
    STATUS      current
    DESCRIPTION
        "On get each bit indicates whether the corresponding attribute is
        configured or unconfigured:
           0 = The attribute is configured (i.e. the configured value is the
               operational value).
           1 = The attribute is unconfigured (i.e. the operational value is
               inherited from the a higher level which could be the default
               value).

        Getting the attribute value itself always returns the operational value
        of that attribute regardless of whether the attribute is configured or
        unconfigured.

        On write each bit indicates wheter or not the corresponding attribute
        should be set to the unconfigured state:
           0 = No operation (i.e. do not change the state of the attribute).
           1 = Set the attribute to the unconfigured state.

        Setting an attribute to a value has the automatic side-effect of setting
        the bit with the same name to zero."
    DEFVAL    { { } }
    ::= { usdBgpAggregateEntry 12 }


-- +++++++++++++++++++++++++++++++++++++++++++++++++++++++++++++++++++++++++++++
-- BGP VRF attributes
-- +++++++++++++++++++++++++++++++++++++++++++++++++++++++++++++++++++++++++++++
--
--  BGP VRF Table
--
usdBgpVrfTable OBJECT-TYPE
    SYNTAX      SEQUENCE OF UsdBgpVrfEntry
    MAX-ACCESS  not-accessible
    STATUS      current
    DESCRIPTION
        "The Unisphere BGP VRF Table describes the BGP-specific characteristics
        of a VPN routing forwarding instance."
    ::= { usdBgpObjects 18 }

usdBgpVrfEntry OBJECT-TYPE
    SYNTAX      UsdBgpVrfEntry
    MAX-ACCESS  not-accessible
    STATUS      current
    DESCRIPTION
        "The BGP VRF Entry describes BGP-specific characteristics of one VRF."
    INDEX     { usdBgpVrfName }
    ::= { usdBgpVrfTable 1 }

UsdBgpVrfEntry ::= SEQUENCE {
    usdBgpVrfName                              UsdVrfName,
    usdBgpVrfSynchronization                   TruthValue,
    usdBgpVrfAutoSummary                       TruthValue,
    usdBgpVrfExternalDistance                  INTEGER,
    usdBgpVrfInternalDistance                  INTEGER,
    usdBgpVrfLocalDistance                     INTEGER,
    usdBgpVrfResetConnectionType               UsdBgpResetConnectionType,
    usdBgpVrfRowStatus                         RowStatus,
    usdBgpVrfOperationalState                  INTEGER,
    usdBgpVrfAddUnicastRoutesToMulticastView   TruthValue,
    usdBgpVrfUnconfiguredAttributes            BITS }

usdBgpVrfName OBJECT-TYPE
    SYNTAX      UsdVrfName
    MAX-ACCESS  not-accessible
    STATUS      current
    DESCRIPTION
        "The name of the VPN Routing Forwarding (VRF) instance."
    ::= { usdBgpVrfEntry 1 }

usdBgpVrfSynchronization OBJECT-TYPE
    SYNTAX      TruthValue
    MAX-ACCESS  read-create
    STATUS      current
    DESCRIPTION
        "Set this object to true(1) in order to have IGP route synchronization
        enabled."
    DEFVAL    { false }
    ::= { usdBgpVrfEntry 2}

usdBgpVrfAutoSummary OBJECT-TYPE
    SYNTAX      TruthValue
    MAX-ACCESS  read-create
    STATUS      current
    DESCRIPTION
        "Set this object to true(1) in order to automatically summarize
        redistributed routes to their natural network mask."
    DEFVAL    { false }
    ::= { usdBgpVrfEntry 3 }

usdBgpVrfExternalDistance OBJECT-TYPE
    SYNTAX      INTEGER (1..255)
    MAX-ACCESS  read-create
    STATUS      current
    DESCRIPTION
        "The administrative distance for external routes."
    DEFVAL    { 20 }
    ::= { usdBgpVrfEntry 4 }

usdBgpVrfInternalDistance OBJECT-TYPE
    SYNTAX      INTEGER (1..255)
    MAX-ACCESS  read-create
    STATUS      current
    DESCRIPTION
        "The administrative distance for internal routes."
    DEFVAL    { 200 }
    ::= { usdBgpVrfEntry 5 }

usdBgpVrfLocalDistance OBJECT-TYPE
    SYNTAX      INTEGER (1..255)
    MAX-ACCESS  read-create
    STATUS      current
    DESCRIPTION
        "The administrative distance for local routes."
    DEFVAL    { 200 }
    ::= { usdBgpVrfEntry 6 }

usdBgpVrfResetConnectionType OBJECT-TYPE
    SYNTAX      UsdBgpResetConnectionType
    MAX-ACCESS  read-create
    STATUS      current
    DESCRIPTION
        "Writing a value to this object causes the sessions to all peers in this
        VRF to be cleared; the value determines what type of clear is executed
        (hard clear, soft clear in, soft clear out, etc.).  Reading this object
        has no effect and always returns resetTypeNoop."
    DEFVAL    { resetTypeNoop }
    ::= { usdBgpVrfEntry 7 }

usdBgpVrfRowStatus OBJECT-TYPE
    SYNTAX      RowStatus
    MAX-ACCESS  read-create
    STATUS      current
    DESCRIPTION
        "Controls creation/deletion of entries in this table according to the
        RowStatus textual convention, constrained to support the following
        values only:
            createAndGo
            destroy "
    ::= { usdBgpVrfEntry 8 }

usdBgpVrfOperationalState OBJECT-TYPE
    SYNTAX      INTEGER {
                    ipVrfNotPresent(0),
                    ipVrfPresent(1) }
    MAX-ACCESS  read-only
    STATUS      current
    DESCRIPTION
        "The BGP VRF operational state."
    ::= { usdBgpVrfEntry 9 }

usdBgpVrfAddUnicastRoutesToMulticastView OBJECT-TYPE
    SYNTAX      TruthValue
    MAX-ACCESS  read-create
    STATUS      current
    DESCRIPTION
        "Set this object to true(1) in order to add routes learnt by IPv4
        Unicast BGP to the multicast route table."
    DEFVAL    { false }
    ::= { usdBgpVrfEntry 10 }

usdBgpVrfUnconfiguredAttributes OBJECT-TYPE
    SYNTAX      BITS {
        usdBgpVrfSynchronization(0),
        usdBgpVrfAutoSummary(1),
        usdBgpVrfExternalDistance(2),
        usdBgpVrfInternalDistance(3),
        usdBgpVrfLocalDistance(4),
        usdBgpVrfAddUnicastRoutesToMulticastView(5) }
    MAX-ACCESS  read-create
    STATUS      current
    DESCRIPTION
        "On get each bit indicates whether the corresponding attribute is
        configured or unconfigured:
           0 = The attribute is configured (i.e. the configured value is the
               operational value).
           1 = The attribute is unconfigured (i.e. the operational value is
               inherited from the a higher level which could be the default
               value).

        Getting the attribute value itself always returns the operational value
        of that attribute regardless of whether the attribute is configured or
        unconfigured.

        On write each bit indicates wheter or not the corresponding attribute
        should be set to the unconfigured state:
           0 = No operation (i.e. do not change the state of the attribute).
           1 = Set the attribute to the unconfigured state.

        Setting an attribute to a value has the automatic side-effect of setting
        the bit with the same name to zero."
    DEFVAL    { { } }
    ::= { usdBgpVrfEntry 13 }


-- +++++++++++++++++++++++++++++++++++++++++++++++++++++++++++++++++++++++++++++
-- BGP Address Family attributes
-- +++++++++++++++++++++++++++++++++++++++++++++++++++++++++++++++++++++++++++++
usdBgpAddressFamilyTable OBJECT-TYPE
    SYNTAX      SEQUENCE OF UsdBgpAddressFamilyEntry
    MAX-ACCESS  not-accessible
    STATUS      current
    DESCRIPTION
        "The BGP AddressFamily Entry describes BGP-specific characteristics of
        one AddressFamily."
    ::= { usdBgpObjects 19 }

usdBgpAddressFamilyEntry OBJECT-TYPE
    SYNTAX      UsdBgpAddressFamilyEntry
    MAX-ACCESS  not-accessible
    STATUS      current
    DESCRIPTION
        "The BGP address family entry"
    INDEX     { usdBgpAddressFamilyVrfName,
                usdBgpAddressFamilyAfi,
                usdBgpAddressFamilySafi }
    ::= { usdBgpAddressFamilyTable 1 }

UsdBgpAddressFamilyEntry ::= SEQUENCE {
    usdBgpAddressFamilyVrfName                      UsdVrfName,
    usdBgpAddressFamilyAfi                          UsdBgpAfi,
    usdBgpAddressFamilySafi                         UsdBgpSafi,
    usdBgpAddressFamilyDefaultOriginate             TruthValue,
    usdBgpAddressFamilyRouteFlapDampening           TruthValue,
    usdBgpAddressFamilyDampeningSuppressThreshold   Unsigned32,
    usdBgpAddressFamilyDampeningReuseThreshold      Unsigned32,
    usdBgpAddressFamilyDampeningMaxHoldDownTime     Unsigned32,
    usdBgpAddressFamilyDampeningHalfLifeReachable   Unsigned32,
    usdBgpAddressFamilyDampeningHalfLifeUnreachable Unsigned32,
    usdBgpAddressFamilyDampeningRouteMapName        DisplayString,
    usdBgpAddressFamilyResetConnectionType          UsdBgpResetConnectionType,
    usdBgpAddressFamilyRowStatus                    RowStatus,
    usdBgpAddressFamilyOperationalState             INTEGER,
    usdBgpAddressFamilyUnconfiguredAttributes       BITS }

usdBgpAddressFamilyVrfName OBJECT-TYPE
    SYNTAX      UsdVrfName
    MAX-ACCESS  not-accessible
    STATUS      current
    DESCRIPTION
        "The name of the VPN Routing Forwarding (VRF) instance in which this
        address-family is configured.  The empty string indicates that this
        address-family is not in a VRF."
    ::= { usdBgpAddressFamilyEntry 1 }

usdBgpAddressFamilyAfi OBJECT-TYPE
    SYNTAX      UsdBgpAfi
    MAX-ACCESS  not-accessible
    STATUS      current
    DESCRIPTION
        "The AFI of the address-family."
    ::= { usdBgpAddressFamilyEntry 2 }

usdBgpAddressFamilySafi OBJECT-TYPE
    SYNTAX      UsdBgpSafi
    MAX-ACCESS  not-accessible
    STATUS      current
    DESCRIPTION
        "The SAFI of the address-family."
    ::= { usdBgpAddressFamilyEntry 3 }

usdBgpAddressFamilyDefaultOriginate OBJECT-TYPE
    SYNTAX      TruthValue
    MAX-ACCESS  read-create
    STATUS      current
    DESCRIPTION
        "Set this object to true(1) in order to advertise a default route, if
        present."
    DEFVAL    { false }
    ::= { usdBgpAddressFamilyEntry 4 }

usdBgpAddressFamilyRouteFlapDampening OBJECT-TYPE
    SYNTAX      TruthValue
    MAX-ACCESS  read-create
    STATUS      current
    DESCRIPTION
        "Set this object to true(1) in order to enable route flap dampening."
    DEFVAL    { false }
    ::= { usdBgpAddressFamilyEntry 5 }

usdBgpAddressFamilyDampeningSuppressThreshold OBJECT-TYPE
    SYNTAX      Unsigned32
    MAX-ACCESS  read-create
    STATUS      current
    DESCRIPTION
        "The dampening cutoff threshold (scaled)."
    DEFVAL    { 1000 }
    ::= { usdBgpAddressFamilyEntry 6 }

usdBgpAddressFamilyDampeningReuseThreshold OBJECT-TYPE
    SYNTAX      Unsigned32
    MAX-ACCESS  read-create
    STATUS      current
    DESCRIPTION
        "The dampening reuse threshold (scaled)."
    DEFVAL    { 1000 }
    ::= { usdBgpAddressFamilyEntry 7 }

usdBgpAddressFamilyDampeningMaxHoldDownTime OBJECT-TYPE
    SYNTAX      Unsigned32
    UNITS       "seconds"
    MAX-ACCESS  read-create
    STATUS      current
    DESCRIPTION
        "Maximum route holddown time, in seconds."
    DEFVAL    { 20 }
    ::= { usdBgpAddressFamilyEntry 8 }

usdBgpAddressFamilyDampeningHalfLifeReachable OBJECT-TYPE
    SYNTAX      Unsigned32
    UNITS       "seconds"
    MAX-ACCESS  read-create
    STATUS      current
    DESCRIPTION
        "Figure of merit half life for reachable routes, in seconds."
    DEFVAL    { 5 }
    ::= { usdBgpAddressFamilyEntry 9 }

usdBgpAddressFamilyDampeningHalfLifeUnreachable OBJECT-TYPE
    SYNTAX      Unsigned32
    UNITS       "seconds"
    MAX-ACCESS  read-create
    STATUS      current
    DESCRIPTION
        "Figure of merit half life for unreachable routes, in seconds."
    DEFVAL    { 5 }
    ::= { usdBgpAddressFamilyEntry 10 }

usdBgpAddressFamilyDampeningRouteMapName OBJECT-TYPE
    SYNTAX      DisplayString (SIZE(0..32))
    MAX-ACCESS  read-create
    STATUS      current
    DESCRIPTION
        "The name of the route-map used to determine which routes are dampened
        and which aren't and to set the dampening parameters for those routes
        which are dampenend.  A zero length route-map name means don't use a
        route-map for this."
    DEFVAL    { "" }
    ::= { usdBgpAddressFamilyEntry 11 }

usdBgpAddressFamilyResetConnectionType OBJECT-TYPE
    SYNTAX      UsdBgpResetConnectionType
    MAX-ACCESS  read-create
    STATUS      current
    DESCRIPTION
        "Writing a value to this object causes one individual address family
        within the sessions to all peers in this VRF to be cleared; the value
        determines what type of clear is executed (hard clear, soft clear in,
        soft clear out, etc.).  Note that hard clearing an address family within
        a session will bounce the session and thus also affect the other address
        families in the session.  Reading this object has no effect and always
        returns resetTypeNoop."
    DEFVAL    { resetTypeNoop }
    ::= { usdBgpAddressFamilyEntry 12 }

usdBgpAddressFamilyRowStatus OBJECT-TYPE
    SYNTAX      RowStatus
    MAX-ACCESS  read-create
    STATUS      current
    DESCRIPTION
        "Controls creation/deletion of entries in this table according to the
        RowStatus textual convention, constrained to support the following
        values only:
            createAndGo
            destroy "
    ::= { usdBgpAddressFamilyEntry 13 }

usdBgpAddressFamilyOperationalState OBJECT-TYPE
    SYNTAX      INTEGER {
                    ipVrfNotPresent(0),
                    ipVrfPresent(1) }
    MAX-ACCESS  read-only
    STATUS      current
    DESCRIPTION
        "The BGP address family operational state."
    ::= { usdBgpAddressFamilyEntry 14 }

usdBgpAddressFamilyUnconfiguredAttributes OBJECT-TYPE
    SYNTAX      BITS {
        usdBgpAddressFamilyDefaultOriginate(0),
        usdBgpAddressFamilyRouteFlapDampening(1),
        usdBgpAddressFamilyDampeningSuppressThreshold(2),
        usdBgpAddressFamilyDampeningReuseThreshold(3),
        usdBgpAddressFamilyDampeningMaxHoldDownTime(4),
        usdBgpAddressFamilyDampeningHalfLifeReachable(5),
        usdBgpAddressFamilyDampeningHalfLifeUnreachable(6),
        usdBgpAddressFamilyDampeningRouteMapName(7) }
    MAX-ACCESS  read-create
    STATUS      current
    DESCRIPTION
        "On get each bit indicates whether the corresponding attribute is
        configured or unconfigured:
           0 = The attribute is configured (i.e. the configured value is the
               operational value).
           1 = The attribute is unconfigured (i.e. the operational value is
               inherited from the a higher level which could be the default
               value).

        Getting the attribute value itself always returns the operational value
        of that attribute regardless of whether the attribute is configured or
        unconfigured.

        On write each bit indicates wheter or not the corresponding attribute
        should be set to the unconfigured state:
           0 = No operation (i.e. do not change the state of the attribute).
           1 = Set the attribute to the unconfigured state.

        Setting an attribute to a value has the automatic side-effect of setting
        the bit with the same name to zero."
    DEFVAL    { { } }
    ::= { usdBgpAddressFamilyEntry 15 }


-- +++++++++++++++++++++++++++++++++++++++++++++++++++++++++++++++++++++++++++++
-- BGP Storage attributes
-- +++++++++++++++++++++++++++++++++++++++++++++++++++++++++++++++++++++++++++++
--
-- Objects set in the usdBgpStorageGroup will not take affect until reboot
--
-- The objects in this group define the initial and maximum size of various
-- heaps and pools used in BGP.
--
-- Each heap or pool is used to store a certain type of configured (e.g. peers)
-- or dynamic (e.g. routes) entries.  The initial size of each heap or pool
-- indicates how large the heap or pool is when BGP is initially created.  As
-- entries are allocated from heaps and pools and the pool eventually becomes
-- exhausted, the heaps and pools grow automatically up the to maximum size for
-- the heap or pool.  Once the heap or pool reaches it maximum size, BGP goes
-- into "overload state" and will stop accepting new configuration or dynamic
-- information for that heap or pool.
--

usdBgpStorageGroup                 OBJECT IDENTIFIER ::= { usdBgpObjects 20 }

usdBgpStorageInitialHeapSize OBJECT-TYPE
    SYNTAX      UsdBgpStorageInteger
    MAX-ACCESS  read-write
    STATUS      current
    DESCRIPTION
        "The initial size of the BGP heap in octets.  The BGP heap is used for a
        small number of variable sized data structures."
    DEFVAL    { 33554432 }
    ::= { usdBgpStorageGroup 1 }

usdBgpStorageMaxHeapSize OBJECT-TYPE
    SYNTAX      UsdBgpStorageInteger
    MAX-ACCESS  read-write
    STATUS      current
    DESCRIPTION
        "The maximum size of the BGP heap in octets."
    DEFVAL    { 536870912 }
    ::= { usdBgpStorageGroup 2 }

usdBgpStorageInitialVrfPoolSize OBJECT-TYPE
    SYNTAX      UsdBgpStorageInteger
    MAX-ACCESS  read-write
    STATUS      current
    DESCRIPTION
        "The initial size of the VRF pool in entries.  One entry is allocated
        from the VRF pool for each VRF used by BGP."
    DEFVAL    { 1 }
    ::= { usdBgpStorageGroup 4 }

usdBgpStorageMaxVrfPoolSize OBJECT-TYPE
    SYNTAX      UsdBgpStorageInteger
    MAX-ACCESS  read-write
    STATUS      current
    DESCRIPTION
        "The maximum size of the VRF pool in entries."
    DEFVAL    { 500000000 }
    ::= { usdBgpStorageGroup 5 }

usdBgpStorageInitialAddressFamilyPoolSize OBJECT-TYPE
    SYNTAX      UsdBgpStorageInteger
    MAX-ACCESS  read-write
    STATUS      current
    DESCRIPTION
        "The initial size of the address-family pool in entries.  One entry is
        allocated from the address-family pool for each address-family used by
        BGP."
    DEFVAL    { 1 }
    ::= { usdBgpStorageGroup 6 }

usdBgpStorageMaxAddressFamilyPoolSize OBJECT-TYPE
    SYNTAX      UsdBgpStorageInteger
    MAX-ACCESS  read-write
    STATUS      current
    DESCRIPTION
        "The initial size of the address-family pool in entries."
    DEFVAL    { 500000000 }
    ::= { usdBgpStorageGroup 7 }

usdBgpStorageInitialPeerPoolSize OBJECT-TYPE
    SYNTAX      UsdBgpStorageInteger
    MAX-ACCESS  read-write
    STATUS      current
    DESCRIPTION
        "The initial size of the peer pool in entries.  One entry is allocated
        from the peer pool for each peer configured in BGP."
    DEFVAL    { 1 }
    ::= { usdBgpStorageGroup 8 }

usdBgpStorageMaxPeerPoolSize OBJECT-TYPE
    SYNTAX      UsdBgpStorageInteger
    MAX-ACCESS  read-write
    STATUS      current
    DESCRIPTION
        "The maximum size of the peer pool in entries."
    DEFVAL    { 500000000 }
    ::= { usdBgpStorageGroup 9 }

usdBgpStorageInitialPeerAfPoolSize OBJECT-TYPE
    SYNTAX      UsdBgpStorageInteger
    MAX-ACCESS  read-write
    STATUS      current
    DESCRIPTION
        "The initial size of the peer-address-family pool in entries.  One entry
        is allocated from the peer-address-family pool for each address family
        activated for any peer in BGP (including the IPv4 unicast address
        families which are usually activated by default for each peer)."
    DEFVAL    { 1 }
    ::= { usdBgpStorageGroup 10 }

usdBgpStorageMaxPeerAfPoolSize OBJECT-TYPE
    SYNTAX      UsdBgpStorageInteger
    MAX-ACCESS  read-write
    STATUS      current
    DESCRIPTION
        "The maximum size of the peer-address-family pool in entries."
    DEFVAL    { 500000000 }
    ::= { usdBgpStorageGroup 11 }

usdBgpStorageInitialPeerGroupPoolSize OBJECT-TYPE
    SYNTAX      UsdBgpStorageInteger
    MAX-ACCESS  read-write
    STATUS      current
    DESCRIPTION
        "The initial size of the peer-group pool in entries.  One entry is
        allocated from the peer-group pool for each peer-group configured in
        BGP."
    DEFVAL    { 1 }
    ::= { usdBgpStorageGroup 12 }

usdBgpStorageMaxPeerGroupPoolSize OBJECT-TYPE
    SYNTAX      UsdBgpStorageInteger
    MAX-ACCESS  read-write
    STATUS      current
    DESCRIPTION
        "The maximum size of the peer-group pool in entries."
    DEFVAL    { 500000000 }
    ::= { usdBgpStorageGroup 13 }

usdBgpStorageInitialPeerGroupAfPoolSize OBJECT-TYPE
    SYNTAX      UsdBgpStorageInteger
    MAX-ACCESS  read-write
    STATUS      current
    DESCRIPTION
        "The initial size of the peer-group-address-family pool in entries.  One
        entry is allocated from the peer-group-address-family pool for each
        address family activated for any peer-group in BGP (including the IPv4
        unicast address families which are usually activated by default for each
        peer-group)."
    DEFVAL    { 1 }
    ::= { usdBgpStorageGroup 14 }

usdBgpStorageMaxPeerGroupAfPoolSize OBJECT-TYPE
    SYNTAX      UsdBgpStorageInteger
    MAX-ACCESS  read-write
    STATUS      current
    DESCRIPTION
        "The maximum size of the peer-group-address-family pool in entries."
    DEFVAL    { 500000000 }
    ::= { usdBgpStorageGroup 15 }

usdBgpStorageInitialNetworkPoolSize OBJECT-TYPE
    SYNTAX      UsdBgpStorageInteger
    MAX-ACCESS  read-write
    STATUS      current
    DESCRIPTION
        "The initial size of the network pool in entries.  One entry is
        allocated from the network pool for each network configured in BGP."
    DEFVAL    { 1 }
    ::= { usdBgpStorageGroup 16 }

usdBgpStorageMaxNetworkPoolSize OBJECT-TYPE
    SYNTAX      UsdBgpStorageInteger
    MAX-ACCESS  read-write
    STATUS      current
    DESCRIPTION
        "The maximum size of the network pool in entries."
    DEFVAL    { 500000000 }
    ::= { usdBgpStorageGroup 17 }

usdBgpStorageInitialAggregatePoolSize OBJECT-TYPE
    SYNTAX      UsdBgpStorageInteger
    MAX-ACCESS  read-write
    STATUS      current
    DESCRIPTION
        "The initial size of the aggregate pool in entries.  One entry is
        allocated from the aggregate pool for each aggregate configured in BGP."
    DEFVAL    { 1 }
    ::= { usdBgpStorageGroup 18 }

usdBgpStorageMaxAggregatePoolSize OBJECT-TYPE
    SYNTAX      UsdBgpStorageInteger
    MAX-ACCESS  read-write
    STATUS      current
    DESCRIPTION
        "The maximum size of the aggregate pool in entries."
    DEFVAL    { 500000000 }
    ::= { usdBgpStorageGroup 19 }

usdBgpStorageInitialDestinationPoolSize OBJECT-TYPE
    SYNTAX      UsdBgpStorageInteger
    MAX-ACCESS  read-write
    STATUS      current
    DESCRIPTION
        "The initial size of the destination pool in entries.  One entry is
        allocated from the destination pool for each unique prefix in the BGP
        RIB."
    DEFVAL    { 1 }
    ::= { usdBgpStorageGroup 20 }

usdBgpStorageMaxDestinationPoolSize OBJECT-TYPE
    SYNTAX      UsdBgpStorageInteger
    MAX-ACCESS  read-write
    STATUS      current
    DESCRIPTION
        "The maximum size of the destination pool in entries."
    DEFVAL    { 500000000 }
    ::= { usdBgpStorageGroup 21 }

usdBgpStorageInitialRoutePoolSize OBJECT-TYPE
    SYNTAX      UsdBgpStorageInteger
    MAX-ACCESS  read-write
    STATUS      current
    DESCRIPTION
        "The initial size of the route pool in entries.  One entry is allocated
        from the route pool for each received non-VPN route in the BGP RIB."
    DEFVAL    { 1 }
    ::= { usdBgpStorageGroup 22 }

usdBgpStorageMaxRoutePoolSize OBJECT-TYPE
    SYNTAX      UsdBgpStorageInteger
    MAX-ACCESS  read-write
    STATUS      current
    DESCRIPTION
        "The maximum size of the route pool in entries."
    DEFVAL    { 500000000 }
    ::= { usdBgpStorageGroup 23 }

usdBgpStorageInitialAttributesPoolSize OBJECT-TYPE
    SYNTAX      UsdBgpStorageInteger
    MAX-ACCESS  read-write
    STATUS      current
    DESCRIPTION
        "The initial size of the attributes pool in entries.  One entry is
        allocated from the attributes pool for each unique combination of path
        attributes of routes in the BGP RIB."
    DEFVAL    { 1 }
    ::= { usdBgpStorageGroup 24 }

usdBgpStorageMaxAttributesPoolSize OBJECT-TYPE
    SYNTAX      UsdBgpStorageInteger
    MAX-ACCESS  read-write
    STATUS      current
    DESCRIPTION
        "The maximum size of the attributes pool in entries."
    DEFVAL    { 500000000 }
    ::= { usdBgpStorageGroup 25 }

usdBgpStorageInitialRouteFlapHistoryPoolSize OBJECT-TYPE
    SYNTAX      UsdBgpStorageInteger
    MAX-ACCESS  read-write
    STATUS      current
    DESCRIPTION
        "The initial size of the route-flap-history pool in entries.  One entry
        is allocated from the route-flap-history pool for each route in the BGP
        RIB which has route-flap dampening history associated with it."
    DEFVAL    { 1 }
    ::= { usdBgpStorageGroup 26 }

usdBgpStorageMaxRouteFlapHistoryPoolSize OBJECT-TYPE
    SYNTAX      UsdBgpStorageInteger
    MAX-ACCESS  read-write
    STATUS      current
    DESCRIPTION
        "The maximum size of the route-flap-history pool in entries."
    DEFVAL    { 500000000 }
    ::= { usdBgpStorageGroup 27 }

usdBgpStorageInitialNetworkRoutePoolSize OBJECT-TYPE
    SYNTAX      UsdBgpStorageInteger
    MAX-ACCESS  read-write
    STATUS      current
    DESCRIPTION
        "The initial size of the network-route pool in entries.  One entry is
        allocated from the network-route pool for each network route in the BGP
        RIB."
    DEFVAL    { 1 }
    ::= { usdBgpStorageGroup 28 }

usdBgpStorageMaxNetworkRoutePoolSize OBJECT-TYPE
    SYNTAX      UsdBgpStorageInteger
    MAX-ACCESS  read-write
    STATUS      current
    DESCRIPTION
        "The maximum size of the network-route pool in entries."
    DEFVAL    { 500000000 }
    ::= { usdBgpStorageGroup 29 }

usdBgpStorageInitialRedistributedRoutePoolSize OBJECT-TYPE
    SYNTAX      UsdBgpStorageInteger
    MAX-ACCESS  read-write
    STATUS      current
    DESCRIPTION
        "The initial size of the redistributed-route pool in entries.  One entry
        is allocated from the redistributed-route pool for each redistributed
        route in the BGP RIB."
    DEFVAL    { 1 }
    ::= { usdBgpStorageGroup 30 }

usdBgpStorageMaxRedistributedRoutePoolSize OBJECT-TYPE
    SYNTAX      UsdBgpStorageInteger
    MAX-ACCESS  read-write
    STATUS      current
    DESCRIPTION
        "The maximum size of the redistributed-route pool in entries."
    DEFVAL    { 500000000 }
    ::= { usdBgpStorageGroup 31 }

usdBgpStorageInitialAggregateRoutePoolSize OBJECT-TYPE
    SYNTAX      UsdBgpStorageInteger
    MAX-ACCESS  read-write
    STATUS      current
    DESCRIPTION
        "The initial size of the aggregate-route pool in entries.  One entry is
        allocated from the aggregate-route pool for each aggregate route in the
        BGP RIB."
    DEFVAL    { 1 }
    ::= { usdBgpStorageGroup 32 }

usdBgpStorageMaxAggregateRoutePoolSize OBJECT-TYPE
    SYNTAX      UsdBgpStorageInteger
    MAX-ACCESS  read-write
    STATUS      current
    DESCRIPTION
        "The maximum size of the aggregate-route pool in entries."
    DEFVAL    { 500000000 }
    ::= { usdBgpStorageGroup 33 }

usdBgpStorageInitialAutoSummaryRoutePoolSize OBJECT-TYPE
    SYNTAX      UsdBgpStorageInteger
    MAX-ACCESS  read-write
    STATUS      current
    DESCRIPTION
        "The initial size of the auto-summary-route pool in entries.  One entry
        is allocated from the auto-summary-route pool for each auto-summary
        route in the BGP RIB."
    DEFVAL    { 1 }
    ::= { usdBgpStorageGroup 34 }

usdBgpStorageMaxAutoSummaryRoutePoolSize OBJECT-TYPE
    SYNTAX      UsdBgpStorageInteger
    MAX-ACCESS  read-write
    STATUS      current
    DESCRIPTION
        "The maximum size of the auto-summary-route pool in entries."
    DEFVAL    { 500000000 }
    ::= { usdBgpStorageGroup 35 }

usdBgpStorageInitialHistoryRoutePoolSize OBJECT-TYPE
    SYNTAX      UsdBgpStorageInteger
    MAX-ACCESS  read-write
    STATUS      obsolete
    DESCRIPTION
        "This object is obsolete.  Setting it has not effect and reading this
        object returns an undefined value."
    DEFVAL    { 1 }
    ::= { usdBgpStorageGroup 36 }

usdBgpStorageMaxHistoryRoutePoolSize OBJECT-TYPE
    SYNTAX      UsdBgpStorageInteger
    MAX-ACCESS  read-write
    STATUS      obsolete
    DESCRIPTION
        "This object is obsolete.  Setting it has not effect and reading this
        object returns an undefined value."
    DEFVAL    { 500000000 }
    ::= { usdBgpStorageGroup 37 }

usdBgpStorageInitialSendQueueEntryPoolSize OBJECT-TYPE
    SYNTAX      UsdBgpStorageInteger
    MAX-ACCESS  read-write
    STATUS      current
    DESCRIPTION
        "The initial size of the send-queue-entry pool in entries.  One entry is
        allocated from the send-queue-entry pool for update messages which is
        queued for transmission to a peer."
    DEFVAL    { 1 }
    ::= { usdBgpStorageGroup 38 }

usdBgpStorageMaxSendQueueEntryPoolSize OBJECT-TYPE
    SYNTAX      UsdBgpStorageInteger
    MAX-ACCESS  read-write
    STATUS      current
    DESCRIPTION
        "The maximum size of the send-queue-entry pool in entries."
    DEFVAL    { 500000000 }
    ::= { usdBgpStorageGroup 39 }

usdBgpStorageInitialVpnRoutePoolSize OBJECT-TYPE
    SYNTAX      UsdBgpStorageInteger
    MAX-ACCESS  read-write
    STATUS      current
    DESCRIPTION
        "The initial size of the vpn-route pool in entries.  One entry is
        allocated from the vpn-route pool for each received VPN route in the BGP
        RIB."
    DEFVAL    { 1 }
    ::= { usdBgpStorageGroup 40 }

usdBgpStorageMaxVpnRoutePoolSize OBJECT-TYPE
    SYNTAX      UsdBgpStorageInteger
    MAX-ACCESS  read-write
    STATUS      current
    DESCRIPTION
        "The maximum size of the vpn-route pool in entries."
    DEFVAL    { 500000000 }
    ::= { usdBgpStorageGroup 41 }

usdBgpStorageInitialRouteTargetPoolSize OBJECT-TYPE
    SYNTAX      UsdBgpStorageInteger
    MAX-ACCESS  read-write
    STATUS      current
    DESCRIPTION
        "The initial size of the route-target pool in entries.  One entry is
        allocated from the route-target pool for each route-target imported in
        any VRF used by BGP."
    DEFVAL    { 1 }
    ::= { usdBgpStorageGroup 42 }

usdBgpStorageMaxRouteTargetPoolSize OBJECT-TYPE
    SYNTAX      UsdBgpStorageInteger
    MAX-ACCESS  read-write
    STATUS      current
    DESCRIPTION
        "The maximum size of the route-target pool in entries."
    DEFVAL    { 500000000 }
    ::= { usdBgpStorageGroup 43 }


-- +++++++++++++++++++++++++++++++++++++++++++++++++++++++++++++++++++++++++++++
-- BGP New Route attributes
-- +++++++++++++++++++++++++++++++++++++++++++++++++++++++++++++++++++++++++++++
--
--  BGP New Route Attribute Table
--
usdBgpNewRouteTable OBJECT-TYPE
    SYNTAX      SEQUENCE OF UsdBgpNewRouteEntry
    MAX-ACCESS  not-accessible
    STATUS      current
    DESCRIPTION
        "The BGP-4 Received Path Attribute Table contains additional information
        about paths to destination networks received from all BGP4 peers."
    ::= { usdBgpObjects 23 }

usdBgpNewRouteEntry OBJECT-TYPE
    SYNTAX      UsdBgpNewRouteEntry
    MAX-ACCESS  not-accessible
    STATUS      current
    DESCRIPTION
        "Additional information about a path to a network."
    INDEX     { usdBgpNewRouteVrfName,
                usdBgpNewRouteAfi,
                usdBgpNewRouteSafi,
                usdBgpNewRouteIpAddrPrefix,
                usdBgpNewRouteIpAddrPrefixLen,
                usdBgpNewRouteDistinguisher,
                usdBgpNewRoutePeer,
                usdBgpNewRouteRouteType,
                usdBgpNewRouteOriginalRd }
    ::= { usdBgpNewRouteTable 1 }

UsdBgpNewRouteEntry ::= SEQUENCE {
    usdBgpNewRouteVrfName                       UsdVrfName,
    usdBgpNewRouteAfi                           UsdBgpAfi,
    usdBgpNewRouteSafi                          UsdBgpSafi,
    usdBgpNewRouteIpAddrPrefix                  IpAddress,
    usdBgpNewRouteIpAddrPrefixLen               INTEGER,
    usdBgpNewRouteDistinguisher                 OCTET STRING,
    usdBgpNewRoutePeer                          IpAddress,
    usdBgpNewRouteRouteType                     INTEGER,
    usdBgpNewRouteOriginalRd                    OCTET STRING,
    usdBgpNewRouteOriginatorId                  IpAddress,
    usdBgpNewRouteAtomicAggregatePresent        TruthValue,
    usdBgpNewRouteMedPresent                    TruthValue,
    usdBgpNewRouteLocalPrefPresent              TruthValue,
    usdBgpNewRouteAggregatorPresent             TruthValue,
    usdBgpNewRouteCommunitiesPresent            TruthValue,
    usdBgpNewRouteOriginatorIdPresent           TruthValue,
    usdBgpNewRouteClusterListPresent            TruthValue,
    usdBgpNewRouteWeight                        Unsigned32,
    usdBgpNewRouteOrigin                        INTEGER,
    usdBgpNewRouteASPathSegment                 OCTET STRING,
    usdBgpNewRouteNextHop                       IpAddress,
    usdBgpNewRouteMultiExitDisc                 Unsigned32,
    usdBgpNewRouteLocalPref                     Unsigned32,
    usdBgpNewRouteAtomicAggregate               INTEGER,
    usdBgpNewRouteAggregatorAS                  INTEGER,
    usdBgpNewRouteAggregatorAddress             IpAddress,
    usdBgpNewRouteBestInIpRouteTable            TruthValue,
    usdBgpNewRouteUnknown                       OCTET STRING,
    usdBgpNewRouteExtendedCommunitiesPresent    TruthValue,
    usdBgpNewRouteValid                         TruthValue,
    usdBgpNewRouteSuppressedBy                  INTEGER,
    usdBgpNewRouteNextHopReachable              TruthValue,
    usdBgpNewRouteSynchronizedWithIgp           TruthValue,
    usdBgpNewRoutePlaceInIpRouteTable           TruthValue,
    usdBgpNewRouteAdvertiseToExternalPeers      TruthValue,
    usdBgpNewRouteAdvertiseToInternalPeers      TruthValue,
    usdBgpNewRouteMplsLabel                     Unsigned32,
    usdBgpNewRouteNextHopMetric                 Unsigned32 }

usdBgpNewRouteVrfName OBJECT-TYPE
    SYNTAX      UsdVrfName
    MAX-ACCESS  not-accessible
    STATUS      current
    DESCRIPTION
        "The name of the VPN Routing Forwarding (VRF) instance in which this
        route is present.  The empty string indicates that this route is not in
        a VRF."
    ::= { usdBgpNewRouteEntry 1 }

usdBgpNewRouteAfi OBJECT-TYPE
    SYNTAX      UsdBgpAfi
    MAX-ACCESS  not-accessible
    STATUS      current
    DESCRIPTION
        "The AFI of the address-family in which this route is present."
    ::= { usdBgpNewRouteEntry 2 }

usdBgpNewRouteSafi OBJECT-TYPE
    SYNTAX      UsdBgpSafi
    MAX-ACCESS  not-accessible
    STATUS      current
    DESCRIPTION
        "The SAFI of the address-family in which this route is present."
    ::= { usdBgpNewRouteEntry 3 }

usdBgpNewRouteIpAddrPrefix OBJECT-TYPE
    SYNTAX      IpAddress
    MAX-ACCESS  not-accessible
    STATUS      current
    DESCRIPTION
        "The IP address prefix of the route.  This object is an IP address
        containing the prefix with length specified by
        usdBgpNewRouteIpAddrPrefixLen.  Any bits beyond the length specified by
        usdBgpNewRouteIpAddrPrefixLen are zeroed."
    ::= { usdBgpNewRouteEntry 4 }

usdBgpNewRouteIpAddrPrefixLen OBJECT-TYPE
    SYNTAX      INTEGER (0..32)
    MAX-ACCESS  not-accessible
    STATUS      current
    DESCRIPTION
        "Length in bits of the IP address prefix of the route."
    ::= { usdBgpNewRouteEntry 5 }

usdBgpNewRouteDistinguisher OBJECT-TYPE
    SYNTAX      OCTET STRING (SIZE(8))
    MAX-ACCESS  not-accessible
    STATUS      current
    DESCRIPTION
        "The Route Distinguisher (RD) of the route.  This object has an
        undefined value for non-VPN routes."
    ::= { usdBgpNewRouteEntry 6 }

usdBgpNewRoutePeer OBJECT-TYPE
    SYNTAX      IpAddress
    MAX-ACCESS  not-accessible
    STATUS      current
    DESCRIPTION
        "The IP address of the peer from which the route was received.  This
        object has value 0.0.0.0 is the route was a locally originated route."
    ::= { usdBgpNewRouteEntry 7 }

usdBgpNewRouteRouteType OBJECT-TYPE
    SYNTAX      INTEGER {
                    routeTypeReceived(1),
                    routeTypeNetwork(2),
                    routeTypeRedistributed(3),
                    routeTypeAggregate(4),
                    routeTypeAutoSummary(5) }
    MAX-ACCESS  not-accessible
    STATUS      current
    DESCRIPTION
        "The type of the route."
    ::= { usdBgpNewRouteEntry 8 }

usdBgpNewRouteOriginalRd OBJECT-TYPE
    SYNTAX      OCTET STRING (SIZE(8))
    MAX-ACCESS  not-accessible
    STATUS      current
    DESCRIPTION
        "The original Route Distinguisher (RD) of a VPN route.  For VPN routes
        which are originated in a VRF or which are received from a CE the
        original RD is equal to the RD of the VRF.  For VPN routes which are
        received from another PE and imported into a VRF, the original RD is the
        RD which was received from the other PE (the RD of the route itself is
        changed to the RD for the VRF when the route is imported into the VRF).
        For non-VPN routes the value of this object is undefined."
    ::= { usdBgpNewRouteEntry 9 }

usdBgpNewRouteOriginatorId OBJECT-TYPE
    SYNTAX      IpAddress
    MAX-ACCESS  read-only
    STATUS      current
    DESCRIPTION
        "The Originator-ID path attribute of the route if present.  The
        usdBgpNewRouteOriginatorIdPresent object indicates whether the
        Originator-ID path attribute is present."
    ::= { usdBgpNewRouteEntry 10 }

usdBgpNewRouteAtomicAggregatePresent OBJECT-TYPE
    SYNTAX      TruthValue
    MAX-ACCESS  read-only
    STATUS      current
    DESCRIPTION
        "Atomic-Aggregate path attribute is present."
    ::= { usdBgpNewRouteEntry 11 }

usdBgpNewRouteMedPresent OBJECT-TYPE
    SYNTAX      TruthValue
    MAX-ACCESS  read-only
    STATUS      current
    DESCRIPTION
        "The Multi-Exit-Discriminator path attribute is present."
    ::= { usdBgpNewRouteEntry 12 }

usdBgpNewRouteLocalPrefPresent OBJECT-TYPE
    SYNTAX      TruthValue
    MAX-ACCESS  read-only
    STATUS      current
    DESCRIPTION
        "The Local-Pref path attribute is present."
    ::= { usdBgpNewRouteEntry 13 }

usdBgpNewRouteAggregatorPresent OBJECT-TYPE
    SYNTAX      TruthValue
    MAX-ACCESS  read-only
    STATUS      current
    DESCRIPTION
        "The Aggregator path attribute is present."
    ::= { usdBgpNewRouteEntry 14 }

usdBgpNewRouteCommunitiesPresent OBJECT-TYPE
    SYNTAX      TruthValue
    MAX-ACCESS  read-only
    STATUS      current
    DESCRIPTION
        "The Communities path attribute is present."
    ::= { usdBgpNewRouteEntry 15 }

usdBgpNewRouteOriginatorIdPresent OBJECT-TYPE
    SYNTAX      TruthValue
    MAX-ACCESS  read-only
    STATUS      current
    DESCRIPTION
        "The Originator-ID path attribute is present."
    ::= { usdBgpNewRouteEntry 16 }

usdBgpNewRouteClusterListPresent OBJECT-TYPE
    SYNTAX      TruthValue
    MAX-ACCESS  read-only
    STATUS      current
    DESCRIPTION
        "The Cluster-List path attribute is present."
    ::= { usdBgpNewRouteEntry 17 }

usdBgpNewRouteWeight OBJECT-TYPE
    SYNTAX      Unsigned32
    MAX-ACCESS  read-only
    STATUS      current
    DESCRIPTION
        "The weight of the route."
    ::= { usdBgpNewRouteEntry 18 }

usdBgpNewRouteOrigin OBJECT-TYPE
    SYNTAX      INTEGER {
                    igp(1),
                    egp(2),
                    incomplete(3) }
    MAX-ACCESS  read-only
    STATUS      current
    DESCRIPTION
        "The value of the Origin path attribute."
    ::= { usdBgpNewRouteEntry 19 }

usdBgpNewRouteASPathSegment OBJECT-TYPE
    SYNTAX      OCTET STRING (SIZE(2..255))
    MAX-ACCESS  read-only
    STATUS      current
    DESCRIPTION
        "The value of the AS-path path attribute (as encoded in the received
        update message)."
    ::= { usdBgpNewRouteEntry 20 }

usdBgpNewRouteNextHop OBJECT-TYPE
    SYNTAX      IpAddress
    MAX-ACCESS  read-only
    STATUS      current
    DESCRIPTION
        "The value of the Next-Hop path attribute."
    ::= { usdBgpNewRouteEntry 21 }

usdBgpNewRouteMultiExitDisc OBJECT-TYPE
    SYNTAX      Unsigned32
    MAX-ACCESS  read-only
    STATUS      current
    DESCRIPTION
        "The value of the Multi-Exit-Discriminator path attribute if present.
        The usdBgpNewRouteMedPresent object indicates whether the
        Multi-Exit-Discriminator path attribute is present."
    ::= { usdBgpNewRouteEntry 22 }

usdBgpNewRouteLocalPref OBJECT-TYPE
    SYNTAX      Unsigned32
    MAX-ACCESS  read-only
    STATUS      current
    DESCRIPTION
        "The value of the Local-Pref path attribute if present.  The
        usdBgpNewRouteLocalPrefPresent object indicates whether the Local-Pref
        path attribute is present."
    ::= { usdBgpNewRouteEntry 23 }

usdBgpNewRouteAtomicAggregate OBJECT-TYPE
    SYNTAX      INTEGER {
                    lessSpecificRouteNotSelected(1),
                    lessSpecificRouteSelected(2) }
    MAX-ACCESS read-only
    STATUS      current
    DESCRIPTION
        "Whether or not the local system has selected a less specific route
        without selecting a more specific route."
    ::= { usdBgpNewRouteEntry 24 }

usdBgpNewRouteAggregatorAS OBJECT-TYPE
    SYNTAX      INTEGER (0..65535)
    MAX-ACCESS  read-only
    STATUS      current
    DESCRIPTION
        "The value of the AS field in the Aggregator path attribute if present.
        The usdBgpNewRouteAggregatorPresent object indicates whether the
        Aggregator path attribute is present."
    ::= { usdBgpNewRouteEntry 25 }

usdBgpNewRouteAggregatorAddress OBJECT-TYPE
    SYNTAX      IpAddress
    MAX-ACCESS  read-only
    STATUS      current
    DESCRIPTION
        "The value of the address field in the Aggregator path attribute if
        present.  The usdBgpNewRouteAggregatorPresent object indicates whether
        the Aggregator path attribute is present."
    ::= { usdBgpNewRouteEntry 26 }

usdBgpNewRouteBestInIpRouteTable OBJECT-TYPE
    SYNTAX      TruthValue
    MAX-ACCESS  read-only
    STATUS      current
    DESCRIPTION
        "When BGP places a routes in the IP route table, that route may not be
        used for forwarding traffic if there are other routes (e.g. IGP routes
        or static routes) to that same prefix with a better administrative
        distance in the IP route table.  This object indicates whether or not
        the BGP route in the IP route table is the best route (and hence is used
        for forwarding traffic)."
    ::= { usdBgpNewRouteEntry 27 }

usdBgpNewRouteUnknown OBJECT-TYPE
    SYNTAX      OCTET STRING (SIZE(0..255))
    MAX-ACCESS  read-only
    STATUS      current
    DESCRIPTION
        "One or more path attributes not understood by this BGP4 speaker.  Size
        zero (0) indicates the absence of such attribute(s).  Octets beyond the
        maximum size, if any, are not recorded by this object."
    ::= { usdBgpNewRouteEntry 28 }

usdBgpNewRouteExtendedCommunitiesPresent OBJECT-TYPE
    SYNTAX      TruthValue
    MAX-ACCESS  read-only
    STATUS      current
    DESCRIPTION
        "Is the Extended-Communities path attribute present?"
    ::= { usdBgpNewRouteEntry 29 }

usdBgpNewRouteValid OBJECT-TYPE
    SYNTAX      TruthValue
    MAX-ACCESS  read-only
    STATUS      current
    DESCRIPTION
        "Is the route valid?  The route is declared invalid if there is
        something wrong with it which is not serious enough for sending a
        notification, but it serious enough for not placing it in the IP route
        table or propagating it to other peers (for example the next-hop of the
        route is a local address)."
    ::= { usdBgpNewRouteEntry 30 }

usdBgpNewRouteSuppressedBy OBJECT-TYPE
    SYNTAX      INTEGER {
                    suppressedByNothing(1),
                    suppressedByAggregate(2),
                    suppressedByAutoSummary(3),
                    suppressedByDampening(4) }
    MAX-ACCESS  read-only
    STATUS      current
    DESCRIPTION
        "Indicates whether or not the route is suppressed, and if so why:
            suppressedByNothing       - Route is not suppressed.
            suppressedByAggregate     - Route is suppressed by a summary-only
                                        aggregate.
            suppressedByAutoSummary   - Route is suppressed by an auto-summary.
            suppressedByDampening     - Route is suppressed as a result of
                                        route-flap dampening."
    ::= { usdBgpNewRouteEntry 31 }

usdBgpNewRouteNextHopReachable OBJECT-TYPE
    SYNTAX      TruthValue
    MAX-ACCESS  read-only
    STATUS      current
    DESCRIPTION
        "Is the indirect next-hop of the route reachable (i.e. can the indirect
        next-hop of the route be resolved to at least one direct next-hop)?"
    ::= { usdBgpNewRouteEntry 32 }

usdBgpNewRouteSynchronizedWithIgp OBJECT-TYPE
    SYNTAX      TruthValue
    MAX-ACCESS  read-only
    STATUS      current
    DESCRIPTION
        "Is the route is synchronized (i.e. is there is an IGP route to the same
        prefix in the IP route table)?"
    ::= { usdBgpNewRouteEntry 33 }

usdBgpNewRoutePlaceInIpRouteTable OBJECT-TYPE
    SYNTAX      TruthValue
    MAX-ACCESS  read-only
    STATUS      current
    DESCRIPTION
        "Has a BGP route for this prefix been placed in the IP route table?"
    ::= { usdBgpNewRouteEntry 34 }

usdBgpNewRouteAdvertiseToExternalPeers OBJECT-TYPE
    SYNTAX      TruthValue
    MAX-ACCESS  read-only
    STATUS      current
    DESCRIPTION
        "Should this route be advertised to external peers?"
    ::= { usdBgpNewRouteEntry 35 }

usdBgpNewRouteAdvertiseToInternalPeers OBJECT-TYPE
    SYNTAX      TruthValue
    MAX-ACCESS  read-only
    STATUS      current
    DESCRIPTION
        "Should this route be advertised to internal peers?"
    ::= { usdBgpNewRouteEntry 36 }

usdBgpNewRouteMplsLabel OBJECT-TYPE
    SYNTAX      Unsigned32
    MAX-ACCESS  read-only
    STATUS      current
    DESCRIPTION
        "The MPLS label for the route."
    ::= { usdBgpNewRouteEntry 37 }

usdBgpNewRouteNextHopMetric OBJECT-TYPE
    SYNTAX      Unsigned32
    MAX-ACCESS  read-only
    STATUS      current
    DESCRIPTION
        "The metric of direct next-hop of this BGP route."
    ::= { usdBgpNewRouteEntry 38 }


--
--  BGP New Route Flap History Table
--
usdBgpNewRouteFlapHistoryTable OBJECT-TYPE
    SYNTAX      SEQUENCE OF UsdBgpNewRouteFlapHistoryEntry
    MAX-ACCESS  not-accessible
    STATUS      current
    DESCRIPTION
        "The BGP Route Flap History Table contains information about recorded
        route flap events."
    ::= { usdBgpObjects 24 }

usdBgpNewRouteFlapHistoryEntry OBJECT-TYPE
    SYNTAX      UsdBgpNewRouteFlapHistoryEntry
    MAX-ACCESS  not-accessible
    STATUS      current
    DESCRIPTION
        "An instance in the list of route flap events."
    INDEX     { usdBgpNewRouteVrfName,
                usdBgpNewRouteAfi,
                usdBgpNewRouteSafi,
                usdBgpNewRouteIpAddrPrefix,
                usdBgpNewRouteIpAddrPrefixLen,
                usdBgpNewRouteDistinguisher,
                usdBgpNewRoutePeer,
                usdBgpNewRouteRouteType,
                usdBgpNewRouteOriginalRd }
    ::= { usdBgpNewRouteFlapHistoryTable 1 }

UsdBgpNewRouteFlapHistoryEntry ::= SEQUENCE {
    usdBgpNewRouteFlapState                 INTEGER,
    usdBgpNewRouteFlapFigureOfMerit         Unsigned32,
    usdBgpNewRouteFlapRemainingTime         Unsigned32,
    usdBgpNewRouteFlapSuppressThreshold     Unsigned32,
    usdBgpNewRouteFlapReuseThreshold        Unsigned32,
    usdBgpNewRouteFlapMaxHoldDownTime       Unsigned32,
    usdBgpNewRouteFlapHalfLifeReachable     Unsigned32,
    usdBgpNewRouteFlapHalfLifeUnreachable   Unsigned32 }

usdBgpNewRouteFlapState OBJECT-TYPE
    SYNTAX      INTEGER {
                    stateAvailable(1),
                    stateSuppressedReachable(2),
                    stateSuppressedUnreachable(3) }
    MAX-ACCESS  read-only
    STATUS      current
    DESCRIPTION
        "Current state:
            stateAvailable(1)             - indicates path is available
            stateSuppressedReachable(2)   - indicates path is suppressed,
                                            destination is reachable
            stateSuppressedUnreachable(3) - indicates path in suppressed,
                                            destination is not reachable "
    ::= { usdBgpNewRouteFlapHistoryEntry 1 }

usdBgpNewRouteFlapFigureOfMerit OBJECT-TYPE
    SYNTAX      Unsigned32
    MAX-ACCESS  read-only
    STATUS      current
    DESCRIPTION
        "Calculated figure-of-merit."
    ::= { usdBgpNewRouteFlapHistoryEntry 2 }

usdBgpNewRouteFlapRemainingTime OBJECT-TYPE
    SYNTAX      Unsigned32
    UNITS       "seconds"
    MAX-ACCESS  read-only
    STATUS      current
    DESCRIPTION
        "Number of seconds until reuse or removal."
    ::= { usdBgpNewRouteFlapHistoryEntry 3 }

usdBgpNewRouteFlapSuppressThreshold OBJECT-TYPE
    SYNTAX      Unsigned32
    MAX-ACCESS  read-only
    STATUS      current
    DESCRIPTION
        "Damping cutoff threshold (scaled)."
    ::= { usdBgpNewRouteFlapHistoryEntry 4 }

usdBgpNewRouteFlapReuseThreshold OBJECT-TYPE
    SYNTAX      Unsigned32
    MAX-ACCESS  read-only
    STATUS      current
    DESCRIPTION
        "Damping reuse threshold (scaled)."
    ::= { usdBgpNewRouteFlapHistoryEntry 5 }

usdBgpNewRouteFlapMaxHoldDownTime OBJECT-TYPE
    SYNTAX      Unsigned32
    UNITS       "seconds"
    MAX-ACCESS  read-only
    STATUS      current
    DESCRIPTION
        "Maximum route holddown time (seconds)."
    ::= { usdBgpNewRouteFlapHistoryEntry 6 }

usdBgpNewRouteFlapHalfLifeReachable OBJECT-TYPE
    SYNTAX      Unsigned32
    UNITS       "seconds"
    MAX-ACCESS  read-only
    STATUS      current
    DESCRIPTION
        "Figure of merit half life for reachable routes (seconds)."
    ::= { usdBgpNewRouteFlapHistoryEntry 7 }

usdBgpNewRouteFlapHalfLifeUnreachable OBJECT-TYPE
    SYNTAX      Unsigned32
    UNITS       "seconds"
    MAX-ACCESS  read-only
    STATUS      current
    DESCRIPTION
        "Figure of merit half life for unreachable routes (seconds)."
    ::= { usdBgpNewRouteFlapHistoryEntry 8 }


--
--  BGP 4 New Route Community Table
--
usdBgpNewRouteCommunityTable OBJECT-TYPE
    SYNTAX      SEQUENCE OF UsdBgpNewRouteCommunityEntry
    MAX-ACCESS  not-accessible
    STATUS      current
    DESCRIPTION
        "The BGP-4 Path Community Table contains information about communities
        within destination networks received from all BGP4 peers."
    ::= { usdBgpObjects 25 }

usdBgpNewRouteCommunityEntry OBJECT-TYPE
    SYNTAX      UsdBgpNewRouteCommunityEntry
    MAX-ACCESS  not-accessible
    STATUS      current
    DESCRIPTION
        "Community attribute information within a path to a network."
    INDEX     { usdBgpNewRouteVrfName,
                usdBgpNewRouteAfi,
                usdBgpNewRouteSafi,
                usdBgpNewRouteIpAddrPrefix,
                usdBgpNewRouteIpAddrPrefixLen,
                usdBgpNewRouteDistinguisher,
                usdBgpNewRoutePeer,
                usdBgpNewRouteRouteType,
                usdBgpNewRouteOriginalRd,
                usdBgpNewRouteCommunityNumber }
    ::= { usdBgpNewRouteCommunityTable 1 }

UsdBgpNewRouteCommunityEntry ::= SEQUENCE {
    usdBgpNewRouteCommunityNumber   Unsigned32 }

usdBgpNewRouteCommunityNumber OBJECT-TYPE
    SYNTAX      Unsigned32
    MAX-ACCESS  read-only
    STATUS      current
    DESCRIPTION
        "The community number."
    ::= { usdBgpNewRouteCommunityEntry 1 }


--
--  BGP 4 New Route Extended Community Table
--
usdBgpNewRouteExtendedCommunityTable OBJECT-TYPE
    SYNTAX      SEQUENCE OF UsdBgpNewRouteExtendedCommunityEntry
    MAX-ACCESS  not-accessible
    STATUS      current
    DESCRIPTION
        "The BGP-4 Path Extended Community Table contains information about
        communities within destination networks received from all BGP4 peers."
    ::= { usdBgpObjects 26 }

usdBgpNewRouteExtendedCommunityEntry OBJECT-TYPE
    SYNTAX      UsdBgpNewRouteExtendedCommunityEntry
    MAX-ACCESS  not-accessible
    STATUS      current
    DESCRIPTION
        "Extended Community attribute information within a path to a network."
    INDEX     { usdBgpNewRouteVrfName,
                usdBgpNewRouteAfi,
                usdBgpNewRouteSafi,
                usdBgpNewRouteIpAddrPrefix,
                usdBgpNewRouteIpAddrPrefixLen,
                usdBgpNewRouteDistinguisher,
                usdBgpNewRoutePeer,
                usdBgpNewRouteRouteType,
                usdBgpNewRouteOriginalRd,
                usdBgpNewRouteExtendedCommunityNumber }
    ::= { usdBgpNewRouteExtendedCommunityTable 1 }

UsdBgpNewRouteExtendedCommunityEntry ::= SEQUENCE {
    usdBgpNewRouteExtendedCommunityNumber   OCTET STRING }

usdBgpNewRouteExtendedCommunityNumber OBJECT-TYPE
    SYNTAX      OCTET STRING (SIZE(8))
    MAX-ACCESS  read-only
    STATUS      current
    DESCRIPTION
        "The extended community number."
    ::= { usdBgpNewRouteExtendedCommunityEntry 1 }


--
--  BGP 4 New Route ClusterId Table
--
usdBgpNewRouteClusterIdTable OBJECT-TYPE
    SYNTAX      SEQUENCE OF UsdBgpNewRouteClusterIdEntry
    MAX-ACCESS  not-accessible
    STATUS      current
    DESCRIPTION
        "The BGP-4 Path ClusterId Table contains information about router
        reflector cluster IDs."
    ::= { usdBgpObjects 27 }

usdBgpNewRouteClusterIdEntry OBJECT-TYPE
    SYNTAX      UsdBgpNewRouteClusterIdEntry
    MAX-ACCESS  not-accessible
    STATUS      current
    DESCRIPTION
        "ClusterId attribute information within a path to a network."
    INDEX     { usdBgpNewRouteVrfName,
                usdBgpNewRouteAfi,
                usdBgpNewRouteSafi,
                usdBgpNewRouteIpAddrPrefix,
                usdBgpNewRouteIpAddrPrefixLen,
                usdBgpNewRouteDistinguisher,
                usdBgpNewRoutePeer,
                usdBgpNewRouteRouteType,
                usdBgpNewRouteOriginalRd,
                usdBgpNewRouteClusterId }
    ::= { usdBgpNewRouteClusterIdTable 1 }

UsdBgpNewRouteClusterIdEntry ::= SEQUENCE {
    usdBgpNewRouteClusterId Unsigned32 }

usdBgpNewRouteClusterId OBJECT-TYPE
    SYNTAX      Unsigned32
    MAX-ACCESS  read-only
    STATUS      current
    DESCRIPTION
        "The cluster ID."
    ::= { usdBgpNewRouteClusterIdEntry 1 }


-- +++++++++++++++++++++++++++++++++++++++++++++++++++++++++++++++++++++++++++++
-- Obsolete tables
-- +++++++++++++++++++++++++++++++++++++++++++++++++++++++++++++++++++++++++++++
-- Following tables have been obsoleted by their new version above.

-- +++++++++++++++++++++++++++++++++++++++++++++++++++++++++++++++++++++++++++++
-- BGP Route attributes
-- +++++++++++++++++++++++++++++++++++++++++++++++++++++++++++++++++++++++++++++
--
--  Obsolete BGP Route Attribute Table
--
usdBgpRouteTable OBJECT-TYPE
    SYNTAX      SEQUENCE OF UsdBgpRouteEntry
    MAX-ACCESS  not-accessible
    STATUS      obsolete
    DESCRIPTION
        "The obsolete BGP-4 Received Path Attribute Table contained additional
        information about paths to destination networks received from all BGP4
        peers.  This table has been replaced by the usdBgpNewRouteTable."
    ::= { usdBgpObjects 13 }

usdBgpRouteEntry OBJECT-TYPE
    SYNTAX      UsdBgpRouteEntry
    MAX-ACCESS  not-accessible
    STATUS      obsolete
    DESCRIPTION
        "Additional information about a path to a network."
    INDEX     { usdBgpRouteVrfName,
                usdBgpRouteAfi,
                usdBgpRouteSafi,
                usdBgpRouteIpAddrPrefix,
                usdBgpRouteIpAddrPrefixLen,
                usdBgpRouteDistinguisher,
                usdBgpRoutePeer,
                usdBgpRouteRouteType }
    ::= { usdBgpRouteTable 1 }

UsdBgpRouteEntry ::= SEQUENCE {
    usdBgpRouteOriginatorId                 IpAddress,
    usdBgpRouteAtomicAggregatePresent       TruthValue,
    usdBgpRouteMedPresent                   TruthValue,
    usdBgpRouteLocalPrefPresent             TruthValue,
    usdBgpRouteAggregatorPresent            TruthValue,
    usdBgpRouteCommunitiesPresent           TruthValue,
    usdBgpRouteOriginatorIdPresent          TruthValue,
    usdBgpRouteClusterListPresent           TruthValue,
    usdBgpRouteWeight                       Unsigned32,
    usdBgpRouteVrfName                      UsdVrfName,
    usdBgpRouteAfi                          UsdBgpAfi,
    usdBgpRouteSafi                         UsdBgpSafi,
    usdBgpRoutePeer                         IpAddress,
    usdBgpRouteIpAddrPrefixLen              INTEGER,
    usdBgpRouteIpAddrPrefix                 IpAddress,
    usdBgpRouteRouteType                    INTEGER,
    usdBgpRouteOrigin                       INTEGER,
    usdBgpRouteASPathSegment                OCTET STRING,
    usdBgpRouteNextHop                      IpAddress,
    usdBgpRouteMultiExitDisc                Unsigned32,
    usdBgpRouteLocalPref                    Unsigned32,
    usdBgpRouteAtomicAggregate              INTEGER,
    usdBgpRouteAggregatorAS                 INTEGER,
    usdBgpRouteAggregatorAddress            IpAddress,
    usdBgpRouteBestInIpRouteTable           TruthValue,
    usdBgpRouteUnknown                      OCTET STRING,
    usdBgpRouteExtendedCommunitiesPresent   TruthValue,
    usdBgpRouteValid                        TruthValue,
    usdBgpRouteSuppressedBy                 INTEGER,
    usdBgpRouteNextHopReachable             TruthValue,
    usdBgpRouteSynchronizedWithIgp          TruthValue,
    usdBgpRoutePlaceInIpRouteTable          TruthValue,
    usdBgpRouteAdvertiseToExternalPeers     TruthValue,
    usdBgpRouteAdvertiseToInternalPeers     TruthValue,
    usdBgpRouteDistinguisher                OCTET STRING,
    usdBgpRouteMplsLabel                    Unsigned32,
    usdBgpRouteNextHopMetric                Unsigned32 }

usdBgpRouteOriginatorId OBJECT-TYPE
    SYNTAX      IpAddress
    MAX-ACCESS  read-only
    STATUS      obsolete
    DESCRIPTION
        "The Originator-ID path attribute of the route if present.  The
        usdBgpRouteOriginatorIdPresent object indicates whether the Originator-ID
        path attribute is present."
    ::= { usdBgpRouteEntry 1 }

usdBgpRouteAtomicAggregatePresent OBJECT-TYPE
    SYNTAX      TruthValue
    MAX-ACCESS  read-only
    STATUS      obsolete
    DESCRIPTION
        "Atomic-Aggregate path attribute is present."
    ::= { usdBgpRouteEntry 2 }

usdBgpRouteMedPresent OBJECT-TYPE
    SYNTAX      TruthValue
    MAX-ACCESS  read-only
    STATUS      obsolete
    DESCRIPTION
        "The Multi-Exit-Discriminator path attribute is present."
    ::= { usdBgpRouteEntry 3 }

usdBgpRouteLocalPrefPresent OBJECT-TYPE
    SYNTAX      TruthValue
    MAX-ACCESS  read-only
    STATUS      obsolete
    DESCRIPTION
        "The Local-Pref path attribute is present."
    ::= { usdBgpRouteEntry 4 }

usdBgpRouteAggregatorPresent OBJECT-TYPE
    SYNTAX      TruthValue
    MAX-ACCESS  read-only
    STATUS      obsolete
    DESCRIPTION
        "The Aggregator path attribute is present."
    ::= { usdBgpRouteEntry 5 }

usdBgpRouteCommunitiesPresent OBJECT-TYPE
    SYNTAX      TruthValue
    MAX-ACCESS  read-only
    STATUS      obsolete
    DESCRIPTION
        "The Communities path attribute is present."
    ::= { usdBgpRouteEntry 6 }

usdBgpRouteOriginatorIdPresent OBJECT-TYPE
    SYNTAX      TruthValue
    MAX-ACCESS  read-only
    STATUS      obsolete
    DESCRIPTION
        "The Originator-ID path attribute is present."
    ::= { usdBgpRouteEntry 7 }

usdBgpRouteClusterListPresent OBJECT-TYPE
    SYNTAX      TruthValue
    MAX-ACCESS  read-only
    STATUS      obsolete
    DESCRIPTION
        "The Cluster-List path attribute is present."
    ::= { usdBgpRouteEntry 8 }

usdBgpRouteWeight OBJECT-TYPE
    SYNTAX      Unsigned32
    MAX-ACCESS  read-only
    STATUS      obsolete
    DESCRIPTION
        "The weight of the route."
    ::= { usdBgpRouteEntry 9 }

usdBgpRouteVrfName OBJECT-TYPE
    SYNTAX      UsdVrfName
    MAX-ACCESS  not-accessible
    STATUS      obsolete
    DESCRIPTION
        "The name of the VPN Routing Forwarding (VRF) instance in which this
        route is present.  The empty string indicates that this route is not in
        a VRF."
    ::= { usdBgpRouteEntry 10 }

usdBgpRouteAfi OBJECT-TYPE
    SYNTAX      UsdBgpAfi
    MAX-ACCESS  not-accessible
    STATUS      obsolete
    DESCRIPTION
        "The AFI of the address-family in which this route is present."
    ::= { usdBgpRouteEntry 11 }

usdBgpRouteSafi OBJECT-TYPE
    SYNTAX      UsdBgpSafi
    MAX-ACCESS  not-accessible
    STATUS      obsolete
    DESCRIPTION
        "The SAFI of the address-family in which this route is present."
    ::= { usdBgpRouteEntry 12 }

usdBgpRoutePeer OBJECT-TYPE
    SYNTAX      IpAddress
    MAX-ACCESS  not-accessible
    STATUS      obsolete
    DESCRIPTION
        "The IP address of the peer from which the route was received.  This
        object has value 0.0.0.0 is the route was a locally originated route."
    ::= { usdBgpRouteEntry 13 }

usdBgpRouteIpAddrPrefixLen OBJECT-TYPE
    SYNTAX      INTEGER (0..32)
    MAX-ACCESS  not-accessible
    STATUS      obsolete
    DESCRIPTION
        "Length in bits of the IP address prefix of the route."
    ::= { usdBgpRouteEntry 14 }

usdBgpRouteIpAddrPrefix OBJECT-TYPE
    SYNTAX      IpAddress
    MAX-ACCESS  not-accessible
    STATUS      obsolete
    DESCRIPTION
        "The IP address prefix of the route.  This object is an IP address
        containing the prefix with length specified by
        usdBgpNewRouteIpAddrPrefixLen.  Any bits beyond the length specified by
        usdBgpNewRouteIpAddrPrefixLen are zeroed."
    ::= { usdBgpRouteEntry 15 }

usdBgpRouteRouteType OBJECT-TYPE
    SYNTAX      INTEGER {
                    routeTypeReceived(1),
                    routeTypeNetwork(2),
                    routeTypeRedistributed(3),
                    routeTypeAggregate(4),
                    routeTypeAutoSummary(5) }
    MAX-ACCESS  not-accessible
    STATUS      obsolete
    DESCRIPTION
        "The type of the route."
    ::= { usdBgpRouteEntry 16 }

usdBgpRouteOrigin OBJECT-TYPE
    SYNTAX      INTEGER {
                    igp(1),
                    egp(2),
                    incomplete(3) }
    MAX-ACCESS  read-only
    STATUS      obsolete
    DESCRIPTION
        "The value of the Origin path attribute."
    ::= { usdBgpRouteEntry 17 }

usdBgpRouteASPathSegment OBJECT-TYPE
    SYNTAX      OCTET STRING (SIZE(2..255))
    MAX-ACCESS  read-only
    STATUS      obsolete
    DESCRIPTION
        "The value of the AS-path path attribute (as encoded in the received
        update message)."
    ::= { usdBgpRouteEntry 18 }

usdBgpRouteNextHop OBJECT-TYPE
    SYNTAX      IpAddress
    MAX-ACCESS  read-only
    STATUS      obsolete
    DESCRIPTION
        "The value of the Next-Hop path attribute."
    ::= { usdBgpRouteEntry 19 }

usdBgpRouteMultiExitDisc OBJECT-TYPE
    SYNTAX      Unsigned32
    MAX-ACCESS  read-only
    STATUS      obsolete
    DESCRIPTION
        "The value of the Multi-Exit-Discriminator path attribute if present.
        The usdBgpRouteMedPresent object indicates whether the
        Multi-Exit-Discriminator path attribute is present."
    ::= { usdBgpRouteEntry 20 }

usdBgpRouteLocalPref OBJECT-TYPE
    SYNTAX      Unsigned32
    MAX-ACCESS  read-only
    STATUS      obsolete
    DESCRIPTION
        "The value of the Local-Pref path attribute if present.  The
        usdBgpRouteLocalPrefPresent object indicates whether the Local-Pref path
        attribute is present."
    ::= { usdBgpRouteEntry 21 }

usdBgpRouteAtomicAggregate OBJECT-TYPE
    SYNTAX      INTEGER {
                    lessSpecificRouteNotSelected(1),
                    lessSpecificRouteSelected(2) }
    MAX-ACCESS  read-only
    STATUS      obsolete
    DESCRIPTION
        "Whether or not the local system has selected a less specific route
        without selecting a more specific route."
    ::= { usdBgpRouteEntry 22 }

usdBgpRouteAggregatorAS OBJECT-TYPE
    SYNTAX      INTEGER (0..65535)
    MAX-ACCESS  read-only
    STATUS      obsolete
    DESCRIPTION
        "The value of the AS field in the Aggregator path attribute if present.
        The usdBgpRouteAggregatorPresent object indicates whether the Aggregator
        path attribute is present."
    ::= { usdBgpRouteEntry 23 }

usdBgpRouteAggregatorAddress OBJECT-TYPE
    SYNTAX      IpAddress
    MAX-ACCESS  read-only
    STATUS      obsolete
    DESCRIPTION
        "The value of the address field in the Aggregator path attribute if
        present.  The usdBgpRouteAggregatorPresent object indicates whether the
        Aggregator path attribute is present."
    ::= { usdBgpRouteEntry 24 }

usdBgpRouteBestInIpRouteTable OBJECT-TYPE
    SYNTAX      TruthValue
    MAX-ACCESS  read-only
    STATUS      obsolete
    DESCRIPTION
        "When BGP places a routes in the IP route table, that route may not be
        used for forwarding traffic if there are other routes (e.g. IGP routes
        or static routes) to that same prefix with a better administrative
        distance in the IP route table.  This object indicates whether or not
        the BGP route in the IP route table is the best route (and hence is used
        for forwarding traffic)."
    ::= { usdBgpRouteEntry 25 }

usdBgpRouteUnknown OBJECT-TYPE
    SYNTAX      OCTET STRING (SIZE(0..255))
    MAX-ACCESS  read-only
    STATUS      obsolete
    DESCRIPTION
        "One or more path attributes not understood by this BGP4 speaker.  Size
        zero (0) indicates the absence of such attribute(s).  Octets beyond the
        maximum size, if any, are not recorded by this object."
    ::= { usdBgpRouteEntry 26 }

usdBgpRouteExtendedCommunitiesPresent OBJECT-TYPE
    SYNTAX      TruthValue
    MAX-ACCESS  read-only
    STATUS      obsolete
    DESCRIPTION
        "Is the Extended-Communities path attribute present?"
    ::= { usdBgpRouteEntry 27 }

usdBgpRouteValid OBJECT-TYPE
    SYNTAX      TruthValue
    MAX-ACCESS  read-only
    STATUS      obsolete
    DESCRIPTION
        "Is the route valid?  The route is declared invalid if there is
        something wrong with it which is not serious enough for sending a
        notification, but it serious enough for not placing it in the IP route
        table or propagating it to other peers (for example the next-hop of the
        route is a local address)."
    ::= { usdBgpRouteEntry 28 }

usdBgpRouteSuppressedBy OBJECT-TYPE
    SYNTAX      INTEGER {
                    suppressedByNothing(1),
                    suppressedByAggregate(2),
                    suppressedByAutoSummary(3),
                    suppressedByDampening(4) }
    MAX-ACCESS  read-only
    STATUS      obsolete
    DESCRIPTION
        "Indicates whether or not the route is suppressed, and if so why:
            suppressedByNothing       - Route is not suppressed.
            suppressedByAggregate     - Route is suppressed by a summary-only
                                        aggregate.
            suppressedByAutoSummary   - Route is suppressed by an auto-summary.
            suppressedByDampening     - Route is suppressed as a result of
                                        route-flap dampening."
    ::= { usdBgpRouteEntry 29 }

usdBgpRouteNextHopReachable OBJECT-TYPE
    SYNTAX      TruthValue
    MAX-ACCESS  read-only
    STATUS      obsolete
    DESCRIPTION
        "Is the indirect next-hop of the route reachable (i.e. can the indirect
        next-hop of the route be resolved to at least one direct next-hop)?"
    ::= { usdBgpRouteEntry 30 }

usdBgpRouteSynchronizedWithIgp OBJECT-TYPE
    SYNTAX      TruthValue
    MAX-ACCESS  read-only
    STATUS      obsolete
    DESCRIPTION
        "Is the route is synchronized (i.e. is there is an IGP route to the same
        prefix in the IP route table)?"
    ::= { usdBgpRouteEntry 31 }

usdBgpRoutePlaceInIpRouteTable OBJECT-TYPE
    SYNTAX      TruthValue
    MAX-ACCESS  read-only
    STATUS      obsolete
    DESCRIPTION
        "Has a BGP route for this prefix been placed in the IP route table?"
    ::= { usdBgpRouteEntry 32 }

usdBgpRouteAdvertiseToExternalPeers OBJECT-TYPE
    SYNTAX      TruthValue
    MAX-ACCESS  read-only
    STATUS      obsolete
    DESCRIPTION
        "Should this route be advertised to external peers?"
    ::= { usdBgpRouteEntry 33 }

usdBgpRouteAdvertiseToInternalPeers OBJECT-TYPE
    SYNTAX      TruthValue
    MAX-ACCESS  read-only
    STATUS      obsolete
    DESCRIPTION
        "Should this route be advertised to internal peers?"
    ::= { usdBgpRouteEntry 34 }

usdBgpRouteDistinguisher OBJECT-TYPE
    SYNTAX      OCTET STRING (SIZE(8))
    MAX-ACCESS  read-only
    STATUS      obsolete
    DESCRIPTION
        "The Route Distinguisher (RD) of the route.  This object has an
        undefined value for non-VPN routes."
    ::= { usdBgpRouteEntry 35 }

usdBgpRouteMplsLabel OBJECT-TYPE
    SYNTAX      Unsigned32
    MAX-ACCESS  read-only
    STATUS      obsolete
    DESCRIPTION
        "The MPLS label for the route."
    ::= { usdBgpRouteEntry 36 }

usdBgpRouteNextHopMetric OBJECT-TYPE
    SYNTAX      Unsigned32
    MAX-ACCESS  read-only
    STATUS      obsolete
    DESCRIPTION
        "The metric of direct next-hop of this BGP route."
    ::= { usdBgpRouteEntry 37 }


--
--  Obsolete BGP Route Flap History Table
--
usdBgpRouteFlapHistoryTable OBJECT-TYPE
    SYNTAX      SEQUENCE OF UsdBgpRouteFlapHistoryEntry
    MAX-ACCESS  not-accessible
    STATUS      obsolete
    DESCRIPTION
        "The obsolete BGP Route Flap History Table contained information about
        recorded route flap events.  This table has been replaced by the
        usdBgpNewRouteFlapHistoryTable."
    ::= { usdBgpObjects 12 }

usdBgpRouteFlapHistoryEntry OBJECT-TYPE
    SYNTAX      UsdBgpRouteFlapHistoryEntry
    MAX-ACCESS  not-accessible
    STATUS      obsolete
    DESCRIPTION
        "An instance in the list of route flap events."
    INDEX     { usdBgpRouteVrfName,
                usdBgpRouteAfi,
                usdBgpRouteSafi,
                usdBgpRouteIpAddrPrefix,
                usdBgpRouteIpAddrPrefixLen,
                usdBgpRouteDistinguisher,
                usdBgpRoutePeer,
                usdBgpRouteRouteType }
    ::= { usdBgpRouteFlapHistoryTable 1 }

UsdBgpRouteFlapHistoryEntry ::= SEQUENCE {
    usdBgpRouteFlapState                INTEGER,
    usdBgpRouteFlapFigureOfMerit        Unsigned32,
    usdBgpRouteFlapRemainingTime        Unsigned32,
    usdBgpRouteFlapSuppressThreshold    Unsigned32,
    usdBgpRouteFlapReuseThreshold       Unsigned32,
    usdBgpRouteFlapMaxHoldDownTime      Unsigned32,
    usdBgpRouteFlapHalfLifeReachable    Unsigned32,
    usdBgpRouteFlapHalfLifeUnreachable  Unsigned32 }

usdBgpRouteFlapState OBJECT-TYPE
    SYNTAX      INTEGER {
                    stateAvailable(1),
                    stateSuppressedReachable(2),
                    stateSuppressedUnreachable(3) }
    MAX-ACCESS  read-only
    STATUS      obsolete
    DESCRIPTION
        "Current state:
            stateAvailable(1)             - indicates path is available
            stateSuppressedReachable(2)   - indicates path is suppressed,
                                            destination is reachable
            stateSuppressedUnreachable(3) - indicates path in suppressed,
                                            destination is not reachable "
    ::= { usdBgpRouteFlapHistoryEntry 1 }

usdBgpRouteFlapFigureOfMerit OBJECT-TYPE
    SYNTAX      Unsigned32
    MAX-ACCESS  read-only
    STATUS      obsolete
    DESCRIPTION
        "Calculated figure-of-merit."
    ::= { usdBgpRouteFlapHistoryEntry 2 }

usdBgpRouteFlapRemainingTime OBJECT-TYPE
    SYNTAX      Unsigned32
    UNITS       "seconds"
    MAX-ACCESS  read-only
    STATUS      obsolete
    DESCRIPTION
        "Number of seconds until reuse or removal."
    ::= { usdBgpRouteFlapHistoryEntry 3 }

usdBgpRouteFlapSuppressThreshold OBJECT-TYPE
    SYNTAX      Unsigned32
    MAX-ACCESS  read-only
    STATUS      obsolete
    DESCRIPTION
        "Damping cutoff threshold (scaled)."
    ::= { usdBgpRouteFlapHistoryEntry 4 }

usdBgpRouteFlapReuseThreshold OBJECT-TYPE
    SYNTAX      Unsigned32
    MAX-ACCESS  read-only
    STATUS      obsolete
    DESCRIPTION
        "Damping reuse threshold (scaled)."
    ::= { usdBgpRouteFlapHistoryEntry 5 }

usdBgpRouteFlapMaxHoldDownTime OBJECT-TYPE
    SYNTAX      Unsigned32
    UNITS       "seconds"
    MAX-ACCESS  read-only
    STATUS      obsolete
    DESCRIPTION
        "Maximum route holddown time (seconds)."
    ::= { usdBgpRouteFlapHistoryEntry 6 }

usdBgpRouteFlapHalfLifeReachable OBJECT-TYPE
    SYNTAX      Unsigned32
    UNITS       "seconds"
    MAX-ACCESS  read-only
    STATUS      obsolete
    DESCRIPTION
        "Figure of merit half life for reachable routes (seconds)."
    ::= { usdBgpRouteFlapHistoryEntry 7 }

usdBgpRouteFlapHalfLifeUnreachable OBJECT-TYPE
    SYNTAX      Unsigned32
    UNITS       "seconds"
    MAX-ACCESS  read-only
    STATUS      obsolete
    DESCRIPTION
        "Figure of merit half life for unreachable routes (seconds)."
    ::= { usdBgpRouteFlapHistoryEntry 8 }


--
--  Obsolete BGP 4 Route Community Table
--
usdBgpRouteCommunityTable OBJECT-TYPE
    SYNTAX      SEQUENCE OF UsdBgpRouteCommunityEntry
    MAX-ACCESS  not-accessible
    STATUS      obsolete
    DESCRIPTION
        "The obsolete BGP-4 Path Community Table contained information about
        communities within destination networks received from all BGP4 peers.
        This table has been replaced by the usdBgpNewRouteCommunityTable."
    ::= { usdBgpObjects 14 }

usdBgpRouteCommunityEntry OBJECT-TYPE
    SYNTAX      UsdBgpRouteCommunityEntry
    MAX-ACCESS  not-accessible
    STATUS      obsolete
    DESCRIPTION
        "Community attribute information within a path to a network."
    INDEX     { usdBgpRouteVrfName,
                usdBgpRouteAfi,
                usdBgpRouteSafi,
                usdBgpRouteIpAddrPrefix,
                usdBgpRouteIpAddrPrefixLen,
                usdBgpRouteDistinguisher,
                usdBgpRoutePeer,
                usdBgpRouteRouteType,
                usdBgpRouteCommunityNumber }
    ::= { usdBgpRouteCommunityTable 1 }

UsdBgpRouteCommunityEntry ::= SEQUENCE {
    usdBgpRouteCommunityNumber  Unsigned32 }

usdBgpRouteCommunityNumber OBJECT-TYPE
    SYNTAX      Unsigned32
    MAX-ACCESS  read-only
    STATUS      obsolete
    DESCRIPTION
        "The community number."
    ::= { usdBgpRouteCommunityEntry 1 }


--
--  Obsolete BGP 4 Route Extended Community Table
--
usdBgpRouteExtendedCommunityTable OBJECT-TYPE
    SYNTAX      SEQUENCE OF UsdBgpRouteExtendedCommunityEntry
    MAX-ACCESS  not-accessible
    STATUS      obsolete
    DESCRIPTION
        "The obsolete BGP-4 Path Extended Community Table contained information
        about communities within destination networks received from all BGP4
        peers.  This table has been replaced by the
        usdBgpNewRouteExtendedCommunityTable."
    ::= { usdBgpObjects 22 }

usdBgpRouteExtendedCommunityEntry OBJECT-TYPE
    SYNTAX      UsdBgpRouteExtendedCommunityEntry
    MAX-ACCESS  not-accessible
    STATUS      obsolete
    DESCRIPTION
        "Extended Community attribute information within a path to a network."
    INDEX     { usdBgpRouteVrfName,
                usdBgpRouteAfi,
                usdBgpRouteSafi,
                usdBgpRouteIpAddrPrefix,
                usdBgpRouteIpAddrPrefixLen,
                usdBgpRouteDistinguisher,
                usdBgpRoutePeer,
                usdBgpRouteRouteType,
                usdBgpRouteExtendedCommunityNumber }
    ::= { usdBgpRouteExtendedCommunityTable 1 }

UsdBgpRouteExtendedCommunityEntry ::= SEQUENCE {
    usdBgpRouteExtendedCommunityNumber  OCTET STRING }

usdBgpRouteExtendedCommunityNumber OBJECT-TYPE
    SYNTAX      OCTET STRING (SIZE(8))
    MAX-ACCESS  read-only
    STATUS      obsolete
    DESCRIPTION
        "The extended community number."
    ::= { usdBgpRouteExtendedCommunityEntry 1 }


--
--  Obsolete BGP 4 Route ClusterId Table
--
usdBgpRouteClusterIdTable OBJECT-TYPE
    SYNTAX      SEQUENCE OF UsdBgpRouteClusterIdEntry
    MAX-ACCESS  not-accessible
    STATUS      obsolete
    DESCRIPTION
        "The obsolete BGP-4 Path ClusterId Table contained information about
        router reflector cluster IDs.  This table has been replaced by the
        usdBgpNewRouteClusterIdTable."
    ::= { usdBgpObjects 15 }

usdBgpRouteClusterIdEntry OBJECT-TYPE
    SYNTAX      UsdBgpRouteClusterIdEntry
    MAX-ACCESS  not-accessible
    STATUS      obsolete
    DESCRIPTION
        "ClusterId attribute information within a path to a network."
    INDEX     { usdBgpRouteVrfName,
                usdBgpRouteAfi,
                usdBgpRouteSafi,
                usdBgpRouteIpAddrPrefix,
                usdBgpRouteIpAddrPrefixLen,
                usdBgpRouteDistinguisher,
                usdBgpRoutePeer,
                usdBgpRouteRouteType,
                usdBgpRouteClusterId }
    ::= { usdBgpRouteClusterIdTable 1 }

UsdBgpRouteClusterIdEntry ::= SEQUENCE {
    usdBgpRouteClusterId    Unsigned32 }

usdBgpRouteClusterId OBJECT-TYPE
    SYNTAX      Unsigned32
    MAX-ACCESS  read-only
    STATUS      obsolete
    DESCRIPTION
        "The cluster id."
    ::= { usdBgpRouteClusterIdEntry 1 }


-- +++++++++++++++++++++++++++++++++++++++++++++++++++++++++++++++++++++++++++++
-- Notifications
-- +++++++++++++++++++++++++++++++++++++++++++++++++++++++++++++++++++++++++++++
-- No notifications are defined in this MIB.


-- +++++++++++++++++++++++++++++++++++++++++++++++++++++++++++++++++++++++++++++
-- Conformance information
-- +++++++++++++++++++++++++++++++++++++++++++++++++++++++++++++++++++++++++++++
usdBgpConformance OBJECT IDENTIFIER ::= { usdBgpMIB 2 }
usdBgpCompliances OBJECT IDENTIFIER ::= { usdBgpConformance 1 }
usdBgpConfGroups  OBJECT IDENTIFIER ::= { usdBgpConformance 2 }

--
-- compliance statements
--
usdBgpCompliance MODULE-COMPLIANCE
    STATUS      obsolete
    DESCRIPTION
        "Obsolete compliance statement for entities which implement the
        Unisphere BGP MIB.  This statement became obsolete when the
        usdBgpDefaultIPv4Unicast object was added to the general cofiguation
        group."
    MODULE   -- this module
        MANDATORY-GROUPS {
            usdBgpGeneralConfGroup,
            usdBgpStatisticsConfGroup,
            usdBgpConfederationPeerConfGroup,
            usdBgpPeerConfGroup,
            usdBgpAfiSafiPeerConfGroup,
            usdBgpPeerAddressFamilyConfGroup,
            usdBgpPeerGroupConfGroup,
            usdBgpPeerGroupAddressFamilyConfGroup,
            usdBgpRouteConfGroup,
            usdBgpNetworkConfGroup,
            usdBgpAggregateConfGroup,
            usdBgpVrfConfGroup,
            usdBgpAddressFamilyConfGroup,
            usdBgpStorageConfGroup }
    ::= { usdBgpCompliances 1 }                                        -- RX 3.0

usdBgpCompliance2 MODULE-COMPLIANCE
    STATUS      obsolete
    DESCRIPTION
        "Obsolete compliance statement for entities which implement the
        Unisphere BGP MIB.  This statement became obsolete when the original
        route destination was added as an index to each of the route
        configuration tables."
    MODULE   -- this module
        MANDATORY-GROUPS {
            usdBgpGeneralConfGroup2,
            usdBgpStatisticsConfGroup,
            usdBgpConfederationPeerConfGroup,
            usdBgpPeerConfGroup,
            usdBgpAfiSafiPeerConfGroup,
            usdBgpPeerAddressFamilyConfGroup,
            usdBgpPeerGroupConfGroup,
            usdBgpPeerGroupAddressFamilyConfGroup,
            usdBgpRouteConfGroup,
            usdBgpNetworkConfGroup,
            usdBgpAggregateConfGroup,
            usdBgpVrfConfGroup,
            usdBgpAddressFamilyConfGroup,
            usdBgpStorageConfGroup }
    ::= { usdBgpCompliances 2 }                                        -- RX 3.2

usdBgpCompliance3 MODULE-COMPLIANCE
    STATUS      obsolete
    DESCRIPTION
        "Obsolete compliance statement for entities which implement the
        Unisphere BGP MIB.  This statement became obsolete when the peer and
        peer-group local-as support was added."
    MODULE   -- this module
        MANDATORY-GROUPS {
            usdBgpGeneralConfGroup2,
            usdBgpStatisticsConfGroup,
            usdBgpConfederationPeerConfGroup,
            usdBgpPeerConfGroup,
            usdBgpAfiSafiPeerConfGroup,
            usdBgpPeerAddressFamilyConfGroup,
            usdBgpPeerGroupConfGroup,
            usdBgpPeerGroupAddressFamilyConfGroup,
            usdBgpNewRouteConfGroup,
            usdBgpNetworkConfGroup,
            usdBgpAggregateConfGroup,
            usdBgpVrfConfGroup,
            usdBgpAddressFamilyConfGroup,
            usdBgpStorageConfGroup }
    ::= { usdBgpCompliances 3 }                                        -- RX 3.3

usdBgpCompliance4 MODULE-COMPLIANCE
    STATUS      obsolete
    DESCRIPTION
        "Obsolete compliance statement for entities which implement the
        Unisphere BGP MIB.  This statement became obsolete when support was
        added for adding unicast BGP routes into a multicast view."
    MODULE   -- this module
        MANDATORY-GROUPS {
            usdBgpGeneralConfGroup2,
            usdBgpStatisticsConfGroup,
            usdBgpConfederationPeerConfGroup,
            usdBgpPeerConfGroup2,
            usdBgpAfiSafiPeerConfGroup,
            usdBgpPeerAddressFamilyConfGroup,
            usdBgpPeerGroupConfGroup2,
            usdBgpPeerGroupAddressFamilyConfGroup,
            usdBgpNewRouteConfGroup,
            usdBgpNetworkConfGroup,
            usdBgpAggregateConfGroup,
            usdBgpVrfConfGroup,
            usdBgpAddressFamilyConfGroup,
            usdBgpStorageConfGroup }
    ::= { usdBgpCompliances 4 }                                        -- RX 3.4

usdBgpCompliance5 MODULE-COMPLIANCE
    STATUS      obsolete
    DESCRIPTION
        "Obsolete compliance statement for entities which implement the
        Unisphere BGP MIB.  This statement became obsolete when the
        usdBgpRedistributeInternal object was added to the general configuration
        group and the history pool size objects were obsoleted and the ability
        to unconfigure BGP attributes from the MIB was added."
    MODULE   -- this module
        MANDATORY-GROUPS {
            usdBgpGeneralConfGroup2,
            usdBgpStatisticsConfGroup,
            usdBgpConfederationPeerConfGroup,
            usdBgpPeerConfGroup2,
            usdBgpAfiSafiPeerConfGroup,
            usdBgpPeerAddressFamilyConfGroup,
            usdBgpPeerGroupConfGroup2,
            usdBgpPeerGroupAddressFamilyConfGroup,
            usdBgpNewRouteConfGroup,
            usdBgpNetworkConfGroup,
            usdBgpAggregateConfGroup,
            usdBgpVrfConfGroup2,
            usdBgpAddressFamilyConfGroup,
            usdBgpStorageConfGroup }
    ::= { usdBgpCompliances 5 }                                        -- RX 3.5

usdBgpCompliance6 MODULE-COMPLIANCE
    STATUS      current
    DESCRIPTION
        "The compliance statement for entities which implement the Unisphere BGP
        MIB."
    MODULE   -- this module
        MANDATORY-GROUPS {
            usdBgpGeneralConfGroup3,
            usdBgpStatisticsConfGroup,
            usdBgpConfederationPeerConfGroup,
            usdBgpPeerConfGroup3,
            usdBgpAfiSafiPeerConfGroup,
            usdBgpPeerAddressFamilyConfGroup2,
            usdBgpPeerGroupConfGroup3,
            usdBgpPeerGroupAddressFamilyConfGroup2,
            usdBgpNewRouteConfGroup,
            usdBgpNetworkConfGroup2,
            usdBgpAggregateConfGroup2,
            usdBgpVrfConfGroup3,
            usdBgpAddressFamilyConfGroup2,
            usdBgpStorageConfGroup2 }
    ::= { usdBgpCompliances 6 }                                        -- RX 4.0

--
-- units of conformance
--
usdBgpGeneralConfGroup OBJECT-GROUP
    OBJECTS {
        usdBgpLocalAsNumber,
        usdBgpEnabled,
        usdBgpIdentifier,
        usdBgpAlwaysCompareMed,
        usdBgpDefaultLocalPreference,
        usdBgpEqualCostLimit,
        usdBgpClientToClientReflection,
        usdBgpClusterId,
        usdBgpConfederationId,
        usdBgpMissingAsWorst,
        usdBgpResetAllConnectionType,
        usdBgpAdvertiseInactive,
        usdBgpEnforceFirstAs,
        usdBgpConfedCompareMed,
        usdBgpGlobalRetryInterval,
        usdBgpGlobalConfigKeepAliveInterval,
        usdBgpGlobalConfigHoldTime,
        usdBgpGlobalAsOriginationInterval,
        usdBgpExternalAdvertisementInterval,
        usdBgpGlobalRibOutEnabled,
        usdBgpOverloadShutdown,
        usdBgpLogNeighborChanges,
        usdBgpFastExternalFallover,
        usdBgpInternalAdvertisementInterval,
        usdBgpMaxAsLimit,
        usdBgpOperationalState,
        usdBgpPreviousOperationalState,
        usdBgpAutomaticRouteTargetFilter }
    STATUS      obsolete
    DESCRIPTION
        "Obsolete collection of objects providing general management of BGP in a
        Unisphere product.  This group became obsolete when the
        usdBgpDefaultIPv4Unicast object was added."
    ::= { usdBgpConfGroups 1 }

usdBgpStatisticsConfGroup OBJECT-GROUP
    OBJECTS {
        usdBgpBaselineTime,
        usdBgpDestinationCount,
        usdBgpDestinationMemoryUsed,
        usdBgpRouteCount,
        usdBgpRouteMemoryUsed,
        usdBgpSelectedRouteCount,
        usdBgpPathAttributeCount,
        usdBgpPathAttributeMemoryUsed,
        usdBgpRouteFlapHistoryCount,
        usdBgpRouteFlapHistoryMemoryUsed,
        usdBgpSuppressedRouteCount }
    STATUS      current
    DESCRIPTION
        "A collection of objects providing statistics of BGP operations in a
        Unisphere product."
    ::= { usdBgpConfGroups 2 }

usdBgpConfederationPeerConfGroup OBJECT-GROUP
    OBJECTS {
        usdBgpConfederationPeerRowStatus }
    STATUS      current
    DESCRIPTION
        "An object providing management of BGP-specific confederation peers in a
        Unisphere product."
    ::= { usdBgpConfGroups 3 }

usdBgpPeerConfGroup OBJECT-GROUP
    OBJECTS {
        usdBgpPeerAdminStatus,
        usdBgpPeerState,
        usdBgpPeerNegotiatedVersion,
        usdBgpPeerLocalAddress,
        usdBgpPeerLocalAddressMask,
        usdBgpPeerLocalPort,
        usdBgpPeerRemoteAsNumber,
        usdBgpPeerRemotePort,
        usdBgpPeerInUpdates,
        usdBgpPeerOutUpdates,
        usdBgpPeerInTotalMessages,
        usdBgpPeerOutTotalMessages,
        usdBgpPeerLastErrorCode,
        usdBgpPeerLastResetReason,
        usdBgpPeerFsmEstablishedTransitions,
        usdBgpPeerFsmEstablishedTime,
        usdBgpPeerRetryInterval,
        usdBgpPeerHoldTime,
        usdBgpPeerKeepAliveInterval,
        usdBgpPeerConfigHoldTime,
        usdBgpPeerConfigKeepAliveInterval,
        usdBgpPeerAsOriginationInterval,
        usdBgpPeerAdvertisementInterval,
        usdBgpPeerInUpdateElapsedTime,
        usdBgpPeerDescription,
        usdBgpPeerRemoteIdentifier,
        usdBgpPeerWeight,
        usdBgpPeerEbgpMultihop,
        usdBgpPeerEbgpMultihopTtl,
        usdBgpPeerUpdateSource,
        usdBgpPeerMd5Password,
        usdBgpPeerMaxUpdateSize,
        usdBgpPeerType,
        usdBgpPeerSupportsCapabilityNegotiation,
        usdBgpPeerCapabilityMultiProtocol,
        usdBgpPeerCapabilityRouteRefresh,
        usdBgpPeerCapabilityRouteRefreshCiscoProprietary,
        usdBgpPeerResetConnectionType,
        usdBgpPeerRowStatus }
    STATUS      obsolete
    DESCRIPTION
        "Obsolete collection of objects providing management of BGP peers in a
        Unisphere product.  This group became obsolete when the
        usdBgpPeerLocalAsNumber object was added."
    ::= { usdBgpConfGroups 4 }

usdBgpAfiSafiPeerConfGroup OBJECT-GROUP
    OBJECTS {
        usdBgpPeerProposedAfiSafiPeerRowStatus,
        usdBgpLocalProposedAfiSafiPeerRowStatus,
        usdBgpExchangedAfiSafiPeerRowStatus }
    STATUS      current
    DESCRIPTION
        "A collection of objects providing management of BGP-specific AFI and
        SAFI peers in a Unisphere product."
    ::= { usdBgpConfGroups 5 }

usdBgpPeerAddressFamilyConfGroup OBJECT-GROUP
    OBJECTS {
        usdBgpPeerAddressFamilyPeerGroup,
        usdBgpPeerAddressFamilyDefaultOriginate,
        usdBgpPeerAddressFamilyNextHopSelf,
        usdBgpPeerAddressFamilySendCommunity,
        usdBgpPeerAddressFamilyDistributeListIn,
        usdBgpPeerAddressFamilyDistributeListOut,
        usdBgpPeerAddressFamilyPrefixListIn,
        usdBgpPeerAddressFamilyPrefixListOut,
        usdBgpPeerAddressFamilyPrefixTreeIn,
        usdBgpPeerAddressFamilyPrefixTreeOut,
        usdBgpPeerAddressFamilyFilterListIn,
        usdBgpPeerAddressFamilyFilterListOut,
        usdBgpPeerAddressFamilyFilterListWeight,
        usdBgpPeerAddressFamilyFilterListWeightValue,
        usdBgpPeerAddressFamilyRouteMapIn,
        usdBgpPeerAddressFamilyRouteMapOut,
        usdBgpPeerAddressFamilyRouteReflectorClient,
        usdBgpPeerAddressFamilyRouteLimitWarn,
        usdBgpPeerAddressFamilyRouteLimitReset,
        usdBgpPeerAddressFamilyRouteLimitWarnOnly,
        usdBgpPeerAddressFamilyRemovePrivateAs,
        usdBgpPeerAddressFamilyUnsuppressMap,
        usdBgpPeerAddressFamilyInboundSoftReconfig,
        usdBgpPeerAddressFamilyResetConnectionType,
        usdBgpPeerAddressFamilyRowStatus,
        usdBgpPeerAddressFamilyAsOverride,
        usdBgpPeerAddressFamilyAllowAsIn,
        usdBgpPeerAddressFamilySendExtendedCommunity }
    STATUS      obsolete
    DESCRIPTION
        "Obsolete collection of objects providing management of BGP peer address
        families in a Unisphere product.  This group became obsolete when the
        ability to unconfigure attributes using the MIB was added."
    ::= { usdBgpConfGroups 6 }

usdBgpPeerGroupConfGroup OBJECT-GROUP
    OBJECTS {
        usdBgpPeerGroupAdminStatus,
        usdBgpPeerGroupRemoteAsNumber,
        usdBgpPeerGroupRetryInterval,
        usdBgpPeerGroupConfigHoldTime,
        usdBgpPeerGroupConfigKeepAliveInterval,
        usdBgpPeerGroupAsOriginationInterval,
        usdBgpPeerGroupAdvertisementInterval,
        usdBgpPeerGroupDescription,
        usdBgpPeerGroupWeight,
        usdBgpPeerGroupEbgpMultihop,
        usdBgpPeerGroupEbgpMultihopTtl,
        usdBgpPeerGroupUpdateSource,
        usdBgpPeerGroupMd5Password,
        usdBgpPeerGroupMaxUpdateSize,
        usdBgpPeerGroupResetConnectionType,
        usdBgpPeerGroupRowStatus }
    STATUS      obsolete
    DESCRIPTION
        "Obsolete collection of objects providing management of BGP peer groups
        in a Unisphere product.  This group became obsolete when the
        usdBgpPeerGroupLocalAsNumber object was added."
    ::= { usdBgpConfGroups 7 }

usdBgpPeerGroupAddressFamilyConfGroup OBJECT-GROUP
    OBJECTS {
        usdBgpPeerGroupAddressFamilyDefaultOriginate,
        usdBgpPeerGroupAddressFamilyNextHopSelf,
        usdBgpPeerGroupAddressFamilySendCommunity,
        usdBgpPeerGroupAddressFamilyDistributeListIn,
        usdBgpPeerGroupAddressFamilyDistributeListOut,
        usdBgpPeerGroupAddressFamilyPrefixListIn,
        usdBgpPeerGroupAddressFamilyPrefixListOut,
        usdBgpPeerGroupAddressFamilyPrefixTreeIn,
        usdBgpPeerGroupAddressFamilyPrefixTreeOut,
        usdBgpPeerGroupAddressFamilyFilterListIn,
        usdBgpPeerGroupAddressFamilyFilterListOut,
        usdBgpPeerGroupAddressFamilyFilterListWeight,
        usdBgpPeerGroupAddressFamilyFilterListWeightValue,
        usdBgpPeerGroupAddressFamilyRouteMapIn,
        usdBgpPeerGroupAddressFamilyRouteMapOut,
        usdBgpPeerGroupAddressFamilyRouteReflectorClient,
        usdBgpPeerGroupAddressFamilyRouteLimitWarn,
        usdBgpPeerGroupAddressFamilyRouteLimitReset,
        usdBgpPeerGroupAddressFamilyRouteLimitWarnOnly,
        usdBgpPeerGroupAddressFamilyRemovePrivateAs,
        usdBgpPeerGroupAddressFamilyUnsuppressMap,
        usdBgpPeerGroupAddressFamilyInboundSoftReconfig,
        usdBgpPeerGroupAddressFamilyResetConnectionType,
        usdBgpPeerGroupAddressFamilyRowStatus,
        usdBgpPeerGroupAddressFamilyAsOverride,
        usdBgpPeerGroupAddressFamilyAllowAsIn,
        usdBgpPeerGroupAddressFamilySendExtendedCommunity }
    STATUS      obsolete
    DESCRIPTION
        "Obsolete collection of objects providing management of BGP peer group
        address families in a Unisphere product.  This group was obsoleted when
        the ability to unconfigure BGP attributes using the MIB was added."
    ::= { usdBgpConfGroups 8 }

usdBgpRouteConfGroup OBJECT-GROUP
    OBJECTS {
        usdBgpRouteFlapState,
        usdBgpRouteFlapFigureOfMerit,
        usdBgpRouteFlapRemainingTime,
        usdBgpRouteFlapSuppressThreshold,
        usdBgpRouteFlapReuseThreshold,
        usdBgpRouteFlapMaxHoldDownTime,
        usdBgpRouteFlapHalfLifeReachable,
        usdBgpRouteFlapHalfLifeUnreachable,
        usdBgpRouteOriginatorId,
        usdBgpRouteAtomicAggregatePresent,
        usdBgpRouteMedPresent,
        usdBgpRouteLocalPrefPresent,
        usdBgpRouteAggregatorPresent,
        usdBgpRouteCommunitiesPresent,
        usdBgpRouteOriginatorIdPresent,
        usdBgpRouteClusterListPresent,
        usdBgpRouteWeight,
        usdBgpRouteOrigin,
        usdBgpRouteASPathSegment,
        usdBgpRouteNextHop,
        usdBgpRouteMultiExitDisc,
        usdBgpRouteLocalPref,
        usdBgpRouteAtomicAggregate,
        usdBgpRouteAggregatorAS,
        usdBgpRouteAggregatorAddress,
        usdBgpRouteBestInIpRouteTable,
        usdBgpRouteUnknown,
        usdBgpRouteExtendedCommunitiesPresent,
        usdBgpRouteValid,
        usdBgpRouteSuppressedBy,
        usdBgpRouteNextHopReachable,
        usdBgpRouteSynchronizedWithIgp,
        usdBgpRoutePlaceInIpRouteTable,
        usdBgpRouteAdvertiseToExternalPeers,
        usdBgpRouteAdvertiseToInternalPeers,
        usdBgpRouteDistinguisher,
        usdBgpRouteMplsLabel,
        usdBgpRouteNextHopMetric,
        usdBgpRouteCommunityNumber,
        usdBgpRouteExtendedCommunityNumber,
        usdBgpRouteClusterId }
    STATUS      obsolete
    DESCRIPTION
        "Obsolete collection of objects providing management of BGP routes in a
        Unisphere product.  This group became obsolete when the original route
        destination was added as an index to each of the tables."
    ::= { usdBgpConfGroups 9 }

usdBgpNetworkConfGroup OBJECT-GROUP
    OBJECTS {
        usdBgpNetworkBackdoor,
        usdBgpNetworkRowStatus,
        usdBgpNetworkWeightSpecified,
        usdBgpNetworkWeight,
        usdBgpNetworkRouteMap }
    STATUS      obsolete
    DESCRIPTION
        "Obsolete collection of objects providing management of BGP networks in
        a Unisphere product.  This group was obsoleted when the ability to
        unconfigure BGP attributes using the MIB was added."
    ::= { usdBgpConfGroups 10 }

usdBgpAggregateConfGroup OBJECT-GROUP
    OBJECTS {
        usdBgpAggregateAsSet,
        usdBgpAggregateSummaryOnly,
        usdBgpAggregateAttributeMap,
        usdBgpAggregateAdvertiseMap,
        usdBgpAggregateRowStatus,
        usdBgpAggregateSuppressMap }
    STATUS      obsolete
    DESCRIPTION
        "Obsolete collection of objects providing consolidation of BGP route
        information in a Unisphere product.  This group was obsoleted when the
        ability to unconfigure BGP attributes using the MIB was added."
    ::= { usdBgpConfGroups 11 }

usdBgpVrfConfGroup OBJECT-GROUP
    OBJECTS {
        usdBgpVrfSynchronization,
        usdBgpVrfAutoSummary,
        usdBgpVrfExternalDistance,
        usdBgpVrfInternalDistance,
        usdBgpVrfLocalDistance,
        usdBgpVrfResetConnectionType,
        usdBgpVrfRowStatus,
        usdBgpVrfOperationalState }
    STATUS      obsolete
    DESCRIPTION
        "Obsolete collection of objects providing management of BGP-specific VPN
        routing forwarding (VRF) characteristics in a Unisphere product.  This
        group became obsolete when the usdBgpVrfAddUnicastRoutesToMulticastView
        object was added."
    ::= { usdBgpConfGroups 12 }

usdBgpAddressFamilyConfGroup OBJECT-GROUP
    OBJECTS {
        usdBgpAddressFamilyDefaultOriginate,
        usdBgpAddressFamilyRouteFlapDampening,
        usdBgpAddressFamilyDampeningSuppressThreshold,
        usdBgpAddressFamilyDampeningReuseThreshold,
        usdBgpAddressFamilyDampeningMaxHoldDownTime,
        usdBgpAddressFamilyDampeningHalfLifeReachable,
        usdBgpAddressFamilyDampeningHalfLifeUnreachable,
        usdBgpAddressFamilyDampeningRouteMapName,
        usdBgpAddressFamilyResetConnectionType,
        usdBgpAddressFamilyRowStatus,
        usdBgpAddressFamilyOperationalState }
    STATUS      obsolete
    DESCRIPTION
        "Obsolete collection of objects providing management of BGP address
        families in a Unisphere product.  This group was obsoleted when the
        ability to unconfigure BGP attributes using the MIB was added."
    ::= { usdBgpConfGroups 13 }

usdBgpStorageConfGroup OBJECT-GROUP
    OBJECTS {
        usdBgpStorageInitialHeapSize,
        usdBgpStorageMaxHeapSize,
        usdBgpStorageInitialVrfPoolSize,
        usdBgpStorageMaxVrfPoolSize,
        usdBgpStorageInitialAddressFamilyPoolSize,
        usdBgpStorageMaxAddressFamilyPoolSize,
        usdBgpStorageInitialPeerPoolSize,
        usdBgpStorageMaxPeerPoolSize,
        usdBgpStorageInitialPeerAfPoolSize,
        usdBgpStorageMaxPeerAfPoolSize,
        usdBgpStorageInitialPeerGroupPoolSize,
        usdBgpStorageMaxPeerGroupPoolSize,
        usdBgpStorageInitialPeerGroupAfPoolSize,
        usdBgpStorageMaxPeerGroupAfPoolSize,
        usdBgpStorageInitialNetworkPoolSize,
        usdBgpStorageMaxNetworkPoolSize,
        usdBgpStorageInitialAggregatePoolSize,
        usdBgpStorageMaxAggregatePoolSize,
        usdBgpStorageInitialDestinationPoolSize,
        usdBgpStorageMaxDestinationPoolSize,
        usdBgpStorageInitialRoutePoolSize,
        usdBgpStorageMaxRoutePoolSize,
        usdBgpStorageInitialAttributesPoolSize,
        usdBgpStorageMaxAttributesPoolSize,
        usdBgpStorageInitialRouteFlapHistoryPoolSize,
        usdBgpStorageMaxRouteFlapHistoryPoolSize,
        usdBgpStorageInitialNetworkRoutePoolSize,
        usdBgpStorageMaxNetworkRoutePoolSize,
        usdBgpStorageInitialRedistributedRoutePoolSize,
        usdBgpStorageMaxRedistributedRoutePoolSize,
        usdBgpStorageInitialAggregateRoutePoolSize,
        usdBgpStorageMaxAggregateRoutePoolSize,
        usdBgpStorageInitialAutoSummaryRoutePoolSize,
        usdBgpStorageMaxAutoSummaryRoutePoolSize,
        usdBgpStorageInitialHistoryRoutePoolSize,
        usdBgpStorageMaxHistoryRoutePoolSize,
        usdBgpStorageInitialSendQueueEntryPoolSize,
        usdBgpStorageMaxSendQueueEntryPoolSize,
        usdBgpStorageInitialVpnRoutePoolSize,
        usdBgpStorageMaxVpnRoutePoolSize,
        usdBgpStorageInitialRouteTargetPoolSize,
        usdBgpStorageMaxRouteTargetPoolSize }
    STATUS      obsolete
    DESCRIPTION
        "Obsolete collection of objects providing management of BGP
        characteristics in a Unisphere product that will not take affect until
        reboot.  This group became obsolete when the history pool size objects
        were obsoleted."
    ::= { usdBgpConfGroups 14 }

usdBgpGeneralConfGroup2 OBJECT-GROUP
    OBJECTS {
        usdBgpLocalAsNumber,
        usdBgpEnabled,
        usdBgpIdentifier,
        usdBgpAlwaysCompareMed,
        usdBgpDefaultLocalPreference,
        usdBgpEqualCostLimit,
        usdBgpClientToClientReflection,
        usdBgpClusterId,
        usdBgpConfederationId,
        usdBgpMissingAsWorst,
        usdBgpResetAllConnectionType,
        usdBgpAdvertiseInactive,
        usdBgpEnforceFirstAs,
        usdBgpConfedCompareMed,
        usdBgpGlobalRetryInterval,
        usdBgpGlobalConfigKeepAliveInterval,
        usdBgpGlobalConfigHoldTime,
        usdBgpGlobalAsOriginationInterval,
        usdBgpExternalAdvertisementInterval,
        usdBgpGlobalRibOutEnabled,
        usdBgpOverloadShutdown,
        usdBgpLogNeighborChanges,
        usdBgpFastExternalFallover,
        usdBgpInternalAdvertisementInterval,
        usdBgpMaxAsLimit,
        usdBgpOperationalState,
        usdBgpPreviousOperationalState,
        usdBgpAutomaticRouteTargetFilter,
        usdBgpDefaultIPv4Unicast }
    STATUS      obsolete
    DESCRIPTION
        "Obsolete collection of objects providing general management of BGP in a
        Unisphere product.  This group became obsolete when the
        usdBgpRedistributeInternal object and unconfigure support were added."
    ::= { usdBgpConfGroups 15 }

usdBgpNewRouteConfGroup OBJECT-GROUP
    OBJECTS {
        usdBgpNewRouteOriginatorId,
        usdBgpNewRouteAtomicAggregatePresent,
        usdBgpNewRouteMedPresent,
        usdBgpNewRouteLocalPrefPresent,
        usdBgpNewRouteAggregatorPresent,
        usdBgpNewRouteCommunitiesPresent,
        usdBgpNewRouteOriginatorIdPresent,
        usdBgpNewRouteClusterListPresent,
        usdBgpNewRouteWeight,
        usdBgpNewRouteOrigin,
        usdBgpNewRouteASPathSegment,
        usdBgpNewRouteNextHop,
        usdBgpNewRouteMultiExitDisc,
        usdBgpNewRouteLocalPref,
        usdBgpNewRouteAtomicAggregate,
        usdBgpNewRouteAggregatorAS,
        usdBgpNewRouteAggregatorAddress,
        usdBgpNewRouteBestInIpRouteTable,
        usdBgpNewRouteUnknown,
        usdBgpNewRouteExtendedCommunitiesPresent,
        usdBgpNewRouteValid,
        usdBgpNewRouteSuppressedBy,
        usdBgpNewRouteNextHopReachable,
        usdBgpNewRouteSynchronizedWithIgp,
        usdBgpNewRoutePlaceInIpRouteTable,
        usdBgpNewRouteAdvertiseToExternalPeers,
        usdBgpNewRouteAdvertiseToInternalPeers,
        usdBgpNewRouteMplsLabel,
        usdBgpNewRouteNextHopMetric,
        usdBgpNewRouteFlapState,
        usdBgpNewRouteFlapFigureOfMerit,
        usdBgpNewRouteFlapRemainingTime,
        usdBgpNewRouteFlapSuppressThreshold,
        usdBgpNewRouteFlapReuseThreshold,
        usdBgpNewRouteFlapMaxHoldDownTime,
        usdBgpNewRouteFlapHalfLifeReachable,
        usdBgpNewRouteFlapHalfLifeUnreachable,
        usdBgpNewRouteCommunityNumber,
        usdBgpNewRouteExtendedCommunityNumber,
        usdBgpNewRouteClusterId }
    STATUS      current
    DESCRIPTION
        "A collection of objects providing management of BGP routes in a
        Unisphere product."
    ::= { usdBgpConfGroups 16 }

usdBgpPeerConfGroup2 OBJECT-GROUP
    OBJECTS {
        usdBgpPeerAdminStatus,
        usdBgpPeerState,
        usdBgpPeerNegotiatedVersion,
        usdBgpPeerLocalAddress,
        usdBgpPeerLocalAddressMask,
        usdBgpPeerLocalPort,
        usdBgpPeerRemoteAsNumber,
        usdBgpPeerRemotePort,
        usdBgpPeerInUpdates,
        usdBgpPeerOutUpdates,
        usdBgpPeerInTotalMessages,
        usdBgpPeerOutTotalMessages,
        usdBgpPeerLastErrorCode,
        usdBgpPeerLastResetReason,
        usdBgpPeerFsmEstablishedTransitions,
        usdBgpPeerFsmEstablishedTime,
        usdBgpPeerRetryInterval,
        usdBgpPeerHoldTime,
        usdBgpPeerKeepAliveInterval,
        usdBgpPeerConfigHoldTime,
        usdBgpPeerConfigKeepAliveInterval,
        usdBgpPeerAsOriginationInterval,
        usdBgpPeerAdvertisementInterval,
        usdBgpPeerInUpdateElapsedTime,
        usdBgpPeerDescription,
        usdBgpPeerRemoteIdentifier,
        usdBgpPeerWeight,
        usdBgpPeerEbgpMultihop,
        usdBgpPeerEbgpMultihopTtl,
        usdBgpPeerUpdateSource,
        usdBgpPeerMd5Password,
        usdBgpPeerMaxUpdateSize,
        usdBgpPeerType,
        usdBgpPeerSupportsCapabilityNegotiation,
        usdBgpPeerCapabilityMultiProtocol,
        usdBgpPeerCapabilityRouteRefresh,
        usdBgpPeerCapabilityRouteRefreshCiscoProprietary,
        usdBgpPeerResetConnectionType,
        usdBgpPeerRowStatus,
        usdBgpPeerLocalAsNumber }
    STATUS      obsolete
    DESCRIPTION
        "Obsolete collection of objects providing management of BGP peers in a
        Unisphere product.  This group became obsolete when the ability to
        unconfigure BGP attributes from the MIB was added."
    ::= { usdBgpConfGroups 17 }

usdBgpPeerGroupConfGroup2 OBJECT-GROUP
    OBJECTS {
        usdBgpPeerGroupAdminStatus,
        usdBgpPeerGroupRemoteAsNumber,
        usdBgpPeerGroupRetryInterval,
        usdBgpPeerGroupConfigHoldTime,
        usdBgpPeerGroupConfigKeepAliveInterval,
        usdBgpPeerGroupAsOriginationInterval,
        usdBgpPeerGroupAdvertisementInterval,
        usdBgpPeerGroupDescription,
        usdBgpPeerGroupWeight,
        usdBgpPeerGroupEbgpMultihop,
        usdBgpPeerGroupEbgpMultihopTtl,
        usdBgpPeerGroupUpdateSource,
        usdBgpPeerGroupMd5Password,
        usdBgpPeerGroupMaxUpdateSize,
        usdBgpPeerGroupResetConnectionType,
        usdBgpPeerGroupRowStatus,
        usdBgpPeerGroupLocalAsNumber }
    STATUS      obsolete
    DESCRIPTION
        "Obsolete collection of objects providing management of BGP peer groups
        in a Unisphere product.  This group was obsoleted when the ability to
        unconfigure BGP attributes using the MIB was added."
    ::= { usdBgpConfGroups 18 }

usdBgpVrfConfGroup2 OBJECT-GROUP
    OBJECTS {
        usdBgpVrfSynchronization,
        usdBgpVrfAutoSummary,
        usdBgpVrfExternalDistance,
        usdBgpVrfInternalDistance,
        usdBgpVrfLocalDistance,
        usdBgpVrfResetConnectionType,
        usdBgpVrfRowStatus,
        usdBgpVrfOperationalState,
        usdBgpVrfAddUnicastRoutesToMulticastView }
    STATUS      obsolete
    DESCRIPTION
        "Obsolete collection of objects providing management of BGP-specific VPN
        routing forwarding (VRF) characteristics in a Unisphere product.  This
        group was obsoleted when the ability to unconfigure BGP attributes using
        the MIB was added."
    ::= { usdBgpConfGroups 19 }

usdBgpGeneralConfGroup3 OBJECT-GROUP
    OBJECTS {
        usdBgpLocalAsNumber,
        usdBgpEnabled,
        usdBgpIdentifier,
        usdBgpAlwaysCompareMed,
        usdBgpDefaultLocalPreference,
        usdBgpEqualCostLimit,
        usdBgpClientToClientReflection,
        usdBgpClusterId,
        usdBgpConfederationId,
        usdBgpMissingAsWorst,
        usdBgpResetAllConnectionType,
        usdBgpAdvertiseInactive,
        usdBgpEnforceFirstAs,
        usdBgpConfedCompareMed,
        usdBgpGlobalRetryInterval,
        usdBgpGlobalConfigKeepAliveInterval,
        usdBgpGlobalConfigHoldTime,
        usdBgpGlobalAsOriginationInterval,
        usdBgpExternalAdvertisementInterval,
        usdBgpGlobalRibOutEnabled,
        usdBgpOverloadShutdown,
        usdBgpLogNeighborChanges,
        usdBgpFastExternalFallover,
        usdBgpInternalAdvertisementInterval,
        usdBgpMaxAsLimit,
        usdBgpOperationalState,
        usdBgpPreviousOperationalState,
        usdBgpAutomaticRouteTargetFilter,
        usdBgpDefaultIPv4Unicast,
        usdBgpRedistributeInternal,
        usdBgpUnconfiguredAttributes }
    STATUS      current
    DESCRIPTION
        "A collection of objects providing general management of BGP in a
        Unisphere product."
    ::= { usdBgpConfGroups 20 }

usdBgpStorageConfGroup2 OBJECT-GROUP
    OBJECTS {
        usdBgpStorageInitialHeapSize,
        usdBgpStorageMaxHeapSize,
        usdBgpStorageInitialVrfPoolSize,
        usdBgpStorageMaxVrfPoolSize,
        usdBgpStorageInitialAddressFamilyPoolSize,
        usdBgpStorageMaxAddressFamilyPoolSize,
        usdBgpStorageInitialPeerPoolSize,
        usdBgpStorageMaxPeerPoolSize,
        usdBgpStorageInitialPeerAfPoolSize,
        usdBgpStorageMaxPeerAfPoolSize,
        usdBgpStorageInitialPeerGroupPoolSize,
        usdBgpStorageMaxPeerGroupPoolSize,
        usdBgpStorageInitialPeerGroupAfPoolSize,
        usdBgpStorageMaxPeerGroupAfPoolSize,
        usdBgpStorageInitialNetworkPoolSize,
        usdBgpStorageMaxNetworkPoolSize,
        usdBgpStorageInitialAggregatePoolSize,
        usdBgpStorageMaxAggregatePoolSize,
        usdBgpStorageInitialDestinationPoolSize,
        usdBgpStorageMaxDestinationPoolSize,
        usdBgpStorageInitialRoutePoolSize,
        usdBgpStorageMaxRoutePoolSize,
        usdBgpStorageInitialAttributesPoolSize,
        usdBgpStorageMaxAttributesPoolSize,
        usdBgpStorageInitialRouteFlapHistoryPoolSize,
        usdBgpStorageMaxRouteFlapHistoryPoolSize,
        usdBgpStorageInitialNetworkRoutePoolSize,
        usdBgpStorageMaxNetworkRoutePoolSize,
        usdBgpStorageInitialRedistributedRoutePoolSize,
        usdBgpStorageMaxRedistributedRoutePoolSize,
        usdBgpStorageInitialAggregateRoutePoolSize,
        usdBgpStorageMaxAggregateRoutePoolSize,
        usdBgpStorageInitialAutoSummaryRoutePoolSize,
        usdBgpStorageMaxAutoSummaryRoutePoolSize,
        usdBgpStorageInitialSendQueueEntryPoolSize,
        usdBgpStorageMaxSendQueueEntryPoolSize,
        usdBgpStorageInitialVpnRoutePoolSize,
        usdBgpStorageMaxVpnRoutePoolSize,
        usdBgpStorageInitialRouteTargetPoolSize,
        usdBgpStorageMaxRouteTargetPoolSize }
    STATUS      current
    DESCRIPTION
        "A collection of objects providing management of BGP characteristics in
        a Unisphere product that will not take affect until reboot."
    ::= { usdBgpConfGroups 21 }

usdBgpPeerConfGroup3 OBJECT-GROUP
    OBJECTS {
        usdBgpPeerAdminStatus,
        usdBgpPeerState,
        usdBgpPeerNegotiatedVersion,
        usdBgpPeerLocalAddress,
        usdBgpPeerLocalAddressMask,
        usdBgpPeerLocalPort,
        usdBgpPeerRemoteAsNumber,
        usdBgpPeerRemotePort,
        usdBgpPeerInUpdates,
        usdBgpPeerOutUpdates,
        usdBgpPeerInTotalMessages,
        usdBgpPeerOutTotalMessages,
        usdBgpPeerLastErrorCode,
        usdBgpPeerLastResetReason,
        usdBgpPeerFsmEstablishedTransitions,
        usdBgpPeerFsmEstablishedTime,
        usdBgpPeerRetryInterval,
        usdBgpPeerHoldTime,
        usdBgpPeerKeepAliveInterval,
        usdBgpPeerConfigHoldTime,
        usdBgpPeerConfigKeepAliveInterval,
        usdBgpPeerAsOriginationInterval,
        usdBgpPeerAdvertisementInterval,
        usdBgpPeerInUpdateElapsedTime,
        usdBgpPeerDescription,
        usdBgpPeerRemoteIdentifier,
        usdBgpPeerWeight,
        usdBgpPeerEbgpMultihop,
        usdBgpPeerEbgpMultihopTtl,
        usdBgpPeerUpdateSource,
        usdBgpPeerMd5Password,
        usdBgpPeerMaxUpdateSize,
        usdBgpPeerType,
        usdBgpPeerSupportsCapabilityNegotiation,
        usdBgpPeerCapabilityMultiProtocol,
        usdBgpPeerCapabilityRouteRefresh,
        usdBgpPeerCapabilityRouteRefreshCiscoProprietary,
        usdBgpPeerResetConnectionType,
        usdBgpPeerRowStatus,
        usdBgpPeerLocalAsNumber,
        usdBgpPeerUnconfiguredAttributes }
    STATUS      current
    DESCRIPTION
        "A collection of objects providing management of BGP peers in a
        Unisphere product."
    ::= { usdBgpConfGroups 22 }

usdBgpPeerAddressFamilyConfGroup2 OBJECT-GROUP
    OBJECTS {
        usdBgpPeerAddressFamilyPeerGroup,
        usdBgpPeerAddressFamilyDefaultOriginate,
        usdBgpPeerAddressFamilyNextHopSelf,
        usdBgpPeerAddressFamilySendCommunity,
        usdBgpPeerAddressFamilyDistributeListIn,
        usdBgpPeerAddressFamilyDistributeListOut,
        usdBgpPeerAddressFamilyPrefixListIn,
        usdBgpPeerAddressFamilyPrefixListOut,
        usdBgpPeerAddressFamilyPrefixTreeIn,
        usdBgpPeerAddressFamilyPrefixTreeOut,
        usdBgpPeerAddressFamilyFilterListIn,
        usdBgpPeerAddressFamilyFilterListOut,
        usdBgpPeerAddressFamilyFilterListWeight,
        usdBgpPeerAddressFamilyFilterListWeightValue,
        usdBgpPeerAddressFamilyRouteMapIn,
        usdBgpPeerAddressFamilyRouteMapOut,
        usdBgpPeerAddressFamilyRouteReflectorClient,
        usdBgpPeerAddressFamilyRouteLimitWarn,
        usdBgpPeerAddressFamilyRouteLimitReset,
        usdBgpPeerAddressFamilyRouteLimitWarnOnly,
        usdBgpPeerAddressFamilyRemovePrivateAs,
        usdBgpPeerAddressFamilyUnsuppressMap,
        usdBgpPeerAddressFamilyInboundSoftReconfig,
        usdBgpPeerAddressFamilyResetConnectionType,
        usdBgpPeerAddressFamilyRowStatus,
        usdBgpPeerAddressFamilyAsOverride,
        usdBgpPeerAddressFamilyAllowAsIn,
        usdBgpPeerAddressFamilySendExtendedCommunity,
        usdBgpPeerAddressFamilyUnconfiguredAttributes }
    STATUS      current
    DESCRIPTION
        "A collection of objects providing management of BGP peer address
        families in a Unisphere product."
    ::= { usdBgpConfGroups 23 }

usdBgpPeerGroupConfGroup3 OBJECT-GROUP
    OBJECTS {
        usdBgpPeerGroupAdminStatus,
        usdBgpPeerGroupRemoteAsNumber,
        usdBgpPeerGroupRetryInterval,
        usdBgpPeerGroupConfigHoldTime,
        usdBgpPeerGroupConfigKeepAliveInterval,
        usdBgpPeerGroupAsOriginationInterval,
        usdBgpPeerGroupAdvertisementInterval,
        usdBgpPeerGroupDescription,
        usdBgpPeerGroupWeight,
        usdBgpPeerGroupEbgpMultihop,
        usdBgpPeerGroupEbgpMultihopTtl,
        usdBgpPeerGroupUpdateSource,
        usdBgpPeerGroupMd5Password,
        usdBgpPeerGroupMaxUpdateSize,
        usdBgpPeerGroupResetConnectionType,
        usdBgpPeerGroupRowStatus,
        usdBgpPeerGroupLocalAsNumber,
        usdBgpPeerGroupUnconfiguredAttributes }
    STATUS      current
    DESCRIPTION
        "A collection of objects providing management of BGP peer groups in a
        Unisphere product."
    ::= { usdBgpConfGroups 24 }

usdBgpPeerGroupAddressFamilyConfGroup2 OBJECT-GROUP
    OBJECTS {
        usdBgpPeerGroupAddressFamilyDefaultOriginate,
        usdBgpPeerGroupAddressFamilyNextHopSelf,
        usdBgpPeerGroupAddressFamilySendCommunity,
        usdBgpPeerGroupAddressFamilyDistributeListIn,
        usdBgpPeerGroupAddressFamilyDistributeListOut,
        usdBgpPeerGroupAddressFamilyPrefixListIn,
        usdBgpPeerGroupAddressFamilyPrefixListOut,
        usdBgpPeerGroupAddressFamilyPrefixTreeIn,
        usdBgpPeerGroupAddressFamilyPrefixTreeOut,
        usdBgpPeerGroupAddressFamilyFilterListIn,
        usdBgpPeerGroupAddressFamilyFilterListOut,
        usdBgpPeerGroupAddressFamilyFilterListWeight,
        usdBgpPeerGroupAddressFamilyFilterListWeightValue,
        usdBgpPeerGroupAddressFamilyRouteMapIn,
        usdBgpPeerGroupAddressFamilyRouteMapOut,
        usdBgpPeerGroupAddressFamilyRouteReflectorClient,
        usdBgpPeerGroupAddressFamilyRouteLimitWarn,
        usdBgpPeerGroupAddressFamilyRouteLimitReset,
        usdBgpPeerGroupAddressFamilyRouteLimitWarnOnly,
        usdBgpPeerGroupAddressFamilyRemovePrivateAs,
        usdBgpPeerGroupAddressFamilyUnsuppressMap,
        usdBgpPeerGroupAddressFamilyInboundSoftReconfig,
        usdBgpPeerGroupAddressFamilyResetConnectionType,
        usdBgpPeerGroupAddressFamilyRowStatus,
        usdBgpPeerGroupAddressFamilyAsOverride,
        usdBgpPeerGroupAddressFamilyAllowAsIn,
        usdBgpPeerGroupAddressFamilySendExtendedCommunity,
        usdBgpPeerGroupAddressFamilyUnconfiguredAttributes }
    STATUS      current
    DESCRIPTION
        "A collection of objects providing management of BGP peer group address
        families in a Unisphere product."
    ::= { usdBgpConfGroups 25 }

usdBgpNetworkConfGroup2 OBJECT-GROUP
    OBJECTS {
        usdBgpNetworkBackdoor,
        usdBgpNetworkRowStatus,
        usdBgpNetworkWeightSpecified,
        usdBgpNetworkWeight,
        usdBgpNetworkRouteMap,
        usdBgpNetworkUnconfiguredAttributes }
    STATUS      current
    DESCRIPTION
        "A collection of objects providing management of BGP networks in a
        Unisphere product."
    ::= { usdBgpConfGroups 26 }

usdBgpAggregateConfGroup2 OBJECT-GROUP
    OBJECTS {
        usdBgpAggregateAsSet,
        usdBgpAggregateSummaryOnly,
        usdBgpAggregateAttributeMap,
        usdBgpAggregateAdvertiseMap,
        usdBgpAggregateRowStatus,
        usdBgpAggregateSuppressMap,
        usdBgpAggregateUnconfiguredAttributes }
    STATUS      current
    DESCRIPTION
        "A collection of objects providing consolidation of BGP route
        information in a Unisphere product."
    ::= { usdBgpConfGroups 27 }

usdBgpVrfConfGroup3 OBJECT-GROUP
    OBJECTS {
        usdBgpVrfSynchronization,
        usdBgpVrfAutoSummary,
        usdBgpVrfExternalDistance,
        usdBgpVrfInternalDistance,
        usdBgpVrfLocalDistance,
        usdBgpVrfResetConnectionType,
        usdBgpVrfRowStatus,
        usdBgpVrfOperationalState,
        usdBgpVrfAddUnicastRoutesToMulticastView,
        usdBgpVrfUnconfiguredAttributes }
    STATUS      current
    DESCRIPTION
        "A collection of objects providing management of BGP-specific VPN
        routing forwarding (VRF) characteristics in a Unisphere product."
    ::= { usdBgpConfGroups 28 }

usdBgpAddressFamilyConfGroup2 OBJECT-GROUP
    OBJECTS {
        usdBgpAddressFamilyDefaultOriginate,
        usdBgpAddressFamilyRouteFlapDampening,
        usdBgpAddressFamilyDampeningSuppressThreshold,
        usdBgpAddressFamilyDampeningReuseThreshold,
        usdBgpAddressFamilyDampeningMaxHoldDownTime,
        usdBgpAddressFamilyDampeningHalfLifeReachable,
        usdBgpAddressFamilyDampeningHalfLifeUnreachable,
        usdBgpAddressFamilyDampeningRouteMapName,
        usdBgpAddressFamilyResetConnectionType,
        usdBgpAddressFamilyRowStatus,
        usdBgpAddressFamilyOperationalState,
        usdBgpAddressFamilyUnconfiguredAttributes }
    STATUS      current
    DESCRIPTION
        "A collection of objects providing management of BGP address families in
        a Unisphere product."
    ::= { usdBgpConfGroups 29 }

END
