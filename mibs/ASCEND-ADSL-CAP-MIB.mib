--			ADSL CAP Enterprise Mib
--
--			Ascend Communications, Inc
--			1275 Harbor Bay Pkwy
--			Alameda, CA 94502
--			+1 510 769 6001
--			info@ascend.com
--
--		Copyright (c) 1993-1995 Ascend Communications, Inc.
--		All rights reserved.
--
-- CVS ID:      $Id: adslcap.mib,v 29.5 1998/10/22 03:56:09 edelhaus Exp $
--
-- 06 Dec 96:	Initial release

	-- Ascend wanTypeAdslCap group
	--
	-- This group contains MIB variables used to manage the ADSL CAP
	-- interface

	-- ADSL CAP interface status
	--
	-- The below entries contain interface status information. The slot
	-- number and interface are identified via that adslCapSlotIndex and 
	-- adslCapLineIndex parameters. 
	--
ASCEND-ADSL-CAP-MIB DEFINITIONS ::= BEGIN

    IMPORTS
	wanTypeAdslCap
	    FROM ASCEND-WAN-MIB
	OBJECT-TYPE
	    FROM RFC-1212;
	
    adslCapLineStatusTable	OBJECT-TYPE
	SYNTAX		SEQUENCE OF AdslCapLineStatusEntry
	ACCESS		not-accessible
	STATUS		mandatory
	DESCRIPTION	"ADSL CAP status parameters."
	::= { wanTypeAdslCap 1 }

    adslCapLineStatusEntry	OBJECT-TYPE
	SYNTAX		AdslCapLineStatusEntry
	ACCESS		not-accessible
	STATUS		mandatory
	DESCRIPTION	"A interface status entry containing objects to describe the
			interface."
	INDEX		{ adslCapStatusIfEntryIndex }
	::= { adslCapLineStatusTable 1 }

    AdslCapLineStatusEntry ::=
	SEQUENCE {
	    adslCapStatusIfEntryIndex
		INTEGER,
	    adslCapStatusShelfIndex
	        INTEGER,
	    adslCapStatusSlotIndex
		INTEGER,
	    adslCapStatusLineIndex
		INTEGER,
	    adslCapStatusUnitType
		INTEGER,
	    adslCapStatusLineState
		INTEGER,
	    adslCapStatusUpRate
		INTEGER,
	    adslCapStatusDownRate
		INTEGER,
	    adslCapStatusVendorId
		INTEGER,
	    adslCapStatusMajorFirmWareVer
		INTEGER,
	    adslCapStatusMinorFirmWareVer
		INTEGER,
	    adslCapStatusHardWareVer
		INTEGER
	}

   adslCapStatusIfEntryIndex    OBJECT-TYPE
	SYNTAX		INTEGER	(1..'7fffffff'h)
	ACCESS		read-only
	STATUS		mandatory
	DESCRIPTION	"Index into the Status Table via the interface group
			 ifIndex value."
	::= { adslCapLineStatusEntry 1 }
   
    adslCapStatusShelfIndex OBJECT-TYPE
	SYNTAX		INTEGER
	ACCESS		read-only
	STATUS		mandatory
	DESCRIPTION	"TNT's ADSL CAP modules Shelf ID."
	::= { adslCapLineStatusEntry 2 }

    adslCapStatusSlotIndex	OBJECT-TYPE
	SYNTAX		INTEGER
	ACCESS		read-only
	STATUS		mandatory
	DESCRIPTION	"TNT's ADSL CAP modules Slot ID."
	::= { adslCapLineStatusEntry 3 }

    adslCapStatusLineIndex	OBJECT-TYPE
	SYNTAX		INTEGER
	ACCESS		read-only
	STATUS		mandatory
	DESCRIPTION	"ADSL CAP modules line ID." 
	::= { adslCapLineStatusEntry 4 }

   adslCapStatusUnitType	OBJECT-TYPE
	SYNTAX		INTEGER {
			    other( 1 ),		-- none of the following
			    coe( 2 ),		-- Central Office Equipment.
			    cpe( 3 )		-- Customer Premises
						-- Equipment. 
			}
	ACCESS		read-only
	STATUS		mandatory
	DESCRIPTION	"Unit type defines if the unit is operating either as a
			Central Office Equipment (COE) or Customer Premiss
			equipment (CPE)."
	::= { adslCapLineStatusEntry 5 }

   adslCapStatusLineState	OBJECT-TYPE
	SYNTAX		INTEGER {
			    other( 1 ),		-- none of the following
			    configure( 2 ),	-- Interface is in
						-- Configuration state. 
			    deactivate( 3 ),    -- Port is down. Deactive 
						-- has been issued. 
			    deactive-lost( 4 ), -- Waiting for LOS or LOST 
						-- indication.
			    start-up( 5 ),	-- Interface is in start-up
						-- mode. 
			    pend-port-up( 6 ), 
			    up( 7 ),		-- Interface is in UP state, and
						-- ready to transfer data.
			    pend-deactivate( 8 ),-- Interface may transition
						-- from UP to DOWN state. 
			    out-of-service( 9 ), -- Interface is placed OOS.
			    analog-loopback( 10 ), 
						-- Port is in some type of 
						-- test state
			    digital-loopback( 11 ) 
						-- Port is in some type of
						-- test state
			}

	ACCESS		read-only
	STATUS		mandatory
	DESCRIPTION	"Interface state describes the current ports
			operating state. States are: Config, Pend Down, 
			Up, Down, Start-up, or N/A."
	::= { adslCapLineStatusEntry 6 }
	
   adslCapStatusUpRate		OBJECT-TYPE
	SYNTAX		INTEGER{
		            m1088000(1088000), 
						-- Maximum operational rate 
						-- is 1 meg. Will down rate 
						-- to 272000.
			    k952000(952000),  
						-- Only trains at 952000.
			    k816000(816000),  
						-- Only trains at 816000.
			    k680000(680000), 
						-- Only trains at 680000.
			    k544000(544000),
						-- Only trains at 544000.
			    k408000(408000),
						-- Only trains at 408000.
			    k272000(272000)
						-- Only trains at 272000.
                               }	 
	ACCESS		read-write
	STATUS		mandatory
	DESCRIPTION	"When parameter is read, it displays the 
			 current up stream (cpe to coe) rate which can
			 differ from the written value."
	::= { adslCapLineStatusEntry 7 }

   adslCapStatusDownRate		OBJECT-TYPE
	SYNTAX		INTEGER{
			    m7168000(7168000), 
						-- Maximum operational rate 
						-- is 7 meg. Will down rate 
						-- to 2688000.
			    m6272000(6272000),  
						-- Only trains at 6272000.
			    m5120000(5120000),
						-- Maximum operational rate 
						-- is 5.1 meg. Will down
						-- rate to 1920000.
			
			    m4480000(4480000),  
						-- Only trains at 4480000.
			    m3200000(3200000), 
						-- Only trains at 3200000.
			    
			    m2688000(2688000),
						-- Only trains at 2688000.
			    m2560000(2560000),
						-- Maximum operational rate 
						-- is 2.5 meg. Will down
						-- rate to 640000.
			    m2240000(2240000),  
						-- Only trains at 2240000.
			    m1920000(1920000),
						-- Only trains at 1920000.
			    m1600000(1600000),
						-- Only trains at 1600000.
			    m1280000(1280000),
						-- Only trains at 1280000.
			    k960000(960000),
						-- Only trains at 960000.
			    k640000(640000)	
						-- Only trains at 640000.
			}
 
	ACCESS		read-write
	STATUS		mandatory
	DESCRIPTION	"When parameter is read, it displays the 
			 current down stream (coe to cpe) rate which can
			 differ from the written value."
	::= { adslCapLineStatusEntry 8 }

   adslCapStatusVendorId   OBJECT-TYPE
	SYNTAX		INTEGER
	ACCESS		read-only
	STATUS		mandatory
	DESCRIPTION	"Vendor identification."
	::= { adslCapLineStatusEntry 9 }

   adslCapStatusMajorFirmWareVer	OBJECT-TYPE
	SYNTAX		INTEGER
	ACCESS		read-only
	STATUS		mandatory
	DESCRIPTION	"Major firmware version."
	::= { adslCapLineStatusEntry 10 }

   adslCapStatusMinorFirmWareVer	OBJECT-TYPE
	SYNTAX		INTEGER
	ACCESS		read-only
	STATUS		mandatory
	DESCRIPTION	"Minor firmware version."
	::= { adslCapLineStatusEntry 11 }

   adslCapStatusHardWareVer	OBJECT-TYPE
	SYNTAX		INTEGER
	ACCESS		read-only
	STATUS		mandatory
	DESCRIPTION	"Hardware version."
	::= { adslCapLineStatusEntry 12 }

    adslCapLineStatisticTable OBJECT-TYPE
	SYNTAX		SEQUENCE OF AdslCapLineStatisticEntry
	ACCESS		not-accessible
	STATUS		mandatory
	DESCRIPTION	"ADSL CAP statistical parameters."
	::= { wanTypeAdslCap 2 }

   adslCapLineStatisticEntry OBJECT-TYPE
	SYNTAX		AdslCapLineStatisticEntry
	ACCESS		not-accessible
	STATUS		mandatory
	DESCRIPTION	"A interface statistical entry containing objects to
			describe the interface."
	INDEX		{ adslCapStatIfEntryIndex }
	::= { adslCapLineStatisticTable 1 }

    AdslCapLineStatisticEntry ::=
	SEQUENCE {
	    adslCapStatIfEntryIndex
		INTEGER,
	    adslCapStatShelfIndex
		INTEGER,
	    adslCapStatSlotIndex
		INTEGER,
	    adslCapStatLineIndex
		INTEGER,
	    adslCapStatConnUpDays
		INTEGER,
	    adslCapStatConnUpHours
	        INTEGER,
	    adslCapStatConnUpMinutes
		INTEGER,
	    adslCapStatRxSignalPresent
		INTEGER,
	    adslCapStatLineQualityDb
		INTEGER,
	    adslCapStatUpDwnCntr
		INTEGER,
	    adslCapStatLineSelfTest
		INTEGER,
	    adslCapStatBertTimer
		INTEGER,
	    adslCapStatBertEna
		INTEGER,
	    adslCapStatBertState
		INTEGER,
	    adslCapStatBertErrorCounter
		INTEGER
	}

   adslCapStatIfEntryIndex    OBJECT-TYPE
	SYNTAX		INTEGER	(1..'7fffffff'h)
	ACCESS		read-only
	STATUS		mandatory
	DESCRIPTION	"Index into the Status Table via the interface group
			 ifIndex value."
	::= { adslCapLineStatisticEntry 1 }
   
   adslCapStatShelfIndex	OBJECT-TYPE
	SYNTAX		INTEGER
	ACCESS		read-only
	STATUS		mandatory
	DESCRIPTION	"ADSL CAP modules Shelf ID."
	::= { adslCapLineStatisticEntry 2 }

   adslCapStatSlotIndex	OBJECT-TYPE
	SYNTAX		INTEGER
	ACCESS		read-only
	STATUS		mandatory
	DESCRIPTION	"ADSL CAP modules Slot ID."
	::= { adslCapLineStatisticEntry 3 }

   adslCapStatLineIndex	OBJECT-TYPE
	SYNTAX		INTEGER
	ACCESS		read-only
	STATUS		mandatory
	DESCRIPTION	"ADSL CAP modules interface ID." 
	::= { adslCapLineStatisticEntry 4 }

   adslCapStatConnUpDays	OBJECT-TYPE
	SYNTAX		INTEGER
	ACCESS		read-only
	STATUS		mandatory
	DESCRIPTION	"Connection up day count."
	::= { adslCapLineStatisticEntry 5 }

   adslCapStatConnUpHours	OBJECT-TYPE
	SYNTAX		INTEGER
	ACCESS		read-only
	STATUS		mandatory
	DESCRIPTION	"Connection Up 24 hour count."
	::= { adslCapLineStatisticEntry 6 }

   adslCapStatConnUpMinutes	OBJECT-TYPE
	SYNTAX		INTEGER
	ACCESS		read-only
	STATUS		mandatory
	DESCRIPTION	"Connection up minute count."
	::= { adslCapLineStatisticEntry 7 }

   adslCapStatRxSignalPresent	OBJECT-TYPE
	SYNTAX		INTEGER {
			    no( 1 ),	-- LOS of signal detected. 
			    yes( 2 )	-- Receive signal present. 
			}
	ACCESS		read-only
	STATUS		mandatory
	DESCRIPTION	"Receive signal present detection."
	::= { adslCapLineStatisticEntry 8 }

  adslCapStatLineQualityDb OBJECT-TYPE
	SYNTAX		INTEGER
	ACCESS		read-only
	STATUS		mandatory
	DESCRIPTION	"Lines noise margin. Reliable data will transfer
			with a reading of -5db or greater."
	::= { adslCapLineStatisticEntry 9 }


    adslCapStatUpDwnCntr OBJECT-TYPE
	SYNTAX		INTEGER
	ACCESS		read-only
	STATUS		mandatory
	DESCRIPTION	"Line Up Down counter value displays the number
			of times the interface transitions from a down to up
			state."
	::= { adslCapLineStatisticEntry 10 }

    adslCapStatLineSelfTest    OBJECT-TYPE
	SYNTAX		INTEGER {
				other( 4 ),
				selfTestFailed( 1 ),	
				localLoopBackFailed( 2 ),
				passed( 3 )
			}
	ACCESS		read-only
	STATUS		mandatory
	DESCRIPTION	"Line hardware self test results (Passed or 
			 Failed)."
	::= { adslCapLineStatisticEntry 11 }

    adslCapStatBertTimer    OBJECT-TYPE
	SYNTAX		INTEGER {
				one-minute(1),
				two-minutes(2),
				three-minutes(3),
				four-minutes(4),
				five-minutes(5),
				ten-minutes(6),
				fifteen-minutes(7),
				twenty-minutes(8),
				thirty-minutes(9)
			}
	ACCESS		read-write
	STATUS		mandatory
	DESCRIPTION	"BER test duration configuration. When two nodes are
			 physically connected, the BER test lasts for the 
			 duration of this timer."
	::= { adslCapLineStatisticEntry 12 }
	
    adslCapStatBertEna    OBJECT-TYPE
	SYNTAX		INTEGER {
				no( 1 ),
				yes( 2 )
			}
	ACCESS		read-write
	STATUS		mandatory
	DESCRIPTION	"Enable/disable of the BER test. If nodes are
			 connected, then the BER test is ran between the
			 units. If this node is not connected to a remote 
			 node, then the interface is placed into analog 
			 loopback and the BER test is started."
	::= { adslCapLineStatisticEntry 13 }
	
    adslCapStatBertState    OBJECT-TYPE
	SYNTAX		INTEGER {
				waiting-for-511-sync(1),
				local-loop-active(2),
				active(3),
				stopped(4),
				loop-back-setup(5),
				start-up(6),
				data-overflow(7),
				ber-sync-loss(8)
			}
	ACCESS		read-only
	STATUS		mandatory
	DESCRIPTION	"BER test states. When this node is not connected to
			 anyother node, then the state enters
			 local-loop-active. When two nodes are conneced then
			 different states are transistioned through. If this
			 is the first node to enable the BER test, the state
			 will transistion from stopped to
			 waiting-for-511-sync. Now this node is waiting for 
			 the remote node to enable its BER test. Once the 
			 remote node enables its BER test, then both nodes 
			 enter the active state. At this point the BER test 
			 starts collecting bit errors."
	::= { adslCapLineStatisticEntry 14 }
	
    adslCapStatBertErrorCounter    OBJECT-TYPE
	SYNTAX		INTEGER
	ACCESS		read-only
	STATUS		mandatory
	DESCRIPTION	"BER test bit error counter."
	::= { adslCapLineStatisticEntry 15 }
	
END
