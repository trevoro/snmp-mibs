-- This MIB was created by extracting information from 
-- Sun Mangement Center 3.5 for use in other applications
-- to help determine what is actually listed in the SMC snmp 
-- agent. Sun has/will not release their MIBS for this 
-- information, so I created them from all information that
-- they have released.
--
-- Most all the information should be correct, but
-- if you find a discrepency please let me know. I do not
-- have all available Sun hardware to test with, so not 
-- not all types of support hardware has been tested.
-- These MIBs have only been tested using the utilities
-- from net-snmp. They may or may not work with other
-- applications.
-- 
-- The MIBs are not detailed, they only are useful in 
-- mapping OIDs to names. At some point in time 
-- descriptions may be given.
--
-- Author: Brian T. O'Neill (btoneill@misplaced.net)
-- Date: 7-30-2003 
-- Version: 0.9
--
-- No guarantees are given regarding the accuracy of this
-- data.
--
-- Note: The naming was done in line with the published
-- MIBS from Sun Microsystems.
--
--
TRAPS-SUNMANAGEMENTCENTER-MIB DEFINITIONS ::= BEGIN

  IMPORTS
	enterprises, NOTIFICATION-TYPE, OBJECT-TYPE, MODULE-IDENTITY
		FROM SNMPv2-SMI
		version FROM INFO-SUNMANAGEMENTCENTER-MIB;

trapList MODULE-IDENTITY
	LAST-UPDATED "0307291011Z"
	ORGANIZATION "none"
	CONTACT-INFO
		"Brian T. O'Neill
		E-mail: btoneill@misplaced.net"	
	DESCRIPTION
            "Trap defns for SMC, taken from the SMC 3.0 DE manual and put into a valid MIB format."
	
	REVISION  "0307291011Z"
	DESCRIPTION
		"Rev 0.1, Initial version of MIB."
	::= { modules 199 }

sun             OBJECT IDENTIFIER ::= { enterprises 42 }
prod            OBJECT IDENTIFIER ::= { sun 2 }
sunsymon        OBJECT IDENTIFIER ::= { prod 12 }
agent           OBJECT IDENTIFIER ::= { sunsymon 2 }
base            OBJECT IDENTIFIER ::= { agent 1 }
modules		OBJECT IDENTIFIER ::= { agent 2 }
--traps           OBJECT IDENTIFIER ::= { base 0 }
traps           OBJECT IDENTIFIER ::= { agent 0 }
trapInfo        OBJECT IDENTIFIER ::= { base 3 }

statusChange NOTIFICATION-TYPE
        OBJECTS { statusOID }
        STATUS current
        DESCRIPTION
        "A statusChange trap signifies that the status of an object has changed."
        ::= { traps 1 }

valueRefresh NOTIFICATION-TYPE
        OBJECTS { refreshOID }
        STATUS current
        DESCRIPTION
        "A valueRefresh trap signifies that the value of an object has been manually refreshed."
        ::= { traps 2 }

event NOTIFICATION-TYPE
        OBJECTS { eventInfo }
        STATUS current
        DESCRIPTION
        "An event trap signifies that an event has been detected and logged by the monitoring software."
        ::= { traps 3 }

moduleLoaded NOTIFICATION-TYPE
        OBJECTS { version }
        STATUS current
        DESCRIPTION
        "A moduleLoaded trap signifies that a module has been loaded."
        ::= { traps 4 }

moduleUnloaded NOTIFICATION-TYPE
        OBJECTS { version }
        STATUS current
        DESCRIPTION
        "A moduleUnloaded trap signifies that a module has been unloaded."
        ::= { traps 5 }

userConfig NOTIFICATION-TYPE
	OBJECTS { version }
	STATUS current
	DESCRIPTION
	"A userConfig trap signifies that something from a user happened."
	::= { traps 6 }

trapClient NOTIFICATION-TYPE
	OBJECTS { version }
	STATUS current
	DESCRIPTION
	"a trapClient is, well unknown to me at this time."
	::= { traps 7 }

userUpdate NOTIFICATION-TYPE
	OBJECTS { version }
	STATUS current 
	DESCRIPTION
	"a userUpdate is when a user is updated."
	::= { traps 8 }

statusOID OBJECT-TYPE
        SYNTAX OBJECT IDENTIFIER
        MAX-ACCESS accessible-for-notify
        STATUS current
        DESCRIPTION
        "The identification of the object for which the status changed. This occurs as the first trap-specific varbind in a statusChangeTrap."
        ::= { trapInfo 1 }

refreshOID OBJECT-TYPE
        SYNTAX OBJECT IDENTIFIER
        MAX-ACCESS accessible-for-notify
        STATUS current
        DESCRIPTION
        "The identification of the object for which the value was refreshed changed. This occurs as the first trap-specific varbind in a valueRefreshTrap."
        ::= { trapInfo 2 }

eventInfo OBJECT-TYPE
        SYNTAX OCTET STRING
        MAX-ACCESS accessible-for-notify
        STATUS current
        DESCRIPTION
        "The event message of the object for which an event was detected. This occurs as the first trap-specific varbind in an eventTrap."
        ::= { trapInfo 3 }

userConfig OBJECT-TYPE
        SYNTAX OCTET STRING
        MAX-ACCESS accessible-for-notify
        STATUS current
        DESCRIPTION
        "The event message of the object for which an event was detected. This occurs as the first trap-specific varbind in an eventTrap."
        ::= { trapInfo 4 }

moduleInfo OBJECT-TYPE
	SYNTAX OCTET STRING
	MAX-ACCESS accessible-for-notify
	STATUS current
	DESCRIPTION
	"module info for which an event happened."
	::= { trapInfo 5 }

END
