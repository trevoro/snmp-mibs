-- *****************************************************************************
-- Unisphere-Data-RADIUS-Client-CONF
--
-- SNMP Agent Capabilities definitions for the RADIUS Client MIB.
--
-- Copyright (c) 2001 Unisphere Networks, Inc.  All rights reserved.
-- *****************************************************************************

Unisphere-Data-RADIUS-Client-CONF DEFINITIONS ::= BEGIN

IMPORTS
    MODULE-IDENTITY, OBJECT-IDENTITY
        FROM SNMPv2-SMI
    AGENT-CAPABILITIES
        FROM SNMPv2-CONF
    usDataAgents
        FROM Unisphere-Data-Agents
    usdRadiusGeneralClientGroup, usdRadiusAuthClientGroup,
    usdRadiusAcctClientGroup, usdRadiusGeneralClientGroup2,
    usdRadiusBasicClientGroup, usdRadiusBrasClientGroup,
    usdRadiusTunnelClientGroup, usdRadiusBrasClientGroup2,
    usdRadiusBasicClientGroup2, usdRadiusBrasClientGroup3,
    usdRadiusBrasClientGroup4, usdRadiusBrasClientGroup5
        FROM Unisphere-Data-RADIUS-CLIENT-MIB;

usdRadiusClientAgent MODULE-IDENTITY
    LAST-UPDATED "200110191444Z"  -- 19-Oct-01 10:44 AM EDT
    ORGANIZATION "Unisphere Networks, Inc."
    CONTACT-INFO
        "       Unisphere Networks, Inc.
        Postal: 10 Technology Park Drive
                Westford, MA  01886
                USA
        Tel:    +1 978 589 5800
        E-mail: mib@UnisphereNetworks.com"
    DESCRIPTION
        "The agent capabilities definitions for the RADIUS Client component of
        the SNMP agent in the Unisphere Data Routing Switch family of products."
    -- Revision History
    REVISION    "200110191444Z"  -- 19-Oct-01 10:44 AM EDT  - RX 4.0
    DESCRIPTION
        "New objects were added to the BRAS group to indicate which RADIUS
        attributes should be included or excluded from RADIUS packets."
    REVISION    "200110162045Z"  -- 16-Oct-01 04:45 PM EDT  - RX 3.3
    DESCRIPTION
        "A new object was added to the BRAS group."
    REVISION    "200109071235Z"  -- 07-Sep-01 08:35 AM EDT  - RX 3.2
    DESCRIPTION
        "The initial release of this management information module."
    ::= { usDataAgents 35 }


-- *****************************************************************************
-- The Radius Client dynamic interface agent capabilities.
-- *****************************************************************************
usdRadiusClientDynamicAgent OBJECT-IDENTITY
    STATUS      current
    DESCRIPTION
        "The registration group of agent capabilities for RADIUS Client
        application which provides complete dynamic interface support in
        addition to basic authentication for CLI access."
    ::= { usdRadiusClientAgent 1 }

usdRadiusClientDynamicAgentV1 AGENT-CAPABILITIES
    PRODUCT-RELEASE
        "Version 1 of the RADIUS Client dynamic interface component of the
        Unisphere Routing Switch SNMP agent.  This version of the RADIUS Client
        component was supported in the Unisphere RX 1.x system releases."
    STATUS      obsolete
    DESCRIPTION
        "The MIB supported by the SNMP agent for the RADIUS Client dynamic
        interface application in the Unisphere Routing Switch.  These
        capabilities became obsolete when a new object was added."
    SUPPORTS    Unisphere-Data-RADIUS-CLIENT-MIB
        INCLUDES  {
            usdRadiusGeneralClientGroup,
            usdRadiusAuthClientGroup,
            usdRadiusAcctClientGroup }
    ::= { usdRadiusClientDynamicAgent 1 }

usdRadiusClientDynamicAgentV2 AGENT-CAPABILITIES
    PRODUCT-RELEASE
        "Version 2 of the RADIUS Client dynamic interface component of the
        Unisphere Routing Switch SNMP agent.  This version of the RADIUS Client
        component was supported in the Unisphere RX 2.x system releases."
    STATUS      obsolete
    DESCRIPTION
        "The MIB supported by the SNMP agent for the RADIUS Client dynamic
        interface application in the Unisphere Routing Switch.  These
        capabilities became obsolete when new objects were added."
    SUPPORTS    Unisphere-Data-RADIUS-CLIENT-MIB
        INCLUDES  {
            usdRadiusGeneralClientGroup2,
            usdRadiusAuthClientGroup,
            usdRadiusAcctClientGroup }
    ::= { usdRadiusClientDynamicAgent 2 }

usdRadiusClientDynamicAgentV3 AGENT-CAPABILITIES
    PRODUCT-RELEASE
        "Version 3 of the RADIUS Client dynamic interface component of the
        Unisphere Routing Switch SNMP agent.  This version of the RADIUS Client
        component was supported in the Unisphere RX 3.0 system release."
    STATUS      obsolete
    DESCRIPTION
        "The MIB supported by the SNMP agent for the RADIUS Client dynamic
        interface application in the Unisphere Routing Switch.  These
        capabilities became obsolete when new B-RAS objects were added."
    SUPPORTS    Unisphere-Data-RADIUS-CLIENT-MIB
        INCLUDES  {
            usdRadiusBasicClientGroup,
            usdRadiusBrasClientGroup,
            usdRadiusTunnelClientGroup,
            usdRadiusAuthClientGroup,
            usdRadiusAcctClientGroup }
    ::= { usdRadiusClientDynamicAgent 3 }

usdRadiusClientDynamicAgentV4 AGENT-CAPABILITIES
    PRODUCT-RELEASE
        "Version 4 of the RADIUS Client dynamic interface component of the
        Unisphere Routing Switch SNMP agent.  This version of the RADIUS Client
        component was supported in the Unisphere RX 3.1 system release."
    STATUS      obsolete
    DESCRIPTION
        "The MIB supported by the SNMP agent for the RADIUS Client dynamic
        interface application in the Unisphere Routing Switch.  These
        capabilities became obsolete when new objects were added."
    SUPPORTS    Unisphere-Data-RADIUS-CLIENT-MIB
        INCLUDES  {
            usdRadiusBasicClientGroup,
            usdRadiusBrasClientGroup2,
            usdRadiusTunnelClientGroup,
            usdRadiusAuthClientGroup,
            usdRadiusAcctClientGroup }
    ::= { usdRadiusClientDynamicAgent 4 }

usdRadiusClientDynamicAgentV5 AGENT-CAPABILITIES
    PRODUCT-RELEASE
        "Version 5 of the RADIUS Client dynamic interface component of the
        Unisphere Routing Switch SNMP agent.  This version of the RADIUS Client
        component was supported in the Unisphere RX 3.2 system release."
    STATUS      obsolete
    DESCRIPTION
        "The MIB supported by the SNMP agent for the RADIUS Client dynamic
        interface application in the Unisphere Routing Switch.  These
        capabilities became obsolete when a new object was added to the BRAS
        group."
    SUPPORTS    Unisphere-Data-RADIUS-CLIENT-MIB
        INCLUDES  {
            usdRadiusBasicClientGroup2,
            usdRadiusBrasClientGroup3,
            usdRadiusTunnelClientGroup,
            usdRadiusAuthClientGroup,
            usdRadiusAcctClientGroup }
    ::= { usdRadiusClientDynamicAgent 5 }

usdRadiusClientDynamicAgentV6 AGENT-CAPABILITIES
    PRODUCT-RELEASE
        "Version 6 of the RADIUS Client dynamic interface component of the
        Unisphere Routing Switch SNMP agent.  This version of the RADIUS Client
        component was supported in the Unisphere RX 3.3 and subsequent RX 3.x
        system releases."
    STATUS      obsolete
    DESCRIPTION
        "The MIB supported by the SNMP agent for the RADIUS Client dynamic
        interface application in the Unisphere Routing Switch.  These
        capabilities became obsolete when new objects were added to indicate
        which RADIUS attributes should be included or excluded from RADIUS
        packets."
    SUPPORTS    Unisphere-Data-RADIUS-CLIENT-MIB
        INCLUDES  {
            usdRadiusBasicClientGroup2,
            usdRadiusBrasClientGroup4,
            usdRadiusTunnelClientGroup,
            usdRadiusAuthClientGroup,
            usdRadiusAcctClientGroup }
    ::= { usdRadiusClientDynamicAgent 6 }

usdRadiusClientDynamicAgentV7 AGENT-CAPABILITIES
    PRODUCT-RELEASE
        "Version 7 of the RADIUS Client dynamic interface component of the
        Unisphere Routing Switch SNMP agent.  This version of the RADIUS Client
        component is supported in the Unisphere RX 4.0 and subsequent system
        releases."
    STATUS      current
    DESCRIPTION
        "The MIB supported by the SNMP agent for the RADIUS Client dynamic
        interface application in the Unisphere Routing Switch."
    SUPPORTS    Unisphere-Data-RADIUS-CLIENT-MIB
        INCLUDES  {
            usdRadiusBasicClientGroup2,
            usdRadiusBrasClientGroup5,
            usdRadiusTunnelClientGroup,
            usdRadiusAuthClientGroup,
            usdRadiusAcctClientGroup }
    ::= { usdRadiusClientDynamicAgent 7 }


-- *****************************************************************************
-- The Radius Client basic CLI access authentication agent capabilities.
-- *****************************************************************************
usdRadiusClientBasicAgent OBJECT-IDENTITY
    STATUS      current
    DESCRIPTION
        "The registration group of agent capabilities for the RADIUS Client
        application which only provides basic authentication for CLI access to a
        Unisphere data routing switch."
    ::= { usdRadiusClientAgent 2 }

usdRadiusClientBasicAgentV1 AGENT-CAPABILITIES
    PRODUCT-RELEASE
        "Version 1 of the basic authentication RADIUS Client component of the
        Unisphere Routing Switch SNMP agent.  This version of the RADIUS Client
        component is supported in the Unisphere RX 3.2 and subsequent system
        releases."
    STATUS      current
    DESCRIPTION
        "The MIB supported by the SNMP agent for the RADIUS Client basic
        authentication application which only supports basic authentication for
        remote CLI access in a Unisphere Data Routing Switch."
    SUPPORTS    Unisphere-Data-RADIUS-CLIENT-MIB
        INCLUDES  {
            usdRadiusBasicClientGroup2,
            usdRadiusAuthClientGroup }
    ::= { usdRadiusClientBasicAgent 1 }

END
