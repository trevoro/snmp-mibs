Wellfleet-E1-MIB DEFINITIONS ::= BEGIN

-- Created by mdl2asn version 3.1
-- Creation date: Wed Aug 30 16:40:37 EDT 1995


    IMPORTS

      IpAddress, Counter, Gauge, TimeTicks, Opaque, enterprises, mgmt
        FROM RFC1155-SMI
      OBJECT-TYPE
        FROM RFC-1212
      TRAP-TYPE
        FROM RFC-1215
      DisplayString, mib-2
        FROM RFC1213-MIB
      wfLine
        FROM Wellfleet-COMMON-MIB;


    wfE1Table OBJECT-TYPE
        SYNTAX	SEQUENCE OF WfE1Entry
        ACCESS	not-accessible
        STATUS	mandatory
        DESCRIPTION
                "E1 line record"
        ::= { wfLine 11 }

    wfE1Entry OBJECT-TYPE
        SYNTAX	WfE1Entry
        ACCESS	not-accessible
        STATUS	mandatory
        DESCRIPTION
                "An entry in the E1 table"
        INDEX	{ wfE1Slot,
    		  wfE1Connector }
        ::= { wfE1Table 1 }

    WfE1Entry ::= SEQUENCE {
    	    wfE1Delete
    		INTEGER,
    	    wfE1Disable
    		INTEGER,
    	    wfE1State
    		INTEGER,
    	    wfE1Slot
    		INTEGER,
    	    wfE1Connector
    		INTEGER,
    	    wfE1Madr
    		OCTET STRING,
    	    wfE1HDB3Support
    		INTEGER,
    	    wfE1ClockMode
    		INTEGER,
    	    wfE1MiniDacs
    		DisplayString,
    	    wfE1BipolarVios
    		Counter,
    	    wfE1FrameErrs
    		Counter,
    	    wfE1RcvRemAlms
    		Counter,
    	    wfE1RcvMfmAlms
    		Counter,
    	    wfE1MfsErrs
    		Counter,
    	    wfE1SyncLoss
    		Counter,
    	    wfE1RcvSig1s
    		Counter,
    	    wfE1RcvUnfrm1s
    		Counter,
    	    wfE1LineType
    		INTEGER,
    	    wfE1CRC4Errors
    		Counter
        }

    wfE1Delete OBJECT-TYPE
        SYNTAX	INTEGER {
    		    created(1),
    		    deleted(2)
    		}
        ACCESS	read-write
        STATUS	mandatory
        DESCRIPTION
                "create/delete parameter, dflt = created"
        DEFVAL	{ created }
        ::= { wfE1Entry 1 }

    wfE1Disable OBJECT-TYPE
        SYNTAX	INTEGER {
    		    enabled(1),
    		    disabled(2)
    		}
        ACCESS	read-write
        STATUS	mandatory
        DESCRIPTION
                "enable/disable parameter, dflt = enabled"
        DEFVAL	{ enabled }
        ::= { wfE1Entry 2 }

    wfE1State OBJECT-TYPE
        SYNTAX	INTEGER {
    		    up(1),
    		    init(3),
    		    notpresent(4)
    		}
        ACCESS	read-only
        STATUS	mandatory
        DESCRIPTION
                "line driver state variable, Not Present, Init, Up"
        DEFVAL	{ notpresent }
        ::= { wfE1Entry 3 }

    wfE1Slot OBJECT-TYPE
        SYNTAX	INTEGER(1..14)
        ACCESS	read-only
        STATUS	mandatory
        DESCRIPTION
                "instance ID Slot, filled in by driver"
        ::= { wfE1Entry 4 }

    wfE1Connector OBJECT-TYPE
        SYNTAX	INTEGER {
    		    one(1),
    		    two(2)
    		}
        ACCESS	read-only
        STATUS	mandatory
        DESCRIPTION
                "instance ID Connector, filled in by driver"
        ::= { wfE1Entry 5 }

    wfE1Madr OBJECT-TYPE
        SYNTAX	OCTET STRING
        ACCESS	read-only
        STATUS	mandatory
        DESCRIPTION
                "Line mac address, filled in by driver"
        ::= { wfE1Entry 6 }

    wfE1HDB3Support OBJECT-TYPE
        SYNTAX	INTEGER {
    		    enabled(1),
    		    disabled(2)
    		}
        ACCESS	read-write
        STATUS	mandatory
        DESCRIPTION
                "HDB3 Support - Enables or disables high density bipolar coding"
        DEFVAL	{ disabled }
        ::= { wfE1Entry 7 }

    wfE1ClockMode OBJECT-TYPE
        SYNTAX	INTEGER {
    		    internal(1),
    		    slave(2),
    		    manual(4)
    		}
        ACCESS	read-write
        STATUS	mandatory
        DESCRIPTION
                "Clock Mode - Specifies the source of the E1 transmit clock"
        DEFVAL	{ internal }
        ::= { wfE1Entry 8 }

    wfE1MiniDacs OBJECT-TYPE
        SYNTAX	DisplayString
        ACCESS	read-write
        STATUS	mandatory
        DESCRIPTION
                "MiniDacs Configuration - assigns each E1 channel to a specific
                function"
        ::= { wfE1Entry 9 }

    wfE1BipolarVios OBJECT-TYPE
        SYNTAX	Counter
        ACCESS	read-only
        STATUS	mandatory
        DESCRIPTION
                "Number of Bipolar Violations"
        ::= { wfE1Entry 10 }

    wfE1FrameErrs OBJECT-TYPE
        SYNTAX	Counter
        ACCESS	read-only
        STATUS	mandatory
        DESCRIPTION
                "Number of Frame errors"
        ::= { wfE1Entry 11 }

    wfE1RcvRemAlms OBJECT-TYPE
        SYNTAX	Counter
        ACCESS	read-only
        STATUS	mandatory
        DESCRIPTION
                "Number of remote alarms received"
        ::= { wfE1Entry 12 }

    wfE1RcvMfmAlms OBJECT-TYPE
        SYNTAX	Counter
        ACCESS	read-only
        STATUS	mandatory
        DESCRIPTION
                "Number of Multiframe Alarms Received"
        ::= { wfE1Entry 13 }

    wfE1MfsErrs OBJECT-TYPE
        SYNTAX	Counter
        ACCESS	read-only
        STATUS	mandatory
        DESCRIPTION
                "Number of instances of CAS Multiframe resync criteria met"
        ::= { wfE1Entry 14 }

    wfE1SyncLoss OBJECT-TYPE
        SYNTAX	Counter
        ACCESS	read-only
        STATUS	mandatory
        DESCRIPTION
                "Number of instances of sync loss"
        ::= { wfE1Entry 15 }

    wfE1RcvSig1s OBJECT-TYPE
        SYNTAX	Counter
        ACCESS	read-only
        STATUS	mandatory
        DESCRIPTION
                "Number of instances of receive signalling all 1's"
        ::= { wfE1Entry 16 }

    wfE1RcvUnfrm1s OBJECT-TYPE
        SYNTAX	Counter
        ACCESS	read-only
        STATUS	mandatory
        DESCRIPTION
                "Number of instances of Receive unframed all 1's"
        ::= { wfE1Entry 17 }

    wfE1LineType OBJECT-TYPE
        SYNTAX	INTEGER {
    		    e1(1),
    		    e1crc4(2)
    		}
        ACCESS	read-write
        STATUS	mandatory
        DESCRIPTION
                "Enable/Disable CRC-4"
        DEFVAL	{ e1 }
        ::= { wfE1Entry 18 }

    wfE1CRC4Errors OBJECT-TYPE
        SYNTAX	Counter
        ACCESS	read-only
        STATUS	mandatory
        DESCRIPTION
                "Count of CRC-4 Errors"
        ::= { wfE1Entry 19 }

    END  -- Wellfleet-E1-MIB
