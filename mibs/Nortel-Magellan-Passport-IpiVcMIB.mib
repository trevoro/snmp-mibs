Nortel-Magellan-Passport-IpiVcMIB
DEFINITIONS ::= BEGIN



IMPORTS

      OBJECT-TYPE
   FROM RFC-1212

      IpAddress
   FROM RFC1155-SMI

      components,
      passportMIBs
   FROM Nortel-Magellan-Passport-UsefulDefinitionsMIB

      Counter32,
      DisplayString,
      StorageType,
      RowStatus,
      Integer32,
      Unsigned32
   FROM Nortel-Magellan-Passport-StandardTextualConventionsMIB

      Hex,
      NonReplicated,
      EnterpriseDateAndTime,
      DigitString
   FROM Nortel-Magellan-Passport-TextualConventionsMIB;




-- LAST-UPDATED   "9903220000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     IpiVc Enterprise MIB."

ipiVcMIB OBJECT IDENTIFIER ::= { passportMIBs 53 }










-- 
-- IpiVc
-- 
-- The IP interface over VC allows access to the module for external 
-- network management.

ipivc OBJECT IDENTIFIER ::= { components 51 }



ipivcRowStatusTable OBJECT-TYPE
   SYNTAX     SEQUENCE OF IpivcRowStatusEntry
   ACCESS     not-accessible
   STATUS     mandatory
   DESCRIPTION
     "This entry controls the addition and deletion of 
      ipivc components."
::= { ipivc 1 }

ipivcRowStatusEntry OBJECT-TYPE
   SYNTAX     IpivcRowStatusEntry
   ACCESS     not-accessible
   STATUS     mandatory
   DESCRIPTION
     "A single entry in the table represents a single 
      ipivc component."
   INDEX {
      ipivcIndex }
::= { ipivcRowStatusTable 1 }

IpivcRowStatusEntry ::= SEQUENCE {
   ipivcRowStatus
      RowStatus,
   ipivcComponentName
      DisplayString,
   ipivcStorageType
      StorageType,
   ipivcIndex
      NonReplicated }

ipivcRowStatus OBJECT-TYPE
   SYNTAX     RowStatus 
   ACCESS     read-write
   STATUS     mandatory
   DESCRIPTION
     "This variable is used as the basis for SNMP naming of
      ipivc components.
      These components can be added and deleted."
::= { ipivcRowStatusEntry 1 }

ipivcComponentName OBJECT-TYPE
   SYNTAX     DisplayString 
   ACCESS     read-only
   STATUS     mandatory
   DESCRIPTION
     "This variable provides the component's string name for
      use with the ASCII Console Interface"
::= { ipivcRowStatusEntry 2 }

ipivcStorageType OBJECT-TYPE
   SYNTAX     StorageType 
   ACCESS     read-only
   STATUS     mandatory
   DESCRIPTION
     "This variable represents the storage type value for the
      ipivc tables."
::= { ipivcRowStatusEntry 4 }

ipivcIndex OBJECT-TYPE
   SYNTAX     NonReplicated 
   ACCESS     not-accessible
   STATUS     mandatory
   DESCRIPTION
     "This variable represents the index for the ipivc tables."
::= { ipivcRowStatusEntry 10 }

ipivcProvTable OBJECT-TYPE
   SYNTAX     SEQUENCE OF IpivcProvEntry
   ACCESS     not-accessible
   STATUS     mandatory
   DESCRIPTION
     "This group contains the provisionable attributes for the IpiVc 
      component."
::= { ipivc 10 }

ipivcProvEntry OBJECT-TYPE
   SYNTAX     IpivcProvEntry
   ACCESS     not-accessible
   STATUS     mandatory
   DESCRIPTION
     "An entry in the ipivcProvTable."
   INDEX {
      ipivcIndex }
::= { ipivcProvTable 1 }

IpivcProvEntry ::= SEQUENCE {
   ipivcIpAddress
      IpAddress,
   ipivcMaximumNumberOfLcn
      Unsigned32 }

ipivcIpAddress OBJECT-TYPE
   SYNTAX     IpAddress 
   ACCESS     read-write
   STATUS     mandatory
   DESCRIPTION
     "This IP Address represents the IP address of the IP interface."
   DEFVAL     { '00000000'H }  -- "0.0.0.0"
::= { ipivcProvEntry 1 }

ipivcMaximumNumberOfLcn OBJECT-TYPE
   SYNTAX     Unsigned32 (24)
   ACCESS     read-only
   STATUS     mandatory
   DESCRIPTION
     "This attribute contains the maximum number of LCNs that can be 
      setup to the IP Interface over Vc. It defines the maximum number of 
      calls that the external network management systems can setup to 
      IpiVc simultaneously."
   DEFVAL     { 24 }
::= { ipivcProvEntry 2 }


-- IpiVc Dna
-- This is the description of the generic Vc Dna Component. It 
-- includes the superset of all attributes which may apply to a VC. 
-- Particular applications will typically offer only a subset of these 
-- attributes by providing a definition of their own Dna subcomponent. 

ipivcDna OBJECT IDENTIFIER ::= { ipivc 2 }



ipivcDnaRowStatusTable OBJECT-TYPE
   SYNTAX     SEQUENCE OF IpivcDnaRowStatusEntry
   ACCESS     not-accessible
   STATUS     mandatory
   DESCRIPTION
     "This entry controls the addition and deletion of 
      ipivcDna components."
::= { ipivcDna 1 }

ipivcDnaRowStatusEntry OBJECT-TYPE
   SYNTAX     IpivcDnaRowStatusEntry
   ACCESS     not-accessible
   STATUS     mandatory
   DESCRIPTION
     "A single entry in the table represents a single 
      ipivcDna component."
   INDEX {
      ipivcIndex,
      ipivcDnaIndex }
::= { ipivcDnaRowStatusTable 1 }

IpivcDnaRowStatusEntry ::= SEQUENCE {
   ipivcDnaRowStatus
      RowStatus,
   ipivcDnaComponentName
      DisplayString,
   ipivcDnaStorageType
      StorageType,
   ipivcDnaIndex
      NonReplicated }

ipivcDnaRowStatus OBJECT-TYPE
   SYNTAX     RowStatus 
   ACCESS     read-only
   STATUS     mandatory
   DESCRIPTION
     "This variable is used as the basis for SNMP naming of
      ipivcDna components.
      These components cannot be added nor deleted."
::= { ipivcDnaRowStatusEntry 1 }

ipivcDnaComponentName OBJECT-TYPE
   SYNTAX     DisplayString 
   ACCESS     read-only
   STATUS     mandatory
   DESCRIPTION
     "This variable provides the component's string name for
      use with the ASCII Console Interface"
::= { ipivcDnaRowStatusEntry 2 }

ipivcDnaStorageType OBJECT-TYPE
   SYNTAX     StorageType 
   ACCESS     read-only
   STATUS     mandatory
   DESCRIPTION
     "This variable represents the storage type value for the
      ipivcDna tables."
::= { ipivcDnaRowStatusEntry 4 }

ipivcDnaIndex OBJECT-TYPE
   SYNTAX     NonReplicated 
   ACCESS     not-accessible
   STATUS     mandatory
   DESCRIPTION
     "This variable represents the index for the ipivcDna tables."
::= { ipivcDnaRowStatusEntry 10 }

ipivcDnaAddressTable OBJECT-TYPE
   SYNTAX     SEQUENCE OF IpivcDnaAddressEntry
   ACCESS     not-accessible
   STATUS     mandatory
   DESCRIPTION
     "DnaAddress group contains attributes common to all Dna's. Every 
      Dna used in the network is defined with this group 0f 2 attributes. 
      String of address digits is complemented by type of address and 
      Npi. These attributes are used to interpret format of the address 
      digits."
::= { ipivcDna 10 }

ipivcDnaAddressEntry OBJECT-TYPE
   SYNTAX     IpivcDnaAddressEntry
   ACCESS     not-accessible
   STATUS     mandatory
   DESCRIPTION
     "An entry in the ipivcDnaAddressTable."
   INDEX {
      ipivcIndex,
      ipivcDnaIndex }
::= { ipivcDnaAddressTable 1 }

IpivcDnaAddressEntry ::= SEQUENCE {
   ipivcDnaNumberingPlanIndicator
      INTEGER,
   ipivcDnaDataNetworkAddress
      DigitString }

ipivcDnaNumberingPlanIndicator OBJECT-TYPE
   SYNTAX     INTEGER  {
                 x121(0),
                 e164(1) }
   ACCESS     read-write
   STATUS     mandatory
   DESCRIPTION
     "This attribute indicates the Numbering Plan Indicator (NPI) of the 
      Dna that is entered. Address may belong to X.121 or E.164 plans. 
      X.121 is used in packet svitched data networks."
   DEFVAL     { x121 }
::= { ipivcDnaAddressEntry 1 }

ipivcDnaDataNetworkAddress OBJECT-TYPE
   SYNTAX     DigitString (SIZE (1..15))
   ACCESS     read-write
   STATUS     mandatory
   DESCRIPTION
     "Dna attribute contains digits which form unique identifier of the 
      customer. It is the equivalent of the telephone number in the 
      telephone network. MaximumLenOfDna is 15digits."
::= { ipivcDnaAddressEntry 2 }

ipivcDnaOutgoingOptionsTable OBJECT-TYPE
   SYNTAX     SEQUENCE OF IpivcDnaOutgoingOptionsEntry
   ACCESS     not-accessible
   STATUS     mandatory
   DESCRIPTION
     "DnaOutOptionsProv group defines call options of a Dna for calls 
      which are made out of the interface represented by Dna. All these 
      options are not used for calls arriving to the interface represented by 
      Dna."
::= { ipivcDna 11 }

ipivcDnaOutgoingOptionsEntry OBJECT-TYPE
   SYNTAX     IpivcDnaOutgoingOptionsEntry
   ACCESS     not-accessible
   STATUS     mandatory
   DESCRIPTION
     "An entry in the ipivcDnaOutgoingOptionsTable."
   INDEX {
      ipivcIndex,
      ipivcDnaIndex }
::= { ipivcDnaOutgoingOptionsTable 1 }

IpivcDnaOutgoingOptionsEntry ::= SEQUENCE {
   ipivcDnaOutCalls
      INTEGER,
   ipivcDnaOutDefaultPathSensitivity
      INTEGER,
   ipivcDnaOutPathSensitivityOverRide
      INTEGER,
   ipivcDnaDefaultTransferPriority
      INTEGER,
   ipivcDnaTransferPriorityOverRide
      INTEGER }

ipivcDnaOutCalls OBJECT-TYPE
   SYNTAX     INTEGER  {
                 disallowed(0),
                 allowed(1) }
   ACCESS     read-only
   STATUS     mandatory
   DESCRIPTION
     "This attribute, if set to a value of allowed indicates that outgoing 
      calls (from the DTE to the network) can be made using this 
      particular DNA. If set to a value of disallowed, then outgoing calls 
      cannot be made using this DNA - such calls will be cleared by the 
      local DCE. This attribute corresponds to the CCITT 'Outgoing Calls 
      Barred' feature for DNAs in that outgoing calls are barred if this 
      attribute is set to a value of disallowed. Either outCalls, or incCalls 
      (or both) must be set to a value of allowed for this DNA to be 
      useable."
   DEFVAL     { disallowed }
::= { ipivcDnaOutgoingOptionsEntry 1 }

ipivcDnaOutDefaultPathSensitivity OBJECT-TYPE
   SYNTAX     INTEGER  {
                 throughput(0),
                 delay(1) }
   ACCESS     read-write
   STATUS     obsolete
   DESCRIPTION
     "This attribute specifies the default class of path sensitivity to 
      network for all outgoing calls using this particular Dna. The chosen 
      default class of path sensitivity applies to all outgoing calls 
      established using this Dna. 
      
      This attribute, if set to a value of throughput, indicates that the 
      default class is throughput sensitive. If set to a value of delay, then 
      the default class is delay sensitive. The default of 
      outDefaultPathSensitivity is throughput."
   DEFVAL     { throughput }
::= { ipivcDnaOutgoingOptionsEntry 11 }

ipivcDnaOutPathSensitivityOverRide OBJECT-TYPE
   SYNTAX     INTEGER  {
                 no(0),
                 yes(1) }
   ACCESS     read-write
   STATUS     obsolete
   DESCRIPTION
     "If this attribute is set to in the call request, the called end will use 
      the calling end provisioning data on path sensitivity to override its 
      own provisioning data.
      
      The default of outPathSensitivityOverRide is no."
   DEFVAL     { no }
::= { ipivcDnaOutgoingOptionsEntry 12 }

ipivcDnaDefaultTransferPriority OBJECT-TYPE
   SYNTAX     INTEGER  {
                 normal(0),
                 high(9) }
   ACCESS     read-write
   STATUS     mandatory
   DESCRIPTION
     "This attribute specifies the default transfer priority to network for 
      all outgoing calls using this particular Dna. It is overRidden by 
      the transferPriority provisioned in the DLCI Direct Call sub-
      component.
      
      The transfer priority is a preference specified by an application 
      according to its delay-sensitivity requirement. Frames with high
      transfer priority are served by the network before the frames with 
      normal priority. 
      
      Each transfer priority contains a predetermined setting for trunk 
      queue (interrupting, delay or throughput), routing metric (delay or 
      throughput). 
      
      When the transfer priority is set at high, the trunk queue is set to 
      high, the routing metric is set to delay.
      
      When the transfer priority is set at normal, the trunk queue is set to 
      normal, the routing metric is set to throughput.
      
      The default of defaultTransferPriority is normal."
   DEFVAL     { normal }
::= { ipivcDnaOutgoingOptionsEntry 18 }

ipivcDnaTransferPriorityOverRide OBJECT-TYPE
   SYNTAX     INTEGER  {
                 no(0),
                 yes(1) }
   ACCESS     read-write
   STATUS     mandatory
   DESCRIPTION
     "When this attribute is set to yes, the called end will use the calling 
      end provisioning data on transfer priority to override its own 
      provisioning data. If it is set no, the called end will use its own 
      provisioning data on transfer priority.
      
      For more information about transfer priority, please refer to the 
      previous attribute defaultTransferPriority.
      
      The default of transferPriorityOverRide is no."
   DEFVAL     { no }
::= { ipivcDnaOutgoingOptionsEntry 19 }

ipivcDnaIncomingOptionsTable OBJECT-TYPE
   SYNTAX     SEQUENCE OF IpivcDnaIncomingOptionsEntry
   ACCESS     not-accessible
   STATUS     mandatory
   DESCRIPTION
     "DnaIncOptions defines set of options for incoming calls. These 
      options are used for calls arriving to the interface represented by 
      Dna. For calls originated from the interfasce, IncomingOptions 
      attributes are not used."
::= { ipivcDna 12 }

ipivcDnaIncomingOptionsEntry OBJECT-TYPE
   SYNTAX     IpivcDnaIncomingOptionsEntry
   ACCESS     not-accessible
   STATUS     mandatory
   DESCRIPTION
     "An entry in the ipivcDnaIncomingOptionsTable."
   INDEX {
      ipivcIndex,
      ipivcDnaIndex }
::= { ipivcDnaIncomingOptionsTable 1 }

IpivcDnaIncomingOptionsEntry ::= SEQUENCE {
   ipivcDnaIncCalls
      INTEGER,
   ipivcDnaIncHighPriorityReverseCharge
      INTEGER,
   ipivcDnaIncNormalPriorityReverseCharge
      INTEGER,
   ipivcDnaIncIntlNormalCharge
      INTEGER,
   ipivcDnaIncIntlReverseCharge
      INTEGER,
   ipivcDnaIncFastSelect
      INTEGER,
   ipivcDnaIncSameService
      INTEGER,
   ipivcDnaIncChargeTransfer
      INTEGER,
   ipivcDnaIncAccess
      INTEGER }

ipivcDnaIncCalls OBJECT-TYPE
   SYNTAX     INTEGER  {
                 disallowed(0),
                 allowed(1) }
   ACCESS     read-only
   STATUS     mandatory
   DESCRIPTION
     "This attribute, if set to a value of allowed  indicates that incoming 
      calls (from the network to the DTE) can be made to this DNA. If set 
      to a value of disallowed, then incoming calls cannot be made to this 
      DNA - such calls will be cleared by the local DCE. This attribute 
      corresponds to the CCITT 'Incoming Calls Barred' feature for 
      DNAs in that incoming calls are barred if this attribute is set to a 
      value of disallowed.
      
      Either outCalls, or incCalls (or both) must be set to a value of 
      allowed for this DNA to be useable."
   DEFVAL     { allowed }
::= { ipivcDnaIncomingOptionsEntry 1 }

ipivcDnaIncHighPriorityReverseCharge OBJECT-TYPE
   SYNTAX     INTEGER  {
                 disallowed(0),
                 allowed(1) }
   ACCESS     read-only
   STATUS     mandatory
   DESCRIPTION
     "This attribute, if set to a value of allowed indicates that incoming 
      high priority, reverse charged calls (from the network to the DTE) 
      can be made to this DNA. If set to a value of disallowed, then such 
      calls cannot be made to this DNA - such calls will be cleared by the 
      local DCE.
      This attribute, together with the 
      incNormalPriorityReverseChargeCalls attribute corresponds to the 
      CCITT 'Reverse Charging Acceptance' feature for DNAs in that 
      reverse charged calls are accepted if both attributes are set to a 
      value of allowed.
      This attribute is ignored if the corresponding attribute, incCalls is 
      set to a value of disallowed."
   DEFVAL     { allowed }
::= { ipivcDnaIncomingOptionsEntry 2 }

ipivcDnaIncNormalPriorityReverseCharge OBJECT-TYPE
   SYNTAX     INTEGER  {
                 disallowed(0),
                 allowed(1) }
   ACCESS     read-only
   STATUS     mandatory
   DESCRIPTION
     "This attribute, if set to a value of allowed indicates that incoming 
      normal priority, reverse charged calls (from the network to the 
      DTE) can be made to this DNA. If set to a value of disallowed, then 
      such calls cannot be made to this DNA - such calls will be cleared 
      by the local DCE. 
      This attribute, together with the 
      incHighPriorityReverseChargeCalls attribute corresponds to the 
      CCITT 'Reverse Charging Acceptance' feature for DNAs in that 
      reverse charged calls are accepted if both attributes are set to a 
      value of allowed.
      This attribute is ignored if the corresponding attribute, incCalls is 
      set to a value of disallowed."
   DEFVAL     { allowed }
::= { ipivcDnaIncomingOptionsEntry 3 }

ipivcDnaIncIntlNormalCharge OBJECT-TYPE
   SYNTAX     INTEGER  {
                 disallowed(0),
                 allowed(1) }
   ACCESS     read-only
   STATUS     mandatory
   DESCRIPTION
     "This attribute, if set to a value of allowed indicates that incoming 
      international normal charged calls (from the network to the DTE) 
      can be made to this DNA. If set to a value of disallowed, then such 
      calls cannot be made to this DNA - such calls will be cleared by the 
      local DCE.
      This attribute also currently controls access to/from the E.164 
      numbering plan, and if set to a value of allowed, then cross-
      numbering plan calls (also normal charged) are allowed. 
      This attribute is ignored if the corresponding attribute, incCalls is 
      set to a value of disallowed."
   DEFVAL     { allowed }
::= { ipivcDnaIncomingOptionsEntry 4 }

ipivcDnaIncIntlReverseCharge OBJECT-TYPE
   SYNTAX     INTEGER  {
                 disallowed(0),
                 allowed(1) }
   ACCESS     read-only
   STATUS     mandatory
   DESCRIPTION
     "This attribute, if set to a value of allowed indicates that incoming 
      international reverse charged calls (from the network to the DTE) 
      can be made to this DNA. If set to a value of disallowed, then such 
      calls cannot be made to this DNA - such calls will be cleared by the 
      local DCE.
      This attribute also currently controls access to/from the E.164 
      numbering plan, and if set to a value of allowed, then cross-
      numbering plan calls (also normal charged) are allowed.
      This attribute is ignored if the corresponding attribute, incCalls is 
      set to a value of disallowed."
   DEFVAL     { allowed }
::= { ipivcDnaIncomingOptionsEntry 5 }

ipivcDnaIncFastSelect OBJECT-TYPE
   SYNTAX     INTEGER  {
                 disallowed(0),
                 allowed(1) }
   ACCESS     read-only
   STATUS     mandatory
   DESCRIPTION
     "This attribute specifies whether fast select calls may be received.
      This attribute, if set to a value of allowed indicates that incoming 
      fast select calls (from the network to the DTE) can be made to this 
      DNA. If set to a value of disallowed, then such calls cannot be 
      made to this DNA - such calls will be cleared by the local DCE.
      This attribute corresponds to the CCITT 'Fast Select Acceptance' 
      feature for DNAs in that incoming fast select calls are accepted if 
      this attribute is set to a value of allowed.
      This attribute is ignored if the corresponding attribute, incCalls is 
      set to a value of disallowed."
   DEFVAL     { disallowed }
::= { ipivcDnaIncomingOptionsEntry 6 }

ipivcDnaIncSameService OBJECT-TYPE
   SYNTAX     INTEGER  {
                 disallowed(0),
                 allowed(1) }
   ACCESS     read-only
   STATUS     mandatory
   DESCRIPTION
     "This attribute, if set to a value of allowed indicates that incoming 
      calls from the same service type (eg: X.25, ITI, SNA) (from the 
      network to the DTE) can be made to this DNA. If set to a value of 
      disallowed, then such calls cannot be made to this DNA - such calls 
      will be cleared by the local DCE.
      This attribute is ignored if the corresponding attribute, incCalls is 
      set to a value of disallowed."
   DEFVAL     { allowed }
::= { ipivcDnaIncomingOptionsEntry 7 }

ipivcDnaIncChargeTransfer OBJECT-TYPE
   SYNTAX     INTEGER  {
                 no(0),
                 yes(1) }
   ACCESS     read-only
   STATUS     mandatory
   DESCRIPTION
     "This attribute, if set to a value of yes indicates that the charges for 
      incoming normal charged calls from a DTE with the same NIC 
      (calls from the network to the DTE) will be transferred to the called 
      DTE. If set to a value of no, then charges will not be transferred.
      This attribute is ignored if the corresponding attribute, incCalls is 
      set to a value of disallowed."
   DEFVAL     { no }
::= { ipivcDnaIncomingOptionsEntry 8 }

ipivcDnaIncAccess OBJECT-TYPE
   SYNTAX     INTEGER  {
                 disallowed(0),
                 allowed(1) }
   ACCESS     read-only
   STATUS     mandatory
   DESCRIPTION
     "This attribute is an extension of the Closed User Group (CUG) 
      facility, as follows:
      This attribute, if set to a value of allowed indicates that incoming 
      calls (from the network to the DTE) from the open (non-CUG) part 
      of the network are permitted. It also permits incoming calls from 
      DTEs that have Outgoing Access capabilities. If set to a value of 
      disallowed, then such calls cannot be made to this DNA - such calls 
      will be cleared by the local DCE.
      This attribute corresponds to the CCITT 'Closed User Group with 
      Incoming Access' feature for DNAs in that incoming access is 
      granted if this attribute is set to a value of allowed."
   DEFVAL     { disallowed }
::= { ipivcDnaIncomingOptionsEntry 9 }

ipivcDnaCallOptionsTable OBJECT-TYPE
   SYNTAX     SEQUENCE OF IpivcDnaCallOptionsEntry
   ACCESS     not-accessible
   STATUS     mandatory
   DESCRIPTION
     "DnaCallOptions group defines additional options for calls not 
      related directly to direction of a call."
::= { ipivcDna 13 }

ipivcDnaCallOptionsEntry OBJECT-TYPE
   SYNTAX     IpivcDnaCallOptionsEntry
   ACCESS     not-accessible
   STATUS     mandatory
   DESCRIPTION
     "An entry in the ipivcDnaCallOptionsTable."
   INDEX {
      ipivcIndex,
      ipivcDnaIndex }
::= { ipivcDnaCallOptionsTable 1 }

IpivcDnaCallOptionsEntry ::= SEQUENCE {
   ipivcDnaServiceCategory
      INTEGER,
   ipivcDnaPacketSizes
      OCTET STRING,
   ipivcDnaDefaultRecvFrmNetworkPacketSize
      INTEGER,
   ipivcDnaDefaultSendToNetworkPacketSize
      INTEGER,
   ipivcDnaDefaultRecvFrmNetworkThruputClass
      Unsigned32,
   ipivcDnaDefaultSendToNetworkThruputClass
      Unsigned32,
   ipivcDnaDefaultRecvFrmNetworkWindowSize
      Unsigned32,
   ipivcDnaDefaultSendToNetworkWindowSize
      Unsigned32,
   ipivcDnaPacketSizeNegotiation
      INTEGER,
   ipivcDnaAccountClass
      Unsigned32,
   ipivcDnaServiceExchange
      Unsigned32,
   ipivcDnaCugFormat
      INTEGER,
   ipivcDnaCug0AsNonCugCall
      INTEGER,
   ipivcDnaFastSelectCallsOnly
      INTEGER }

ipivcDnaServiceCategory OBJECT-TYPE
   SYNTAX     INTEGER  {
                 gsp(0),
                 x25(1),
                 enhancedIti(2),
                 ncs(3),
                 mlti(4),
                 sm(5),
                 ici(6),
                 dsp3270(7),
                 iam(8),
                 mlhi(9),
                 term3270(10),
                 iti(11),
                 bsi(13),
                 hostIti(14),
                 x75(15),
                 hdsp3270(16),
                 api3201(20),
                 sdlc(21),
                 snaMultiHost(22),
                 redirectionServ(23),
                 trSnaTpad(24),
                 offnetNui(25),
                 gasServer(26),
                 vapServer(28),
                 vapAgent(29),
                 frameRelay(30),
                 ipiVc(31) }
   ACCESS     read-only
   STATUS     mandatory
   DESCRIPTION
     "This attribute is computed based on the type of service within which 
      this DNA is configured. It is placed into the Service Category 
      attributes in the accounting record by both ends of the VC."
   DEFVAL     { ipiVc }
::= { ipivcDnaCallOptionsEntry 1 }

ipivcDnaPacketSizes OBJECT-TYPE
   SYNTAX     OCTET STRING (SIZE (2))
   ACCESS     read-only
   STATUS     mandatory
   DESCRIPTION
     "This attribute indicates the allowable packet sizes supported for 
      calls setup using this DNA.  To set a given packet size to be allowed 
      on the DNA, the packet size is entered, and the corresponding bit in 
      the structure is set to a value of 1.  To set a given packet size to be 
      disallowed on the DNA, the packet size is entered preceeded with 
      the '~' character, and the corresponding bit in the structure is set to a 
      value of 0. CCITT recommends that packet size 128 always be 
      supported.

      Description of bits:
      n16(0)
      n32(1)
      n64(2)
      n128(3)
      n256(4)
      n512(5)
      n1024(6)
      n2048(7)
      n4096(8)"
   DEFVAL     { '0100'H }
::= { ipivcDnaCallOptionsEntry 2 }

ipivcDnaDefaultRecvFrmNetworkPacketSize OBJECT-TYPE
   SYNTAX     INTEGER  {
                 n16(4),
                 n32(5),
                 n64(6),
                 n128(7),
                 n256(8),
                 n512(9),
                 n1024(10),
                 n2048(11),
                 n4096(12) }
   ACCESS     read-only
   STATUS     mandatory
   DESCRIPTION
     "This attribute indicates the default local receive packet size from 
      network to DTE for all calls using this particular DNA."
   DEFVAL     { n2048 }
::= { ipivcDnaCallOptionsEntry 3 }

ipivcDnaDefaultSendToNetworkPacketSize OBJECT-TYPE
   SYNTAX     INTEGER  {
                 n16(4),
                 n32(5),
                 n64(6),
                 n128(7),
                 n256(8),
                 n512(9),
                 n1024(10),
                 n2048(11),
                 n4096(12) }
   ACCESS     read-only
   STATUS     mandatory
   DESCRIPTION
     "This attribute indicates the default local send packet size from DTE 
      to network for all calls using this particular DNA."
   DEFVAL     { n2048 }
::= { ipivcDnaCallOptionsEntry 4 }

ipivcDnaDefaultRecvFrmNetworkThruputClass OBJECT-TYPE
   SYNTAX     Unsigned32 (0..15)
   ACCESS     read-only
   STATUS     mandatory
   DESCRIPTION
     "This attribute indicates the default receive throughput class for all 
      calls using this particular DNA."
   DEFVAL     { 10 }
::= { ipivcDnaCallOptionsEntry 5 }

ipivcDnaDefaultSendToNetworkThruputClass OBJECT-TYPE
   SYNTAX     Unsigned32 (0..15)
   ACCESS     read-only
   STATUS     mandatory
   DESCRIPTION
     "This attribute indicates the default send throughput class for all calls 
      using this particular DNA."
   DEFVAL     { 10 }
::= { ipivcDnaCallOptionsEntry 6 }

ipivcDnaDefaultRecvFrmNetworkWindowSize OBJECT-TYPE
   SYNTAX     Unsigned32 (1..7)
   ACCESS     read-only
   STATUS     mandatory
   DESCRIPTION
     "This attribute indicates the default number of data packets that can 
      be received by the DTE from the DCE before more packets can be 
      received. This view is oriented with respect to the DTE."
   DEFVAL     { 2 }
::= { ipivcDnaCallOptionsEntry 7 }

ipivcDnaDefaultSendToNetworkWindowSize OBJECT-TYPE
   SYNTAX     Unsigned32 (1..7)
   ACCESS     read-only
   STATUS     mandatory
   DESCRIPTION
     "This attribute indicates the number of data packets that can be 
      transmitted from the DTE to the DCE and must be acknowledged 
      before more packets can be transmitted."
   DEFVAL     { 2 }
::= { ipivcDnaCallOptionsEntry 8 }

ipivcDnaPacketSizeNegotiation OBJECT-TYPE
   SYNTAX     INTEGER  {
                 endToEnd(0),
                 local(1) }
   ACCESS     read-only
   STATUS     mandatory
   DESCRIPTION
     "This attribute, if set to a value of local indicates that packet sizes 
      can be negotiated locally at the interface irrespective of the remote 
      interface. If set to a value of endtoEnd, then local negotiation is not 
      permitted and packet sizes are negotiated between 2 ends of Vc."
   DEFVAL     { local }
::= { ipivcDnaCallOptionsEntry 9 }

ipivcDnaAccountClass OBJECT-TYPE
   SYNTAX     Unsigned32 (0..255)
   ACCESS     read-write
   STATUS     mandatory
   DESCRIPTION
     "This attribute specifies the accounting class which is reserved for 
      network operations usage. Its value is returned in the accounting 
      record in the local and remote service type attributes. Use of this 
      attribute is decided by network operator.
      This attribute is returned by the local VC in the accounting record 
      for all calls setup using this particular DNA."
   DEFVAL     { 0 }
::= { ipivcDnaCallOptionsEntry 10 }

ipivcDnaServiceExchange OBJECT-TYPE
   SYNTAX     Unsigned32 (0..255)
   ACCESS     read-write
   STATUS     mandatory
   DESCRIPTION
     "This attribute is an arbitrary number, Data Service Exchange, as 
      entered by the network operator and reported in accounting record. 
      It is converted into an internal 8-bit integer value for use in the 
      accounting record as well as in various X.25 and X.75 Tariff 
      utilities."
   DEFVAL     { 0 }
::= { ipivcDnaCallOptionsEntry 12 }

ipivcDnaCugFormat OBJECT-TYPE
   SYNTAX     INTEGER  {
                 basic(0),
                 extended(1) }
   ACCESS     read-only
   STATUS     mandatory
   DESCRIPTION
     "This attribute specifies which cug format is used when DTE signals 
      CUG indices, basic or extended.
      This attribute, if set to a value of extended indicates that the DTE 
      signals and receives CUG indices in extended CUG format.  If set 
      to a value of basic, then the DTE signals and receives CUG indices 
      in the basic CUG format."
   DEFVAL     { basic }
::= { ipivcDnaCallOptionsEntry 13 }

ipivcDnaCug0AsNonCugCall OBJECT-TYPE
   SYNTAX     INTEGER  {
                 disallowed(0),
                 allowed(1) }
   ACCESS     read-only
   STATUS     mandatory
   DESCRIPTION
     "This attribute, if set to a value of allowed indicates that when a 
      CUG index of 0 is signalled in a call request packet, the call is 
      treated as a non-CUG call.  If this attribute is set to a value of 
      disallowed, then a CUG index of 0 is treated as an index, and an 
      attempt is made to find the particular CUG corresponding with the 
      DNA."
   DEFVAL     { disallowed }
::= { ipivcDnaCallOptionsEntry 14 }

ipivcDnaFastSelectCallsOnly OBJECT-TYPE
   SYNTAX     INTEGER  {
                 no(0),
                 yes(1) }
   ACCESS     read-only
   STATUS     mandatory
   DESCRIPTION
     "This attribute, if set to a value of yes, indicates that the service is 
      permitted restricted fast select calls only in both the incoming and 
      the outgoing directions using this DNA. If set to a value of no, then 
      non fast select calls are permitted as well."
   DEFVAL     { no }
::= { ipivcDnaCallOptionsEntry 17 }


-- IpiVc Dna Cug
-- ClosedUserGroup options defines options associated with national 
-- or international Cug Identifier. Other Dna's in the network can have 
-- Cug's defined which groups these Dna's by Cug InterlockCode. If 
-- Dna's are defined with Cugs, calls from Dna's which do not have 
-- the same interlockCode defined are refused. Attributes incAccess 
-- and outAccess can override this rule.

ipivcDnaCug OBJECT IDENTIFIER ::= { ipivcDna 2 }



ipivcDnaCugRowStatusTable OBJECT-TYPE
   SYNTAX     SEQUENCE OF IpivcDnaCugRowStatusEntry
   ACCESS     not-accessible
   STATUS     mandatory
   DESCRIPTION
     "This entry controls the addition and deletion of 
      ipivcDnaCug components."
::= { ipivcDnaCug 1 }

ipivcDnaCugRowStatusEntry OBJECT-TYPE
   SYNTAX     IpivcDnaCugRowStatusEntry
   ACCESS     not-accessible
   STATUS     mandatory
   DESCRIPTION
     "A single entry in the table represents a single 
      ipivcDnaCug component."
   INDEX {
      ipivcIndex,
      ipivcDnaIndex,
      ipivcDnaCugIndex }
::= { ipivcDnaCugRowStatusTable 1 }

IpivcDnaCugRowStatusEntry ::= SEQUENCE {
   ipivcDnaCugRowStatus
      RowStatus,
   ipivcDnaCugComponentName
      DisplayString,
   ipivcDnaCugStorageType
      StorageType,
   ipivcDnaCugIndex
      NonReplicated }

ipivcDnaCugRowStatus OBJECT-TYPE
   SYNTAX     RowStatus 
   ACCESS     read-only
   STATUS     mandatory
   DESCRIPTION
     "This variable is used as the basis for SNMP naming of
      ipivcDnaCug components.
      These components cannot be added nor deleted."
::= { ipivcDnaCugRowStatusEntry 1 }

ipivcDnaCugComponentName OBJECT-TYPE
   SYNTAX     DisplayString 
   ACCESS     read-only
   STATUS     mandatory
   DESCRIPTION
     "This variable provides the component's string name for
      use with the ASCII Console Interface"
::= { ipivcDnaCugRowStatusEntry 2 }

ipivcDnaCugStorageType OBJECT-TYPE
   SYNTAX     StorageType 
   ACCESS     read-only
   STATUS     mandatory
   DESCRIPTION
     "This variable represents the storage type value for the
      ipivcDnaCug tables."
::= { ipivcDnaCugRowStatusEntry 4 }

ipivcDnaCugIndex OBJECT-TYPE
   SYNTAX     NonReplicated 
   ACCESS     not-accessible
   STATUS     mandatory
   DESCRIPTION
     "This variable represents the index for the ipivcDnaCug tables."
::= { ipivcDnaCugRowStatusEntry 10 }

ipivcDnaCugCugOptionsTable OBJECT-TYPE
   SYNTAX     SEQUENCE OF IpivcDnaCugCugOptionsEntry
   ACCESS     not-accessible
   STATUS     mandatory
   DESCRIPTION
     "This group defines options for Dna closed user group. Attributes in 
      this group define options associated with interlockCode. Dna's with 
      the same Cug (interlockCode) can make calls within this group. 
      Various combinations which permit or prevent calls in the same Cug 
      group are defined here."
::= { ipivcDnaCug 10 }

ipivcDnaCugCugOptionsEntry OBJECT-TYPE
   SYNTAX     IpivcDnaCugCugOptionsEntry
   ACCESS     not-accessible
   STATUS     mandatory
   DESCRIPTION
     "An entry in the ipivcDnaCugCugOptionsTable."
   INDEX {
      ipivcIndex,
      ipivcDnaIndex,
      ipivcDnaCugIndex }
::= { ipivcDnaCugCugOptionsTable 1 }

IpivcDnaCugCugOptionsEntry ::= SEQUENCE {
   ipivcDnaCugType
      INTEGER,
   ipivcDnaCugDnic
      DigitString,
   ipivcDnaCugInterlockCode
      Unsigned32,
   ipivcDnaCugOutCalls
      INTEGER,
   ipivcDnaCugIncCalls
      INTEGER,
   ipivcDnaCugPrivileged
      INTEGER }

ipivcDnaCugType OBJECT-TYPE
   SYNTAX     INTEGER  {
                 national(0),
                 international(1) }
   ACCESS     read-write
   STATUS     mandatory
   DESCRIPTION
     "This attribute specifies the CUG type - the CUG is either a national 
      CUG, or an international CUG.  International closed user groups are 
      usually established between DTEs for which there is an X.75 
      Gateway between; whereas national closed user groups are usually 
      established between DTEs for which there is no X.75 Gateway 
      between.  (National CUGs cannot normally traverse an X.75 
      Gateway).
      If this attribute is set to national, then the CUG is a national CUG, 
      in which case, the DNIC should be left at its default value of 
      BCD.0000 since it is not part of a national CUG.  If this attribute is 
      set to international, then the CUG is an international CUG, in 
      which case, the DNIC should be set appropriately as part of the 
      CUG interlock code."
   DEFVAL     { national }
::= { ipivcDnaCugCugOptionsEntry 1 }

ipivcDnaCugDnic OBJECT-TYPE
   SYNTAX     DigitString (SIZE (4))
   ACCESS     read-write
   STATUS     mandatory
   DESCRIPTION
     "This attribute specifies the DNIC (Data Network ID Code) of the 
      Cug by which packet networks are identified if the Cug is an 
      International Cug - it is specified as 4 BCD digits. This attribute is 
      not applicable if the Cug is a National Cug, as specified by the Cug 
      TYPE attribute. There are usually 1 or 2 DNICs assigned per 
      country, for public networks. The U.S. is an exception where each 
      BOC has a DNIC. Also, a group of private networks can have its 
      own DNIC.
      
      DNIC value is not an arbitrary number. It is assigned by 
      international aggreement and controlled by CCITT."
   DEFVAL     { '30303030'H }  -- "0000"
::= { ipivcDnaCugCugOptionsEntry 2 }

ipivcDnaCugInterlockCode OBJECT-TYPE
   SYNTAX     Unsigned32 (0..65535)
   ACCESS     read-write
   STATUS     mandatory
   DESCRIPTION
     "This attribute specifies the Cug Identifier of a national or 
      international Cug call. It is an arbitrary number and it also can be 
      called Cug in some descriptions. Interfaces (Dna's) defined with 
      this number can make calls to Dna's with the same interlockCode."
   DEFVAL     { 0 }
::= { ipivcDnaCugCugOptionsEntry 3 }

ipivcDnaCugOutCalls OBJECT-TYPE
   SYNTAX     INTEGER  {
                 disallowed(0),
                 allowed(1) }
   ACCESS     read-only
   STATUS     mandatory
   DESCRIPTION
     "This attribute, if set to a value of allowed indicates that outgoing 
      calls (from the DTE into the network) can be made using this 
      particular CUG. If set to a value of disallowed, then outgoing calls 
      cannot be made using this CUG - such calls will be cleared by the 
      local DCE.
      This attribute corresponds to the CCITT 'Outgoing Calls Barred' 
      feature for CUGs in that outgoing calls are barred if this attribute is 
      set to a value of disallowed."
   DEFVAL     { disallowed }
::= { ipivcDnaCugCugOptionsEntry 5 }

ipivcDnaCugIncCalls OBJECT-TYPE
   SYNTAX     INTEGER  {
                 disallowed(0),
                 allowed(1) }
   ACCESS     read-only
   STATUS     mandatory
   DESCRIPTION
     "This attribute, if set to a value of allowed indicates that incoming 
      calls (from the network to the DTE) can be made using this 
      particular CUG. If set to a value of disallowed, then incoming calls 
      cannot be made using this CUG - such calls will be cleared by the 
      local DCE.
      This attribute corresponds to the CCITT 'Incoming Calls Barred' 
      feature for CUGs in that incoming calls are barred if this attribute is 
      set to a value of disallowed."
   DEFVAL     { allowed }
::= { ipivcDnaCugCugOptionsEntry 6 }

ipivcDnaCugPrivileged OBJECT-TYPE
   SYNTAX     INTEGER  {
                 no(0),
                 yes(1) }
   ACCESS     read-write
   STATUS     mandatory
   DESCRIPTION
     "This attribute, if set to a value of yes indicates that this CUG is a 
      privileged CUG.  In DPN, at least one side of a call setup within a 
      CUG must have the CUG as a privileged CUG.  If set to a value of 
      no, then the CUG is not privileged.
      If both the local DTE and the remote DTE subscribe to the CUG, 
      but it is not privileged, then the call will be cleared.  This attribute is 
      typically used for a host DTE which must accept calls from many 
      other DTEs in which case the other DTEs cannot call one another, 
      but can call the host.  In this example, the host would have the 
      privileged CUG, and the other DTEs would belong to the same 
      CUG, but it would not be privileged."
   DEFVAL     { yes }
::= { ipivcDnaCugCugOptionsEntry 7 }


-- 
-- IpiVc DefaultRoute
-- 
-- This component contains information for setting up a default route 
-- on the IpiVc service.The default route feature permits establishment 
-- of a TCP/IP connection to the Software Distribution (SDS).
-- 

ipivcDr OBJECT IDENTIFIER ::= { ipivc 3 }



ipivcDrRowStatusTable OBJECT-TYPE
   SYNTAX     SEQUENCE OF IpivcDrRowStatusEntry
   ACCESS     not-accessible
   STATUS     mandatory
   DESCRIPTION
     "This entry controls the addition and deletion of 
      ipivcDr components."
::= { ipivcDr 1 }

ipivcDrRowStatusEntry OBJECT-TYPE
   SYNTAX     IpivcDrRowStatusEntry
   ACCESS     not-accessible
   STATUS     mandatory
   DESCRIPTION
     "A single entry in the table represents a single 
      ipivcDr component."
   INDEX {
      ipivcIndex,
      ipivcDrIndex }
::= { ipivcDrRowStatusTable 1 }

IpivcDrRowStatusEntry ::= SEQUENCE {
   ipivcDrRowStatus
      RowStatus,
   ipivcDrComponentName
      DisplayString,
   ipivcDrStorageType
      StorageType,
   ipivcDrIndex
      NonReplicated }

ipivcDrRowStatus OBJECT-TYPE
   SYNTAX     RowStatus 
   ACCESS     read-write
   STATUS     mandatory
   DESCRIPTION
     "This variable is used as the basis for SNMP naming of
      ipivcDr components.
      These components can be added and deleted."
::= { ipivcDrRowStatusEntry 1 }

ipivcDrComponentName OBJECT-TYPE
   SYNTAX     DisplayString 
   ACCESS     read-only
   STATUS     mandatory
   DESCRIPTION
     "This variable provides the component's string name for
      use with the ASCII Console Interface"
::= { ipivcDrRowStatusEntry 2 }

ipivcDrStorageType OBJECT-TYPE
   SYNTAX     StorageType 
   ACCESS     read-only
   STATUS     mandatory
   DESCRIPTION
     "This variable represents the storage type value for the
      ipivcDr tables."
::= { ipivcDrRowStatusEntry 4 }

ipivcDrIndex OBJECT-TYPE
   SYNTAX     NonReplicated 
   ACCESS     not-accessible
   STATUS     mandatory
   DESCRIPTION
     "This variable represents the index for the ipivcDr tables."
::= { ipivcDrRowStatusEntry 10 }

ipivcDrProvTable OBJECT-TYPE
   SYNTAX     SEQUENCE OF IpivcDrProvEntry
   ACCESS     not-accessible
   STATUS     mandatory
   DESCRIPTION
     "This group contains the provisionable attributes for setting up a 
      default route on the IpiVc service."
::= { ipivcDr 10 }

ipivcDrProvEntry OBJECT-TYPE
   SYNTAX     IpivcDrProvEntry
   ACCESS     not-accessible
   STATUS     mandatory
   DESCRIPTION
     "An entry in the ipivcDrProvTable."
   INDEX {
      ipivcIndex,
      ipivcDrIndex }
::= { ipivcDrProvTable 1 }

IpivcDrProvEntry ::= SEQUENCE {
   ipivcDrCallingIpAddress
      IpAddress,
   ipivcDrCallingNumberingPlanIndicator
      INTEGER,
   ipivcDrCallingDataNetworkAddress
      DigitString }

ipivcDrCallingIpAddress OBJECT-TYPE
   SYNTAX     IpAddress 
   ACCESS     read-write
   STATUS     mandatory
   DESCRIPTION
     "The field specifies the IP Address of the remote end, which issues 
      the X.25 call."
   DEFVAL     { '00000000'H }  -- "0.0.0.0"
::= { ipivcDrProvEntry 1 }

ipivcDrCallingNumberingPlanIndicator OBJECT-TYPE
   SYNTAX     INTEGER  {
                 x121(0),
                 e164(1) }
   ACCESS     read-write
   STATUS     mandatory
   DESCRIPTION
     "This field specifies the numbering plan of the address."
   DEFVAL     { x121 }
::= { ipivcDrProvEntry 2 }

ipivcDrCallingDataNetworkAddress OBJECT-TYPE
   SYNTAX     DigitString (SIZE (1..15))
   ACCESS     read-write
   STATUS     mandatory
   DESCRIPTION
     "This field specifies the address (in Binary Coded Decimal BCD 
      format) assigned to the remote end."
::= { ipivcDrProvEntry 3 }

-- 
-- *** THIS SUBTREE CURRENTLY NOT IMPLEMENTED ***
-- 

-- 
-- IpiVc Lcn/<n>
-- 
-- The Logical Channel Number responsible for the logical connection 
-- with the VC. There can be up to 24 instances of Lcn on the IpiVc 
-- component.

ipivcLcn OBJECT IDENTIFIER ::= { ipivc 4 }



ipivcLcnRowStatusTable OBJECT-TYPE
   SYNTAX     SEQUENCE OF IpivcLcnRowStatusEntry
   ACCESS     not-accessible
   STATUS     mandatory
   DESCRIPTION
     "*** THIS TABLE CURRENTLY NOT IMPLEMENTED ***

      This entry controls the addition and deletion of 
      ipivcLcn components."
::= { ipivcLcn 1 }

ipivcLcnRowStatusEntry OBJECT-TYPE
   SYNTAX     IpivcLcnRowStatusEntry
   ACCESS     not-accessible
   STATUS     mandatory
   DESCRIPTION
     "A single entry in the table represents a single 
      ipivcLcn component."
   INDEX {
      ipivcIndex,
      ipivcLcnIndex }
::= { ipivcLcnRowStatusTable 1 }

IpivcLcnRowStatusEntry ::= SEQUENCE {
   ipivcLcnRowStatus
      RowStatus,
   ipivcLcnComponentName
      DisplayString,
   ipivcLcnStorageType
      StorageType,
   ipivcLcnIndex
      Integer32 }

ipivcLcnRowStatus OBJECT-TYPE
   SYNTAX     RowStatus 
   ACCESS     read-only
   STATUS     mandatory
   DESCRIPTION
     "This variable is used as the basis for SNMP naming of
      ipivcLcn components.
      These components cannot be added nor deleted."
::= { ipivcLcnRowStatusEntry 1 }

ipivcLcnComponentName OBJECT-TYPE
   SYNTAX     DisplayString 
   ACCESS     read-only
   STATUS     mandatory
   DESCRIPTION
     "This variable provides the component's string name for
      use with the ASCII Console Interface"
::= { ipivcLcnRowStatusEntry 2 }

ipivcLcnStorageType OBJECT-TYPE
   SYNTAX     StorageType 
   ACCESS     read-only
   STATUS     mandatory
   DESCRIPTION
     "This variable represents the storage type value for the
      ipivcLcn tables."
::= { ipivcLcnRowStatusEntry 4 }

ipivcLcnIndex OBJECT-TYPE
   SYNTAX     Integer32 (16..39)
   ACCESS     not-accessible
   STATUS     mandatory
   DESCRIPTION
     "This variable represents the index for the ipivcLcn tables."
::= { ipivcLcnRowStatusEntry 10 }

ipivcLcnStateTable OBJECT-TYPE
   SYNTAX     SEQUENCE OF IpivcLcnStateEntry
   ACCESS     not-accessible
   STATUS     mandatory
   DESCRIPTION
     "*** THIS TABLE CURRENTLY NOT IMPLEMENTED ***

      This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { ipivcLcn 10 }

ipivcLcnStateEntry OBJECT-TYPE
   SYNTAX     IpivcLcnStateEntry
   ACCESS     not-accessible
   STATUS     mandatory
   DESCRIPTION
     "An entry in the ipivcLcnStateTable."
   INDEX {
      ipivcIndex,
      ipivcLcnIndex }
::= { ipivcLcnStateTable 1 }

IpivcLcnStateEntry ::= SEQUENCE {
   ipivcLcnAdminState
      INTEGER,
   ipivcLcnOperationalState
      INTEGER,
   ipivcLcnUsageState
      INTEGER,
   ipivcLcnAvailabilityStatus
      OCTET STRING,
   ipivcLcnProceduralStatus
      OCTET STRING,
   ipivcLcnControlStatus
      OCTET STRING,
   ipivcLcnAlarmStatus
      OCTET STRING,
   ipivcLcnStandbyStatus
      INTEGER,
   ipivcLcnUnknownStatus
      INTEGER }

ipivcLcnAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { ipivcLcnStateEntry 1 }

ipivcLcnOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { ipivcLcnStateEntry 2 }

ipivcLcnUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { ipivcLcnStateEntry 3 }

ipivcLcnAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { ipivcLcnStateEntry 4 }

ipivcLcnProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { ipivcLcnStateEntry 5 }

ipivcLcnControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { ipivcLcnStateEntry 6 }

ipivcLcnAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { ipivcLcnStateEntry 7 }

ipivcLcnStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { ipivcLcnStateEntry 8 }

ipivcLcnUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { ipivcLcnStateEntry 9 }

ipivcLcnOperTable OBJECT-TYPE
   SYNTAX     SEQUENCE OF IpivcLcnOperEntry
   ACCESS     not-accessible
   STATUS     mandatory
   DESCRIPTION
     "*** THIS TABLE CURRENTLY NOT IMPLEMENTED ***

      This group contains status of the internal IP network interface."
::= { ipivcLcn 11 }

ipivcLcnOperEntry OBJECT-TYPE
   SYNTAX     IpivcLcnOperEntry
   ACCESS     not-accessible
   STATUS     mandatory
   DESCRIPTION
     "An entry in the ipivcLcnOperTable."
   INDEX {
      ipivcIndex,
      ipivcLcnIndex }
::= { ipivcLcnOperTable 1 }

IpivcLcnOperEntry ::= SEQUENCE {
   ipivcLcnIpInterfaceDevice
      INTEGER,
   ipivcLcnDestinationIpAddress
      IpAddress,
   ipivcLcnPacketsSent
      Counter32,
   ipivcLcnPacketsReceived
      Counter32,
   ipivcLcnDiscardTxPackets
      Counter32,
   ipivcLcnDiscardRcvPackets
      Counter32 }

ipivcLcnIpInterfaceDevice OBJECT-TYPE
   SYNTAX     INTEGER  {
                 inactive(0),
                 active(1) }
   ACCESS     read-only
   STATUS     mandatory
   DESCRIPTION
     "The status of the internal IP network interface is inactive until an IP 
      packet is exchanged between a Network Management Station and 
      the internal IP network interface (via the LCN). At this point, the 
      status changes to active."
   DEFVAL     { inactive }
::= { ipivcLcnOperEntry 1 }

ipivcLcnDestinationIpAddress OBJECT-TYPE
   SYNTAX     IpAddress 
   ACCESS     read-only
   STATUS     mandatory
   DESCRIPTION
     "This attribute specifies the IP address of the remote network device 
      connected to this interface. The destinationIpAddress default is 
      0.0.0.0, until the first data packet is received from the remote end."
   DEFVAL     { '00000000'H }  -- "0.0.0.0"
::= { ipivcLcnOperEntry 2 }

ipivcLcnPacketsSent OBJECT-TYPE
   SYNTAX     Counter32 
   ACCESS     read-only
   STATUS     mandatory
   DESCRIPTION
     "This attribute counts the number of IP packets sent from this 
      interface."
::= { ipivcLcnOperEntry 3 }

ipivcLcnPacketsReceived OBJECT-TYPE
   SYNTAX     Counter32 
   ACCESS     read-only
   STATUS     mandatory
   DESCRIPTION
     "This attribute counts the number of IP packets received from the 
      remote network device."
::= { ipivcLcnOperEntry 4 }

ipivcLcnDiscardTxPackets OBJECT-TYPE
   SYNTAX     Counter32 
   ACCESS     read-only
   STATUS     mandatory
   DESCRIPTION
     "This attribute counts the number of IP packets destined to the 
      remote end which were discarded by the interface."
::= { ipivcLcnOperEntry 5 }

ipivcLcnDiscardRcvPackets OBJECT-TYPE
   SYNTAX     Counter32 
   ACCESS     read-only
   STATUS     mandatory
   DESCRIPTION
     "This attribute counts number of IP packets received from the remote 
      end which were discarded by this interface."
::= { ipivcLcnOperEntry 6 }

-- 
-- *** THIS SUBTREE CURRENTLY NOT IMPLEMENTED ***
-- 

-- ... Vc()
-- This component defines display of general Vc dynamic attributes

ipivcLcnVc OBJECT IDENTIFIER ::= { ipivcLcn 2 }



ipivcLcnVcRowStatusTable OBJECT-TYPE
   SYNTAX     SEQUENCE OF IpivcLcnVcRowStatusEntry
   ACCESS     not-accessible
   STATUS     mandatory
   DESCRIPTION
     "*** THIS TABLE CURRENTLY NOT IMPLEMENTED ***

      This entry controls the addition and deletion of 
      ipivcLcnVc components."
::= { ipivcLcnVc 1 }

ipivcLcnVcRowStatusEntry OBJECT-TYPE
   SYNTAX     IpivcLcnVcRowStatusEntry
   ACCESS     not-accessible
   STATUS     mandatory
   DESCRIPTION
     "A single entry in the table represents a single 
      ipivcLcnVc component."
   INDEX {
      ipivcIndex,
      ipivcLcnIndex,
      ipivcLcnVcIndex }
::= { ipivcLcnVcRowStatusTable 1 }

IpivcLcnVcRowStatusEntry ::= SEQUENCE {
   ipivcLcnVcRowStatus
      RowStatus,
   ipivcLcnVcComponentName
      DisplayString,
   ipivcLcnVcStorageType
      StorageType,
   ipivcLcnVcIndex
      NonReplicated }

ipivcLcnVcRowStatus OBJECT-TYPE
   SYNTAX     RowStatus 
   ACCESS     read-only
   STATUS     mandatory
   DESCRIPTION
     "This variable is used as the basis for SNMP naming of
      ipivcLcnVc components.
      These components cannot be added nor deleted."
::= { ipivcLcnVcRowStatusEntry 1 }

ipivcLcnVcComponentName OBJECT-TYPE
   SYNTAX     DisplayString 
   ACCESS     read-only
   STATUS     mandatory
   DESCRIPTION
     "This variable provides the component's string name for
      use with the ASCII Console Interface"
::= { ipivcLcnVcRowStatusEntry 2 }

ipivcLcnVcStorageType OBJECT-TYPE
   SYNTAX     StorageType 
   ACCESS     read-only
   STATUS     mandatory
   DESCRIPTION
     "This variable represents the storage type value for the
      ipivcLcnVc tables."
::= { ipivcLcnVcRowStatusEntry 4 }

ipivcLcnVcIndex OBJECT-TYPE
   SYNTAX     NonReplicated 
   ACCESS     not-accessible
   STATUS     mandatory
   DESCRIPTION
     "This variable represents the index for the ipivcLcnVc tables."
::= { ipivcLcnVcRowStatusEntry 10 }

ipivcLcnVcCadTable OBJECT-TYPE
   SYNTAX     SEQUENCE OF IpivcLcnVcCadEntry
   ACCESS     not-accessible
   STATUS     mandatory
   DESCRIPTION
     "*** THIS TABLE CURRENTLY NOT IMPLEMENTED ***

      This group represents operational call data related to General Vc. It 
      can be displayed only for General Vc which is created by 
      application."
::= { ipivcLcnVc 10 }

ipivcLcnVcCadEntry OBJECT-TYPE
   SYNTAX     IpivcLcnVcCadEntry
   ACCESS     not-accessible
   STATUS     mandatory
   DESCRIPTION
     "An entry in the ipivcLcnVcCadTable."
   INDEX {
      ipivcIndex,
      ipivcLcnIndex,
      ipivcLcnVcIndex }
::= { ipivcLcnVcCadTable 1 }

IpivcLcnVcCadEntry ::= SEQUENCE {
   ipivcLcnVcType
      INTEGER,
   ipivcLcnVcState
      INTEGER,
   ipivcLcnVcPreviousState
      INTEGER,
   ipivcLcnVcDiagnosticCode
      Unsigned32,
   ipivcLcnVcPreviousDiagnosticCode
      Unsigned32,
   ipivcLcnVcCalledNpi
      INTEGER,
   ipivcLcnVcCalledDna
      DigitString,
   ipivcLcnVcCalledLcn
      Unsigned32,
   ipivcLcnVcCallingNpi
      INTEGER,
   ipivcLcnVcCallingDna
      DigitString,
   ipivcLcnVcCallingLcn
      Unsigned32,
   ipivcLcnVcAccountingEnabled
      INTEGER,
   ipivcLcnVcFastSelectCall
      INTEGER,
   ipivcLcnVcLocalRxPktSize
      INTEGER,
   ipivcLcnVcLocalTxPktSize
      INTEGER,
   ipivcLcnVcLocalTxWindowSize
      Unsigned32,
   ipivcLcnVcLocalRxWindowSize
      Unsigned32,
   ipivcLcnVcPathReliability
      INTEGER,
   ipivcLcnVcAccountingEnd
      INTEGER,
   ipivcLcnVcPriority
      INTEGER,
   ipivcLcnVcSegmentSize
      Unsigned32,
   ipivcLcnVcSubnetTxPktSize
      INTEGER,
   ipivcLcnVcSubnetTxWindowSize
      Unsigned32,
   ipivcLcnVcSubnetRxPktSize
      INTEGER,
   ipivcLcnVcSubnetRxWindowSize
      Unsigned32,
   ipivcLcnVcMaxSubnetPktSize
      Unsigned32,
   ipivcLcnVcTransferPriorityToNetwork
      INTEGER,
   ipivcLcnVcTransferPriorityFromNetwork
      INTEGER }

ipivcLcnVcType OBJECT-TYPE
   SYNTAX     INTEGER  {
                 svc(0),
                 pvc(1) }
   ACCESS     read-only
   STATUS     mandatory
   DESCRIPTION
     "This attribute displays the type of call, pvc or svc. type is provided 
      at provisioning time."
::= { ipivcLcnVcCadEntry 1 }

ipivcLcnVcState OBJECT-TYPE
   SYNTAX     INTEGER  {
                 creating(0),
                 readyP1(1),
                 dteWaitingP2(2),
                 dceWaitingP3(3),
                 dataTransferP4(4),
                 unsupportedP5(5),
                 dteClearRequestP6(6),
                 dceClearIndicationP7(7),
                 termination(8) }
   ACCESS     read-only
   STATUS     mandatory
   DESCRIPTION
     "This attribute displays the state of call control. P5 state is not 
      supported but is listed for completness. Transitions from one state to 
      another take very short time. state most often displayed is 
      dataTransferP4."
::= { ipivcLcnVcCadEntry 2 }

ipivcLcnVcPreviousState OBJECT-TYPE
   SYNTAX     INTEGER  {
                 creating(0),
                 readyP1(1),
                 dteWaitingP2(2),
                 dceWaitingP3(3),
                 dataTransferP4(4),
                 unsupportedP5(5),
                 dteClearRequestP6(6),
                 dceClearIndicationP7(7),
                 termination(8) }
   ACCESS     read-only
   STATUS     mandatory
   DESCRIPTION
     "This attribute displays the previous state of call control. This is a 
      valuable field to determine how the processing is progressing."
::= { ipivcLcnVcCadEntry 3 }

ipivcLcnVcDiagnosticCode OBJECT-TYPE
   SYNTAX     Unsigned32 (0..255)
   ACCESS     read-only
   STATUS     mandatory
   DESCRIPTION
     "This attribute displays the internal substate of call control. It is used 
      to further refine state of call processing."
::= { ipivcLcnVcCadEntry 4 }

ipivcLcnVcPreviousDiagnosticCode OBJECT-TYPE
   SYNTAX     Unsigned32 (0..255)
   ACCESS     read-only
   STATUS     mandatory
   DESCRIPTION
     "This attribute displays the internal substate of call control. It is used 
      to further refine state of call processing."
::= { ipivcLcnVcCadEntry 5 }

ipivcLcnVcCalledNpi OBJECT-TYPE
   SYNTAX     INTEGER  {
                 x121(0),
                 e164(1) }
   ACCESS     read-only
   STATUS     mandatory
   DESCRIPTION
     "This attribute displays the Numbering Plan Indicator (NPI) of the 
      called end."
::= { ipivcLcnVcCadEntry 6 }

ipivcLcnVcCalledDna OBJECT-TYPE
   SYNTAX     DigitString (SIZE (1..15))
   ACCESS     read-only
   STATUS     mandatory
   DESCRIPTION
     "This attribute displays the Data Network Address (Dna) of the 
      called (destination) DTE to which this call is sent. This address if 
      defined at recieving end will complete Vc connection."
::= { ipivcLcnVcCadEntry 7 }

ipivcLcnVcCalledLcn OBJECT-TYPE
   SYNTAX     Unsigned32 (1..65535)
   ACCESS     read-only
   STATUS     mandatory
   DESCRIPTION
     "This attribute displays the Logical Channel Number of the called 
      end. It is valid only after both ends of Vc exchanged relevant 
      information."
::= { ipivcLcnVcCadEntry 8 }

ipivcLcnVcCallingNpi OBJECT-TYPE
   SYNTAX     INTEGER  {
                 x121(0),
                 e164(1) }
   ACCESS     read-only
   STATUS     mandatory
   DESCRIPTION
     "This attribute displays the Numbering Plan Indicator (NPI) of the 
      calling end."
::= { ipivcLcnVcCadEntry 9 }

ipivcLcnVcCallingDna OBJECT-TYPE
   SYNTAX     DigitString (SIZE (1..15))
   ACCESS     read-only
   STATUS     mandatory
   DESCRIPTION
     "This attribute displays the Data Network Address (Dna) of the 
      calling end."
::= { ipivcLcnVcCadEntry 10 }

ipivcLcnVcCallingLcn OBJECT-TYPE
   SYNTAX     Unsigned32 (1..65535)
   ACCESS     read-only
   STATUS     mandatory
   DESCRIPTION
     "This attribute displays the Logical Channel Number of the calling 
      end."
::= { ipivcLcnVcCadEntry 11 }

ipivcLcnVcAccountingEnabled OBJECT-TYPE
   SYNTAX     INTEGER  {
                 yes(0),
                 no(1) }
   ACCESS     read-only
   STATUS     mandatory
   DESCRIPTION
     "This attribute indicates that this optional section of accounting 
      record is suppressed or permitted. If accountingEnabled is yes, 
      conditions for generation of accounting record were met. These 
      conditions include billing options, vc recovery conditions and 
      Module wide accounting data options."
::= { ipivcLcnVcCadEntry 12 }

ipivcLcnVcFastSelectCall OBJECT-TYPE
   SYNTAX     INTEGER  {
                 no(0),
                 yes(1) }
   ACCESS     read-only
   STATUS     mandatory
   DESCRIPTION
     "This attribute displays that this is a fast select call."
::= { ipivcLcnVcCadEntry 13 }

ipivcLcnVcLocalRxPktSize OBJECT-TYPE
   SYNTAX     INTEGER  {
                 unknown(0),
                 n16(4),
                 n32(5),
                 n64(6),
                 n128(7),
                 n256(8),
                 n512(9),
                 n1024(10),
                 n2048(11),
                 n4096(12) }
   ACCESS     read-only
   STATUS     mandatory
   DESCRIPTION
     "This attribute displays the locally negotiated size of send packets."
::= { ipivcLcnVcCadEntry 14 }

ipivcLcnVcLocalTxPktSize OBJECT-TYPE
   SYNTAX     INTEGER  {
                 unknown(0),
                 n16(4),
                 n32(5),
                 n64(6),
                 n128(7),
                 n256(8),
                 n512(9),
                 n1024(10),
                 n2048(11),
                 n4096(12) }
   ACCESS     read-only
   STATUS     mandatory
   DESCRIPTION
     "This attribute displays the locally negotiated size of send packets."
::= { ipivcLcnVcCadEntry 15 }

ipivcLcnVcLocalTxWindowSize OBJECT-TYPE
   SYNTAX     Unsigned32 (0..127)
   ACCESS     read-only
   STATUS     mandatory
   DESCRIPTION
     "This attribute displays the send window size provided on incoming 
      call packets or the default when a call request packet does not 
      explicitly provide the window size."
::= { ipivcLcnVcCadEntry 16 }

ipivcLcnVcLocalRxWindowSize OBJECT-TYPE
   SYNTAX     Unsigned32 (0..127)
   ACCESS     read-only
   STATUS     mandatory
   DESCRIPTION
     "This attribute displays the receive window size provided on 
      incoming call packets or the default when a call request does not 
      explicitly provide the window sizes."
::= { ipivcLcnVcCadEntry 17 }

ipivcLcnVcPathReliability OBJECT-TYPE
   SYNTAX     INTEGER  {
                 high(0),
                 normal(1) }
   ACCESS     read-only
   STATUS     mandatory
   DESCRIPTION
     "This attribute displays the path reliability."
::= { ipivcLcnVcCadEntry 19 }

ipivcLcnVcAccountingEnd OBJECT-TYPE
   SYNTAX     INTEGER  {
                 callingEnd(0),
                 calledEnd(1) }
   ACCESS     read-only
   STATUS     mandatory
   DESCRIPTION
     "This attribute indicates if this end should generate an accounting 
      record. Normally, callingEnd is the end to generate an accounting 
      record."
::= { ipivcLcnVcCadEntry 20 }

ipivcLcnVcPriority OBJECT-TYPE
   SYNTAX     INTEGER  {
                 normal(0),
                 high(1) }
   ACCESS     read-only
   STATUS     mandatory
   DESCRIPTION
     "This attribute displays whether the call is a normal or a high 
      priority call."
::= { ipivcLcnVcCadEntry 21 }

ipivcLcnVcSegmentSize OBJECT-TYPE
   SYNTAX     Unsigned32 (0..4096)
   ACCESS     read-only
   STATUS     mandatory
   DESCRIPTION
     "This attribute displays the segment size (in bytes) used on the call. 
      It is used to calculate the number of segments transmitted and 
      received."
::= { ipivcLcnVcCadEntry 22 }

ipivcLcnVcSubnetTxPktSize OBJECT-TYPE
   SYNTAX     INTEGER  {
                 unknown(0),
                 n16(4),
                 n32(5),
                 n64(6),
                 n128(7),
                 n256(8),
                 n512(9),
                 n1024(10),
                 n2048(11),
                 n4096(12) }
   ACCESS     read-only
   STATUS     mandatory
   DESCRIPTION
     "This attribute displays the locally negotiated size of the data packets 
      on this Vc."
::= { ipivcLcnVcCadEntry 23 }

ipivcLcnVcSubnetTxWindowSize OBJECT-TYPE
   SYNTAX     Unsigned32 (0..4096)
   ACCESS     read-only
   STATUS     mandatory
   DESCRIPTION
     "This attribute displays the current send window size of Vc."
::= { ipivcLcnVcCadEntry 24 }

ipivcLcnVcSubnetRxPktSize OBJECT-TYPE
   SYNTAX     INTEGER  {
                 unknown(0),
                 n16(4),
                 n32(5),
                 n64(6),
                 n128(7),
                 n256(8),
                 n512(9),
                 n1024(10),
                 n2048(11),
                 n4096(12) }
   ACCESS     read-only
   STATUS     mandatory
   DESCRIPTION
     "This attribute displays the locally negotiated size of receive packets."
::= { ipivcLcnVcCadEntry 25 }

ipivcLcnVcSubnetRxWindowSize OBJECT-TYPE
   SYNTAX     Unsigned32 (0..4096)
   ACCESS     read-only
   STATUS     mandatory
   DESCRIPTION
     "This attribute displays the receive window size provided on 
      incoming call packets and to the default when a call request does 
      not explicitly provide the window sizes."
::= { ipivcLcnVcCadEntry 26 }

ipivcLcnVcMaxSubnetPktSize OBJECT-TYPE
   SYNTAX     Unsigned32 (0..4096)
   ACCESS     read-only
   STATUS     mandatory
   DESCRIPTION
     "This attribute displays the maximum packet size allowed on Vc."
::= { ipivcLcnVcCadEntry 27 }

ipivcLcnVcTransferPriorityToNetwork OBJECT-TYPE
   SYNTAX     INTEGER  {
                 normal(0),
                 high(9) }
   ACCESS     read-only
   STATUS     mandatory
   DESCRIPTION
     "This attribute displays the priority in which data is transferred to the 
      network.
      
      The transfer priority is a preference specified by an application 
      according to its delay-sensitivity requirement. Frames with high
      transfer priority are served by the network before the frames with 
      normal priority. 
      
      Each transfer priority contains a predetermined setting for trunk 
      queue (interrupting, delay or throughput), and routing metric (delay 
      or throughput).
      
      When the transfer priority is set at high, the trunk queue is set to 
      high, the routing metric is set to delay.
      
      When the transfer priority is set at normal, the trunk queue is set to 
      normal, the routing metric is set to throughput."
::= { ipivcLcnVcCadEntry 28 }

ipivcLcnVcTransferPriorityFromNetwork OBJECT-TYPE
   SYNTAX     INTEGER  {
                 normal(0),
                 high(9) }
   ACCESS     read-only
   STATUS     mandatory
   DESCRIPTION
     "This attribute displays the priority in which data is transferred from 
      the network.
      
      The transfer priority is a preference specified by an application 
      according to its delay-sensitivity requirement. Frames with high
      transfer priority are served by the network before the frames with 
      normal priority. 
      
      Each transfer priority contains a predetermined setting for trunk 
      queue (interrupting, delay or throughput), and routing metric (delay 
      or throughput). 
      
      When the transfer priority is set at high, and the trunk queue is set 
      to high, the routing metric is set to delay.
      
      When the transfer priority is set at normal, the trunk queue is set to 
      normal, and the routing metric is set to throughput."
::= { ipivcLcnVcCadEntry 29 }

ipivcLcnVcIntdTable OBJECT-TYPE
   SYNTAX     SEQUENCE OF IpivcLcnVcIntdEntry
   ACCESS     not-accessible
   STATUS     mandatory
   DESCRIPTION
     "*** THIS TABLE CURRENTLY NOT IMPLEMENTED ***

      This group defines display of interval data collected by Vc. Data in 
      this group is variable and may depend on time when this display 
      command is issued."
::= { ipivcLcnVc 11 }

ipivcLcnVcIntdEntry OBJECT-TYPE
   SYNTAX     IpivcLcnVcIntdEntry
   ACCESS     not-accessible
   STATUS     mandatory
   DESCRIPTION
     "An entry in the ipivcLcnVcIntdTable."
   INDEX {
      ipivcIndex,
      ipivcLcnIndex,
      ipivcLcnVcIndex }
::= { ipivcLcnVcIntdTable 1 }

IpivcLcnVcIntdEntry ::= SEQUENCE {
   ipivcLcnVcCallReferenceNumber
      Hex,
   ipivcLcnVcElapsedTimeTillNow
      Unsigned32,
   ipivcLcnVcSegmentsRx
      Unsigned32,
   ipivcLcnVcSegmentsSent
      Unsigned32,
   ipivcLcnVcStartTime
      EnterpriseDateAndTime }

ipivcLcnVcCallReferenceNumber OBJECT-TYPE
   SYNTAX     Hex (0..16777215)
   ACCESS     read-only
   STATUS     mandatory
   DESCRIPTION
     "This attribute displays the call reference number which is a unique 
      number generated by the switch.The same Call Reference Number 
      is stored in the interval data (accounting record) at both ends of the 
      call. It can be used as one of the attributes in matching duplicate 
      records generated at each end of the call."
::= { ipivcLcnVcIntdEntry 1 }

ipivcLcnVcElapsedTimeTillNow OBJECT-TYPE
   SYNTAX     Unsigned32 (0..16777215)
   ACCESS     read-only
   STATUS     mandatory
   DESCRIPTION
     "This attribute displays the elapsed time representing the period of 
      this interval data. It is elapsed time in 0.1 second increments since 
      Vc started."
::= { ipivcLcnVcIntdEntry 2 }

ipivcLcnVcSegmentsRx OBJECT-TYPE
   SYNTAX     Unsigned32 (0..16777215)
   ACCESS     read-only
   STATUS     mandatory
   DESCRIPTION
     "This attribute displays the number of segments received at the time 
      command was issued. This is the segment received count 
      maintained by accounting at each end of the Vc. This counter is 
      updated only when the packet cannot be successfully delivered out 
      of the sink Vc and to the sink AP Conditions in which packets may 
      be discarded by the sink Vc include: missing packets due to subnet 
      discards, segmentation protocol violations due to subnet discard, 
      duplicated and out-of-ranged packets and packets that arrive while 
      Vc is in path recovery state."
::= { ipivcLcnVcIntdEntry 3 }

ipivcLcnVcSegmentsSent OBJECT-TYPE
   SYNTAX     Unsigned32 (0..16777215)
   ACCESS     read-only
   STATUS     mandatory
   DESCRIPTION
     "This attribute displays the number of segments sent at the time 
      command was issued. This is the segment sent count maintained by 
      accounting at the source Vc. Vc only counts packets that Vc thinks 
      can be delivered successfully into the subnet. In reality, these 
      packets may be dropped by trunking, for instance. This counter is 
      not updated when splitting fails, when Vc is in a path recovery state, 
      when packet forwarding fails to forward this packet and when 
      subsequent packets have to be discarded as we want to minimize the 
      chance of out-of-sequence and do not intentionally send out-of-
      sequenced packets into the subnet."
::= { ipivcLcnVcIntdEntry 4 }

ipivcLcnVcStartTime OBJECT-TYPE
   SYNTAX     EnterpriseDateAndTime (SIZE (0 | 19))
   ACCESS     read-only
   STATUS     mandatory
   DESCRIPTION
     "This attribute displays the start time of this interval period. If Vc 
      spans 12 hour time or time of day change startTime reflects new 
      time as recorded at 12 hour periods or time of day changes."
::= { ipivcLcnVcIntdEntry 5 }

ipivcLcnVcStatsTable OBJECT-TYPE
   SYNTAX     SEQUENCE OF IpivcLcnVcStatsEntry
   ACCESS     not-accessible
   STATUS     mandatory
   DESCRIPTION
     "*** THIS TABLE CURRENTLY NOT IMPLEMENTED ***

      ... Statistics(Stats)
      This group defines general attributes collected by general Vc.
      The purpose of Vc attributes is to aid end users and verification 
      people to understand the Vc internal behavior. This is particularly 
      useful when the network has experienced abnormality and we want 
      to isolate problems and pinpoint trouble spots. 
      Attributes are collected on a per Vc basis. Until a need is identified, 
      statistics are not collected at a processor level. Each attribute is 
      stored in a 32 bit field and is initialized to zero when a Vc enters 
      into the data transfer state. When a PVC is disconnected and then 
      connected again, the attributes will be reset. Attributes cannot be 
      reset through other methods."
::= { ipivcLcnVc 12 }

ipivcLcnVcStatsEntry OBJECT-TYPE
   SYNTAX     IpivcLcnVcStatsEntry
   ACCESS     not-accessible
   STATUS     mandatory
   DESCRIPTION
     "An entry in the ipivcLcnVcStatsTable."
   INDEX {
      ipivcIndex,
      ipivcLcnIndex,
      ipivcLcnVcIndex }
::= { ipivcLcnVcStatsTable 1 }

IpivcLcnVcStatsEntry ::= SEQUENCE {
   ipivcLcnVcAckStackingTimeouts
      Unsigned32,
   ipivcLcnVcOutOfRangeFrmFromSubnet
      Unsigned32,
   ipivcLcnVcDuplicatesFromSubnet
      Unsigned32,
   ipivcLcnVcFrmRetryTimeouts
      Unsigned32,
   ipivcLcnVcPeakRetryQueueSize
      Unsigned32,
   ipivcLcnVcPeakOoSeqQueueSize
      Unsigned32,
   ipivcLcnVcPeakOoSeqFrmForwarded
      Unsigned32,
   ipivcLcnVcPeakStackedAcksRx
      Unsigned32,
   ipivcLcnVcSubnetRecoveries
      Unsigned32,
   ipivcLcnVcWindowClosuresToSubnet
      Unsigned32,
   ipivcLcnVcWindowClosuresFromSubnet
      Unsigned32,
   ipivcLcnVcWrTriggers
      Unsigned32 }

ipivcLcnVcAckStackingTimeouts OBJECT-TYPE
   SYNTAX     Unsigned32 (0..5000)
   ACCESS     read-only
   STATUS     mandatory
   DESCRIPTION
     "This attribute counts the number of ack stacking timer expiries.
      It is used as an indicator of the acknowledgment behavior across the 
      subnet when ack stacking is in effect. If it expires often, usually this 
      means end users will experience longer delay.
      The ack stacking timer specifies how long the Vc will wait before 
      finally sending the subnet acknowledgment. if this attribute is set to 
      a value of 0, then the Vc will automatically return acknowledgment 
      packets without delay. If this attribute is set to a value other than 
      zero, then the Vc will wait for this amount of time in an attempt to 
      piggyback the acknowledgment packet on another credit or data 
      packet. If the Vc cannot piggyback the acknowledgment packet 
      within this time, then the packet is returned without piggybacking."
::= { ipivcLcnVcStatsEntry 1 }

ipivcLcnVcOutOfRangeFrmFromSubnet OBJECT-TYPE
   SYNTAX     Unsigned32 (0..5000)
   ACCESS     read-only
   STATUS     mandatory
   DESCRIPTION
     "This attribute counts the number of subnet frames discarded due to 
      the sequence number being out of range.
      Two Categories apply for the General Vc
      1) lost Acks (previous Range)
      2) unexpected Packets (next Range)
      Vc internally maintains its own sequence number of packet order 
      and sequencing. Due to packet retransmission, Vc may receive 
      duplicate packets that have the same Vc internal sequence number. 
      Only 1 copy is accepted by the Vc and other copies of the same 
      packets are detected through this count. This attribute can be used to 
      record the frequency of packet retransmission due to Vc and other 
      part of the subnet."
::= { ipivcLcnVcStatsEntry 2 }

ipivcLcnVcDuplicatesFromSubnet OBJECT-TYPE
   SYNTAX     Unsigned32 (0..5000)
   ACCESS     read-only
   STATUS     mandatory
   DESCRIPTION
     "This attribute counts the number of subnet packets discarded due to 
      duplication. It is used to detect software error fault or duplication 
      caused by retransmitting."
::= { ipivcLcnVcStatsEntry 3 }

ipivcLcnVcFrmRetryTimeouts OBJECT-TYPE
   SYNTAX     Unsigned32 (0..5000)
   ACCESS     read-only
   STATUS     mandatory
   DESCRIPTION
     "This attribute counts the number of frames which have 
      retransmission time-out.
      If packets from Vc into the subnet are discarded by the subnet, the 
      source Vc will not receive any acknowledgment. The retransmission 
      timer then expires and packets will be retransmitted again. Note that 
      the Vc idle probe may be retransmitted and is included in this count. 
      This statistics does not show the distribution of how many times 
      packets are retransmitted (e.g. first retransmission results in 
      successful packet forwarding)."
::= { ipivcLcnVcStatsEntry 4 }

ipivcLcnVcPeakRetryQueueSize OBJECT-TYPE
   SYNTAX     Unsigned32 (0..5000)
   ACCESS     read-only
   STATUS     mandatory
   DESCRIPTION
     "This attribute indicates the peak size of the retransmission queue.
      This attribute is used as an indicator of the acknowledgment 
      behavior across the subnet. It records the largest body of 
      unacknowledged packets."
::= { ipivcLcnVcStatsEntry 5 }

ipivcLcnVcPeakOoSeqQueueSize OBJECT-TYPE
   SYNTAX     Unsigned32 (0..5000)
   ACCESS     read-only
   STATUS     mandatory
   DESCRIPTION
     "This attribute indicates the peak size of the out of sequence queue.
      This attribute is used as an indicator of the sequencing behavior 
      across the subnet. It records the largest body of out of sequence 
      packets."
::= { ipivcLcnVcStatsEntry 6 }

ipivcLcnVcPeakOoSeqFrmForwarded OBJECT-TYPE
   SYNTAX     Unsigned32 (0..5000)
   ACCESS     read-only
   STATUS     mandatory
   DESCRIPTION
     "This attribute indicates the peak size of the sequence packet queue.
      This attribute is used as an indicator of the sequencing behavior 
      across the subnet. It records the largest body of out of sequence 
      packets, which by the receipt of an expected packet have been 
      transformed to expected packets. The number of times this peak is 
      reached is not recorded as it is traffic dependent."
::= { ipivcLcnVcStatsEntry 7 }

ipivcLcnVcPeakStackedAcksRx OBJECT-TYPE
   SYNTAX     Unsigned32 (0..5000)
   ACCESS     read-only
   STATUS     mandatory
   DESCRIPTION
     "This attribute indicates the peak size of wait acks.
      This attribute is used as an indicator of the acknowledgment 
      behavior across the subnet. It records the largest collective 
      acknowledgment."
::= { ipivcLcnVcStatsEntry 8 }

ipivcLcnVcSubnetRecoveries OBJECT-TYPE
   SYNTAX     Unsigned32 (0..5000)
   ACCESS     read-only
   STATUS     mandatory
   DESCRIPTION
     "This attribute counts the number of successful Vc recovery attempts.
      This attribute is used as an indicator of how many times the Vc path 
      is broken but can be recovered. This attribute is useful to record the 
      number of network path failures."
::= { ipivcLcnVcStatsEntry 9 }

ipivcLcnVcWindowClosuresToSubnet OBJECT-TYPE
   SYNTAX     Unsigned32 (0..5000)
   ACCESS     read-only
   STATUS     mandatory
   DESCRIPTION
     "This attribute counts the number of window closures to subnet.
      A packet may have been sent into the subnet but its 
      acknowledgment from the remote Vc has not yet been received. 
      This is a 8 bit sequence number.This number is useful in detecting 
      whether the Vc is sending any packet into the subnet."
::= { ipivcLcnVcStatsEntry 10 }

ipivcLcnVcWindowClosuresFromSubnet OBJECT-TYPE
   SYNTAX     Unsigned32 (0..5000)
   ACCESS     read-only
   STATUS     mandatory
   DESCRIPTION
     "This attribute counts the number of window closures from subnet.
      This attribute is useful in detecting whether the Vc is receiving any 
      packet from the subnet."
::= { ipivcLcnVcStatsEntry 11 }

ipivcLcnVcWrTriggers OBJECT-TYPE
   SYNTAX     Unsigned32 (0..5000)
   ACCESS     read-only
   STATUS     mandatory
   DESCRIPTION
     "This attribute displays the number of times the Vc stays within the 
      W-R region. The W-R region is a value used to determined the 
      timing of credit transmission. Should the current window size be 
      beneath this value, the credits will be transmitted immediately. 
      Otherwise, they will be transmitted later with actual data. The 
      wrTriggers statistic is therefore used to analyze the flow control and 
      credit mechanism."
::= { ipivcLcnVcStatsEntry 12 }




-- 
-- Version and Compliance statements
-- 



-- Object-Group Statement:
-- A list of all current accessible leaf objects.

-- OBJECTS { ipivcDrComponentName,
--           ipivcLcnStorageType,
--           ipivcDnaPacketSizes,
--           ipivcIpAddress,
--           ipivcLcnVcDuplicatesFromSubnet,
--           ipivcLcnVcStartTime,
--           ipivcLcnControlStatus,
--           ipivcLcnAdminState,
--           ipivcLcnVcDiagnosticCode,
--           ipivcDnaDefaultRecvFrmNetworkWindowSize,
--           ipivcStorageType,
--           ipivcDnaDefaultRecvFrmNetworkPacketSize,
--           ipivcComponentName,
--           ipivcLcnRowStatus,
--           ipivcLcnVcLocalRxWindowSize,
--           ipivcLcnVcCallingLcn,
--           ipivcLcnVcWindowClosuresToSubnet,
--           ipivcLcnVcOutOfRangeFrmFromSubnet,
--           ipivcLcnDiscardRcvPackets,
--           ipivcDnaCugStorageType,
--           ipivcLcnVcCalledDna,
--           ipivcLcnUsageState,
--           ipivcLcnVcType,
--           ipivcDnaCugPrivileged,
--           ipivcLcnVcAccountingEnabled,
--           ipivcLcnVcSegmentsSent,
--           ipivcDnaCugIncCalls,
--           ipivcDnaCugOutCalls,
--           ipivcDnaCugDnic,
--           ipivcDnaIncIntlReverseCharge,
--           ipivcLcnVcPreviousState,
--           ipivcMaximumNumberOfLcn,
--           ipivcLcnVcSubnetRecoveries,
--           ipivcDrRowStatus,
--           ipivcDnaNumberingPlanIndicator,
--           ipivcDrStorageType,
--           ipivcDnaDataNetworkAddress,
--           ipivcLcnIpInterfaceDevice,
--           ipivcLcnOperationalState,
--           ipivcDnaDefaultSendToNetworkThruputClass,
--           ipivcDnaIncHighPriorityReverseCharge,
--           ipivcLcnVcSegmentSize,
--           ipivcDnaCugRowStatus,
--           ipivcLcnPacketsSent,
--           ipivcDnaPacketSizeNegotiation,
--           ipivcLcnVcCalledLcn,
--           ipivcLcnDiscardTxPackets,
--           ipivcLcnVcComponentName,
--           ipivcLcnPacketsReceived,
--           ipivcLcnVcFastSelectCall,
--           ipivcLcnVcPeakOoSeqQueueSize,
--           ipivcLcnVcWindowClosuresFromSubnet,
--           ipivcDnaCug0AsNonCugCall,
--           ipivcDnaFastSelectCallsOnly,
--           ipivcDnaIncIntlNormalCharge,
--           ipivcLcnAvailabilityStatus,
--           ipivcLcnVcSubnetTxWindowSize,
--           ipivcDnaIncNormalPriorityReverseCharge,
--           ipivcDnaDefaultSendToNetworkWindowSize,
--           ipivcLcnAlarmStatus,
--           ipivcLcnVcAckStackingTimeouts,
--           ipivcLcnVcPriority,
--           ipivcLcnVcPathReliability,
--           ipivcDnaDefaultSendToNetworkPacketSize,
--           ipivcDnaComponentName,
--           ipivcDnaAccountClass,
--           ipivcDrCallingNumberingPlanIndicator,
--           ipivcLcnVcCallReferenceNumber,
--           ipivcLcnVcLocalTxWindowSize,
--           ipivcLcnVcState,
--           ipivcRowStatus,
--           ipivcDnaOutCalls,
--           ipivcLcnVcSubnetRxWindowSize,
--           ipivcLcnVcPeakStackedAcksRx,
--           ipivcLcnVcStorageType,
--           ipivcLcnProceduralStatus,
--           ipivcDnaStorageType,
--           ipivcDrCallingDataNetworkAddress,
--           ipivcDnaDefaultTransferPriority,
--           ipivcLcnVcAccountingEnd,
--           ipivcLcnVcSubnetTxPktSize,
--           ipivcLcnVcCalledNpi,
--           ipivcLcnVcElapsedTimeTillNow,
--           ipivcLcnComponentName,
--           ipivcDnaCugFormat,
--           ipivcLcnVcTransferPriorityToNetwork,
--           ipivcDnaCugType,
--           ipivcLcnDestinationIpAddress,
--           ipivcLcnVcRowStatus,
--           ipivcDnaIncCalls,
--           ipivcDnaIncFastSelect,
--           ipivcDnaIncAccess,
--           ipivcLcnVcLocalTxPktSize,
--           ipivcLcnVcPreviousDiagnosticCode,
--           ipivcLcnVcCallingNpi,
--           ipivcLcnVcSubnetRxPktSize,
--           ipivcLcnVcWrTriggers,
--           ipivcDrCallingIpAddress,
--           ipivcDnaRowStatus,
--           ipivcLcnVcCallingDna,
--           ipivcLcnVcPeakRetryQueueSize,
--           ipivcDnaIncChargeTransfer,
--           ipivcLcnVcPeakOoSeqFrmForwarded,
--           ipivcLcnVcSegmentsRx,
--           ipivcLcnVcFrmRetryTimeouts,
--           ipivcDnaTransferPriorityOverRide,
--           ipivcDnaCugComponentName,
--           ipivcDnaIncSameService,
--           ipivcDnaDefaultRecvFrmNetworkThruputClass,
--           ipivcDnaCugInterlockCode,
--           ipivcLcnVcLocalRxPktSize,
--           ipivcDnaServiceExchange,
--           ipivcDnaServiceCategory,
--           ipivcLcnUnknownStatus,
--           ipivcLcnStandbyStatus,
--           ipivcLcnVcTransferPriorityFromNetwork,
--           ipivcLcnVcMaxSubnetPktSize }
-- STATUS  mandatory
-- DESCRIPTION
--   "A list of all current accessible leaf objects."

ipiVcGroup OBJECT IDENTIFIER ::= { ipiVcMIB 1 }
ipiVcGroupBE OBJECT IDENTIFIER ::= { ipiVcGroup 5 }
ipiVcGroupBE01 OBJECT IDENTIFIER ::= { ipiVcGroupBE 2 }
ipiVcGroupBE01A OBJECT IDENTIFIER ::= { ipiVcGroupBE01 2 }



-- Agent-Capabilities Statement:

-- PRODUCT-RELEASE "Passport Release 7.0 IpiVc."
-- STATUS          mandatory
-- DESCRIPTION     "IpiVc MIB: MIB Version BE01A,
--                  Software Version BG00S4C."
-- SUPPORTS        Nortel-Magellan-Passport-IpiVcMIB
--    INCLUDES     { ipiVcGroupBE01A }

ipiVcCapabilities OBJECT IDENTIFIER ::= { ipiVcMIB 3 }
ipiVcCapabilitiesBE OBJECT IDENTIFIER ::= { ipiVcCapabilities 5 }
ipiVcCapabilitiesBE01 OBJECT IDENTIFIER ::= { ipiVcCapabilitiesBE 2 }
ipiVcCapabilitiesBE01A OBJECT IDENTIFIER ::= { ipiVcCapabilitiesBE01 2 }





END
