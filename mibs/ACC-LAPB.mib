ACC-LAPB DEFINITIONS ::= BEGIN

    IMPORTS
	 OBJECT-TYPE, IpAddress, TimeTicks, Gauge, Counter FROM RFC1155-SMI
        accTrapLogSeqNum FROM ACC-SYSTEM
	accBRG, DisplayString, RowStatus, IfIndex, SmdsAddress
             FROM ACC-MIB;
-- LAPB Group
      accLapb    OBJECT IDENTIFIER ::= { accBRG 7 }
	accLapbNum	OBJECT-TYPE   
			SYNTAX	INTEGER
			ACCESS	read-only
			STATUS	mandatory
			DESCRIPTION
			 " Number of HDLC ports"
			::= { accLapb 1 }
	accLapbParmTable	OBJECT-TYPE
			SYNTAX	SEQUENCE OF AccLapbParmEntry
			ACCESS	not-accessible
			STATUS	mandatory
			DESCRIPTION
			 " HDLC LAPB port parameters"
			::= { accLapb 2 }
          accLapbParmEntry      OBJECT-TYPE
                        SYNTAX  AccLapbParmEntry
                        ACCESS  not-accessible
                        STATUS  mandatory
                        DESCRIPTION
                         " LAPB parameters for a port."
                        INDEX { accLapbIndex }
                        ::= { accLapbParmTable 1 }
			AccLapbParmEntry ::= SEQUENCE {
			    accLapbIndex	INTEGER,
			    accLapbType		INTEGER,
			    accLapbT1Timer	INTEGER,
			    accLapbN2Count	INTEGER,
			    accLapbFrameWindow	INTEGER,
			    accLapbFlags	INTEGER,
			    accHdlcRrPolling	INTEGER,
			    accHdlcFCS		INTEGER,
			    accHdlcCoding	INTEGER,
			    accHdlcDuplex	INTEGER,
			    accHdlcIdleFill	INTEGER
			    }
	    accLapbIndex	OBJECT-TYPE   
			SYNTAX	INTEGER
			ACCESS	read-only
			STATUS	mandatory
			DESCRIPTION
			 " Physical port number of this interface."
			::= { accLapbParmEntry 1 }
	    accLapbType		OBJECT-TYPE   
			SYNTAX	INTEGER {
				dte(0),
				dce(1)
				}
			ACCESS	read-write
			STATUS	mandatory
			DESCRIPTION
			 " LAPB station type for this interface.
			"
			::= { accLapbParmEntry 2 }
	    accLapbT1Timer	OBJECT-TYPE   
			SYNTAX	INTEGER (1..32000)
			ACCESS	read-write
			STATUS	mandatory
			DESCRIPTION
			 " T1 timer value (in milliseconds) for this
			   interface."
                        DEFVAL { 3000 }
			::= { accLapbParmEntry 3 }
	    accLapbN2Count	OBJECT-TYPE   
			SYNTAX	INTEGER (2..20)
			ACCESS	read-write
			STATUS	mandatory
			DESCRIPTION
			 " N2 counter (retry counter) for this interface."
                        DEFVAL { 20 }
			::= { accLapbParmEntry 4 }
	    accLapbFrameWindow	OBJECT-TYPE   
			SYNTAX	INTEGER (1..127)
			ACCESS	read-write
			STATUS	mandatory
			DESCRIPTION
			 " LAPB frame window.  If a value greater than
			   7 is specified, modulo-128 sequencing is used
			   instead of modulo-8 sequencing."
                        DEFVAL { 7 }
			::= { accLapbParmEntry 5 }
	    accLapbFlags	OBJECT-TYPE   
			SYNTAX	INTEGER (1..32)
			ACCESS	read-write
			STATUS	mandatory
			DESCRIPTION
			 " Number of flags to insert between frames
			   on transmission."
                        DEFVAL { 2 }
			::= { accLapbParmEntry 6 }
	    accHdlcRrPolling	OBJECT-TYPE
			SYNTAX  INTEGER (1..32000)
			ACCESS	read-write
			STATUS	mandatory
			DESCRIPTION
			"T3 Timer."
			::= { accLapbParmEntry 7 }
	    accHdlcFCS	OBJECT-TYPE
			SYNTAX  INTEGER  {
				ccitt-16(1),
				ccitt-32(2)
				}
			ACCESS	read-write
			STATUS	mandatory
			DESCRIPTION
			"FCS Mode."
			::= { accLapbParmEntry 8 }
	    accHdlcCoding	OBJECT-TYPE
			SYNTAX  INTEGER  {
				nrz (0),
				nrzi (1)
				}
			ACCESS	read-write
			STATUS	mandatory
			DESCRIPTION
			"HDLC Coding type.
			"
			::= { accLapbParmEntry 9 }
	    accHdlcDuplex	OBJECT-TYPE
			SYNTAX  INTEGER  {
				full (0),
				half (1)
				}
			ACCESS	read-write
			STATUS	mandatory
			DESCRIPTION
			"HDLC Duplex mode.
			"
			::= { accLapbParmEntry 10 }
	accHdlcIdleFill	OBJECT-TYPE
			SYNTAX	INTEGER {
				flags(1),
				ones(2)
			}
			ACCESS	read-write
			STATUS	mandatory
			DESCRIPTION
				"Fill between frames with flags or ones"
			::= { accLapbParmEntry 11 }
	accLapbStatTable    OBJECT-TYPE
			SYNTAX SEQUENCE OF AccLapbStatEntry
			ACCESS not-accessible
			STATUS mandatory
			DESCRIPTION
                          " A list of statistics for serial ports
                            configured for LABP protocol."
			::= { accLapb 3 }
          accLapbStatEntry  OBJECT-TYPE
                        SYNTAX AccLapbStatEntry
                        ACCESS not-accessible
                        STATUS mandatory
                        DESCRIPTION
                          " LAPB statistics for a specific port."
                        INDEX { accLapbStatIndex }
                        ::= { accLapbStatTable 1 }
		AccLapbStatEntry ::= SEQUENCE {
	    		accLapbStatIndex	INTEGER,
	    		accLapbStatBadFCSIns	Counter,
	    		accLapbStatFRMRIns	Counter,
	    		accLapbStatT1Timeouts 	Counter,
	    		accLapbStatREJIns 	Counter,
	    		accLapbStatREJOuts	Counter,
	    		accLapbStatShortIns	Counter
			}
	    accLapbStatIndex  OBJECT-TYPE    
			SYNTAX	INTEGER
			ACCESS	read-only
			STATUS	mandatory
			DESCRIPTION
                          " Port number for this LAPB serial port"
			::= { accLapbStatEntry 1 }
	    accLapbStatBadFCSIns  OBJECT-TYPE  
			SYNTAX	Counter
			ACCESS	read-only
			STATUS	mandatory
			DESCRIPTION
                          " Number of LAPB frames received with bad
                            frame checksum (FCS)."
			::= { accLapbStatEntry 2 }
	    accLapbStatFRMRIns	OBJECT-TYPE  
			SYNTAX	Counter
			ACCESS	read-only
			STATUS	mandatory
			DESCRIPTION
                          " Number of LAPB frames received with
                            framing errors"
			::= { accLapbStatEntry 3 }
	    accLapbStatT1Timeouts  OBJECT-TYPE	
			SYNTAX	Counter
			ACCESS	read-only
			STATUS	mandatory
			DESCRIPTION
                          " Number of T1 timeouts detected on this port"
			::= { accLapbStatEntry 4 }
	    accLapbStatREJIns  OBJECT-TYPE  
			SYNTAX	Counter
			ACCESS	read-only
			STATUS	mandatory
			DESCRIPTION
                          " number of REJECT LAPB frames received"
			::= { accLapbStatEntry 5 }
	    accLapbStatREJOuts	OBJECT-TYPE  
			SYNTAX	Counter
			ACCESS	read-only
			STATUS	mandatory
			DESCRIPTION
                          " Number of LAPB REJECT frames transmitted"
			::= { accLapbStatEntry 6 }
	    accLapbStatShortIns	 OBJECT-TYPE  
			SYNTAX	Counter
			ACCESS	read-only
			STATUS	mandatory
			DESCRIPTION
                          " Number of short LAPB frames received"
			::= { accLapbStatEntry 7 }

END
