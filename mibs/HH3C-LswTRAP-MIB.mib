HH3C-LswTRAP-MIB DEFINITIONS ::= BEGIN

IMPORTS enterprises, OBJECT-TYPE FROM SNMPv2-SMI;

hh3c OBJECT IDENTIFIER ::= { enterprises 25506 }
hh3cRhw OBJECT IDENTIFIER ::= { hh3c 8 }
hh3clswCommon OBJECT IDENTIFIER ::= { hh3cRhw 35 }
hh3cLswdevMMib OBJECT IDENTIFIER ::= { hh3clswCommon 9 }
hh3cLswdevMMibObject OBJECT IDENTIFIER ::= { hh3cLswdevMMib 1 }
hh3cdevMPowerStatusTable OBJECT IDENTIFIER ::= { hh3cLswdevMMibObject 2 }
hh3cdevMPowerStatusEntry OBJECT IDENTIFIER ::= { hh3cdevMPowerStatusTable 1 }
hh3cDevMPowerNum OBJECT IDENTIFIER ::= { hh3cdevMPowerStatusEntry 1 }
hh3cdevMFanStatusTable OBJECT IDENTIFIER ::= { hh3cLswdevMMibObject 1 }
hh3cdevMFanStatusEntry OBJECT IDENTIFIER ::= { hh3cdevMFanStatusTable 1 }
hh3cDevMFanNum OBJECT IDENTIFIER ::= { hh3cdevMFanStatusEntry 1 }
hh3cDevMFirstTrapTime OBJECT IDENTIFIER ::= { hh3cLswdevMMibObject 13 }
Hh3cLswTypeOfSlot ::=
	INTEGER {
	type-NULL(0),
	type-10OR100M(1),
	type-1000BASE-LX-SM(2),
	type-1000BASE-SX-MM(3),
	type-1000BASE-TX(4),
	type-100M-SINGLEMODE-FX(5),
	type-100M-MULTIMODE-FX(6),
	type-100M-100BASE-TX(7),
	type-100M-HUB(8),
	type-VDSL(9),
	type-STACK(10),
	type-1000BASE-ZENITH-FX(11),
	type-1000BASE-LONG-FX(12),
	type-ADSL(13),
	type-4T10OR100-4FX100SM(14),
	type-4T10OR100-4FX100MM(15),
	type-VSPL(16),
	type-ASPL(17),
	type-1000M-SFP(18),
	type-LS82O2CM(19),
	type-LS82P2CM(20),
	type-LS82O4GM(21),
	type-LS82GB4C(22),
	type-LS82GT4C(23),
	type-LS82ST4C(24),
	bOARD-TYPE-LS82DSPU(25),
	bOARD-TYPE-LS81GP8U(26),
	bOARD-TYPE-LS82GT20(27),
	bOARD-TYPE-LS82FE48(28),
	type-LS82T24B(29),
	type-LSB1SRPA(30),
	type-LSB1FT48A(31),
	type-LSB1FT48B(32),
	type-LSB1F48GA(33),
	type-LSB1F48GB(34),
	type-LSB1FP20A(35),
	type-LSB1FP20B(36),
	type-FT48A(37),
	type-GP4U(38),
	type-GP2U(39),
	type-TGX1A(40),
	type-1000BASE-LX-SM-IR-SC(41),
	type-1000BASE-SX-MM-SR-SC(42),
	type-1000BASE-T-RJ45(43),
	type-100BASE-FX-SM-IR-SC(44),
	type-100BASE-FX-MM-SR-SC(45),
	type-GIGA-STACK-1M-PC(46),
	type-1000BASE-LX-SM-VLR-LC(47),
	type-1000BASE-LX-SM-LR-LC(48),
	type-100BASE-FX-SM-LR-SC(49),
	type-1000BASE-X-GBIC(50),
	type-100M-SINGLEMODE-FX-LC(51),
	type-100M-MULTIMODE-FX-LC(52),
	type-1000BASE-4SFP(53),
	type-1000BASE-4GBIC(54),
	type-1000BASE-FIXED-4SFP(55),
	type-1000BASE-FIXED-4GBIC(56),
	type-LSB1GP12A(57),
	type-LSB1GP12B(58),
	type-LSB1TGX1A(59),
	type-LSB1TGX1B(60),
	type-LSB1P4G8A(61),
	type-LSB1P4G8B(62),
	type-LSB1A4G8A(63),
	type-LSB1A4G8B(64),
	type-FT48C(65),
	type-FP20(66),
	bOARD-TYPE-LS81FT48(67),
	bOARD-TYPE-LS81GB8U(68),
	bOARD-TYPE-LS81GT8U(69),
	bOARD-TYPE-LS81FS24(70),
	bOARD-TYPE-LS81FM24(71),
	bOARD-TYPE-LS82GP20(72),
	type-LSB1SRPB(73),
	type-LSB1F32GA(74),
	type-LSB1F32GB(75),
	type-LSB2FT48A(76),
	type-LSB2FT48B(77),
	type-LSB1GT12A(78),
	type-LSB1GT12B(79),
	type-PC4U(80),
	type-FT32A(81),
	type-GT4U(82),
	bOARD-TYPE-LS83FP20A(83),
	bOARD-TYPE-LS82HGMU(84),
	type-LSB1GP8TB(85),
	type-LSB1GP8TC(86),
	type-LSB1GT8PB(87),
	type-LSB1GT8PC(88),
	type-LSB1FT48C(89),
	type-LSB1FP20C(90),
	type-LSB1F32GC(91),
	type-LSB1GT12C(92),
	type-LSB1GP12C(93),
	type-LSB1P4G8C(94),
	type-LSB1TGX1C(95),
	type-LSB1GT24B(96),
	type-LSB1GT24C(97),
	type-LSB1GP24B(98),
	type-LSB1GP24C(99),
	type-LSB1XP2B(100),
	type-LSB1XP2C(101),
	type-LSB1GV48B(102),
	type-LSB1GV48C(103),
	type-LSB1SRPC(104),
	type-LSB1SRP1N0(105),
	type-LSB1SRP1N1(106),
	type-LSB1SRP1N2(107),
	type-GT24(108),
	type-GP24(109),
	type-XP2(110),
	type-GV48(111),
	type-LSG1GP8U(112),
	type-LSG1GT8U(113),
	type-LSG1TG1U(114),
	type-LSG1TD1U(115),
	type-LSB2FT48C(116),
	type-LSB1GT48B(117),
	type-LSB1GT48C(118),
	type-LS81GT48(119),
	type-LS81SRPG0(120),
	type-LS81SRPG1(121),
	type-LS81SRPG2(122),
	type-LS81SRPG3(123),
	type-SR01SRPUB(125),
	type-SR01SRPUA(126),
	type-SR01GP12L(127),
	type-SR01GP12W(128),
	type-SR01FT48L(129),
	type-SR01FT48W(130),
	type-SR01XK1W(131),
	type-SR01FP20W(132),
	type-SR01GT12W(133),
	type-SR01F32GL(134),
	type-SR01F32GW(135),
	type-SR01GT8PL(136),
	type-SR01GT8PW(137),
	type-SR01P4G8W(138),
	type-LSA1FP8U(139),
	type-LSB1SP4B(140),
	type-LSB1SP4C(141),
	type-LSB1UP1B(142),
	type-LSB1UP1C(143),
	type-LSB1XP4B(144),
	type-LSB1XP4C(145),
	type-SP4(146),
	type-UP1(147),
	type-XP4(148),
	type-LS81VSNP(149),
	type-LS81T12P(150),
	type-LS81P12T(151),
	type-LS81GP8UB(152),
	type-LS81FT48E(153),
	type-LS81GP4UB(154),
	type-LS81GT8UE(155),
	type-LS81GT48A(156),
	type-LS81FP48(157),
	type-LSB1XK1B(158),
	type-LSB1XK1C(159),
	type-SR01SRPUC(160),
	type-SR01SRPUD(161),
	type-SR01SRPUE(162),
	type-LSB1SRP1N3(163),
	type-LSB1VP2B(164),
	type-LSB1NATB(165),
	type-LSB1VPNB(166),
	type-LSGP8P(167),
	type-LSXK1P(168),
	type-LSXP2P(169),
	type-LS81FT48F(170),
	type-LS81PT8G(171),
	type-LS81PT4G(172),
	type-LSSTK24G(173),
	type-LS82GT20A(174),
	type-LS82GP20A(175),
	type-LS81TGX1C(176),
	type-VP2(177),
	type-LSA1FB8U(178),
	type-LS81T12PE(179),
	type-LS81P12TE(180),
	type-LSB1SRP2N0(181),
	type-LSB1SRP2N3(182),
	type-LSB1GV48DB(183),
	type-LSB1FW8B(184),
	type-LSB1IPSEC8B(185),
	type-LSB1IDSB(186),
	type-LSB1IPSB(187),
	type-LSB2FT48CA(188),
	type-LSB1FP20CA(189),
	type-LSB1F32GCA(190),
	type-LSB1P4G8CA(191),
	type-LSB1GT12CA(192),
	type-LSB1GT24CA(193),
	type-LSB1GP12CA(194),
	type-LSB1GP24CA(195),
	type-LSB1GT8PCA(196),
	type-LSB1XP2CA(197),
	type-LSB1XK1CA(198),
	type-LSB1XP4CA(199),
	type-LSB1UP1CA(200),
	type-LSB1SP4CA(201),
	type-LSB1VP2CA(202),
	type-SR01FT48WA(203),
	type-SR01FP20WA(204),
	type-SR01F32GWA(205),
	type-SR01P4G8WA(206),
	type-SR01GT12WA(207),
	type-SR01GT24WA(208),
	type-SR01GP12WA(209),
	type-SR01GP24WA(210),
	type-SR01GT8PWA(211),
	type-SR01XP2WA(212),
	type-SR01XK1WA(213),
	type-SR01UP1WA(214),
	type-SR01SP4WA(215),
	type-GP8U(216),
	type-LSEXP1P(217),
	type-LSEXK1P(218),
	type-LSEXS1P(219),
	type-LS81GP48(220),
	type-LS81GT48B(221),
	type-LS81T16P(222),
	type-LS81T32P(223),
	type-LS81TGX2(224),
	type-LS81TGX4(225),
	type-LSB1GV48DA(226),
	type-SR01GV48VB(227),
	type-LSB1GT24DB(228),
	type-LSB1GP24DB(229),
	type-LSB1GP24DC(230),
	type-LSB1FW8DB(231),
	type-LSB1IPSEC8DB(232),
	type-SR01GT24VB(233),
	type-SR01GP24VC(234),
	type-SR01VP2WA(235),
	type-SR01FW8VB(236),
	type-SR01IPSEC8VB(237),
	type-SR01NATL(238),
	type-SR01VPNL(239),
	type-LSB1GP24CB(240),
	type-LSB1GP48DB(241),
	type-LSB1XP2CB(242),
	type-XP4L(243),
	type-LSB1XP4LDB(244),
	type-LSB1XP4LDC(245),
	type-AHP4(246),
	type-LSB1AHP4GCA(247),
	type-CLP4(248),
	type-LSB1CLP4GCA(249),
	type-ET32(250),
	type-LSB1ET32GCA(251),
	type-LSB1IDSDB(252),
	type-LSB1SRP2N1(253),
	bOARD-TYPE-LS82SRPB(254),
	bORAD-TYPE-LS83SRPC(255),
	type-Main(256),
	type-LSB1SRP2N2(257),
	type-LSB1NAMB(258),
	type-RSP2(259),
	type-LSB1RSP2CA(260),
	type-SR01XP4LVC(261),
	type-SR01AHP4GWA(262),
	type-SR01CLP4GWA(263),
	type-SR01ET32GWA(264),
	type-SR01IDSVB(265),
	type-SR01SRPUF(266),
	type-SR01NAML(267),
	type-SR01RSP2WA(268),
	type-LSPM1XP1P(269),
	type-LSPM1XP2P(270),
	type-LSPM1CX2P(271),
	type-STK-1000BASE-T(272),
	type-LSB1SRP1M0(300),
	type-LSB1SRP1M1(301),
	type-LSB1GP12DB(302),
	type-LSB1GT12DB(303),
	type-LSB1XK1DB(304),
	type-LSB1XP2DB(305),
	type-LSB1XP2DC(306),
	type-LSB1GT48LDB(307),
	type-LSB1XP4TDB(308),
	type-LSB1XP4TDC(309),
	type-LSB1RSP2DC(310),
	type-LSB1VP2DC(311),
	type-LSB1XP4DB(312),
	type-LSB1SRP2E0(313),
	type-LSB1SRP2E1(314),
	type-LSB1SRP2E2(315),
	type-LSB1SRP2E3(316),
	type-SR01SRPUQ(317),
	type-AHP1(318),
	type-AHP2(319),
	type-CLP1(320),
	type-CLP2(321),
	type-ET16(322),
	type-LSB1SRP1NA0(323),
	type-LSB1SRP1NA1(324),
	type-LSB1SRP1NA2(325),
	type-LSB1SRP1NA3(326),
	type-SR01AHP1GWA(327),
	type-SR01AHP2GWA(328),
	type-SR01CLP1GWA(329),
	type-SR01CLP2GWA(330),
	type-SR01ET16GWA(331),
	type-SR01GP12VB(332),
	type-SR01XK1VB(333),
	type-SR01XP2VC(334),
	type-SR01XP4LVB(335),
	type-SR01SRPUEA(336),
	type-LSB1SRP1N4(337),
	type-LSB1SRP1N5(338),
	type-LSB1SRP1N6(339),
	type-LSB1SRP1N7(340),
	type-LSB1SRP2N4(341),
	type-LSB1SRP2N5(342),
	type-LSB1SRP2N6(343),
	type-LSB1SRP2N7(344),
	type-LSB1SRP1NA4(345),
	type-LSB1SRP1NA5(346),
	type-LSB1SRP1NA6(347),
	type-LSB1SRP1NA7(348),
	type-LSB2GV48DA(349),
	type-LSB1RGP2GDB(350),
	type-LSB1RGP4GDB(351),
	type-LSB2GP24DB(352),
	type-LSB2GP24DC(353),
	type-LSB2GT24DB(354),
	type-LSB2FW8DB(355),
	type-LSB2IPSEC8DB(356),
	type-LSB2GV48DB(357),
	type-RGP2(358),
	type-RGP4(359),
	type-SR02FW8VB(360),
	type-SR02IPSEC8VB(361),
	type-LSB2SRP1N0(362),
	type-LSB2SRP1N1(363),
	type-LSB2SRP1N2(364),
	type-LSB2SRP1N3(365),
	type-LSB2SRP1N4(366),
	type-LSB2SRP1N5(367),
	type-LSB2SRP1N6(368),
	type-LSB2SRP1N7(369),
	type-SR02SRPUE(370),
	type-SR01LN1BQH0(371),
	type-SR01DXP1L(372),
	type-SR01DGP10L(373),
	type-SR01DRSP2L(374),
	type-SR01DRUP1L(375),
	type-SR01DGP20R(376),
	type-SR01DPLP8L(377),
	type-SR01DXP2R(378),
	type-LSB1FW2A0(379),
	type-LSB1GP48LDB(380),
	type-SR01LN1BNA0(381),
	type-SR01LN2BQH0(382),
	type-SR01LN2BNA0(383),
	type-SR01DGT20R(384),
	type-SR01DPSP4L(385),
	type-SR01DPUP1L(386),
	type-SR01DPL2G6L(387),
	type-SR01DPH2G6L(388),
	type-SR01DPS2G4L(389),
	type-SR01DCL1G8L(390),
	type-SR01DCL2G8L(391),
	type-SR01DET8G8L(392),
	type-SR02SRP2E3(393),
	type-SR02SRP1E3(394),
	type-SR02SRP1M3(395),
	type-SR01DQCP4L(396),
	type-SR01DTCP8L(397),
	type-LSB1AFC1A0(398),
	type-LSB1SSL1A0(399),
	type-IMNAM(400),
	type-IMNAT(401),
	type-PICAHP1L(402),
	type-PICALP4L(403),
	type-PICCHP4L(404),
	type-PICCHS1G4L(405),
	type-PICCLS4G4L(406),
	type-PICCSP1L(407),
	type-LSB1ACG1A0(408),
	type-LST1MRPNC1(409),
	type-LST1SF18B1(410),
	type-LST1SF08B1(411),
	type-LST1GT48LEC1(412),
	type-LST1GP48LEC1(413),
	type-LST1XP4LEC1(414),
	type-LST1XP8LEC1(415),
	type-LSR1SRP2B1(416),
	type-LSR1SRP2C1(417),
	type-LSR1SRP2B2(418),
	type-LSR1SRP2C2(419),
	type-LSR1GT24LEC1(420),
	type-LSR1GP24LEB1(421),
	type-LSR1GP24LEC1(422),
	type-LSR1GT48LEB1(423),
	type-LSR1GT48LEC1(424),
	type-LSR1GP48LEB1(425),
	type-LSR1GP48LEC1(426),
	type-LSR2GV48REB1(427),
	type-LSR1XP2LEB1(428),
	type-LSR1XP2LEC1(429),
	type-LSR1XP4LEB1(430),
	type-LSR1XP4LEC1(431),
	type-IMFW(432),
	type-LSB1LB1A0(433),
	type-LSB1IPS1A0(434),
	type-LST1GT48LEB1(435),
	type-LST1GP48LEB1(436),
	type-LST1XP4LEB1(437),
	type-LST1XP8LEB1(438),
	type-LST1XP32REB1(439),
	type-LST1XP32REC1(440),
	type-LSR1FW2A1(441),
	type-LSR1SSL1A1(442),
	type-SR01DET32G2L(443),
	type-LSR1GP24LEF1(444),
	type-LSR1XP4LEF1(445),
	type-LSR1LB1A1(446),
	type-LSR1NSM1A1(447),
	type-LSR1ACG1A1(448),
	type-LSR1IPS1A1(449),
	type-LSR2GP24LEB1(450),
	type-LSR2GT24LEB1(451),
	type-LSR2GT48LEB1(452),
	type-SPC-GP24L(453),
	type-SPC-GT48L(454),
	type-SPC-GP48L(455),
	type-SPC-XP2L(456),
	type-SPC-XP4L(457),
	type-SR06SRP2E3(458),
	type-SPE-2010-E(459),
	type-SPE-2020-E(460),
	type-SPC-XP4L-S-SDI(461),
	type-SPC-GT48L-SDI(462),
	type-SPC-GP48L-S-SDI(463),
	type-SR02OPMA0(464),
	type-LSR1XP16REB1(465),
	type-LSR1GP48LEF1(466),
	type-LST1GP48LEF1(467),
	type-LST1XP8LEF1(468),
	type-SPE-1010-II(469),
	type-SPE-1010-E-II(470),
	type-SPE-1020-II(471),
	type-SPE-1020-E-II(472),
	type-LST1FW2A1(473),
	type-LST1NSM1A1(474),
	type-LST1LB1A1(475),
	type-LST1ACG1A1(476),
	type-LST1IPS1A1(477),
	type-LSR1DRUP1L1(478),
	type-LSR1DPUP1L1(479),
	type-LSR1DPSP4L1(480),
	type-LSR1DTCP8L1(481),
	type-LSR1DXP1L1(482),
	type-LSR1DGP10L1(483),
	type-LSR1LN1BNL1(484),
	type-LSR1LN2BL1(485),
	type-LSR1SRP2D1(486),
	type-IM-NAT-II(487),
	type-IM-NAM-II(488),
	type-CR-MRP-I(489),
	type-CR-SF18C(490),
	type-CR-SF08C(491),
	type-CR-SPC-XP8LEF(492),
	type-CR-SPC-XP4LEF(493),
	type-CR-SPC-GP48LEF(494),
	type-CR-SPC-GT48LEF(495),
	type-CR-SPE-3020-E(496),
	type-CR-SPC-PUP4L-E(497),
	type-LST1SF08C1(498),
	type-LST1SF18C1(499),
	type-LS81GP16TM(500),
	type-LS81VP4C(501),
	type-LS8M1PT8P0(502),
	type-LS8M1PT8GB0(503),
	type-LS8M1PT4GB0(504),
	type-LS81GP2R(505),
	type-LS81GP4R(506),
	type-LS81IPSECA(507),
	type-LS81FWA(508),
	type-LS82VSNP(509),
	type-LSQ1GV48SA(510),
	type-LSQ1SRPB(511),
	type-LSQ1SRP2XB(512),
	type-LSQ1SRP1CB(513),
	type-LSQ1FV48SA(514),
	type-LSD1MPUA(515),
	type-LSD1GP20A0(516),
	type-LSD1GP20TA0(517),
	type-LSD1GP36A0(518),
	type-LSD1GP20XA0(519),
	type-LSD1GP20EA0(520),
	type-LSD1GP20RA0(521),
	type-LSD1GP16A0(522),
	type-LSD1GT16A0(523),
	type-LSD1XP2A0(524),
	type-LSD1EP2A0(525),
	type-LSD1RP2A0(526),
	type-LSQ1GV48SC(527),
	type-LSQ1FP48SA(528),
	type-LSQ1GP24SC(529),
	type-LSQ1GT24SC(530),
	type-LSQ1TGX2SC(531),
	type-LSQ1GP12EA(532),
	type-LSQ1TGX1EA(533),
	type-LSQ1P24XGSC(534),
	type-LSQ1T24XGSC(535),
	type-LS81TGX1B(536),
	type-LSQ1PT4PSC0(537),
	type-LS81SRPG13(538),
	type-LS81SRPG14(539),
	type-LS81SRPG15(540),
	type-LSQ1GP48SC0(541),
	type-LSQ1GP12SC0(542),
	type-LSD1SRPA0(543),
	type-LSD1SRPB0(544),
	type-LSD1SRPC0(545),
	type-LSD1GT16PES0(546),
	type-LSD1GP24ES0(547),
	type-LSD1GT24XES0(548),
	type-LSD1GP24XES0(549),
	type-LSD1XP2ES0(550),
	type-LSD1GP48ES0(551),
	type-LSQ1MPUA0(552),
	type-LSQ1MPUA1(553),
	type-LSQ1FWBSC0(554),
	type-LSQ1PT8PSC0(555),
	type-LSQ1PT16PSC0(556),
	type-SA11MPUA0(557),
	type-SA11MPUB0(558),
	type-LSQ1AFCBSC0(559),
	type-LSQ1MPUB0(560),
	type-LSQ1MPUB1(561),
	type-LSQ1PT4PSC1(562),
	type-LSQ1PT8PSC1(563),
	type-LSQ1PT16PSC1(564),
	type-LSQ1FP48USA0(565),
	type-LSQ1FP48USA1(566),
	type-LSQ1FV48USA0(567),
	type-LSQ1FV48USA1(568),
	type-LSQ1SRPD0(569),
	type-LSQ1CGP24TSC0(570),
	type-LSQ1GP24TSC0(571),
	type-LSQ1ACGASC0(572),
	type-LSD1XP1ES0(573),
	type-LSD1GP12ES0(574),
	type-LSQ1SRP12GB0(575),
	type-LSQ1GV40PSC0(576),
	type-LSQ1FWBSC1(577),
	type-LSQ1NSMSC0(578),
	type-LSQ1NSMSC1(579),
	type-LSQ1AFDBSC0(580),
	type-LS81MPUB(581),
	type-LS81FP48XL(582),
	type-LS81FT48XL(583),
	type-LS81GP12XL(584),
	type-LS81GP24XL(585),
	type-LS81GP48XL(586),
	type-LS81GT24XL(587),
	type-LS81GT48XL(588),
	type-LS81TGX2XL(589),
	type-LSQ1GV48SD0(590),
	type-LSQ1GP48EB0(591),
	type-LSQ1IPSSC0(592),
	type-LSQ1GV48SD1(593),
	type-LSQ1GP48SD0(594),
	type-LSQ1GP48SD1(595),
	type-LSQ1SRPA0(596),
	type-LSQ1SRPA1(597),
	type-LSQ2FP48SA0(598),
	type-LSQ2FP48SA1(599),
	type-LSQ2FT48SA0(600),
	type-LSQ2FT48SA1(601),
	type-LSQ1GV24PSC0(602),
	type-LSQ1GV24PSC1(603),
	type-LSQ1CGV24PSC0(604),
	type-LSQ1CGV24PSC1(605),
	type-LSQ1GP24TEB0(606),
	type-LSQ1GP24TEB1(607),
	type-LSQ1GP24TSD0(608),
	type-LSQ1GP24TSD1(609),
	type-LSQ1GP24TXSD0(610),
	type-LSQ1GP24TXSD1(611),
	type-LSQ1TGX2EB0(612),
	type-LSQ1TGX2EB1(613),
	type-LSQ1TGX2SD0(614),
	type-LSQ1TGX2SD1(615),
	type-LSQ1TGX4SD0(616),
	type-LSQ1TGX4SD1(617),
	type-LSQ1TGX8SD0(618),
	type-LSQ1TGX8SD1(619),
	type-LSQ1GP48EB1(620),
	type-LSQ1TGX4EB0(621),
	type-LSQ1TGX4EB1(622),
	type-LSQ1GP12SC3(623),
	type-LSQ1GP24TSC3(624),
	type-LSQ1GP48SC3(625),
	type-LSQ1GV48SC3(626),
	type-LSQ1MPUA3(627),
	type-LSQ1SRP1CB3(628),
	type-LSQ1SRPA3(629),
	type-LSQ2FP48SA3(630),
	type-LSQ2FT48SA3(631),
	type-LSQ1MPUB3(632),
	type-LSQ1CGP24TSC3(633),
	type-LSQ1MPUB4(634),
	type-LSQ1SRPD4(635),
	type-LSQ1SSLSC0(636),
	type-LSQ1LBSC0(637),
	type-LSQ1NAT24SC0(638),
	type-LSQ1SRP12GB4(639),
	type-LSQ1TGS8SC0(640),
	type-LSQ3PT4PSC0(641),
	type-EWPXM2MPUB0(642),
	type-EWPXM2SRP12GB0(643),
	type-EWPXM2SRPD0(644),
	type-EWPXM2GP24TSD0(645),
	type-EWPXM2GP24TXSD0(646),
	type-EWPXM2TGX4SD0(647),
	type-EWPXM2GP48SD0(648),
	type-EWPXM2GP24TSC0(649),
	type-EWPXM2TGX2SC0(650),
	type-EWPXM2GP48SC0(651),
	type-LS7500-GP48-SC(652),
	type-LS7500-GP48-SD(653),
	type-LS7500-GT48-SC(654),
	type-LS7500-GT48-SD(655),
	type-LS7500-SRPG1(656),
	type-LS7500-SRPG2(657),
	type-LS7500-XP4-SD(658),
	type-LS7500-XP8-SD(659),
	type-LSQ4PT4PSC0(660),
	type-LSQ4PT8PSC0(661),
	type-LSQ4PT16PSC0(662),
	type-LSQ1GP24TSA0(663),
	type-LSQ1GV24PSA0(664),
	type-LSQ1SRPD3(665),
	type-LSQ1SUPA0(666),
	type-LSU1FAB04A0(667),
	type-LSU1FAB08A0(668),
	type-LSU1TGS8EA0(669),
	type-LSU1TGS8EB0(670),
	type-LSU1TGS8SE0(671),
	type-LSUTGS16SC0(672),
	type-LSU1SUPA0(673),
	type-LSU1GP24TXEA0(674),
	type-LSU1GP24TXEB0(675),
	type-LSU1GP24TXSE0(676),
	type-LSU1GP48EA0(677),
	type-LSU1GP48EB0(678),
	type-LSU1GP48SE0(679),
	type-LSU1GT48EA0(680),
	type-LSU1GT48SE0(681),
	type-LSU1TGX4EA0(682),
	type-LSU1TGX4EB0(683),
	type-LSU1TGX4SE0(684),
	type-LSQ1FAB08A0(685),
	type-EWPX2WCMD0(686),
	type-LSQ1WCMD0(687),
	type-LSQ1IAGSC0(688),
	type-LSU1GP24TSE0(689),
	type-LSQ1TGS16SC0(690),
	type-EWPX2TGS16SC0(691),
	type-LSQ1SUPA3(692),
	type-LSQ1FAB04A3(693),
	type-LSQ1FAB08A3(694),
	type-LSQ1GT48SC0(695),
	type-LSR2SRP2C1(696),
	type-LSR2SRP2C2(697),
	type-1000BASE-X-COMBO(701),
	type-EPON-1000M(702),
	type-1000BASE-FIXED-2SFP-T-2RJ45(703),
	type-100M-1550-BIDI(704),
	type-100M-1310-BIDI(705),
	type-1000BASE-FIXED-4RJ45-4SFP-COMBO(706),
	type-LSH1PK2T(707),
	type-LSPM2GP2P(708),
	type-LSWM1GT16P(709),
	type-LSWM1GP16P(710),
	type-LSWM1XP2P(711),
	type-LSWM1XP4P(712),
	type-LSWM1SP2P(713),
	type-LSWM1SP4P(714),
	type-LSWM148POEM(715),
	type-LSWM1FW10(716),
	type-LSWM1WCM10(717),
	type-LSWM1IPS10(718),
	type-LSWM1WCM20(719),
	type-LSPM2SP2P(725),
	type-LSPM2SP2PA(726),
	type-LSP5GP8P(727),
	type-LSP5GT8P(728),
	type-LSWM1FC4P(729),
	type-LSW1XGT4P0(730),
	type-LSW1XGT2P0(731),
	type-LSP1XGT2P(732),
	type-LSPM1XGT2P(733),
	type-WX5002MPU(800),
	type-LS8M1WCMA(801),
	type-EWPX1G24XA0(802),
	type-LSQ1WCMB0(803),
	type-LSB1WCM2A0(804),
	type-EWPX1WCMB0(805),
	type-EWPX1G24XC0(806),
	type-EWPX1WCMC0(807),
	type-EWPX1FWA0(808),
	type-EWPX1G10XC0(809),
	type-EWPX1WCM10C0(810),
	type-LSR1WCM2A1(811),
	type-EWPX1WAP0(812),
	type-EWPX1WCMD0(813),
	type-EWPX1G24XCE0(814),
	type-EWPX1WCMCE0(815),
	type-LSR1DRSP2L1(900),
	type-PIC-CLF2G8L(901),
	type-PIC-CLF4G8L(902),
	type-SR02SRP2F3(903),
	type-SR02SRP1F3(904),
	type-LST1GT48LEA1(905),
	type-LST1GP48LEA1(906),
	type-LST2XP8LEA1(907),
	type-LST1GT48LEY1(908),
	type-LST1GP48LEY1(909),
	type-LST1XP32REY1(910),
	type-LST1XP8LEY1(911),
	type-LST1GP48LEZ1(912),
	type-LST1XP8LEZ1(913),
	type-IM-FW-II(914),
	type-IM-IPS(915),
	type-IM-SSL(916),
	type-IM-LB(917),
	type-IM-ACG(918),
	type-LSR1XP16REC1(919),
	type-LST2XP8LEB1(920),
	type-LST2XP8LEC1(921),
	type-LST2XP8LEF1(922),
	type-LST2XP4LEB1(923),
	type-LST2XP4LEC1(924),
	type-LST2XP32REB1(925),
	type-LST2XP32REC1(926),
	type-LSR1WCM3A1(927),
	type-LST1XP16LEB1(928),
	type-LST1XP16LEC1(929),
	type-CR-SPC-XP4L-E-I(930),
	type-LST2MRPNC1(931),
	type-LST2SF08C1(932),
	type-LST2SF18C1(933),
	type-SR02SRP2G3(934),
	type-CR-SPE-3020-E-I(935),
	type-CR-SPC-PUP4L-E-I(936),
	type-CR-SPC-XP4LEF-I(937),
	type-CR-SPC-XP8LEF-I(938),
	type-LST3XP8LEB1(939),
	type-LST3XP8LEC1(940),
	type-LST1FW3A1(941),
	type-CR-IM-NAM1A(942),
	type-LSR2SRP2B1(943),
	type-LSR2SRP2B2(944),
	type-LSR2SRP2D1(945),
	type-LST3XP8LEY1(946),
	type-LST2XP32REY1(947),
	type-LST1XP16LEY1(948),
	type-SR0M2SRP2G3(949),
	type-SR0M2SRP1G3(950),
	type-SPC-GP48LA(951),
	type-SPC-GT48LA(952),
	type-SPC-XP4LA(953),
	type-SPC-XP2LA(954),
	type-SPC-GP24LA(955),
	type-SPC-XP16RA(956),
	type-CR-IM-FW1A(957),
	type-SPC-XP16R(958),
	type-CR-IM-LB1A(959),
	type-LST1GT48LEC2(960),
	type-LST1GP48LEC2(961),
	type-LST1XP16LEC2(962),
	type-LST2XP8LEC2(963),
	type-LST2XP32REC2(964),
	type-CR-IM-MAC1A(965),
	type-LST1XP48LFD1(966),
	type-LST1XP40RFD1(967),
	type-LST1XP40RFG1(968),
	type-LST1XLP16RFD1(969),
	type-LST1CP4RFD1(970),
	type-LST1CP4RFG1(971),
	type-LST1SF08E1(972),
	type-LST1SF18E1(973),
	type-LST1MRPNE1(974),
	type-LSX1CGX8FB0(975),
	type-LSX1CGX8FB0(976),
	type-LSX1QGS24FB0(977),
	type-LSX1QGS24FB1(978),
	type-LSX1TGS24FB0(979),
	type-LSX1TGS24FB1(980),
	type-LSX1TGS48FB0(981),
	type-LSX1TGS48FB1(982),
	type-LST1XP48LFD2(983),
	type-LST1XP40RFD2(984),
	type-LST1XP40RFG2(985),
	type-LST1XLP16RFD2(986),
	type-LST1CP4RFD2(987),
	type-LST1CP4RFG2(988),
	type-MPE-1004(989),
	type-MIC-GP4L(990),
	type-MIC-GP8L(991),
	type-MIC-SP4L(992),
	type-MIC-ET16L(993),
	type-MIC-CLP4L(994),
	type-MIC-CLP2L(995),
	type-LST1IPS2A1(996),
	type-LSU1QGC4SF0(1201),
	type-LSU1QGS8SF0(1202),
	type-LSU1TGS48SF0(1203),
	type-LSU1QGS4SF0(1204),
	type-LSU1TGS32SF0(1205),
	type-LSU1FAB08D0(1206),
	type-LSU1FAB04B0(1207),
	type-LSU1FAB08B0(1208),
	type-LSU1FAB12D0(1209),
	type-LSU1FAB12B0(1210),
	type-LSU1FAB04D0(1211),
	type-LSQ1CTGS16SC0(1212),
	type-EWPX2CTGS16SC0(1213),
	type-LSU3WCMD0(1214),
	type-EWPX3WCMD0(1215),
	type-LSQ1QGS4SC0(1216),
	type-LSQ1QGC4SC0(1217),
	type-LSU1TGT24SF0(1218),
	type-LSQ1QGS8SC3(1219),
	type-LSQ1TGS32SC3(1220),
	type-LSQ1QGS4SC3(1221),
	type-LSQ1TGS48SC3(1222),
	type-LSQ1QGC4SC3(1223),
	type-LSQ1FAB12D3(1224),
	type-LSQ1FAB08D3(1225),
	type-LSQ1FAB04D3(1226),
	type-LSQ1TGS8EB3(1227),
	type-LSQ1TGT24SC3(1228),
	type-LSQ1FAB08B0(1229),
	type-EWPX2CTGS16SC(1230),
	type-LSU1SUPB0(1231),
	type-LSQ1GP48SA0(1232),
	type-LSQ1TGX2SA0(1233),
	type-LSV1SRPUA(1234),
	type-LSV1QGS12SA(1235),
	type-LSV1MPUA(1236),
	type-LSX1SUP10A0(1237),
	type-LSX1SUP16A0(1238),
	type-LSX1SUP10A1(1239),
	type-LSX1SUP16A1(1240),
	type-LSX1FAB10B0(1241),
	type-LSX1FAB16B0(1242),
	type-LSX1FAB10B1(1243),
	type-LSX1FAB16B1(1244),
	type-LSX1QGS16EA0(1245),
	type-LSX1TGS48EA0(1246),
	type-LSX1QGS16EA1(1247),
	type-LSX1TGS48EA1(1248),
	type-LSU1TGT24SF9(1249),
	type-LSU1QGS8SF9(1250),
	type-LSU1QGS4SF9(1251),
	type-LSU1TGS48SF9(1252),
	type-LSU1TGS32SF9(1253),
	type-LSU1FAB08D9(1254),
	type-LSU1SUPB9(1255),
	type-RPU-5120-28SC-HI(1400),
	type-RPU-5120-52SC-HI(1401),
	type-RPU-5120-34C-HI(1402),
	type-RPU-5120-58C-HI(1403),
	type-RPU-5500-34C-HI(1404),
	type-RPU-5500-58C-HI(1405),
	type-RPU-5500-34C-HI-D(1406),
	type-RPU-5500-58C-HI-D(1407),
	type-RPU-5820V2-52Q(1408),
	type-RPU-5820V2-52QF(1409),
	type-RPU-5820V2-52QS-GE(1410)
	}

hh3cLswDeviceAdmin OBJECT IDENTIFIER ::= { hh3clswCommon 18 }
hh3cLswSlotConf OBJECT IDENTIFIER ::= { hh3cLswDeviceAdmin 4 }
hh3cLswFrameTable OBJECT IDENTIFIER ::= { hh3cLswSlotConf 2 }
hh3cLswFrameEntry OBJECT IDENTIFIER ::= { hh3cLswFrameTable 1 }
hh3cLswFrameIndex OBJECT IDENTIFIER ::= { hh3cLswFrameEntry 1 }
hh3cLswSlotTable OBJECT IDENTIFIER ::= { hh3cLswSlotConf 3 }
hh3cLswSlotEntry OBJECT IDENTIFIER ::= { hh3cLswSlotTable 1 }
hh3cLswSlotIndex OBJECT IDENTIFIER ::= { hh3cLswSlotEntry 1 }
hh3cLswSubslotTable OBJECT IDENTIFIER ::= { hh3cLswSlotConf 4 }
hh3cLswSubslotEntry OBJECT IDENTIFIER ::= { hh3cLswSubslotTable 1 }
hh3cLswSubslotIndex OBJECT IDENTIFIER ::= { hh3cLswSubslotEntry 1 }
hh3cLswTrapMib OBJECT IDENTIFIER ::= { hh3clswCommon 12 }

hh3csLswTRAPMibObject OBJECT IDENTIFIER ::= { hh3cLswTrapMib 1 }

hh3cpowerfailure TRAP-TYPE
	ENTERPRISE hh3csLswTRAPMibObject
	VARIABLES { hh3cDevMPowerNum, hh3cDevMFirstTrapTime }
DESCRIPTION "Power supply failure"
	::= 1


hh3cPowerNormal TRAP-TYPE
	ENTERPRISE hh3csLswTRAPMibObject
	VARIABLES { hh3cDevMPowerNum, hh3cDevMFirstTrapTime }
DESCRIPTION "Power supply normal"
	::= 2


hh3cMasterPowerNormal TRAP-TYPE
	ENTERPRISE hh3csLswTRAPMibObject
	VARIABLES { hh3cDevMPowerNum }
DESCRIPTION "Master power supply normal"
	::= 3


hh3cSlavePowerNormal TRAP-TYPE
	ENTERPRISE hh3csLswTRAPMibObject
	VARIABLES { hh3cDevMPowerNum }
DESCRIPTION "Slave power supply normal"
	::= 4


hh3cPowerRemoved TRAP-TYPE
	ENTERPRISE hh3csLswTRAPMibObject
	VARIABLES { hh3cDevMPowerNum }
DESCRIPTION "Power removed"
	::= 5


hh3cfanfailure TRAP-TYPE
	ENTERPRISE hh3csLswTRAPMibObject
	VARIABLES { hh3cDevMFanNum }
DESCRIPTION "Fan failure"
	::= 6


hh3cFanNormal TRAP-TYPE
	ENTERPRISE hh3csLswTRAPMibObject
	VARIABLES { hh3cDevMFanNum }
DESCRIPTION "Fan normal"
	::= 7


hh3cBoardRemoved TRAP-TYPE
	ENTERPRISE hh3csLswTRAPMibObject
	VARIABLES { hh3cLswFrameIndex, hh3cLswSlotIndex }
DESCRIPTION "Board removed"
	::= 8


hh3cBoardInserted TRAP-TYPE
	ENTERPRISE hh3csLswTRAPMibObject
	VARIABLES { hh3cLswFrameIndex, hh3cLswSlotIndex }
DESCRIPTION "Board inserted"
	::= 9


hh3cBoardFailure TRAP-TYPE
	ENTERPRISE hh3csLswTRAPMibObject
	VARIABLES { hh3cLswFrameIndex, hh3cLswSlotIndex }
DESCRIPTION "Board failed"
	::= 10


hh3cBoardNormal TRAP-TYPE
	ENTERPRISE hh3csLswTRAPMibObject
	VARIABLES { hh3cLswFrameIndex, hh3cLswSlotIndex }
DESCRIPTION "Board normal"
	::= 11


hh3cSubcardRemove TRAP-TYPE
	ENTERPRISE hh3csLswTRAPMibObject
	VARIABLES { hh3cLswFrameIndex, hh3cLswSlotIndex, hh3cLswSubslotIndex }
DESCRIPTION "Sub card removeed"
	::= 12


hh3cSubcardInsert TRAP-TYPE
	ENTERPRISE hh3csLswTRAPMibObject
	VARIABLES { hh3cLswFrameIndex, hh3cLswSlotIndex, hh3cLswSubslotIndex }
DESCRIPTION "Sub card inserted"
	::= 13


hh3cBoardTemperatureLower TRAP-TYPE
	ENTERPRISE hh3csLswTRAPMibObject
	VARIABLES { hh3cLswFrameIndex, hh3cLswSlotIndex }
DESCRIPTION "Board temperature low"
	::= 14


hh3cBoardTemperatureFromLowerToNormal TRAP-TYPE
	ENTERPRISE hh3csLswTRAPMibObject
	VARIABLES { hh3cLswFrameIndex, hh3cLswSlotIndex }
DESCRIPTION "Board temperature form lower to normal"
	::= 15


hh3cBoardTemperatureHigher TRAP-TYPE
	ENTERPRISE hh3csLswTRAPMibObject
	VARIABLES { hh3cLswFrameIndex, hh3cLswSlotIndex }
DESCRIPTION "Board temperature high"
	::= 16


hh3cBoardTemperatureFormHigherToNormal TRAP-TYPE
	ENTERPRISE hh3csLswTRAPMibObject
	VARIABLES { hh3cLswFrameIndex, hh3cLswSlotIndex }
DESCRIPTION "Board temperature from higher to normal"
	::= 17


hh3cRequestLoading TRAP-TYPE
	ENTERPRISE hh3csLswTRAPMibObject
	VARIABLES { hh3cLswFrameIndex, hh3cLswSlotIndex }
DESCRIPTION "Board request load"
	::= 18


hh3cLoadFailure TRAP-TYPE
	ENTERPRISE hh3csLswTRAPMibObject
	VARIABLES { hh3cLswFrameIndex, hh3cLswSlotIndex }
DESCRIPTION "Board load failure"
	::= 19


hh3cLoadFinished TRAP-TYPE
	ENTERPRISE hh3csLswTRAPMibObject
	VARIABLES { hh3cLswFrameIndex, hh3cLswSlotIndex }
DESCRIPTION "Board load finished"
	::= 20


hh3cBackBoardModeSetFuilure TRAP-TYPE
	ENTERPRISE hh3csLswTRAPMibObject
	VARIABLES { hh3cLswFrameIndex }
DESCRIPTION "Back board mode set failure"
	::= 21


hh3cBackBoardModeSetOK TRAP-TYPE
	ENTERPRISE hh3csLswTRAPMibObject
	VARIABLES { hh3cLswFrameIndex }
DESCRIPTION "Back board mode set OK"
	::= 22


hh3cPowerInserted TRAP-TYPE
	ENTERPRISE hh3csLswTRAPMibObject
	VARIABLES { hh3cDevMPowerNum }
DESCRIPTION "Power inserted"
	::= 23


hh3cBootImageUpdated TRAP-TYPE
	ENTERPRISE hh3csLswTRAPMibObject
	VARIABLES { hh3cLswFrameIndex, hh3cLswSlotIndex }
DESCRIPTION "This trap node indicates that the boot image of specified board
is updated."
	::= 24


END
