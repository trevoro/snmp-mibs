-- ********************************************************************
-- ********************************************************************
-- **      Copyright (c) 1996 Computer Associates International.     **
-- **                                                                **
-- **                                                                **
-- ** Computer Associates Intl. retains the right to change this MIB **
-- ** without notification.                                          **
-- **                                                                **
-- **                                                                **
-- ** Author: Dave Edborg                                            **
-- **                                                                **
-- ** CAIOPSMIB: This MIB defines the traps issued by CA-Security    **
-- **            Products                                            **
-- **                                                                **
-- ********************************************************************
-- ********************************************************************
-- ** Modification Log:                                              **
-- **                                                                **
-- ** MM/DD/YYYY USERID  :                                           **
-- **                                                                **
-- **                                                                **
-- ********************************************************************
-- ********************************************************************

CAISECMIB DEFINITIONS ::= BEGIN

--
-- The below statements import basic types from the relevant
-- definitions.
--

IMPORTS
 enterprises
  FROM RFC1155-SMI
 DisplayString
  FROM RFC1213-MIB
 TRAP-TYPE
  FROM RFC-1215
 OBJECT-TYPE
  FROM RFC-1212;
-- *******************************************************************
-- ** Sun cannot handle imports well - see man pages on mib2schema
-- ** have to define these again
-- *******************************************************************
cai             OBJECT IDENTIFIER ::= { enterprises 791 }
caiSysMgt         OBJECT IDENTIFIER ::= { cai           2 }
caiDbMgt          OBJECT IDENTIFIER ::= { cai           3 }
caiAppSft         OBJECT IDENTIFIER ::= { cai           4 }

-- *******************************************************************
-- **                                                               **
-- ** Start the definition of CAI Security MIB.                     **
-- **                                                               **
-- *******************************************************************
-- *******************************************************************

-- *******************************************************************
-- *******************************************************************
-- **                                                               **
-- ** This level expands 'caiSysMgt' branch.                        **
-- ** FYI->caiSysMgt       OBJECT IDENTIFIER ::= { cai          2 } **
-- **                                                               **
-- *******************************************************************
-- *******************************************************************

caiSecurity  OBJECT IDENTIFIER ::= { caiSysMgt   3 }

-- *******************************************************************
-- *******************************************************************
-- **                                                               **
-- ** This level expands 'caiSecurity branch                        **
-- **                                                               **
-- *******************************************************************
-- *******************************************************************

caiACF2      OBJECT IDENTIFIER ::= { caiSecurity 2 }

caiACF2LstMsg OBJECT-TYPE
 SYNTAX DisplayString (SIZE(0..256))
 ACCESS read-only
 STATUS mandatory
 DESCRIPTION "This object type is used when defining TRAPs to send
              CA-ACF2 messages in a trap.
             "
-- ** The CA-ACF2/MVS TRAP List OID is 1.3.6.1.4.1.791.2.3.2.2       **
 ::= { caiACF2   2 }



-- *******************************************************************
-- *******************************************************************
-- **                                                               **
-- ** Following defines the traps used by CA products.              **
-- ** Traps are defined using the conventions in RFC 1215.          **
-- ** Trap numbers are allocated as follows. If need be, they       **
-- ** can be expanded on an as per need basis.                      **
-- **                                                               **
-- ** 1-999  - Reserved for CA-Unicenter for Unix                   **
-- ** 1000-1099 - Reserved for CA-ACF2/MVS 1.3.6.1.4.1.791.2.3.2    **
-- ** 1100-1199 - Reserved for CA-TSS/MVS  1.3.6.1.4.1.791.2.3.3    **
-- ** 1200-1999 - Reserved for CA-Security 1.3.6.1.4.1.791.2.3      **
-- ** 2000-2099 - Reserved for CA-OPS/MVS  1.3.6.1.4.1.791.2.4      **
-- **                                                               **
-- *******************************************************************
-- *******************************************************************

-- *******************************************************************
-- **  CA-ACF2 Traps
-- **    1000 - Dataset VIO
-- **    1001 - Resource VIO
-- **    1020 - System Entry Violation
-- **    1030 - User suspend
-- *******************************************************************

caiACF2AVT1    TRAP-TYPE
 ENTERPRISE  cai
 VARIABLES { caiACF2LstMsg }
 DESCRIPTION "Reason: A dataset violation occurred
              Msgref: ACF99913
              Values:     Value definition
                LOGINID  - MVS user's 8 character logonID
                JOBNAME  - Jobname under which the violation occurred
                SOURCE   - User's entry source
                SEVERITY - 'VIO' literal
                ACCESS   - 'EXEC', 'READ', 'UPDATE', 'ALLOC' literals
                DSN      - Data set name for which access disallowed.
                           member name if avail in parens. 52 char max.
                VOL      - Volume serial number on which the data set
                           resides
                PROGRAM  - Current program under which the violation
                           occurred
                RMRC     - Return code from CA-ACF2 data set validation
                MAJOR    - Numeric identifier of the CA-ACF2 component
                           through which access is attempted
             "
 ::= 1000


caiACF2AVT2    TRAP-TYPE
 ENTERPRISE  cai
 VARIABLES { caiACF2LstMsg }
 DESCRIPTION "Reason: A resource violation occurred
              Msgref: ACF04056
              Values:     Value definition
                LOGINID  - MVS user's 8 character logonID
                JOBNAME  - Jobname under which the violation occurred
                SOURCE   - User's entry source
                SEVERITY - 'VIO' literal
                ACCESS   - 'EXEC', 'READ', 'UPDATE', 'ALLOC' literals
                RESOURCE - Resource name: if it exceeds 64 characters, it
                           will be truncated: truncation will be indicated
                           by three periods '...', trailing the resource
                           name
                CLASS    - Resource class name
                RMC      - Rule manager return code:  0 == record resident
                                                      4 == record obtained
                                                           from database
                                                      8 == record not found
                INT      - Rule interpreter return code, includes:
                                                     16 == rule prevents
                                                           access
                                                     20 == no rule applies
             "
 ::= 1001


caiACF2PVT1    TRAP-TYPE
 ENTERPRISE  cai
 VARIABLES { caiACF2LstMsg }
 DESCRIPTION "Reason: A password violation occurred
              Msgref: ACF01200
              Values:     Value definition
                LOGINID  - MVS user's 8 character logonID
                JOBNAME  - Jobname under which the violation occurred
                SOURCE   - User's entry source
                TYPE     - 'VIO' for entry violation, 'LOG' for entry
                           logging
                PROGRAM  - Current program under which the violation
                           occurred
                CODE     - Numeric value representing the violation reason:
                           append this value to message ID 'ACF01...' to
                           determine the reason for the violation.  This
                           value will be zero '0' for entry logging.
             "
 ::= 1020


caiACF2USP1    TRAP-TYPE
 ENTERPRISE  cai
 VARIABLES { caiACF2LstMsg }
 DESCRIPTION "Reason: User suspended
              Msgref:
              Values:     Value definition
                LOGINID  - MVS user's 8 character logonID
                JOBNAME  - Jobname under which the violation occurred
                SOURCE   - User's entry source
                TYPE     - 'ENTRY' for entry violations, 'DSN' Dataset VIO,
                           'RES' resource vio, 'ADMIN'  by administrative
                           action.
                PROGRAM  - Current program under which the violation
                           occurred
                CODE     - Numeric value representing the violation reason:
                           append this value to message ID 'ACF01...' to
                           determine the reason for the violation.  This
                           value will be zero '0' for entry logging.
             "
 ::= 1030

-- *******************************************************************
-- **  CA-TSS Traps
-- **    1100 - Volume VIO
-- **    1001 - Data set VIO
-- **    1102 - Resource VIO
-- **    1120 - System Entry Violation
-- **    1130 - User suspended
-- *******************************************************************

caiTSS       OBJECT IDENTIFIER ::= { caiSecurity 3 }

caiTSSLstMsg OBJECT-TYPE
 SYNTAX DisplayString (SIZE(0..256))
 ACCESS read-only
 STATUS mandatory
 DESCRIPTION "This object type is used when defining TRAPs to send
              CA-ACF2 messages in a trap.
             "
-- ** The CA-TSS/MVS TRAP List OID is 1.3.6.1.4.1.791.2.3.2.3        **
 ::= { caiTSS    2 }

caiTSSAVT1    TRAP-TYPE
 ENTERPRISE  cai
 VARIABLES { caiTSSLstMsg }
 DESCRIPTION "Reason: A volume violation occurred
              Msgref: TSS7200E
              Values:     Value definition
                ACID     - MVS user's 8 character accessor ID
                JOBNAME  - Jobname under which the violation occurred
                SOURCE   - User's entry source
                FACILITY -
                SEVERITY - 'VIO' literal
                ACCESS   - 'EXEC', 'READ', 'UPDATE', 'ALLOC' literals
                VOL      - Volume serial number on which the data set
                           resides
                PROGRAM  - Current program under which the violation
                           occurred
                CODES    - ?
             "
 ::= 1100

caiTSSAVT2    TRAP-TYPE
 ENTERPRISE  cai
 VARIABLES { caiTSSLstMsg }
 DESCRIPTION "Reason: A DATASET violation occurred
              Msgref: TSS7220E
                ACID     - MVS user's 8 character accessor ID
                JOBNAME  - Jobname under which the violation occurred
                SOURCE   - User's entry source
                FACILITY -
                SEVERITY - 'VIO' literal
                ACCESS   - 'EXEC', 'READ', 'UPDATE', 'ALLOC' literals
                DSN      - Data set name for which access disallowed.
                           member name if avail in parens. 52 char max.
                PROGRAM  - Current program under which the violation
                           occurred
                CODES    - ?
             "
 ::= 1101


caiTSSAVT3    TRAP-TYPE
 ENTERPRISE  cai
 VARIABLES { caiTSSLstMsg }
 DESCRIPTION "Reason: A RESOURCE violation occurred
              Msgref: TSS7250E
                ACID     - MVS user's 8 character accessor ID
                JOBNAME  - Jobname under which the violation occurred
                SOURCE   - User's entry source
                FACILITY -
                SEVERITY - 'VIO' literal
                ACCESS   - 'EXEC', 'READ', 'UPDATE', 'ALLOC' literals
                RESOURCE - Resource name: if it exceeds 64 characters, it
                           will be truncated: truncation will be indicated
                           by three periods '...', trailing the resource
                           name
                PROGRAM  - Current program under which the violation
                           occurred
                CODES    - ?
             "
-- *******************************************************************
-- * Value format: ACID SEVERITY  ACCESSTYPE 'RESOURCE'
-- *               JOBNAME PROGRAM 'MSG TEXT'
-- *******************************************************************
 ::= 1102

caiTSSPVT1    TRAP-TYPE
 ENTERPRISE  cai
 VARIABLES { caiTSSLstMsg }
 DESCRIPTION "Reason: A password violation occurred
              Action:
              Msgref: TSS7100E
                ACID     - MVS user's 8 character accessor ID
                JOBNAME  - Jobname under which the violation occurred
                SOURCE   - User's entry source
                FACILITY -
                VIOTYPE  - 'VIO/BADPW/UNKN USER' literal ?
                CODES    - ?
             "
-- *******************************************************************
-- * Value format: LOGONID VIOTYPE
-- *******************************************************************
 ::= 1120

caiTSSUSP1    TRAP-TYPE
 ENTERPRISE  cai
 VARIABLES { caiTSSLstMsg }
 DESCRIPTION "Reason: User suspended
              Action:
              Msgref: TSS
                ACID     - MVS user's 8 character accessor ID
                JOBNAME  - Jobname under which the violation occurred
                SOURCE   - User's entry source
                FACILITY -
                VIOTYPE  - 'VIO/BADPW/UNKN USER' literal ?
                CODES    - ?
             "
-- *******************************************************************
-- * Value format: LOGONID
-- *******************************************************************
 ::= 1130

-- **************************************************************
--
-- Trap numbers in the range 30000 to 30999 are reserved for
-- user defined trap numbers.
--
-- **************************************************************

END
