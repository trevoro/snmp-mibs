REDLINE-AN80I-IF-MIB DEFINITIONS ::= BEGIN

IMPORTS
	redlineTransmission
		FROM REDLINE-MIB
	MODULE-IDENTITY,
	OBJECT-TYPE,
	NOTIFICATION-TYPE,
	Unsigned32,
	Counter32,
	Integer32,
	Counter64,
	TimeTicks
		FROM SNMPv2-SMI
	OBJECT-GROUP,
	NOTIFICATION-GROUP,
	MODULE-COMPLIANCE
		FROM SNMPv2-CONF
	DisplayString,
	MacAddress,
	RowStatus 
		FROM SNMPv2-TC;

redlineAn80iIfMib MODULE-IDENTITY
	LAST-UPDATED "200511281543Z"
	ORGANIZATION "Redline Communications Inc."
	CONTACT-INFO
		"Henryk Kijak
		email: hkijak@redlinecommunications.com"
	DESCRIPTION
		"This MIB module contains object definitions
		applicable only to Redline AN80i module."
	REVISION "200511281543Z"
	DESCRIPTION
		"Initial version."
	::= { redlineTransmission 2 }


--
-- Scalars and Tables
--

-- An80iIf PTP variables

redlineAn80iIfPtpObjects OBJECT IDENTIFIER ::= { redlineAn80iIfMib 1 }


-- An80iIf PTP link configuration variables 

redlineAn80iIfPtpLinkConfig OBJECT IDENTIFIER ::= { redlineAn80iIfPtpObjects 1 }


an80iIfEncryptionControl OBJECT-TYPE
	SYNTAX  INTEGER {
			off(1),
			redline(2),
			aes128(3),
			aes192(4),
			aes256(5) }
	MAX-ACCESS read-write
	STATUS current
	DESCRIPTION
		"Specifies if encryption type."
	::= { redlineAn80iIfPtpLinkConfig 1 }

an80iIfModReduction OBJECT-TYPE
	SYNTAX INTEGER (0 .. 7)
	MAX-ACCESS read-write
	STATUS current
	DESCRIPTION
		"Applies when the adaptive rate is disabled, and 
		 specifies how many levels the system must drop in 
		 modulation before beginning retransmission to address 
		 packet errors."
	::= { redlineAn80iIfPtpLinkConfig 2 }

an80iIfAdaptiveMod OBJECT-TYPE
	SYNTAX  INTEGER {
			enabled(1),
			disabled(2) }
	MAX-ACCESS read-write
	STATUS current
	DESCRIPTION
		"If enabled, the system automatically adjust the 
		 modulation to obtain the maximum throughput."
	::= { redlineAn80iIfPtpLinkConfig 3 }

an80iIfUncodedBurstRate OBJECT-TYPE
	SYNTAX INTEGER (0..7)
        UNITS ""
	MAX-ACCESS read-write
	STATUS current
	DESCRIPTION
		"The maximum index of the link uncoded burst rate. 
		The rate also depends on the channel width.
		The possible values are 0..7."
	::= { redlineAn80iIfPtpLinkConfig 4 }

an80iIfEncryptionKey OBJECT-TYPE
	SYNTAX OCTET STRING
	MAX-ACCESS read-write
	STATUS current
	DESCRIPTION
		"The Encryption Key used for the AN-80i.  
		 Enter the MAC address of the peer equipment
		 to enable over-the-air data encryption."
	::= { redlineAn80iIfPtpLinkConfig 5 }

an80iIfPacketRetransControl OBJECT-TYPE
	SYNTAX  INTEGER {
			enabled(1),
			disabled(2) }
	MAX-ACCESS read-write
	STATUS current
	DESCRIPTION
		"Enables/disables packet retransmission. The 
		 retransmission scheme is based on the Acknowledge
		 /Request (ARQ) algorithm that detects when packets 
		 are lost and makes a request to the MAC scheduler 
		 to repeat transmission of the lost packets."
	::= { redlineAn80iIfPtpLinkConfig 6 }

an80iIfLinkLenMode OBJECT-TYPE
	SYNTAX INTEGER { 
			auto(1), 
			manual(2) }
	MAX-ACCESS read-write
	STATUS current
	DESCRIPTION
		"In manual mode the system uses the user-supplied 
		 value for link length. In the auto mode the system 
		 calculate itself the distance, which can be read 
		 using 'calculated distance'."
	::= { redlineAn80iIfPtpLinkConfig 7 }

an80iIfLinkLength OBJECT-TYPE
	SYNTAX Integer32
	UNITS "Km"
	MAX-ACCESS read-write
	STATUS current
	DESCRIPTION
		"User supplied PTP Link Length [Km]."
	::= { redlineAn80iIfPtpLinkConfig 8 }


an80iIfCalcLinkDst OBJECT-TYPE
	SYNTAX Integer32
	UNITS "Km"
	MAX-ACCESS read-only
	STATUS current
	DESCRIPTION
		"The calculated link distance [Km]."
	::= { redlineAn80iIfPtpLinkConfig 9}

an80iIfLinkName OBJECT-TYPE
	SYNTAX DisplayString (SIZE (0..31))
	MAX-ACCESS read-write
	STATUS current
	DESCRIPTION
		"Link Name."
	::= { redlineAn80iIfPtpLinkConfig 10}

-- An80iIf PTP link statistic counters

redlineAn80iIfPtpLinkStats OBJECT IDENTIFIER ::= { redlineAn80iIfPtpObjects 2 }

an80iIfCurrUncodedBurstRate OBJECT-TYPE
	SYNTAX Unsigned32
        UNITS ""
	MAX-ACCESS read-only
	STATUS current
	DESCRIPTION
		"Indicates the index of the link uncoded burst rate.
		 With adaptive modulation enabled, this rate may change 
		 over time."
	::= { redlineAn80iIfPtpLinkStats 1 }

an80iIfPtpLinkStatus OBJECT-TYPE
	SYNTAX  INTEGER {
			up(1),
			down(2) }
	MAX-ACCESS read-only
	STATUS current
	DESCRIPTION
		"Indicates if the link has been established/not established."
	::= { redlineAn80iIfPtpLinkStats 2 }

an80iIfRxPackets OBJECT-TYPE
	SYNTAX Counter64
	MAX-ACCESS read-only
	STATUS current
	DESCRIPTION
		"Indicates the number of received wireless packets 
		 with a correct CRC."
	::= { redlineAn80iIfPtpLinkStats 3 }

an80iIfRxPacketsReTx OBJECT-TYPE
	SYNTAX Counter64
	MAX-ACCESS read-only
	STATUS current
	DESCRIPTION 
		"Indicates the number of received retransmitted 
		 wireless packets with a correct CRC."
	::= { redlineAn80iIfPtpLinkStats 4 }

an80iIfRxPacketsDisc OBJECT-TYPE
	SYNTAX Counter64
	MAX-ACCESS read-only
	STATUS current
	DESCRIPTION
		"Indicates the number of received retransmitted 
		 wireless packets with bad CRC."
	::= { redlineAn80iIfPtpLinkStats 5 }

an80iIfTxPackets OBJECT-TYPE
	SYNTAX Counter64
	MAX-ACCESS read-only
	STATUS current
	DESCRIPTION
		"Indicates the number of transmitted packets that 
		 were received correctly by the other equipment."
	::= { redlineAn80iIfPtpLinkStats 6 }

an80iIfTxPacketsReTx OBJECT-TYPE
	SYNTAX Counter64
	MAX-ACCESS read-only
	STATUS current
	DESCRIPTION 
		"Indicates the number of retransmitted wireless 
		 packets received correctly by the other equipment."
	::= { redlineAn80iIfPtpLinkStats 7 }

an80iIfTxPacketsDisc OBJECT-TYPE
	SYNTAX Counter64
	MAX-ACCESS read-only
	STATUS current
	DESCRIPTION
		"Indicates the number of retransmitted wireless 
		 packets that were not received correctly by the 
		 other equipment"
	::= { redlineAn80iIfPtpLinkStats 8 }

an80iIfRssiMin OBJECT-TYPE
	SYNTAX Integer32
	MAX-ACCESS read-only
	STATUS current
	DESCRIPTION
		"Indicates the minimum received signal strength for the 
		 measuring interval."
	::= { redlineAn80iIfPtpLinkStats 9 }

an80iIfRssiMean OBJECT-TYPE
	SYNTAX Integer32
	MAX-ACCESS read-only
	STATUS current
	DESCRIPTION
		"Indicates the average received signal strength for the 
		 measuring interval."
	::= { redlineAn80iIfPtpLinkStats 10 }

an80iIfRssiMax OBJECT-TYPE
	SYNTAX Integer32
	MAX-ACCESS read-only
	STATUS current
	DESCRIPTION
		"Indicates the maximum received signal strength for the 
		 measuring interval."
	::= { redlineAn80iIfPtpLinkStats 11 }

an80iIfAvrSinAdr OBJECT-TYPE
	SYNTAX Integer32
	MAX-ACCESS read-only
	STATUS current
	DESCRIPTION
		"Indicates the Signal to interference, noise and 
		 distortion ratio."
	::= { redlineAn80iIfPtpLinkStats 12 }

-- An80iIf PMP variables

redlineAn80iIfPmpObjects OBJECT IDENTIFIER ::= { redlineAn80iIfMib 2 }


-- An80iIf PMP Ss variables

redlineAn80iIfPmpSsObjects OBJECT IDENTIFIER ::= { redlineAn80iIfPmpObjects 1 }

an80iIfLastMissedMacAddress OBJECT-TYPE
	SYNTAX MacAddress
	MAX-ACCESS read-only
	STATUS current
	DESCRIPTION
		"MAC address for the last SS that attempted to register 
		 but it was not present in the 'Links' table"
	::= { redlineAn80iIfPmpSsObjects 1 }

an80iIfLastRegistMacAddress OBJECT-TYPE
	SYNTAX MacAddress
	MAX-ACCESS read-only
	STATUS current
	DESCRIPTION
		"MAC address for the last SS that successfuly registered" 
	::= { redlineAn80iIfPmpSsObjects 2 }

an80iIfDenyMacAddress OBJECT-TYPE
	SYNTAX MacAddress
	MAX-ACCESS read-write
	STATUS current
	DESCRIPTION
		"MAC address for the SS that will be denied by this SC"
	::= { redlineAn80iIfPmpSsObjects 3 }

an80iIfLastRegistLinkId OBJECT-TYPE
	SYNTAX INTEGER(0..1023)
	MAX-ACCESS read-only
	STATUS current
	DESCRIPTION
		"The link ID for the last SS that successfully registered" 
	::= { redlineAn80iIfPmpSsObjects 4 }


-- An80iIf PMP Link Configuration Table

an80iIfPmpLinkConfigTable OBJECT-TYPE
	SYNTAX      SEQUENCE OF An80iIfPmpLinkConfigEntry
	MAX-ACCESS  not-accessible
	STATUS      current
	DESCRIPTION
		"This table contains the PMP link configuration information."
	::= { redlineAn80iIfPmpObjects 2 }

an80iIfPmpLinkConfigEntry OBJECT-TYPE
	SYNTAX      An80iIfPmpLinkConfigEntry
	MAX-ACCESS  not-accessible
	STATUS      current
	DESCRIPTION
		"This table provides one row for each PMP link that has been
		 configured in the SC."
	INDEX { an80iIfPmpLinkId }
	::= { an80iIfPmpLinkConfigTable 1 }

An80iIfPmpLinkConfigEntry ::= SEQUENCE {  
	an80iIfPmpLinkId INTEGER,
	an80iIfPmpLinkName DisplayString,
	an80iIfPmpLinkPeerMacAddress MacAddress,
	an80iIfPmpLinkULBurstRate Unsigned32,
	an80iIfPmpLinkDLBurstRate Unsigned32,
	an80iIfPmpLinkConfigStatus RowStatus
}

an80iIfPmpLinkId OBJECT-TYPE
	SYNTAX INTEGER(4..1023)
	MAX-ACCESS not-accessible
	STATUS current
	DESCRIPTION
		"The PMP Link Identifier."
	::= { an80iIfPmpLinkConfigEntry 1 }

an80iIfPmpLinkName OBJECT-TYPE
	SYNTAX DisplayString (SIZE (0..15))
	MAX-ACCESS read-create
	STATUS current
	DESCRIPTION
		"The PMP Link Name."
	::= { an80iIfPmpLinkConfigEntry 2 }

an80iIfPmpLinkPeerMacAddress OBJECT-TYPE
	SYNTAX MacAddress
	MAX-ACCESS read-create
	STATUS current
	DESCRIPTION
		"The MAC address for the peer SS"
	::= { an80iIfPmpLinkConfigEntry 3 }

an80iIfPmpLinkULBurstRate OBJECT-TYPE
	SYNTAX Unsigned32
        UNITS ""
	MAX-ACCESS read-create
	STATUS current
	DESCRIPTION
		"User supplied index of the uplink uncoded burst rate."
	::= { an80iIfPmpLinkConfigEntry 4 }

an80iIfPmpLinkDLBurstRate OBJECT-TYPE
	SYNTAX Unsigned32
        UNITS ""
	MAX-ACCESS read-create
	STATUS current
	DESCRIPTION
		"User supplied index of the downlink uncoded burst rate."
	::= { an80iIfPmpLinkConfigEntry 5 }

an80iIfPmpLinkConfigStatus OBJECT-TYPE
        SYNTAX          RowStatus
        MAX-ACCESS      read-create
        STATUS          current
        DESCRIPTION
            "This object is used to create a new row or modify or
             delete an existing row in this table."
        ::= { an80iIfPmpLinkConfigEntry 6 }

-- An80iIf PMP Link Statistics Table

an80iIfPmpLinkStatsTable OBJECT-TYPE
	SYNTAX      SEQUENCE OF An80iIfPmpLinkStatsEntry
	MAX-ACCESS  not-accessible
	STATUS      current
	DESCRIPTION
		"This table contains the PMP link statistics information."
	::= { redlineAn80iIfPmpObjects 3 }

an80iIfPmpLinkStatsEntry OBJECT-TYPE
	SYNTAX      An80iIfPmpLinkStatsEntry
	MAX-ACCESS  not-accessible
	STATUS      current
	DESCRIPTION
		"This table provides one row for each PMP link that has been
		 configured in the Service Controller."
	INDEX { an80iIfPmpLinkId }
	::= { an80iIfPmpLinkStatsTable 1 }

An80iIfPmpLinkStatsEntry ::= SEQUENCE {  
	an80iIfPmpLinkStatus INTEGER,
	an80iIfPmpLinkStatusCode Integer32,
	an80iIfRegPmpLinkConns Integer32,
	an80iIfPmpLinkLostCount Counter32,
	an80iIfPmpLinkUpTime TimeTicks,
	an80iIfPmpLinkCurrDLUncBurstRate Unsigned32,
	an80iIfPmpLinkDLRssi Integer32,
	an80iIfPmpLinkDLSinAdr Integer32,
	an80iIfPmpLinkDLLostFrm Counter64,
	an80iIfPmpLinkDLBlksTot Counter64,
	an80iIfPmpLinkDLBlksRetr Counter64,
	an80iIfPmpLinkDLBlksDisc Counter64,
	an80iIfPmpLinkCurrULUncBurstRate Unsigned32,
	an80iIfPmpLinkULRssi Integer32,
	an80iIfPmpLinkULSinAdr Integer32,
	an80iIfPmpLinkULLostFrm Counter64,
	an80iIfPmpLinkULBlksTot Counter64,
	an80iIfPmpLinkULBlksRetr Counter64,
	an80iIfPmpLinkULBlksDisc Counter64,
	an80iIfPmpLinkStatsStatus RowStatus
}

an80iIfPmpLinkStatus OBJECT-TYPE
	SYNTAX  INTEGER {
			up(1),
			down(2) }
	MAX-ACCESS read-only
	STATUS current
	DESCRIPTION
		"Indicates if the link has been established/not established."
	::= { an80iIfPmpLinkStatsEntry 1 }

an80iIfPmpLinkStatusCode OBJECT-TYPE
	SYNTAX  Integer32
	MAX-ACCESS read-only
	STATUS current
	DESCRIPTION
		"Indicates the error code for the link."
	::= { an80iIfPmpLinkStatsEntry 2 }

an80iIfRegPmpLinkConns OBJECT-TYPE
	SYNTAX  Integer32
	MAX-ACCESS read-only
	STATUS current
	DESCRIPTION
		"Indicates the registered connections for this Link."
	::= { an80iIfPmpLinkStatsEntry 3 }

an80iIfPmpLinkUpTime OBJECT-TYPE
	SYNTAX  TimeTicks
	MAX-ACCESS read-only
	STATUS current
	DESCRIPTION
		"The time (in hundredths of a second) elapsed since 
		 the link was established (up) last time."
	::= { an80iIfPmpLinkStatsEntry 4 }

an80iIfPmpLinkLostCount OBJECT-TYPE
	SYNTAX Counter32
	MAX-ACCESS read-only 
	STATUS current
	DESCRIPTION
		"Number of times the link has been lost since the 
		 system started."
	::= { an80iIfPmpLinkStatsEntry 5 }

an80iIfPmpLinkCurrDLUncBurstRate OBJECT-TYPE
	SYNTAX Unsigned32
        UNITS ""
	MAX-ACCESS read-only
	STATUS current
	DESCRIPTION
		"Indicates the index of the link's downlink actual uncoded burst 
		 rate."
	::= { an80iIfPmpLinkStatsEntry 6 }

an80iIfPmpLinkDLRssi OBJECT-TYPE
	SYNTAX Integer32
	MAX-ACCESS read-only
	STATUS current
	DESCRIPTION
		"Indicates the link's DL RSSI (Received Signal Strength 
		 Indicator)."
	::= { an80iIfPmpLinkStatsEntry 7 }

an80iIfPmpLinkDLSinAdr OBJECT-TYPE
	SYNTAX Integer32
	MAX-ACCESS read-only
	STATUS current
	DESCRIPTION
		"Indicates the link's DL SINADR (Signal Interference 
		 and Noise Distorsion Ratio)."
	::= { an80iIfPmpLinkStatsEntry 8 }

an80iIfPmpLinkDLLostFrm OBJECT-TYPE
	SYNTAX Counter64
	MAX-ACCESS read-only
	STATUS current
	DESCRIPTION
		"Indicates the link's DL lost frames."
	::= { an80iIfPmpLinkStatsEntry 9 }

an80iIfPmpLinkDLBlksTot OBJECT-TYPE
	SYNTAX Counter64
	MAX-ACCESS read-only
	STATUS current
	DESCRIPTION
		"Indicates the link's DL blocks transmitted."
	::= { an80iIfPmpLinkStatsEntry 10 }

an80iIfPmpLinkDLBlksRetr OBJECT-TYPE
	SYNTAX Counter64
	MAX-ACCESS read-only
	STATUS current
	DESCRIPTION
		"Indicates the link's DL block re-transmitted."
	::= { an80iIfPmpLinkStatsEntry 11 }

an80iIfPmpLinkDLBlksDisc OBJECT-TYPE
	SYNTAX Counter64
	MAX-ACCESS read-only
	STATUS current
	DESCRIPTION
		"Indicates the link's DL blocks lost"
	::= { an80iIfPmpLinkStatsEntry 12 }

an80iIfPmpLinkCurrULUncBurstRate OBJECT-TYPE
	SYNTAX Unsigned32
        UNITS "Mb/s"
	MAX-ACCESS read-only
	STATUS current
	DESCRIPTION
		"Indicates the index of the link's uplink actual uncoded burst 
		 rate."
	::= { an80iIfPmpLinkStatsEntry 13 }

an80iIfPmpLinkULRssi OBJECT-TYPE
	SYNTAX Integer32
	MAX-ACCESS read-only
	STATUS current
	DESCRIPTION
		"Indicates the link's UL RSSI (Received Signal Strength 
		 Indicator)."
	::= { an80iIfPmpLinkStatsEntry 14 }

an80iIfPmpLinkULSinAdr OBJECT-TYPE
	SYNTAX Integer32
	MAX-ACCESS read-only
	STATUS current
	DESCRIPTION
		"Indicates the link's UL SINADR (Signal Interference 
		 and Noise Distorsion Ratio)."
	::= { an80iIfPmpLinkStatsEntry 15 }

an80iIfPmpLinkULLostFrm OBJECT-TYPE
	SYNTAX Counter64
	MAX-ACCESS read-only
	STATUS current
	DESCRIPTION
		"Indicates the link's UL lost frames."
	::= { an80iIfPmpLinkStatsEntry 16 }

an80iIfPmpLinkULBlksTot OBJECT-TYPE
	SYNTAX Counter64
	MAX-ACCESS read-only
	STATUS current
	DESCRIPTION
		"Indicates the link's UL blocks transmitted."
	::= { an80iIfPmpLinkStatsEntry 17 }

an80iIfPmpLinkULBlksRetr OBJECT-TYPE
	SYNTAX Counter64
	MAX-ACCESS read-only
	STATUS current
	DESCRIPTION
		"Indicates the link's UL block re-transmitted."
	::= { an80iIfPmpLinkStatsEntry 18 }

an80iIfPmpLinkULBlksDisc OBJECT-TYPE
	SYNTAX Counter64
	MAX-ACCESS read-only
	STATUS current
	DESCRIPTION
		"Indicates the link's UL blocks lost"
	::= { an80iIfPmpLinkStatsEntry 19 }

an80iIfPmpLinkStatsStatus OBJECT-TYPE
        SYNTAX          RowStatus
        MAX-ACCESS      read-only
        STATUS          current
        DESCRIPTION
            "This object is used to create a new row or modify or
             delete an existing row in this table."
        ::= { an80iIfPmpLinkStatsEntry 20 }

-- An80iIf PMP Group Configuration Table

an80iIfPmpGroupConfigTable OBJECT-TYPE
	SYNTAX      SEQUENCE OF An80iIfPmpGroupConfigEntry
	MAX-ACCESS  not-accessible
	STATUS      current
	DESCRIPTION
		"This table contains group configuration information. 
		 The group defined as a broadcast domain."
	::= { redlineAn80iIfPmpObjects 4 }

an80iIfPmpGroupConfigEntry OBJECT-TYPE
	SYNTAX      An80iIfPmpGroupConfigEntry
	MAX-ACCESS  not-accessible
	STATUS      current
	DESCRIPTION
		"This table provides one row for each group defined in 
		 the Service Controller"
	INDEX { an80iIfPmpGroupId }
	::= { an80iIfPmpGroupConfigTable 1 }

An80iIfPmpGroupConfigEntry ::= SEQUENCE {  
	an80iIfPmpGroupId INTEGER,
	an80iIfPmpGroupName DisplayString,
	an80iIfPmpGroupTaggingControl INTEGER,
	an80iIfPmpGroupVlanId INTEGER,
	an80iIfPmpGroupDefPriority INTEGER,
	an80iIfPmpGroupSCEtherControl INTEGER,
	an80iIfPmpGroupQosLevel INTEGER,
	an80iIfPmpGroupRate INTEGER,
	an80iIfPmpGroupSStoSSMulticast INTEGER,
	an80iIfPmpGroupConfigStatus RowStatus
}

an80iIfPmpGroupId OBJECT-TYPE
	SYNTAX INTEGER(4..1023)
	MAX-ACCESS not-accessible
	STATUS current
	DESCRIPTION
		"The PMP Group Identifier."
	::= { an80iIfPmpGroupConfigEntry 1 }

an80iIfPmpGroupName OBJECT-TYPE
	SYNTAX DisplayString (SIZE (0..15))
	MAX-ACCESS read-create
	STATUS current
	DESCRIPTION
		"The PMP Group Name."
	::= { an80iIfPmpGroupConfigEntry 2 }

an80iIfPmpGroupTaggingControl OBJECT-TYPE
	SYNTAX  INTEGER {
			passThrough(1),
			tagged(2) }
	MAX-ACCESS read-create
	STATUS current
	DESCRIPTION
		"Specifies tagging mode.Only one pass-through group 
		 can exist. This is the default group. In the 
		 pass-through mode all the Ethernet packets that do 
		 not have a VLAN tag or an undefined VID will be 
		 classified in this group."
	::= { an80iIfPmpGroupConfigEntry 3 }

an80iIfPmpGroupVlanId OBJECT-TYPE
	SYNTAX INTEGER(0..4095)
	MAX-ACCESS read-create
	STATUS current
	DESCRIPTION
		"In the tagged mode all Ethernet packets that have this 
		 VID will be classified to belong to this group."
	::= { an80iIfPmpGroupConfigEntry 4 }

an80iIfPmpGroupDefPriority OBJECT-TYPE
	SYNTAX INTEGER(0..7)
	MAX-ACCESS read-create
	STATUS current
	DESCRIPTION
		"This field is used every time a tag is added at the 
		 exit point. The priority will be the one specified 
		 at the entry point."
	::= { an80iIfPmpGroupConfigEntry 5 }

an80iIfPmpGroupSCEtherControl OBJECT-TYPE
	SYNTAX  INTEGER {
			enable(1),
			disable(2) }
	MAX-ACCESS read-create
	STATUS current
	DESCRIPTION
		"Makes the Sector Controller a member of the group."
	::= { an80iIfPmpGroupConfigEntry 6 }

an80iIfPmpGroupQosLevel OBJECT-TYPE
	SYNTAX INTEGER(0..53)
	MAX-ACCESS read-create
	STATUS current
	DESCRIPTION
		"QoS level (index) that will affect the bandwidth 
		 and the delay for this group."
	::= { an80iIfPmpGroupConfigEntry 7 }

an80iIfPmpGroupConfigStatus OBJECT-TYPE
        SYNTAX          RowStatus
        MAX-ACCESS      read-create
        STATUS          current
        DESCRIPTION
            "This object is used to create a new row or modify or
             delete an existing row in this table."
        ::= { an80iIfPmpGroupConfigEntry 8 }

an80iIfPmpGroupRate OBJECT-TYPE
	SYNTAX INTEGER (0..8)
        UNITS ""
	MAX-ACCESS read-create
	STATUS current
	DESCRIPTION
		"Define the index of the group rate. (0..7, 8=auto)"
	::= { an80iIfPmpGroupConfigEntry 9 }

an80iIfPmpGroupSStoSSMulticast OBJECT-TYPE
	SYNTAX INTEGER {
			enable(1),
			disable(2) }
        UNITS ""
	MAX-ACCESS read-create
	STATUS current
	DESCRIPTION
		"Enable the Subscriber to subscriber multicast
		traffic."
	::= { an80iIfPmpGroupConfigEntry 10 }


-- An80iIf PMP Group Statistics Table

an80iIfPmpGroupStatsTable OBJECT-TYPE
	SYNTAX      SEQUENCE OF An80iIfPmpGroupStatsEntry
	MAX-ACCESS  not-accessible
	STATUS      current
	DESCRIPTION
		"This table contains group statistics information. 
		 The group defined as a broadcast domain."
	::= { redlineAn80iIfPmpObjects 5 }

an80iIfPmpGroupStatsEntry OBJECT-TYPE
	SYNTAX		An80iIfPmpGroupStatsEntry
	MAX-ACCESS  	not-accessible
	STATUS      	current
	DESCRIPTION
		"This table provides one row for each group defined in 
		 the Service Controller"
	INDEX { an80iIfPmpGroupId }
	::= { an80iIfPmpGroupStatsTable 1 }

An80iIfPmpGroupStatsEntry ::= SEQUENCE {
	an80iIfPmpGroupPacketsTx Counter64,
	an80iIfPmpGroupPacketDisc Counter64 ,
	an80iIfPmpGroupStatsStatus RowStatus
}	

an80iIfPmpGroupPacketsTx OBJECT-TYPE
	SYNTAX		Counter64
	MAX-ACCESS 	read-only
	STATUS 		current
	DESCRIPTION
		"Broadcast/multicast Ethernet packets classified 
		 and transmitted to the group."
	::= { an80iIfPmpGroupStatsEntry 1 }

an80iIfPmpGroupPacketDisc OBJECT-TYPE
	SYNTAX		Counter64
	MAX-ACCESS 	read-only
	STATUS 		current
	DESCRIPTION
		"Ethernet packets classified to be sent to the 
		 group but discarded due to unavailable memory."
	::= { an80iIfPmpGroupStatsEntry 2 }

an80iIfPmpGroupStatsStatus OBJECT-TYPE
        SYNTAX          RowStatus
        MAX-ACCESS      read-only
        STATUS          current
        DESCRIPTION
            "This object is used to create a new row or modify or
             delete an existing row in this table."
        ::= { an80iIfPmpGroupStatsEntry 3 }

-- An80iIf PMP Connections Configuration Table

an80iIfPmpConnConfigTable OBJECT-TYPE
	SYNTAX      SEQUENCE OF An80iIfPmpConnConfigEntry
	MAX-ACCESS  not-accessible
	STATUS      current
	DESCRIPTION
		"This table contains connections configuration information. 
		 One connection defines the transport parameter for 
		 Ethernet packets that have specific properties."
	::= { redlineAn80iIfPmpObjects 6 }

an80iIfPmpConnConfigEntry OBJECT-TYPE
	SYNTAX      An80iIfPmpConnConfigEntry
	MAX-ACCESS  not-accessible
	STATUS      current
	DESCRIPTION
		"This table provides one row for each connection defined in 
		 the Service Controller"
	INDEX { an80iIfPmpConnId }
	::= { an80iIfPmpConnConfigTable 1 }

An80iIfPmpConnConfigEntry ::= SEQUENCE {  
	an80iIfPmpConnId INTEGER,
	an80iIfPmpConnName DisplayString,
	an80iIfPmpConnTaggingControl INTEGER,
	an80iIfPmpConnVlanId INTEGER,
	an80iIfPmpConnDefPriority INTEGER,
	an80iIfPmpConnDefParentLink INTEGER,
	an80iIfPmpConnDefParenGroup INTEGER,
	an80iIfPmpConnDLQos INTEGER,
	an80iIfPmpConnULQos INTEGER,
	an80iIfPmpConnConfigStatus RowStatus
}

an80iIfPmpConnId OBJECT-TYPE
	SYNTAX INTEGER(4..1023)
	MAX-ACCESS not-accessible
	STATUS current
	DESCRIPTION
		"The PMP Conn Identifier."
	::= { an80iIfPmpConnConfigEntry 1 }

an80iIfPmpConnName OBJECT-TYPE
	SYNTAX DisplayString (SIZE (0..15))
	MAX-ACCESS read-create
	STATUS current
	DESCRIPTION
		"The PMP Conn Name."
	::= { an80iIfPmpConnConfigEntry 2 }

an80iIfPmpConnTaggingControl OBJECT-TYPE
	SYNTAX  INTEGER {
			passThrough(1),
			tagged(2) }
	MAX-ACCESS read-create
	STATUS current
	DESCRIPTION
		"Specifies tagging mode. Only one pass-through connection 
		 can be defined on each link. This is the default connection. 
		 All the untagged packets or with a VID that is not defined 
		 will be transmitted on this connection."
	::= { an80iIfPmpConnConfigEntry 3 }

an80iIfPmpConnVlanId OBJECT-TYPE
	SYNTAX INTEGER(0..4095)
	MAX-ACCESS read-create
	STATUS current
	DESCRIPTION
		"Specifies VLAN Id for the tagged mode."
	::= { an80iIfPmpConnConfigEntry 4 }

an80iIfPmpConnDefPriority OBJECT-TYPE
	SYNTAX INTEGER(0..7)
	MAX-ACCESS read-create
	STATUS current
	DESCRIPTION
		"This field is used every time a tag is added at the 
		 exit point. The priority will be the one specified 
		 at the entry point."
	::= { an80iIfPmpConnConfigEntry 5 }

an80iIfPmpConnDefParentLink OBJECT-TYPE
	SYNTAX INTEGER(4..1023)
	MAX-ACCESS read-create
	STATUS current
	DESCRIPTION
		"This object specifies the parent link of the connection."
	::= { an80iIfPmpConnConfigEntry 6 }

an80iIfPmpConnDefParenGroup OBJECT-TYPE
	SYNTAX INTEGER(4..1023)
	MAX-ACCESS read-create
	STATUS current
	DESCRIPTION
		"This object specifies the parent group of the connection."
	::= { an80iIfPmpConnConfigEntry 7 }

an80iIfPmpConnDLQos OBJECT-TYPE
	SYNTAX INTEGER(0..53)
	MAX-ACCESS read-create
	STATUS current
	DESCRIPTION
		"Connection QoS level (index) that will affect the DL 
                 bandwidth and the delay."
	::= { an80iIfPmpConnConfigEntry 8 }

an80iIfPmpConnULQos OBJECT-TYPE
	SYNTAX INTEGER(0..53)
	MAX-ACCESS read-create
	STATUS current
	DESCRIPTION
		"Connection QoS level (index) that will affect the UL 
                 bandwidth and the delay."
	::= { an80iIfPmpConnConfigEntry 9 }

an80iIfPmpConnConfigStatus OBJECT-TYPE
        SYNTAX          RowStatus
        MAX-ACCESS      read-create
        STATUS          current
        DESCRIPTION
            "This object is used to create a new row or modify or
             delete an existing row in this table."
        ::= { an80iIfPmpConnConfigEntry 10 }

-- An80iIf PMP Connections Statistics Table

an80iIfPmpConnStatsTable OBJECT-TYPE
	SYNTAX      SEQUENCE OF An80iIfPmpConnStatsEntry
	MAX-ACCESS  not-accessible
	STATUS      current
	DESCRIPTION
		"This table contains connections configuration information.
		 One connection defines the transport parameter for 
		 Ethernet packets that have specific properties."
	::= { redlineAn80iIfPmpObjects 7 }

an80iIfPmpConnStatsEntry OBJECT-TYPE
	SYNTAX      An80iIfPmpConnStatsEntry
	MAX-ACCESS  not-accessible
	STATUS      current
	DESCRIPTION
		"This table provides one row for each connection defined in 
		 the Service Controller"
	INDEX { an80iIfPmpConnId }
	::= { an80iIfPmpConnStatsTable 1 }

An80iIfPmpConnStatsEntry ::= SEQUENCE {
	an80iIfPmpConnDLPacketsTx Counter64,
	an80iIfPmpConnDLPacketsRx Counter64,
	an80iIfPmpConnDLPacketsDisc Counter64,
	an80iIfPmpConnULPacketsTx Counter64,
	an80iIfPmpConnULPacketsRx Counter64,
	an80iIfPmpConnULPacketsDisc Counter64,
	an80iIfPmpConnStatsStatus RowStatus
}

an80iIfPmpConnDLPacketsTx OBJECT-TYPE
	SYNTAX Counter64
	MAX-ACCESS read-only
	STATUS current
	DESCRIPTION
		"Indicates Ethernet packets sent by SC."
	::= { an80iIfPmpConnStatsEntry 1 }

an80iIfPmpConnDLPacketsRx OBJECT-TYPE
	SYNTAX Counter64
	MAX-ACCESS read-only
	STATUS current
	DESCRIPTION
		"Indicates Ethernet packets receivedby SS."
	::= { an80iIfPmpConnStatsEntry 2 }

an80iIfPmpConnDLPacketsDisc OBJECT-TYPE
	SYNTAX Counter64
	MAX-ACCESS read-only
	STATUS current
	DESCRIPTION
		"Indicates packets discarded due to full buffer."
	::= { an80iIfPmpConnStatsEntry 3 }


an80iIfPmpConnULPacketsTx OBJECT-TYPE
	SYNTAX Counter64
	MAX-ACCESS read-only
	STATUS current
	DESCRIPTION
		"Indicates Ethernet packets sent by SS."
	::= { an80iIfPmpConnStatsEntry 4 }

an80iIfPmpConnULPacketsRx OBJECT-TYPE
	SYNTAX Counter64
	MAX-ACCESS read-only
	STATUS current
	DESCRIPTION
		"Indicates Ethernet packets received SC."
	::= { an80iIfPmpConnStatsEntry 5 }

an80iIfPmpConnULPacketsDisc OBJECT-TYPE
	SYNTAX Counter64
	MAX-ACCESS read-only
	STATUS current
	DESCRIPTION
		"Indicates packets discarded due to full buffer."
	::= { an80iIfPmpConnStatsEntry 6 }

an80iIfPmpConnStatsStatus OBJECT-TYPE
        SYNTAX          RowStatus
        MAX-ACCESS      read-only
        STATUS          current
        DESCRIPTION
            "This object is used to create a new row or modify or
             delete an existing row in this table."
        ::= { an80iIfPmpConnStatsEntry 7 }

-- AN80iIf trap definitions 

redlineAn80iIfTrapDefinitions OBJECT IDENTIFIER ::= { redlineAn80iIfMib 0 }


an80iIfRegistrationFailedTrap NOTIFICATION-TYPE
	OBJECTS {
		an80iIfLastMissedMacAddress }
	STATUS current
	DESCRIPTION 
		"Event that reports the failure of a registration attempt 
		 of a SS that is not defined in the link table."
	::= { redlineAn80iIfTrapDefinitions 1 }

an80iIfRegistrationOKTrap NOTIFICATION-TYPE
	OBJECTS {
		an80iIfLastRegistMacAddress }
	STATUS current
	DESCRIPTION 
		"An event to report the successful SS registration."
	::= { redlineAn80iIfTrapDefinitions 2 }

--
-- Conformance
--

redlineAn80iIfConformance OBJECT IDENTIFIER ::= { redlineAn80iIfMib 4 }

--
-- Groups
--

redlineAn80iIfGroups OBJECT IDENTIFIER ::= { redlineAn80iIfConformance 1 }

--
-- Compliance
--

redlineAn80iIfCompls OBJECT IDENTIFIER ::= { redlineAn80iIfConformance 2 }

redlineAn80iIfPtpGroup OBJECT-GROUP
	OBJECTS {
		an80iIfEncryptionControl,
		an80iIfModReduction,
		an80iIfAdaptiveMod,
		an80iIfUncodedBurstRate,
		an80iIfEncryptionKey,
		an80iIfPacketRetransControl,
		an80iIfLinkLenMode,
		an80iIfLinkLength,
		an80iIfCurrUncodedBurstRate,
		an80iIfPtpLinkStatus,
		an80iIfRxPackets,
		an80iIfRxPacketsReTx,
		an80iIfRxPacketsDisc,
		an80iIfTxPackets,
		an80iIfTxPacketsReTx,
		an80iIfTxPacketsDisc,
		an80iIfRssiMin,
		an80iIfRssiMean,
		an80iIfRssiMax,
		an80iIfAvrSinAdr,
		an80iIfCalcLinkDst,
		an80iIfLinkName }
	STATUS current
	DESCRIPTION
		"Point to point link objects."
	::= { redlineAn80iIfGroups 1 }


redlineAn80iIfPmpGroup OBJECT-GROUP
	OBJECTS {
		an80iIfLastMissedMacAddress,
		an80iIfLastRegistMacAddress,
		an80iIfDenyMacAddress,
		an80iIfLastRegistLinkId,
		an80iIfPmpLinkName,
		an80iIfPmpLinkPeerMacAddress,
		an80iIfPmpLinkULBurstRate,
		an80iIfPmpLinkDLBurstRate,
		an80iIfPmpLinkStatus,
		an80iIfPmpLinkStatusCode,
		an80iIfRegPmpLinkConns,
		an80iIfPmpLinkLostCount,
		an80iIfPmpLinkUpTime,
		an80iIfPmpLinkLostCount,
		an80iIfPmpLinkCurrDLUncBurstRate,
		an80iIfPmpLinkLostCount,
		an80iIfPmpLinkDLSinAdr,
		an80iIfPmpLinkDLLostFrm,
		an80iIfPmpLinkDLBlksTot,
		an80iIfPmpLinkDLBlksRetr,
		an80iIfPmpLinkDLBlksDisc,
		an80iIfPmpLinkCurrULUncBurstRate,
		an80iIfPmpLinkULRssi,
		an80iIfPmpLinkULSinAdr,
		an80iIfPmpLinkULLostFrm,
		an80iIfPmpLinkULBlksTot,
		an80iIfPmpLinkULBlksRetr,
		an80iIfPmpLinkULBlksDisc,
		an80iIfPmpGroupName,
		an80iIfPmpGroupTaggingControl,
		an80iIfPmpGroupVlanId,
		an80iIfPmpGroupDefPriority,
		an80iIfPmpGroupSCEtherControl,
		an80iIfPmpGroupQosLevel,
		an80iIfPmpGroupPacketsTx,
		an80iIfPmpGroupPacketDisc,
		an80iIfPmpConnName,
		an80iIfPmpConnTaggingControl,
		an80iIfPmpConnVlanId,
		an80iIfPmpConnDefPriority,
		an80iIfPmpConnDefParentLink,
		an80iIfPmpConnDefParenGroup,
		an80iIfPmpConnDLQos,
		an80iIfPmpConnULQos,
		an80iIfPmpConnDLPacketsTx,
		an80iIfPmpConnDLPacketsRx,
		an80iIfPmpConnDLPacketsDisc,
		an80iIfPmpConnULPacketsTx,
		an80iIfPmpConnULPacketsRx,
		an80iIfPmpConnULPacketsDisc
 }
	STATUS current
	DESCRIPTION
		"Point to multipoint link objects."
	::= { redlineAn80iIfGroups 2 }

redlineAn80iIfNotificationGroup NOTIFICATION-GROUP
	NOTIFICATIONS {
		an80iIfRegistrationFailedTrap,
		an80iIfRegistrationOKTrap
}
	STATUS current
	DESCRIPTION
		"The notifications which indicate specific events
		 within the AN80i interface."
	::= { redlineAn80iIfGroups 3 }

redlineAn80iIfCompliance MODULE-COMPLIANCE
	STATUS current
	DESCRIPTION
		"The compliance statement for SNMP entities that
		implement this MIB module."

	MODULE 
	MANDATORY-GROUPS {
			redlineAn80iIfPtpGroup,
                        redlineAn80iIfPmpGroup,
			redlineAn80iIfNotificationGroup 
}
	::= { redlineAn80iIfCompls 1 }

END
