CXMLPPP-IP-NCP-MIB DEFINITIONS ::= BEGIN


IMPORTS
	OBJECT-TYPE		FROM RFC-1212
	cxMLPPP,SapIndex	FROM CXProduct-SMI;

--  Internet Protocol Network Control Protocol Status table
--  
--  This table will be automatically created when a lower service access point will be created.

--  The table describing:
--  	status available for monitoring the current state of the IPNCP associated to a lower service 
--	access point
--
-- The following objects reflect the values of the option parameters used in the PPP IP Network 
-- Control Protocol
--   mlpppIpNsLocalToRemoteCompressionProtocol
--   mlpppIpNsRemoteToLocalCompressionProtocol
--   mlpppIpNsRemoteMaxSlotId
--   mlpppIpNsLocalMaxSlotId
--
-- These values are not available until after the PPP Option
-- negotiation has completed, which is indicated by the link
-- reaching the open state (i.e., virtNetIfStatus is set to
-- opened).
--
-- Therefore, when virtNetIfStatus is not opened
-- the contents of these objects is undefined. The value
-- returned when accessing the objects is an implementation
-- dependent issue.

mlpppIpNsTable			OBJECT-TYPE
		SYNTAX	SEQUENCE OF MlpppIpNsEntry
		ACCESS	not-accessible
		STATUS	mandatory
		DESCRIPTION
"A table containing status parameters about each MLPPP  module layer PPP 
IP Network Control Protocol."
		::= { cxMLPPP 52 }


mlpppIpNsEntry			OBJECT-TYPE
		SYNTAX	MlpppIpNsEntry
		ACCESS	not-accessible
		STATUS	mandatory
		DESCRIPTION
"Status parameters for a specific PPP IP Network Control Protocol."
		INDEX { mlpppIpNsLSapNumber, mlpppIpNsNumber }
		::= { mlpppIpNsTable 1 }


MlpppIpNsEntry	::=
		SEQUENCE {
-- Parameters
			mlpppIpNsLSapNumber			SapIndex,
			mlpppIpNsNumber			INTEGER,

-- 
-- Control		
-- Status
			mlpppIpNsLocalToRemoteComp		INTEGER,
               		mlpppIpNsRemoteToLocalComp		INTEGER
-- Statistics
			}

mlpppIpNsLSapNumber 		OBJECT-TYPE
		SYNTAX	SapIndex
		ACCESS	read-only
		STATUS	mandatory
		DESCRIPTION
"Indicates the row that contains objects for monitoring a SAP that is 
associated with one of the PPP links.

Range of Values: 1-10

Default Value: none"
		::= { mlpppIpNsEntry 1 }

mlpppIpNsNumber 		OBJECT-TYPE
		SYNTAX	INTEGER
		ACCESS	read-only
		STATUS	mandatory
		DESCRIPTION
"Indicates the row that contains objects for monitoring a SAP that is 
associated with one of the PPP links.

Range of Values: 1

Default Value: none"
		::= { mlpppIpNsEntry 2 }

mlpppIpNsLocalToRemoteComp   	OBJECT-TYPE
               	SYNTAX    	INTEGER {
			                         none(1),
			                         vj-tcp(2)
			              }
	              ACCESS    	read-only
               	STATUS    	mandatory	
	              DESCRIPTION
"Identifies whether the local end of the IP-PPP link is using TCP/IP 
header compression (vj-tcp) to send packets to the remote. 

The value of this object is determined when the PPP configuration is 
negotiated. The local port's preference for header compression is 
determined using mlpppIpNcComp of  mlpppIpNcTable. 

Options: 
none (1) 

vj-tcp (2): header compression

Default Value: None"              	
::= { mlpppIpNsEntry 40 }


mlpppIpNsRemoteToLocalComp   	OBJECT-TYPE
       		SYNTAX    	INTEGER {
		                         		none(1),
                         				vj-tcp(2)
                    			}
               	ACCESS    	read-only
               	STATUS    	mandatory
               	DESCRIPTION
"Identifies whether the remote end of the IP-PPP link is using TCP/IP 
header compression (vj-tcp) to send packets to the local end.

The value of this object is determined when the PPP configuration is 
negotiated. The local port's preference for header compression is 
determined using mlpppIpNcComp of mlpppIpNcTable.

Options:
none (1)

vj-tcp (2): header compression

Default value: None"
               	::= { mlpppIpNsEntry 41 }


--  Internet Protocol Network Control Protocol Configuration table
--  
--  This table will be automaticly created when an upper service access point will be created.

--  The table describing:
--	parameters required to configure a PPP IP Network Control Protocol associated to an 
--	upper service access point

mlpppIpNcTable			OBJECT-TYPE
		SYNTAX	SEQUENCE OF MlpppIpNcEntry
		ACCESS	not-accessible
		STATUS	mandatory
		DESCRIPTION
"A table containing configuration parameters about each MLPPP  module 
layer's PPP IP Network Control Protocol."
		::= { cxMLPPP 53 }

mlpppIpNcEntry			OBJECT-TYPE
		SYNTAX	MlpppIpNcEntry
		ACCESS	not-accessible
		STATUS	mandatory
		DESCRIPTION
"The configuration parameters for a specific PPP IP Network Control Protocol."
		INDEX { mlpppIpNcUSapNumber, mlpppIpNcNumber }
		::= { mlpppIpNcTable 1 }


MlpppIpNcEntry	::=
		SEQUENCE {
-- Parameters
			mlpppIpNcUSapNumber		SapIndex,
			mlpppIpNcNumber		INTEGER,

-- 
			mlpppIpNcComp			INTEGER
-- Control		
-- Status
-- Statistics
			}

mlpppIpNcUSapNumber 		OBJECT-TYPE
		SYNTAX	SapIndex
		ACCESS	read-only
		STATUS	mandatory
		DESCRIPTION
"Indicates the row containing objects for monitoring a SAP that is 
associated with one of the MLPPP links .

Range of Values: 1-10

Default Value: none"
		::= { mlpppIpNcEntry 1 }


mlpppIpNcNumber 		OBJECT-TYPE
		SYNTAX	INTEGER
		ACCESS	read-only
		STATUS	mandatory
		DESCRIPTION
 "Indicates the row containing objects for monitoring a SAP associated 
with one of the MLPPP links.

Range of Values: 1

Default Value: none"
		::= { mlpppIpNcEntry 2 }



mlpppIpNcComp   		OBJECT-TYPE
               	SYNTAX    	INTEGER {
			                         none(1),
			                         vj-tcp(2)
			              }
               	ACCESS    	read-write
	               STATUS    	mandatory
	               DESCRIPTION
"Determines whether the local end of PPP link wants to use TCP/IP header 
compression (vj-tcp) to send packets over the link. If header compression 
is desired, the local will negotiate for its implementation with the 
remote end of the link. The result of the negotiation is displayed in 
mlpppIpNsLocalToRemoteComp (the local) and mlpppIpNsRemoteToLocalComp 
(remote). If compression is not desired, there will be no attempt to 
negotiate with the other end of the link.

Options:
none (1)

vj-tcp (2): header compression

Default Value: none

Configuration Changed: administrative"
               	REFERENCE
                         		"Section 4.0, Van Jacobson TCP/IP Header
                         		Compression of RFC1332."
               	DEFVAL    { none }
               	::= { mlpppIpNcEntry 10 }

END
