-------------------------------------------------------------------------------
-- file: E3Extensions.mib 
--
-- description:
--   This file contains the SNMP definitions for Newbridge Extensions on
--   E3 objects.
--
-- history:
--   P.129221 / 96.11.27 / R. To / Creation from V1.0 of MIBTemplate.mib
--   %%history-start%%
--   96.12.13 rickt P.129221: Added new E3Extensions MIB Module. 
--   %%history-end%%
--
-- Copyright 1996 Newbridge Networks Corporation.  All Rights Reserved
-------------------------------------------------------------------------------

NNCEXTE3-MIB DEFINITIONS ::= BEGIN

  IMPORTS
    nncExtensions
      FROM NNCGNI0001-SMI
    MODULE-IDENTITY, OBJECT-TYPE, Gauge32, Integer32
      FROM SNMPv2-SMI
    MODULE-COMPLIANCE, OBJECT-GROUP
      FROM SNMPv2-CONF
    ifIndex
      FROM IF-MIB;
      
  nncExtE3 MODULE-IDENTITY
    LAST-UPDATED   "9611251500Z"
    ORGANIZATION   "Newbridge Networks Corporation"
    CONTACT-INFO   "Newbridge Networks Corporation
                    Postal: 600 March Road
                            Kanata, Ontario
                            Canada K2K 2E6

                    Phone:  +1 613 591 3600
                    Fax:    +1 613 591 3680"
    
    DESCRIPTION  "This module contains definitions for Newbridge extensions 
                  to E3 objects.  It is used as a supplement to rfc1407."
  
    ::= { nncExtensions 40 }


  nncExtE3Objects     OBJECT IDENTIFIER ::= { nncExtE3 1 }
  nncExtE3Traps       OBJECT IDENTIFIER ::= { nncExtE3 2 }
  nncExtE3Groups      OBJECT IDENTIFIER ::= { nncExtE3 3 }
  nncExtE3Compliances OBJECT IDENTIFIER ::= { nncExtE3 4 }

--------------------------------------------------------------------------------
-- Object Definitions
--
-- This MIB module contains the following tables:
--
--  E3 Near End Current 15 Minutes Table
--  E3 Near End Interval 15 Minutes Table
--  E3 Near End Total Table
--
--  E3 Far End Current 15 Minutes Table
--  E3 Far End Interval 15 Minutes Table
--  E3 Far End Total Table
--
--------------------------------------------------------------------------------

--------------------------------------------------------------------------------
-- Table 1: Near End Statistics Current 15 Minutes Table
--------------------------------------------------------------------------------

  nncExtE3Current15MinTable   OBJECT-TYPE
    SYNTAX        SEQUENCE OF NncExtE3Current15MinEntry
    MAX-ACCESS    not-accessible
    STATUS        current
    DESCRIPTION   "NNC Extension to dsx3CurrentTable."
    ::= { nncExtE3Objects 1 }


  nncExtE3Current15MinEntry   OBJECT-TYPE
    SYNTAX        NncExtE3Current15MinEntry
    MAX-ACCESS    not-accessible
    STATUS        current
    DESCRIPTION   "An entry in nncExtE3Current15MinTable."
    INDEX         { ifIndex }
    ::= { nncExtE3Current15MinTable 1 }


  NncExtE3Current15MinEntry ::=
    SEQUENCE {
      nncExtE3Current15MinESs           Gauge32,
      nncExtE3Current15MinSESs          Gauge32,
      nncExtE3Current15MinSEFs          Gauge32
    }

  nncExtE3Current15MinESs   OBJECT-TYPE
    SYNTAX        Gauge32
    MAX-ACCESS    read-only
    STATUS        current
    DESCRIPTION   "The counter associated with the number of Path Errored
                  Seconds encountered by a E3 interface in the current
                  15 minute interval.  
                  This counts the seconds containing one or more BIP
                  errors, one or more LOF defects, one or more LOS defects,
                  or a detected incoming AIS. This counter is valid when
                  an interface is configured for Direct cell mapping.
                  When an interface is configured for PLCP cell mapping,
                  the counter returns the last valid count when the port
                  is in the Direct mode."
    ::= { nncExtE3Current15MinEntry 1 }

  nncExtE3Current15MinSESs   OBJECT-TYPE
    SYNTAX        Gauge32
    MAX-ACCESS    read-only
    STATUS        current
    DESCRIPTION   "The counter associated with the number of Path Severely
                  Errored Seconds encountered by a E3 interface in the
                  current 15 minute interval. 
                  This counts the seconds containing 34 or more BIP
                  errors, one or more LOF defects, one or more LOS defects,
                  or a detected incoming AIS. This counter is valid when
                  an interface is configured for Direct cell mapping.
                  When an interface is configured for PLCP cell mapping,
                  the counter returns the last valid count when the
                  port is in the Direct mode."
    ::= { nncExtE3Current15MinEntry 2 }

  nncExtE3Current15MinSEFs   OBJECT-TYPE
    SYNTAX        Gauge32
    MAX-ACCESS    read-only
    STATUS        current
    DESCRIPTION   "The counter associated with the number of Path Severely
                  Errored Frames encountered by a E3 interface in the
                  current 15 minute interval. 
                  This counts framing pattern errors.  In Direct cell
                  mapping mode, this is the count of frames with errored 
                  FA1/FA2 bytes in the G.832 overhead. In PLCP mode,
                  this is the count of frames with an errored G.751
                  Frame Alignment byte."
    ::= { nncExtE3Current15MinEntry 3 }


--------------------------------------------------------------------------------
-- Table 2: Near End Statistics Interval 15 Minutes Table
--------------------------------------------------------------------------------

  nncExtE3Interval15MinTable   OBJECT-TYPE
    SYNTAX        SEQUENCE OF NncExtE3Interval15MinEntry
    MAX-ACCESS    not-accessible
    STATUS        current
    DESCRIPTION   "NNC Extension to dsx3IntervalTable."
    ::= { nncExtE3Objects 2 }


  nncExtE3Interval15MinEntry   OBJECT-TYPE
    SYNTAX        NncExtE3Interval15MinEntry
    MAX-ACCESS    not-accessible
    STATUS        current
    DESCRIPTION   "An entry in nncExtE3Interval15MinTable."
    INDEX         { ifIndex, nncExtE3Interval15MinNumber }
    ::= { nncExtE3Interval15MinTable 1 }


  NncExtE3Interval15MinEntry ::=
    SEQUENCE {
      nncExtE3Interval15MinNumber        Integer32,
      nncExtE3Interval15MinESs           Gauge32,
      nncExtE3Interval15MinSESs          Gauge32,
      nncExtE3Interval15MinSEFs          Gauge32
    }

  nncExtE3Interval15MinNumber   OBJECT-TYPE
    SYNTAX        Integer32 (1..96)
    MAX-ACCESS    not-accessible
    STATUS        current
    DESCRIPTION   "A number between 1 and 96, where 1 is the most recently
                  completed 15 minute interval and 96 is the least recently 
                  completed 15 minutes interval (assuming that all 96 
                  intervals are valid)."
    ::= { nncExtE3Interval15MinEntry 1 }

  nncExtE3Interval15MinESs   OBJECT-TYPE
    SYNTAX        Gauge32
    MAX-ACCESS    read-only
    STATUS        current
    DESCRIPTION   "The counter associated with the number of Path Errored
                  Seconds encountered by a E3 interface in one of the
                  previous 15 minute intervals.  
                  This counts the seconds containing one or more BIP
                  errors, one or more LOF defects, one or more LOS defects,
                  or a detected incoming AIS. This counter is valid when
                  an interface is configured for Direct cell mapping.
                  When an interface is configured for PLCP cell mapping,
                  the counter returns the last valid count when the port
                  is in the Direct mode."
    ::= { nncExtE3Interval15MinEntry 2 }

  nncExtE3Interval15MinSESs   OBJECT-TYPE
    SYNTAX        Gauge32
    MAX-ACCESS    read-only
    STATUS        current
    DESCRIPTION   "The counter associated with the number of Path Severely
                  Errored Seconds encountered by a E3 interface in one of
                  the previous 15 minute intervals. 
                  This counts the seconds containing 34 or more BIP
                  errors, one or more LOF defects, one or more LOS defects,
                  or a detected incoming AIS. This counter is valid when
                  an interface is configured for Direct cell mapping.
                  When an interface is configured for PLCP cell mapping,
                  the counter returns the last valid count when the
                  port is in the Direct mode."
    ::= { nncExtE3Interval15MinEntry 3 }

  nncExtE3Interval15MinSEFs   OBJECT-TYPE
    SYNTAX        Gauge32
    MAX-ACCESS    read-only
    STATUS        current
    DESCRIPTION   "The counter associated with the number of Path Severely
                  Errored Frames encountered by a E3 interface in one of
                  the previous 15 minute intervals. 
                  This counts framing pattern errors.  In Direct cell
                  mapping mode, this is the count of frames with errored 
                  FA1/FA2 bytes in the G.832 overhead. In PLCP mode,
                  this is the count of frames with an errored G.751
                  Frame Alignment byte."
    ::= { nncExtE3Interval15MinEntry 4 }


--------------------------------------------------------------------------------
-- Table 3: Near End Statistics Total 24 Hours Table
--------------------------------------------------------------------------------

  nncExtE3Total24HrTable   OBJECT-TYPE
    SYNTAX        SEQUENCE OF NncExtE3Total24HrEntry
    MAX-ACCESS    not-accessible
    STATUS        current
    DESCRIPTION   "NNC Extension to dsx3TotalTable."
    ::= { nncExtE3Objects 3 }


  nncExtE3Total24HrEntry   OBJECT-TYPE
    SYNTAX        NncExtE3Total24HrEntry
    MAX-ACCESS    not-accessible
    STATUS        current
    DESCRIPTION   "An entry in nncExtE3Total24HrTable."
    INDEX         { ifIndex }
    ::= { nncExtE3Total24HrTable 1 }


  NncExtE3Total24HrEntry ::=
    SEQUENCE {
      nncExtE3Total24HrESs           Gauge32,
      nncExtE3Total24HrSESs          Gauge32,
      nncExtE3Total24HrSEFs          Gauge32
    }

  nncExtE3Total24HrESs   OBJECT-TYPE
    SYNTAX        Gauge32
    MAX-ACCESS    read-only
    STATUS        current
    DESCRIPTION   "The counter associated with the number of Path Errored
                  Seconds encountered by a E3 interface in the
                  previous 24 hours interval.  
                  This counts the seconds containing one or more BIP
                  errors, one or more LOF defects, one or more LOS defects,
                  or a detected incoming AIS. This counter is valid when
                  an interface is configured for Direct cell mapping.
                  When an interface is configured for PLCP cell mapping,
                  the counter returns the last valid count when the port
                  is in the Direct mode."
    ::= { nncExtE3Total24HrEntry 1 }

  nncExtE3Total24HrSESs   OBJECT-TYPE
    SYNTAX        Gauge32
    MAX-ACCESS    read-only
    STATUS        current
    DESCRIPTION   "The counter associated with the number of Path Severely
                  Errored Seconds encountered by a E3 interface in the
                  previous 24 hours interval. 
                  This counts the seconds containing 34 or more BIP
                  errors, one or more LOF defects, one or more LOS defects,
                  or a detected incoming AIS. This counter is valid when
                  an interface is configured for Direct cell mapping.
                  When an interface is configured for PLCP cell mapping,
                  the counter returns the last valid count when the
                  port is in the Direct mode."
    ::= { nncExtE3Total24HrEntry 2 }

  nncExtE3Total24HrSEFs   OBJECT-TYPE
    SYNTAX        Gauge32
    MAX-ACCESS    read-only
    STATUS        current
    DESCRIPTION   "The counter associated with the number of Path Severely
                  Errored Frames encountered by a E3 interface in the
                  previous 24 hours interval. 
                  This counts framing pattern errors.  In Direct cell
                  mapping mode, this is the count of frames with errored 
                  FA1/FA2 bytes in the G.832 overhead. In PLCP mode,
                  this is the count of frames with an errored G.751
                  Frame Alignment byte."
    ::= { nncExtE3Total24HrEntry 3 }


--------------------------------------------------------------------------------
-- Table 4: Far End Statistics Current 15 Minutes Table
--------------------------------------------------------------------------------

  nncExtE3FarEndCurrent15MinTable   OBJECT-TYPE
    SYNTAX        SEQUENCE OF NncExtE3FarEndCurrent15MinEntry
    MAX-ACCESS    not-accessible
    STATUS        current
    DESCRIPTION   "NNC Extension to dsx3FarEndCurrentTable."
    ::= { nncExtE3Objects 4 }


  nncExtE3FarEndCurrent15MinEntry   OBJECT-TYPE
    SYNTAX        NncExtE3FarEndCurrent15MinEntry
    MAX-ACCESS    not-accessible
    STATUS        current
    DESCRIPTION   "An entry in nncExtE3FarEndCurrent15MinTable."
    INDEX         { ifIndex }
    ::= { nncExtE3FarEndCurrent15MinTable 1 }


  NncExtE3FarEndCurrent15MinEntry ::=
    SEQUENCE {
      nncExtE3FarEndCurrent15MinFEBEs         Gauge32,
      nncExtE3FarEndCurrent15MinESs           Gauge32,
      nncExtE3FarEndCurrent15MinSESs          Gauge32
    }

  nncExtE3FarEndCurrent15MinFEBEs   OBJECT-TYPE
    SYNTAX        Gauge32
    MAX-ACCESS    read-only
    STATUS        current
    DESCRIPTION   "The counter associated with the number of Far End
                  Block Errors encountered by a E3 interface in the
                  current 15 minute interval.
                  This is the count of received FEBEs. This counter will
                  not increment while failure defects are present. 
                  This counter is valid when an interface is configured 
                  for Direct cell mapping. When an interface is configured
                  for PLCP cell mapping, the counter returns the last
                  valid count when the port is in the Direct mode."
    ::= { nncExtE3FarEndCurrent15MinEntry 1 }

  nncExtE3FarEndCurrent15MinESs   OBJECT-TYPE
    SYNTAX        Gauge32
    MAX-ACCESS    read-only
    STATUS        current
    DESCRIPTION   "The counter associated with the number of Far End Path 
                  Errored Seconds encountered by a E3 interface in the
                  current 15 minute interval.
                  This counts the seconds containing one or more FEBEs. 
                  This counter is valid when an interface is configured 
                  for Direct cell mapping. When an interface is configured
                  for PLCP cell mapping, the counter returns the last
                  valid count when the port is in the Direct mode."
    ::= { nncExtE3FarEndCurrent15MinEntry 2 }

  nncExtE3FarEndCurrent15MinSESs   OBJECT-TYPE
    SYNTAX        Gauge32
    MAX-ACCESS    read-only
    STATUS        current
    DESCRIPTION   "The counter associated with the number of Far End Path 
                  Severely Errored Seconds encountered by a E3 interface 
                  in the current 15 minute interval.
                  This counts the seconds containing 34 or more FEBEs. 
                  This counter is valid when an interface is configured 
                  for Direct cell mapping. When an interface is configured
                  for PLCP cell mapping, the counter returns the last
                  valid count when the port is in the Direct mode."
    ::= { nncExtE3FarEndCurrent15MinEntry 3 }


--------------------------------------------------------------------------------
-- Table 5: Far End Statistics Interval 15 Minutes Table
--------------------------------------------------------------------------------

  nncExtE3FarEndInterval15MinTable   OBJECT-TYPE
    SYNTAX        SEQUENCE OF NncExtE3FarEndInterval15MinEntry
    MAX-ACCESS    not-accessible
    STATUS        current
    DESCRIPTION   "NNC Extension to dsx3FarEndIntervalTable."
    ::= { nncExtE3Objects 5 }


  nncExtE3FarEndInterval15MinEntry   OBJECT-TYPE
    SYNTAX        NncExtE3FarEndInterval15MinEntry
    MAX-ACCESS    not-accessible
    STATUS        current
    DESCRIPTION   "An entry in nncExtE3FarEndInterval15MinTable."
    INDEX         { ifIndex, nncExtE3FarEndInterval15MinNumber }
    ::= { nncExtE3FarEndInterval15MinTable 1 }


  NncExtE3FarEndInterval15MinEntry ::=
    SEQUENCE {
      nncExtE3FarEndInterval15MinNumber        Integer32,
      nncExtE3FarEndInterval15MinFEBEs         Gauge32,
      nncExtE3FarEndInterval15MinESs           Gauge32,
      nncExtE3FarEndInterval15MinSESs          Gauge32
    }

  nncExtE3FarEndInterval15MinNumber   OBJECT-TYPE
    SYNTAX        Integer32 (1..96)
    MAX-ACCESS    not-accessible
    STATUS        current
    DESCRIPTION   "A number between 1 and 96, where 1 is the most recently
                  completed 15 minute interval and 96 is the least recently 
                  completed 15 minutes interval (assuming that all 96 
                  intervals are valid)."
    ::= { nncExtE3FarEndInterval15MinEntry 1 }

  nncExtE3FarEndInterval15MinFEBEs   OBJECT-TYPE
    SYNTAX        Gauge32
    MAX-ACCESS    read-only
    STATUS        current
    DESCRIPTION   "The counter associated with the number of Far End
                  Block Errors encountered by a E3 interface in one of
                  the previous 15 minute intervals.
                  This is the count of received FEBEs. This counter will
                  not increment while failure defects are present. 
                  This counter is valid when an interface is configured 
                  for Direct cell mapping. When an interface is configured
                  for PLCP cell mapping, the counter returns the last
                  valid count when the port is in the Direct mode."
    ::= { nncExtE3FarEndInterval15MinEntry 2 }

  nncExtE3FarEndInterval15MinESs   OBJECT-TYPE
    SYNTAX        Gauge32
    MAX-ACCESS    read-only
    STATUS        current
    DESCRIPTION   "The counter associated with the number of Far End Path 
                  Errored Seconds encountered by a E3 interface in one of
                  the previous 15 minute intervals.
                  This counts the seconds containing one or more FEBEs. 
                  This counter is valid when an interface is configured 
                  for Direct cell mapping. When an interface is configured
                  for PLCP cell mapping, the counter returns the last
                  valid count when the port is in the Direct mode."
    ::= { nncExtE3FarEndInterval15MinEntry 3 }

  nncExtE3FarEndInterval15MinSESs   OBJECT-TYPE
    SYNTAX        Gauge32
    MAX-ACCESS    read-only
    STATUS        current
    DESCRIPTION   "The counter associated with the number of Far End Path 
                  Severely Errored Seconds encountered by a E3 interface 
                  in one of the previous 15 minute intervals.
                  This counts the seconds containing 34 or more FEBEs. 
                  This counter is valid when an interface is configured 
                  for Direct cell mapping. When an interface is configured
                  for PLCP cell mapping, the counter returns the last
                  valid count when the port is in the Direct mode."
    ::= { nncExtE3FarEndInterval15MinEntry 4 }


--------------------------------------------------------------------------------
-- Table 6: Far End Statistics Total 24 Hours Table
--------------------------------------------------------------------------------

  nncExtE3FarEndTotal24HrTable   OBJECT-TYPE
    SYNTAX        SEQUENCE OF NncExtE3FarEndTotal24HrEntry
    MAX-ACCESS    not-accessible
    STATUS        current
    DESCRIPTION   "NNC Extension to dsx3FarEndTotalTable."
    ::= { nncExtE3Objects 6 }


  nncExtE3FarEndTotal24HrEntry   OBJECT-TYPE
    SYNTAX        NncExtE3FarEndTotal24HrEntry
    MAX-ACCESS    not-accessible
    STATUS        current
    DESCRIPTION   "An entry in nncExtE3FarEndTotal24HrTable."
    INDEX         { ifIndex }
    ::= { nncExtE3FarEndTotal24HrTable 1 }


  NncExtE3FarEndTotal24HrEntry ::=
    SEQUENCE {
      nncExtE3FarEndTotal24HrFEBEs         Gauge32,
      nncExtE3FarEndTotal24HrESs           Gauge32,
      nncExtE3FarEndTotal24HrSESs          Gauge32
    }

  nncExtE3FarEndTotal24HrFEBEs   OBJECT-TYPE
    SYNTAX        Gauge32
    MAX-ACCESS    read-only
    STATUS        current
    DESCRIPTION   "The counter associated with the number of Far End
                  Block Errors encountered by a E3 interface in the
                  previous 24 hours interval.
                  This is the count of received FEBEs. This counter will
                  not increment while failure defects are present. 
                  This counter is valid when an interface is configured 
                  for Direct cell mapping. When an interface is configured
                  for PLCP cell mapping, the counter returns the last
                  valid count when the port is in the Direct mode."
    ::= { nncExtE3FarEndTotal24HrEntry 1 }

  nncExtE3FarEndTotal24HrESs   OBJECT-TYPE
    SYNTAX        Gauge32
    MAX-ACCESS    read-only
    STATUS        current
    DESCRIPTION   "The counter associated with the number of Far End Path 
                  Errored Seconds encountered by a E3 interface in the
                  previous 24 hours interval.
                  This counts the seconds containing one or more FEBEs. 
                  This counter is valid when an interface is configured 
                  for Direct cell mapping. When an interface is configured
                  for PLCP cell mapping, the counter returns the last
                  valid count when the port is in the Direct mode."
    ::= { nncExtE3FarEndTotal24HrEntry 2 }

  nncExtE3FarEndTotal24HrSESs   OBJECT-TYPE
    SYNTAX        Gauge32
    MAX-ACCESS    read-only
    STATUS        current
    DESCRIPTION   "The counter associated with the number of Far End Path 
                  Severely Errored Seconds encountered by a E3 interface 
                  in the previous 24 hours interval.
                  This counts the seconds containing 34 or more FEBEs. 
                  This counter is valid when an interface is configured 
                  for Direct cell mapping. When an interface is configured
                  for PLCP cell mapping, the counter returns the last
                  valid count when the port is in the Direct mode."
    ::= { nncExtE3FarEndTotal24HrEntry 3 }


--------------------------------------------------------------------------------
-- Conformance Group Definitions
--------------------------------------------------------------------------------

  nncExtE3Current15MinGroup  OBJECT-GROUP
    OBJECTS  {
      nncExtE3Current15MinESs,
      nncExtE3Current15MinSESs,
      nncExtE3Current15MinSEFs
    }
    STATUS        current
    DESCRIPTION   "Collection of objects providing 15 minute current 
                  statistics for E3 interface."
  ::= { nncExtE3Groups 1 }

  nncExtE3Interval15MinGroup  OBJECT-GROUP
    OBJECTS  {
      nncExtE3Interval15MinNumber,
      nncExtE3Interval15MinESs,
      nncExtE3Interval15MinSESs,
      nncExtE3Interval15MinSEFs
    }
    STATUS        current
    DESCRIPTION   "Collection of objects providing 15 minute interval 
                  statistics for E3 interface."
  ::= { nncExtE3Groups 2 }

  nncExtE3Total24HrGroup  OBJECT-GROUP
    OBJECTS  {
      nncExtE3Total24HrESs,
      nncExtE3Total24HrSESs,
      nncExtE3Total24HrSEFs
    }
    STATUS        current
    DESCRIPTION   "Collection of objects providing previous 24 hours 
                  statistics for E3 interface."
  ::= { nncExtE3Groups 3 }

  nncExtE3FarEndCurrent15MinGroup  OBJECT-GROUP
    OBJECTS  {
      nncExtE3FarEndCurrent15MinFEBEs,
      nncExtE3FarEndCurrent15MinESs,
      nncExtE3FarEndCurrent15MinSESs
    }
    STATUS        current
    DESCRIPTION   "Collection of objects providing 15 minute current 
                  statistics for E3 interface."
  ::= { nncExtE3Groups 4 }

  nncExtE3FarEndInterval15MinGroup  OBJECT-GROUP
    OBJECTS  {
      nncExtE3FarEndInterval15MinNumber,
      nncExtE3FarEndInterval15MinFEBEs,
      nncExtE3FarEndInterval15MinESs,
      nncExtE3FarEndInterval15MinSESs
    }
    STATUS        current
    DESCRIPTION   "Collection of objects providing 15 minute interval 
                  statistics for E3 interface."
  ::= { nncExtE3Groups 5 }

  nncExtE3FarEndTotal24HrGroup  OBJECT-GROUP
    OBJECTS  {
      nncExtE3FarEndTotal24HrFEBEs,
      nncExtE3FarEndTotal24HrESs,
      nncExtE3FarEndTotal24HrSESs
    }
    STATUS        current
    DESCRIPTION   "Collection of objects providing previous 24 hours 
                  statistics for E3 interface."
  ::= { nncExtE3Groups 6 }


--------------------------------------------------------------------------------
-- Compliance Statements (mandatory)
--------------------------------------------------------------------------------

  nncExtE3Compliance  MODULE-COMPLIANCE
    STATUS        current
    DESCRIPTION   "The compliance statement for Newbridge E3 interfaces."
    MODULE 
      MANDATORY-GROUPS {
        nncExtE3Current15MinGroup,
        nncExtE3Interval15MinGroup,
        nncExtE3Total24HrGroup,
        nncExtE3FarEndCurrent15MinGroup,
        nncExtE3FarEndInterval15MinGroup,
        nncExtE3FarEndTotal24HrGroup
      }
  ::= { nncExtE3Compliances 1 } 


-------------------------------------------------------------------------------
--  Review Minutes 
-------------------------------------------------------------------------------
--  MINUTES-BEGIN
--    REVIEW-DATE  "1996.11.27"
--    BODY  "
--
--  TO:  Ken Duesling*, Aleksandar Radovic*, Nelson Gillette*
--  CC:  Randy Jone, Steve Bews, Steve McCaughan 
--       Numbers Admin, Melanie Paquette
--  FROM:  Rick To*
--
--  A meeting was held on 1996.11.27 to review NncExtDsx3.mib
--  Attendees are marked with * in the TO and CC lists above.
--
--  Outcome
--
--  It was the consensus of the review team that this file is 
--  acceptable with the indicated modifications.
--
--  Actions:
--  A1 -   Rick To to update the file as indicated in D1 below.  
--    Response:  Status: CLOSED
--
--  Decisions:
--  D1 -   NncExtDsx3.mib shall be updated as follows:
--     a. Restrict context of these objects to only E3; rename MIB
--        module from NncExtDsx3 to NncExtE3.
--     b. Expand definitions of the stats objects. Use information
--        from 31FS0096.
--     c. For Near End ESs and SESs, indicate that they are only 
--        available in Direct Mode (and not PLCP).
--     d. Add 15Min to the name of Current and Interval objects.
--  "
--
--  END-MINUTES
--
END -- DEFINITION OF NNCEXTE3-MIB
