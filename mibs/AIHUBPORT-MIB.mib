AIHUBPORT-MIB DEFINITIONS ::=  BEGIN

-- Applied Innovation Hub Port Control MIB definitions
-- @(#) ai $Revision:   1.00  $ $Date:   1 Nov 2000 12:23:37  $

IMPORTS
    DisplayString
        FROM RFC1213-MIB
		  
		PositiveInteger FROM AISYSTEM-MIB

    MODULE-IDENTITY, OBJECT-TYPE, Counter32, Gauge32,
    enterprises
        FROM SNMPv2-SMI;


-- group object IDs

aii             OBJECT IDENTIFIER ::= { enterprises 539 }
aiSystemOID     OBJECT IDENTIFIER ::= { aii 2 }

aiHubport  MODULE-IDENTITY
    LAST-UPDATED "980803164411Z"
    ORGANIZATION "Applied Innovation Incorporated"
    CONTACT-INFO
        "        Engineering MIB Administrator

        Postal:  Applied Innovation Inc.
                 5800 Innovation Drive
                 Dublin, OH 43016-3271

           Tel:  614/798-2000
           Fax:  614/798-1770
        E-mail:  snmp@aiinet.com"
    DESCRIPTION  " The MIB Module for Hub Port Control."
    ::= { aii 27 }

-- System group for Hub Port Control

aiHubCnf    OBJECT IDENTIFIER ::= { aiHubport 1 }

-- System Group

hubPortCnfTable OBJECT-TYPE
        SYNTAX          SEQUENCE OF HUBPortCnfEntry
        MAX-ACCESS      not-accessible
        STATUS          current
        DESCRIPTION
                "Table of configuration information about hub ports."
        ::= { aiHubCnf 1 }

hubPortCnfEntry  OBJECT-TYPE
        SYNTAX		HUBPortCnfEntry
        MAX-ACCESS	not-accessible
        STATUS		current
        DESCRIPTION
	        "Entries of aiLinkTable."
        INDEX { hubPortIndex }
	::= { hubPortCnfTable 1 }

HUBPortCnfEntry ::= SEQUENCE {
	hubPortIndex            PositiveInteger,
        hubPortIfIndex          PositiveInteger,
        hubPortSpeedCtrl        DisplayString
        }

hubPortIndex OBJECT-TYPE
        SYNTAX          INTEGER (1..1024)
        MAX-ACCESS      read-only
        STATUS          current
        DESCRIPTION
                "This object identifies the port within the group
                for which this entry contains information."
        ::= {hubPortCnfEntry 1}

hubPortIfIndex OBJECT-TYPE
	SYNTAX		INTEGER (1..1024)
        MAX-ACCESS  	read-only
	STATUS		current
	DESCRIPTION
                "The index into the interfaces group of MIB-II, which defines what type
                of interface this link is.  This definition describes a protocol
                stack in only the most general way.  The interface which appears here may
                have other interfaces stacked beneath it which are also in the interface
                table."
	::= {hubPortCnfEntry 2}

hubPortSpeedCtrl OBJECT-TYPE
        SYNTAX		INTEGER {
                                auto(0),
                                t10(1),
                                tx100(3)
                        }
        MAX-ACCESS	read-write
	STATUS		current
	DESCRIPTION	"The speed control setting for hub ports."
	::= {hubPortCnfEntry 3}

END
