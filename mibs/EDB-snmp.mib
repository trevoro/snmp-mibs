-- Title:         Fibronics' MIB  
-- MIB Module :   Private MIB for  MultiHUB EDB
-- Version    :   V1.0
-- Date       :   Jan 1, 1995
-- By         :   Gadi K.
-- Contact    :   Edna Ganon
-- Email:     :   edna@fibronics.co.il 
-- 
-- Description:   MIB for the EDB SNMP Agents
-- Copyright (c) 1991 Fibronics International

          EDB-snmp DEFINITIONS ::= BEGIN

          IMPORTS
			 TRAP-TYPE FROM RFC-1215
		DisplayString FROM SNMPv2-TC
                  mgmt, NetworkAddress, IpAddress, Counter, Gauge,
                          TimeTicks, internet
                      FROM RFC1155-SMI
		  PhysAddress
		  	FROM RFC1213-MIB
                  OBJECT-TYPE
                          FROM RFC-1212;


 


          -- *****************************************
          --       E D B       M I B
          -- ****************************************
	   


          private    OBJECT IDENTIFIER ::= { internet 4 }
          enterprises OBJECT IDENTIFIER ::= { private 1 }


                  fibronics  OBJECT IDENTIFIER ::= { enterprises 22 }
                  trap            OBJECT IDENTIFIER ::= { fibronics 3 }
                  traprun         OBJECT IDENTIFIER ::= { trap 1 }
                  traperm         OBJECT IDENTIFIER ::= { trap 2 }
                  trapvar         OBJECT IDENTIFIER ::= { trap 3 }
		  fm800		  OBJECT IDENTIFIER ::= { fibronics 51 }
		  fmsystem	  OBJECT IDENTIFIER ::= { fm800 1 }
		  fmslot	  OBJECT IDENTIFIER ::= { fm800 2 }
		  fmlu		  OBJECT IDENTIFIER ::= { fm800 3 }
		  fmdiag	  OBJECT IDENTIFIER ::= { fm800 5 }

		  fmsystemrun	  OBJECT IDENTIFIER ::= { fmsystem 1 }
		  fmsystemperm	  OBJECT IDENTIFIER ::= { fmsystem 2 }




------------------------------------------------
--
--          T R A P     T A B L E
--
------------------------------------------------

--   Trap runtime objects
------------------------------------------------


rTrapAddrTbl	OBJECT-TYPE
	SYNTAX  SEQUENCE OF RTrapAddrEntry
	ACCESS  not-accessible
	STATUS  mandatory
	DESCRIPTION "Table of managers to which traps
  		     must be sent. Up to 10 
		     entries in table"
	::= { traprun 1 }

rTrapAddrEntry	OBJECT-TYPE
	SYNTAX  RTrapAddrEntry
	ACCESS  not-accessible
	STATUS  mandatory
	INDEX   { rTrapAddrAddr }
	::= { rTrapAddrTbl 1 }

RTrapAddrEntry ::= SEQUENCE {
	rTrapAddrAddr
		IpAddress,
	rTrapAddrComm
	        OCTET STRING,
	rTrapAddrVer
		INTEGER,
	rTrapAddrType
		OCTET STRING,
	rTrapAddrState
		INTEGER,
	rTrapAddrFlag
		INTEGER,
	rTrapAddrAge
		INTEGER
	}

rTrapAddrAddr 	OBJECT-TYPE
	SYNTAX	IpAddress
        ACCESS  read-write
        STATUS  mandatory
	DESCRIPTION "IP address of entity
		     requesting event notification"
	::= { rTrapAddrEntry 1 }

rTrapAddrComm 	OBJECT-TYPE
        SYNTAX  OCTET STRING
        ACCESS  read-write
        STATUS  mandatory
	DESCRIPTION "Community name the receiving
 		     entity will expect.
                    When reading the instance of this
                    object the value has no meaning."
	::= { rTrapAddrEntry 2 }

rTrapAddrVer  	OBJECT-TYPE
	SYNTAX  INTEGER
        ACCESS  read-write
        STATUS  mandatory
	DESCRIPTION "Version number supported by
		     destination node"
	::= { rTrapAddrEntry 3 }

rTrapAddrType 	OBJECT-TYPE
	SYNTAX  OCTET STRING
        ACCESS  read-write
        STATUS  mandatory
	DESCRIPTION "Type of event that should be
		     reported to this address,
                     bit 0 - authentication trap
		     bit 1 - other SNMP traps
		     bit 2 - Error Traps
		     bit 3 - Diagnostic Traps
		     bit 4 - Debug Traps
		     bit 5 - Enterprise Traps other than fmDiagGenericTrap"
	::= { rTrapAddrEntry 4 }

rTrapAddrState	OBJECT-TYPE
	SYNTAX  INTEGER {
		active(1),
		inactive(2)
		}
        ACCESS  read-write
        STATUS  mandatory
	DESCRIPTION "Determines status of this entry"
	::= { rTrapAddrEntry 5 }

rTrapAddrFlag	OBJECT-TYPE
	SYNTAX	INTEGER {
		fixed(0),
		removable(1)
		}
	ACCESS	read-write
	STATUS	mandatory
	DESCRIPTION "If the entry is fixed, it can not
		be deleted because of aging"
	::= { rTrapAddrEntry 6 }

rTrapAddrAge	OBJECT-TYPE
	SYNTAX	INTEGER
	ACCESS	read-only
	STATUS	mandatory
	DESCRIPTION "Aging time of the entry (in sec)"
	::= { rTrapAddrEntry 7 }

rTrapLearning	OBJECT-TYPE
	SYNTAX	INTEGER {
		disable(0),
		enable(1)
		}
	ACCESS	read-only
	STATUS  mandatory
	DESCRIPTION "Learn the addresses of the managers
		automatically."
	::= { traprun 2 }

rTrapAging	OBJECT-TYPE
	SYNTAX	INTEGER 
	ACCESS	read-only
	STATUS	mandatory
	DESCRIPTION "Time in sec. until we erase a trap
		entry"
	::= { traprun 3 }


--   Trap permanents objects

pTrapAddrTbl	OBJECT-TYPE
	SYNTAX  SEQUENCE OF PTrapAddrEntry
	ACCESS  not-accessible
	STATUS  mandatory
	DESCRIPTION "Table of managers to which traps
  		     must be sent. Up to 10 
		     entries in table"
	::= { traperm 1 }

pTrapAddrEntry	OBJECT-TYPE
	SYNTAX  PTrapAddrEntry
	ACCESS  not-accessible
	STATUS  mandatory
	INDEX   { pTrapAddrAddr }
	::= { pTrapAddrTbl 1 }

PTrapAddrEntry ::= SEQUENCE {
	pTrapAddrAddr
		IpAddress,
	pTrapAddrComm
	        OCTET STRING,
	pTrapAddrVer
		INTEGER,
	pTrapAddrType
		OCTET STRING,
	pTrapAddrState
		INTEGER
	}

pTrapAddrAddr 	OBJECT-TYPE
	SYNTAX	IpAddress
        ACCESS  read-write
        STATUS  mandatory
	DESCRIPTION "IP address of entity
		     requesting event notification"
	::= { pTrapAddrEntry 1 }

pTrapAddrComm 	OBJECT-TYPE
        SYNTAX  OCTET STRING
        ACCESS  read-write
        STATUS  mandatory
	DESCRIPTION "Community name the receiving
 		     entity will expect.
                    When reading the instance of this
                    object the value has no meaning."
	::= { pTrapAddrEntry 2 }

pTrapAddrVer  	OBJECT-TYPE
	SYNTAX  INTEGER
        ACCESS  read-write
        STATUS  mandatory
	DESCRIPTION "Version number supported by
		     destination node"
	::= { pTrapAddrEntry 3 }

pTrapAddrType 	OBJECT-TYPE
	SYNTAX  OCTET STRING
        ACCESS  read-write
        STATUS  mandatory
	DESCRIPTION "Type of event that should be
		     reported to this address,
                     bit 0 - authentication trap
		     bit 1 - other SNMP traps
		     bit 2 - Error Traps
		     bit 3 - Diagnostic Traps
		     bit 4 - Debug Traps
		     bit 5 - all Enterprise Traps other than fmDiagGenericTrap"
	::= { pTrapAddrEntry 4 }

pTrapAddrState 	OBJECT-TYPE
	SYNTAX  INTEGER {
		active(1),
		inactive(2)
		}
        ACCESS  read-write
        STATUS  mandatory
	DESCRIPTION "Determines status of this entry"
	::= { pTrapAddrEntry 5 }

pTrapLearning	OBJECT-TYPE
	SYNTAX	INTEGER {
		disable(0),
		enable(1)
		}
	ACCESS	read-write
	STATUS  mandatory
	DESCRIPTION "Learn the addresses of the managers
		automatically."
	::= { traperm 2 }

pTrapAging	OBJECT-TYPE
	SYNTAX	INTEGER 
	ACCESS	read-write
	STATUS	mandatory
	DESCRIPTION "Time in sec. until we erase a trap
		entry"
	::= { traperm 3 }

------------------------------------------------

-- System Group RunTime
------------------------------------------------

fmSystemPSAdmin	OBJECT-TYPE
	SYNTAX  INTEGER {
		primary-power(1),
		secondary-power(2)
		}
	ACCESS  read-write
	STATUS  mandatory
	DESCRIPTION "Changes power supply to
		   primary or secondary.
                   When reading the instance of this
	           object the value has no meaning."

	::= { fmsystemrun 1 }

fmSystemPSOper	OBJECT-TYPE
	SYNTAX  INTEGER {
		primary-power(1),
		secondary-power(2)
		}
	ACCESS  read-only
	STATUS  mandatory
	DESCRIPTION "Which power supply active"
	::= { fmsystemrun 2 }


fmSystemPSCfg	OBJECT-TYPE
	SYNTAX  INTEGER {
		primary-power(1),
		secondary-power(2),
		primary-and-secondary-power(3)
		}
	ACCESS  read-write
	STATUS  mandatory
	DESCRIPTION "Configuration of power supply"
	::= { fmsystemrun 3 }


fmSystemReset	OBJECT-TYPE
	SYNTAX  INTEGER {
		cold-reset(0),
		warm-reset(1),
		power-up(2),
		meaning-less-value(127)
		}
	ACCESS  read-write
	STATUS  mandatory
	DESCRIPTION "Resetting the CARD.
                    When reading the instance of this
	            object the value has no meaning.
		    cold reset is performed with selftest ,
		    while warm start is performed without
		    selftest"

	::= { fmsystemrun 4 }

fmSystemSelfTestLevel	OBJECT-TYPE
	SYNTAX	INTEGER {
		none(0),
		partial(1),
		full(2),
		extended(3)
		}
	ACCESS	read-write
	STATUS	mandatory
	DESCRIPTION "Type of self test to be
		     executed upon cold-reset"
	::= { fmsystemrun 5 }

fmSystemVersion	OBJECT-TYPE
	SYNTAX	OCTET STRING
	ACCESS	read-only
	STATUS	mandatory
	DESCRIPTION "Version of the station. The version includes
		     station type, hardware version and software version.
		     The string can include CR and LF"
		::= { fmsystemrun 6 }

fmSystemIpAddr		OBJECT-TYPE
	SYNTAX	IpAddress
	ACCESS	read-only
	STATUS  mandatory
	DESCRIPTION "IP address of the agent"
	::= { fmsystemrun 7 }

fmSystemIPNetMask	OBJECT-TYPE
	SYNTAX	IpAddress
	ACCESS	read-only
	STATUS	mandatory
	DESCRIPTION "IP Network Mask"
	::= { fmsystemrun 8 }

fmSystemIPDefGway	OBJECT-TYPE
	SYNTAX	IpAddress
	ACCESS	read-only
	STATUS	mandatory
	DESCRIPTION "Default Gateway Address"
	::= { fmsystemrun 9 }

fmSystemFileServer     OBJECT-TYPE
        SYNTAX  IpAddress
        ACCESS  read-write
        STATUS  mandatory
        DESCRIPTION "IP address to which a TFTP for boot is sent."
        ::= { fmsystemrun 10 }

fmSystemBootFile       OBJECT-TYPE
        SYNTAX  OCTET STRING
        ACCESS  read-only
        STATUS  mandatory
        DESCRIPTION "Path and file name that is
                   sent as a TFTP request"
        ::= { fmsystemrun 11 }

fmSystemBootMode       OBJECT-TYPE
        SYNTAX  INTEGER {
                internal-memory(1),
                bootp(2)
                }
        ACCESS  read-only
        STATUS  deprecated
        DESCRIPTION "Method for booting"
        ::= { fmsystemrun 12 }

fmSystemDownLoad   OBJECT-TYPE
        SYNTAX  INTEGER {
                download(1),
		meaning-less-value(127)
                }
        ACCESS  read-write
        STATUS  mandatory
        DESCRIPTION "Downloading the EDB.
                     When reading the instance of this
	             object the value has no meaning."
        ::= { fmsystemrun 13 }

fmSystemSlipIpAddr          OBJECT-TYPE
        SYNTAX  IpAddress
        ACCESS  read-only
        STATUS  mandatory
        DESCRIPTION "SLIP IP address.
	            This is object is available
		    only when slip interface exist "
        ::= { fmsystemrun 14 }

fmSystemSlipIPNetMask       OBJECT-TYPE
        SYNTAX  IpAddress
        ACCESS  read-only
        STATUS  mandatory
        DESCRIPTION "SLIP IP Network Mask
	            This is object is available
		    only when slip interface exist "
        ::= { fmsystemrun 15 }

fmSystemSlipBaudRate OBJECT-TYPE
        SYNTAX  INTEGER {
                baud1200(0),
                baud2400(1),
                baud4800(2),
                baud9600(3),
                baud19200(4),
                baud38400(5)
                }
	 
        ACCESS  read-only
        STATUS  mandatory
        DESCRIPTION "SLIP Baud rate
 	             This is object is available
		     only when slip interface exist "
        ::= { fmsystemrun 16 }

fmSystemSlipParity   OBJECT-TYPE
        SYNTAX  INTEGER {
                none(0),
                odd(1),
                even(2)
                }
        ACCESS  read-only
        STATUS  mandatory
        DESCRIPTION "SLIP Parity
	             This is object is available
		     only when slip interface exist "
        ::= { fmsystemrun 17 }

fmSystemSlipStopBits	OBJECT-TYPE
        SYNTAX  INTEGER {
                one(0),
                two(1)
                }
        ACCESS  read-only
        STATUS  mandatory
        DESCRIPTION "SLIP Stop Bits 
	             This is object is available
		     only when slip interface exist "
        ::= { fmsystemrun 18 }


------------------------------------------------
--  System Group Permanent
------------------------------------------------


pfmSystemIpAddr		OBJECT-TYPE
	SYNTAX	IpAddress
	ACCESS	read-write
	STATUS  mandatory
	DESCRIPTION "IP address of the agent"
	::= { fmsystemperm 7 }

pfmSystemIPNetMask	OBJECT-TYPE
	SYNTAX	IpAddress
	ACCESS	read-write
	STATUS	mandatory
	DESCRIPTION "IP Network Mask"
	::= { fmsystemperm 8 }

pfmSystemIPDefGway	OBJECT-TYPE
	SYNTAX	IpAddress
	ACCESS	read-write
	STATUS	mandatory
	DESCRIPTION "Default Gateway Address"
	::= { fmsystemperm 9 }

pfmSystemFileServer	OBJECT-TYPE
	SYNTAX  IpAddress
	ACCESS  read-write
	STATUS  mandatory
	DESCRIPTION "IP address to which a TFTP for boot is sent."
	::= { fmsystemperm 10 }

pfmSystemBootFile	OBJECT-TYPE
	SYNTAX  OCTET STRING
	ACCESS  read-write
	STATUS  mandatory
	DESCRIPTION "Path and file name that is 
		   sent as a TFTP request"
	::= { fmsystemperm 11 }

pfmSystemBootMode	OBJECT-TYPE
	SYNTAX  INTEGER {
		internal-memory(1),
		bootp(2)
		}
	ACCESS  read-write
	STATUS  mandatory
	DESCRIPTION "Method for booting"
	::= { fmsystemperm 12 }


pfmSystemReadCommunity	OBJECT-TYPE
	SYNTAX	OCTET STRING
	ACCESS	read-write
	STATUS  mandatory
	DESCRIPTION "Community string for reading
                    When reading the instance of this
                    object the value has no meaning."
	::= { fmsystemperm 13 }

pfmSystemWriteCommunity	OBJECT-TYPE
	SYNTAX	OCTET STRING
	ACCESS	read-write
	STATUS	mandatory
	DESCRIPTION "Community string for writing
                    When reading the instance of this
                    object the value has no meaning."
	::= { fmsystemperm 14 }
	
pfmSystemSlipIpAddr          OBJECT-TYPE
        SYNTAX  IpAddress
        ACCESS  read-write
        STATUS  mandatory
        DESCRIPTION "SLIP IP address 
                     This is object is available
	             only when slip interface exist "
        ::= { fmsystemperm 15 }

pfmSystemSlipIPNetMask       OBJECT-TYPE
        SYNTAX  IpAddress
        ACCESS  read-write
        STATUS  mandatory
        DESCRIPTION "SLIP IP Network Mask
                     This is object is available
	             only when slip interface exist "
        ::= { fmsystemperm 16 }

	
pfmSystemSlipBaudRate OBJECT-TYPE
        SYNTAX  INTEGER {
                baud1200(0),
                baud2400(1),
                baud4800(2),
                baud9600(3),
                baud19200(4),
                baud38400(5)
                }
        ACCESS  read-write
        STATUS  mandatory
        DESCRIPTION "SLIP Baud rate 
                     This is object is available
	             only when slip interface exist "
        ::= { fmsystemperm 17 }


pfmSystemSlipParity   OBJECT-TYPE
        SYNTAX  INTEGER {
                none(0),
                odd(1),
                even(2)
                }
        ACCESS  read-write
        STATUS  mandatory
        DESCRIPTION "SLIP Parity 
                     This is object is available
	             only when slip interface exist "
        ::= { fmsystemperm 18 }

pfmSystemSlipStopBits    OBJECT-TYPE
        SYNTAX  INTEGER {
                one(0),
                two(1)
                }
        ACCESS  read-write
        STATUS  mandatory
        DESCRIPTION "SLIP Stop Bits 
                     This is object is available
	             only when slip interface exist "
        ::= { fmsystemperm 19 }

------------------------------------------------

-- Slot Group Runtime
------------------------------------------------

fmSlotMasterClear  	OBJECT-TYPE
	SYNTAX	INTEGER
	ACCESS	read-write
	STATUS	mandatory
	DESCRIPTION "Upon writing, performs a master
		     clear command on all the slots.
                   When reading the instance of this
	           object the value has no meaning."
		     
		     
	::= { fmslot 1 }

fmSlotTable	OBJECT-TYPE
	SYNTAX  SEQUENCE OF FmSlotEntry
	ACCESS  not-accessible
	STATUS  mandatory
	::= { fmslot 2 }

fmSlotEntry	OBJECT-TYPE
	SYNTAX  FmSlotEntry
	ACCESS  not-accessible
	STATUS  mandatory
	INDEX   { fmSlotIndex }
	::= { fmSlotTable 1 }


FmSlotEntry ::= SEQUENCE {
	fmSlotIndex
		INTEGER,
        fmSlotID
		INTEGER,
	fmSlotDescr
		OCTET STRING,
	fmSlotInfo
		OCTET STRING,
	fmSlotStatus
		OCTET STRING,
	fmSlotPrevStatus
		OCTET STRING,
	fmSlotRLBSet
		INTEGER,
	fmSlotRLBClear
		INTEGER,
	fmSlotExpCode
		INTEGER,
	fmSlotTrapMask
		INTEGER,
	pfmSlotTrapMask
		INTEGER,
        fmSlotIpAddr
                IpAddress

	}

fmSlotIndex	OBJECT-TYPE
	SYNTAX  INTEGER
	ACCESS  read-only
	STATUS  mandatory
	DESCRIPTION "Slot Number"
	::= { fmSlotEntry 1 }

fmSlotID	OBJECT-TYPE
	SYNTAX  INTEGER {
		unconfig(0),
		empty(1),
		cc832-10(2),
		cc832-12(3),
		cc832-20(4),
		cc832-31(5),
		cc832-32(6),
		cc832-41(7),
		cc832-42(8),
		cc832-44(9),
		cc832-46A(10),
		cc892-832(65537),
		lc322(65540),
		cc892-201(65544),
		cc892-202(65545),
		cc892-214(65548),
		cc892-321(65552),
		cc892-46B(65553),
		cc892-301(65560),
		cc892-303(65562),
		cc892-308(65563),
		cc892-233(65568),
		cc892-260(65576),
		cc892-427(65580),
		sw892-11X(65584),
		cc892-432(65588),
		cc892-420(65589),
		cc892-421(65591),
		cc892-422(65590),
		cc892-401(65592),
		cc892-240(65594),
		cc892-241(65595),
		cc892-211(65550),
		cc892-212(65551),
		lc303(65566),
		lc308(65567),
		lc312(65578),
                cc832-10-ID(65541),
                cc832-12-ID(65542),
                cc832-20-ID(65543),
                cc832-41-ID(65557),
                cc832-42-ID(65558),
                cc832-44-ID(65559),
		general-smartcard(131072),
		lc308-129(131073),
		lc303-129(131075),
		lc312-129(131077)
	}
	ACCESS  read-write
	STATUS  mandatory
	DESCRIPTION "ID of the card in the slot"
	::= { fmSlotEntry 2 }

fmSlotDescr	OBJECT-TYPE
	SYNTAX  OCTET STRING
	ACCESS  read-only
	STATUS  mandatory
	DESCRIPTION "Ascii string. Description
		   of the card"
	::= { fmSlotEntry 3 }

fmSlotInfo	OBJECT-TYPE
	SYNTAX	OCTET STRING
	ACCESS  read-write
	STATUS  mandatory
	DESCRIPTION "User general info for the slot.
		     Can be the use of that slot, its
		     location etc..."
	::= { fmSlotEntry 4 }

fmSlotStatus	OBJECT-TYPE
	SYNTAX  OCTET STRING
	ACCESS  read-only
	STATUS  mandatory
	DESCRIPTION "8 bytes. 60 status bits of
		the card. For more information about
		the meaning of the status, read the
		specific user manual of each card.
		The channel leds are encoded into
		2 bytes." 
	::= { fmSlotEntry 5 }

fmSlotPrevStatus	OBJECT-TYPE
	SYNTAX  OCTET STRING
	ACCESS  read-only
	STATUS  mandatory
	DESCRIPTION "8 bytes. Previous 60 status
		   bits of the card. This
		   object id is used mainly
		   for traps (see Card Trap)"
	::= { fmSlotEntry 6 }

fmSlotRLBSet	OBJECT-TYPE
	SYNTAX  INTEGER
	ACCESS  read-write
	STATUS  mandatory
	DESCRIPTION "Argument: 1 - 4. Perform a
		   RLB set operation on the
   		   channel passed as argument.
                   When reading the instance of this
	           object the value has no meaning."
	::= { fmSlotEntry 7 }

fmSlotRLBClear	OBJECT-TYPE
	SYNTAX  INTEGER
	ACCESS  read-write
	STATUS  mandatory
	DESCRIPTION "Argument: 1 - 4. Perform a
		   RLB clear operation on the
		   channel passed as argument.
                   When reading the instance of this
	           object the value has no meaning."
	::= { fmSlotEntry 8 }

fmSlotExpCode	OBJECT-TYPE
	SYNTAX  INTEGER
	ACCESS  read-write
	STATUS  mandatory
	DESCRIPTION "Perform an expanded command
                     on the slot. For expanded codes,
		     see specific card user manual.
                     When reading the instance of this
	             object the value has no meaning.
		     
		     Extended command codes for NDS cards
		     ------------------------------------

		     1. CC892.303 (Ethernet)
		     
		        Code (Dec/Hex)       Command
			-----------------------------------
			02/02		     Detach Port 13
			03/03		     Attach Port 13
			04/04		     Detach Port 01
			05/05		     Attach Port 01
			06/06		     Detach Port 02
			07/07		     Attach Port 02
			08/08		     Detach Port 03
			09/09		     Attach Port 03
			10/0A		     Detach Port 04
			11/0B		     Attach Port 04
			12/0C		     Detach Port 05
			13/0D		     Attach Port 05
			14/0E		     Detach Port 06
			15/0F		     Attach Port 06
			16/10		     Detach Port 07
			17/11		     Attach Port 07
			18/12		     Detach Port 08
			19/13		     Attach Port 08
			20/14		     Detach Port 09
			21/15		     Attach Port 09
			22/16		     Detach Port 10
			23/17		     Attach Port 10
			24/18		     Detach Port 11
			25/19		     Attach Port 11
			26/1A		     Detach Port 12
			27/1B		     Attach Port 12
			28/1C		     Detach All Ports
			29/1D		     Attach All Ports
			30/1E		     Reset Card       
			31/1F		     Link Select   

			======================================================



		     2. CC892.308 (Ethernet)
		     
		        Code (Dec/Hex)       Command
			-----------------------------------
			02/02		     Detach Port 01
			03/03		     Attach Port 01
			04/04		     Detach Port 02
			05/05		     Attach Port 02
			06/06		     Detach Port 03
			07/07		     Attach Port 03
			08/08		     Detach Port 04
			09/09		     Attach Port 04
			10/0A		     Detach Port 05
			11/0B		     Attach Port 05
			12/0C		     Detach Port 06
			13/0D		     Attach Port 06
			14/0E		     Detach Port 07
			15/0F		     Attach Port 07
			16/10		     Detach Port 08
			17/11		     Attach Port 08
			...
			28/1C		     Detach All Ports
			29/1D		     Attach All Ports
			30/1E		     Reset Card       
			31/1F		     Link Select

			================================================

		     3. CC892.322 (Token-ring)

			Module 323
			----------
		     
		        Code (Dec/Hex)       Command
			-----------------------------------
			02/02		     Detach Port 01
			03/03		     Attach Port 01
			04/04		     Detach Port 02
			05/05		     Attach Port 02
			06/06		     Detach Port 03
			07/07		     Attach Port 03
			08/08		     Detach Port 04
			09/09		     Attach Port 04
			10/0A		     Detach Port 05
			11/0B		     Attach Port 05
			12/0C		     Detach Port 06
			13/0D		     Attach Port 06

			18/12		     Detach Port 07
			19/13		     Attach Port 07
			20/14		     Detach Port 08
			21/15		     Attach Port 08
			22/16		     Detach Port 19
			23/17		     Attach Port 19
			24/18		     Detach Port 10
			25/19		     Attach Port 10
			26/1A		     Detach Port 11
			27/1B		     Attach Port 11
			28/1C		     Detach Port 12
			29/1D		     Attach Port 12

			30/1E		     Reset Card

			34/22		     Detach Port 13
			35/23		     Attach Port 13
			36/24		     Detach Port 14
			37/25		     Attach Port 14
			38/26		     Detach Port 15
			39/27		     Attach Port 15
			40/28		     Detach Port 16
			41/29		     Attach Port 16
			42/2A		     Detach Port 17
			43/2B		     Attach Port 17
			44/2C		     Detach Port 18
			45/2D		     Attach Port 18

			50/32		     Detach Port 19
			51/33		     Attach Port 19
			52/34		     Detach Port 20
			53/35		     Attach Port 20
			54/36		     Detach Port 21
			55/37		     Attach Port 21
			56/38		     Detach Port 22
			57/39		     Attach Port 22
			58/3A		     Detach Port 23
			59/3B		     Attach Port 23
			60/3C		     Detach Port 24
			61/3D		     Attach Port 24

			77/4D		     Detach All Ports
			79/4F		     Attach All Ports

			========================================================

			Module 325
			----------

			30/1E		     Reset Card

			80/50  		     Detach Local Port 1 (channel 1)
			81/51 		     Attach Local Port 1 (channel 1)
			82/52  		     Detach Local Port 2 (channel 1)
			83/53 		     Attach Local Port 2 (channel 1)

			88/58  		     Detach Local Port 1 (channel 3)
			89/59 		     Attach Local Port 1 (channel 3)
			90/5A  		     Detach Local Port 2 (channel 3)
			91/5B 		     Attach Local Port 2 (channel 3)

			77/4D		     Detach All Ports
			79/4F		     Attach All Ports


		     4. CC892.427 (Voice)
		     
		        Code (Dec/Hex)       Command
			-----------------------------------
			04/04		     Loopback OFF on Port 1
			05/05		     Loopback ON on Port 1
			06/06		     Loopback OFF on Port 2
			07/07		     Loopback ON on Port 2
			08/08		     Loopback OFF on Port 3
			09/09		     Loopback ON on Port 3
			10/0A		     Loopback OFF on Port 4
			11/0B		     Loopback ON on Port 4
			12/0C		     Loopback OFF on Port 5
			13/0D		     Loopback ON on Port 5
			14/0E		     Loopback OFF on Port 6
			15/0F		     Loopback ON on Port 6
			16/10		     Loopback OFF on Port 7
			17/11		     Loopback ON on Port 7
			18/12		     Loopback OFF on Port 8
			19/13		     Loopback ON on Port 8
			20/14		     Loopback OFF on Port 9
			21/15		     Loopback ON on Port 9
			22/16		     Loopback OFF on Port 10
			23/17		     Loopback ON on Port 10
			24/18		     Loopback OFF on Port 11
			25/19		     Loopback ON on Port 11
			26/1A		     Loopback OFF on Port 12
			27/1B		     Loopback ON on Port 12
			28/1C		     Loopback OFF on Port 13
			29/1D		     Loopback ON on Port 13
			30/1E		     Loopback OFF on Port 14
			31/1F		     Loopback ON on Port 14
			32/20		     Loopback OFF on Port 15
			33/21		     Loopback ON on Port 15
			34/22		     Loopback OFF on Port 16
			35/23		     Loopback ON on Port 16
			37/25		     Loopback ALL on Ports 1-8
			39/27		     Loopback ALL on Ports 9-16
			40/28		     Alternate Mode on Channel Module #1
			41/29		     Normal Mode on Channel Module #1
			42/2A		     Alternate Mode on Channel Module #2
			43/2B		     Normal Mode on Channel Module #2
			45/2D		     Configuration Load Module #1
			47/2F		     Configuration Load Module #2

			======================================================

			"
	::= { fmSlotEntry 9 }
				

fmSlotTrapMask	OBJECT-TYPE
	SYNTAX	INTEGER {
		no-mask(0),
		mask(1)
		}
	ACCESS	read-write
	STATUS  mandatory
	DESCRIPTION "When the value is 1, no more traps
		     from that slot are sent, until next reset.
		     (temporary mask)"
	::= { fmSlotEntry 10 }

	
pfmSlotTrapMask	OBJECT-TYPE
	SYNTAX	INTEGER {
		no-mask(0),
		mask(1)
		}
	ACCESS	read-write
	STATUS  mandatory
	DESCRIPTION "When the value is 1, no more traps for that slot
	will be sent, starting after next reset (permanent mask)"
	::= { fmSlotEntry 11 }

fmSlotIpAddr          OBJECT-TYPE
        SYNTAX  IpAddress
        ACCESS  read-only
        STATUS  mandatory
        DESCRIPTION " IP address of a channel card.
                    This is object is available
                    only for channel cards which have their
                    own IP addresses (e.g., LC303/129)"
        ::= { fmSlotEntry 12 }


------------------------------------------------
-- Logic Unit Group Runtime
------------------------------------------------

fmLUID		OBJECT-TYPE
	SYNTAX  INTEGER {
		unconfig(0),
		none(1),
		lu100(2),
		lu101(3),
		lu102(4),
		lu103(5),
		lu104(6),
		lu105(7),
		lu106(8),
		lu107(9),
		lu108(10)
		}
	ACCESS  read-write
	STATUS  mandatory
	DESCRIPTION "Logic unit ID"
	::= { fmlu 1 }

fmLUDescr	OBJECT-TYPE
	SYNTAX  OCTET STRING
	ACCESS  read-only
	STATUS  mandatory
	DESCRIPTION "Ascii string. Description
		   of the logic unit"
	::= { fmlu 2 }

fmLUStatus	OBJECT-TYPE
	SYNTAX  OCTET STRING
	ACCESS  read-only
	STATUS  mandatory
	DESCRIPTION "One byte of LU status"
	::= { fmlu 3 }


fmLULinkSelect	OBJECT-TYPE
	SYNTAX  INTEGER {
		main-link(0),
		sec-link(1)
		}
	ACCESS  read-write
	STATUS  mandatory
	DESCRIPTION "Setup LU link."
 	::= { fmlu 4 }

fmLULoopBackSet	OBJECT-TYPE
	SYNTAX	INTEGER
	ACCESS	read-write
	STATUS	mandatory
	DESCRIPTION "Upon writing, performs LLB command.
                     When reading the instance of this 
                     object the value has no meaning."
	::= { fmlu 5 }

fmLULoopBackClr	OBJECT-TYPE
	SYNTAX	INTEGER
	ACCESS	read-write
	STATUS	mandatory
	DESCRIPTION "Upon writing, clear LLB command.
                     When reading the instance of this
	             object the value has no meaning."
	::= { fmlu 6 }

fmLUTrapMask	OBJECT-TYPE
	SYNTAX	INTEGER {
		no-mask(0),
		mask(1)
		}
	ACCESS	read-write
	STATUS  mandatory
	DESCRIPTION "When the value is 1, no more traps
		     from the LU are sent, until next reset.
		     (temporary mask)"
	::= { fmlu 7 }

pfmLUTrapMask	OBJECT-TYPE
	SYNTAX	INTEGER {
		no-mask(0),
		mask(1)
		}
	ACCESS	read-write
	STATUS  mandatory
	DESCRIPTION "When the value is 1, no more traps for the LU
	will be sent, starting after next reset (permanent mask)"
	::= { fmlu 8 }



------------------------------------------------
--  Diagnostic Group
------------------------------------------------

fmDiagConfig	OBJECT-TYPE
	SYNTAX	OCTET STRING
	ACCESS	read-only	
	STATUS	mandatory
	DESCRIPTION "Version of the station. The version includes
		    station type, hardware version and software version.
		    The string can include CR and LF"
		::= { fmdiag 1 }


fmDiagTrapInfo	OBJECT-TYPE
	SYNTAX	DisplayString (SIZE (0..255))
	ACCESS	read-only
	STATUS  mandatory
	DESCRIPTION "Used for generic traps. The first word
		is the trap code. The rest of the string is
		the extra information. Contains CR and LF char."
	::= { fmdiag 2 }


fmDiagFaultTable  OBJECT-TYPE
        SYNTAX  SEQUENCE OF FmDiagFaultEntry 
        ACCESS  not-accessible
	STATUS  optional
  	 DESCRIPTION "Table of fault reports from the agent"
	 ::= { fmdiag 3 }


fmDiagFaultEntry  OBJECT-TYPE
        SYNTAX  FmDiagFaultEntry
	ACCESS  not-accessible
	STATUS  optional
  	INDEX   { fmDiagFaultIndex}
	::=     { fmDiagFaultTable 1 }


FmDiagFaultEntry ::= SEQUENCE {
        fmDiagFaultIndex
	        INTEGER,
        fmDiagFaultReport
	        OCTET STRING
	}


fmDiagFaultIndex OBJECT-TYPE
        SYNTAX  INTEGER
	ACCESS  read-only
	STATUS  optional
        DESCRIPTION "The fault index in the
  			      fault table"
        ::= { fmDiagFaultEntry 1 }			      		      
						
fmDiagFaultReport	OBJECT-TYPE
	SYNTAX	DisplayString  (SIZE (0..255))
	ACCESS	read-only
	STATUS	optional
  	DESCRIPTION "Get the faults detected by the agent"
        ::= { fmDiagFaultEntry 2 }			      		      

fmDiagDebug     	OBJECT-TYPE
	SYNTAX	INTEGER {
		normal-mode(0),
		debug-mode(1)
		}
	ACCESS	read-write
	STATUS  mandatory
	DESCRIPTION "This object is for factory use only. Users must not
		     write into this variable or improper operation
		     can occur."
	::= { fmdiag 4 }


  -- *********************************************************
  -- **                                                     **
  -- **                                                     **
  -- **        T R A P          D E F I N I T I O N S       **
  -- **                                                     **
  -- **                                                     **
  -- *********************************************************


fmPowerSupplyFail	TRAP-TYPE	
	ENTERPRISE fm800
	VARIABLES { fmSystemPSOper }
        DESCRIPTION "This trap message is generated as soon
		as one of the power supply has failed"
	::= 1

fmPrimaryPowerSupplyOK	TRAP-TYPE
	ENTERPRISE fm800
	VARIABLES { fmSystemPSOper }
	DESCRIPTION "This trap is issued when primary power
		supply return to work"
	::= 2

fmSecondPowerSupplyOK	TRAP-TYPE
	ENTERPRISE fm800
	VARIABLES { fmSystemPSOper }
	DESCRIPTION "This trap is issued when second power
		supply return to work"
	::= 3

fmPowerSupplyChangeConfig	TRAP-TYPE
	ENTERPRISE fm800
	VARIABLES { fmSystemPSCfg,
		    fmSystemPSOper
		  }
	DESCRIPTION "Issued when a change in the configuration
		of the power supply is done"
	::= 4

fmLUOutOfSync		TRAP-TYPE
	ENTERPRISE fm800
	VARIABLES { fmLUID,
		    fmLUStatus
		  }
	DESCRIPTION "Issued when the Logic unit goes
		out of synchronization"
	::= 7

fmLUReturnToSync	TRAP-TYPE
	ENTERPRISE fm800
	VARIABLES { fmLUID,
		    fmLUStatus
		  }
	DESCRIPTION "Issues as soon as the logic unit
		returns to synchronization"
	::= 8

fmLUPassToMain		TRAP-TYPE
	ENTERPRISE fm800
	VARIABLES { fmLUID,
		    fmLUStatus
		  }
	DESCRIPTION "Issues as soon as the logic unit
		pass to main link"
	::= 9

fmLUPassToSecond	TRAP-TYPE
	ENTERPRISE fm800
	VARIABLES { fmLUID,
		    fmLUStatus
		  }
	DESCRIPTION "Issues as soon as the logic unit
		pass to second link"
	::= 10

fmLUPrimaryLinkFail	TRAP-TYPE
	ENTERPRISE fm800
	VARIABLES { fmLUID,
		    fmLUStatus
		  }
	DESCRIPTION "When primary link of the logic unit  fails
		 this trap is issued"
	::= 11

fmLUPrimaryLinkOK	TRAP-TYPE
	ENTERPRISE fm800
	VARIABLES { fmLUID,
		    fmLUStatus
		  }
	DESCRIPTION "When primary link of the logic unit  fails
		 this trap is issued"
	::= 12

fmLUSecondLinkFail	TRAP-TYPE
	ENTERPRISE fm800
	VARIABLES { fmLUID,
		    fmLUStatus
		  }
	DESCRIPTION "When second link of the logic unit  fails
		 this trap is issued"
	::= 13

fmLUSecondLinkOK	TRAP-TYPE
	ENTERPRISE fm800
	VARIABLES { fmLUID,
		    fmLUStatus
		  }
	DESCRIPTION "When second link of the logic unit  fails
		 this trap is issued"
	::= 14

	
fmLULLBOn		TRAP-TYPE
	ENTERPRISE fm800
	VARIABLES { fmLUID,
		    fmLUStatus
		  }
	DESCRIPTION "When the logic unit enters LLB mode"
	::= 15

fmLULLBOff		TRAP-TYPE
	ENTERPRISE fm800
	VARIABLES { fmLUID,
		    fmLUStatus
		  }
	DESCRIPTION "When the logic unit exits LLB mode"
	::= 16

fmLUChangeConfig		TRAP-TYPE
	ENTERPRISE fm800
	VARIABLES { fmLUID,
		    fmLUStatus
		  }
	DESCRIPTION "Issues when a change in the LU configuration
		is done"
	::= 20

fmSlotTrap		TRAP-TYPE
	ENTERPRISE fm800
	VARIABLES { fmSlotIndex,
		    fmSlotID,
		    fmSlotStatus,
		    fmSlotPrevStatus }
	DESCRIPTION "Generated when a significant status has
		changed in a slot. By xoring the 2 statuses,
		the NMS can identify the cause of the trap."
	::= 25

fmSlotChangeConfig	TRAP-TYPE
	ENTERPRISE fm800
	VARIABLES { fmSlotIndex,
		    fmSlotID,
		    fmSlotStatus
		   }
	DESCRIPTION "Issued when the system detects
		 changes in its slots configuration"
	::= 26

fmDiagGenericTrap	TRAP-TYPE
	ENTERPRISE fm800
	VARIABLES { fmDiagTrapInfo }
	DESCRIPTION "Generic Trap information"
	::= 30




  
END
