Nortel-Magellan-Passport-BgpMIB
DEFINITIONS ::= BEGIN



IMPORTS

      OBJECT-TYPE
   FROM RFC-1212

      IpAddress
   FROM RFC1155-SMI

      passportMIBs
   FROM Nortel-Magellan-Passport-UsefulDefinitionsMIB

      Counter32,
      DisplayString,
      StorageType,
      RowStatus,
      Gauge32,
      Integer32,
      Unsigned32
   FROM Nortel-Magellan-Passport-StandardTextualConventionsMIB

      AsciiString,
      Hex,
      NonReplicated,
      HexString,
      IntegerSequence
   FROM Nortel-Magellan-Passport-TextualConventionsMIB

      vrIpIndex,
      vrIp
   FROM Nortel-Magellan-Passport-IpMIB

      vrIndex
   FROM Nortel-Magellan-Passport-VirtualRouterMIB;




-- LAST-UPDATED   "9906090000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     Bgp Enterprise MIB."

bgpMIB OBJECT IDENTIFIER ::= { passportMIBs 141 }










-- Vr/<string> Ip BorderGatewayProtocol
-- This component is used to run the Border Gateway Protocol for IP.

vrIpBgp OBJECT IDENTIFIER ::= { vrIp 21 }



vrIpBgpRowStatusTable OBJECT-TYPE
   SYNTAX     SEQUENCE OF VrIpBgpRowStatusEntry
   ACCESS     not-accessible
   STATUS     mandatory
   DESCRIPTION
     "This entry controls the addition and deletion of 
      vrIpBgp components."
::= { vrIpBgp 1 }

vrIpBgpRowStatusEntry OBJECT-TYPE
   SYNTAX     VrIpBgpRowStatusEntry
   ACCESS     not-accessible
   STATUS     mandatory
   DESCRIPTION
     "A single entry in the table represents a single 
      vrIpBgp component."
   INDEX {
      vrIndex,
      vrIpIndex,
      vrIpBgpIndex }
::= { vrIpBgpRowStatusTable 1 }

VrIpBgpRowStatusEntry ::= SEQUENCE {
   vrIpBgpRowStatus
      RowStatus,
   vrIpBgpComponentName
      DisplayString,
   vrIpBgpStorageType
      StorageType,
   vrIpBgpIndex
      NonReplicated }

vrIpBgpRowStatus OBJECT-TYPE
   SYNTAX     RowStatus 
   ACCESS     read-write
   STATUS     mandatory
   DESCRIPTION
     "This variable is used as the basis for SNMP naming of
      vrIpBgp components.
      These components can be added and deleted."
::= { vrIpBgpRowStatusEntry 1 }

vrIpBgpComponentName OBJECT-TYPE
   SYNTAX     DisplayString 
   ACCESS     read-only
   STATUS     mandatory
   DESCRIPTION
     "This variable provides the component's string name for
      use with the ASCII Console Interface"
::= { vrIpBgpRowStatusEntry 2 }

vrIpBgpStorageType OBJECT-TYPE
   SYNTAX     StorageType 
   ACCESS     read-only
   STATUS     mandatory
   DESCRIPTION
     "This variable represents the storage type value for the
      vrIpBgp tables."
::= { vrIpBgpRowStatusEntry 4 }

vrIpBgpIndex OBJECT-TYPE
   SYNTAX     NonReplicated 
   ACCESS     not-accessible
   STATUS     mandatory
   DESCRIPTION
     "This variable represents the index for the vrIpBgp tables."
::= { vrIpBgpRowStatusEntry 10 }

vrIpBgpProvTable OBJECT-TYPE
   SYNTAX     SEQUENCE OF VrIpBgpProvEntry
   ACCESS     not-accessible
   STATUS     mandatory
   DESCRIPTION
     "This group contains the provisionable attributes for the Bgp 
      component."
::= { vrIpBgp 100 }

vrIpBgpProvEntry OBJECT-TYPE
   SYNTAX     VrIpBgpProvEntry
   ACCESS     not-accessible
   STATUS     mandatory
   DESCRIPTION
     "An entry in the vrIpBgpProvTable."
   INDEX {
      vrIndex,
      vrIpIndex,
      vrIpBgpIndex }
::= { vrIpBgpProvTable 1 }

VrIpBgpProvEntry ::= SEQUENCE {
   vrIpBgpBgpIdentifier
      IpAddress,
   vrIpBgpLocalAs
      Unsigned32,
   vrIpBgpDefaultLocalPreference
      Unsigned32,
   vrIpBgpDefaultMultiExitDisc
      Unsigned32,
   vrIpBgpRouteThrottleLimit
      Unsigned32,
   vrIpBgpRouteThrottleInter
      Unsigned32,
   vrIpBgpRouteReflector
      INTEGER,
   vrIpBgpRouteReflectorCluster
      IpAddress }

vrIpBgpBgpIdentifier OBJECT-TYPE
   SYNTAX     IpAddress 
   ACCESS     read-write
   STATUS     mandatory
   DESCRIPTION
     "This attribute specifies the Bgp Identifier of this Bgp component 
      instance. It is picked from the IP address space, and should follow 
      the same rule as choosing an unique IP address for IpPort."
::= { vrIpBgpProvEntry 1 }

vrIpBgpLocalAs OBJECT-TYPE
   SYNTAX     Unsigned32 (0..65535)
   ACCESS     read-write
   STATUS     mandatory
   DESCRIPTION
     "This attribute specifies the autonomous system identifier 
      for this Bgp component instance."
::= { vrIpBgpProvEntry 2 }

vrIpBgpDefaultLocalPreference OBJECT-TYPE
   SYNTAX     Unsigned32 (0..4294967295)
   ACCESS     read-write
   STATUS     mandatory
   DESCRIPTION
     "This attribute specifies this Bgp component instance's default 
      degree of preference for routes. It can be overridden by the 
      localPreference provisioned in ImportPolicy. A higher value 
      indicates a more preferred route."
   DEFVAL     { 144 }
::= { vrIpBgpProvEntry 3 }

vrIpBgpDefaultMultiExitDisc OBJECT-TYPE
   SYNTAX     Unsigned32 (0..4294967295)
   ACCESS     read-write
   STATUS     mandatory
   DESCRIPTION
     "This attribute specifies this Bgp component instance's default metric 
      to discriminate between multiple exit points to the same adjacent 
      autonomous system. It can be overridden by the 
      sendMultiExitDiscToEbgp provisioned in ExportPolicy. A lower 
      value indicates a more preferred route."
   DEFVAL     { 4294967294 }
::= { vrIpBgpProvEntry 4 }

vrIpBgpRouteThrottleLimit OBJECT-TYPE
   SYNTAX     Unsigned32 (1..1000)
   ACCESS     read-write
   STATUS     mandatory
   DESCRIPTION
     "This attribute specifies the maximum number of routes in the IP 
      forwarding table this Bgp component instance will process at one 
      time to decide if a route in the IP forwarding table should be 
      exported to a peer. This limit is used for the throttling and is made 
      configurable because the throttling requirements will be different 
      under different network configurations. The default value is 250."
   DEFVAL     { 250 }
::= { vrIpBgpProvEntry 5 }

vrIpBgpRouteThrottleInter OBJECT-TYPE
   SYNTAX     Unsigned32 (1..30)
   ACCESS     read-write
   STATUS     mandatory
   DESCRIPTION
     "This attribute specifies the interval in seconds, between the 
      processing of the routes in the IP forwarding table to decide if a 
      route in the IP forwarding table should be exported to a peer. This 
      interval is used for the throttling and is made configurable because 
      the throttling requirements will be different under different network 
      configurations. The default value is 5 seconds."
   DEFVAL     { 5 }
::= { vrIpBgpProvEntry 6 }

vrIpBgpRouteReflector OBJECT-TYPE
   SYNTAX     INTEGER  {
                 true(1),
                 false(2) }
   ACCESS     read-write
   STATUS     mandatory
   DESCRIPTION
     "This attribute specifies whether this Bgp instance is a Route 
      Reflector. If the value of this attribute is true, Bgp redistributes 
      routes it learns from an IBGP speaker to other IBGP speakers in the 
      AS. The rule of redistribution depends on the peer type: 1) When a 
      route is learned from a non-client peer, it is redistributed to all the 
      client peers within the cluster. 2) When a route is learned from a 
      client peer, it is redistributed to all the non-client peers and also to 
      the client peers. If the value of this attribute is false, Bgp does not 
      redistribute routes it learns from one IBGP speaker to other IBGP 
      speakers in the AS."
   DEFVAL     { false }
::= { vrIpBgpProvEntry 7 }

vrIpBgpRouteReflectorCluster OBJECT-TYPE
   SYNTAX     IpAddress 
   ACCESS     read-write
   STATUS     mandatory
   DESCRIPTION
     "This attribute identifies the cluster consisting of the Route Reflector 
      and its peer clients. When routeReflector of Bgp is true, value of 
      0.0.0.0 or 255.255.255.255 is invalid; the default value of this 
      attribute is same as bgpIdentifier. For redundancy, a cluster may 
      have more than one Route Reflector; in this case, the value of this 
      attribute of all the Route Reflectors in the same cluster should be 
      same. The value of this attribute is ignored when routeReflector of 
      Bgp is false"
::= { vrIpBgpProvEntry 8 }

vrIpBgpOperTable OBJECT-TYPE
   SYNTAX     SEQUENCE OF VrIpBgpOperEntry
   ACCESS     not-accessible
   STATUS     mandatory
   DESCRIPTION
     "This group contains the operational attributes for the Bgp 
      component."
::= { vrIpBgp 101 }

vrIpBgpOperEntry OBJECT-TYPE
   SYNTAX     VrIpBgpOperEntry
   ACCESS     not-accessible
   STATUS     mandatory
   DESCRIPTION
     "An entry in the vrIpBgpOperTable."
   INDEX {
      vrIndex,
      vrIpIndex,
      vrIpBgpIndex }
::= { vrIpBgpOperTable 1 }

VrIpBgpOperEntry ::= SEQUENCE {
   vrIpBgpTableVersion
      Counter32,
   vrIpBgpInMsgs
      Counter32,
   vrIpBgpInErrors
      Counter32,
   vrIpBgpInErrorMsgs
      Counter32,
   vrIpBgpOutMsgs
      Counter32,
   vrIpBgpOutDiscards
      Counter32,
   vrIpBgpOutErrorMsgs
      Counter32,
   vrIpBgpIndbSize
      Counter32 }

vrIpBgpTableVersion OBJECT-TYPE
   SYNTAX     Counter32 
   ACCESS     read-only
   STATUS     mandatory
   DESCRIPTION
     "This attribute indicates the version of the BGP routing table. It is 
      incremented every time the BGP routing table changes. This 
      counter will wrap to zero once the value exceeds the maximum 
      value."
::= { vrIpBgpOperEntry 2 }

vrIpBgpInMsgs OBJECT-TYPE
   SYNTAX     Counter32 
   ACCESS     read-only
   STATUS     mandatory
   DESCRIPTION
     "This attribute counts the total number of BGP messages received 
      without error. This counter will wrap to zero once the value exceeds 
      the maximum value."
::= { vrIpBgpOperEntry 3 }

vrIpBgpInErrors OBJECT-TYPE
   SYNTAX     Counter32 
   ACCESS     read-only
   STATUS     mandatory
   DESCRIPTION
     "This attribute counts the total number of BGP messages received 
      from all peers that proved to be in error. This counter will wrap to 
      zero once the value exceeds the maximum value."
::= { vrIpBgpOperEntry 4 }

vrIpBgpInErrorMsgs OBJECT-TYPE
   SYNTAX     Counter32 
   ACCESS     read-only
   STATUS     mandatory
   DESCRIPTION
     "This attribute counts the total number of BGP NOTIFICATION 
      messages from all the peers. This counter will wrap to zero once the 
      value exceeds the maximum value."
::= { vrIpBgpOperEntry 5 }

vrIpBgpOutMsgs OBJECT-TYPE
   SYNTAX     Counter32 
   ACCESS     read-only
   STATUS     mandatory
   DESCRIPTION
     "This attribute counts the total number of BGP messages sent to 
      peers. This counter will wrap to zero once the value exceeds the 
      maximum value."
::= { vrIpBgpOperEntry 6 }

vrIpBgpOutDiscards OBJECT-TYPE
   SYNTAX     Counter32 
   ACCESS     read-only
   STATUS     mandatory
   DESCRIPTION
     "This attribute counts the number of BGP messages that were locally 
      generated but were not sent out due to resource limitations within a 
      Bgp instance. This counter will wrap to zero once the value exceeds 
      the maximum value."
::= { vrIpBgpOperEntry 7 }

vrIpBgpOutErrorMsgs OBJECT-TYPE
   SYNTAX     Counter32 
   ACCESS     read-only
   STATUS     mandatory
   DESCRIPTION
     "This attribute counts the BGP NOTIFICATION messages sent to 
      the peers. This counter will wrap to zero once the value exceeds the 
      maximum value."
::= { vrIpBgpOperEntry 8 }

vrIpBgpIndbSize OBJECT-TYPE
   SYNTAX     Counter32 
   ACCESS     read-only
   STATUS     mandatory
   DESCRIPTION
     "This attribute indicates the number of Bgp indb entries under this 
      Bgp component instance."
::= { vrIpBgpOperEntry 9 }

vrIpBgpStateTable OBJECT-TYPE
   SYNTAX     SEQUENCE OF VrIpBgpStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { vrIpBgp 102 }

vrIpBgpStateEntry OBJECT-TYPE
   SYNTAX     VrIpBgpStateEntry
   ACCESS     not-accessible
   STATUS     mandatory
   DESCRIPTION
     "An entry in the vrIpBgpStateTable."
   INDEX {
      vrIndex,
      vrIpIndex,
      vrIpBgpIndex }
::= { vrIpBgpStateTable 1 }

VrIpBgpStateEntry ::= SEQUENCE {
   vrIpBgpAdminState
      INTEGER,
   vrIpBgpOperationalState
      INTEGER,
   vrIpBgpUsageState
      INTEGER }

vrIpBgpAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { vrIpBgpStateEntry 1 }

vrIpBgpOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { vrIpBgpStateEntry 2 }

vrIpBgpUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { vrIpBgpStateEntry 3 }

vrIpBgpAdminControlTable OBJECT-TYPE
   SYNTAX     SEQUENCE OF VrIpBgpAdminControlEntry
   ACCESS     not-accessible
   STATUS     mandatory
   DESCRIPTION
     "This group includes the Administrative Control attribute. This 
      attribute defines the current administrative state of this component."
::= { vrIpBgp 103 }

vrIpBgpAdminControlEntry OBJECT-TYPE
   SYNTAX     VrIpBgpAdminControlEntry
   ACCESS     not-accessible
   STATUS     mandatory
   DESCRIPTION
     "An entry in the vrIpBgpAdminControlTable."
   INDEX {
      vrIndex,
      vrIpIndex,
      vrIpBgpIndex }
::= { vrIpBgpAdminControlTable 1 }

VrIpBgpAdminControlEntry ::= SEQUENCE {
   vrIpBgpSnmpAdminStatus
      INTEGER }

vrIpBgpSnmpAdminStatus OBJECT-TYPE
   SYNTAX     INTEGER  {
                 up(1),
                 down(2),
                 testing(3) }
   ACCESS     read-write
   STATUS     mandatory
   DESCRIPTION
     "The desired state of the interface. The up state indicates the 
      interface is operational and packet forwarding is allowed. The down 
      state indicates the interface is not operational and packet forwarding 
      is unavailable. The testing state indicates that no operational 
      packets can be passed."
   DEFVAL     { up }
::= { vrIpBgpAdminControlEntry 1 }

vrIpBgpOperStatusTable OBJECT-TYPE
   SYNTAX     SEQUENCE OF VrIpBgpOperStatusEntry
   ACCESS     not-accessible
   STATUS     mandatory
   DESCRIPTION
     "This group includes the Operational Status attribute. This attribute 
      defines the current operational state of this component."
::= { vrIpBgp 106 }

vrIpBgpOperStatusEntry OBJECT-TYPE
   SYNTAX     VrIpBgpOperStatusEntry
   ACCESS     not-accessible
   STATUS     mandatory
   DESCRIPTION
     "An entry in the vrIpBgpOperStatusTable."
   INDEX {
      vrIndex,
      vrIpIndex,
      vrIpBgpIndex }
::= { vrIpBgpOperStatusTable 1 }

VrIpBgpOperStatusEntry ::= SEQUENCE {
   vrIpBgpSnmpOperStatus
      INTEGER }

vrIpBgpSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { vrIpBgpOperStatusEntry 1 }


-- Vr/<string> Ip Bgp Peer/<Ip Address>
-- This component identifies the properties of a Bgp peer.
-- The index value of this entry identifies the IP address of that peer. 
-- This component is required for BGP to set up a peer session with 
-- the peer with the IP address identified in the index value.

vrIpBgpPeer OBJECT IDENTIFIER ::= { vrIpBgp 2 }



vrIpBgpPeerRowStatusTable OBJECT-TYPE
   SYNTAX     SEQUENCE OF VrIpBgpPeerRowStatusEntry
   ACCESS     not-accessible
   STATUS     mandatory
   DESCRIPTION
     "This entry controls the addition and deletion of 
      vrIpBgpPeer components."
::= { vrIpBgpPeer 1 }

vrIpBgpPeerRowStatusEntry OBJECT-TYPE
   SYNTAX     VrIpBgpPeerRowStatusEntry
   ACCESS     not-accessible
   STATUS     mandatory
   DESCRIPTION
     "A single entry in the table represents a single 
      vrIpBgpPeer component."
   INDEX {
      vrIndex,
      vrIpIndex,
      vrIpBgpIndex,
      vrIpBgpPeerPeerAddressIndex }
::= { vrIpBgpPeerRowStatusTable 1 }

VrIpBgpPeerRowStatusEntry ::= SEQUENCE {
   vrIpBgpPeerRowStatus
      RowStatus,
   vrIpBgpPeerComponentName
      DisplayString,
   vrIpBgpPeerStorageType
      StorageType,
   vrIpBgpPeerPeerAddressIndex
      IpAddress }

vrIpBgpPeerRowStatus OBJECT-TYPE
   SYNTAX     RowStatus 
   ACCESS     read-write
   STATUS     mandatory
   DESCRIPTION
     "This variable is used as the basis for SNMP naming of
      vrIpBgpPeer components.
      These components can be added and deleted."
::= { vrIpBgpPeerRowStatusEntry 1 }

vrIpBgpPeerComponentName OBJECT-TYPE
   SYNTAX     DisplayString 
   ACCESS     read-only
   STATUS     mandatory
   DESCRIPTION
     "This variable provides the component's string name for
      use with the ASCII Console Interface"
::= { vrIpBgpPeerRowStatusEntry 2 }

vrIpBgpPeerStorageType OBJECT-TYPE
   SYNTAX     StorageType 
   ACCESS     read-only
   STATUS     mandatory
   DESCRIPTION
     "This variable represents the storage type value for the
      vrIpBgpPeer tables."
::= { vrIpBgpPeerRowStatusEntry 4 }

vrIpBgpPeerPeerAddressIndex OBJECT-TYPE
   SYNTAX     IpAddress 
   ACCESS     not-accessible
   STATUS     mandatory
   DESCRIPTION
     "This variable represents the index for the vrIpBgpPeer tables."
::= { vrIpBgpPeerRowStatusEntry 10 }

vrIpBgpPeerProvTable OBJECT-TYPE
   SYNTAX     SEQUENCE OF VrIpBgpPeerProvEntry
   ACCESS     not-accessible
   STATUS     mandatory
   DESCRIPTION
     "This group contains the provisionable attributes for this 
      BGP Peer component"
::= { vrIpBgpPeer 10 }

vrIpBgpPeerProvEntry OBJECT-TYPE
   SYNTAX     VrIpBgpPeerProvEntry
   ACCESS     not-accessible
   STATUS     mandatory
   DESCRIPTION
     "An entry in the vrIpBgpPeerProvTable."
   INDEX {
      vrIndex,
      vrIpIndex,
      vrIpBgpIndex,
      vrIpBgpPeerPeerAddressIndex }
::= { vrIpBgpPeerProvTable 1 }

VrIpBgpPeerProvEntry ::= SEQUENCE {
   vrIpBgpPeerPeerAs
      Unsigned32,
   vrIpBgpPeerLocalAddressConfigured
      IpAddress,
   vrIpBgpPeerKeepAliveConfigured
      Unsigned32,
   vrIpBgpPeerHoldTimeConfigured
      Unsigned32,
   vrIpBgpPeerConnectRetryTime
      Unsigned32,
   vrIpBgpPeerMinAsOrigTime
      Unsigned32,
   vrIpBgpPeerMinRouteAdvTime
      Unsigned32,
   vrIpBgpPeerDefaultInAggMed
      Unsigned32,
   vrIpBgpPeerIsRouteReflectorClient
      INTEGER }

vrIpBgpPeerPeerAs OBJECT-TYPE
   SYNTAX     Unsigned32 (0..65535)
   ACCESS     read-write
   STATUS     mandatory
   DESCRIPTION
     "This attribute specifies the autonomous system identifier of this 
      BGP Peer component. It will be used to verify the autonomous 
      system identifier learned from the peer through the OPEN message. 
      The peer connection will be rejected and a NOTIFICATION 
      message will be sent to the peer if these two numbers don't match."
   DEFVAL     { 0 }
::= { vrIpBgpPeerProvEntry 1 }

vrIpBgpPeerLocalAddressConfigured OBJECT-TYPE
   SYNTAX     IpAddress 
   ACCESS     read-write
   STATUS     mandatory
   DESCRIPTION
     "This attribute specifies the local IP address configured for this Bgp 
      Peer connection. If this attribute is 0.0.0.0, TCP will choose a local 
      IP interface based on the remote IP address of this peer connection 
      and the IP forwarding table. The value chosen is stored in the 
      localAddressUsed attribute under the same Peer component."
   DEFVAL     { '00000000'H }  -- "0.0.0.0"
::= { vrIpBgpPeerProvEntry 2 }

vrIpBgpPeerKeepAliveConfigured OBJECT-TYPE
   SYNTAX     Unsigned32 (0..21845)
   ACCESS     read-write
   STATUS     mandatory
   DESCRIPTION
     "This attribute specifies the configured interval in seconds, between 
      BGP KEEPALIVE message retransmissions. It is used to establish 
      the ratio between keepalive interval and hold time. If this attribute is 
      zero, then the holdTimeConfigured attribute should also be zero, 
      which means that periodic KEEPALIVE messages will not be sent."
   DEFVAL     { 30 }
::= { vrIpBgpPeerProvEntry 3 }

vrIpBgpPeerHoldTimeConfigured OBJECT-TYPE
   SYNTAX     Unsigned32 (0 | 3..65535)
   ACCESS     read-write
   STATUS     mandatory
   DESCRIPTION
     "This attribute specifies the maximum time in seconds, that may 
      elapse without receiving a KEEPALIVE or UPDATE message 
      before the connection is considered down. The hold time must be 
      either zero or at least three seconds. If this attribute is zero, then the 
      keepAliveConfigured attribute should also be zero, which means 
      that periodic KEEPALIVE messages will not be sent."
   DEFVAL     { 90 }
::= { vrIpBgpPeerProvEntry 4 }

vrIpBgpPeerConnectRetryTime OBJECT-TYPE
   SYNTAX     Unsigned32 (1..65535)
   ACCESS     read-write
   STATUS     mandatory
   DESCRIPTION
     "This attribute specifies the time interval in seconds for the 
      ConnectRetry timer. It is the minimum amount of time that must 
      elapse between successive TCP connection retries for establishing 
      BGP peer connection."
   DEFVAL     { 120 }
::= { vrIpBgpPeerProvEntry 5 }

vrIpBgpPeerMinAsOrigTime OBJECT-TYPE
   SYNTAX     Unsigned32 (1..65535)
   ACCESS     read-write
   STATUS     mandatory
   DESCRIPTION
     "This attribute specifies the time interval in seconds for the 
      MinAsOriginationInterval timer. It is the minimum amount of time 
      that must elapse between updates that advertise a change to a route 
      within the local autonomous system to neighboring autonomous 
      systems."
   DEFVAL     { 15 }
::= { vrIpBgpPeerProvEntry 6 }

vrIpBgpPeerMinRouteAdvTime OBJECT-TYPE
   SYNTAX     Unsigned32 (1..65535)
   ACCESS     read-write
   STATUS     mandatory
   DESCRIPTION
     "This attribute specifies the time interval in seconds for the 
      MinRouteAdvertisementInterval timer. Feasible routes received 
      from peers in other autonomous systems may only be re-advertised 
      to peers in other autonomous systems at a rate no greater than 
      MinRouteAdvertisementInterval."
   DEFVAL     { 30 }
::= { vrIpBgpPeerProvEntry 7 }

vrIpBgpPeerDefaultInAggMed OBJECT-TYPE
   SYNTAX     Unsigned32 (0..4294967295)
   ACCESS     read-write
   STATUS     mandatory
   DESCRIPTION
     "This attribute specifies this Bgp Peer component instance's metric 
      for generating a dynamic default route whenever this external bgp 
      peer got established. It is used to prioritize between the dynamic 
      default routes generated by Passport Bgp speakers. If this attribute 
      is not set, Bgp will not generate a dynamic default route. If this 
      attribute is set, Bgp will automatically generate a dynamic default 
      route when the connection established."
   DEFVAL     { 4294967295 }
::= { vrIpBgpPeerProvEntry 8 }

vrIpBgpPeerIsRouteReflectorClient OBJECT-TYPE
   SYNTAX     INTEGER  {
                 true(1),
                 false(2) }
   ACCESS     read-write
   STATUS     mandatory
   DESCRIPTION
     "This attribute specifies whether the peer is a client peer or non-
      client peer of this Bgp instance. The attribute is only meaningful if 
      attribute routeReflector of Bgp is true."
   DEFVAL     { false }
::= { vrIpBgpPeerProvEntry 9 }

vrIpBgpPeerStateTable OBJECT-TYPE
   SYNTAX     SEQUENCE OF VrIpBgpPeerStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { vrIpBgpPeer 11 }

vrIpBgpPeerStateEntry OBJECT-TYPE
   SYNTAX     VrIpBgpPeerStateEntry
   ACCESS     not-accessible
   STATUS     mandatory
   DESCRIPTION
     "An entry in the vrIpBgpPeerStateTable."
   INDEX {
      vrIndex,
      vrIpIndex,
      vrIpBgpIndex,
      vrIpBgpPeerPeerAddressIndex }
::= { vrIpBgpPeerStateTable 1 }

VrIpBgpPeerStateEntry ::= SEQUENCE {
   vrIpBgpPeerAdminState
      INTEGER,
   vrIpBgpPeerOperationalState
      INTEGER,
   vrIpBgpPeerUsageState
      INTEGER }

vrIpBgpPeerAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { vrIpBgpPeerStateEntry 1 }

vrIpBgpPeerOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { vrIpBgpPeerStateEntry 2 }

vrIpBgpPeerUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { vrIpBgpPeerStateEntry 3 }

vrIpBgpPeerOperTable OBJECT-TYPE
   SYNTAX     SEQUENCE OF VrIpBgpPeerOperEntry
   ACCESS     not-accessible
   STATUS     mandatory
   DESCRIPTION
     "This group contains the operational attributes for the Peer 
      component."
::= { vrIpBgpPeer 12 }

vrIpBgpPeerOperEntry OBJECT-TYPE
   SYNTAX     VrIpBgpPeerOperEntry
   ACCESS     not-accessible
   STATUS     mandatory
   DESCRIPTION
     "An entry in the vrIpBgpPeerOperTable."
   INDEX {
      vrIndex,
      vrIpIndex,
      vrIpBgpIndex,
      vrIpBgpPeerPeerAddressIndex }
::= { vrIpBgpPeerOperTable 1 }

VrIpBgpPeerOperEntry ::= SEQUENCE {
   vrIpBgpPeerConnectionState
      INTEGER,
   vrIpBgpPeerBgpIdentifier
      IpAddress,
   vrIpBgpPeerVersionNegotiated
      Unsigned32,
   vrIpBgpPeerHoldTimeNegotiated
      Unsigned32,
   vrIpBgpPeerKeepAliveNegotiated
      Unsigned32,
   vrIpBgpPeerLocalAddressUsed
      IpAddress,
   vrIpBgpPeerLocalPort
      Unsigned32,
   vrIpBgpPeerRemotePort
      Unsigned32,
   vrIpBgpPeerLastError
      HexString,
   vrIpBgpPeerConnectionEstablishedTime
      Gauge32,
   vrIpBgpPeerConnectionEstablishedTransitions
      Counter32,
   vrIpBgpPeerInUpdateElapsedTime
      Gauge32,
   vrIpBgpPeerInMsgs
      Counter32,
   vrIpBgpPeerInUpdates
      Counter32,
   vrIpBgpPeerInErrors
      Counter32,
   vrIpBgpPeerInErrorMsgs
      Counter32,
   vrIpBgpPeerOutMsgs
      Counter32,
   vrIpBgpPeerOutUpdates
      Counter32,
   vrIpBgpPeerOutDiscards
      Counter32,
   vrIpBgpPeerOutErrorMsgs
      Counter32,
   vrIpBgpPeerInRoutes
      Counter32 }

vrIpBgpPeerConnectionState OBJECT-TYPE
   SYNTAX     INTEGER  {
                 idle(1),
                 connect(2),
                 active(3),
                 openSent(4),
                 openConfirm(5),
                 established(6) }
   ACCESS     read-only
   STATUS     mandatory
   DESCRIPTION
     "This attribute indicates the current state of this BGP peer 
      connection. The meaning of each state is as follows:
      idle - it is the initial state of the BGP peer connection. Error events 
      will also cause BGP peer connection to transit to the idle state.
      connect - BGP has initiated a TCP connection request to this peer, 
      and waiting for reply from that peer.
      active - BGP is not initiating a TCP connection request to this peer, 
      because TCP connection failed and is waiting for connection retry 
      time-out.
      openSent - a TCP connection to this peer has been established, but 
      the OPEN message has not been successfully exchanged.
      openConfirm - OPEN message has been successfully exchanged 
      with this peer, but the first KEEPALIVE message has not been 
      received from that peer.
      established - the first KEEPALIVE message has been received 
      from this peer, which means this BGP peer connection has been 
      established.
      See RFC 1771 for a detailed description of BGP state transitions."
   DEFVAL     { idle }
::= { vrIpBgpPeerOperEntry 3 }

vrIpBgpPeerBgpIdentifier OBJECT-TYPE
   SYNTAX     IpAddress 
   ACCESS     read-only
   STATUS     mandatory
   DESCRIPTION
     "This attribute indicates the BGP Identifier of this Bgp Peer 
      component. It is learned from the peer through the OPEN message."
::= { vrIpBgpPeerOperEntry 4 }

vrIpBgpPeerVersionNegotiated OBJECT-TYPE
   SYNTAX     Unsigned32 (0..4)
   ACCESS     read-only
   STATUS     mandatory
   DESCRIPTION
     "This attribute indicates the BGP version number negotiated with 
      this peer through the OPEN message. Currently, only BGP version 
      4 is supported. BGP will reject the peer connection if our peer 
      proposes a BGP version other than 4."
::= { vrIpBgpPeerOperEntry 5 }

vrIpBgpPeerHoldTimeNegotiated OBJECT-TYPE
   SYNTAX     Unsigned32 (0 | 3..65535)
   ACCESS     read-only
   STATUS     mandatory
   DESCRIPTION
     "This attribute indicates the maximum time in seconds, that may 
      elapse without receiving a KEEPALIVE or UPDATE message 
      before the connection is considered down. This is the negotiated 
      value with peer through the OPEN message. The hold time must be 
      either zero or at least three seconds. If the negotiated hold time is 
      zero, then periodic KEEPALIVE messages are not expected from 
      the peer."
::= { vrIpBgpPeerOperEntry 6 }

vrIpBgpPeerKeepAliveNegotiated OBJECT-TYPE
   SYNTAX     Unsigned32 (0..21845)
   ACCESS     read-only
   STATUS     mandatory
   DESCRIPTION
     "This attribute indicates the interval in seconds, between BGP 
      KEEPALIVE message retransmissions. This keepalive interval will 
      have the same ratio to the hold time negotiated with the peer as that 
      of the locally configured keepalive and hold time. This attribute will 
      be zero if the holdTimeNegotiated attribute is zero, which means 
      periodic KEEPALIVE messages will not be sent."
::= { vrIpBgpPeerOperEntry 7 }

vrIpBgpPeerLocalAddressUsed OBJECT-TYPE
   SYNTAX     IpAddress 
   ACCESS     read-only
   STATUS     mandatory
   DESCRIPTION
     "This attribute indicates the local IP address used for this BGP peer 
      connection. If the localAddressConfigured attribute is non-zero, its 
      value will be used. Otherwise, the local address will be assigned by 
      TCP based on the remote IP address of this peer connection and the 
      IP forwarding table."
::= { vrIpBgpPeerOperEntry 8 }

vrIpBgpPeerLocalPort OBJECT-TYPE
   SYNTAX     Unsigned32 (0..65535)
   ACCESS     read-only
   STATUS     mandatory
   DESCRIPTION
     "This attribute indicates the local TCP port for the connection 
      between the BGP peers."
::= { vrIpBgpPeerOperEntry 9 }

vrIpBgpPeerRemotePort OBJECT-TYPE
   SYNTAX     Unsigned32 (0..65535)
   ACCESS     read-only
   STATUS     mandatory
   DESCRIPTION
     "This attribute indicates the remote TCP port for the connection 
      between the BGP peers."
::= { vrIpBgpPeerOperEntry 10 }

vrIpBgpPeerLastError OBJECT-TYPE
   SYNTAX     HexString (SIZE (2))
   ACCESS     read-only
   STATUS     mandatory
   DESCRIPTION
     "This attribute indicates the last error code and subcode seen by this 
      Bgp component instance on this peer connection. The first byte of 
      this two byte OCTET STRING contains the error code, and the 
      second byte contains the subcode. A value of zero means that no 
      error has occurred. Check RFC 1771 for mappings of error codes 
      and error subcodes."
::= { vrIpBgpPeerOperEntry 11 }

vrIpBgpPeerConnectionEstablishedTime OBJECT-TYPE
   SYNTAX     Gauge32 (0..4294967295)
   ACCESS     read-only
   STATUS     mandatory
   DESCRIPTION
     "This attribute indicates how long since this Peer component's last 
      transition to or from the established state. It is set to zero when the 
      Peer component is activated.
      DESCRIPTION"
   DEFVAL     { 0 }
::= { vrIpBgpPeerOperEntry 12 }

vrIpBgpPeerConnectionEstablishedTransitions OBJECT-TYPE
   SYNTAX     Counter32 
   ACCESS     read-only
   STATUS     mandatory
   DESCRIPTION
     "This attribute counts the total number of times the BGP connection 
      state transitioned into the established state."
::= { vrIpBgpPeerOperEntry 13 }

vrIpBgpPeerInUpdateElapsedTime OBJECT-TYPE
   SYNTAX     Gauge32 (0..4294967295)
   ACCESS     read-only
   STATUS     mandatory
   DESCRIPTION
     "This attribute indicates the elapsed time in seconds since the last 
      BGP UPDATE message was received from the peer. Each time 
      inUpdates attribute is incremented, the value of this attribute is set 
      to zero."
::= { vrIpBgpPeerOperEntry 14 }

vrIpBgpPeerInMsgs OBJECT-TYPE
   SYNTAX     Counter32 
   ACCESS     read-only
   STATUS     mandatory
   DESCRIPTION
     "This attribute counts the number of BGP messages received without 
      error from the BGP peer. This counter will wrap to zero once the 
      value exceeds the maximum value."
::= { vrIpBgpPeerOperEntry 15 }

vrIpBgpPeerInUpdates OBJECT-TYPE
   SYNTAX     Counter32 
   ACCESS     read-only
   STATUS     mandatory
   DESCRIPTION
     "This attribute counts the number of BGP UPDATE messages 
      received on this peer connection. This counter will wrap to zero 
      once the value exceeds the maximum value."
::= { vrIpBgpPeerOperEntry 16 }

vrIpBgpPeerInErrors OBJECT-TYPE
   SYNTAX     Counter32 
   ACCESS     read-only
   STATUS     mandatory
   DESCRIPTION
     "This attribute counts the number of messages received from this 
      BGP peer that proved to be in error. This counter will wrap to zero 
      once the value exceeds the maximum value."
::= { vrIpBgpPeerOperEntry 17 }

vrIpBgpPeerInErrorMsgs OBJECT-TYPE
   SYNTAX     Counter32 
   ACCESS     read-only
   STATUS     mandatory
   DESCRIPTION
     "This attribute counts the number of BGP NOTIFICATION 
      messages received from this BGP peer. This counter will wrap to 
      zero once the value exceeds the maximum value."
::= { vrIpBgpPeerOperEntry 18 }

vrIpBgpPeerOutMsgs OBJECT-TYPE
   SYNTAX     Counter32 
   ACCESS     read-only
   STATUS     mandatory
   DESCRIPTION
     "This attribute counts the number of locally generated BGP 
      messages sent to this BGP peer. It does not include discarded 
      messages. This counter will wrap to zero once the value exceeds the 
      maximum value."
::= { vrIpBgpPeerOperEntry 19 }

vrIpBgpPeerOutUpdates OBJECT-TYPE
   SYNTAX     Counter32 
   ACCESS     read-only
   STATUS     mandatory
   DESCRIPTION
     "This attribute counts the number of BGP UPDATE messages sent to 
      this peer. This counter will wrap to zero once the value exceeds the 
      maximum value."
::= { vrIpBgpPeerOperEntry 20 }

vrIpBgpPeerOutDiscards OBJECT-TYPE
   SYNTAX     Counter32 
   ACCESS     read-only
   STATUS     mandatory
   DESCRIPTION
     "This attribute counts the number of locally generated BGP 
      messages not sent to this BGP peer due to resource limitations 
      within a BGP entity. This counter will wrap to zero once the value 
      exceeds the maximum value."
::= { vrIpBgpPeerOperEntry 21 }

vrIpBgpPeerOutErrorMsgs OBJECT-TYPE
   SYNTAX     Counter32 
   ACCESS     read-only
   STATUS     mandatory
   DESCRIPTION
     "This attribute counts the number of BGP NOTIFICATION 
      messages sent to this BGP peer. This counter will wrap to zero once 
      the value exceeds the maximum value."
::= { vrIpBgpPeerOperEntry 22 }

vrIpBgpPeerInRoutes OBJECT-TYPE
   SYNTAX     Counter32 
   ACCESS     read-only
   STATUS     mandatory
   DESCRIPTION
     "This attribute indicates the number of routes received from this 
      BGP peer."
::= { vrIpBgpPeerOperEntry 23 }


-- Vr/<string> Ip Bgp Import/n
-- Each instance of this component describes a BGP import policy. A 
-- BGP import policy is used to decide if certain routing information 
-- learned from its peer is to be ignored or used. 
-- If no import policy is provisioned, BGP will accept all routes 
-- received from its IBGP peers, but will not use any routing 
-- information received from its EBGP peers. 
-- If multiple import policies are provisioned, the one with the most 
-- specific match will apply.
-- The keys are matched in the following order from the least specified 
-- to the most specified:
-- Network,
-- peerAs, 
-- peerIpAddress,
-- originAs, 
-- originProtocol,
-- matchAsPath,
-- matchCommunity.
-- Example1: 
-- There are 2 import policies defined:
-- vr/0 ip bgp import/1, originProtocol = any, originAs = 20, 
-- usageFlag = use
-- vr/0 ip bgp import/2, originProtocol = igp, usageFlag = ignore 
-- If a BGP NLRI contains a route originally learned from an igp with 
-- origin AS 20, it will be used.
-- Example2: 
-- There are 2 import policies defined:
-- vr/0 ip bgp import/1, originProtocol = any, matchAsPath = "1 2 3",, 
-- usageFlag = ignore
-- vr/0 ip bgp import/2, originProtocol = any, usageFlag = use
-- If a BGP NLRI contains a route originally learned from an igp with 
-- the AsPath "1 2 3 4", it will be ignored.
-- DESCRIPTION	

vrIpBgpImport OBJECT IDENTIFIER ::= { vrIpBgp 3 }



vrIpBgpImportRowStatusTable OBJECT-TYPE
   SYNTAX     SEQUENCE OF VrIpBgpImportRowStatusEntry
   ACCESS     not-accessible
   STATUS     mandatory
   DESCRIPTION
     "This entry controls the addition and deletion of 
      vrIpBgpImport components."
::= { vrIpBgpImport 1 }

vrIpBgpImportRowStatusEntry OBJECT-TYPE
   SYNTAX     VrIpBgpImportRowStatusEntry
   ACCESS     not-accessible
   STATUS     mandatory
   DESCRIPTION
     "A single entry in the table represents a single 
      vrIpBgpImport component."
   INDEX {
      vrIndex,
      vrIpIndex,
      vrIpBgpIndex,
      vrIpBgpImportIndex }
::= { vrIpBgpImportRowStatusTable 1 }

VrIpBgpImportRowStatusEntry ::= SEQUENCE {
   vrIpBgpImportRowStatus
      RowStatus,
   vrIpBgpImportComponentName
      DisplayString,
   vrIpBgpImportStorageType
      StorageType,
   vrIpBgpImportIndex
      Integer32 }

vrIpBgpImportRowStatus OBJECT-TYPE
   SYNTAX     RowStatus 
   ACCESS     read-write
   STATUS     mandatory
   DESCRIPTION
     "This variable is used as the basis for SNMP naming of
      vrIpBgpImport components.
      These components can be added and deleted."
::= { vrIpBgpImportRowStatusEntry 1 }

vrIpBgpImportComponentName OBJECT-TYPE
   SYNTAX     DisplayString 
   ACCESS     read-only
   STATUS     mandatory
   DESCRIPTION
     "This variable provides the component's string name for
      use with the ASCII Console Interface"
::= { vrIpBgpImportRowStatusEntry 2 }

vrIpBgpImportStorageType OBJECT-TYPE
   SYNTAX     StorageType 
   ACCESS     read-only
   STATUS     mandatory
   DESCRIPTION
     "This variable represents the storage type value for the
      vrIpBgpImport tables."
::= { vrIpBgpImportRowStatusEntry 4 }

vrIpBgpImportIndex OBJECT-TYPE
   SYNTAX     Integer32 (0..65535)
   ACCESS     not-accessible
   STATUS     mandatory
   DESCRIPTION
     "This variable represents the index for the vrIpBgpImport tables."
::= { vrIpBgpImportRowStatusEntry 10 }

vrIpBgpImportProvTable OBJECT-TYPE
   SYNTAX     SEQUENCE OF VrIpBgpImportProvEntry
   ACCESS     not-accessible
   STATUS     mandatory
   DESCRIPTION
     "This group contains all the provisionable attributes for the Import 
      component."
::= { vrIpBgpImport 10 }

vrIpBgpImportProvEntry OBJECT-TYPE
   SYNTAX     VrIpBgpImportProvEntry
   ACCESS     not-accessible
   STATUS     mandatory
   DESCRIPTION
     "An entry in the vrIpBgpImportProvTable."
   INDEX {
      vrIndex,
      vrIpIndex,
      vrIpBgpIndex,
      vrIpBgpImportIndex }
::= { vrIpBgpImportProvTable 1 }

VrIpBgpImportProvEntry ::= SEQUENCE {
   vrIpBgpImportPeerAs
      Unsigned32,
   vrIpBgpImportPeerIpAddress
      IpAddress,
   vrIpBgpImportOriginAs
      Unsigned32,
   vrIpBgpImportOriginProtocol
      INTEGER,
   vrIpBgpImportUsageFlag
      INTEGER,
   vrIpBgpImportLocalPreference
      Unsigned32,
   vrIpBgpImportPreferredOver
      INTEGER,
   vrIpBgpImportAsPathExpression
      AsciiString,
   vrIpBgpImportCommunityExpression
      AsciiString,
   vrIpBgpImportExpressPreference
      Unsigned32,
   vrIpBgpImportAppendCommunity
      Unsigned32 }

vrIpBgpImportPeerAs OBJECT-TYPE
   SYNTAX     Unsigned32 (0..65535)
   ACCESS     read-write
   STATUS     mandatory
   DESCRIPTION
     "This key attribute specifies the autonomous system number of the 
      peer from which the routes are learned. A value of 0 for this 
      attribute means that peer AS number will match any AS number."
   DEFVAL     { 0 }
::= { vrIpBgpImportProvEntry 1 }

vrIpBgpImportPeerIpAddress OBJECT-TYPE
   SYNTAX     IpAddress 
   ACCESS     read-write
   STATUS     mandatory
   DESCRIPTION
     "This key attribute specifies the IP address of the peer from which 
      the routes are learned. A value of 0.0.0.0 for this attribute means 
      that peer IP address will match any IP address."
   DEFVAL     { '00000000'H }  -- "0.0.0.0"
::= { vrIpBgpImportProvEntry 2 }

vrIpBgpImportOriginAs OBJECT-TYPE
   SYNTAX     Unsigned32 (0..65535)
   ACCESS     read-write
   STATUS     mandatory
   DESCRIPTION
     "This key attribute specifies the autonomous system number where 
      the routes were originated. A value of 0 for this attribute means 
      origin AS number will match any AS number."
   DEFVAL     { 0 }
::= { vrIpBgpImportProvEntry 3 }

vrIpBgpImportOriginProtocol OBJECT-TYPE
   SYNTAX     INTEGER  {
                 any(0),
                 igp(1),
                 egp(2),
                 incomplete(3) }
   ACCESS     read-write
   STATUS     mandatory
   DESCRIPTION
     "This key attribute specifies the protocols that originated the routes. 
      A value of incomplete for this attribute means this information is 
      not available."
   DEFVAL     { any }
::= { vrIpBgpImportProvEntry 4 }

vrIpBgpImportUsageFlag OBJECT-TYPE
   SYNTAX     INTEGER  {
                 use(1),
                 ignore(2),
                 exclude(3) }
   ACCESS     read-write
   STATUS     mandatory
   DESCRIPTION
     "This attribute specifies whether BGP will use, ignore, or exclude 
      information in received update if it meets criteria specified by the 
      key attributes of this component. When it is set to exclude the 
      matching routes if selected are installed in the routing database and 
      forwarding table with an unreachable next hop."
   DEFVAL     { use }
::= { vrIpBgpImportProvEntry 5 }

vrIpBgpImportLocalPreference OBJECT-TYPE
   SYNTAX     Unsigned32 (0..4294967295)
   ACCESS     read-write
   STATUS     mandatory
   DESCRIPTION
     "This attribute specifies this Bgp component instance's degree of 
      preference for those routes that match the criteria of this import 
      policy. A higher value indicates a more preferred route. A value of 0 
      for this attribute means that the default local preference value 
      provisioned under the Bgp component should be used."
   DEFVAL     { 0 }
::= { vrIpBgpImportProvEntry 6 }

vrIpBgpImportPreferredOver OBJECT-TYPE
   SYNTAX     INTEGER  {
                 overIntOspf(6),
                 underIntOspf(70) }
   ACCESS     read-write
   STATUS     mandatory
   DESCRIPTION
     "This attribute indicates the preference of the external BGP route 
      with the OSPF internal route. overIntOspf means that the external 
      BGP route is chosen over OSPF internal route, while underIntOspf 
      means that the OSPF internal route is chosen over the external BGP 
      route. The default preference is set to underIntOspf."
   DEFVAL     { underIntOspf }
::= { vrIpBgpImportProvEntry 7 }

vrIpBgpImportAsPathExpression OBJECT-TYPE
   SYNTAX     AsciiString (SIZE (0..255))
   ACCESS     read-write
   STATUS     mandatory
   DESCRIPTION
     "This key attribute allows the user to enter a regular expression to 
      match the import AS Path Attribute of the received update message. 
      Note: the AS Path Attribute lists the ASs in reverse traversal order. 
      The syntax of the regular expression is a subset of the RFC 2280. 
      The basic syntax of a regular expression is a list of AS number 
      separated by a space which making up a AS path.
      The following characters has the special meaning:
      '.' 					- Matches any AS number.
      '^n' 		- Matches the first AS item (n) in the AS Path Attribute,
      or in order words, matches the last AS (n) traversed in
      the AS path.
      'n$' 		- Matches the last AS item (n) in the AS Path Attribute,
      or in order words, matches the first AS (n) traversed in
      the AS path.
      '[n1 ... n2]' 		- Matches any AS number that appeared in the set n1 ...
      n2.	
      'n1 - n2' 		- Matches any AS number between the range of n1 and
      n2.
      '()' 		- is supported to change the order of evaluation.
      'n*' 		- Matches 0 or more occurrences of n, where n can be a
      set, 	 range or AS number.
      'n+' 		- Matches 1 or more occurrences of n, where n can be a
      set, range or AS number.
      'n?' 		- Matches 0 or 1 occurrences of n, where n can be a AS
      set, range or number.
      The following logical operators are evaluated in decending order:
      'NOT' 		- Given a regular expression x, NOT x matches the AS
      number 	pattern that is not matched by x. 
      'AND'		- Given two regular expressions x and y, x AND y
      matches the intersection of the AS path that are
      matched by x and those are matched by y.
      'OR' 		- Given two regular expressions x and y, x OR y
      matches the union of the AS path that are matched by x
      and those are matched by y.
      For example: The AS path '5 4 3 2 1', where 1 is the origin AS, 
      would be matched by any one of the following regular expressions:
      1$,
      ^5,
      4 3,
      5 3 - 4*,
      5 [4 3 2] not10 2 1,
      not (6 7 8 9 10) and 5 4 .* 1
      Empty regular expression implies a match on all AS path."
::= { vrIpBgpImportProvEntry 8 }

vrIpBgpImportCommunityExpression OBJECT-TYPE
   SYNTAX     AsciiString (SIZE (0..255))
   ACCESS     read-write
   STATUS     mandatory
   DESCRIPTION
     "This key attribute allows the user to enter a regular expression to 
      match the import Community Attribute of the received update 
      message. The syntax of the regular expression is a subset of the 
      RFC 2280. 
      The basic syntax of a regular expression is a list of Community 
      number seperated by a space which making up a Community 
      attribute.
      The following characters has the special meaning:
      '[n1 ... n2]' 		- Matches any Community number that appeared in the
      set n1 ...							n2.	
      'n1 - n2' 		- Matches any Community number between the range of
      n1 and 							n2.
      '()' 		- is supported to change the order of evaluation.
      'n*' 		- Matches 0 or more occurrences of n, where n can be a
      set, 	 range or Community number.
      'n+' 		- Matches 1 or more occurrences of n, where n can be a
      set, range or Community number.
      'n?' 		- Matches 0 or 1 occurrences of n, where n can be a
      set, range or number.
      The following logical operators are evaluated in decending order:
      'NOT' 		- Given a regular expression x, NOT x matches the
      Community 			attribute that is not matched by x. 
      'AND'		- Given two regular expressions x and y, x AND y
      matches the intersection of the Community attribute that
      are matched by x and those are matched by y.
      'OR' 		- Given two regular expressions x and y, x OR y
      matches the union of the Community attribute that are
      matched by x and those are matched by y.
      For example: The Community path '1 2 3 4 5'would be matched by 
      any one of the following regular expressions:
      1,
      5,
      4 3,
      2 3 - 4*,
      1 [3 4 2]+ ,
      not (6 7 8 9 10) and 1 2
      Empty regular expression implies a match on all Community path."
::= { vrIpBgpImportProvEntry 9 }

vrIpBgpImportExpressPreference OBJECT-TYPE
   SYNTAX     Unsigned32 (0..255)
   ACCESS     read-write
   STATUS     mandatory
   DESCRIPTION
     "This attribute specifies the relative preference of the policy which 
      use the keys expressAsPath and expressCommunity. This attribute is 
      ignored if attributes expressAsPath and expressCommunity are both 
      empty. This attribute is used to break the tie when two import 
      policies' expression attributes match a specific AS Path or 
      Community. A higher value indicates a more preferred policy."
   DEFVAL     { 128 }
::= { vrIpBgpImportProvEntry 10 }

vrIpBgpImportAppendCommunity OBJECT-TYPE
   SYNTAX     Unsigned32 (0..4294967295)
   ACCESS     read-write
   STATUS     mandatory
   DESCRIPTION
     "This attribute indicates which community number this Import policy 
      will send along with the Path Attribute. Refer to RFC 1997 for the 
      detailed description of how this attribute may be used to pass 
      additional information to BGP peers. If the value is set to 0, no 
      community is appended to the Community attribute."
   DEFVAL     { 0 }
::= { vrIpBgpImportProvEntry 11 }


-- Vr/<string> Ip Bgp Import/n Network/n
-- This is an optional subcomponent of Import component and 
-- identifies destination networks that this BGP import policy applies 
-- to. This component is used as a key for the import policy. If no 
-- network list is provisioned, the import policy applies to all 
-- networks.

vrIpBgpImportNet OBJECT IDENTIFIER ::= { vrIpBgpImport 2 }



vrIpBgpImportNetRowStatusTable OBJECT-TYPE
   SYNTAX     SEQUENCE OF VrIpBgpImportNetRowStatusEntry
   ACCESS     not-accessible
   STATUS     mandatory
   DESCRIPTION
     "This entry controls the addition and deletion of 
      vrIpBgpImportNet components."
::= { vrIpBgpImportNet 1 }

vrIpBgpImportNetRowStatusEntry OBJECT-TYPE
   SYNTAX     VrIpBgpImportNetRowStatusEntry
   ACCESS     not-accessible
   STATUS     mandatory
   DESCRIPTION
     "A single entry in the table represents a single 
      vrIpBgpImportNet component."
   INDEX {
      vrIndex,
      vrIpIndex,
      vrIpBgpIndex,
      vrIpBgpImportIndex,
      vrIpBgpImportNetIndex }
::= { vrIpBgpImportNetRowStatusTable 1 }

VrIpBgpImportNetRowStatusEntry ::= SEQUENCE {
   vrIpBgpImportNetRowStatus
      RowStatus,
   vrIpBgpImportNetComponentName
      DisplayString,
   vrIpBgpImportNetStorageType
      StorageType,
   vrIpBgpImportNetIndex
      Integer32 }

vrIpBgpImportNetRowStatus OBJECT-TYPE
   SYNTAX     RowStatus 
   ACCESS     read-write
   STATUS     mandatory
   DESCRIPTION
     "This variable is used as the basis for SNMP naming of
      vrIpBgpImportNet components.
      These components can be added and deleted."
::= { vrIpBgpImportNetRowStatusEntry 1 }

vrIpBgpImportNetComponentName OBJECT-TYPE
   SYNTAX     DisplayString 
   ACCESS     read-only
   STATUS     mandatory
   DESCRIPTION
     "This variable provides the component's string name for
      use with the ASCII Console Interface"
::= { vrIpBgpImportNetRowStatusEntry 2 }

vrIpBgpImportNetStorageType OBJECT-TYPE
   SYNTAX     StorageType 
   ACCESS     read-only
   STATUS     mandatory
   DESCRIPTION
     "This variable represents the storage type value for the
      vrIpBgpImportNet tables."
::= { vrIpBgpImportNetRowStatusEntry 4 }

vrIpBgpImportNetIndex OBJECT-TYPE
   SYNTAX     Integer32 (0..65535)
   ACCESS     not-accessible
   STATUS     mandatory
   DESCRIPTION
     "This variable represents the index for the vrIpBgpImportNet tables."
::= { vrIpBgpImportNetRowStatusEntry 10 }

vrIpBgpImportNetProvTable OBJECT-TYPE
   SYNTAX     SEQUENCE OF VrIpBgpImportNetProvEntry
   ACCESS     not-accessible
   STATUS     mandatory
   DESCRIPTION
     "This group contains the set of provisionable attributes for the 
      Network component."
::= { vrIpBgpImportNet 10 }

vrIpBgpImportNetProvEntry OBJECT-TYPE
   SYNTAX     VrIpBgpImportNetProvEntry
   ACCESS     not-accessible
   STATUS     mandatory
   DESCRIPTION
     "An entry in the vrIpBgpImportNetProvTable."
   INDEX {
      vrIndex,
      vrIpIndex,
      vrIpBgpIndex,
      vrIpBgpImportIndex,
      vrIpBgpImportNetIndex }
::= { vrIpBgpImportNetProvTable 1 }

VrIpBgpImportNetProvEntry ::= SEQUENCE {
   vrIpBgpImportNetPrefix
      IpAddress,
   vrIpBgpImportNetLength
      Unsigned32 }

vrIpBgpImportNetPrefix OBJECT-TYPE
   SYNTAX     IpAddress 
   ACCESS     read-write
   STATUS     mandatory
   DESCRIPTION
     "This attribute specifies the network prefix whose length is 
      determined by the length attribute under the same Network 
      component."
::= { vrIpBgpImportNetProvEntry 1 }

vrIpBgpImportNetLength OBJECT-TYPE
   SYNTAX     Unsigned32 (1..32)
   ACCESS     read-write
   STATUS     mandatory
   DESCRIPTION
     "This attribute specifies the length of the network prefix."
::= { vrIpBgpImportNetProvEntry 2 }


-- Vr/<string> Ip Bgp Export/n
-- Each instance of this component describes a BGP export policy. A 
-- BGP export policy is used to decide if certain routing information 
-- should be blocked or advertised to its peers.
-- If no export policy is provisioned, BGP will advertise all external 
-- BGP learned routes to its internal peers, but not advertise any 
-- routing information to its external peers.
-- If multiple export policies are provisioned, the one with the most 
-- specific match will apply.
-- The keys are matched in the following order from the least specified 
-- to the most specified:
-- peerAs,
-- peerIpAddress, 
-- protocol, 
-- ripInterface (if applicable), 
-- egpAs, bgpAs, ripNeighbour, or ospfTag (whichever is applicable),
-- Network,
-- matchAsPath,
-- matchCommunity.
-- Example1: 
-- There are 2 export policies defined:
-- vr/0 ip bgp export/1, protocol = all, advertiseStatus = send
-- vr/0 ip bgp export/2, protocol = rip, advertiseStatus = block 
-- BGP will generate BGP updates for all routes except the routes 
-- learned from RIP.
-- Example2: 
-- There are 2 export policies defined:
-- vr/0 ip bgp export/1, protocol = all, matchCommunity = 303, 
-- advertiseStatus = send
-- vr/0 ip bgp export/2, protocol = all, advertiseStatus = block 
-- BGP will generate BGP updates for all routes that belongs to 
-- Community 303.
-- DESCRIPTION	

vrIpBgpExport OBJECT IDENTIFIER ::= { vrIpBgp 4 }



vrIpBgpExportRowStatusTable OBJECT-TYPE
   SYNTAX     SEQUENCE OF VrIpBgpExportRowStatusEntry
   ACCESS     not-accessible
   STATUS     mandatory
   DESCRIPTION
     "This entry controls the addition and deletion of 
      vrIpBgpExport components."
::= { vrIpBgpExport 1 }

vrIpBgpExportRowStatusEntry OBJECT-TYPE
   SYNTAX     VrIpBgpExportRowStatusEntry
   ACCESS     not-accessible
   STATUS     mandatory
   DESCRIPTION
     "A single entry in the table represents a single 
      vrIpBgpExport component."
   INDEX {
      vrIndex,
      vrIpIndex,
      vrIpBgpIndex,
      vrIpBgpExportIndex }
::= { vrIpBgpExportRowStatusTable 1 }

VrIpBgpExportRowStatusEntry ::= SEQUENCE {
   vrIpBgpExportRowStatus
      RowStatus,
   vrIpBgpExportComponentName
      DisplayString,
   vrIpBgpExportStorageType
      StorageType,
   vrIpBgpExportIndex
      Integer32 }

vrIpBgpExportRowStatus OBJECT-TYPE
   SYNTAX     RowStatus 
   ACCESS     read-write
   STATUS     mandatory
   DESCRIPTION
     "This variable is used as the basis for SNMP naming of
      vrIpBgpExport components.
      These components can be added and deleted."
::= { vrIpBgpExportRowStatusEntry 1 }

vrIpBgpExportComponentName OBJECT-TYPE
   SYNTAX     DisplayString 
   ACCESS     read-only
   STATUS     mandatory
   DESCRIPTION
     "This variable provides the component's string name for
      use with the ASCII Console Interface"
::= { vrIpBgpExportRowStatusEntry 2 }

vrIpBgpExportStorageType OBJECT-TYPE
   SYNTAX     StorageType 
   ACCESS     read-only
   STATUS     mandatory
   DESCRIPTION
     "This variable represents the storage type value for the
      vrIpBgpExport tables."
::= { vrIpBgpExportRowStatusEntry 4 }

vrIpBgpExportIndex OBJECT-TYPE
   SYNTAX     Integer32 (0..65535)
   ACCESS     not-accessible
   STATUS     mandatory
   DESCRIPTION
     "This variable represents the index for the vrIpBgpExport tables."
::= { vrIpBgpExportRowStatusEntry 10 }

vrIpBgpExportProvTable OBJECT-TYPE
   SYNTAX     SEQUENCE OF VrIpBgpExportProvEntry
   ACCESS     not-accessible
   STATUS     mandatory
   DESCRIPTION
     "This group contains all the provisioned attributes for the Export 
      component."
::= { vrIpBgpExport 10 }

vrIpBgpExportProvEntry OBJECT-TYPE
   SYNTAX     VrIpBgpExportProvEntry
   ACCESS     not-accessible
   STATUS     mandatory
   DESCRIPTION
     "An entry in the vrIpBgpExportProvTable."
   INDEX {
      vrIndex,
      vrIpIndex,
      vrIpBgpIndex,
      vrIpBgpExportIndex }
::= { vrIpBgpExportProvTable 1 }

VrIpBgpExportProvEntry ::= SEQUENCE {
   vrIpBgpExportPeerAs
      Unsigned32,
   vrIpBgpExportPeerIpAddress
      IpAddress,
   vrIpBgpExportProtocol
      INTEGER,
   vrIpBgpExportEgpAsId
      Unsigned32,
   vrIpBgpExportBgpAsId
      Unsigned32,
   vrIpBgpExportOspfTag
      Hex,
   vrIpBgpExportRipInterface
      IpAddress,
   vrIpBgpExportRipNeighbor
      IpAddress,
   vrIpBgpExportAdvertiseStatus
      INTEGER,
   vrIpBgpExportMultiExitDisc
      Unsigned32,
   vrIpBgpExportSendMultiExitDiscToEbgp
      INTEGER,
   vrIpBgpExportAsPathExpression
      AsciiString,
   vrIpBgpExportCommunityExpression
      AsciiString,
   vrIpBgpExportExpressPreference
      Unsigned32,
   vrIpBgpExportSendCommunity
      Unsigned32,
   vrIpBgpExportInsertDummyAs
      IntegerSequence }

vrIpBgpExportPeerAs OBJECT-TYPE
   SYNTAX     Unsigned32 (0..65535)
   ACCESS     read-write
   STATUS     mandatory
   DESCRIPTION
     "This key attribute specifies the autonomous system number of the 
      peer where the routes are advertised to. A value of 0 for this 
      attribute means this export policy applies to all peer ASes."
   DEFVAL     { 0 }
::= { vrIpBgpExportProvEntry 1 }

vrIpBgpExportPeerIpAddress OBJECT-TYPE
   SYNTAX     IpAddress 
   ACCESS     read-write
   STATUS     mandatory
   DESCRIPTION
     "This key attribute specifies the IP address of the peer where the 
      routes are advertised to. A value of 0.0.0.0 for this attribute means 
      this export policy applies to all peers."
   DEFVAL     { '00000000'H }  -- "0.0.0.0"
::= { vrIpBgpExportProvEntry 2 }

vrIpBgpExportProtocol OBJECT-TYPE
   SYNTAX     INTEGER  {
                 all(1),
                 egp(2),
                 rip(3),
                 ospfInternal(4),
                 ospfExternal(5),
                 staticLocal(6),
                 staticRemote(7),
                 bgpInternal(8),
                 bgpExternal(9) }
   ACCESS     read-write
   STATUS     mandatory
   DESCRIPTION
     "This key attribute specifies which protocol the export policy applies 
      to. If it is set to all, that means this export policy will apply all 
      routes in the IP routing table.
      Example: 
      vr/1 ip ospf export/1 with
      advertise Status = block
      protocol = bgpExternal
      bgpAsId = 3
      peerAs = 5
      This policy specifies that all routes learned from EBGP Peers that 
      are originated from AS 3 should not be advertised to AS 5."
   DEFVAL     { all }
::= { vrIpBgpExportProvEntry 3 }

vrIpBgpExportEgpAsId OBJECT-TYPE
   SYNTAX     Unsigned32 (0..65535)
   ACCESS     read-write
   STATUS     mandatory
   DESCRIPTION
     "This key attribute specifies the EGP autonomous system number 
      that this export policy will apply to.
      When this value is non-zero, the protocol attribute must be set to 
      egp."
   DEFVAL     { 0 }
::= { vrIpBgpExportProvEntry 4 }

vrIpBgpExportBgpAsId OBJECT-TYPE
   SYNTAX     Unsigned32 (0..65535)
   ACCESS     read-write
   STATUS     mandatory
   DESCRIPTION
     "This key attribute specifies the BGP autonomous system number 
      that this export policy will apply to.
      When this value is non-zero, the protocol attribute must be set to 
      either bgpInternal or bgpExternal."
   DEFVAL     { 0 }
::= { vrIpBgpExportProvEntry 5 }

vrIpBgpExportOspfTag OBJECT-TYPE
   SYNTAX     Hex (0..4294967295)
   ACCESS     read-write
   STATUS     mandatory
   DESCRIPTION
     "This key attribute specifies the OSPF tag when the protocol 
      attribute is set to either ospfInternal or ospfExternal. The default 
      tag value 4294967295 (FFFFFFFF in hex) indicates that the tag not 
      specified."
   DEFVAL     { 4294967295 }
::= { vrIpBgpExportProvEntry 6 }

vrIpBgpExportRipInterface OBJECT-TYPE
   SYNTAX     IpAddress 
   ACCESS     read-write
   STATUS     mandatory
   DESCRIPTION
     "This key attribute specifies the local RIP interface where the routes 
      are learned from.
      The ripInterface attribute when non-zero should be equal to one of 
      the IP addresses provisioned as a logicalIf component under IpPort. 
      Otherwise, this policy will be ignored.
      The value of the protocol attribute must be set to rip if a value for 
      the ripInterface attribute is non-zero."
   DEFVAL     { '00000000'H }  -- "0.0.0.0"
::= { vrIpBgpExportProvEntry 7 }

vrIpBgpExportRipNeighbor OBJECT-TYPE
   SYNTAX     IpAddress 
   ACCESS     read-write
   STATUS     mandatory
   DESCRIPTION
     "This key attribute specifies the RIP neighbor where the routes were 
      learned from.
      The value of the protocol attribute must be set to rip
      if a value for the ripNeighbor attribute is non-zero."
   DEFVAL     { '00000000'H }  -- "0.0.0.0"
::= { vrIpBgpExportProvEntry 8 }

vrIpBgpExportAdvertiseStatus OBJECT-TYPE
   SYNTAX     INTEGER  {
                 send(1),
                 block(2) }
   ACCESS     read-write
   STATUS     mandatory
   DESCRIPTION
     "This attribute specifies whether data will be exported if it meets 
      criteria specified by the other key attributes of this component."
   DEFVAL     { send }
::= { vrIpBgpExportProvEntry 9 }

vrIpBgpExportMultiExitDisc OBJECT-TYPE
   SYNTAX     Unsigned32 (0..4294967295)
   ACCESS     read-write
   STATUS     mandatory
   DESCRIPTION
     "This attribute specifies this Bgp component instance's metric to 
      discriminate between multiple exit points to an adjacent 
      autonomous system if the route meets the criteria specified by the 
      key attributes of this component. A lower value indicates a more 
      preferred route. A value of 0 for this attribute means the default 
      MED value provisioned under the Bgp component should be used."
   DEFVAL     { 0 }
::= { vrIpBgpExportProvEntry 10 }

vrIpBgpExportSendMultiExitDiscToEbgp OBJECT-TYPE
   SYNTAX     INTEGER  {
                 false(1),
                 true(2) }
   ACCESS     read-write
   STATUS     mandatory
   DESCRIPTION
     "This attribute specifies whether the Multi Exit Discriminator(MED) 
      attribute should be included in an update message sent to an EBGP 
      peer."
   DEFVAL     { false }
::= { vrIpBgpExportProvEntry 11 }

vrIpBgpExportAsPathExpression OBJECT-TYPE
   SYNTAX     AsciiString (SIZE (0..255))
   ACCESS     read-write
   STATUS     mandatory
   DESCRIPTION
     "This key attribute allows the user to enter a regular expression to 
      match the import AS Path Attribute of the export update message. 
      Note: the AS Path Attribute lists the ASs in reverse traversal order. 
      The syntax of the regular expression is a subset of the RFC 2280. 
      The basic syntax of a regular expression is a list of AS number 
      separated by a space which making up a AS path.
      The following characters has the special meaning:
      '.' 					- Matches any AS number.
      '^n' 		- Matches the first AS item (n) in the AS Path Attribute,
      or in order words, matches the last AS (n) traversed in
      the AS path.
      'n$' 		- Matches the last AS item (n) in the AS Path Attribute,
      or in order words, matches the first AS (n) traversed in
      the AS path.
      '[n1 ... n2]' 		- Matches any AS number that appeared in the set n1 ...
      n2.	
      'n1 - n2' 		- Matches any AS number between the range of n1 and
      n2.
      '()' 		- is supported to change the order of evaluation.
      'n*' 		- Matches 0 or more occurrences of n, where n can be a
      set, 	 range or AS number.
      'n+' 		- Matches 1 or more occurrences of n, where n can be a
      set, range or AS number.
      'n?' 		- Matches 0 or 1 occurrences of n, where n can be a
      set, range or number.
      The following logical operators are evaluated in decending order:
      'NOT' 		- Given a regular expression x, NOT x matches the AS
      number 	pattern that is not matched by x. 
      'AND'		- Given two regular expressions x and y, x AND y
      matches the intersection of the AS path that are
      matched by x and those are matched by y.
      'OR' 		- Given two regular expressions x and y, x OR y
      matches the union of the AS path that are matched by x
      and those are matched by y.
      For example: The AS path '5 4 3 2 1', where 1 is the origin AS, 
      would be matched by any one of the following regular expressions:
      1$,
      ^5,
      4 3,
      5 3 - 4*,
      5 [4 3 2] not10 2 1,
      not (6 7 8 9 10) and 5 4 .* 1
      Empty regular expression implies a match on all AS path."
::= { vrIpBgpExportProvEntry 12 }

vrIpBgpExportCommunityExpression OBJECT-TYPE
   SYNTAX     AsciiString (SIZE (0..255))
   ACCESS     read-write
   STATUS     mandatory
   DESCRIPTION
     "This key attribute allows the user to enter a regular expression to 
      match the import Community Attribute of the received update 
      message. The syntax of the regular expression is a subset of the 
      RFC 2280. 
      The basic syntax of a regular expression is a list of Community 
      number seperated by a space which making up a Community 
      attribute.
      The following characters has the special meaning:
      '[n1 ... n2]' 		- Matches any Community number that appeared in the
      set n1 ...							n2.	
      'n1 - n2' 		- Matches any Community number between the range of
      n1 and 							n2.
      '()' 		- is supported to change the order of evaluation.
      'n*' 		- Matches 0 or more occurrences of n, where n can be a
      set, 	 range or Community number.
      'n+' 		- Matches 1 or more occurrences of n, where n can be a
      set, range or Community number.
      'n?' 		- Matches 0 or 1 occurrences of n, where n can be a
      set, range or number.
      The following logical operators are evaluated in decending order:
      'NOT' 		- Given a regular expression x, NOT x matches the
      Community 			attribute that is not matched by x. 
      'AND'		- Given two regular expressions x and y, x AND y
      matches the intersection of the Community attribute that
      are matched by x and those are matched by y.
      'OR' 		- Given two regular expressions x and y, x OR y
      matches the union of the Community attribute that are
      matched by x and those are matched by y.
      For example: The Community path '1 2 3 4 5' would be match by 
      any one of the following regular expressions:
      4 3,
      2 3 - 4*,
      1 [3 4 2]+ 4,
      not (6 7 8 9 10) and 1 2
      Empty regular expression implies a match on all Community path."
::= { vrIpBgpExportProvEntry 13 }

vrIpBgpExportExpressPreference OBJECT-TYPE
   SYNTAX     Unsigned32 (0..255)
   ACCESS     read-write
   STATUS     mandatory
   DESCRIPTION
     "This attribute specifies the relative preference of the policy which 
      use the keys expressAsPath and expressCommunity. This attribute is 
      ignored if attributes expressAsPath and expressCommunity are both 
      empty. This attribute is used to break the tie when two export 
      policies' expression attributes match a specific AS Path or 
      Community. A higher value indicates a more preferred policy."
   DEFVAL     { 128 }
::= { vrIpBgpExportProvEntry 14 }

vrIpBgpExportSendCommunity OBJECT-TYPE
   SYNTAX     Unsigned32 (0..4294967295)
   ACCESS     read-write
   STATUS     mandatory
   DESCRIPTION
     "This attribute indicates which community number this Export policy 
      will send along with the Path Attribute. Refer to RFC 1997 for the 
      detailed description of how this attribute may be used to pass 
      additional information to BGP peers. If the value is set to 0, no 
      community is added to the Community attribute."
   DEFVAL     { 0 }
::= { vrIpBgpExportProvEntry 15 }

vrIpBgpExportInsertDummyAs OBJECT-TYPE
   SYNTAX     IntegerSequence 
   ACCESS     read-write
   STATUS     mandatory
   DESCRIPTION
     "This attribute specifies the AS number(s) to be inserted into the AS 
      Path Attribute. The value is a seuence of AS number seperated by 
      period(.). For example, if the value is 20.20.30, the AS numbers 20, 
      20 and 30 would be inserted at the end of the AS Path Attribute just 
      before the local AS number."
::= { vrIpBgpExportProvEntry 200 }


-- Vr/<string> Ip Bgp Export/n Network/n
-- This is an optional subcomponent of the Export component and 
-- identifies a destination network that this BGP export policy will 
-- apply to. This component is used as a key for the export policy. If 
-- no network list is provisioned, the import policy applies to all 
-- networks.

vrIpBgpExportNet OBJECT IDENTIFIER ::= { vrIpBgpExport 2 }



vrIpBgpExportNetRowStatusTable OBJECT-TYPE
   SYNTAX     SEQUENCE OF VrIpBgpExportNetRowStatusEntry
   ACCESS     not-accessible
   STATUS     mandatory
   DESCRIPTION
     "This entry controls the addition and deletion of 
      vrIpBgpExportNet components."
::= { vrIpBgpExportNet 1 }

vrIpBgpExportNetRowStatusEntry OBJECT-TYPE
   SYNTAX     VrIpBgpExportNetRowStatusEntry
   ACCESS     not-accessible
   STATUS     mandatory
   DESCRIPTION
     "A single entry in the table represents a single 
      vrIpBgpExportNet component."
   INDEX {
      vrIndex,
      vrIpIndex,
      vrIpBgpIndex,
      vrIpBgpExportIndex,
      vrIpBgpExportNetIndex }
::= { vrIpBgpExportNetRowStatusTable 1 }

VrIpBgpExportNetRowStatusEntry ::= SEQUENCE {
   vrIpBgpExportNetRowStatus
      RowStatus,
   vrIpBgpExportNetComponentName
      DisplayString,
   vrIpBgpExportNetStorageType
      StorageType,
   vrIpBgpExportNetIndex
      Integer32 }

vrIpBgpExportNetRowStatus OBJECT-TYPE
   SYNTAX     RowStatus 
   ACCESS     read-write
   STATUS     mandatory
   DESCRIPTION
     "This variable is used as the basis for SNMP naming of
      vrIpBgpExportNet components.
      These components can be added and deleted."
::= { vrIpBgpExportNetRowStatusEntry 1 }

vrIpBgpExportNetComponentName OBJECT-TYPE
   SYNTAX     DisplayString 
   ACCESS     read-only
   STATUS     mandatory
   DESCRIPTION
     "This variable provides the component's string name for
      use with the ASCII Console Interface"
::= { vrIpBgpExportNetRowStatusEntry 2 }

vrIpBgpExportNetStorageType OBJECT-TYPE
   SYNTAX     StorageType 
   ACCESS     read-only
   STATUS     mandatory
   DESCRIPTION
     "This variable represents the storage type value for the
      vrIpBgpExportNet tables."
::= { vrIpBgpExportNetRowStatusEntry 4 }

vrIpBgpExportNetIndex OBJECT-TYPE
   SYNTAX     Integer32 (0..65535)
   ACCESS     not-accessible
   STATUS     mandatory
   DESCRIPTION
     "This variable represents the index for the vrIpBgpExportNet tables."
::= { vrIpBgpExportNetRowStatusEntry 10 }

vrIpBgpExportNetProvTable OBJECT-TYPE
   SYNTAX     SEQUENCE OF VrIpBgpExportNetProvEntry
   ACCESS     not-accessible
   STATUS     mandatory
   DESCRIPTION
     "This group contains the set of provisionable attributes for the 
      Network component."
::= { vrIpBgpExportNet 10 }

vrIpBgpExportNetProvEntry OBJECT-TYPE
   SYNTAX     VrIpBgpExportNetProvEntry
   ACCESS     not-accessible
   STATUS     mandatory
   DESCRIPTION
     "An entry in the vrIpBgpExportNetProvTable."
   INDEX {
      vrIndex,
      vrIpIndex,
      vrIpBgpIndex,
      vrIpBgpExportIndex,
      vrIpBgpExportNetIndex }
::= { vrIpBgpExportNetProvTable 1 }

VrIpBgpExportNetProvEntry ::= SEQUENCE {
   vrIpBgpExportNetPrefix
      IpAddress,
   vrIpBgpExportNetLength
      Unsigned32 }

vrIpBgpExportNetPrefix OBJECT-TYPE
   SYNTAX     IpAddress 
   ACCESS     read-write
   STATUS     mandatory
   DESCRIPTION
     "This attribute specifies the network prefix whose length is 
      determined by the length attribute under the same Network 
      component."
::= { vrIpBgpExportNetProvEntry 1 }

vrIpBgpExportNetLength OBJECT-TYPE
   SYNTAX     Unsigned32 (1..32)
   ACCESS     read-write
   STATUS     mandatory
   DESCRIPTION
     "This attribute specifies the length of the network prefix."
::= { vrIpBgpExportNetProvEntry 2 }


-- Vr/<string> Ip Bgp As/n
-- This component associates attributes to an autonomous system.

vrIpBgpAs OBJECT IDENTIFIER ::= { vrIpBgp 5 }



vrIpBgpAsRowStatusTable OBJECT-TYPE
   SYNTAX     SEQUENCE OF VrIpBgpAsRowStatusEntry
   ACCESS     not-accessible
   STATUS     mandatory
   DESCRIPTION
     "This entry controls the addition and deletion of 
      vrIpBgpAs components."
::= { vrIpBgpAs 1 }

vrIpBgpAsRowStatusEntry OBJECT-TYPE
   SYNTAX     VrIpBgpAsRowStatusEntry
   ACCESS     not-accessible
   STATUS     mandatory
   DESCRIPTION
     "A single entry in the table represents a single 
      vrIpBgpAs component."
   INDEX {
      vrIndex,
      vrIpIndex,
      vrIpBgpIndex,
      vrIpBgpAsIndex }
::= { vrIpBgpAsRowStatusTable 1 }

VrIpBgpAsRowStatusEntry ::= SEQUENCE {
   vrIpBgpAsRowStatus
      RowStatus,
   vrIpBgpAsComponentName
      DisplayString,
   vrIpBgpAsStorageType
      StorageType,
   vrIpBgpAsIndex
      Integer32 }

vrIpBgpAsRowStatus OBJECT-TYPE
   SYNTAX     RowStatus 
   ACCESS     read-write
   STATUS     mandatory
   DESCRIPTION
     "This variable is used as the basis for SNMP naming of
      vrIpBgpAs components.
      These components can be added and deleted."
::= { vrIpBgpAsRowStatusEntry 1 }

vrIpBgpAsComponentName OBJECT-TYPE
   SYNTAX     DisplayString 
   ACCESS     read-only
   STATUS     mandatory
   DESCRIPTION
     "This variable provides the component's string name for
      use with the ASCII Console Interface"
::= { vrIpBgpAsRowStatusEntry 2 }

vrIpBgpAsStorageType OBJECT-TYPE
   SYNTAX     StorageType 
   ACCESS     read-only
   STATUS     mandatory
   DESCRIPTION
     "This variable represents the storage type value for the
      vrIpBgpAs tables."
::= { vrIpBgpAsRowStatusEntry 4 }

vrIpBgpAsIndex OBJECT-TYPE
   SYNTAX     Integer32 (0..65535)
   ACCESS     not-accessible
   STATUS     mandatory
   DESCRIPTION
     "This variable represents the index for the vrIpBgpAs tables."
::= { vrIpBgpAsRowStatusEntry 10 }

vrIpBgpAsProvTable OBJECT-TYPE
   SYNTAX     SEQUENCE OF VrIpBgpAsProvEntry
   ACCESS     not-accessible
   STATUS     mandatory
   DESCRIPTION
     "This group contains the attributes associated to each autonomous 
      system for this Bgp component instance."
::= { vrIpBgpAs 10 }

vrIpBgpAsProvEntry OBJECT-TYPE
   SYNTAX     VrIpBgpAsProvEntry
   ACCESS     not-accessible
   STATUS     mandatory
   DESCRIPTION
     "An entry in the vrIpBgpAsProvTable."
   INDEX {
      vrIndex,
      vrIpIndex,
      vrIpBgpIndex,
      vrIpBgpAsIndex }
::= { vrIpBgpAsProvTable 1 }

VrIpBgpAsProvEntry ::= SEQUENCE {
   vrIpBgpAsWeight
      Unsigned32 }

vrIpBgpAsWeight OBJECT-TYPE
   SYNTAX     Unsigned32 (0..255)
   ACCESS     read-write
   STATUS     mandatory
   DESCRIPTION
     "This attribute specifies the weight for an autonomous system. It 
      allows users to prefer some ASes over others. It is used in route 
      selection. Lowest weight is preferred. Setting the weight of an AS 
      to 255 will make any route that traverses through that AS 
      unpreferred."
   DEFVAL     { 128 }
::= { vrIpBgpAsProvEntry 1 }


-- Vr/<string> Ip Bgp AggregatePolicy/<Ip Address>,<Decimal>
-- This component is used to perform aggregation of BGP routes for 
-- exporting. Aggregation is the process of combining the 
-- characteristics of several different routes in such a way that a single 
-- route can be advertised. Aggregation reduces the amount of 
-- information that a BGP speaker must store and exchange with other 
-- BGP speakers. Refer to RFC1771 for the set of rules regarding 
-- which routes can be aggregated. 
-- A network subcomponent is automatically added with the same 
-- network range as the aggregation policy key and its action is set to 
-- aggregate. So by default all subnets under the aggregation key 
-- range will be aggregated.
-- Examples:
-- Example #1: aggregate all the networks covered by A.0.0.0/8
-- add vr/0 ip bgp aggregate/A.0.0.0,8
-- (Note: the following subcomponent vr/0 ip bgp aggregate/A.0.0.0,8 
-- network/0 prefix A.0.0.0, length 8, action aggregate will be 
-- automatically added)
-- 
-- Example #2: aggregate A.B.0.0/16 and A.C.0.0/16 as A.0.0.0/8 and 
-- advertise other networks
-- add vr/0 ip bgp aggregate/A.0.0.0,8
-- set vr/0 ip bgp aggregate/A.0.0.0,8 network/0 prefix A.B.0.0, length 
-- 16, action aggregate
-- (Note: this set command will overwrite the default network 
-- subcomponent
-- vr/0 ip bgp aggregate/A.0.0.0,8 network/0 prefix A.0.0.0, length 8, 
-- action aggregate)
-- add vr/0 ip bgp aggregate/A.0.0.0,8 network/1
-- set vr/0 ip bgp aggregate/A.0.0.0,8 network/1 prefix A.C.0.0, length 
-- 16, action aggregate
-- 
-- Example #3: aggregate A.B.0.0/16 and A.C.0.0/16 as A.0.0.0/8 and 
-- advertise other networks; also advertise A.B.C.0/24
-- add vr/0 ip bgp aggregate/A.0.0.0,8
-- set vr/0 ip bgp aggregate/A.0.0.0,8 networkl/0 prefix A.B.0.0, 
-- length 16, action aggregate
-- add vr/0 ip bgp aggregate/A.0.0.0,8 network/1
-- set vr/0 ip bgp aggregate/A.0.0.0,8 network/1 prefix A.C.0.0, length 
-- 16, action aggregate
-- add vr/0 ip bgp aggregate/A.0.0.0,8 network/2
-- set vr/0 ip bgp aggregate/A.0.0.0,8 network/2 prefix A.B.C.0, 
-- length 24, action advertise
-- 
-- Example #4: aggregate all networks under A.0.0.0/8, meanwhile 
-- advertise A.B.0.0/16
-- add vr/0 ip bgp aggregate/A.0.0.0,8
-- add vr/0 ip bgp aggregate/A.0.0.0,8 network/1
-- set vr/0 ip bgp aggregate/A.0.0.0,8 network/1 prefix A.B.0.0, length 
-- 16, action advertise

vrIpBgpAggregate OBJECT IDENTIFIER ::= { vrIpBgp 6 }



vrIpBgpAggregateRowStatusTable OBJECT-TYPE
   SYNTAX     SEQUENCE OF VrIpBgpAggregateRowStatusEntry
   ACCESS     not-accessible
   STATUS     mandatory
   DESCRIPTION
     "This entry controls the addition and deletion of 
      vrIpBgpAggregate components."
::= { vrIpBgpAggregate 1 }

vrIpBgpAggregateRowStatusEntry OBJECT-TYPE
   SYNTAX     VrIpBgpAggregateRowStatusEntry
   ACCESS     not-accessible
   STATUS     mandatory
   DESCRIPTION
     "A single entry in the table represents a single 
      vrIpBgpAggregate component."
   INDEX {
      vrIndex,
      vrIpIndex,
      vrIpBgpIndex,
      vrIpBgpAggregatePrefixIndex,
      vrIpBgpAggregateLengthIndex }
::= { vrIpBgpAggregateRowStatusTable 1 }

VrIpBgpAggregateRowStatusEntry ::= SEQUENCE {
   vrIpBgpAggregateRowStatus
      RowStatus,
   vrIpBgpAggregateComponentName
      DisplayString,
   vrIpBgpAggregateStorageType
      StorageType,
   vrIpBgpAggregatePrefixIndex
      IpAddress,
   vrIpBgpAggregateLengthIndex
      Integer32 }

vrIpBgpAggregateRowStatus OBJECT-TYPE
   SYNTAX     RowStatus 
   ACCESS     read-write
   STATUS     mandatory
   DESCRIPTION
     "This variable is used as the basis for SNMP naming of
      vrIpBgpAggregate components.
      These components can be added and deleted."
::= { vrIpBgpAggregateRowStatusEntry 1 }

vrIpBgpAggregateComponentName OBJECT-TYPE
   SYNTAX     DisplayString 
   ACCESS     read-only
   STATUS     mandatory
   DESCRIPTION
     "This variable provides the component's string name for
      use with the ASCII Console Interface"
::= { vrIpBgpAggregateRowStatusEntry 2 }

vrIpBgpAggregateStorageType OBJECT-TYPE
   SYNTAX     StorageType 
   ACCESS     read-only
   STATUS     mandatory
   DESCRIPTION
     "This variable represents the storage type value for the
      vrIpBgpAggregate tables."
::= { vrIpBgpAggregateRowStatusEntry 4 }

vrIpBgpAggregatePrefixIndex OBJECT-TYPE
   SYNTAX     IpAddress 
   ACCESS     not-accessible
   STATUS     mandatory
   DESCRIPTION
     "This variable represents an index for the vrIpBgpAggregate tables."
::= { vrIpBgpAggregateRowStatusEntry 10 }

vrIpBgpAggregateLengthIndex OBJECT-TYPE
   SYNTAX     Integer32 (0..32)
   ACCESS     not-accessible
   STATUS     mandatory
   DESCRIPTION
     "This variable represents an index for the vrIpBgpAggregate tables."
::= { vrIpBgpAggregateRowStatusEntry 11 }


-- Vr/<string> Ip Bgp AggregatePolicy/ Network/n
-- This is an optional subcomponent of Aggregate component and 
-- identifies a set of more specific routes that this BGP will aggregate 
-- or advertise together with the aggregated route.

vrIpBgpAggregateNet OBJECT IDENTIFIER ::= { vrIpBgpAggregate 2 }



vrIpBgpAggregateNetRowStatusTable OBJECT-TYPE
   SYNTAX     SEQUENCE OF VrIpBgpAggregateNetRowStatusEntry
   ACCESS     not-accessible
   STATUS     mandatory
   DESCRIPTION
     "This entry controls the addition and deletion of 
      vrIpBgpAggregateNet components."
::= { vrIpBgpAggregateNet 1 }

vrIpBgpAggregateNetRowStatusEntry OBJECT-TYPE
   SYNTAX     VrIpBgpAggregateNetRowStatusEntry
   ACCESS     not-accessible
   STATUS     mandatory
   DESCRIPTION
     "A single entry in the table represents a single 
      vrIpBgpAggregateNet component."
   INDEX {
      vrIndex,
      vrIpIndex,
      vrIpBgpIndex,
      vrIpBgpAggregatePrefixIndex,
      vrIpBgpAggregateLengthIndex,
      vrIpBgpAggregateNetIndex }
::= { vrIpBgpAggregateNetRowStatusTable 1 }

VrIpBgpAggregateNetRowStatusEntry ::= SEQUENCE {
   vrIpBgpAggregateNetRowStatus
      RowStatus,
   vrIpBgpAggregateNetComponentName
      DisplayString,
   vrIpBgpAggregateNetStorageType
      StorageType,
   vrIpBgpAggregateNetIndex
      Integer32 }

vrIpBgpAggregateNetRowStatus OBJECT-TYPE
   SYNTAX     RowStatus 
   ACCESS     read-write
   STATUS     mandatory
   DESCRIPTION
     "This variable is used as the basis for SNMP naming of
      vrIpBgpAggregateNet components.
      These components can be added and deleted."
::= { vrIpBgpAggregateNetRowStatusEntry 1 }

vrIpBgpAggregateNetComponentName OBJECT-TYPE
   SYNTAX     DisplayString 
   ACCESS     read-only
   STATUS     mandatory
   DESCRIPTION
     "This variable provides the component's string name for
      use with the ASCII Console Interface"
::= { vrIpBgpAggregateNetRowStatusEntry 2 }

vrIpBgpAggregateNetStorageType OBJECT-TYPE
   SYNTAX     StorageType 
   ACCESS     read-only
   STATUS     mandatory
   DESCRIPTION
     "This variable represents the storage type value for the
      vrIpBgpAggregateNet tables."
::= { vrIpBgpAggregateNetRowStatusEntry 4 }

vrIpBgpAggregateNetIndex OBJECT-TYPE
   SYNTAX     Integer32 (0..65535)
   ACCESS     not-accessible
   STATUS     mandatory
   DESCRIPTION
     "This variable represents the index for the vrIpBgpAggregateNet tables."
::= { vrIpBgpAggregateNetRowStatusEntry 10 }

vrIpBgpAggregateNetProvTable OBJECT-TYPE
   SYNTAX     SEQUENCE OF VrIpBgpAggregateNetProvEntry
   ACCESS     not-accessible
   STATUS     mandatory
   DESCRIPTION
     "This group contains the set of provisionable attributes for the 
      Network component."
::= { vrIpBgpAggregateNet 10 }

vrIpBgpAggregateNetProvEntry OBJECT-TYPE
   SYNTAX     VrIpBgpAggregateNetProvEntry
   ACCESS     not-accessible
   STATUS     mandatory
   DESCRIPTION
     "An entry in the vrIpBgpAggregateNetProvTable."
   INDEX {
      vrIndex,
      vrIpIndex,
      vrIpBgpIndex,
      vrIpBgpAggregatePrefixIndex,
      vrIpBgpAggregateLengthIndex,
      vrIpBgpAggregateNetIndex }
::= { vrIpBgpAggregateNetProvTable 1 }

VrIpBgpAggregateNetProvEntry ::= SEQUENCE {
   vrIpBgpAggregateNetPrefix
      IpAddress,
   vrIpBgpAggregateNetLength
      Unsigned32,
   vrIpBgpAggregateNetProtocol
      INTEGER,
   vrIpBgpAggregateNetEgpAsId
      Unsigned32,
   vrIpBgpAggregateNetBgpAsId
      Unsigned32,
   vrIpBgpAggregateNetOspfTag
      Hex,
   vrIpBgpAggregateNetRipInterface
      IpAddress,
   vrIpBgpAggregateNetAction
      INTEGER }

vrIpBgpAggregateNetPrefix OBJECT-TYPE
   SYNTAX     IpAddress 
   ACCESS     read-write
   STATUS     mandatory
   DESCRIPTION
     "This attribute specifies the network prefix whose length is 
      determined by the length attribute under the same Network 
      component."
   DEFVAL     { '00000000'H }  -- "0.0.0.0"
::= { vrIpBgpAggregateNetProvEntry 1 }

vrIpBgpAggregateNetLength OBJECT-TYPE
   SYNTAX     Unsigned32 (0..32)
   ACCESS     read-write
   STATUS     mandatory
   DESCRIPTION
     "This attribute specifies the length of the network prefix."
   DEFVAL     { 0 }
::= { vrIpBgpAggregateNetProvEntry 2 }

vrIpBgpAggregateNetProtocol OBJECT-TYPE
   SYNTAX     INTEGER  {
                 all(1),
                 egp(2),
                 rip(3),
                 ospfInternal(4),
                 ospfExternal(5),
                 staticLocal(6),
                 staticRemote(7),
                 bgpInternal(8),
                 bgpExternal(9) }
   ACCESS     read-write
   STATUS     mandatory
   DESCRIPTION
     "This attribute specifies the IP protocols to which this route should 
      belong."
   DEFVAL     { all }
::= { vrIpBgpAggregateNetProvEntry 3 }

vrIpBgpAggregateNetEgpAsId OBJECT-TYPE
   SYNTAX     Unsigned32 (0..65535)
   ACCESS     read-write
   STATUS     mandatory
   DESCRIPTION
     "This attribute specifies an EGP autonomous system number. 
      
      When this value is non-zero, the protocol attribute must be set to 
      either egp or to all. And this more specific route will be advertised 
      together with the aggregated route only if it is learned through egp 
      and this attribute matches the EGP autonomous system number 
      where the network is learned from.
      The default value 0 indicates that the EGP autonomous system 
      number is not specified."
   DEFVAL     { 0 }
::= { vrIpBgpAggregateNetProvEntry 4 }

vrIpBgpAggregateNetBgpAsId OBJECT-TYPE
   SYNTAX     Unsigned32 (0..65535)
   ACCESS     read-write
   STATUS     mandatory
   DESCRIPTION
     "This attribute specifies the BGP autonomous system number.
      
      When this value is non-zero, the protocol attribute must be set to 
      either bgp or to all. And this more specific route will be advertised 
      together with the aggregated route only if it is learned through BGP 
      and this attribute matches the BGP autonomous system number 
      where the network is learned from.
      The default value 0 indicates that the BGP autonomous system 
      number is not specified."
   DEFVAL     { 0 }
::= { vrIpBgpAggregateNetProvEntry 5 }

vrIpBgpAggregateNetOspfTag OBJECT-TYPE
   SYNTAX     Hex (0..4294967295)
   ACCESS     read-write
   STATUS     mandatory
   DESCRIPTION
     "This attribute specifies the OSPF tag.
      
      When this attribute is set to a value other than the default value 
      FFFFFFFF in hex, the protocol attribute must be set to either ospf 
      or to all. And this more specific route will be advertised together 
      with the aggregated route only if its OSPF tag matches this 
      value. 
      The default tag value 4294967295 (FFFFFFFF in hex) indicates that 
      the tag is not specified."
   DEFVAL     { 4294967295 }
::= { vrIpBgpAggregateNetProvEntry 6 }

vrIpBgpAggregateNetRipInterface OBJECT-TYPE
   SYNTAX     IpAddress 
   ACCESS     read-write
   STATUS     mandatory
   DESCRIPTION
     "This attribute specifies a local RIP interface which should be equal 
      to one of the IP addresses provisioned as a logicalIf component 
      under IpPort.
      
      When this value is non-zero, the value of the protocol attribute must 
      be either set to rip or to all. And this more specific route will be 
      advertised together with the aggregated route only if it is learned 
      through RIP and this RIP interface.
      The default value 0.0.0.0 indicates that the RIP interface is not 
      specified."
   DEFVAL     { '00000000'H }  -- "0.0.0.0"
::= { vrIpBgpAggregateNetProvEntry 7 }

vrIpBgpAggregateNetAction OBJECT-TYPE
   SYNTAX     INTEGER  {
                 aggregate(1),
                 advertise(2) }
   ACCESS     read-write
   STATUS     mandatory
   DESCRIPTION
     "This attribute specifies whether this network should be aggregated 
      or advertised out."
   DEFVAL     { aggregate }
::= { vrIpBgpAggregateNetProvEntry 8 }

-- 
-- *** THIS SUBTREE CURRENTLY NOT IMPLEMENTED ***
-- 

-- Vr/<string> Ip Bgp IndbEntry/<Ip Address>,<Decimal>,<Ip 
-- Address>
-- This component describes a BGP route received from one of its 
-- peers.

vrIpBgpIndb OBJECT IDENTIFIER ::= { vrIpBgp 7 }



vrIpBgpIndbRowStatusTable OBJECT-TYPE
   SYNTAX     SEQUENCE OF VrIpBgpIndbRowStatusEntry
   ACCESS     not-accessible
   STATUS     mandatory
   DESCRIPTION
     "*** THIS TABLE CURRENTLY NOT IMPLEMENTED ***

      This entry controls the addition and deletion of 
      vrIpBgpIndb components."
::= { vrIpBgpIndb 1 }

vrIpBgpIndbRowStatusEntry OBJECT-TYPE
   SYNTAX     VrIpBgpIndbRowStatusEntry
   ACCESS     not-accessible
   STATUS     mandatory
   DESCRIPTION
     "A single entry in the table represents a single 
      vrIpBgpIndb component."
   INDEX {
      vrIndex,
      vrIpIndex,
      vrIpBgpIndex,
      vrIpBgpIndbPrefixIndex,
      vrIpBgpIndbLengthIndex,
      vrIpBgpIndbPeerIndex }
::= { vrIpBgpIndbRowStatusTable 1 }

VrIpBgpIndbRowStatusEntry ::= SEQUENCE {
   vrIpBgpIndbRowStatus
      RowStatus,
   vrIpBgpIndbComponentName
      DisplayString,
   vrIpBgpIndbStorageType
      StorageType,
   vrIpBgpIndbPrefixIndex
      IpAddress,
   vrIpBgpIndbLengthIndex
      Integer32,
   vrIpBgpIndbPeerIndex
      IpAddress }

vrIpBgpIndbRowStatus OBJECT-TYPE
   SYNTAX     RowStatus 
   ACCESS     read-only
   STATUS     mandatory
   DESCRIPTION
     "This variable is used as the basis for SNMP naming of
      vrIpBgpIndb components.
      These components cannot be added nor deleted."
::= { vrIpBgpIndbRowStatusEntry 1 }

vrIpBgpIndbComponentName OBJECT-TYPE
   SYNTAX     DisplayString 
   ACCESS     read-only
   STATUS     mandatory
   DESCRIPTION
     "This variable provides the component's string name for
      use with the ASCII Console Interface"
::= { vrIpBgpIndbRowStatusEntry 2 }

vrIpBgpIndbStorageType OBJECT-TYPE
   SYNTAX     StorageType 
   ACCESS     read-only
   STATUS     mandatory
   DESCRIPTION
     "This variable represents the storage type value for the
      vrIpBgpIndb tables."
::= { vrIpBgpIndbRowStatusEntry 4 }

vrIpBgpIndbPrefixIndex OBJECT-TYPE
   SYNTAX     IpAddress 
   ACCESS     not-accessible
   STATUS     mandatory
   DESCRIPTION
     "This variable represents an index for the vrIpBgpIndb tables."
::= { vrIpBgpIndbRowStatusEntry 10 }

vrIpBgpIndbLengthIndex OBJECT-TYPE
   SYNTAX     Integer32 (0..32)
   ACCESS     not-accessible
   STATUS     mandatory
   DESCRIPTION
     "This variable represents an index for the vrIpBgpIndb tables."
::= { vrIpBgpIndbRowStatusEntry 11 }

vrIpBgpIndbPeerIndex OBJECT-TYPE
   SYNTAX     IpAddress 
   ACCESS     not-accessible
   STATUS     mandatory
   DESCRIPTION
     "This variable represents an index for the vrIpBgpIndb tables."
::= { vrIpBgpIndbRowStatusEntry 12 }

vrIpBgpIndbOperTable OBJECT-TYPE
   SYNTAX     SEQUENCE OF VrIpBgpIndbOperEntry
   ACCESS     not-accessible
   STATUS     mandatory
   DESCRIPTION
     "*** THIS TABLE CURRENTLY NOT IMPLEMENTED ***

      This group contains all the operational attributes of the IndbEntry 
      component."
::= { vrIpBgpIndb 10 }

vrIpBgpIndbOperEntry OBJECT-TYPE
   SYNTAX     VrIpBgpIndbOperEntry
   ACCESS     not-accessible
   STATUS     mandatory
   DESCRIPTION
     "An entry in the vrIpBgpIndbOperTable."
   INDEX {
      vrIndex,
      vrIpIndex,
      vrIpBgpIndex,
      vrIpBgpIndbPrefixIndex,
      vrIpBgpIndbLengthIndex,
      vrIpBgpIndbPeerIndex }
::= { vrIpBgpIndbOperTable 1 }

VrIpBgpIndbOperEntry ::= SEQUENCE {
   vrIpBgpIndbOrigin
      INTEGER,
   vrIpBgpIndbInLocaldb
      INTEGER,
   vrIpBgpIndbNextHop
      IpAddress,
   vrIpBgpIndbLocalPreference
      Unsigned32,
   vrIpBgpIndbCalcLocalPref
      Unsigned32,
   vrIpBgpIndbMultiExitDiscriminator
      Unsigned32,
   vrIpBgpIndbAtomicAggregate
      INTEGER,
   vrIpBgpIndbAggregatorAs
      Unsigned32,
   vrIpBgpIndbAggregatorAddr
      IpAddress,
   vrIpBgpIndbAsPath
      AsciiString,
   vrIpBgpIndbUnknownAttributes
      AsciiString,
   vrIpBgpIndbCommunityPath
      AsciiString,
   vrIpBgpIndbAsOriginatorId
      IpAddress }

vrIpBgpIndbOrigin OBJECT-TYPE
   SYNTAX     INTEGER  {
                 igp(1),
                 egp(2),
                 incomplete(3) }
   ACCESS     read-only
   STATUS     mandatory
   DESCRIPTION
     "This attribute indicates the ultimate origin of the path information. 
      A value of incomplete means this information is not available."
::= { vrIpBgpIndbOperEntry 4 }

vrIpBgpIndbInLocaldb OBJECT-TYPE
   SYNTAX     INTEGER  {
                 false(1),
                 true(2) }
   ACCESS     read-only
   STATUS     mandatory
   DESCRIPTION
     "This attribute indicates whether or not this route was chosen as the 
      best BGP4 route."
::= { vrIpBgpIndbOperEntry 5 }

vrIpBgpIndbNextHop OBJECT-TYPE
   SYNTAX     IpAddress 
   ACCESS     read-only
   STATUS     mandatory
   DESCRIPTION
     "This attribute indicates the IP address of the border router that 
      should be used as the next hop for the destination network."
::= { vrIpBgpIndbOperEntry 6 }

vrIpBgpIndbLocalPreference OBJECT-TYPE
   SYNTAX     Unsigned32 (0..4294967295)
   ACCESS     read-only
   STATUS     mandatory
   DESCRIPTION
     "This attribute indicates our IBGP peer's degree of preference for an 
      advertised route. A higher value indicates a more preferred route."
::= { vrIpBgpIndbOperEntry 7 }

vrIpBgpIndbCalcLocalPref OBJECT-TYPE
   SYNTAX     Unsigned32 (0..4294967295)
   ACCESS     read-only
   STATUS     mandatory
   DESCRIPTION
     "This attribute indicates our degree of preference for this route. A 
      higher value indicates a more preferred route."
::= { vrIpBgpIndbOperEntry 8 }

vrIpBgpIndbMultiExitDiscriminator OBJECT-TYPE
   SYNTAX     Unsigned32 (0..4294967295)
   ACCESS     read-only
   STATUS     mandatory
   DESCRIPTION
     "This attribute indicates a metric used to discriminate between 
      multiple exit points to the same adjacent autonomous system. A 
      lower value indicates a more preferred route."
::= { vrIpBgpIndbOperEntry 9 }

vrIpBgpIndbAtomicAggregate OBJECT-TYPE
   SYNTAX     INTEGER  {
                 lessSpecificRouteNotSelected(1),
                 lessSpecificRouteSelected(2) }
   ACCESS     read-only
   STATUS     mandatory
   DESCRIPTION
     "This attribute indicates whether or not the local system has selected 
      a less specific route without selecting a more specific route."
::= { vrIpBgpIndbOperEntry 10 }

vrIpBgpIndbAggregatorAs OBJECT-TYPE
   SYNTAX     Unsigned32 (0..65535)
   ACCESS     read-only
   STATUS     mandatory
   DESCRIPTION
     "This attribute indicates the AS number of the last BGP4 speaker 
      that performed route aggregation. A value of zero (0) indicates the 
      absence of this attribute."
::= { vrIpBgpIndbOperEntry 11 }

vrIpBgpIndbAggregatorAddr OBJECT-TYPE
   SYNTAX     IpAddress 
   ACCESS     read-only
   STATUS     mandatory
   DESCRIPTION
     "This attribute indicates the IP address of the last BGP4 speaker that 
      performed route aggregation. A value of 0.0.0.0 indicates the 
      absence of this attribute."
::= { vrIpBgpIndbOperEntry 12 }

vrIpBgpIndbAsPath OBJECT-TYPE
   SYNTAX     AsciiString (SIZE (2..255))
   ACCESS     read-only
   STATUS     mandatory
   DESCRIPTION
     "This attribute indicates the sequence of AS path segments. The AS 
      Path Attribute lists the ASs in reverse traversal order."
::= { vrIpBgpIndbOperEntry 13 }

vrIpBgpIndbUnknownAttributes OBJECT-TYPE
   SYNTAX     AsciiString (SIZE (0..255))
   ACCESS     read-only
   STATUS     mandatory
   DESCRIPTION
     "This attribute indicates all the path attributes not understood by this 
      Bgp component instance."
::= { vrIpBgpIndbOperEntry 14 }

vrIpBgpIndbCommunityPath OBJECT-TYPE
   SYNTAX     AsciiString (SIZE (0..255))
   ACCESS     read-only
   STATUS     mandatory
   DESCRIPTION
     "This attribute indicates the Community path attribute."
::= { vrIpBgpIndbOperEntry 15 }

vrIpBgpIndbAsOriginatorId OBJECT-TYPE
   SYNTAX     IpAddress 
   ACCESS     read-only
   STATUS     mandatory
   DESCRIPTION
     "This attribute is associated with the Route Reflector. It indicates the 
      router-id of the originator in the local AS. A value of 0.0.0.0 
      indicates this attribute is not present in the learned IBGP route or if 
      this Bgp instance is not a Route Reflector."
::= { vrIpBgpIndbOperEntry 16 }

vrIpBgpIndbRrClusterListTable OBJECT-TYPE
   SYNTAX     SEQUENCE OF VrIpBgpIndbRrClusterListEntry
   ACCESS     not-accessible
   STATUS     mandatory
   DESCRIPTION
     "*** THIS TABLE CURRENTLY NOT IMPLEMENTED ***

      This attribute indicates a sequence of cluster-ids that the route has 
      traversed. A blank list indicates this attribute is not present in the 
      learned IBGP route or if this Bgp instance is not a Route Reflector."
::= { vrIpBgpIndb 798 }

vrIpBgpIndbRrClusterListEntry OBJECT-TYPE
   SYNTAX     VrIpBgpIndbRrClusterListEntry
   ACCESS     not-accessible
   STATUS     mandatory
   DESCRIPTION
     "An entry in the vrIpBgpIndbRrClusterListTable."
   INDEX {
      vrIndex,
      vrIpIndex,
      vrIpBgpIndex,
      vrIpBgpIndbPrefixIndex,
      vrIpBgpIndbLengthIndex,
      vrIpBgpIndbPeerIndex,
      vrIpBgpIndbRrClusterListValue }
::= { vrIpBgpIndbRrClusterListTable 1 }

VrIpBgpIndbRrClusterListEntry ::= SEQUENCE {
   vrIpBgpIndbRrClusterListValue
      IpAddress }

vrIpBgpIndbRrClusterListValue OBJECT-TYPE
   SYNTAX     IpAddress 
   ACCESS     read-only
   STATUS     mandatory
   DESCRIPTION
     "This variable represents both the value and the index for the
      vrIpBgpIndbRrClusterListTable."
::= { vrIpBgpIndbRrClusterListEntry 1 }

-- 
-- *** THIS SUBTREE CURRENTLY NOT IMPLEMENTED ***
-- 

-- Vr/<string> Ip Bgp LocaldbEntry/<Ip Address>,<Decimal>,<Ip 
-- Address>
-- This component describes an entry in the BGP local database. This 
-- database contains the routing information that the BGP speaker has 
-- selected by applying its local import policies and decision process 
-- to the routing information stored in IndbEntry.

vrIpBgpLocaldb OBJECT IDENTIFIER ::= { vrIpBgp 8 }



vrIpBgpLocaldbRowStatusTable OBJECT-TYPE
   SYNTAX     SEQUENCE OF VrIpBgpLocaldbRowStatusEntry
   ACCESS     not-accessible
   STATUS     mandatory
   DESCRIPTION
     "*** THIS TABLE CURRENTLY NOT IMPLEMENTED ***

      This entry controls the addition and deletion of 
      vrIpBgpLocaldb components."
::= { vrIpBgpLocaldb 1 }

vrIpBgpLocaldbRowStatusEntry OBJECT-TYPE
   SYNTAX     VrIpBgpLocaldbRowStatusEntry
   ACCESS     not-accessible
   STATUS     mandatory
   DESCRIPTION
     "A single entry in the table represents a single 
      vrIpBgpLocaldb component."
   INDEX {
      vrIndex,
      vrIpIndex,
      vrIpBgpIndex,
      vrIpBgpLocaldbPrefixIndex,
      vrIpBgpLocaldbLengthIndex,
      vrIpBgpLocaldbPeerIndex }
::= { vrIpBgpLocaldbRowStatusTable 1 }

VrIpBgpLocaldbRowStatusEntry ::= SEQUENCE {
   vrIpBgpLocaldbRowStatus
      RowStatus,
   vrIpBgpLocaldbComponentName
      DisplayString,
   vrIpBgpLocaldbStorageType
      StorageType,
   vrIpBgpLocaldbPrefixIndex
      IpAddress,
   vrIpBgpLocaldbLengthIndex
      Integer32,
   vrIpBgpLocaldbPeerIndex
      IpAddress }

vrIpBgpLocaldbRowStatus OBJECT-TYPE
   SYNTAX     RowStatus 
   ACCESS     read-only
   STATUS     mandatory
   DESCRIPTION
     "This variable is used as the basis for SNMP naming of
      vrIpBgpLocaldb components.
      These components cannot be added nor deleted."
::= { vrIpBgpLocaldbRowStatusEntry 1 }

vrIpBgpLocaldbComponentName OBJECT-TYPE
   SYNTAX     DisplayString 
   ACCESS     read-only
   STATUS     mandatory
   DESCRIPTION
     "This variable provides the component's string name for
      use with the ASCII Console Interface"
::= { vrIpBgpLocaldbRowStatusEntry 2 }

vrIpBgpLocaldbStorageType OBJECT-TYPE
   SYNTAX     StorageType 
   ACCESS     read-only
   STATUS     mandatory
   DESCRIPTION
     "This variable represents the storage type value for the
      vrIpBgpLocaldb tables."
::= { vrIpBgpLocaldbRowStatusEntry 4 }

vrIpBgpLocaldbPrefixIndex OBJECT-TYPE
   SYNTAX     IpAddress 
   ACCESS     not-accessible
   STATUS     mandatory
   DESCRIPTION
     "This variable represents an index for the vrIpBgpLocaldb tables."
::= { vrIpBgpLocaldbRowStatusEntry 10 }

vrIpBgpLocaldbLengthIndex OBJECT-TYPE
   SYNTAX     Integer32 (0..32)
   ACCESS     not-accessible
   STATUS     mandatory
   DESCRIPTION
     "This variable represents an index for the vrIpBgpLocaldb tables."
::= { vrIpBgpLocaldbRowStatusEntry 11 }

vrIpBgpLocaldbPeerIndex OBJECT-TYPE
   SYNTAX     IpAddress 
   ACCESS     not-accessible
   STATUS     mandatory
   DESCRIPTION
     "This variable represents an index for the vrIpBgpLocaldb tables."
::= { vrIpBgpLocaldbRowStatusEntry 12 }

vrIpBgpLocaldbOperTable OBJECT-TYPE
   SYNTAX     SEQUENCE OF VrIpBgpLocaldbOperEntry
   ACCESS     not-accessible
   STATUS     mandatory
   DESCRIPTION
     "*** THIS TABLE CURRENTLY NOT IMPLEMENTED ***

      This group contains all the operational attributes of the 
      LocaldbEntry component."
::= { vrIpBgpLocaldb 10 }

vrIpBgpLocaldbOperEntry OBJECT-TYPE
   SYNTAX     VrIpBgpLocaldbOperEntry
   ACCESS     not-accessible
   STATUS     mandatory
   DESCRIPTION
     "An entry in the vrIpBgpLocaldbOperTable."
   INDEX {
      vrIndex,
      vrIpIndex,
      vrIpBgpIndex,
      vrIpBgpLocaldbPrefixIndex,
      vrIpBgpLocaldbLengthIndex,
      vrIpBgpLocaldbPeerIndex }
::= { vrIpBgpLocaldbOperTable 1 }

VrIpBgpLocaldbOperEntry ::= SEQUENCE {
   vrIpBgpLocaldbOrigin
      INTEGER,
   vrIpBgpLocaldbNextHop
      IpAddress,
   vrIpBgpLocaldbLocalPreference
      Unsigned32,
   vrIpBgpLocaldbMultiExitDiscriminator
      Unsigned32,
   vrIpBgpLocaldbAtomicAggregate
      INTEGER,
   vrIpBgpLocaldbAggregatorAs
      Unsigned32,
   vrIpBgpLocaldbAggregatorAddr
      IpAddress,
   vrIpBgpLocaldbAsPath
      AsciiString,
   vrIpBgpLocaldbUnknownAttributes
      AsciiString,
   vrIpBgpLocaldbCommunityPath
      AsciiString,
   vrIpBgpLocaldbAsOriginatorId
      IpAddress }

vrIpBgpLocaldbOrigin OBJECT-TYPE
   SYNTAX     INTEGER  {
                 igp(1),
                 egp(2),
                 incomplete(3) }
   ACCESS     read-only
   STATUS     mandatory
   DESCRIPTION
     "This attribute indicates the ultimate origin of the path information. 
      A value of incomplete means this information is not available."
::= { vrIpBgpLocaldbOperEntry 4 }

vrIpBgpLocaldbNextHop OBJECT-TYPE
   SYNTAX     IpAddress 
   ACCESS     read-only
   STATUS     mandatory
   DESCRIPTION
     "This attribute indicates the IP address of the border router that 
      should be used as the next hop for the destination network."
::= { vrIpBgpLocaldbOperEntry 5 }

vrIpBgpLocaldbLocalPreference OBJECT-TYPE
   SYNTAX     Unsigned32 (0..4294967295)
   ACCESS     read-only
   STATUS     mandatory
   DESCRIPTION
     "This attribute indicates our IBGP peer's degree of preference for an 
      advertised route. A higher value indicates a more preferred route."
::= { vrIpBgpLocaldbOperEntry 6 }

vrIpBgpLocaldbMultiExitDiscriminator OBJECT-TYPE
   SYNTAX     Unsigned32 (0..4294967295)
   ACCESS     read-only
   STATUS     mandatory
   DESCRIPTION
     "This attribute indicates a metric used to discriminate between 
      multiple exit points to the same adjacent autonomous system. A 
      lower value indicates a more preferred route."
::= { vrIpBgpLocaldbOperEntry 7 }

vrIpBgpLocaldbAtomicAggregate OBJECT-TYPE
   SYNTAX     INTEGER  {
                 lessSpecificRouteNotSelected(1),
                 lessSpecificRouteSelected(2) }
   ACCESS     read-only
   STATUS     mandatory
   DESCRIPTION
     "This attribute indicates whether or not the local system has selected 
      a less specific route without selecting a more specific route."
::= { vrIpBgpLocaldbOperEntry 8 }

vrIpBgpLocaldbAggregatorAs OBJECT-TYPE
   SYNTAX     Unsigned32 (0..65535)
   ACCESS     read-only
   STATUS     mandatory
   DESCRIPTION
     "This attribute indicates the AS number of the last BGP4 speaker 
      that performed route aggregation. A value of zero (0) indicates the 
      absence of this attribute."
::= { vrIpBgpLocaldbOperEntry 9 }

vrIpBgpLocaldbAggregatorAddr OBJECT-TYPE
   SYNTAX     IpAddress 
   ACCESS     read-only
   STATUS     mandatory
   DESCRIPTION
     "This attribute indicates the IP address of the last BGP4 speaker that 
      performed route aggregation. A value of 0.0.0.0 indicates the 
      absence of this attribute."
::= { vrIpBgpLocaldbOperEntry 10 }

vrIpBgpLocaldbAsPath OBJECT-TYPE
   SYNTAX     AsciiString (SIZE (2..255))
   ACCESS     read-only
   STATUS     mandatory
   DESCRIPTION
     "This attribute indicates the sequence of AS path segments. The AS 
      Path Attribute lists the ASs in reverse traversal order."
::= { vrIpBgpLocaldbOperEntry 11 }

vrIpBgpLocaldbUnknownAttributes OBJECT-TYPE
   SYNTAX     AsciiString (SIZE (0..255))
   ACCESS     read-only
   STATUS     mandatory
   DESCRIPTION
     "This attribute indicates all the path attributes not understood by this 
      Bgp component instance."
::= { vrIpBgpLocaldbOperEntry 12 }

vrIpBgpLocaldbCommunityPath OBJECT-TYPE
   SYNTAX     AsciiString (SIZE (0..255))
   ACCESS     read-only
   STATUS     mandatory
   DESCRIPTION
     "This attribute indicates the Community path attribute."
::= { vrIpBgpLocaldbOperEntry 13 }

vrIpBgpLocaldbAsOriginatorId OBJECT-TYPE
   SYNTAX     IpAddress 
   ACCESS     read-only
   STATUS     mandatory
   DESCRIPTION
     "This attribute is associated with the Route Reflector. It indicates the 
      router-id of the originator in the local AS. A value of 0.0.0.0 
      indicates this attribute is not present in the learned IBGP route or if 
      this Bgp instance is not a Route Reflector."
::= { vrIpBgpLocaldbOperEntry 14 }

vrIpBgpLocaldbRrClusterListTable OBJECT-TYPE
   SYNTAX     SEQUENCE OF VrIpBgpLocaldbRrClusterListEntry
   ACCESS     not-accessible
   STATUS     mandatory
   DESCRIPTION
     "*** THIS TABLE CURRENTLY NOT IMPLEMENTED ***

      This attribute indicates a sequence of cluster-ids that the route has 
      traversed. A blank list indicates this attribute is not present in the 
      learned IBGP route or if this Bgp instance is not a Route Reflector."
::= { vrIpBgpLocaldb 797 }

vrIpBgpLocaldbRrClusterListEntry OBJECT-TYPE
   SYNTAX     VrIpBgpLocaldbRrClusterListEntry
   ACCESS     not-accessible
   STATUS     mandatory
   DESCRIPTION
     "An entry in the vrIpBgpLocaldbRrClusterListTable."
   INDEX {
      vrIndex,
      vrIpIndex,
      vrIpBgpIndex,
      vrIpBgpLocaldbPrefixIndex,
      vrIpBgpLocaldbLengthIndex,
      vrIpBgpLocaldbPeerIndex,
      vrIpBgpLocaldbRrClusterListValue }
::= { vrIpBgpLocaldbRrClusterListTable 1 }

VrIpBgpLocaldbRrClusterListEntry ::= SEQUENCE {
   vrIpBgpLocaldbRrClusterListValue
      IpAddress }

vrIpBgpLocaldbRrClusterListValue OBJECT-TYPE
   SYNTAX     IpAddress 
   ACCESS     read-only
   STATUS     mandatory
   DESCRIPTION
     "This variable represents both the value and the index for the
      vrIpBgpLocaldbRrClusterListTable."
::= { vrIpBgpLocaldbRrClusterListEntry 1 }

-- 
-- *** THIS SUBTREE CURRENTLY NOT IMPLEMENTED ***
-- 

-- Vr/<string> Ip Bgp OutdbEntry/<Ip Address>,<Decimal>,<Ip 
-- Address>
-- This component describes an entry in the BGP output database that 
-- BGP advertises to its peers. The database contents are selected by 
-- applying its local export policies to the routing information stored 
-- in the IP forwarding table.

vrIpBgpOutdb OBJECT IDENTIFIER ::= { vrIpBgp 9 }



vrIpBgpOutdbRowStatusTable OBJECT-TYPE
   SYNTAX     SEQUENCE OF VrIpBgpOutdbRowStatusEntry
   ACCESS     not-accessible
   STATUS     mandatory
   DESCRIPTION
     "*** THIS TABLE CURRENTLY NOT IMPLEMENTED ***

      This entry controls the addition and deletion of 
      vrIpBgpOutdb components."
::= { vrIpBgpOutdb 1 }

vrIpBgpOutdbRowStatusEntry OBJECT-TYPE
   SYNTAX     VrIpBgpOutdbRowStatusEntry
   ACCESS     not-accessible
   STATUS     mandatory
   DESCRIPTION
     "A single entry in the table represents a single 
      vrIpBgpOutdb component."
   INDEX {
      vrIndex,
      vrIpIndex,
      vrIpBgpIndex,
      vrIpBgpOutdbPrefixIndex,
      vrIpBgpOutdbLengthIndex,
      vrIpBgpOutdbPeerIndex }
::= { vrIpBgpOutdbRowStatusTable 1 }

VrIpBgpOutdbRowStatusEntry ::= SEQUENCE {
   vrIpBgpOutdbRowStatus
      RowStatus,
   vrIpBgpOutdbComponentName
      DisplayString,
   vrIpBgpOutdbStorageType
      StorageType,
   vrIpBgpOutdbPrefixIndex
      IpAddress,
   vrIpBgpOutdbLengthIndex
      Integer32,
   vrIpBgpOutdbPeerIndex
      IpAddress }

vrIpBgpOutdbRowStatus OBJECT-TYPE
   SYNTAX     RowStatus 
   ACCESS     read-only
   STATUS     mandatory
   DESCRIPTION
     "This variable is used as the basis for SNMP naming of
      vrIpBgpOutdb components.
      These components cannot be added nor deleted."
::= { vrIpBgpOutdbRowStatusEntry 1 }

vrIpBgpOutdbComponentName OBJECT-TYPE
   SYNTAX     DisplayString 
   ACCESS     read-only
   STATUS     mandatory
   DESCRIPTION
     "This variable provides the component's string name for
      use with the ASCII Console Interface"
::= { vrIpBgpOutdbRowStatusEntry 2 }

vrIpBgpOutdbStorageType OBJECT-TYPE
   SYNTAX     StorageType 
   ACCESS     read-only
   STATUS     mandatory
   DESCRIPTION
     "This variable represents the storage type value for the
      vrIpBgpOutdb tables."
::= { vrIpBgpOutdbRowStatusEntry 4 }

vrIpBgpOutdbPrefixIndex OBJECT-TYPE
   SYNTAX     IpAddress 
   ACCESS     not-accessible
   STATUS     mandatory
   DESCRIPTION
     "This variable represents an index for the vrIpBgpOutdb tables."
::= { vrIpBgpOutdbRowStatusEntry 10 }

vrIpBgpOutdbLengthIndex OBJECT-TYPE
   SYNTAX     Integer32 (0..32)
   ACCESS     not-accessible
   STATUS     mandatory
   DESCRIPTION
     "This variable represents an index for the vrIpBgpOutdb tables."
::= { vrIpBgpOutdbRowStatusEntry 11 }

vrIpBgpOutdbPeerIndex OBJECT-TYPE
   SYNTAX     IpAddress 
   ACCESS     not-accessible
   STATUS     mandatory
   DESCRIPTION
     "This variable represents an index for the vrIpBgpOutdb tables."
::= { vrIpBgpOutdbRowStatusEntry 12 }

vrIpBgpOutdbOperTable OBJECT-TYPE
   SYNTAX     SEQUENCE OF VrIpBgpOutdbOperEntry
   ACCESS     not-accessible
   STATUS     mandatory
   DESCRIPTION
     "*** THIS TABLE CURRENTLY NOT IMPLEMENTED ***

      This group contains all the operational attributes of the OutdbEntry 
      component."
::= { vrIpBgpOutdb 10 }

vrIpBgpOutdbOperEntry OBJECT-TYPE
   SYNTAX     VrIpBgpOutdbOperEntry
   ACCESS     not-accessible
   STATUS     mandatory
   DESCRIPTION
     "An entry in the vrIpBgpOutdbOperTable."
   INDEX {
      vrIndex,
      vrIpIndex,
      vrIpBgpIndex,
      vrIpBgpOutdbPrefixIndex,
      vrIpBgpOutdbLengthIndex,
      vrIpBgpOutdbPeerIndex }
::= { vrIpBgpOutdbOperTable 1 }

VrIpBgpOutdbOperEntry ::= SEQUENCE {
   vrIpBgpOutdbOrigin
      INTEGER,
   vrIpBgpOutdbNextHop
      IpAddress,
   vrIpBgpOutdbLocalPreference
      Unsigned32,
   vrIpBgpOutdbMultiExitDiscriminator
      Unsigned32,
   vrIpBgpOutdbAtomicAggregate
      INTEGER,
   vrIpBgpOutdbAggregatorAs
      Unsigned32,
   vrIpBgpOutdbAggregatorAddr
      IpAddress,
   vrIpBgpOutdbAsPath
      AsciiString,
   vrIpBgpOutdbUnknownAttributes
      AsciiString,
   vrIpBgpOutdbCommunityPath
      AsciiString,
   vrIpBgpOutdbAsOriginatorId
      IpAddress }

vrIpBgpOutdbOrigin OBJECT-TYPE
   SYNTAX     INTEGER  {
                 igp(1),
                 egp(2),
                 incomplete(3) }
   ACCESS     read-only
   STATUS     mandatory
   DESCRIPTION
     "This attribute indicates the ultimate origin of the path information. 
      A value of incomplete means this information is not available."
::= { vrIpBgpOutdbOperEntry 4 }

vrIpBgpOutdbNextHop OBJECT-TYPE
   SYNTAX     IpAddress 
   ACCESS     read-only
   STATUS     mandatory
   DESCRIPTION
     "This attribute indicates the IP address of the border router that 
      should be used as the next hop for the destination network."
::= { vrIpBgpOutdbOperEntry 5 }

vrIpBgpOutdbLocalPreference OBJECT-TYPE
   SYNTAX     Unsigned32 (0..4294967295)
   ACCESS     read-only
   STATUS     mandatory
   DESCRIPTION
     "This attribute indicates this Bgp instance's degree of preference for 
      an advertised route. A higher value indicates a more preferred route."
::= { vrIpBgpOutdbOperEntry 6 }

vrIpBgpOutdbMultiExitDiscriminator OBJECT-TYPE
   SYNTAX     Unsigned32 (0..4294967295)
   ACCESS     read-only
   STATUS     mandatory
   DESCRIPTION
     "This attribute indicates a metric used to discriminate between 
      multiple exit points to the same adjacent autonomous system. A 
      lower value indicates a more preferred route."
::= { vrIpBgpOutdbOperEntry 7 }

vrIpBgpOutdbAtomicAggregate OBJECT-TYPE
   SYNTAX     INTEGER  {
                 lessSpecificRouteNotSelected(1),
                 lessSpecificRouteSelected(2) }
   ACCESS     read-only
   STATUS     mandatory
   DESCRIPTION
     "This attribute indicates whether or not the local system has selected 
      a less specific route without selecting a more specific route."
::= { vrIpBgpOutdbOperEntry 8 }

vrIpBgpOutdbAggregatorAs OBJECT-TYPE
   SYNTAX     Unsigned32 (0..65535)
   ACCESS     read-only
   STATUS     mandatory
   DESCRIPTION
     "This attribute indicates the AS number of the last BGP4 speaker 
      that performed route aggregation. A value of zero (0) indicates the 
      absence of this attribute."
::= { vrIpBgpOutdbOperEntry 9 }

vrIpBgpOutdbAggregatorAddr OBJECT-TYPE
   SYNTAX     IpAddress 
   ACCESS     read-only
   STATUS     mandatory
   DESCRIPTION
     "This attribute indicates the IP address of the last BGP4 speaker that 
      performed route aggregation. A value of 0.0.0.0 indicates the 
      absence of this attribute."
::= { vrIpBgpOutdbOperEntry 10 }

vrIpBgpOutdbAsPath OBJECT-TYPE
   SYNTAX     AsciiString (SIZE (2..255))
   ACCESS     read-only
   STATUS     mandatory
   DESCRIPTION
     "This attribute indicates the sequence of AS path segments. The AS 
      Path Attribute lists the ASs in reverse traversal order."
::= { vrIpBgpOutdbOperEntry 11 }

vrIpBgpOutdbUnknownAttributes OBJECT-TYPE
   SYNTAX     AsciiString (SIZE (0..255))
   ACCESS     read-only
   STATUS     mandatory
   DESCRIPTION
     "This attribute indicates all the path attributes not understood by this 
      Bgp component instance."
::= { vrIpBgpOutdbOperEntry 12 }

vrIpBgpOutdbCommunityPath OBJECT-TYPE
   SYNTAX     AsciiString (SIZE (0..255))
   ACCESS     read-only
   STATUS     mandatory
   DESCRIPTION
     "This attribute indicates the Community path attribute."
::= { vrIpBgpOutdbOperEntry 13 }

vrIpBgpOutdbAsOriginatorId OBJECT-TYPE
   SYNTAX     IpAddress 
   ACCESS     read-only
   STATUS     mandatory
   DESCRIPTION
     "This attribute is associated with the Route Reflector. It indicates the 
      router-id of the originator of a route in the local AS. When the 
      Route Reflector distributes a learned IBGP route to other IBGP 
      speakers, the value of this attribute in the learned route is used if 
      one is present; othewise, the Route Reflector's router-id is used. A 
      value of 0.0.0.0 indicates this Bgp instance is not a Route Reflector."
::= { vrIpBgpOutdbOperEntry 14 }

vrIpBgpOutdbRrClusterListTable OBJECT-TYPE
   SYNTAX     SEQUENCE OF VrIpBgpOutdbRrClusterListEntry
   ACCESS     not-accessible
   STATUS     mandatory
   DESCRIPTION
     "*** THIS TABLE CURRENTLY NOT IMPLEMENTED ***

      This attribute indicates a sequence of cluster-ids that the route has 
      traversed. When the Route Reflector redistributes a learned IBGP to 
      other IBGP speakers, the cluster id of this Route Reflector is 
      appended to the cluster list of the learned IBGP route. If this Bgp 
      instance is not a Route Reflector, this attribute is blank."
::= { vrIpBgpOutdb 799 }

vrIpBgpOutdbRrClusterListEntry OBJECT-TYPE
   SYNTAX     VrIpBgpOutdbRrClusterListEntry
   ACCESS     not-accessible
   STATUS     mandatory
   DESCRIPTION
     "An entry in the vrIpBgpOutdbRrClusterListTable."
   INDEX {
      vrIndex,
      vrIpIndex,
      vrIpBgpIndex,
      vrIpBgpOutdbPrefixIndex,
      vrIpBgpOutdbLengthIndex,
      vrIpBgpOutdbPeerIndex,
      vrIpBgpOutdbRrClusterListValue }
::= { vrIpBgpOutdbRrClusterListTable 1 }

VrIpBgpOutdbRrClusterListEntry ::= SEQUENCE {
   vrIpBgpOutdbRrClusterListValue
      IpAddress }

vrIpBgpOutdbRrClusterListValue OBJECT-TYPE
   SYNTAX     IpAddress 
   ACCESS     read-only
   STATUS     mandatory
   DESCRIPTION
     "This variable represents both the value and the index for the
      vrIpBgpOutdbRrClusterListTable."
::= { vrIpBgpOutdbRrClusterListEntry 1 }




-- 
-- Version and Compliance statements
-- 



-- Object-Group Statement:
-- A list of all current accessible leaf objects.

-- OBJECTS { vrIpBgpRouteReflectorCluster,
--           vrIpBgpImportCommunityExpression,
--           vrIpBgpAggregateNetProtocol,
--           vrIpBgpAggregateNetRipInterface,
--           vrIpBgpExportPeerAs,
--           vrIpBgpPeerInErrorMsgs,
--           vrIpBgpPeerVersionNegotiated,
--           vrIpBgpExportRipNeighbor,
--           vrIpBgpPeerComponentName,
--           vrIpBgpAdminState,
--           vrIpBgpExportMultiExitDisc,
--           vrIpBgpImportComponentName,
--           vrIpBgpIndbAggregatorAs,
--           vrIpBgpPeerInUpdateElapsedTime,
--           vrIpBgpPeerOutMsgs,
--           vrIpBgpIndbNextHop,
--           vrIpBgpIndbAggregatorAddr,
--           vrIpBgpIndbAtomicAggregate,
--           vrIpBgpExportInsertDummyAs,
--           vrIpBgpRouteThrottleInter,
--           vrIpBgpAggregateNetEgpAsId,
--           vrIpBgpRouteReflector,
--           vrIpBgpLocalAs,
--           vrIpBgpImportExpressPreference,
--           vrIpBgpLocaldbUnknownAttributes,
--           vrIpBgpIndbAsOriginatorId,
--           vrIpBgpImportAppendCommunity,
--           vrIpBgpAggregateNetComponentName,
--           vrIpBgpPeerLocalPort,
--           vrIpBgpOutdbComponentName,
--           vrIpBgpPeerInErrors,
--           vrIpBgpAggregateNetRowStatus,
--           vrIpBgpImportUsageFlag,
--           vrIpBgpDefaultLocalPreference,
--           vrIpBgpImportNetStorageType,
--           vrIpBgpIndbComponentName,
--           vrIpBgpIndbCalcLocalPref,
--           vrIpBgpExportPeerIpAddress,
--           vrIpBgpAsWeight,
--           vrIpBgpLocaldbAtomicAggregate,
--           vrIpBgpExportAdvertiseStatus,
--           vrIpBgpExportOspfTag,
--           vrIpBgpIndbMultiExitDiscriminator,
--           vrIpBgpImportNetLength,
--           vrIpBgpLocaldbStorageType,
--           vrIpBgpOutdbStorageType,
--           vrIpBgpLocaldbMultiExitDiscriminator,
--           vrIpBgpPeerInMsgs,
--           vrIpBgpImportAsPathExpression,
--           vrIpBgpPeerStorageType,
--           vrIpBgpInErrorMsgs,
--           vrIpBgpOutdbMultiExitDiscriminator,
--           vrIpBgpImportLocalPreference,
--           vrIpBgpLocaldbAggregatorAddr,
--           vrIpBgpComponentName,
--           vrIpBgpLocaldbOrigin,
--           vrIpBgpImportNetRowStatus,
--           vrIpBgpPeerLocalAddressConfigured,
--           vrIpBgpPeerHoldTimeConfigured,
--           vrIpBgpImportStorageType,
--           vrIpBgpLocaldbNextHop,
--           vrIpBgpPeerBgpIdentifier,
--           vrIpBgpImportNetPrefix,
--           vrIpBgpOutdbRowStatus,
--           vrIpBgpOutdbAsPath,
--           vrIpBgpPeerKeepAliveNegotiated,
--           vrIpBgpRouteThrottleLimit,
--           vrIpBgpExportNetComponentName,
--           vrIpBgpAggregateNetOspfTag,
--           vrIpBgpIndbLocalPreference,
--           vrIpBgpOutdbCommunityPath,
--           vrIpBgpPeerAdminState,
--           vrIpBgpPeerConnectRetryTime,
--           vrIpBgpAggregateComponentName,
--           vrIpBgpAggregateNetStorageType,
--           vrIpBgpIndbInLocaldb,
--           vrIpBgpInErrors,
--           vrIpBgpIndbUnknownAttributes,
--           vrIpBgpLocaldbAggregatorAs,
--           vrIpBgpPeerRowStatus,
--           vrIpBgpDefaultMultiExitDisc,
--           vrIpBgpRowStatus,
--           vrIpBgpExportCommunityExpression,
--           vrIpBgpPeerConnectionState,
--           vrIpBgpImportRowStatus,
--           vrIpBgpPeerHoldTimeNegotiated,
--           vrIpBgpAggregateNetLength,
--           vrIpBgpImportOriginProtocol,
--           vrIpBgpExportEgpAsId,
--           vrIpBgpPeerMinRouteAdvTime,
--           vrIpBgpTableVersion,
--           vrIpBgpPeerConnectionEstablishedTime,
--           vrIpBgpSnmpOperStatus,
--           vrIpBgpPeerRemotePort,
--           vrIpBgpPeerUsageState,
--           vrIpBgpOutErrorMsgs,
--           vrIpBgpPeerPeerAs,
--           vrIpBgpInMsgs,
--           vrIpBgpExportComponentName,
--           vrIpBgpImportPeerAs,
--           vrIpBgpAsStorageType,
--           vrIpBgpLocaldbCommunityPath,
--           vrIpBgpIndbRowStatus,
--           vrIpBgpAggregateStorageType,
--           vrIpBgpPeerKeepAliveConfigured,
--           vrIpBgpStorageType,
--           vrIpBgpAggregateNetPrefix,
--           vrIpBgpPeerOperationalState,
--           vrIpBgpExportSendMultiExitDiscToEbgp,
--           vrIpBgpOutdbAsOriginatorId,
--           vrIpBgpExportRipInterface,
--           vrIpBgpExportSendCommunity,
--           vrIpBgpOutdbAtomicAggregate,
--           vrIpBgpPeerInRoutes,
--           vrIpBgpPeerOutDiscards,
--           vrIpBgpLocaldbLocalPreference,
--           vrIpBgpExportNetStorageType,
--           vrIpBgpPeerLastError,
--           vrIpBgpIndbAsPath,
--           vrIpBgpIndbRrClusterListValue,
--           vrIpBgpAggregateRowStatus,
--           vrIpBgpImportPreferredOver,
--           vrIpBgpExportBgpAsId,
--           vrIpBgpSnmpAdminStatus,
--           vrIpBgpImportPeerIpAddress,
--           vrIpBgpExportNetLength,
--           vrIpBgpAsRowStatus,
--           vrIpBgpPeerOutUpdates,
--           vrIpBgpPeerMinAsOrigTime,
--           vrIpBgpLocaldbComponentName,
--           vrIpBgpPeerLocalAddressUsed,
--           vrIpBgpExportAsPathExpression,
--           vrIpBgpOutdbUnknownAttributes,
--           vrIpBgpExportExpressPreference,
--           vrIpBgpAggregateNetAction,
--           vrIpBgpOutdbLocalPreference,
--           vrIpBgpUsageState,
--           vrIpBgpOutdbRrClusterListValue,
--           vrIpBgpExportNetRowStatus,
--           vrIpBgpAsComponentName,
--           vrIpBgpExportProtocol,
--           vrIpBgpExportStorageType,
--           vrIpBgpPeerIsRouteReflectorClient,
--           vrIpBgpPeerOutErrorMsgs,
--           vrIpBgpLocaldbRowStatus,
--           vrIpBgpLocaldbAsPath,
--           vrIpBgpExportNetPrefix,
--           vrIpBgpOutdbAggregatorAddr,
--           vrIpBgpIndbSize,
--           vrIpBgpOutdbOrigin,
--           vrIpBgpLocaldbRrClusterListValue,
--           vrIpBgpLocaldbAsOriginatorId,
--           vrIpBgpOutdbAggregatorAs,
--           vrIpBgpOperationalState,
--           vrIpBgpOutdbNextHop,
--           vrIpBgpAggregateNetBgpAsId,
--           vrIpBgpIndbStorageType,
--           vrIpBgpPeerConnectionEstablishedTransitions,
--           vrIpBgpImportNetComponentName,
--           vrIpBgpIndbOrigin,
--           vrIpBgpOutDiscards,
--           vrIpBgpIndbCommunityPath,
--           vrIpBgpPeerInUpdates,
--           vrIpBgpExportRowStatus,
--           vrIpBgpPeerDefaultInAggMed,
--           vrIpBgpBgpIdentifier,
--           vrIpBgpImportOriginAs,
--           vrIpBgpOutMsgs }
-- STATUS  mandatory
-- DESCRIPTION
--   "A list of all current accessible leaf objects."

bgpGroup OBJECT IDENTIFIER ::= { bgpMIB 1 }
bgpGroupBE OBJECT IDENTIFIER ::= { bgpGroup 5 }
bgpGroupBE01 OBJECT IDENTIFIER ::= { bgpGroupBE 2 }
bgpGroupBE01A OBJECT IDENTIFIER ::= { bgpGroupBE01 2 }



-- Agent-Capabilities Statement:

-- PRODUCT-RELEASE "Passport Release 7.0 Bgp."
-- STATUS          mandatory
-- DESCRIPTION     "Bgp MIB: MIB Version BE01A,
--                  Software Version BG00S4C."
-- SUPPORTS        Nortel-Magellan-Passport-BgpMIB
--    INCLUDES     { bgpGroupBE01A }

bgpCapabilities OBJECT IDENTIFIER ::= { bgpMIB 3 }
bgpCapabilitiesBE OBJECT IDENTIFIER ::= { bgpCapabilities 5 }
bgpCapabilitiesBE01 OBJECT IDENTIFIER ::= { bgpCapabilitiesBE 2 }
bgpCapabilitiesBE01A OBJECT IDENTIFIER ::= { bgpCapabilitiesBE01 2 }





END
