-- **************************************************************************
-- *            SNMP Private MIB
-- *            Copyright(c) - Johnson Controls
-- * 
-- *            This MIB defines the SNMP Interface of Johnson Controls
-- *             PROTOTYPE ONLY
-- * HISTORY
-- * Date      Name     Rel    EC/PT#  Task# Reason for change
-- * _________ _______ _______ _____ ______________________________________
-- * 01 APR 18 kehossm  1.00                 Develop Prototype using SNMPv1                                       Use function prototypes from rtos_ex.h
-- * 01 JUL 26 perryt   1.00   23708  Delete imported files     
-- *    
-- **************************************************************************

JohnsonControlsInc-MIB   DEFINITIONS ::= BEGIN


private                 OBJECT IDENTIFIER ::= { iso(1) org(3) dod(6) internet(1) 4 }
enterprises             OBJECT IDENTIFIER ::= { private 1 }

-- This is our private MIB 
johnsonControlsInc      OBJECT IDENTIFIER ::= { enterprises 4399 }

-- This node contains all the stuff related to our JohnsonControls Division branches
corporate               OBJECT IDENTIFIER ::= { johnsonControlsInc 1 }
jciControlsGroup        OBJECT IDENTIFIER ::= { johnsonControlsInc 2 }

        
END
