-- *****************************************************************************
-- Unisphere-Data-Fractional-T1-CONF
--
-- SNMP Agent Capabilities definitions for the Fractional T1 MIB.
--
-- Copyright (c) 2001 Unisphere Networks, Inc.  All rights reserved.
-- *****************************************************************************

Unisphere-Data-Fractional-T1-CONF DEFINITIONS ::= BEGIN

IMPORTS
    MODULE-IDENTITY
        FROM SNMPv2-SMI
    AGENT-CAPABILITIES
        FROM SNMPv2-CONF
    usDataAgents
        FROM Unisphere-Data-Agents
    usdFt1Group,
    usdFt1Group2
        FROM Unisphere-Data-FRACTIONAL-T1-MIB;

usdFractionalT1Agent MODULE-IDENTITY
    LAST-UPDATED "200103292203Z"  -- 29-Mar-01 05:03 PM EST
    ORGANIZATION "Unisphere Networks, Inc."
    CONTACT-INFO
        "       Unisphere Networks, Inc.
        Postal: 10 Technology Park Drive
                Westford, MA 01886
                USA
        Tel:    +1 978 589 5800
        E-mail: mib@UnisphereNetworks.com"
    DESCRIPTION
        "The agent capabilities definitions for the Fractional T1 component of
        the SNMP agent in the Unisphere Routing Switch family of products."
    -- Revision History
    REVISION    "200103292203Z"  -- 29-Mar-01 05:03 PM EST  - RX 3.2
    DESCRIPTION
        "The initial release of this management information module."
    ::= { usDataAgents 16 }

usdFractionalT1AgentV1 AGENT-CAPABILITIES
    PRODUCT-RELEASE
        "Version 1 of the Fractional T1 component of the Unisphere Routing
        Switch SNMP agent.  This version of the Fractional T1 component was
        supported in the Unisphere RX 1.0 system release."
    STATUS      obsolete
    DESCRIPTION
        "The MIB supported by the SNMP agent for the Fractional T1 application
        in the Unisphere Routing Switch.  These capabilities became obsolete
        when rsFt1IfDataPolarity was obsoleted."

    SUPPORTS        Unisphere-Data-FRACTIONAL-T1-MIB
        INCLUDES  { usdFt1Group }

    ::= { usdFractionalT1Agent 1 }

usdFractionalT1AgentV2 AGENT-CAPABILITIES
    PRODUCT-RELEASE
        "Version 2 of the Fractional T1 component of the Unisphere Routing
        Switch SNMP agent.  This version of the Fractional T1 component is
        supported in the Unisphere RX 1.1 and subsequent system releases."
    STATUS      current
    DESCRIPTION
        "The MIB supported by the SNMP agent for the Fractional T1 application
        in the Unisphere Routing Switch."

    SUPPORTS        Unisphere-Data-FRACTIONAL-T1-MIB
        INCLUDES  { usdFt1Group2 }

    ::= { usdFractionalT1Agent 2 }

END
