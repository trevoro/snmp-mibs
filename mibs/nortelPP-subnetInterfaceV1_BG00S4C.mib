Nortel-Magellan-Passport-SubnetInterfaceMIB
DEFINITIONS ::= BEGIN



IMPORTS

      OBJECT-TYPE
   FROM RFC-1212

      passportMIBs
   FROM Nortel-Magellan-Passport-UsefulDefinitionsMIB

      DisplayString,
      StorageType,
      RowStatus,
      Integer32,
      Unsigned32
   FROM Nortel-Magellan-Passport-StandardTextualConventionsMIB

      NonReplicated,
      DigitString
   FROM Nortel-Magellan-Passport-TextualConventionsMIB

      mod,
      modIndex
   FROM Nortel-Magellan-Passport-ShelfMIB;




-- LAST-UPDATED   "9808030000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     SubnetInterface Enterprise MIB."

subnetInterfaceMIB OBJECT IDENTIFIER ::= { passportMIBs 45 }










-- 
-- ModuleData Vcs
-- ModuleData VirtualCircuitSystem is used to define a number of 
-- general characteristics for all Vcs that originate from or terminate 
-- on a particular module. As an example, the Vc Window matrix is 
-- defined on a module basis to provide the expected virtual circuit 
-- window sizes to associate with all Vcs on the module. All the 
-- modules in the network should have identical VirtualCircuitSystem 
-- attributes. If these attributes are not consistent across the network 
-- applications which need Vc may not be able to establish calls. 

modVcs OBJECT IDENTIFIER ::= { mod 2 }



modVcsRowStatusTable OBJECT-TYPE
   SYNTAX     SEQUENCE OF ModVcsRowStatusEntry
   ACCESS     not-accessible
   STATUS     mandatory
   DESCRIPTION
     "This entry controls the addition and deletion of 
      modVcs components."
::= { modVcs 1 }

modVcsRowStatusEntry OBJECT-TYPE
   SYNTAX     ModVcsRowStatusEntry
   ACCESS     not-accessible
   STATUS     mandatory
   DESCRIPTION
     "A single entry in the table represents a single 
      modVcs component."
   INDEX {
      modIndex,
      modVcsIndex }
::= { modVcsRowStatusTable 1 }

ModVcsRowStatusEntry ::= SEQUENCE {
   modVcsRowStatus
      RowStatus,
   modVcsComponentName
      DisplayString,
   modVcsStorageType
      StorageType,
   modVcsIndex
      NonReplicated }

modVcsRowStatus OBJECT-TYPE
   SYNTAX     RowStatus 
   ACCESS     read-write
   STATUS     mandatory
   DESCRIPTION
     "This variable is used as the basis for SNMP naming of
      modVcs components.
      These components can be added and deleted."
::= { modVcsRowStatusEntry 1 }

modVcsComponentName OBJECT-TYPE
   SYNTAX     DisplayString 
   ACCESS     read-only
   STATUS     mandatory
   DESCRIPTION
     "This variable provides the component's string name for
      use with the ASCII Console Interface"
::= { modVcsRowStatusEntry 2 }

modVcsStorageType OBJECT-TYPE
   SYNTAX     StorageType 
   ACCESS     read-only
   STATUS     mandatory
   DESCRIPTION
     "This variable represents the storage type value for the
      modVcs tables."
::= { modVcsRowStatusEntry 4 }

modVcsIndex OBJECT-TYPE
   SYNTAX     NonReplicated 
   ACCESS     not-accessible
   STATUS     mandatory
   DESCRIPTION
     "This variable represents the index for the modVcs tables."
::= { modVcsRowStatusEntry 10 }

modVcsAccOptTable OBJECT-TYPE
   SYNTAX     SEQUENCE OF ModVcsAccOptEntry
   ACCESS     not-accessible
   STATUS     mandatory
   DESCRIPTION
     "Accounting information is owned by the Vc System; it is stored in 
      the Vc Accounting component, which itself is considered to be a 
      component on the switch. The Accounting Component contains a 
      bit map indicating which of the accounting facilities are to be 
      spooled in the accounting record - for example, bit '0' if set 
      indicates that the accounting facility with facility code H.00 should 
      be spooled if present in the Vc for accounting purposes. The data 
      contained in the Vc Accounting must be identical network wide 
      even though the component can be changed and upgraded on a 
      module by module basis."
::= { modVcs 10 }

modVcsAccOptEntry OBJECT-TYPE
   SYNTAX     ModVcsAccOptEntry
   ACCESS     not-accessible
   STATUS     mandatory
   DESCRIPTION
     "An entry in the modVcsAccOptTable."
   INDEX {
      modIndex,
      modVcsIndex }
::= { modVcsAccOptTable 1 }

ModVcsAccOptEntry ::= SEQUENCE {
   modVcsSegmentSize
      INTEGER,
   modVcsUnitsCounted
      INTEGER,
   modVcsAccountingFax
      OCTET STRING,
   modVcsGenerationMode
      INTEGER }

modVcsSegmentSize OBJECT-TYPE
   SYNTAX     INTEGER  {
                 n1(0),
                 n2(1),
                 n4(2),
                 n8(3),
                 n16(4),
                 n32(5),
                 n64(6),
                 n128(7),
                 n256(8),
                 n512(9),
                 n1024(10),
                 n2048(11),
                 n4096(12) }
   ACCESS     read-write
   STATUS     mandatory
   DESCRIPTION
     "This attribute specifies the segment size for accounting of national 
      calls. Minimum allowed segment size is 1. If data segment is sent 
      which is less than segmentSize it is still counted as one segment."
   DEFVAL     { n128 }
::= { modVcsAccOptEntry 1 }

modVcsUnitsCounted OBJECT-TYPE
   SYNTAX     INTEGER  {
                 segments(0),
                 frames(1) }
   ACCESS     read-write
   STATUS     mandatory
   DESCRIPTION
     "This attribute specifies what is counted by frame services. If set to 
      frames, frames are counted, else segments are counted."
   DEFVAL     { segments }
::= { modVcsAccOptEntry 2 }

modVcsAccountingFax OBJECT-TYPE
   SYNTAX     OCTET STRING (SIZE (1))
   ACCESS     read-write
   STATUS     mandatory
   DESCRIPTION
     "Each value corresponds to an accounting facility code, of which 
      there are currently 10 facility codes defined with codes H.00 to 
      H.09, and corresponding to the above 10 facilities.
      
      Each of the above facilities may or may not be present and stored in 
      the Vc for accounting purposes, depending on the nature of the call. 
      For example, only those Vcs where a NUI (Network User Identifier) 
      is used for charging or identification purposes will have a NUI 
      stored in the Vc.

      Description of bits:
      notused0(0)
      notused1(1)
      originalCalledAddressFax(2)"
   DEFVAL     { '20'H }
::= { modVcsAccOptEntry 3 }

modVcsGenerationMode OBJECT-TYPE
   SYNTAX     INTEGER  {
                 bothEnds(0),
                 singleEnd(1) }
   ACCESS     read-write
   STATUS     mandatory
   DESCRIPTION
     "This attribute specifies part of the rules by which the network 
      generates accounting records. If set to bothEnds, then both ends of 
      the Vc generate accounting records. If set to singleEnd, then the 
      charged end of the Vc generates accounting records. In single end 
      generation mode, if the call does not clear gracefully, both ends of 
      the Vc will generate accounting record."
   DEFVAL     { singleEnd }
::= { modVcsAccOptEntry 4 }

modVcsAddOptTable OBJECT-TYPE
   SYNTAX     SEQUENCE OF ModVcsAddOptEntry
   ACCESS     not-accessible
   STATUS     mandatory
   DESCRIPTION
     "The Vc AddressingOptions group describes the addressing 
      parameters. It is currently owned by the Vc.
      
      Most of the data contained in the Vc AddressingOptions group is 
      identical network wide even though the group can be changed and 
      upgraded on a module by module basis."
::= { modVcs 12 }

modVcsAddOptEntry OBJECT-TYPE
   SYNTAX     ModVcsAddOptEntry
   ACCESS     not-accessible
   STATUS     mandatory
   DESCRIPTION
     "An entry in the modVcsAddOptTable."
   INDEX {
      modIndex,
      modVcsIndex }
::= { modVcsAddOptTable 1 }

ModVcsAddOptEntry ::= SEQUENCE {
   modVcsDefaultNumberingPlan
      INTEGER,
   modVcsNetworkIdType
      INTEGER,
   modVcsX121Type
      INTEGER,
   modVcsNetworkIdCode
      DigitString,
   modVcsX121IntlAddresses
      INTEGER,
   modVcsX121IntllPrefixDigit
      Unsigned32,
   modVcsX121MinAddressLength
      Unsigned32,
   modVcsX121MaxAddressLength
      Unsigned32,
   modVcsX121ToE164EscapeSignificance
      INTEGER,
   modVcsE164IntlFormatAllowed
      INTEGER,
   modVcsE164IntlPrefixDigits
      DigitString,
   modVcsE164NatlPrefixDigit
      Unsigned32,
   modVcsE164LocalAddressLength
      Unsigned32,
   modVcsE164TeleCountryCode
      DigitString,
   modVcsE164NatlMinAddressLength
      Unsigned32,
   modVcsE164NatlMaxAddressLength
      Unsigned32,
   modVcsE164IntlMinAddressLength
      Unsigned32,
   modVcsE164IntlMaxAddressLength
      Unsigned32,
   modVcsE164LocalMinAddressLength
      Unsigned32,
   modVcsE164LocalMaxAddressLength
      Unsigned32 }

modVcsDefaultNumberingPlan OBJECT-TYPE
   SYNTAX     INTEGER  {
                 x121(0),
                 e164(1) }
   ACCESS     read-write
   STATUS     mandatory
   DESCRIPTION
     "This attribute specifies the numbering plan used which determines 
      the address format: X.121-- the international numbering plan for 
      public packet switched data networks or E.164-- the international 
      numbering plan for ISDN and PSTN.
      
      The default numbering plan does not need to be consistent across all 
      of the nodes in the network."
   DEFVAL     { x121 }
::= { modVcsAddOptEntry 3 }

modVcsNetworkIdType OBJECT-TYPE
   SYNTAX     INTEGER  {
                 dnic(0),
                 inic(1) }
   ACCESS     read-only
   STATUS     mandatory
   DESCRIPTION
     "This attribute specifies whether the network uses a DNIC or INIC. It 
      is used by X.75 Gateways to indicate whether in network the DNIC 
      or INIC is used in various utilities. If it is DNIC it can be DNIC or 
      DCC type. If it is INIC it can be 4 digits only."
   DEFVAL     { dnic }
::= { modVcsAddOptEntry 4 }

modVcsX121Type OBJECT-TYPE
   SYNTAX     INTEGER  {
                 dnic(0),
                 dcc(1) }
   ACCESS     read-write
   STATUS     mandatory
   DESCRIPTION
     "This attribute specifies whether DNIC mode or DCC mode is used 
      in X.121 address of international calls.
      
      If DCC is specified, then the first 3 digits of each DNA must be the 
      Network ID Code.
      If this attribute is changed all Dnas in the network must start with 
      this code. Numbering plan is affected by the change."
   DEFVAL     { dnic }
::= { modVcsAddOptEntry 5 }

modVcsNetworkIdCode OBJECT-TYPE
   SYNTAX     DigitString (SIZE (3..4))
   ACCESS     read-write
   STATUS     mandatory
   DESCRIPTION
     "This attribute specifies the DNIC (Data Network ID Code) of the 
      network or DCC code."
::= { modVcsAddOptEntry 6 }

modVcsX121IntlAddresses OBJECT-TYPE
   SYNTAX     INTEGER  {
                 disallowed(0),
                 allowed(1) }
   ACCESS     read-write
   STATUS     mandatory
   DESCRIPTION
     "This attribute indicates if any DTE is allowed to signal international 
      addresses."
   DEFVAL     { allowed }
::= { modVcsAddOptEntry 7 }

modVcsX121IntllPrefixDigit OBJECT-TYPE
   SYNTAX     Unsigned32 (0..9)
   ACCESS     read-write
   STATUS     mandatory
   DESCRIPTION
     "This attribute indicates the prefix digit to be used for X.121 
      international calls. When this digit is provided the call will have full 
      international address."
   DEFVAL     { 9 }
::= { modVcsAddOptEntry 8 }

modVcsX121MinAddressLength OBJECT-TYPE
   SYNTAX     Unsigned32 (1..16)
   ACCESS     read-write
   STATUS     mandatory
   DESCRIPTION
     "This attribute indicates minimum length of x121 address."
   DEFVAL     { 1 }
::= { modVcsAddOptEntry 11 }

modVcsX121MaxAddressLength OBJECT-TYPE
   SYNTAX     Unsigned32 (1..16)
   ACCESS     read-write
   STATUS     mandatory
   DESCRIPTION
     "This attribute indicates maximum length of x121 address."
   DEFVAL     { 15 }
::= { modVcsAddOptEntry 12 }

modVcsX121ToE164EscapeSignificance OBJECT-TYPE
   SYNTAX     INTEGER  {
                 no(0),
                 yes(1) }
   ACCESS     read-write
   STATUS     mandatory
   DESCRIPTION
     "This attribute specifies whether an X.121 to E.164 escape digit has 
      significance in selecting an X.32 (analog) or an ISDN switched 
      path. If two values are significant (the value 0 or the value 9) then 
      yes is set to this attribute. If the value of the originally entered 
      escape digit is not significant in routing the call then value of no is 
      assigned to this attribute."
   DEFVAL     { no }
::= { modVcsAddOptEntry 13 }

modVcsE164IntlFormatAllowed OBJECT-TYPE
   SYNTAX     INTEGER  {
                 disallowed(0),
                 allowed(1) }
   ACCESS     read-write
   STATUS     mandatory
   DESCRIPTION
     "This attribute indicates whether or not to allow national format 
      E.164 addresses. If this attribute is set to a value of Yes (=1) then 
      national format E.164 addresses are not allowed and international 
      format addresses only are allowed. If this attribute is set to a value 
      of No (=0), then national format E.164 addresses are allowed.
      
      If only international format E.164 addresses are allowed, then the 
      'e164NatlPrefixDigit' attribute is not required, nor is the 
      'e164IntlPrefixDigits' required."
   DEFVAL     { allowed }
::= { modVcsAddOptEntry 14 }

modVcsE164IntlPrefixDigits OBJECT-TYPE
   SYNTAX     DigitString (SIZE (0..3))
   ACCESS     read-write
   STATUS     mandatory
   DESCRIPTION
     "This attribute specifies the E.164 international prefix digits. If 
      applicable, it is specified as 1 to 3 BCD digits.
      
      The 3 BCD digits are stored with the length of the international 
      prefix in the low order nibble, nibble [0] followed by the most 
      significant digit of the international prefix in the next low order 
      nibble, nibble [1], etc.
      
      This attribute is not required if the corresponding attribute, 
      'e164IntlFormatOnly' is set to a value of Yes (=1)."
   DEFVAL     { '30'H }  -- "0"
::= { modVcsAddOptEntry 15 }

modVcsE164NatlPrefixDigit OBJECT-TYPE
   SYNTAX     Unsigned32 (0..9)
   ACCESS     read-write
   STATUS     mandatory
   DESCRIPTION
     "This attribute contains the E.164 national prefix which may be 
      added in front of E.164 local or national call. If 
      e164IntlFormatOnly is set to 1, this attribute is not needed."
   DEFVAL     { 1 }
::= { modVcsAddOptEntry 16 }

modVcsE164LocalAddressLength OBJECT-TYPE
   SYNTAX     Unsigned32 (4..15)
   ACCESS     read-write
   STATUS     mandatory
   DESCRIPTION
     "This attribute indicates the length of a local E.164 DNA on this 
      module. This attribute is not required if the corresponding attribute, 
      e164IntlFormatOnly is set to a value of yes.
      
      This attribute does not need to be consistent across all of the nodes 
      in the network."
   DEFVAL     { 7 }
::= { modVcsAddOptEntry 17 }

modVcsE164TeleCountryCode OBJECT-TYPE
   SYNTAX     DigitString (SIZE (1..4))
   ACCESS     read-write
   STATUS     mandatory
   DESCRIPTION
     "This attribute specifies the E.164 Telephone Country Code (TCC) 
      for the country in which the network resides. If applicable, it is 
      specified as 1 to 3 BCD digits.
      
      The 3 BCD digits are stored with the length of the TCC in the low 
      order nibble, nibble [0] followed by the most significant digit of the 
      TCC in the next low order nibble, nibble [1], etc."
   DEFVAL     { '31'H }  -- "1"
::= { modVcsAddOptEntry 18 }

modVcsE164NatlMinAddressLength OBJECT-TYPE
   SYNTAX     Unsigned32 (1..16)
   ACCESS     read-write
   STATUS     mandatory
   DESCRIPTION
     "This attribute indicates minimum length of e164 national address."
   DEFVAL     { 1 }
::= { modVcsAddOptEntry 20 }

modVcsE164NatlMaxAddressLength OBJECT-TYPE
   SYNTAX     Unsigned32 (1..16)
   ACCESS     read-write
   STATUS     mandatory
   DESCRIPTION
     "This attribute indicates maximum length of e164 national address."
   DEFVAL     { 15 }
::= { modVcsAddOptEntry 21 }

modVcsE164IntlMinAddressLength OBJECT-TYPE
   SYNTAX     Unsigned32 (1..16)
   ACCESS     read-write
   STATUS     mandatory
   DESCRIPTION
     "This attribute indicates minimum length of e164 international 
      address."
   DEFVAL     { 1 }
::= { modVcsAddOptEntry 22 }

modVcsE164IntlMaxAddressLength OBJECT-TYPE
   SYNTAX     Unsigned32 (1..16)
   ACCESS     read-write
   STATUS     mandatory
   DESCRIPTION
     "This attribute indicates maximum length of e164 international 
      address."
   DEFVAL     { 15 }
::= { modVcsAddOptEntry 23 }

modVcsE164LocalMinAddressLength OBJECT-TYPE
   SYNTAX     Unsigned32 (1..16)
   ACCESS     read-write
   STATUS     mandatory
   DESCRIPTION
     "This attribute indicates minimum length of e164 local address."
   DEFVAL     { 1 }
::= { modVcsAddOptEntry 24 }

modVcsE164LocalMaxAddressLength OBJECT-TYPE
   SYNTAX     Unsigned32 (1..16)
   ACCESS     read-write
   STATUS     mandatory
   DESCRIPTION
     "This attribute indicates maximum length of e164 local address."
   DEFVAL     { 15 }
::= { modVcsAddOptEntry 25 }

modVcsIntOptTable OBJECT-TYPE
   SYNTAX     SEQUENCE OF ModVcsIntOptEntry
   ACCESS     not-accessible
   STATUS     mandatory
   DESCRIPTION
     "The Vc InterfaceOptions group defines Vc system parameters 
      common in the network. It is owned by the Vc and is considered to 
      be a module wide component on the switch.
      
      The data contained in the Vc InterfaceOptions group must be 
      identical network wide even though this group can be changed and 
      upgraded on a module by module basis."
::= { modVcs 13 }

modVcsIntOptEntry OBJECT-TYPE
   SYNTAX     ModVcsIntOptEntry
   ACCESS     not-accessible
   STATUS     mandatory
   DESCRIPTION
     "An entry in the modVcsIntOptTable."
   INDEX {
      modIndex,
      modVcsIndex }
::= { modVcsIntOptTable 1 }

ModVcsIntOptEntry ::= SEQUENCE {
   modVcsHighPriorityPacketSizes
      OCTET STRING,
   modVcsMaxSubnetPacketSize
      INTEGER,
   modVcsCallSetupTimer
      Unsigned32,
   modVcsCallRetryTimer
      Unsigned32,
   modVcsDelaySubnetAcks
      INTEGER }

modVcsHighPriorityPacketSizes OBJECT-TYPE
   SYNTAX     OCTET STRING (SIZE (2))
   ACCESS     read-only
   STATUS     mandatory
   DESCRIPTION
     "This attribute indicates which packet sizes are supported for high 
      priority calls within the network.

      Description of bits:
      n16(0)
      n32(1)
      n64(2)
      n128(3)
      n256(4)
      n512(5)
      n1024(6)
      n2048(7)
      n4096(8)"
   DEFVAL     { 'ff80'H }
::= { modVcsIntOptEntry 1 }

modVcsMaxSubnetPacketSize OBJECT-TYPE
   SYNTAX     INTEGER  {
                 n16(4),
                 n32(5),
                 n64(6),
                 n128(7),
                 n256(8),
                 n512(9),
                 n1024(10),
                 n2048(11),
                 n4096(12) }
   ACCESS     read-write
   STATUS     mandatory
   DESCRIPTION
     "This attribute specifies the maximum subnet packet size used for the 
      connections originating or terminating on this module. All modules 
      in the same network should have the same maxSubnetPacketSize.
      
      If this value is not identical throughout the network, the following 
      points need to be considered:
      
      a) When Passport and DPN switches are connected in the same 
      network, the maxSubnetPacketSize on a DPN switch can be at most 
      2048 and the DPN part of the network must be configured with 
      hardware which supports this size:
      
      -  Dedicated PE386 Network link/Trunk
      -  Minimum measured link speed of 256Kbits/sec
      
      This hardware has to be present on every potential data path 
      between connecting end points!
      
      b) The calling end of the connection signals the 
      maxSubnetPacketSize value to the called end. The called end then 
      compares this value to its own provisioned value and selects the 
      smaller value. Note that this smaller value is not signalled back to 
      the calling end. The calling and called ends can therefore have 
      different maxSubnetPacketSize values."
   DEFVAL     { n512 }
::= { modVcsIntOptEntry 2 }

modVcsCallSetupTimer OBJECT-TYPE
   SYNTAX     Unsigned32 (5..100)
   ACCESS     read-write
   STATUS     mandatory
   DESCRIPTION
     "This attribute specifies the Vc callSetupTimer in units of 1 second 
      ticks. This timer specifies how long the Vc will wait, after sending 
      a subnet Call Request packet into the network, for a response from 
      the remote end of the Vc (in the form of a subnet Raccept packet). 
      If, after sending a subnet Call packet into the network, a response is 
      not received within this time period, the Vc will time out, clearing 
      the call in the assumption that the remote end is unreachable. This 
      timer must be long enough to take into account the time required for 
      routing the subnet Call Request through the Source Call Routing 
      and the Destination Call Routing systems in order to be delivered to 
      the final destination."
   DEFVAL     { 5 }
::= { modVcsIntOptEntry 3 }

modVcsCallRetryTimer OBJECT-TYPE
   SYNTAX     Unsigned32 (30..300)
   ACCESS     read-write
   STATUS     mandatory
   DESCRIPTION
     "This attribute specifies, for Vc implementing Direct Calls with the 
      auto-call retry feature (including PVCs), the Vc callRetryTimer in 
      units of 1 second ticks. This timer specifies how long the Vc will 
      wait between unsuccessful call attempts."
   DEFVAL     { 60 }
::= { modVcsIntOptEntry 4 }

modVcsDelaySubnetAcks OBJECT-TYPE
   SYNTAX     INTEGER  {
                 no(0),
                 yes(1) }
   ACCESS     read-write
   STATUS     mandatory
   DESCRIPTION
     "This attribute specifies delay acknowledgment timer mechanism.
      If this attribute is set to no, then the Vc will automatically return 
      acknowledgment packets without delay. If this attribute is set to yes, 
      then the Vc will wait for one second in an attempt to piggyback the 
      acknowledgment packet on another credit or data packet. If the Vc 
      cannot piggyback the acknowledgment packet within this time, then 
      the packet is returned without piggybacking."
   DEFVAL     { no }
::= { modVcsIntOptEntry 5 }

modVcsWinsTable OBJECT-TYPE
   SYNTAX     SEQUENCE OF ModVcsWinsEntry
   ACCESS     not-accessible
   STATUS     mandatory
   DESCRIPTION
     "This is the windowSize corresponding to the given packet size and 
      throughput class. All Vcs using the windowSize matrix support 
      large Vc windows on both ends of the Vc, and support the signalling 
      of the chosen Vc window size from the destination (called) end to 
      the source (calling) end. This is the only matrix supported.
      The windowSize should be configured in the same way network 
      wide, though it can be upgraded on a module by module basis. Vcs 
      using the windowSize matrix will run properly if the matrices on 
      different nodes differ since the Vc window is selected by the 
      destination (called) side of the Vc."
::= { modVcs 213 }

modVcsWinsEntry OBJECT-TYPE
   SYNTAX     ModVcsWinsEntry
   ACCESS     not-accessible
   STATUS     mandatory
   DESCRIPTION
     "An entry in the modVcsWinsTable."
   INDEX {
      modIndex,
      modVcsIndex,
      modVcsWinsPktIndex,
      modVcsWinsTptIndex }
::= { modVcsWinsTable 1 }

ModVcsWinsEntry ::= SEQUENCE {
   modVcsWinsPktIndex
      INTEGER,
   modVcsWinsTptIndex
      Integer32,
   modVcsWinsValue
      Unsigned32 }

modVcsWinsPktIndex OBJECT-TYPE
   SYNTAX     INTEGER  {
                 n16(0),
                 n32(1),
                 n64(2),
                 n128(3),
                 n256(4),
                 n512(5),
                 n1024(6),
                 n2048(7),
                 n4096(8),
                 n8192(9),
                 n32768(10),
                 n65535(11) }
   ACCESS     not-accessible
   STATUS     mandatory
   DESCRIPTION
     "This variable represents the next to last index for the 
      modVcsWinsTable."
::= { modVcsWinsEntry 1 }

modVcsWinsTptIndex OBJECT-TYPE
   SYNTAX     Integer32 (0..15)
   ACCESS     not-accessible
   STATUS     mandatory
   DESCRIPTION
     "This variable represents the final index for the 
      modVcsWinsTable."
::= { modVcsWinsEntry 2 }

modVcsWinsValue OBJECT-TYPE
   SYNTAX     Unsigned32 (1..63)
   ACCESS     read-write
   STATUS     mandatory
   DESCRIPTION
     "This variable represents an individual value for the
      modVcsWinsTable."
::= { modVcsWinsEntry 3 }




-- 
-- Version and Compliance statements
-- 



-- Object-Group Statement:
-- A list of all current accessible leaf objects.

-- OBJECTS { modVcsCallSetupTimer,
--           modVcsE164LocalMaxAddressLength,
--           modVcsWinsValue,
--           modVcsE164IntlMinAddressLength,
--           modVcsE164IntlFormatAllowed,
--           modVcsX121Type,
--           modVcsNetworkIdCode,
--           modVcsRowStatus,
--           modVcsX121MaxAddressLength,
--           modVcsSegmentSize,
--           modVcsE164LocalAddressLength,
--           modVcsDelaySubnetAcks,
--           modVcsGenerationMode,
--           modVcsCallRetryTimer,
--           modVcsE164NatlMinAddressLength,
--           modVcsE164IntlMaxAddressLength,
--           modVcsAccountingFax,
--           modVcsComponentName,
--           modVcsNetworkIdType,
--           modVcsX121ToE164EscapeSignificance,
--           modVcsE164TeleCountryCode,
--           modVcsE164LocalMinAddressLength,
--           modVcsX121IntlAddresses,
--           modVcsDefaultNumberingPlan,
--           modVcsX121IntllPrefixDigit,
--           modVcsStorageType,
--           modVcsE164IntlPrefixDigits,
--           modVcsE164NatlPrefixDigit,
--           modVcsX121MinAddressLength,
--           modVcsE164NatlMaxAddressLength,
--           modVcsHighPriorityPacketSizes,
--           modVcsUnitsCounted,
--           modVcsMaxSubnetPacketSize }
-- STATUS  mandatory
-- DESCRIPTION
--   "A list of all current accessible leaf objects."

subnetInterfaceGroup OBJECT IDENTIFIER ::= { subnetInterfaceMIB 1 }
subnetInterfaceGroupBE OBJECT IDENTIFIER ::= { subnetInterfaceGroup 5 }
subnetInterfaceGroupBE00 OBJECT IDENTIFIER ::= { subnetInterfaceGroupBE 1 }
subnetInterfaceGroupBE00A OBJECT IDENTIFIER ::= { subnetInterfaceGroupBE00 2 }



-- Agent-Capabilities Statement:

-- PRODUCT-RELEASE "Passport Release 7.0 SubnetInterface."
-- STATUS          mandatory
-- DESCRIPTION     "SubnetInterface MIB: MIB Version BE00A,
--                  Software Version BG00S4C."
-- SUPPORTS        Nortel-Magellan-Passport-SubnetInterfaceMIB
--    INCLUDES     { subnetInterfaceGroupBE00A }

subnetInterfaceCapabilities OBJECT IDENTIFIER ::= { subnetInterfaceMIB 3 }
subnetInterfaceCapabilitiesBE OBJECT IDENTIFIER ::= { subnetInterfaceCapabilities 5 }
subnetInterfaceCapabilitiesBE00 OBJECT IDENTIFIER ::= { subnetInterfaceCapabilitiesBE 1 }
subnetInterfaceCapabilitiesBE00A OBJECT IDENTIFIER ::= { subnetInterfaceCapabilitiesBE00 2 }





END
