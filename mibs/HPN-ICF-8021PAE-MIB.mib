-- ==================================================================
-- Copyright (c) 2010-2013 Hewlett-Packard Development Company, L.P.
-- 
-- Description: 802.1X MIB
-- Reference:
-- Version: V1.3
-- History:
-- 1) 2003-03-27 Fuzhenyu created  
-- 2) v1.1 2004-08-28 chaiyongfu 
--         change node  hpnicfdot1xAuthServerTimeout's DEFVAL { 30 } to DEFVAL { 100 }
--    v1.2 2004-10-12 updated by gaolong
--         Import NOTIFICATION-TYPE
--         Remove chinese characters
--         Fix time format of  hpnicfpaeExtMib.
--    v1.3 2007-10-23 updated by chaiyongfu
--         Add node hpnicfdot1xAuthMethod, hpnicfdot1xpaeportMcastTrigStatus,
--         hpnicfdot1xpaeportHandshakeStatus
-- ==================================================================

HPN-ICF-8021PAE-MIB DEFINITIONS ::= BEGIN

    IMPORTS
    hpnicfRhw          
        FROM HPN-ICF-OID-MIB
    IpAddress, OBJECT-TYPE,Unsigned32,NOTIFICATION-TYPE
        FROM SNMPv2-SMI
    
    MODULE-IDENTITY
            FROM SNMPv2-SMI 
    MacAddress
        FROM SNMPv2-TC

    dot1xPaePortNumber
            FROM IEEE8021-PAE-MIB;          
   

     hpnicfpaeExtMib MODULE-IDENTITY
            LAST-UPDATED "200106290000Z"
            ORGANIZATION
                ""
            CONTACT-INFO
                ""
            DESCRIPTION
            "this file extends IEEE8021-PAE-MIB(802.1x)"
            REVISION "200106290000Z"
            DESCRIPTION
            ""
            ::= { hpnicfRhw 6 }
   -- ============================================================
   -- groups in the PAE MIB
   -- ============================================================

   hpnicfpaeExtMibObjects           OBJECT IDENTIFIER ::= { hpnicfpaeExtMib 1 }    
   hpnicfdot1xPaeSystem             OBJECT IDENTIFIER ::= { hpnicfpaeExtMibObjects 1 }
   hpnicfdot1xPaeAuthenticator      OBJECT IDENTIFIER ::= { hpnicfpaeExtMibObjects 2 }
 
   -- ============================================================

    hpnicfdot1xAuthQuietPeriod OBJECT-TYPE
            SYNTAX             Unsigned32
            MAX-ACCESS     read-write
            STATUS             current
            DESCRIPTION
                    "The value, in seconds, of the quietPeriod constant
                    currently in use by the Authenticator PAE state
                    machine."
            REFERENCE
                    " 9.4.1, quietPeriod"
            DEFVAL { 60 }
            ::= { hpnicfdot1xPaeSystem 1 }

    hpnicfdot1xAuthTxPeriod OBJECT-TYPE
            SYNTAX             Unsigned32
            MAX-ACCESS     read-write
            STATUS             current
            DESCRIPTION
                    "The value, in seconds, of the txPeriod constant
                    currently in use by the Authenticator PAE state
                    machine."
            REFERENCE
                    " 9.4.1, txPeriod"
            DEFVAL { 30 }
            ::= { hpnicfdot1xPaeSystem 2 }

    hpnicfdot1xAuthSuppTimeout OBJECT-TYPE
            SYNTAX             Unsigned32
            MAX-ACCESS     read-write
            STATUS             current
            DESCRIPTION
                   "The value, in seconds, of the suppTimeout constant
                   currently in use by the Backend Authentication state
                   machine."
            REFERENCE
                   " 9.4.1, suppTimeout"
            DEFVAL { 30 }
            ::= { hpnicfdot1xPaeSystem 3 }

   hpnicfdot1xAuthServerTimeout OBJECT-TYPE
           SYNTAX             Unsigned32
           MAX-ACCESS     read-write
           STATUS             current
           DESCRIPTION
                   "The value, in seconds, of the serverTimeout constant
                   currently in use by the Backend Authentication state
                   machine."
           REFERENCE
                   " 9.4.1, serverTimeout"
           DEFVAL { 100 }
           ::= { hpnicfdot1xPaeSystem 4 }

   hpnicfdot1xAuthMaxReq OBJECT-TYPE
           SYNTAX             Unsigned32
           MAX-ACCESS     read-write
           STATUS             current
           DESCRIPTION
                   "The value of the maxReq constant currently in use by
                   the Backend Authentication state machine."
           REFERENCE
                   " 9.4.1, maxReq"
           DEFVAL { 2 }
           ::= { hpnicfdot1xPaeSystem 5 }

   hpnicfdot1xAuthReAuthPeriod OBJECT-TYPE
           SYNTAX             Unsigned32
           MAX-ACCESS     read-write
           STATUS             current
           DESCRIPTION
                   "The value, in seconds, of the reAuthPeriod constant
                   currently in use by the Reauthentication Timer state
                   machine."
           REFERENCE
                   " 9.4.1, reAuthPeriod"
           DEFVAL  { 3600 }
           ::= { hpnicfdot1xPaeSystem 6 }
 
   hpnicfdot1xAuthMethod OBJECT-TYPE
           SYNTAX         INTEGER { chap(1), pap(2), eap(3) }
           MAX-ACCESS     read-write
           STATUS         current
           DESCRIPTION
                   "The value defines the 802.1X authenticatin method."
           REFERENCE
                   ""
           DEFVAL  { 1 }
           ::= { hpnicfdot1xPaeSystem 7 }

   -- ============================================================
   -- The Authenticator Configuration Extracte Table
   -- ============================================================

   hpnicfdot1xAuthConfigExtTable OBJECT-TYPE
           SYNTAX             SEQUENCE OF Hpnicfdot1xAuthConfigExtEntry
           MAX-ACCESS     not-accessible
           STATUS             current
           DESCRIPTION
                   " table extends dot1xAuthConfigTable"
            REFERENCE
                    " 9.4.1 Authenticator Configuration"
            ::= { hpnicfdot1xPaeAuthenticator 1 }

    hpnicfdot1xAuthConfigExtEntry OBJECT-TYPE
            SYNTAX             Hpnicfdot1xAuthConfigExtEntry
            MAX-ACCESS     not-accessible
            STATUS             current
            DESCRIPTION
                    " The configuration information for an Authenticator PAE."
            INDEX { dot1xPaePortNumber }
            ::= { hpnicfdot1xAuthConfigExtTable 1 }
            
    Hpnicfdot1xAuthConfigExtEntry   ::=
    SEQUENCE {
        hpnicfdot1xpaeportAuthAdminStatus   INTEGER ,
        hpnicfdot1xpaeportControlledType    INTEGER ,
        hpnicfdot1xpaeportMaxUserNum        INTEGER ,
        hpnicfdot1xpaeportUserNumNow		INTEGER ,
        hpnicfdot1xpaeportClearStatistics	INTEGER ,
        hpnicfdot1xpaeportMcastTrigStatus   INTEGER ,
        hpnicfdot1xpaeportHandshakeStatus   INTEGER
        }
        
    hpnicfdot1xpaeportAuthAdminStatus  OBJECT-TYPE
           SYNTAX             INTEGER { enabled( 1), disabled( 2) }
           MAX-ACCESS     read-write
           STATUS             current
           DESCRIPTION
                   "The administrative enable/disable state for Port Access Control in a port."
           REFERENCE
                   ""
           DEFVAL  {2}
           ::= { hpnicfdot1xAuthConfigExtEntry 1 }
           
           
    hpnicfdot1xpaeportControlledType  OBJECT-TYPE
           SYNTAX             INTEGER { port(1), mac(2) }
           MAX-ACCESS     read-write
           STATUS             current
           DESCRIPTION
                   "Port Access Control type , base port access control or base MAC access control"
           REFERENCE
                   ""
           DEFVAL  {2}
           ::= { hpnicfdot1xAuthConfigExtEntry 2 }
           
    hpnicfdot1xpaeportMaxUserNum  OBJECT-TYPE
           SYNTAX             INTEGER 
           MAX-ACCESS     read-write
           STATUS             current
           DESCRIPTION
                   "the max num of online user in a port"
           REFERENCE
                   ""
           DEFVAL  {256}
           ::= { hpnicfdot1xAuthConfigExtEntry 3 }
          
    hpnicfdot1xpaeportUserNumNow  OBJECT-TYPE
           SYNTAX             INTEGER 
           MAX-ACCESS     read-only
           STATUS             current
           DESCRIPTION
                   "the num of online user in a port now "
           REFERENCE
                   ""
           ::= { hpnicfdot1xAuthConfigExtEntry 4 }             
      
        
    hpnicfdot1xpaeportClearStatistics  OBJECT-TYPE
           SYNTAX             INTEGER {clear(1)}
           MAX-ACCESS     read-write
           STATUS             current
           DESCRIPTION
                   "Clear various Statistics viz. "
           REFERENCE
                   ""
           ::= { hpnicfdot1xAuthConfigExtEntry 5 }    
           
           
    hpnicfdot1xpaeportMcastTrigStatus  OBJECT-TYPE
           SYNTAX         INTEGER { enabled( 1), disabled( 2) }
           MAX-ACCESS     read-write
           STATUS         current
           DESCRIPTION
                   "The administrative enable/disable state for sending
                   muticast EAP_REQ/ID packet."
           REFERENCE
                   ""
           DEFVAL  {1}
           ::= { hpnicfdot1xAuthConfigExtEntry 6 }
           
    hpnicfdot1xpaeportHandshakeStatus  OBJECT-TYPE
           SYNTAX         INTEGER { enabled( 1 ), disabled( 2 ) }
           MAX-ACCESS     read-write
           STATUS         current
           DESCRIPTION
                   "The administrative enable/disable state for sending
                   handshake EAP_REQ/ID packet."
           REFERENCE
                   ""
           DEFVAL  {1}
           ::= { hpnicfdot1xAuthConfigExtEntry 7 }

  -- trap defination
    hpnicfdot1xPaeTraps             OBJECT IDENTIFIER ::= { hpnicfpaeExtMibObjects 0 }

    hpnicfsupplicantproxycheck NOTIFICATION-TYPE 
      OBJECTS { hpnicfproxycheckVlanId, hpnicfproxycheckPortName, hpnicfproxycheckMacAddr, hpnicfproxycheckIpaddr, hpnicfproxycheckUsrName }
      STATUS current
      DESCRIPTION ""
      ::= { hpnicfdot1xPaeTraps 1 }

    hpnicfproxycheckVlanId OBJECT-TYPE 
      SYNTAX INTEGER
      MAX-ACCESS accessible-for-notify
      STATUS current
      DESCRIPTION "."
      ::= { hpnicfdot1xPaeTraps 2 }

    hpnicfproxycheckPortName OBJECT-TYPE 
      SYNTAX OCTET STRING
      MAX-ACCESS accessible-for-notify
      STATUS current
      DESCRIPTION "."
      ::= { hpnicfdot1xPaeTraps 3 }

    hpnicfproxycheckMacAddr OBJECT-TYPE 
      SYNTAX MacAddress
      MAX-ACCESS accessible-for-notify
      STATUS current
      DESCRIPTION "."
      ::= { hpnicfdot1xPaeTraps 4 }
      
    hpnicfproxycheckIpaddr OBJECT-TYPE 
      SYNTAX IpAddress
      MAX-ACCESS accessible-for-notify
      STATUS current
      DESCRIPTION "."
      ::= { hpnicfdot1xPaeTraps 5 } 
              
    hpnicfproxycheckUsrName OBJECT-TYPE 
      SYNTAX OCTET STRING
      MAX-ACCESS accessible-for-notify
      STATUS current
      DESCRIPTION "."
      ::= { hpnicfdot1xPaeTraps 6 }               
END
