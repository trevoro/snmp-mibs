P8541-MIB DEFINITIONS ::= BEGIN


IMPORTS
	enterprises
		FROM RFC1155-SMI
	OBJECT-TYPE
		FROM RFC-1212;
  
  DisplayString ::= OCTET STRING


comet         OBJECT IDENTIFIER ::= { enterprises 22626 }
products      OBJECT IDENTIFIER ::= { comet 1 }
p8541         OBJECT IDENTIFIER ::= { products 5 }
settings      OBJECT IDENTIFIER ::= { p8541 1 }
channels      OBJECT IDENTIFIER ::= { p8541 2 }
channel1      OBJECT IDENTIFIER ::= { channels 1 }
channel2      OBJECT IDENTIFIER ::= { channels 2 }
channel3      OBJECT IDENTIFIER ::= { channels 3 }
channel4      OBJECT IDENTIFIER ::= { channels 4 }
traps         OBJECT IDENTIFIER ::= { p8541 3 }
tables	      OBJECT IDENTIFIER ::= { p8541 4 }

-- Power Source MIB
-- Parameters (Prefix ps)

-----------------------------------------------------------------------
-- settings
-----------------------------------------------------------------------
sensorName OBJECT-TYPE
	SYNTAX		DisplayString (SIZE (0..16))
	ACCESS		read-only
	STATUS		mandatory
	DESCRIPTION	"Sensor name."
::= { settings 1 }

-----------------------------------------------------------------------
-- channels
-----------------------------------------------------------------------

-----------------------------------------------------------------------
-- channel1
-----------------------------------------------------------------------
ch1Name OBJECT-TYPE
	SYNTAX		DisplayString (SIZE (0..16))
	ACCESS		read-only
	STATUS		mandatory
	DESCRIPTION	"Channel 1 name."
::= { channel1 1 }

ch1Val OBJECT-TYPE
	SYNTAX		DisplayString (SIZE (0..8))
	ACCESS		read-only
	STATUS		mandatory
	DESCRIPTION	"Channel 1 temperature."
::= { channel1 2 }

ch1IntVal OBJECT-TYPE
	SYNTAX		INTEGER (-550..1250)
	ACCESS		read-only
	STATUS		mandatory
	DESCRIPTION	"Channel 1 temperature * 10 (12,5 dgr C = 125)."
::= { channel1 3 }

ch1Alarm OBJECT-TYPE
	SYNTAX		INTEGER (0..1)
	ACCESS		read-only
	STATUS		mandatory
	DESCRIPTION	"Alarm on channel 1; 0 - No alarm, 1 - Alarm Hi, 2- Alarm Lo."
::= { channel1 4 }

ch1LimHi OBJECT-TYPE
	SYNTAX		DisplayString (SIZE (0..8))
	ACCESS		read-only
	STATUS		mandatory
	DESCRIPTION	"Channel 1 temperature upper alarm limit."
::= { channel1 5 }

ch1LimLo OBJECT-TYPE
	SYNTAX		DisplayString (SIZE (0..8))
	ACCESS		read-only
	STATUS		mandatory
	DESCRIPTION	"Channel 1 temperature low alarm limit."
::= { channel1 6 }

ch1LimHyst OBJECT-TYPE
	SYNTAX		DisplayString (SIZE (0..8))
	ACCESS		read-only
	STATUS		mandatory
	DESCRIPTION	"Channel 1 temperature hysteressis."
::= { channel1 7 }

ch1Delay OBJECT-TYPE
	SYNTAX		INTEGER (0..65534)
	ACCESS		read-only
	STATUS		mandatory
	DESCRIPTION	"Channel 1 temperature alarm delay [s]."
::= { channel1 8 }

-----------------------------------------------------------------------
-- channel2
-----------------------------------------------------------------------
ch2Name OBJECT-TYPE
	SYNTAX		DisplayString (SIZE (0..16))
	ACCESS		read-only
	STATUS		mandatory
	DESCRIPTION	"Channel 2 name."
::= { channel2 1 }

ch2Val OBJECT-TYPE
	SYNTAX		DisplayString (SIZE (0..8))
	ACCESS		read-only
	STATUS		mandatory
	DESCRIPTION	"Channel 2 temperature."
::= { channel2 2 }

ch2IntVal OBJECT-TYPE
	SYNTAX		INTEGER (-550..1250)
	ACCESS		read-only
	STATUS		mandatory
	DESCRIPTION	"Channel 2 temperature * 10 (12,5 dgr C = 125)."
::= { channel2 3 }

ch2Alarm OBJECT-TYPE
	SYNTAX		INTEGER (0..1)
	ACCESS		read-only
	STATUS		mandatory
	DESCRIPTION	"Alarm on channel 2; 0 - No alarm, 1 - Alarm Hi, 2- Alarm Lo."
::= { channel2 4 }

ch2LimHi OBJECT-TYPE
	SYNTAX		DisplayString (SIZE (0..8))
	ACCESS		read-only
	STATUS		mandatory
	DESCRIPTION	"Channel 2 temperature upper alarm limit."
::= { channel2 5 }

ch2LimLo OBJECT-TYPE
	SYNTAX		DisplayString (SIZE (0..8))
	ACCESS		read-only
	STATUS		mandatory
	DESCRIPTION	"Channel 2 temperature low alarm limit."
::= { channel2 6 }

ch2LimHyst OBJECT-TYPE
	SYNTAX		DisplayString (SIZE (0..8))
	ACCESS		read-only
	STATUS		mandatory
	DESCRIPTION	"Channel 2 temperature hysteressis."
::= { channel2 7 }

ch2Delay OBJECT-TYPE
	SYNTAX		INTEGER (0..65534)
	ACCESS		read-only
	STATUS		mandatory
	DESCRIPTION	"Channel 2 temperature alarm delay [s]."
::= { channel2 8 }

-----------------------------------------------------------------------
-- channel3
-----------------------------------------------------------------------
ch3Name OBJECT-TYPE
	SYNTAX		DisplayString (SIZE (0..16))
	ACCESS		read-only
	STATUS		mandatory
	DESCRIPTION	"Channel 3 name."
::= { channel3 1 }

ch3Val OBJECT-TYPE
	SYNTAX		DisplayString (SIZE (0..8))
	ACCESS		read-only
	STATUS		mandatory
	DESCRIPTION	"Channel 3 temperature."
::= { channel3 2 }

ch3IntVal OBJECT-TYPE
	SYNTAX		INTEGER (-550..1250)
	ACCESS		read-only
	STATUS		mandatory
	DESCRIPTION	"Channel 3 temperature * 10 (12,5 dgr C = 125)."
::= { channel3 3 }

ch3Alarm OBJECT-TYPE
	SYNTAX		INTEGER (0..1)
	ACCESS		read-only
	STATUS		mandatory
	DESCRIPTION	"Alarm on channel 3; 0 - No alarm, 1 - Alarm Hi, 2- Alarm Lo."
::= { channel3 4 }

ch3LimHi OBJECT-TYPE
	SYNTAX		DisplayString (SIZE (0..8))
	ACCESS		read-only
	STATUS		mandatory
	DESCRIPTION	"Channel 3 temperature upper alarm limit."
::= { channel3 5 }

ch3LimLo OBJECT-TYPE
	SYNTAX		DisplayString (SIZE (0..8))
	ACCESS		read-only
	STATUS		mandatory
	DESCRIPTION	"Channel 3 temperature low alarm limit."
::= { channel3 6 }

ch3LimHyst OBJECT-TYPE
	SYNTAX		DisplayString (SIZE (0..8))
	ACCESS		read-only
	STATUS		mandatory
	DESCRIPTION	"Channel 3 temperature hysteressis."
::= { channel3 7 }

ch3Delay OBJECT-TYPE
	SYNTAX		INTEGER (0..65534)
	ACCESS		read-only
	STATUS		mandatory
	DESCRIPTION	"Channel 3 temperature alarm delay [s]."
::= { channel3 8 }

-----------------------------------------------------------------------
-- channel4
-----------------------------------------------------------------------
ch4Name OBJECT-TYPE
	SYNTAX		DisplayString (SIZE (0..16))
	ACCESS		read-only
	STATUS		mandatory
	DESCRIPTION	"Channel 4 name."
::= { channel4 1 }

ch4Val OBJECT-TYPE
	SYNTAX		DisplayString (SIZE (0..8))
	ACCESS		read-only
	STATUS		mandatory
	DESCRIPTION	"Channel 4 temperature."
::= { channel4 2 }

ch4IntVal OBJECT-TYPE
	SYNTAX		INTEGER (-550..1250)
	ACCESS		read-only
	STATUS		mandatory
	DESCRIPTION	"Channel 4 temperature * 10 (12,5 dgr C = 125)."
::= { channel4 3 }

ch4Alarm OBJECT-TYPE
	SYNTAX		INTEGER (0..1)
	ACCESS		read-only
	STATUS		mandatory
	DESCRIPTION	"Alarm on channel 4; 0 - No alarm, 1 - Alarm Hi, 2- Alarm Lo."
::= { channel4 4 }

ch4LimHi OBJECT-TYPE
	SYNTAX		DisplayString (SIZE (0..8))
	ACCESS		read-only
	STATUS		mandatory
	DESCRIPTION	"Channel 4 temperature upper alarm limit."
::= { channel4 5 }

ch4LimLo OBJECT-TYPE
	SYNTAX		DisplayString (SIZE (0..8))
	ACCESS		read-only
	STATUS		mandatory
	DESCRIPTION	"Channel 4 temperature low alarm limit."
::= { channel4 6 }

ch4LimHyst OBJECT-TYPE
	SYNTAX		DisplayString (SIZE (0..8))
	ACCESS		read-only
	STATUS		mandatory
	DESCRIPTION	"Channel 4 temperature hysteressis."
::= { channel4 7 }

ch4Delay OBJECT-TYPE
	SYNTAX		INTEGER (0..65534)
	ACCESS		read-only
	STATUS		mandatory
	DESCRIPTION	"Channel 4 temperature alarm delay [s]."
::= { channel4 8 }

-----------------------------------------------------------------------
-- traps
-----------------------------------------------------------------------

messageString OBJECT-TYPE
	SYNTAX		DisplayString (SIZE (0..30))
	ACCESS		read-only
	STATUS		mandatory
	DESCRIPTION	"Message giving more detailed information on alarms."
::= { traps 1 }

-----------------------------------------------------------------------
-- tables
-----------------------------------------------------------------------
historyTable OBJECT-TYPE
	SYNTAX  SEQUENCE OF HistoryEntry
	ACCESS  not-accessible
	STATUS  mandatory
	DESCRIPTION	"Table of the history values."
::= { tables 1 }

historyEntry OBJECT-TYPE
	SYNTAX  HistoryEntry
	ACCESS  not-accessible
	STATUS  optional
	DESCRIPTION	"History values entries."
	INDEX   { ch1temperature }
::= { historyTable 1 }

HistoryEntry ::=
	SEQUENCE {
		ch1temperature
			INTEGER,
		ch2temperature
			INTEGER,
		ch3temperature
			INTEGER,
		ch4temperature
			INTEGER
		}

ch1temperature OBJECT-TYPE
	SYNTAX  INTEGER (1..65535)
	ACCESS  read-only
	STATUS  mandatory
	DESCRIPTION	"Temperature reading."
::= { historyEntry 1 }

ch2temperature OBJECT-TYPE
	SYNTAX  INTEGER (1..65535)
	ACCESS  read-only
	STATUS  mandatory
	DESCRIPTION	"Humidity reading."
::= { historyEntry 2 }

ch3temperature OBJECT-TYPE
	SYNTAX  INTEGER (1..65535)
	ACCESS  read-only
	STATUS  mandatory
	DESCRIPTION	"Computed value reading."
::= { historyEntry 3 }

ch4temperature OBJECT-TYPE
	SYNTAX  INTEGER (1..65535)
	ACCESS  read-only
	STATUS  mandatory
	DESCRIPTION	"Pressure reading."
::= { historyEntry 4 }

END
