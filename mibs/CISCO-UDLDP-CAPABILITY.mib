-- *****************************************************************
-- CISCO-UDLDP-CAPABILITY.my:
-- Cisco CISCO-UDLDP-MIB AGENT-CAPABILITIES
--
-- August 2003, Padma Pullela 
--
-- Copyright (c) 2003 by Cisco Systesms, Inc.
-- All rights reserved.
-- *****************************************************************

CISCO-UDLDP-CAPABILITY DEFINITIONS ::= BEGIN

IMPORTS
        MODULE-IDENTITY
                FROM SNMPv2-SMI
        AGENT-CAPABILITIES
                FROM SNMPv2-CONF
        ciscoAgentCapability
                FROM CISCO-SMI;

ciscoUdldpCapability MODULE-IDENTITY
        LAST-UPDATED    "200308060000Z"
        ORGANIZATION    "Cisco Systems, Inc."
        CONTACT-INFO
                "       Cisco Systems
                        Customer Service

                Postal: 170 West Tasman Drive
                        San Jose, CA  95134
                        USA

                   Tel: +1 800 553-NETS

                E-mail: cs-lan-switch-snmp@cisco.com"
        DESCRIPTION
                "The capabilities description of 
                 CISCO-UDLDP-MIB."

        REVISION        "200308060000Z"
        DESCRIPTION
                "Initial version of this MIB module."
        ::= { ciscoAgentCapability 344 }

ciscoUdldpCapV12R0214SXCat6K  AGENT-CAPABILITIES
    PRODUCT-RELEASE     "Cisco IOS 12.2(14SX) on Catalyst 6000/6500
                         and Cisco 7600 series devices."
    STATUS              current
    DESCRIPTION         "CISCO-UDLDP-MIB capabilities."

    SUPPORTS            CISCO-UDLDP-MIB
    INCLUDES            { ciscoUdldpMIBGroup2 }
    ::= { ciscoUdldpCapability 1 }

ciscoUdldpCapCatOSV07R0604  AGENT-CAPABILITIES
    PRODUCT-RELEASE     "Cisco CatOS 7.6(4)." 
    STATUS              current
    DESCRIPTION         "CISCO-UDLDP-MIB capabilities."

    SUPPORTS            CISCO-UDLDP-MIB
    INCLUDES            { ciscoUdldpMIBGroup,
                          ciscoUdldpAggreModeOptionalGroup
                        }
    ::= { ciscoUdldpCapability 2 }

ciscoUdldpCapCatOSV08R0101 AGENT-CAPABILITIES
    PRODUCT-RELEASE     "Cisco CatOS 8.1(1)." 
    STATUS              current
    DESCRIPTION         "CISCO-UDLDP-MIB capabilities."

    SUPPORTS            CISCO-UDLDP-MIB
    INCLUDES            { ciscoUdldpMIBGroup,
                          ciscoUdldpAggreModeOptionalGroup,
                          ciscoUdldpMIBGroup2
                        }
    VARIATION           cudldpGlobalMode
    SYNTAX              INTEGER { enable(1), disable(2)}
    DESCRIPTION         "Only enable(1) and disable(2) are supported. "

    VARIATION           cudldpInterfaceAdminMode
    SYNTAX              INTEGER { enable(1), disable(2), aggressive(3)}
    DESCRIPTION         "Only enable(1), disable(2) and aggressive(3)
                         are supported. "
    ::= { ciscoUdldpCapability 3 }

END
