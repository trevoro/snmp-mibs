Nortel-MsCarrier-MscPassport-TimeMIB
DEFINITIONS ::= BEGIN



IMPORTS

      OBJECT-TYPE
   FROM RFC-1212

      IpAddress
   FROM RFC1155-SMI

      mscPassportMIBs,
      mscComponents
   FROM Nortel-MsCarrier-MscPassport-UsefulDefinitionsMIB

      Counter32,
      RowPointer,
      DisplayString,
      StorageType,
      RowStatus,
      Integer32,
      Unsigned32
   FROM Nortel-MsCarrier-MscPassport-StandardTextualConventionsMIB

      NonReplicated,
      EnterpriseDateAndTime
   FROM Nortel-MsCarrier-MscPassport-TextualConventionsMIB;




-- LAST-UPDATED   "9909010000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     Time Enterprise MIB."

timeMIB OBJECT IDENTIFIER ::= { mscPassportMIBs 13 }










-- Time
-- The Time component provides access to time and date information 
-- on this module. It has operational attributes and optional 
-- provisionable Server subcomponents.

mscTime OBJECT IDENTIFIER ::= { mscComponents 19 }



mscTimeRowStatusTable OBJECT-TYPE
   SYNTAX     SEQUENCE OF MscTimeRowStatusEntry
   ACCESS     not-accessible
   STATUS     mandatory
   DESCRIPTION
     "This entry controls the addition and deletion of 
      mscTime components."
::= { mscTime 1 }

mscTimeRowStatusEntry OBJECT-TYPE
   SYNTAX     MscTimeRowStatusEntry
   ACCESS     not-accessible
   STATUS     mandatory
   DESCRIPTION
     "A single entry in the table represents a single 
      mscTime component."
   INDEX {
      mscTimeIndex }
::= { mscTimeRowStatusTable 1 }

MscTimeRowStatusEntry ::= SEQUENCE {
   mscTimeRowStatus
      RowStatus,
   mscTimeComponentName
      DisplayString,
   mscTimeStorageType
      StorageType,
   mscTimeIndex
      NonReplicated }

mscTimeRowStatus OBJECT-TYPE
   SYNTAX     RowStatus 
   ACCESS     read-only
   STATUS     mandatory
   DESCRIPTION
     "This variable is used as the basis for SNMP naming of
      mscTime components.
      These components cannot be added nor deleted."
::= { mscTimeRowStatusEntry 1 }

mscTimeComponentName OBJECT-TYPE
   SYNTAX     DisplayString 
   ACCESS     read-only
   STATUS     mandatory
   DESCRIPTION
     "This variable provides the component's string name for
      use with the ASCII Console Interface"
::= { mscTimeRowStatusEntry 2 }

mscTimeStorageType OBJECT-TYPE
   SYNTAX     StorageType 
   ACCESS     read-only
   STATUS     mandatory
   DESCRIPTION
     "This variable represents the storage type value for the
      mscTime tables."
::= { mscTimeRowStatusEntry 4 }

mscTimeIndex OBJECT-TYPE
   SYNTAX     NonReplicated 
   ACCESS     not-accessible
   STATUS     mandatory
   DESCRIPTION
     "This variable represents the index for the mscTime tables."
::= { mscTimeRowStatusEntry 10 }

mscTimeOperTable OBJECT-TYPE
   SYNTAX     SEQUENCE OF MscTimeOperEntry
   ACCESS     not-accessible
   STATUS     mandatory
   DESCRIPTION
     "This group contains the operational attributes of the Time 
      component."
::= { mscTime 10 }

mscTimeOperEntry OBJECT-TYPE
   SYNTAX     MscTimeOperEntry
   ACCESS     not-accessible
   STATUS     mandatory
   DESCRIPTION
     "An entry in the mscTimeOperTable."
   INDEX {
      mscTimeIndex }
::= { mscTimeOperTable 1 }

MscTimeOperEntry ::= SEQUENCE {
   mscTimeNetworkTime
      EnterpriseDateAndTime,
   mscTimeSyncStatus
      INTEGER,
   mscTimeSyncSource
      IpAddress,
   mscTimeTimeOffset
      Unsigned32,
   mscTimeModuleTime
      EnterpriseDateAndTime,
   mscTimeOffset
      INTEGER,
   mscTimeMainServer
      IpAddress,
   mscTimeXntpVersion
      Unsigned32 }

mscTimeNetworkTime OBJECT-TYPE
   SYNTAX     EnterpriseDateAndTime (SIZE (0 | 19))
   ACCESS     read-write
   STATUS     obsolete
   DESCRIPTION
     "The networkTime attribute represents the current date and time. The 
      operator resets the current date and time by setting this attribute. If 
      syncStatus is synchronized or synchronizing, the set verb is 
      disabled."
::= { mscTimeOperEntry 1 }

mscTimeSyncStatus OBJECT-TYPE
   SYNTAX     INTEGER  {
                 synchronized(0),
                 unsynchronized(1),
                 synchronizing(4),
                 unspecified(5) }
   ACCESS     read-only
   STATUS     mandatory
   DESCRIPTION
     "This attribute indicates the XNTP (Network Time Protocol) 
      synchronization status of this module. If the value is synchronized 
      or synchronizing, the syncSource attribute indicates the IP address 
      of the main network time server.
      The values have the following meanings:
      synchronized -- The module is synchronized with the network time 
      server.
      unsynchronized -- There is no network time server selected as 
      XNTP server for the module to synchronize its time with.
      synchronizing -- The module is trying to synchronize with the 
      network time server.
      unknown -- The synchronization status of the module is unknown."
::= { mscTimeOperEntry 2 }

mscTimeSyncSource OBJECT-TYPE
   SYNTAX     IpAddress 
   ACCESS     read-only
   STATUS     obsolete
   DESCRIPTION
     "The syncSource is the IP address of the time server host to which 
      the module's syncStatus is synchronized. If the module's syncStatus 
      is unsynchronized, the address is 0.0.0.0."
::= { mscTimeOperEntry 3 }

mscTimeTimeOffset OBJECT-TYPE
   SYNTAX     Unsigned32 (0..1440)
   ACCESS     read-write
   STATUS     obsolete
   DESCRIPTION
     "The timeOffset attribute is the number of minutes, to add to the 
      reference time, which is equal to the Universal Coordinated Time 
      (UTC), to obtain the moduleTime."
   DEFVAL     { 0 }
::= { mscTimeOperEntry 4 }

mscTimeModuleTime OBJECT-TYPE
   SYNTAX     EnterpriseDateAndTime (SIZE (0 | 19))
   ACCESS     read-write
   STATUS     mandatory
   DESCRIPTION
     "This attribute indicates the current date and time on this module. 
      The moduleTime is obtained by adding an offset to the reference 
      time, which is the Universal Time Coordinated (UTC). When the 
      moduleTime is set, it keeps the value even if the card boots. It is the 
      time used for time stamps, such as in alarms and accounting data. 
      The operator resets the current date and time by setting this attribute 
      when syncStatus is unsynchronized. Setting this attribute is not 
      allowed if syncStatus is synchronized or synchronizing."
::= { mscTimeOperEntry 5 }

mscTimeOffset OBJECT-TYPE
   SYNTAX     INTEGER (-720..1440)
   ACCESS     read-write
   STATUS     mandatory
   DESCRIPTION
     "This attribute specifies the number of minutes to be added to the 
      reference time, which is Universal Coordinated Time (UTC), to 
      obtain the moduleTime. It keeps its value even if the card boots. 
      However, if the node is powered-off for more than 24 hours, it 
      resets to the default value, which is 0. The specified value should be 
      in the range -720 (-12 hours) to 720 (+12 hours). Values greater 
      than 720 are accepted for backward compatibility; for example, 780 
      (13 hours) corresponds to an offset of -11 hours. If a value greater 
      than 720 is entered, it will be displayed as a negative offset."
   DEFVAL     { 0 }
::= { mscTimeOperEntry 6 }

mscTimeMainServer OBJECT-TYPE
   SYNTAX     IpAddress 
   ACCESS     read-only
   STATUS     mandatory
   DESCRIPTION
     "This attribute indicates the IP address of the main network time 
      server that this module synchronizes with. If syncStatus is 
      unsynchronized, then mainServer is 0.0.0.0."
::= { mscTimeOperEntry 7 }

mscTimeXntpVersion OBJECT-TYPE
   SYNTAX     Unsigned32 (0..15)
   ACCESS     read-only
   STATUS     mandatory
   DESCRIPTION
     "This attribute indicates the current protocol version of XNTP 
      running on this module."
::= { mscTimeOperEntry 8 }

mscTimeSyncSourcesTable OBJECT-TYPE
   SYNTAX     SEQUENCE OF MscTimeSyncSourcesEntry
   ACCESS     not-accessible
   STATUS     mandatory
   DESCRIPTION
     "This attribute indicates the IP addresses of the network time servers 
      that this module synchronizes with. XNTP uses the clock values of 
      the network time servers to set its moduleTime."
::= { mscTime 391 }

mscTimeSyncSourcesEntry OBJECT-TYPE
   SYNTAX     MscTimeSyncSourcesEntry
   ACCESS     not-accessible
   STATUS     mandatory
   DESCRIPTION
     "An entry in the mscTimeSyncSourcesTable."
   INDEX {
      mscTimeIndex,
      mscTimeSyncSourcesValue }
::= { mscTimeSyncSourcesTable 1 }

MscTimeSyncSourcesEntry ::= SEQUENCE {
   mscTimeSyncSourcesValue
      IpAddress }

mscTimeSyncSourcesValue OBJECT-TYPE
   SYNTAX     IpAddress 
   ACCESS     read-only
   STATUS     mandatory
   DESCRIPTION
     "This variable represents both the value and the index for the
      mscTimeSyncSourcesTable."
::= { mscTimeSyncSourcesEntry 1 }


-- Time Server/n
-- The Server component represents a single network time server that 
-- this module can use for network time synchronization.

mscTimeServer OBJECT IDENTIFIER ::= { mscTime 3 }



mscTimeServerRowStatusTable OBJECT-TYPE
   SYNTAX     SEQUENCE OF MscTimeServerRowStatusEntry
   ACCESS     not-accessible
   STATUS     mandatory
   DESCRIPTION
     "This entry controls the addition and deletion of 
      mscTimeServer components."
::= { mscTimeServer 1 }

mscTimeServerRowStatusEntry OBJECT-TYPE
   SYNTAX     MscTimeServerRowStatusEntry
   ACCESS     not-accessible
   STATUS     mandatory
   DESCRIPTION
     "A single entry in the table represents a single 
      mscTimeServer component."
   INDEX {
      mscTimeIndex,
      mscTimeServerIndex }
::= { mscTimeServerRowStatusTable 1 }

MscTimeServerRowStatusEntry ::= SEQUENCE {
   mscTimeServerRowStatus
      RowStatus,
   mscTimeServerComponentName
      DisplayString,
   mscTimeServerStorageType
      StorageType,
   mscTimeServerIndex
      Integer32 }

mscTimeServerRowStatus OBJECT-TYPE
   SYNTAX     RowStatus 
   ACCESS     read-write
   STATUS     mandatory
   DESCRIPTION
     "This variable is used as the basis for SNMP naming of
      mscTimeServer components.
      These components can be added and deleted."
::= { mscTimeServerRowStatusEntry 1 }

mscTimeServerComponentName OBJECT-TYPE
   SYNTAX     DisplayString 
   ACCESS     read-only
   STATUS     mandatory
   DESCRIPTION
     "This variable provides the component's string name for
      use with the ASCII Console Interface"
::= { mscTimeServerRowStatusEntry 2 }

mscTimeServerStorageType OBJECT-TYPE
   SYNTAX     StorageType 
   ACCESS     read-only
   STATUS     mandatory
   DESCRIPTION
     "This variable represents the storage type value for the
      mscTimeServer tables."
::= { mscTimeServerRowStatusEntry 4 }

mscTimeServerIndex OBJECT-TYPE
   SYNTAX     Integer32 (1..10)
   ACCESS     not-accessible
   STATUS     mandatory
   DESCRIPTION
     "This variable represents the index for the mscTimeServer tables."
::= { mscTimeServerRowStatusEntry 10 }

mscTimeServerProvTable OBJECT-TYPE
   SYNTAX     SEQUENCE OF MscTimeServerProvEntry
   ACCESS     not-accessible
   STATUS     mandatory
   DESCRIPTION
     "This group contains the provisionable attributes of the Server 
      component."
::= { mscTimeServer 11 }

mscTimeServerProvEntry OBJECT-TYPE
   SYNTAX     MscTimeServerProvEntry
   ACCESS     not-accessible
   STATUS     mandatory
   DESCRIPTION
     "An entry in the mscTimeServerProvTable."
   INDEX {
      mscTimeIndex,
      mscTimeServerIndex }
::= { mscTimeServerProvTable 1 }

MscTimeServerProvEntry ::= SEQUENCE {
   mscTimeServerIpAddress
      IpAddress,
   mscTimeServerIpStack
      INTEGER }

mscTimeServerIpAddress OBJECT-TYPE
   SYNTAX     IpAddress 
   ACCESS     read-write
   STATUS     mandatory
   DESCRIPTION
     "This attribute specifies the IP address of a network time server that 
      the module will attempt to synchronize with. The value of 
      ipAddress must be unique across all Server components."
::= { mscTimeServerProvEntry 1 }

mscTimeServerIpStack OBJECT-TYPE
   SYNTAX     INTEGER  {
                 ipiFrIpiVc(1),
                 vrIp(2) }
   ACCESS     read-write
   STATUS     mandatory
   DESCRIPTION
     "This attribute specifies the IP stack that XNTP uses to communi-
      cate with the network time server. If ipiFrIpiVc is selected, then an 
      IpiFr or IpiVc component must be provisioned on this module. If 
      vrIp is selected, then Ip must be provisioned under the management 
      Vr on this module."
   DEFVAL     { ipiFrIpiVc }
::= { mscTimeServerProvEntry 2 }

mscTimeServerStateTable OBJECT-TYPE
   SYNTAX     SEQUENCE OF MscTimeServerStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscTimeServer 12 }

mscTimeServerStateEntry OBJECT-TYPE
   SYNTAX     MscTimeServerStateEntry
   ACCESS     not-accessible
   STATUS     mandatory
   DESCRIPTION
     "An entry in the mscTimeServerStateTable."
   INDEX {
      mscTimeIndex,
      mscTimeServerIndex }
::= { mscTimeServerStateTable 1 }

MscTimeServerStateEntry ::= SEQUENCE {
   mscTimeServerAdminState
      INTEGER,
   mscTimeServerOperationalState
      INTEGER,
   mscTimeServerUsageState
      INTEGER }

mscTimeServerAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscTimeServerStateEntry 1 }

mscTimeServerOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscTimeServerStateEntry 2 }

mscTimeServerUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscTimeServerStateEntry 3 }

mscTimeServerOperTable OBJECT-TYPE
   SYNTAX     SEQUENCE OF MscTimeServerOperEntry
   ACCESS     not-accessible
   STATUS     mandatory
   DESCRIPTION
     "This group contains the operational attributes of the Server 
      component."
::= { mscTimeServer 13 }

mscTimeServerOperEntry OBJECT-TYPE
   SYNTAX     MscTimeServerOperEntry
   ACCESS     not-accessible
   STATUS     mandatory
   DESCRIPTION
     "An entry in the mscTimeServerOperTable."
   INDEX {
      mscTimeIndex,
      mscTimeServerIndex }
::= { mscTimeServerOperTable 1 }

MscTimeServerOperEntry ::= SEQUENCE {
   mscTimeServerXntpVersion
      Unsigned32,
   mscTimeServerStratum
      Unsigned32,
   mscTimeServerPoll
      Unsigned32,
   mscTimeServerPktSent
      Counter32,
   mscTimeServerPktRecv
      Counter32,
   mscTimeServerPktValid
      Counter32,
   mscTimeServerStatus
      OCTET STRING }

mscTimeServerXntpVersion OBJECT-TYPE
   SYNTAX     Unsigned32 (0..15)
   ACCESS     read-only
   STATUS     mandatory
   DESCRIPTION
     "This attribute indicates the version of XNTP currently in use by the 
      network time server."
::= { mscTimeServerOperEntry 1 }

mscTimeServerStratum OBJECT-TYPE
   SYNTAX     Unsigned32 (0..16)
   ACCESS     read-only
   STATUS     mandatory
   DESCRIPTION
     "This attribute indicates the stratum level of the clock on the network 
      time server."
::= { mscTimeServerOperEntry 2 }

mscTimeServerPoll OBJECT-TYPE
   SYNTAX     Unsigned32 (0..15)
   ACCESS     read-only
   STATUS     mandatory
   DESCRIPTION
     "This attribute indicates the time interval for the Passport module to 
      poll the network time server for time synchronization."
::= { mscTimeServerOperEntry 3 }

mscTimeServerPktSent OBJECT-TYPE
   SYNTAX     Counter32 
   ACCESS     read-only
   STATUS     mandatory
   DESCRIPTION
     "This attribute counts the packets sent to the network time server."
::= { mscTimeServerOperEntry 4 }

mscTimeServerPktRecv OBJECT-TYPE
   SYNTAX     Counter32 
   ACCESS     read-only
   STATUS     mandatory
   DESCRIPTION
     "This attribute counts the packets received from the network time 
      server, including the invalid packets."
::= { mscTimeServerOperEntry 5 }

mscTimeServerPktValid OBJECT-TYPE
   SYNTAX     Counter32 
   ACCESS     read-only
   STATUS     mandatory
   DESCRIPTION
     "This attribute counts the valid packets received from the network 
      time server."
::= { mscTimeServerOperEntry 6 }

mscTimeServerStatus OBJECT-TYPE
   SYNTAX     OCTET STRING (SIZE (2))
   ACCESS     read-only
   STATUS     mandatory
   DESCRIPTION
     "This attribute indicates the status of the network time server.
      main -- This network time server is working properly, and is the 
      system servers (synchronization sources) of the module.
      primary -- This network time server is working properly, and is the 
      primary servers (one of the synchronization sources) of the module
      secondary -- This network time server is working properly, but its 
      offset and dispersion is not stable or too high so that it can not be 
      selected as one of the primary time synchronization sources. But if 
      the primary synchronization sources are not available, it can take 
      over the responsibility and become the time synchronization source 
      of the module.
      unused -- This network time server is not used as a server 
      (synchronization source) of the module.
      noResponse -- This network time server is not responding to the 
      module's time synchronization request. This could be caused by 
      network error or protocol error, or network time server 
      configuration error.
      stratumTooHigh -- This network time server has the bad stratum 
      (higher than 16), or its stratum is higher than the module's stratum.
      leapUnsync -- This network time server's leap value indicates that 
      this network time server is not synchronized.
      clockUnsync -- This network time server's clock values indicates 
      that this network time server is not synchronized.
      rootTooNoisy -- This network time server's root dispersion is too 
      high, so that its time stamp is not used.
      peerTooNoisy -- The modules dispersion relative to this network 
      time server is too high, so this network time server's time stamp is 
      not used.
      faultStick -- This offset of the module relative to this network time 
      server is out of the range or too high, so that it can not be selected 
      as one of the primary time synchronization source.

      Description of bits:
      main(0)
      primary(1)
      secondary(2)
      unused(3)
      noResponse(4)
      stratumTooHigh(5)
      leapUnsync(6)
      clockUnsync(7)
      rootTooNoisy(8)
      peerTooNoisy(9)
      faultStick(10)"
::= { mscTimeServerOperEntry 392 }


-- NetworkSynchronization 
-- The NetworkSynchronization component administers the network 
-- clock synchronization.

mscNS OBJECT IDENTIFIER ::= { mscComponents 20 }



mscNSRowStatusTable OBJECT-TYPE
   SYNTAX     SEQUENCE OF MscNSRowStatusEntry
   ACCESS     not-accessible
   STATUS     mandatory
   DESCRIPTION
     "This entry controls the addition and deletion of 
      mscNS components."
::= { mscNS 1 }

mscNSRowStatusEntry OBJECT-TYPE
   SYNTAX     MscNSRowStatusEntry
   ACCESS     not-accessible
   STATUS     mandatory
   DESCRIPTION
     "A single entry in the table represents a single 
      mscNS component."
   INDEX {
      mscNSIndex }
::= { mscNSRowStatusTable 1 }

MscNSRowStatusEntry ::= SEQUENCE {
   mscNSRowStatus
      RowStatus,
   mscNSComponentName
      DisplayString,
   mscNSStorageType
      StorageType,
   mscNSIndex
      NonReplicated }

mscNSRowStatus OBJECT-TYPE
   SYNTAX     RowStatus 
   ACCESS     read-write
   STATUS     mandatory
   DESCRIPTION
     "This variable is used as the basis for SNMP naming of
      mscNS components.
      These components can be added and deleted."
::= { mscNSRowStatusEntry 1 }

mscNSComponentName OBJECT-TYPE
   SYNTAX     DisplayString 
   ACCESS     read-only
   STATUS     mandatory
   DESCRIPTION
     "This variable provides the component's string name for
      use with the ASCII Console Interface"
::= { mscNSRowStatusEntry 2 }

mscNSStorageType OBJECT-TYPE
   SYNTAX     StorageType 
   ACCESS     read-only
   STATUS     mandatory
   DESCRIPTION
     "This variable represents the storage type value for the
      mscNS tables."
::= { mscNSRowStatusEntry 4 }

mscNSIndex OBJECT-TYPE
   SYNTAX     NonReplicated 
   ACCESS     not-accessible
   STATUS     mandatory
   DESCRIPTION
     "This variable represents the index for the mscNS tables."
::= { mscNSRowStatusEntry 10 }

mscNSProvTable OBJECT-TYPE
   SYNTAX     SEQUENCE OF MscNSProvEntry
   ACCESS     not-accessible
   STATUS     mandatory
   DESCRIPTION
     "This group contains all of the provisioning data for the 
      NetworkSynchronization component."
::= { mscNS 10 }

mscNSProvEntry OBJECT-TYPE
   SYNTAX     MscNSProvEntry
   ACCESS     not-accessible
   STATUS     mandatory
   DESCRIPTION
     "An entry in the mscNSProvTable."
   INDEX {
      mscNSIndex }
::= { mscNSProvTable 1 }

MscNSProvEntry ::= SEQUENCE {
   mscNSPrimaryReference
      RowPointer,
   mscNSSecondaryReference
      RowPointer,
   mscNSTertiaryReference
      RowPointer }

mscNSPrimaryReference OBJECT-TYPE
   SYNTAX     RowPointer 
   ACCESS     read-write
   STATUS     mandatory
   DESCRIPTION
     "This component name is the port that is the preferred choice as the 
      reference for the network clock."
::= { mscNSProvEntry 1 }

mscNSSecondaryReference OBJECT-TYPE
   SYNTAX     RowPointer 
   ACCESS     read-write
   STATUS     mandatory
   DESCRIPTION
     "This component name is the port that is the second choice for the 
      reference for the network clock."
::= { mscNSProvEntry 2 }

mscNSTertiaryReference OBJECT-TYPE
   SYNTAX     RowPointer 
   ACCESS     read-write
   STATUS     mandatory
   DESCRIPTION
     "This component name is the port that is the third choice for the 
      reference for the network clock."
::= { mscNSProvEntry 3 }

mscNSStateTable OBJECT-TYPE
   SYNTAX     SEQUENCE OF MscNSStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { mscNS 11 }

mscNSStateEntry OBJECT-TYPE
   SYNTAX     MscNSStateEntry
   ACCESS     not-accessible
   STATUS     mandatory
   DESCRIPTION
     "An entry in the mscNSStateTable."
   INDEX {
      mscNSIndex }
::= { mscNSStateTable 1 }

MscNSStateEntry ::= SEQUENCE {
   mscNSAdminState
      INTEGER,
   mscNSOperationalState
      INTEGER,
   mscNSUsageState
      INTEGER }

mscNSAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscNSStateEntry 1 }

mscNSOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscNSStateEntry 2 }

mscNSUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscNSStateEntry 3 }

mscNSOperTable OBJECT-TYPE
   SYNTAX     SEQUENCE OF MscNSOperEntry
   ACCESS     not-accessible
   STATUS     mandatory
   DESCRIPTION
     "This group contains the operational attributes for the network clock 
      sync"
::= { mscNS 12 }

mscNSOperEntry OBJECT-TYPE
   SYNTAX     MscNSOperEntry
   ACCESS     not-accessible
   STATUS     mandatory
   DESCRIPTION
     "An entry in the mscNSOperTable."
   INDEX {
      mscNSIndex }
::= { mscNSOperTable 1 }

MscNSOperEntry ::= SEQUENCE {
   mscNSClockSyncState
      INTEGER,
   mscNSActiveReference
      RowPointer,
   mscNSStandbyReference
      RowPointer }

mscNSClockSyncState OBJECT-TYPE
   SYNTAX     INTEGER  {
                 freeRun(0),
                 synchronizing(1),
                 synchronized(3) }
   ACCESS     read-only
   STATUS     mandatory
   DESCRIPTION
     "When the clockSyncState is in the freeRun state, either no 
      reference have beed provisioned or none of the provisioned 
      references have been found to be valid. The Stratum-3 clock is 
      allowed to run freely at its last adjusted frequency.  When the 
      clockSyncState is in the synchronizing state, the Stratum-3 is 
      trying to synchronize in frequency to a valid provisioned reference. 
      This state should last approximately 1-2 minutes, provided the 
      reference is stable.  Once frequency synchronization is acheived, a 
      null phase is acquired and the clockSyncState enters the 
      synchronized state. In this state, both phase and frequency are 
      tracked and compensated for. This node is now ready to support 
      transparent data services."
::= { mscNSOperEntry 1 }

mscNSActiveReference OBJECT-TYPE
   SYNTAX     RowPointer 
   ACCESS     read-only
   STATUS     mandatory
   DESCRIPTION
     "Indicates the active 8Khz clock reference source"
::= { mscNSOperEntry 2 }

mscNSStandbyReference OBJECT-TYPE
   SYNTAX     RowPointer 
   ACCESS     read-only
   STATUS     mandatory
   DESCRIPTION
     "Indicates the standby 8Khz clock reference source which will be 
      selected if a failure is detected on the active source."
::= { mscNSOperEntry 3 }




-- 
-- Version and Compliance statements
-- 



-- Object-Group Statement:
-- A list of all current accessible leaf objects.

-- OBJECTS { mscTimeServerStorageType,
--           mscTimeServerPktValid,
--           mscNSOperationalState,
--           mscTimeServerOperationalState,
--           mscTimeServerStatus,
--           mscTimeOffset,
--           mscTimeRowStatus,
--           mscTimeServerAdminState,
--           mscTimeServerIpStack,
--           mscTimeXntpVersion,
--           mscNSStandbyReference,
--           mscNSActiveReference,
--           mscNSSecondaryReference,
--           mscTimeServerPoll,
--           mscTimeServerRowStatus,
--           mscNSClockSyncState,
--           mscTimeServerXntpVersion,
--           mscNSAdminState,
--           mscTimeServerIpAddress,
--           mscTimeServerPktSent,
--           mscNSPrimaryReference,
--           mscNSTertiaryReference,
--           mscNSRowStatus,
--           mscTimeComponentName,
--           mscTimeSyncSourcesValue,
--           mscNSUsageState,
--           mscTimeServerUsageState,
--           mscTimeServerStratum,
--           mscTimeStorageType,
--           mscTimeMainServer,
--           mscTimeSyncStatus,
--           mscNSComponentName,
--           mscTimeServerComponentName,
--           mscTimeModuleTime,
--           mscTimeServerPktRecv,
--           mscNSStorageType }
-- STATUS  mandatory
-- DESCRIPTION
--   "A list of all current accessible leaf objects."

timeGroup OBJECT IDENTIFIER ::= { timeMIB 1 }
timeGroupCA OBJECT IDENTIFIER ::= { timeGroup 1 }
timeGroupCA02 OBJECT IDENTIFIER ::= { timeGroupCA 3 }
timeGroupCA02A OBJECT IDENTIFIER ::= { timeGroupCA02 2 }



-- Agent-Capabilities Statement:

-- PRODUCT-RELEASE "MscPassport Release 1.2 Time."
-- STATUS          mandatory
-- DESCRIPTION     "Carrier Passport Time MIB: MIB Version CA02A,
--                  Software Version CA02S9C."
-- SUPPORTS        Nortel-MsCarrier-MscPassport-TimeMIB
--    INCLUDES     { timeGroupCA02A }

timeCapabilities OBJECT IDENTIFIER ::= { timeMIB 3 }
timeCapabilitiesCA OBJECT IDENTIFIER ::= { timeCapabilities 1 }
timeCapabilitiesCA02 OBJECT IDENTIFIER ::= { timeCapabilitiesCA 3 }
timeCapabilitiesCA02A OBJECT IDENTIFIER ::= { timeCapabilitiesCA02 2 }





END
