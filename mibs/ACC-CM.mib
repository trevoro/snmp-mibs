ACC-CM DEFINITIONS ::= BEGIN

    IMPORTS
	 OBJECT-TYPE, TimeTicks FROM RFC1155-SMI
	 TRAP-TYPE FROM RFC-1215
	       accTrapLogSeqNum FROM ACC-SYSTEM
	accBRG, DisplayString, RowStatus, IfIndex, SmdsAddress
             FROM ACC-MIB
	accIfName FROM ACC-SYSTEM
        accServiceProfileName
             FROM ACC-SERVICEPROFILE
        ifName
             FROM ACC-FAKE;
-- Call Manager Group
accCmGroup	OBJECT IDENTIFIER ::= { accBRG 64 }
	accCmCallTable	OBJECT-TYPE
		SYNTAX SEQUENCE OF AccCmCallTableEntry
		ACCESS	not-accessible
		STATUS	mandatory
		DESCRIPTION
		"Table containing the call specific information as maintained 
		 by the call management, the call connection table."
		::= { accCmGroup 1 }
	accCmCallTableEntry	OBJECT-TYPE
		SYNTAX 	AccCmCallTableEntry
		ACCESS	not-accessible
		STATUS	mandatory
		DESCRIPTION
		"An entry in the call management call connection table."
		INDEX { INTEGER }
		::= { accCmCallTable 1 }
	AccCmCallTableEntry  ::= SEQUENCE {
		accCmCallIndex  INTEGER,
		accCmCallInfc	OCTET STRING,
		accCmDmType	INTEGER,
		accCmEmIndex	OCTET STRING,
		accCmEmType	INTEGER,
		accCmEmRsrc	OCTET STRING,
		accCmCallDirn	INTEGER
	}
	accCmCallIndex	OBJECT-TYPE
		SYNTAX	INTEGER
		ACCESS	read-only
		STATUS	mandatory
		DESCRIPTION
		"The internal call index assigned."
		::= { accCmCallTableEntry 1 }
	accCmCallInfc	OBJECT-TYPE
		SYNTAX	OCTET STRING
		ACCESS	read-only
		STATUS	mandatory
		DESCRIPTION
		"The Interface on which the resources are allocated for 
		 this call."
		::= { accCmCallTableEntry 2 }
	accCmDmType	OBJECT-TYPE
		SYNTAX	INTEGER {
			isdn (1),
			pstn (2),
			tunnel (3),
			dl2 (4),
			none (9)
		}
		ACCESS	read-only
		STATUS	mandatory
		DESCRIPTION
		"The dial resource type  allocated or being used for 
		 this call."
		::= { accCmCallTableEntry 3 }
	accCmEmIndex	OBJECT-TYPE
		SYNTAX	OCTET STRING
		ACCESS	read-only
		STATUS	mandatory
		DESCRIPTION
		"The endpoint resource allocated or being used for 
		 this call."
		::= { accCmCallTableEntry 4 }
	accCmEmType	OBJECT-TYPE
		SYNTAX	INTEGER {
			hdlc (1),
			modem (2),
			pots (3),
			none (9)
		}
		ACCESS	read-only
		STATUS	mandatory
		DESCRIPTION
		"The endpoint manager type which allocated the resource 
		 used for this call."
		::= { accCmCallTableEntry 5 }
	accCmEmRsrc	OBJECT-TYPE
		SYNTAX	OCTET STRING
		ACCESS	read-only
		STATUS	mandatory
		DESCRIPTION
		"The endpoint resource category, allocated or being used 
		 for this call."
		::= { accCmCallTableEntry 6 }
	accCmCallDirn	OBJECT-TYPE
		SYNTAX	INTEGER
		ACCESS	read-only
		STATUS	mandatory
		DESCRIPTION
		"The direction of this call, whether incoming/ outgoing/
		 permanent."
		::= { accCmCallTableEntry 7 }
-- Call Manager Table
	accCmTable	OBJECT-TYPE
		SYNTAX SEQUENCE OF AccCmTableEntry
		ACCESS	not-accessible
		STATUS	mandatory
		DESCRIPTION
		"Table containing the call manager internal parameters."
		::= { accCmGroup 2 }
	accCmTableEntry	OBJECT-TYPE
		SYNTAX 	AccCmTableEntry
		ACCESS	not-accessible
		STATUS	mandatory
		DESCRIPTION
		"An entry in the call management message parameter table."
                INDEX { INTEGER }
                ::= { accCmTable 1 }
	AccCmTableEntry	::= SEQUENCE {
		accCmMsgLevel	INTEGER
	}
	accCmMsgLevel	OBJECT-TYPE
		SYNTAX	INTEGER
		ACCESS	read-write
		STATUS	mandatory
		DESCRIPTION
		" The call management message level for generating traps."
		::= { accCmTableEntry 1 }
-- Call Manager Interface Parameter Table
	accCmInfcParmTable	OBJECT-TYPE
		SYNTAX SEQUENCE OF AccCmInfcParmTableEntry
		ACCESS	not-accessible
		STATUS	mandatory
		DESCRIPTION
		"Table containing  Interface specific information as 
		 maintained by the call management interface table."
		::= { accCmGroup 3 }
	accCmInfcParmTableEntry	OBJECT-TYPE
		SYNTAX 	AccCmInfcParmTableEntry
		ACCESS	not-accessible
		STATUS	mandatory
		DESCRIPTION
		"An entry in the call management Interface table."
                INDEX { INTEGER }
                ::= { accCmInfcParmTable 1 }
	AccCmInfcParmTableEntry	::= SEQUENCE {
		accCmInfc		INTEGER,
		accCmInfcMsgLevel	INTEGER
	}
	accCmInfc	OBJECT-TYPE
		SYNTAX	INTEGER
		ACCESS	read-only
		STATUS	mandatory
		DESCRIPTION
		"The Interface on which the paramters are being updated/
		 displayed."
		::= { accCmInfcParmTableEntry 1 }
	accCmInfcMsgLevel	OBJECT-TYPE
		SYNTAX	INTEGER
		ACCESS	read-write
		STATUS	mandatory
		DESCRIPTION
		"The interface message level for generating traps."
		::= { accCmInfcParmTableEntry 2 }
-- Composite Call Table
	accCmCompCallTable OBJECT-TYPE
	    SYNTAX SEQUENCE OF AccCmCompCallEntry
	    ACCESS not-accessible
	    STATUS mandatory
	    DESCRIPTION
	    " Composite table of all incoming and outgoing calls "
	    ::= { accCmGroup 4 }
	accCmCompCallEntry OBJECT-TYPE
	    SYNTAX AccCmCompCallEntry
	    ACCESS not-accessible
	    STATUS mandatory
	    DESCRIPTION
	    " An entry in the composite call table. "
	    INDEX { accCmCallIdent }
	    ::= { accCmCompCallTable 1 }
	AccCmCompCallEntry ::= SEQUENCE {
	    accCmCallIdent INTEGER,
	    accCmCallSegment INTEGER,
	    accCmCallDisposition INTEGER,
	    accCmCallType INTEGER,
	    accCmServiceProfile OCTET STRING,
	    accCmPayloadStatus INTEGER,
	    accCmDialInfc INTEGER,
	    accCmDialType INTEGER,
	    accCmDialState INTEGER,
	    accCmEndpointInfc INTEGER,
	    accCmEndpointType INTEGER,
	    accCmEndpointState INTEGER,
	    accCmCalledNumber OCTET STRING,
	    accCmCallingNumber OCTET STRING,
	    accCmCallDuration TimeTicks
	    }
	accCmCallIdent OBJECT-TYPE
	    SYNTAX INTEGER
	    ACCESS read-only
	    STATUS mandatory
	    DESCRIPTION
	    " A unique identifier for this call "
	    ::= { accCmCompCallEntry 1 }
	accCmCallSegment OBJECT-TYPE
	    SYNTAX INTEGER {
		incoming (1),
		outgoing (2),
		permanent (3)
	    }
	    ACCESS read-only
	    STATUS mandatory
	    DESCRIPTION
	    " Type of call segment "
	    ::= { accCmCompCallEntry 2 }
	accCmCallDisposition OBJECT-TYPE
	    SYNTAX INTEGER {
		received (1),
		validated (2),
		authorized (3),
		configured (4),
		rejected (5),
		accepted (6),
		switched (7),
		returned (8),
		disconnected (9),
		released (10),
		permanent (11)
	    }
	    ACCESS read-only
	    STATUS mandatory
	    DESCRIPTION
	    " Call disposition "
	    ::= { accCmCompCallEntry 3 }
	accCmCallType OBJECT-TYPE
	    SYNTAX INTEGER {
		cm64 (1),
		cm56 (2),
		udi (3),
		rdi (4),
		speech (8),
		audio3 (16),
		modem (24),
		audio7 (32),
		audio (48),
		wideband (64),
		multirate (128),
		v-110 (256),
		nband (263),
		data (455),
		circuit (134217727),
		packet (134217728)
	    }
	    ACCESS read-only
	    STATUS mandatory
	    DESCRIPTION
	    " Bearer type for the call  "
	    ::= { accCmCompCallEntry 4 }
	accCmServiceProfile OBJECT-TYPE
	    SYNTAX OCTET STRING
	    ACCESS read-only
	    STATUS mandatory
	    DESCRIPTION
	    " Service profile used by the call "
	    ::= { accCmCompCallEntry 5 }
	accCmPayloadStatus OBJECT-TYPE
	    SYNTAX INTEGER {
		released (1),
		deferred (2),
		establishing (3),
		established (4),
		releasing (5)
	    }
	    ACCESS read-only
	    STATUS mandatory
	    DESCRIPTION
	    " Status of the payload of the call "
	    ::= { accCmCompCallEntry 6 }
	accCmDialInfc OBJECT-TYPE
	    SYNTAX INTEGER
	    ACCESS read-only
	    STATUS mandatory
	    DESCRIPTION
	    " Dialing interface used for the call "
	    ::= { accCmCompCallEntry 7 }
	accCmDialType OBJECT-TYPE
	    SYNTAX INTEGER {
		isdn (1),
		pstn (2),
		tunnel (3),
		dl2 (4),
		vna (5),
		ss7 (6),
		none (9)
	    }
	    ACCESS read-only
	    STATUS mandatory
	    DESCRIPTION
	    " Signaling type of the dialing interface  "
	    ::= { accCmCompCallEntry 8 }
	accCmDialState OBJECT-TYPE
	    SYNTAX INTEGER {
		initiated (1),
		sending (2),
		proceeding (3),
		delivered (4),
		offered (6),
		alerting (7),
		answered (8),
		routing (9),
		connected (10),
		disconn-req (11),
		disconn-ind (12),
		suspend (15),
		resume (17),
		releasing (19),
		receiving (25),
		busy (99)
	    }
	    ACCESS read-only
	    STATUS mandatory
	    DESCRIPTION
	    " Signaling state of the call "
	    ::= { accCmCompCallEntry 9 }
	accCmEndpointInfc OBJECT-TYPE
	    SYNTAX INTEGER
	    ACCESS read-only
	    STATUS mandatory
	    DESCRIPTION
	    " Endpoint interface used for the call "
	    ::= { accCmCompCallEntry 10 }
	accCmEndpointType OBJECT-TYPE
	    SYNTAX INTEGER {
		hdlc (1),
		modem (2),
		g-711mu (3),
		g-711a (4),
		g-729a (5),
		none (127)
	    }
	    ACCESS read-only
	    STATUS mandatory
	    DESCRIPTION
	    " Type of endpoint used for the call "
	    ::= { accCmCompCallEntry 11 }
	accCmEndpointState OBJECT-TYPE
	    SYNTAX INTEGER {
		released (1),
		assigning (2),
		assigned (3),
		setup (4),
		ready (5),
		alerting (6),
		answered (7),
		converse (8),
		suspend (9),
		resume (10),
		releasing (11)
	    }
	    ACCESS read-only
	    STATUS mandatory
	    DESCRIPTION
	    " The state of the endpoint "
	    ::= { accCmCompCallEntry 12 }
	accCmCalledNumber OBJECT-TYPE
	    SYNTAX OCTET STRING
	    ACCESS read-only
	    STATUS mandatory
	    DESCRIPTION
	    " Called number "
	    ::= { accCmCompCallEntry 13 }
	accCmCallingNumber OBJECT-TYPE
	    SYNTAX OCTET STRING
	    ACCESS read-only
	    STATUS mandatory
	    DESCRIPTION
	    " Calling Number "
	    ::= { accCmCompCallEntry 14 }
	accCmCallDuration OBJECT-TYPE
	    SYNTAX TimeTicks
	    ACCESS read-only
	    STATUS mandatory
	    DESCRIPTION
	    " Call duration  "
	    ::= { accCmCompCallEntry 15 }
-- Non-switched call table
	accCmNsCallTable OBJECT-TYPE
	    SYNTAX SEQUENCE OF AccCmNsCallEntry
	    ACCESS not-accessible
	    STATUS mandatory
	    DESCRIPTION
	    " Table of calls which have not been switched.  These calls
	      have either been originated or accepted."
	    ::= { accCmGroup 5 }
	accCmNsCallEntry OBJECT-TYPE
	    SYNTAX AccCmNsCallEntry
	    ACCESS not-accessible
	    STATUS mandatory
	    DESCRIPTION
	    " An entry in the non-switched call table "
	    INDEX { accCmNsCallIdent }
	    ::= { accCmNsCallTable 1 }
	AccCmNsCallEntry ::= SEQUENCE {
	    accCmNsCallIdent INTEGER,
	    accCmNsCallSegment INTEGER,
	    accCmNsCallDisposition INTEGER,
	    accCmNsCallType INTEGER,
	    accCmNsServiceProfile OCTET STRING,
	    accCmNsPayloadStatus INTEGER,
	    accCmNsDialInfc INTEGER,
	    accCmNsDialType INTEGER,
	    accCmNsDialState INTEGER,
	    accCmNsEndpointInfc INTEGER,
	    accCmNsEndpointType INTEGER,
	    accCmNsEndpointState INTEGER,
	    accCmNsCalledNumber OCTET STRING,
	    accCmNsCallingNumber OCTET STRING,
	    accCmNsCallDuration TimeTicks
	    }
	accCmNsCallIdent OBJECT-TYPE
	    SYNTAX INTEGER
	    ACCESS read-only
	    STATUS mandatory
	    DESCRIPTION
	    " A unique call identifier for this call "
	    ::= { accCmNsCallEntry 1 }
	accCmNsCallSegment OBJECT-TYPE
	    SYNTAX INTEGER {
		incoming (1),
		outgoing (2),
		permanent (3)
	    }
	    ACCESS read-only
	    STATUS mandatory
	    DESCRIPTION
	    " Type of call segment "
	    ::= { accCmNsCallEntry 2 }
	accCmNsCallDisposition OBJECT-TYPE
	    SYNTAX INTEGER {
		received (1),
		validated (2),
		authorized (3),
		configured (4),
		rejected (5),
		accepted (6),
		switched (7),
		returned (8),
		disconnected (9),
		released (10),
		permanent (11)
	    }
	    ACCESS read-only
	    STATUS mandatory
	    DESCRIPTION
	    " Call disposition  "
	    ::= { accCmNsCallEntry 3 }
	accCmNsCallType OBJECT-TYPE
	    SYNTAX INTEGER {
		cm64 (1),
		cm56 (2),
		udi (3),
		rdi (4),
		speech (8),
		audio3 (16),
		modem (24),
		audio7 (32),
		audio (48),
		wideband (64),
		multirate (128),
		v-110 (256),
		nband (263),
		data (455),
		circuit (134217727),
		packet (134217728)
	    }
	    ACCESS read-only
	    STATUS mandatory
	    DESCRIPTION
	    " Bearer type for the call  "
	    ::= { accCmNsCallEntry 4 }
	accCmNsServiceProfile OBJECT-TYPE
	    SYNTAX OCTET STRING
	    ACCESS read-only
	    STATUS mandatory
	    DESCRIPTION
	    " Service profile used by the call  "
	    ::= { accCmNsCallEntry 5 }
	accCmNsPayloadStatus OBJECT-TYPE
	    SYNTAX INTEGER {
		released (1),
		deferred (2),
		establishing (3),
		established (4),
		releasing (5)
	    }
	    ACCESS read-only
	    STATUS mandatory
	    DESCRIPTION
	    " Status of the payload of the call "
	    ::= { accCmNsCallEntry 6 }
	accCmNsDialInfc OBJECT-TYPE
	    SYNTAX INTEGER
	    ACCESS read-only
	    STATUS mandatory
	    DESCRIPTION
	    " Dialing interface used for the call  "
	    ::= { accCmNsCallEntry 7 }
	accCmNsDialType OBJECT-TYPE
	    SYNTAX INTEGER {
		isdn (1),
		pstn (2),
		tunnel (3),
		dl2 (4),
		vna (5),
		ss7 (6),
		none (127)
	    }
	    ACCESS read-only
	    STATUS mandatory
	    DESCRIPTION
	    " Signaling type of the dialing interface  "
	    ::= { accCmNsCallEntry 8 }
	accCmNsDialState OBJECT-TYPE
	    SYNTAX INTEGER {
		initiated (1),
		sending (2),
		proceeding (3),
		delivered (4),
		offered (6),
		alerting (7),
		answered (8),
		routing (9),
		connected (10),
		disconn-req (11),
		disconn-ind (12),
		suspend (15),
		resume (17),
		releasing (19),
		receiving (25),
		busy (99)
	    }
	    ACCESS read-only
	    STATUS mandatory
	    DESCRIPTION
	    " Signaling state of the call "
	    ::= { accCmNsCallEntry 9 }
	accCmNsEndpointInfc OBJECT-TYPE
	    SYNTAX INTEGER
	    ACCESS read-only
	    STATUS mandatory
	    DESCRIPTION
	    " Endpoint interface used for the call  "
	    ::= { accCmNsCallEntry 10 }
	accCmNsEndpointType OBJECT-TYPE
	    SYNTAX INTEGER {
		hdlc (1),
		modem (2),
		g-711mu (3),
		g-711a (4),
		g-729a (5),
		none (127)
	    }
	    ACCESS read-only
	    STATUS mandatory
	    DESCRIPTION
	    " Type of endpoint used for the call  "
	    ::= { accCmNsCallEntry 11 }
	accCmNsEndpointState OBJECT-TYPE
	    SYNTAX INTEGER {
		released (1),
		assigning (2),
		assigned (3),
		setup (4),
		ready (5),
		alerting (6),
		answered (7),
		converse (8),
		suspend (9),
		resume (10),
		releasing (11)
	    }
	    ACCESS read-only
	    STATUS mandatory
	    DESCRIPTION
	    " State of the endpoint "
	    ::= { accCmNsCallEntry 12 }
	accCmNsCalledNumber OBJECT-TYPE
	    SYNTAX OCTET STRING
	    ACCESS read-only
	    STATUS mandatory
	    DESCRIPTION
	    " Called Number "
	    ::= { accCmNsCallEntry 13 }
	accCmNsCallingNumber OBJECT-TYPE
	    SYNTAX OCTET STRING
	    ACCESS read-only
	    STATUS mandatory
	    DESCRIPTION
	    " Calling Number "
	    ::= { accCmNsCallEntry 14 }
	accCmNsCallDuration OBJECT-TYPE
	    SYNTAX TimeTicks
	    ACCESS read-only
	    STATUS mandatory
	    DESCRIPTION
	    " Call Duration "
	    ::= { accCmNsCallEntry 15 }
-- <accCmSwCall Table Name Here>
	accCmSwCallTable OBJECT-TYPE
	    SYNTAX SEQUENCE OF AccCmSwCallEntry
	    ACCESS not-accessible
	    STATUS mandatory
	    DESCRIPTION
	    "  "
	    ::= { accCmGroup 6 }
	accCmSwCallEntry OBJECT-TYPE
	    SYNTAX AccCmSwCallEntry
	    ACCESS not-accessible
	    STATUS mandatory
	    DESCRIPTION
	    "  "
	    INDEX { accCmSwCallIdent }
	    ::= { accCmSwCallTable 1 }
	AccCmSwCallEntry ::= SEQUENCE {
	    accCmSwCallIdent INTEGER,
	    accCmSwCallSegment INTEGER,
	    accCmSwCallDisposition INTEGER,
	    accCmSwCallType INTEGER,
	    accCmSwServiceProfile OCTET STRING,
	    accCmSwPayloadStatus INTEGER,
	    accCmSwDialInfc INTEGER,
	    accCmSwDialType INTEGER,
	    accCmSwDialState INTEGER,
	    accCmSwEndpointInfc INTEGER,
	    accCmSwEndpointType INTEGER,
	    accCmSwEndpointState INTEGER,
	    accCmSwCalledNumber OCTET STRING,
	    accCmSwCallingNumber OCTET STRING,
	    accCmSwCallDuration TimeTicks
	    }
	accCmSwCallIdent OBJECT-TYPE
	    SYNTAX INTEGER
	    ACCESS read-only
	    STATUS mandatory
	    DESCRIPTION
	    " A unique call identifier for this call "
	    ::= { accCmSwCallEntry 1 }
	accCmSwCallSegment OBJECT-TYPE
	    SYNTAX INTEGER {
		incoming (1),
		outgoing (2),
		permanent (3)
	    }
	    ACCESS read-only
	    STATUS mandatory
	    DESCRIPTION
	    " Type of call segment  "
	    ::= { accCmSwCallEntry 2 }
	accCmSwCallDisposition OBJECT-TYPE
	    SYNTAX INTEGER {
		received (1),
		validated (2),
		authorized (3),
		configured (4),
		rejected (5),
		accepted (6),
		switched (7),
		returned (8),
		disconnected (9),
		released (10),
		permanent (11)
	    }
	    ACCESS read-only
	    STATUS mandatory
	    DESCRIPTION
	    " Call disposition "
	    ::= { accCmSwCallEntry 3 }
	accCmSwCallType OBJECT-TYPE
	    SYNTAX INTEGER {
		cm64 (1),
		cm56 (2),
		udi (3),
		rdi (4),
		speech (8),
		audio3 (16),
		modem (24),
		audio7 (32),
		audio (48),
		wideband (64),
		multirate (128),
		v-110 (256),
		nband (263),
		data (455),
		circuit (134217727),
		packet (134217728)
	    }
	    ACCESS read-only
	    STATUS mandatory
	    DESCRIPTION
	    " Bearer type for the call  "
	    ::= { accCmSwCallEntry 4 }
	accCmSwServiceProfile OBJECT-TYPE
	    SYNTAX OCTET STRING
	    ACCESS read-only
	    STATUS mandatory
	    DESCRIPTION
	    " Service profile used by the call "
	    ::= { accCmSwCallEntry 5 }
	accCmSwPayloadStatus OBJECT-TYPE
	    SYNTAX INTEGER {
		released (1),
		deferred (2),
		establishing (3),
		established (4),
		releasing (5)
	    }
	    ACCESS read-only
	    STATUS mandatory
	    DESCRIPTION
	    " Status of the payload of the call "
	    ::= { accCmSwCallEntry 6 }
	accCmSwDialInfc OBJECT-TYPE
	    SYNTAX INTEGER
	    ACCESS read-only
	    STATUS mandatory
	    DESCRIPTION
	    " Dialing interface used for the call  "
	    ::= { accCmSwCallEntry 7 }
	accCmSwDialType OBJECT-TYPE
	    SYNTAX INTEGER {
		isdn (1),
		pstn (2),
		tunnel (3),
		dl2 (4),
		vna (5),
		ss7 (6),
		none (9)
	    }
	    ACCESS read-only
	    STATUS mandatory
	    DESCRIPTION
	    " Signaling type of the dialing interface "
	    ::= { accCmSwCallEntry 8 }
	accCmSwDialState OBJECT-TYPE
	    SYNTAX INTEGER {
		initiated (1),
		sending (2),
		proceeding (3),
		delivered (4),
		offered (6),
		alerting (7),
		answered (8),
		routing (9),
		connected (10),
		disconn-req (11),
		disconn-ind (12),
		suspend (15),
		resume (17),
		releasing (19),
		receiving (25),
		busy (99)
	    }
	    ACCESS read-only
	    STATUS mandatory
	    DESCRIPTION
	    " Signaling state of the call "
	    ::= { accCmSwCallEntry 9 }
	accCmSwEndpointInfc OBJECT-TYPE
	    SYNTAX INTEGER
	    ACCESS read-only
	    STATUS mandatory
	    DESCRIPTION
	    " Endpoint interface used for the call "
	    ::= { accCmSwCallEntry 10 }
	accCmSwEndpointType OBJECT-TYPE
	    SYNTAX INTEGER {
		hdlc (1),
		modem (2),
		g-711mu (3),
		g-711a (4),
		g-729a (5),
		none (127)
	    }
	    ACCESS read-only
	    STATUS mandatory
	    DESCRIPTION
	    " Type of endpoint used for the call "
	    ::= { accCmSwCallEntry 11 }
	accCmSwEndpointState OBJECT-TYPE
	    SYNTAX INTEGER {
		released (1),
		assigning (2),
		assigned (3),
		setup (4),
		ready (5),
		alerting (6),
		answered (7),
		converse (8),
		suspend (9),
		resume (10),
		releasing (11)
	    }
	    ACCESS read-only
	    STATUS mandatory
	    DESCRIPTION
	    " State of the endpoint "
	    ::= { accCmSwCallEntry 12 }
	accCmSwCalledNumber OBJECT-TYPE
	    SYNTAX OCTET STRING
	    ACCESS read-only
	    STATUS mandatory
	    DESCRIPTION
	    " Called number "
	    ::= { accCmSwCallEntry 13 }
	accCmSwCallingNumber OBJECT-TYPE
	    SYNTAX OCTET STRING
	    ACCESS read-only
	    STATUS mandatory
	    DESCRIPTION
	    " Calling number "
	    ::= { accCmSwCallEntry 14 }
	accCmSwCallDuration OBJECT-TYPE
	    SYNTAX TimeTicks
	    ACCESS read-only
	    STATUS mandatory
	    DESCRIPTION
	    " Call duration "
	    ::= { accCmSwCallEntry 15 }
-- START CFG_TRAP_ENHANCEMENTS
-- Cm Traps Branch Enterprise
      accCmTraps OBJECT IDENTIFIER      ::= { accCmGroup 7 }
        accCmTrapMsg     OBJECT-TYPE
                SYNTAX          DisplayString
                ACCESS          read-only
                STATUS          mandatory
                DESCRIPTION
		" Enterprise Trap Message for Cm"
                ::= { accCmTraps 1 }
-- END CFG_TRAP_ENHANCEMENTS  

        accCmEvntBlockedTrap TRAP-TYPE
                ENTERPRISE   accCmTraps 
                VARIABLES  { accCmTrapMsg,
                             accIfName ,
                              accTrapLogSeqNum}
                DESCRIPTION
                "If the Dial Manager which provides services to the
                 Call Manager is NULL the dial manager event is
                 blocked., and hence the same call manager failure
                 is reported
SEVERITY-DEFAULT: Minor 
EVENTTYPE-DEFAULT: 10 
ADDITIONAL-TEXT-VARIABLES: { accTrapLogSeqNum,accCmTrapMsg }
PCAUSE-DEFAULT: 46 " 
 
                ::= 1
        accStaleCallCntxtTrap TRAP-TYPE
                ENTERPRISE   accCmTraps 
                VARIABLES  { accCmTrapMsg ,
                              accTrapLogSeqNum}
                DESCRIPTION
                "If the call context is stale or the magic number doesn't
                 match this CM Failure trap is generated
SEVERITY-DEFAULT: Minor 
EVENTTYPE-DEFAULT: 10 
ADDITIONAL-TEXT-VARIABLES: { accTrapLogSeqNum,accCmTrapMsg }
PCAUSE-DEFAULT: 46 " 
 
                ::= 2
        accCmUnExpectedEvntTrap TRAP-TYPE
                ENTERPRISE   accCmTraps 
                VARIABLES  { accCmTrapMsg,
                             accIfName ,
                              accTrapLogSeqNum}
                DESCRIPTION
                "If the call context is stale because the magic number
                 doesn't match this CM Failure trap is generated
SEVERITY-DEFAULT: Minor 
EVENTTYPE-DEFAULT: 10 
ADDITIONAL-TEXT-VARIABLES: { accTrapLogSeqNum,accCmTrapMsg }
PCAUSE-DEFAULT: 46 " 
 
                ::= 3
        accCmEmEvntWOCntxtTrap TRAP-TYPE
                ENTERPRISE   accCmTraps 
                VARIABLES  { accCmTrapMsg ,
                              accTrapLogSeqNum}
                DESCRIPTION  
                "If the call context is stale because the magic number
                 doesn't match this CM Failure trap is generated
SEVERITY-DEFAULT: Minor 
EVENTTYPE-DEFAULT: 10 
ADDITIONAL-TEXT-VARIABLES: { accTrapLogSeqNum,accCmTrapMsg }
PCAUSE-DEFAULT: 46 " 
 
                ::= 4
        accCmUnXpctdEmEventTrap TRAP-TYPE
                ENTERPRISE   accCmTraps 
                VARIABLES  { accCmTrapMsg,
                             accIfName ,
                              accTrapLogSeqNum}
                DESCRIPTION
                "Indicates unexpected state machine event in the
                 Call Manger on a particular port name
SEVERITY-DEFAULT: Minor 
EVENTTYPE-DEFAULT: 10 
ADDITIONAL-TEXT-VARIABLES: { accTrapLogSeqNum,accCmTrapMsg }
PCAUSE-DEFAULT: 46 " 
 
                ::= 5
        accCmSwitchingTrap TRAP-TYPE
                ENTERPRISE   accCmTraps 
                VARIABLES  { accCmTrapMsg,
                             accIfName ,
                              accTrapLogSeqNum}
                DESCRIPTION
                " Trap 6
SEVERITY-DEFAULT: Minor 
EVENTTYPE-DEFAULT: 10 
ADDITIONAL-TEXT-VARIABLES: { accTrapLogSeqNum,accCmTrapMsg }
PCAUSE-DEFAULT: 46 " 
 
        ::= 6
        accCmDms1StatusIndTrap TRAP-TYPE
                ENTERPRISE   accCmTraps 
                VARIABLES  { accCmTrapMsg,
                             accIfName ,
                              accTrapLogSeqNum}
                DESCRIPTION
                "DMS1_STATUS_IND in DM state 
SEVERITY-DEFAULT: Minor 
EVENTTYPE-DEFAULT: 10 
ADDITIONAL-TEXT-VARIABLES: { accTrapLogSeqNum,accCmTrapMsg }
PCAUSE-DEFAULT: 46 " 
 
                ::= 7
        accCmSpConflictPhysPortTrap TRAP-TYPE
                ENTERPRISE   accCmTraps 
                VARIABLES  { accCmTrapMsg,
                             accServiceProfileName ,
                              accTrapLogSeqNum}
                DESCRIPTION
                "In the Service Profile  name doesn't match the bound
                 name for the physical port., hence the Call Manager
                 failure trap
SEVERITY-DEFAULT: Warning 
EVENTTYPE-DEFAULT: 10 
ADDITIONAL-TEXT-VARIABLES: { accTrapLogSeqNum,accCmTrapMsg }
PCAUSE-DEFAULT: 7 " 
 
                ::= 8
        accCmSpInconsDynTunnelingTrap TRAP-TYPE
                ENTERPRISE   accCmTraps 
                VARIABLES  { accCmTrapMsg,
                             accIfName ,
                              accTrapLogSeqNum}
                DESCRIPTION
                "Only tunnel ports can be configured dynamically by
                 RADIUS or the VPSM.  Therefore, if a configuration
                 entry exists which is not a tunnel port and the service
                 profile type is not L2TP, it will cause a Call Manager
                 to clear the call, hence the trap
SEVERITY-DEFAULT: Warning 
EVENTTYPE-DEFAULT: 10 
ADDITIONAL-TEXT-VARIABLES: { accTrapLogSeqNum,accCmTrapMsg }
PCAUSE-DEFAULT: 7 " 
 
                ::= 9
        accCmRedundantReqTrap TRAP-TYPE
                ENTERPRISE   accCmTraps 
                VARIABLES  { accCmTrapMsg,
                             accIfName ,
                              accTrapLogSeqNum}
                DESCRIPTION
                "If there is a request to unbind a service profile.,
                 to which already there was request,
                 then this trap of redundant request is generated
SEVERITY-DEFAULT: Warning 
EVENTTYPE-DEFAULT: 10 
ADDITIONAL-TEXT-VARIABLES: { accTrapLogSeqNum,accCmTrapMsg }
PCAUSE-DEFAULT: 7 " 
 
                ::= 10 
        accCmNoMemTunnelTrap TRAP-TYPE
                ENTERPRISE   accCmTraps 
                VARIABLES  { accCmTrapMsg,
                             accIfName ,
                              accTrapLogSeqNum}
                DESCRIPTION
                "Beacuse of shortage in memory if a ALLOc to
                 VPSM parameter fails, this configuration
                 failure is indicated by this trap
SEVERITY-DEFAULT: Major 
EVENTTYPE-DEFAULT: 10 
ADDITIONAL-TEXT-VARIABLES: { accTrapLogSeqNum,accCmTrapMsg }
PCAUSE-DEFAULT: 32 " 
 
                ::= 11
        accCmUnExpctdDmEvntInDmStateTrap TRAP-TYPE
                ENTERPRISE   accCmTraps 
                VARIABLES  { accCmTrapMsg,
                             accIfName ,
                              accTrapLogSeqNum}
                DESCRIPTION
                " 
SEVERITY-DEFAULT: Indeterminate 
EVENTTYPE-DEFAULT: 10 
ADDITIONAL-TEXT-VARIABLES: { accTrapLogSeqNum,accCmTrapMsg }
PCAUSE-DEFAULT: 46 " 
 
                ::= 12
        accCmUnExpctdDmEvntWOCntxtTrap TRAP-TYPE
                ENTERPRISE   accCmTraps 
                VARIABLES  { accCmTrapMsg,
                             accIfName ,
                              accTrapLogSeqNum}
                DESCRIPTION
                " 
SEVERITY-DEFAULT: Indeterminate 
EVENTTYPE-DEFAULT: 10 
ADDITIONAL-TEXT-VARIABLES: { accTrapLogSeqNum,accCmTrapMsg }
PCAUSE-DEFAULT: 46 " 
 
                ::= 13
        accCmPayldPathTrap TRAP-TYPE
                ENTERPRISE   accCmTraps 
                VARIABLES  { accCmTrapMsg,
                             accIfName ,
                              accTrapLogSeqNum}
                DESCRIPTION
                " 
SEVERITY-DEFAULT: Indeterminate 
EVENTTYPE-DEFAULT: 10 
ADDITIONAL-TEXT-VARIABLES: { accTrapLogSeqNum,accCmTrapMsg }
PCAUSE-DEFAULT: 46 " 
 
                ::= 14
        accCmUnXpctedRelatedEvntTrap TRAP-TYPE
                ENTERPRISE   accCmTraps 
                VARIABLES  { accCmTrapMsg,
                             accIfName ,
                              accTrapLogSeqNum}
                DESCRIPTION
                " 
SEVERITY-DEFAULT: Indeterminate 
EVENTTYPE-DEFAULT: 10 
ADDITIONAL-TEXT-VARIABLES: { accTrapLogSeqNum,accCmTrapMsg }
PCAUSE-DEFAULT: 46 " 
 
                ::= 15
        accCmNoPayLdPathTrap TRAP-TYPE
                ENTERPRISE   accCmTraps 
                VARIABLES  { accCmTrapMsg,
                             accIfName ,
                              accTrapLogSeqNum}
                DESCRIPTION
                "No Payload path 
SEVERITY-DEFAULT: Warning 
EVENTTYPE-DEFAULT: 10 
ADDITIONAL-TEXT-VARIABLES: { accTrapLogSeqNum,accCmTrapMsg }
PCAUSE-DEFAULT: 7 " 
 
                ::= 16
        accCmForcdCallRlsStalldTrap TRAP-TYPE
                ENTERPRISE   accCmTraps 
                VARIABLES  { accCmTrapMsg,
                             accIfName ,
                              accTrapLogSeqNum}
                DESCRIPTION
                "Forced call release stalled, clean-up initiated 
SEVERITY-DEFAULT: Warning 
EVENTTYPE-DEFAULT: 10 
ADDITIONAL-TEXT-VARIABLES: { accTrapLogSeqNum,accCmTrapMsg }
PCAUSE-DEFAULT: 7 " 
 
                ::= 17
        accCmGrmdCallTypeInvalidTrap TRAP-TYPE
                ENTERPRISE   accCmTraps 
                VARIABLES  { accCmTrapMsg,
                             accIfName ,
                              accTrapLogSeqNum}
                DESCRIPTION
                "Groomed call type is invalid
SEVERITY-DEFAULT: Warning 
EVENTTYPE-DEFAULT: 10 
ADDITIONAL-TEXT-VARIABLES: { accTrapLogSeqNum,accCmTrapMsg }
PCAUSE-DEFAULT: 7 " 
 
                ::= 18
        accCmGrmdCallTypeAbmigsTrap TRAP-TYPE
                ENTERPRISE   accCmTraps 
                VARIABLES  { accCmTrapMsg,
                             accIfName ,
                              accTrapLogSeqNum}
                DESCRIPTION
                "Groomed call type is ambiguous
SEVERITY-DEFAULT: Warning 
EVENTTYPE-DEFAULT: 10 
ADDITIONAL-TEXT-VARIABLES: { accTrapLogSeqNum,accCmTrapMsg }
PCAUSE-DEFAULT: 7 " 
 
                ::= 19
END
