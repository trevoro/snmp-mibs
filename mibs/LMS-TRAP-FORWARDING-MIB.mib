LMS-TRAP-FORWARDING-MIB DEFINITIONS ::= BEGIN

   IMPORTS
	TRAP-TYPE FROM RFC-1215
       enterprises, Counter, Gauge,
       TimeTicks, NetworkAddress
 FROM RFC1155-SMI
OBJECT-TYPE FROM RFC-1212
       DisplayString
 FROM RFC1213-MIB;
 
-- OBJECT IDENTIFIERS
   lotus         OBJECT IDENTIFIER ::= { enterprises 334 }
   notes        OBJECT IDENTIFIER ::= { lotus 1 }
   lcs          OBJECT IDENTIFIER ::= { lotus 2 }
   softswitch OBJECT IDENTIFIER ::= { lotus 3 }
   common-mibs OBJECT IDENTIFIER ::= { softswitch 1 }
   lms  OBJECT IDENTIFIER ::= { softswitch 2 }
   lmsTrapData  OBJECT IDENTIFIER ::= { lms 3 } 
   -- comment this out if using the MODULE-IDENTITY macro
   lmsTrap  OBJECT IDENTIFIER ::= { lms 2 }   

  

TimeInterval ::= INTEGER (0..2147483647)


-- MODULE IDENTIFICATION   use in V2 version only

--lmsTrap MODULE-IDENTITY
--       LAST-UPDATED "9511280000Z"
--       ORGANIZATION "Lotus Development Corporation"
--       CONTACT-INFO
--         " Bruce Ernst
--            Postal:  Lotus Development Corporation
--                   640 Lee Road , Suite 200
--     Chesterbrook Corporate Center
--                   Wayne, PA  19087
--                   US
--
--            Tel: +1 610 251 3404
--            Fax: +1 610 251 3550
--            E-Mail: bge@softsw.ssw.com"
--       DESCRIPTION
--         "The MIB module describing LMS traps and trap forwarding controls
--   Version 1 - first cut - outline only. 8/30/95
--   Version 1.1 - minor updates and typo corrections 9/6/95
--   Version 1.2 - Added traps for each severity of LMS event
--  "
--       ::= {  lms 2 }

-- TRAP CONTROL/ADMINISTRATION VARIABLES:

eventFwdTableModificationStatus OBJECT-TYPE
 SYNTAX     INTEGER {
   unknown(1),
   no-access(2),
   read-only(3),
   read-modify(4),
   read-create(5)
   }
 ACCESS    read-only
 STATUS     mandatory
 DESCRIPTION
   "Indicates the combination of possible functions allowed on the 
lmsEventFwdTable
    table, subject to overriding SNMP security attributes and the ACCESS clause
    restrictions on the objects themselves.  The values are:
     unknown  -  Managers privileges are unknown.
  no-access -  Managers may neither read nor write to this table.
  read-only -  Managers may only read the table, they cannot add
       or delete conceptual rows and cannot change the value
       of any variable, even those with ACCESS of 'read-write'.
  read-modify -  Managers may read the table, and change the value
       of variables whose ACCESS is 'read-write'.
  read-create -  Managers may read the table, change the value of
       variables whose ACCESS is 'read-write', and create
       or delete conceptual rows in the table."
 ::= { lmsTrap 1 }

nextFwdEntryIndex  OBJECT-TYPE
 SYNTAX     INTEGER
 ACCESS    read-only
 STATUS     mandatory
 DESCRIPTION
   "The index that may be used by a manager on a 'set-request' PDU to create
     a new conceptual row in the lmsEventFwdTable table."
 ::= { lmsTrap 2 }

trapWindowTime  OBJECT-TYPE
 SYNTAX     TimeInterval
 ACCESS    read-write
 STATUS     mandatory
 DESCRIPTION
   "A control time window, expresses in 1/100ths of a second, used in 
conjunction 
    with the maxTrapsPerWindow variable to prevent a 'trap storm' caused by a
    rapidly recurring error condition ."
 ::= { lmsTrap 3 }

maxTrapsPerWindow  OBJECT-TYPE
 SYNTAX     INTEGER
 ACCESS    read-write
 STATUS     mandatory
 DESCRIPTION
   "The maximum number of traps to be forwarded in the time interval expressed 
in the
     trapWindowTime variable. Used to prevent a 'trap storm' caused by a rapidly
     recurring error condition."
 ::= { lmsTrap 4 }

numDroppedMaxPerWindowTraps  OBJECT-TYPE
 SYNTAX     Counter
 ACCESS    read-only
 STATUS     mandatory
 DESCRIPTION
   "The number of traps intended for this destination, which were not forwarded 
due
     to the maxTrapsPerWindow count being met or exceeded."
 ::= { lmsTrap 5 }

lmsEventFwdTable OBJECT-TYPE
 SYNTAX SEQUENCE OF LMSEventFwdEntry
 ACCESS not-accessible
 STATUS     mandatory
 DESCRIPTION
   "The table holding information to control/administer
   forwarding of LMS events to SNMP-based management
   stations or applications."
 ::= { lmsTrap 6 }

lmsEventFwdEntry OBJECT-TYPE
 SYNTAX     LMSEventFwdEntry
 ACCESS     not-accessible
 STATUS      mandatory
 DESCRIPTION
   "The entry associated with each destination to which 
   LMS events should be forwarded as SNMP traps."
 INDEX {fwdEntryIndex}
 ::= {lmsEventFwdTable 1}

LMSEventFwdEntry ::= SEQUENCE {
 fwdEntryIndex
     INTEGER,
 rowStatus
     INTEGER,
 destinationNetAddr
     NetworkAddress,
 destinationCommunity
     DisplayString,
 destinationPort
     INTEGER,
 forwardingEnabled
     INTEGER,
 forwardingFilterName
     DisplayString,
 lastTrapSequenceNumber
     INTEGER,
 lastTrapTime
     TimeTicks,
 numDroppedDisabledTraps
     Counter
    }


fwdEntryIndex  OBJECT-TYPE
 SYNTAX     INTEGER
 ACCESS    read-only
 STATUS     mandatory
 DESCRIPTION
   "The integer index into the lmsEventFwdTable table."
 ::= { lmsEventFwdEntry 1 }

rowStatus  OBJECT-TYPE
 SYNTAX     INTEGER {
   active(1),
   notInService(2),
   notReady(3),
   createAndGo(4),
   createAndWait(5),
   destroy(6)
        }
 ACCESS    read-write
 STATUS     mandatory
 DESCRIPTION
   "The status of the conceptual row. These are mapped to the same values as the
     RowStatus textual conversion in SNMPv2 and carry the same semantics."
 ::= { lmsEventFwdEntry 2 }

destinationNetAddr  OBJECT-TYPE
 SYNTAX     NetworkAddress
 ACCESS    read-write
 STATUS     mandatory
 DESCRIPTION
   "The network address of the destination entity for trap forwarding."
 ::= { lmsEventFwdEntry 3 }

destinationCommunity  OBJECT-TYPE
 SYNTAX     DisplayString
 ACCESS     read-write
 STATUS     mandatory
 DESCRIPTION
   "The community name to be used when sending traps to the destination entity. 
This
    variable is non-defined in SNMPv2 implementions."
 ::= { lmsEventFwdEntry 4 }

destinationPort  OBJECT-TYPE
 SYNTAX     INTEGER
 ACCESS    read-write
 STATUS     mandatory
 DESCRIPTION
   "The UDP port at the 'destinationNetAddr' to which the trap should be sent."
 ::= { lmsEventFwdEntry 5 }

forwardingEnabled  OBJECT-TYPE
 SYNTAX     INTEGER {
   enabled(1),
   disabled(2)
   }
 ACCESS    read-write
 STATUS     mandatory
 DESCRIPTION
   "Indicates whether forwarding is enabled for this destination at the present 
time.
    Used to temporarily suspend forwarding."
 ::= { lmsEventFwdEntry 6 }

forwardingFilterName  OBJECT-TYPE
 SYNTAX     DisplayString
 ACCESS    read-write
 STATUS     mandatory
 DESCRIPTION
   "Undefined at the present time - bge."
 ::= { lmsEventFwdEntry 7 }

lastTrapSequenceNumber  OBJECT-TYPE
 SYNTAX     INTEGER
 ACCESS    read-only
 STATUS     mandatory
 DESCRIPTION
   "The sequence number of the last trap sent to this destination.  All traps 
sent to
     a given destination are sequenced via a 32-bit, wrapping counter. A 
manager may
     use this variable to determine if any traps for this destination have been 
'lost'."
 ::= { lmsEventFwdEntry 8 }

lastTrapTime  OBJECT-TYPE
 SYNTAX     TimeTicks
 ACCESS    read-only
 STATUS     mandatory
 DESCRIPTION
   "The value of sysUpTime as included in the last trap sent to this 
destination."
 ::= { lmsEventFwdEntry 9 }

numDroppedDisabledTraps  OBJECT-TYPE
 SYNTAX     Counter
 ACCESS    read-only
 STATUS     mandatory
 DESCRIPTION
   "The number of traps intended for this destination, which were not forwarded 
due
    to the variable forwardingEnabled begin set to disabled(2)."
 ::= { lmsEventFwdEntry 10 }



-- MOST RECENT TRAP VARIABLES:

lmsEvComponentType OBJECT-TYPE
 SYNTAX     INTEGER {
   global(1),
   switch(2),
   core(3),
   mta(4),
   mta-group(5),
   queue(6),
   mea(7),
   other(8)
   }
 ACCESS    not-accessible
 STATUS     mandatory
 DESCRIPTION
   "Identifies the type of LMS component issuing the event."
 ::= { lmsTrapData 1 }

lmsEvComponentDN OBJECT-TYPE
 SYNTAX     DisplayString
 ACCESS    not-accessible
 STATUS     mandatory
 DESCRIPTION
   "Identifies the most unique (rightmost) portion of the Spyder Distinguished
    Name of the component issuing the event.  The combination of  
lmsEvComponentType
    and lmsEvComponentDN MUST uniquely identify the issuing component."
 ::= { lmsTrapData 2 }

lmsEvDbId OBJECT-TYPE
 SYNTAX     INTEGER
 ACCESS    not-accessible
 STATUS     mandatory
 DESCRIPTION
   "Identifies the unique key used to identify this event in the LMS event 
database."
 ::= { lmsTrapData 3 }

lmsEvOID OBJECT-TYPE
 SYNTAX     INTEGER
 ACCESS    not-accessible
 STATUS     mandatory
 DESCRIPTION
   "Identifies the specific LMS event OID conatined in the LMS event."
 ::= { lmsTrapData 4 }

numLmsEvSequences OBJECT-TYPE
 SYNTAX     Counter
 ACCESS    not-accessible
 STATUS     mandatory
 DESCRIPTION
   "A monotonically increasing, wrapping counter indication the sequence number
    of this event, relative to the destination of the trap.  Events that are 
not forwarded
    to a destination (destination temporarily disabled, windowTime exceeded) do 
not
    cause this sequence number to increase."
 ::= { lmsTrapData 5 }

lmsEvSeverity OBJECT-TYPE
 SYNTAX     INTEGER
 ACCESS    not-accessible
 STATUS     mandatory
 DESCRIPTION
   "The original severity assigned to the LMS event."
 ::= { lmsTrapData 6 }

lmsEvSupportingText OBJECT-TYPE
 SYNTAX     DisplayString
 ACCESS    not-accessible
 STATUS     mandatory
 DESCRIPTION
   "Textual information supporting the event data.  The meaning of the brief 
text must 
    be obvious in the context of the trap - for the sake of brevity it need not 
be a
    gramatically correct sentence."
 ::= { lmsTrapData 7 }



-- TRAPS
-- This part of the MIB module defines the traps that the LMS event forwarding
-- sub-agent may issue.

lmsCritical TRAP-TYPE
  ENTERPRISE lms
  VARIABLES  { lmsEvComponentType,  lmsEvComponentDN,  lmsEvDbId,
           lmsEvOID, numLmsEvSequences, lmsEvSeverity,
           lmsEvSupportingText }
  DESCRIPTION
   "A critical alarm forwarded from the LMS event subsystem."
  ::= 1

lmsMajor  TRAP-TYPE
  ENTERPRISE lms
  VARIABLES  { lmsEvComponentType,  lmsEvComponentDN,  lmsEvDbId,
           lmsEvOID, numLmsEvSequences, lmsEvSeverity,
           lmsEvSupportingText }
  DESCRIPTION
   "A major alarm forwarded from the LMS event subsystem."
  ::= 2

lmsMinor  TRAP-TYPE
  ENTERPRISE lms
  VARIABLES  { lmsEvComponentType,  lmsEvComponentDN,  lmsEvDbId,
           lmsEvOID, numLmsEvSequences, lmsEvSeverity,
           lmsEvSupportingText }
  DESCRIPTION
   "A minor alarm forwarded from the LMS event subsystem."
  ::= 3

lmsWarning TRAP-TYPE
  ENTERPRISE lms
  VARIABLES  { lmsEvComponentType,  lmsEvComponentDN,  lmsEvDbId,
           lmsEvOID, numLmsEvSequences, lmsEvSeverity,
           lmsEvSupportingText }
  DESCRIPTION
   "A warning or indeterminate forwarded from the LMS event subsystem."
  ::= 4

lmsCleared TRAP-TYPE
  ENTERPRISE lms
  VARIABLES  { lmsEvComponentType,  lmsEvComponentDN,  lmsEvDbId,
           lmsEvOID, numLmsEvSequences, lmsEvSeverity,
           lmsEvSupportingText }
  DESCRIPTION
   "A cleared forwarded from the LMS event subsystem."
  ::= 5

lmsInformational TRAP-TYPE
  ENTERPRISE lms
  VARIABLES  { lmsEvComponentType,  lmsEvComponentDN,  lmsEvDbId,
           lmsEvOID, numLmsEvSequences, lmsEvSeverity,
           lmsEvSupportingText }
  DESCRIPTION
   "An informational event forwarded from the LMS event subsystem."
  ::= 6

-- CONFORMANCE INFORMATION
 -- Used ONLY in V2 MIBs
-- COMPLIANCE STATEMENTS
 -- Used ONLY in V2 MIBs
-- UNITS OF CONFORMANCE
 -- Used ONLY in V2 MIBs


END
