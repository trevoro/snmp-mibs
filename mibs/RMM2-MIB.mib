RMM2-MIB DEFINITIONS ::= BEGIN

IMPORTS
	MODULE-IDENTITY,OBJECT-TYPE,enterprises		FROM SNMPv2-SMI
	IpAddress, Integer32, NOTIFICATION-TYPE			FROM SNMPv2-SMI
	DisplayString,DateAndTime,MacAddress  		FROM SNMPv2-TC
	MODULE-COMPLIANCE, OBJECT-GROUP 	        FROM SNMPv2-CONF;

intelRmm2 MODULE-IDENTITY
    LAST-UPDATED "200612130000Z"
    ORGANIZATION "Intel Corporation"
    CONTACT-INFO "
                  Intel Corporation
                 "
    DESCRIPTION  "This mib describes the SNMP functions of the
		  KVM by Intel Corporation."
		::= { enterprises 343 }

rmm2		OBJECT IDENTIFIER ::= { intelRmm2 1 }

board		OBJECT IDENTIFIER ::= { rmm2 1 }
host		OBJECT IDENTIFIER ::= { rmm2 2 }
common		OBJECT IDENTIFIER ::= { rmm2 3 }
traps		OBJECT IDENTIFIER ::= { rmm2 4 }

info		OBJECT IDENTIFIER ::= { board 1 }
users		OBJECT IDENTIFIER ::= { board 2 }
actions		OBJECT IDENTIFIER ::= { board 3 }

hostInfo	OBJECT IDENTIFIER ::= { host 1 }
hostActions	OBJECT IDENTIFIER ::= { host 2 }

firmwareVersion	OBJECT-TYPE
			SYNTAX		DisplayString
			MAX-ACCESS	read-only
			STATUS		current
			DESCRIPTION
				"The current firmware version"
		::= { info 1 }

serialNumber	OBJECT-TYPE
			SYNTAX		DisplayString
			MAX-ACCESS	read-only
			STATUS		current
			DESCRIPTION
				"The serial number."
		::= { info 2 }

ip		OBJECT-TYPE
			SYNTAX		IpAddress
			MAX-ACCESS	read-only
			STATUS		current
			DESCRIPTION
				"The current IP address. A value of 0.0.0.0 indicates an error
				or an unset option."
		::= { info 3 }

netmask		OBJECT-TYPE
			SYNTAX		IpAddress
			MAX-ACCESS	read-only
			STATUS		current
			DESCRIPTION
				"The current Netmask. A value of 0.0.0.0 indicates an error
				or an unset option."

		::= { info 4 }

gateway		OBJECT-TYPE
			SYNTAX		IpAddress
			MAX-ACCESS	read-only
			STATUS		current
			DESCRIPTION
				"The current Gateway. A value of 0.0.0.0 indicates an error
				or an unset option."
		::= { info 5 }

mac		OBJECT-TYPE
			SYNTAX		MacAddress
			MAX-ACCESS	read-only
			STATUS		current
		DESCRIPTION
				"The current MAC address."
		::= { info 6 }

hardwareRev	OBJECT-TYPE
			SYNTAX		Integer32(0..255)
			MAX-ACCESS	read-only
			STATUS		current
			DESCRIPTION
				"The hardware revision number."
		::= { info 7 }

eventType       OBJECT-TYPE
                        SYNTAX		DisplayString
			MAX-ACCESS	not-accessible
			STATUS		current
			DESCRIPTION
				"The name of a generic log event"
		::= { info 8 }
		
eventDesc       OBJECT-TYPE
                        SYNTAX		DisplayString
			MAX-ACCESS	not-accessible
			STATUS		current
			DESCRIPTION
				"The description text of a generic log event"
		::= { info 9 }

userLoginName	OBJECT-TYPE
			SYNTAX		DisplayString
			MAX-ACCESS	not-accessible
			STATUS		current
			DESCRIPTION
				"The login of a user."
		::= { info 10 }

remoteHost	OBJECT-TYPE
			SYNTAX		IpAddress
			MAX-ACCESS	not-accessible
			STATUS		current
			DESCRIPTION
				"The IP of the remote host from which a user is logged in."
		::= { info 11 }

checkHostPower	OBJECT-TYPE
			SYNTAX		INTEGER {
						hasPower(1),
						hasnoPower(2),
						error(3),
						notsupported(4)
					}
			MAX-ACCESS	read-only
			STATUS		current
			DESCRIPTION
				"The Power status of the host."
		::= { hostInfo 1 }

hostReset	OBJECT-TYPE
			SYNTAX		INTEGER {
						reset(1)
					}
			MAX-ACCESS	read-write
			STATUS		current
			DESCRIPTION
				"This virtually presses the Reset button of the host."
			::= { hostActions 1 }

hostPower	OBJECT-TYPE
			SYNTAX		INTEGER {
						longPress(1)
					}
			MAX-ACCESS	read-write
			STATUS		current
			DESCRIPTION
				"This virtually presses the Power button of the host
				with a short or long press."
			::= { hostActions 2 }

resetBoard	OBJECT-TYPE
			SYNTAX		INTEGER {
						reset(1)
					}
			MAX-ACCESS	read-write
			STATUS		current
			DESCRIPTION
				"Resets the board."
			::= { actions 1 }

dummyTrap NOTIFICATION-TYPE
	STATUS current
	DESCRIPTION
		"Dummy Trap for testing"
	::= { traps 1 }

loginfailed NOTIFICATION-TYPE
	OBJECTS { userLoginName, remoteHost }
        STATUS current
        DESCRIPTION
		"Failed login try."
        ::= { traps 2 }

loginsuccess NOTIFICATION-TYPE
	OBJECTS { userLoginName, remoteHost }
	STATUS current
	DESCRIPTION
		"Success login."
	::= { traps 3 }

securityViolation NOTIFICATION-TYPE
	OBJECTS { userLoginName, remoteHost }
	STATUS current
	DESCRIPTION
		"Security violation."
	::= { traps 4 }

generic NOTIFICATION-TYPE	
        OBJECTS { eventType, eventDesc }	
        STATUS current
	DESCRIPTION
		"This trap is used for any other notification message."
	::= { traps 5 }

logout NOTIFICATION-TYPE
	OBJECTS { userLoginName, remoteHost }
	STATUS current
	DESCRIPTION
		"User logout."
	::= { traps 6 }

END
