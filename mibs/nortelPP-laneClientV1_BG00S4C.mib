Nortel-Magellan-Passport-LaneClientMIB
DEFINITIONS ::= BEGIN



IMPORTS

      OBJECT-TYPE
   FROM RFC-1212

      components,
      passportMIBs
   FROM Nortel-Magellan-Passport-UsefulDefinitionsMIB

      Counter32,
      RowPointer,
      DisplayString,
      StorageType,
      RowStatus,
      InterfaceIndex,
      Integer32,
      MacAddress,
      Unsigned32
   FROM Nortel-Magellan-Passport-StandardTextualConventionsMIB

      AsciiString,
      DashedHexString,
      NonReplicated,
      HexString,
      Link
   FROM Nortel-Magellan-Passport-TextualConventionsMIB;




-- LAST-UPDATED   "9808030000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     LaneClient Enterprise MIB."

laneClientMIB OBJECT IDENTIFIER ::= { passportMIBs 71 }










-- LanEmulationClient/n
-- This component represents a LAN Emulation Client (LEC) as 
-- specified in the ATM Forum LAN Emulation over ATM 
-- Specification (LANE). The LEC provides a MAC level emulated 
-- Ethernet service to higher layer protocols using ATM VCCs.
-- 
-- The 'laneClient' feature must be provisioned on all ILS and ATM 
-- cards.

lec OBJECT IDENTIFIER ::= { components 124 }



lecRowStatusTable OBJECT-TYPE
   SYNTAX     SEQUENCE OF LecRowStatusEntry
   ACCESS     not-accessible
   STATUS     mandatory
   DESCRIPTION
     "This entry controls the addition and deletion of 
      lec components."
::= { lec 1 }

lecRowStatusEntry OBJECT-TYPE
   SYNTAX     LecRowStatusEntry
   ACCESS     not-accessible
   STATUS     mandatory
   DESCRIPTION
     "A single entry in the table represents a single 
      lec component."
   INDEX {
      lecIndex }
::= { lecRowStatusTable 1 }

LecRowStatusEntry ::= SEQUENCE {
   lecRowStatus
      RowStatus,
   lecComponentName
      DisplayString,
   lecStorageType
      StorageType,
   lecIndex
      Integer32 }

lecRowStatus OBJECT-TYPE
   SYNTAX     RowStatus 
   ACCESS     read-write
   STATUS     mandatory
   DESCRIPTION
     "This variable is used as the basis for SNMP naming of
      lec components.
      These components can be added and deleted."
::= { lecRowStatusEntry 1 }

lecComponentName OBJECT-TYPE
   SYNTAX     DisplayString 
   ACCESS     read-only
   STATUS     mandatory
   DESCRIPTION
     "This variable provides the component's string name for
      use with the ASCII Console Interface"
::= { lecRowStatusEntry 2 }

lecStorageType OBJECT-TYPE
   SYNTAX     StorageType 
   ACCESS     read-only
   STATUS     mandatory
   DESCRIPTION
     "This variable represents the storage type value for the
      lec tables."
::= { lecRowStatusEntry 4 }

lecIndex OBJECT-TYPE
   SYNTAX     Integer32 (0..31)
   ACCESS     not-accessible
   STATUS     mandatory
   DESCRIPTION
     "This variable represents the index for the lec tables."
::= { lecRowStatusEntry 10 }

lecCidDataTable OBJECT-TYPE
   SYNTAX     SEQUENCE OF LecCidDataEntry
   ACCESS     not-accessible
   STATUS     mandatory
   DESCRIPTION
     "This group contains the attribute for a component's Customer 
      Identifier (CID). Refer to the attribute description for a detailed 
      explanation of CIDs."
::= { lec 10 }

lecCidDataEntry OBJECT-TYPE
   SYNTAX     LecCidDataEntry
   ACCESS     not-accessible
   STATUS     mandatory
   DESCRIPTION
     "An entry in the lecCidDataTable."
   INDEX {
      lecIndex }
::= { lecCidDataTable 1 }

LecCidDataEntry ::= SEQUENCE {
   lecCustomerIdentifier
      Unsigned32 }

lecCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { lecCidDataEntry 1 }

lecIfEntryTable OBJECT-TYPE
   SYNTAX     SEQUENCE OF LecIfEntryEntry
   ACCESS     not-accessible
   STATUS     mandatory
   DESCRIPTION
     "This group contains the provisionable attributes for the ifEntry."
::= { lec 11 }

lecIfEntryEntry OBJECT-TYPE
   SYNTAX     LecIfEntryEntry
   ACCESS     not-accessible
   STATUS     mandatory
   DESCRIPTION
     "An entry in the lecIfEntryTable."
   INDEX {
      lecIndex }
::= { lecIfEntryTable 1 }

LecIfEntryEntry ::= SEQUENCE {
   lecIfAdminStatus
      INTEGER,
   lecIfIndex
      InterfaceIndex }

lecIfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { lecIfEntryEntry 1 }

lecIfIndex OBJECT-TYPE
   SYNTAX     InterfaceIndex (1..65535)
   ACCESS     read-only
   STATUS     mandatory
   DESCRIPTION
     "This is the index for the IfEntry. Its value is automatically initialized 
      during the provisioning process."
::= { lecIfEntryEntry 2 }

lecMpTable OBJECT-TYPE
   SYNTAX     SEQUENCE OF LecMpEntry
   ACCESS     not-accessible
   STATUS     mandatory
   DESCRIPTION
     "This group contains the base provisioning data for the Media 
      Application component."
::= { lec 12 }

lecMpEntry OBJECT-TYPE
   SYNTAX     LecMpEntry
   ACCESS     not-accessible
   STATUS     mandatory
   DESCRIPTION
     "An entry in the lecMpTable."
   INDEX {
      lecIndex }
::= { lecMpTable 1 }

LecMpEntry ::= SEQUENCE {
   lecLinkToProtocolPort
      Link }

lecLinkToProtocolPort OBJECT-TYPE
   SYNTAX     Link 
   ACCESS     read-write
   STATUS     mandatory
   DESCRIPTION
     "This attribute contains a protocol port component name. The attribute 
      associates the application with a protocol port."
::= { lecMpEntry 1 }

lecProvTable OBJECT-TYPE
   SYNTAX     SEQUENCE OF LecProvEntry
   ACCESS     not-accessible
   STATUS     mandatory
   DESCRIPTION
     "This group contains the provisionable attributes for the 
      LanEmulationClient component."
::= { lec 13 }

lecProvEntry OBJECT-TYPE
   SYNTAX     LecProvEntry
   ACCESS     not-accessible
   STATUS     mandatory
   DESCRIPTION
     "An entry in the lecProvTable."
   INDEX {
      lecIndex }
::= { lecProvTable 1 }

LecProvEntry ::= SEQUENCE {
   lecLanType
      INTEGER,
   lecMaxFrameSize
      INTEGER,
   lecLanName
      AsciiString,
   lecV2Capable
      INTEGER,
   lecLecsAddress
      HexString,
   lecLesAddress
      HexString,
   lecMaxDataSvcs
      Unsigned32,
   lecMaxArpEntries
      Unsigned32,
   lecIlsForwarder
      Link }

lecLanType OBJECT-TYPE
   SYNTAX     INTEGER  {
                 unspecified(1),
                 ethernet(2) }
   ACCESS     read-write
   STATUS     mandatory
   DESCRIPTION
     "This attribute specifies the data frame format for this LEC. Auto-
      configuring LECs use this attribute in their Configure requests. 
      Manually-configured LECs use it in their Join requests. A value of 
      unspecified implies that the data frame format is obtained from the 
      LECS or LES.
      The value of this attribute may be overridden by the LECS or LES; 
      actualLanType contains the actual value."
   DEFVAL     { unspecified }
::= { lecProvEntry 1 }

lecMaxFrameSize OBJECT-TYPE
   SYNTAX     INTEGER  {
                 unspecified(0),
                 n1516(1516),
                 n1580(1580),
                 n4544(4544),
                 n9234(9234),
                 n18190(18190) }
   ACCESS     read-write
   STATUS     mandatory
   DESCRIPTION
     "This attribute specifies the maximum data frame size for this LEC. 
      Auto-configuring LECs use this attribute in their Configure 
      requests. Manually-configured LECs use it in their Join requests. A 
      value of unspecified may only be used for auto-configuring LECs.  
      A value of 1580 may only be specified for a LEC that has the 
      v2Capable attribute set to yes."
   DEFVAL     { unspecified }
::= { lecProvEntry 2 }

lecLanName OBJECT-TYPE
   SYNTAX     AsciiString (SIZE (0..32))
   ACCESS     read-write
   STATUS     mandatory
   DESCRIPTION
     "This attribute specifies the ELAN name for this LEC. Auto-
      configuring LECs use this attribute in their Configure requests. 
      Manually-configured LECs use it in their Join requests. An empty 
      string means unspecified.
      The value of this attribute may be overridden by the LECS or LES; 
      actualLanName contains the actual value."
::= { lecProvEntry 3 }

lecV2Capable OBJECT-TYPE
   SYNTAX     INTEGER  {
                 yes(1),
                 no(2) }
   ACCESS     read-write
   STATUS     mandatory
   DESCRIPTION
     "This attribute specifies whether this LEC exhibits LANE v2 
      behavior where it differs in its requirements from LANE v1 
      behavior."
   DEFVAL     { yes }
::= { lecProvEntry 4 }

lecLecsAddress OBJECT-TYPE
   SYNTAX     HexString (SIZE (0..20))
   ACCESS     read-write
   STATUS     mandatory
   DESCRIPTION
     "This attribute specifies the ATM address of the LECS. If this 
      attribute is non-null, the LEC attempts to set up a Configuration 
      Direct SVC to this address as the first step in the LECS Connect 
      phase. Otherwise, the well known LECS ATM address is used.
      Only one of the attributes lecsAddress and lesAddress can be 
      specified at one time."
::= { lecProvEntry 5 }

lecLesAddress OBJECT-TYPE
   SYNTAX     HexString (SIZE (0..20))
   ACCESS     read-write
   STATUS     mandatory
   DESCRIPTION
     "This attribute specifies the ATM address of the LES. The LEC uses 
      this address to connect directly to the LES, thus bypassing the 
      LECS. A LEC which did not use the LECS is deemed to be 
      manually-configured.
      Only one of the attributes lecsAddress and lesAddress can be 
      specified at one time."
::= { lecProvEntry 6 }

lecMaxDataSvcs OBJECT-TYPE
   SYNTAX     Unsigned32 (16..1018)
   ACCESS     read-write
   STATUS     mandatory
   DESCRIPTION
     "This attribute specifies the maximum number of Data Direct SVCs 
      which this LEC can have active at any one time. When operating at 
      the maximum, an SVC setup request releases the oldest 10% of the 
      Data Direct SVCs of this LEC.
      A SET alarm is issued when currDataSvcs rises above 95% of this 
      value and is CLEAR-ed when it falls below 85%.
      Set maxDataSvcs as low as acceptable since a fixed amount of 
      memory is consumed proportional to this value on every LP with 
      this feature present."
   DEFVAL     { 16 }
::= { lecProvEntry 7 }

lecMaxArpEntries OBJECT-TYPE
   SYNTAX     Unsigned32 (32..10240)
   ACCESS     read-write
   STATUS     mandatory
   DESCRIPTION
     "This attribute specifies the maximum number of entries which this 
      LEC can have in its LE_ARP table at any one time. When operating 
      at the maximum, if an additional entry must be installed, up to 10% 
      of the oldest entries are removed.
      A SET alarm is issued when currArpEntries rises above 95% of this 
      value and is CLEAR-ed when it falls below 85%."
   DEFVAL     { 5120 }
::= { lecProvEntry 8 }

lecIlsForwarder OBJECT-TYPE
   SYNTAX     Link 
   ACCESS     read-write
   STATUS     mandatory
   DESCRIPTION
     "This attribute specifies the IlsForwarder that this LEC is using."
::= { lecProvEntry 9 }

lecStateTable OBJECT-TYPE
   SYNTAX     SEQUENCE OF LecStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { lec 15 }

lecStateEntry OBJECT-TYPE
   SYNTAX     LecStateEntry
   ACCESS     not-accessible
   STATUS     mandatory
   DESCRIPTION
     "An entry in the lecStateTable."
   INDEX {
      lecIndex }
::= { lecStateTable 1 }

LecStateEntry ::= SEQUENCE {
   lecAdminState
      INTEGER,
   lecOperationalState
      INTEGER,
   lecUsageState
      INTEGER }

lecAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { lecStateEntry 1 }

lecOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { lecStateEntry 2 }

lecUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { lecStateEntry 3 }

lecOperStatusTable OBJECT-TYPE
   SYNTAX     SEQUENCE OF LecOperStatusEntry
   ACCESS     not-accessible
   STATUS     mandatory
   DESCRIPTION
     "This group includes the Operational Status attribute. This attribute 
      defines the current operational state of this component."
::= { lec 16 }

lecOperStatusEntry OBJECT-TYPE
   SYNTAX     LecOperStatusEntry
   ACCESS     not-accessible
   STATUS     mandatory
   DESCRIPTION
     "An entry in the lecOperStatusTable."
   INDEX {
      lecIndex }
::= { lecOperStatusTable 1 }

LecOperStatusEntry ::= SEQUENCE {
   lecSnmpOperStatus
      INTEGER }

lecSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { lecOperStatusEntry 1 }

lecOperTable OBJECT-TYPE
   SYNTAX     SEQUENCE OF LecOperEntry
   ACCESS     not-accessible
   STATUS     mandatory
   DESCRIPTION
     "This group contains the operational status attributes of the 
      LanEmulationClient component."
::= { lec 17 }

lecOperEntry OBJECT-TYPE
   SYNTAX     LecOperEntry
   ACCESS     not-accessible
   STATUS     mandatory
   DESCRIPTION
     "An entry in the lecOperTable."
   INDEX {
      lecIndex }
::= { lecOperTable 1 }

LecOperEntry ::= SEQUENCE {
   lecActualLanType
      INTEGER,
   lecActualMaxFrameSize
      INTEGER,
   lecActualLanName
      AsciiString,
   lecElanId
      Unsigned32,
   lecActualV2Capable
      INTEGER,
   lecConfigurationSource
      INTEGER,
   lecActualLecsAddress
      HexString,
   lecActualLesAddress
      HexString,
   lecAtmAddress
      HexString,
   lecMacAddress
      MacAddress,
   lecLecId
      Unsigned32,
   lecInterfaceState
      INTEGER,
   lecLastFailureResponseCode
      INTEGER,
   lecLastFailureState
      INTEGER }

lecActualLanType OBJECT-TYPE
   SYNTAX     INTEGER  {
                 unspecified(1),
                 ethernet(2) }
   ACCESS     read-only
   STATUS     mandatory
   DESCRIPTION
     "This attribute indicates the data frame format of this LEC. This may 
      come from the lanType attribute, LECS or LES. The data frame 
      format is not unspecified for an operational LEC.
      This attribute represents the 'C2' LEC state parameter in the ATM 
      Forum LANE specification.
      
      Token Ring data frame format is not supported. The LEC does not 
      become operational if the LECS or LES specify a LAN type of 
      Token Ring."
::= { lecOperEntry 1 }

lecActualMaxFrameSize OBJECT-TYPE
   SYNTAX     INTEGER  {
                 unspecified(0),
                 n1516(1516),
                 n1580(1580),
                 n4544(4544),
                 n9234(9234),
                 n18190(18190) }
   ACCESS     read-only
   STATUS     mandatory
   DESCRIPTION
     "This attribute indicates the maximum data frame size of this LEC. 
      This may come from the maxFrameSize attribute, LECS or LES. 
      The value is not unspecified for an operational LEC. 
      If the LEC's actualV2Capable attribute is no, the value will be 
      limited to one of 1516, 4544, 9234, 18190.
      This attribute represents the 'C3' LEC state parameter in the ATM 
      Forum LANE specification."
::= { lecOperEntry 2 }

lecActualLanName OBJECT-TYPE
   SYNTAX     AsciiString (SIZE (0..32))
   ACCESS     read-only
   STATUS     mandatory
   DESCRIPTION
     "This attribute indicates the name of the ELAN to which this LEC is 
      connected. This may come from the lanName attribute, LECS or 
      LES. It may be null for an operational LEC.
      This attribute represents the 'C5' LEC state parameter in the ATM 
      Forum LANE specification."
::= { lecOperEntry 3 }

lecElanId OBJECT-TYPE
   SYNTAX     Unsigned32 (0..4294967295)
   ACCESS     read-only
   STATUS     mandatory
   DESCRIPTION
     "This attribute identifies the ELAN to which this LEC is connected. 
      For v2, the  value will be set in the configuration phase, 
      otherwise it will be 0."
::= { lecOperEntry 4 }

lecActualV2Capable OBJECT-TYPE
   SYNTAX     INTEGER  {
                 yes(1),
                 no(2) }
   ACCESS     read-only
   STATUS     mandatory
   DESCRIPTION
     "This attribute indicates whether this LEC exhibits LANE v2 
      behavior. The value is set in the Join phase."
::= { lecOperEntry 5 }

lecConfigurationSource OBJECT-TYPE
   SYNTAX     INTEGER  {
                 usedProvisionedLecsAddress(1),
                 gotLecsAddressViaIlmi(2),
                 usedWellKnownLecsAddress(3),
                 usedLecsPvc(4),
                 didNotUseLecs(5) }
   ACCESS     read-only
   STATUS     mandatory
   DESCRIPTION
     "This attribute indicates whether this LEC used the LECS, and if so, 
      the method  used to establish the Configuration Direct VCC. 
      The attribute retains this value when the LEC is reset.
      - usedProvisionedLecsAddress: The ATM address specified in 
      lecsAddress was used to locate the LECS.
      - gotLecsAddressViaIlmi: The ATM address of the LECS was 
      located via the ILMI protocol.
      - usedWellKnownLecsAddress: The well-known ATM address 
      0x47007900000000000000000000-00A03E000001-00 was used to 
      locate the LECS.
      - usedLecsPvc: The well known PVC of VPI=0, VCI=17 was used 
      to locate the LECS.
      - didNotUseLecs: The LECS was bypassed and the ATM address 
      specified in lesAddress was used to locate the LES."
::= { lecOperEntry 6 }

lecActualLecsAddress OBJECT-TYPE
   SYNTAX     HexString (SIZE (0..20))
   ACCESS     read-only
   STATUS     mandatory
   DESCRIPTION
     "This attribute indicates the ATM address of the LECS used to 
      configure this LEC. The address is null if the LECS was not used."
::= { lecOperEntry 7 }

lecActualLesAddress OBJECT-TYPE
   SYNTAX     HexString (SIZE (0..20))
   ACCESS     read-only
   STATUS     mandatory
   DESCRIPTION
     "This attribute indicates the ATM address of the LES which is 
      currently serving this LEC. The address is not null for an 
      operational LEC.
      This attribute represents the 'C9' LEC state parameter in the ATM 
      Forum LANE specification."
::= { lecOperEntry 8 }

lecAtmAddress OBJECT-TYPE
   SYNTAX     HexString (SIZE (0..20))
   ACCESS     read-only
   STATUS     mandatory
   DESCRIPTION
     "This attribute indicates the ATM address of this LEC.
      This attribute represents the 'C1' LEC state parameter in the ATM 
      Forum LANE specification."
::= { lecOperEntry 9 }

lecMacAddress OBJECT-TYPE
   SYNTAX     MacAddress (SIZE (6))
   ACCESS     read-only
   STATUS     mandatory
   DESCRIPTION
     "This attribute indicates the MAC address of this LEC.
      This attribute represents the 'C6' LEC state parameter in the ATM 
      Forum LANE specification."
::= { lecOperEntry 10 }

lecLecId OBJECT-TYPE
   SYNTAX     Unsigned32 (0..65279)
   ACCESS     read-only
   STATUS     mandatory
   DESCRIPTION
     "This attribute indicates the LANE Client Identifier (LECID) 
      assigned to this LEC by the LES during the Join phase. The LECID 
      uniquely identifies a LEC on a particular ELAN.
      This attribute represents the 'C14' LEC state parameter in the ATM 
      Forum LANE specification."
::= { lecOperEntry 11 }

lecInterfaceState OBJECT-TYPE
   SYNTAX     INTEGER  {
                 initialState(1),
                 lecsConnect(2),
                 configure(3),
                 join(4),
                 initialRegistration(5),
                 busConnect(6),
                 operational(7) }
   ACCESS     read-only
   STATUS     mandatory
   DESCRIPTION
     "This attribute indicates the current state of the LEC. Note that 
      ifOperStatus is up only when interfaceState is operational.
      - initialState: Some parameters (such as addresses and ELAN 
      name) are known to the LEC.
      - lecsConnect: LEC establishes Configuration Direct VCC to 
      LECS. Manually-configured LECs skip this state.
      - configure: LEC discovers LES.
      - join: LEC establishes control connections to LES. LEC is 
      assigned unique LECID and knows all ELAN parameters.
      - initialRegistration: LEC may register additional MAC addresses 
      with LES. This is in addition to the single MAC address registered 
      during Join phase.
      - busConnect: LEC issues LE_ARP to locate the BUS and sets up 
      the connection. The BUS then establishes the Multicast Forward 
      VCC to the LEC.
      - operational: LEC is operational and can forward data traffic."
::= { lecOperEntry 12 }

lecLastFailureResponseCode OBJECT-TYPE
   SYNTAX     INTEGER  {
                 none(1),
                 timeout(2),
                 undefinedError(3),
                 versionNotSupported(4),
                 invalidRequestParameters(5),
                 duplicateLanDestination(6),
                 duplicateAtmAddress(7),
                 insufficientResources(8),
                 accessDenied(9),
                 invalidRequesterId(10),
                 invalidLanDestination(11),
                 invalidAtmAddress(12),
                 noConfiguration(13),
                 leConfigureError(14),
                 insufficientInformation(15) }
   ACCESS     read-only
   STATUS     mandatory
   DESCRIPTION
     "The attribute indicates the status code from the last failed Configure 
      or Join response. Failed responses are those for which the 
      LE_CONFIGURE_RESPONSE / LE_JOIN_RESPONSE frame 
      contains a non-zero code, or fails to arrive within a time-out period. 
      If none of the LEC's requests have failed, this attribute has the value 
      none."
::= { lecOperEntry 13 }

lecLastFailureState OBJECT-TYPE
   SYNTAX     INTEGER  {
                 initialState(1),
                 lecsConnect(2),
                 configure(3),
                 join(4),
                 initialRegistration(5),
                 busConnect(6),
                 operational(7) }
   ACCESS     read-only
   STATUS     mandatory
   DESCRIPTION
     "This attribute indicates the state that the LEC was in when it 
      updated the lastFailureResponseCode. If lastFailureResponseCode 
      is none, this attribute has the value initialState.
      See the interfaceState attribute for a description of each state."
::= { lecOperEntry 14 }

lecStatsTable OBJECT-TYPE
   SYNTAX     SEQUENCE OF LecStatsEntry
   ACCESS     not-accessible
   STATUS     mandatory
   DESCRIPTION
     "This group contains the statistical attributes of the 
      LanEmulationClient component."
::= { lec 18 }

lecStatsEntry OBJECT-TYPE
   SYNTAX     LecStatsEntry
   ACCESS     not-accessible
   STATUS     mandatory
   DESCRIPTION
     "An entry in the lecStatsTable."
   INDEX {
      lecIndex }
::= { lecStatsTable 1 }

LecStatsEntry ::= SEQUENCE {
   lecArpRequestsOut
      Counter32,
   lecArpRepliesIn
      Counter32,
   lecArpRequestsIn
      Counter32,
   lecArpRepliesOut
      Counter32,
   lecControlFramesOut
      Counter32,
   lecControlFramesIn
      Counter32,
   lecSvcFailures
      Counter32,
   lecCurrDataSvcs
      Unsigned32,
   lecPeakDataSvcs
      Unsigned32,
   lecCurrArpEntries
      Unsigned32,
   lecPeakArpEntries
      Unsigned32,
   lecBadControlFrames
      Counter32,
   lecProtocolViolations
      Counter32,
   lecUnsupportedTlvs
      Counter32 }

lecArpRequestsOut OBJECT-TYPE
   SYNTAX     Counter32 
   ACCESS     read-only
   STATUS     mandatory
   DESCRIPTION
     "This attribute counts the LE_ARP_REQUESTS sent by this LEC. 
      This counter wraps to zero when the maximum value is reached."
::= { lecStatsEntry 1 }

lecArpRepliesIn OBJECT-TYPE
   SYNTAX     Counter32 
   ACCESS     read-only
   STATUS     mandatory
   DESCRIPTION
     "This attribute counts the LE_ARP_RESPONSES received by this 
      LEC. This counter wraps to zero when the maximum value is 
      reached."
::= { lecStatsEntry 2 }

lecArpRequestsIn OBJECT-TYPE
   SYNTAX     Counter32 
   ACCESS     read-only
   STATUS     mandatory
   DESCRIPTION
     "This attribute counts the LE_ARP_REQUESTS received by this 
      LEC. This counter wraps to zero when the maximum value is 
      reached."
::= { lecStatsEntry 3 }

lecArpRepliesOut OBJECT-TYPE
   SYNTAX     Counter32 
   ACCESS     read-only
   STATUS     mandatory
   DESCRIPTION
     "This attribute counts the LE_ARP_RESPONSES sent by this LEC. 
      This counter wraps to zero when the maximum value is reached."
::= { lecStatsEntry 4 }

lecControlFramesOut OBJECT-TYPE
   SYNTAX     Counter32 
   ACCESS     read-only
   STATUS     mandatory
   DESCRIPTION
     "This attribute counts the control packets sent by this LEC. This 
      counter wraps to zero when the maximum value is reached."
::= { lecStatsEntry 5 }

lecControlFramesIn OBJECT-TYPE
   SYNTAX     Counter32 
   ACCESS     read-only
   STATUS     mandatory
   DESCRIPTION
     "This attribute counts the control packets received by this LEC. This 
      counter wraps to zero when the maximum value is reached."
::= { lecStatsEntry 6 }

lecSvcFailures OBJECT-TYPE
   SYNTAX     Counter32 
   ACCESS     read-only
   STATUS     mandatory
   DESCRIPTION
     "This attribute counts the number of SVCs that could not be set up. 
      The reasons for failure are:
      - outgoing SVCs that this LEC failed to establish;
      - incoming SVCs that this LEC failed to establish; and
      - incoming SVCs that this LEC rejected for protocol or security 
      reasons.
      This counter wraps to zero when the maximum value is reached."
::= { lecStatsEntry 7 }

lecCurrDataSvcs OBJECT-TYPE
   SYNTAX     Unsigned32 (0..4292967295)
   ACCESS     read-only
   STATUS     mandatory
   DESCRIPTION
     "This attribute counts the number of Data Direct SVCs that this LEC 
      has in service."
::= { lecStatsEntry 8 }

lecPeakDataSvcs OBJECT-TYPE
   SYNTAX     Unsigned32 (0..4292967295)
   ACCESS     read-only
   STATUS     mandatory
   DESCRIPTION
     "The attribute is the peak value of currDataSvcs. In other words, this 
      value is the maximum number of Data Direct SVCs that this LEC 
      had in service at any one time."
::= { lecStatsEntry 9 }

lecCurrArpEntries OBJECT-TYPE
   SYNTAX     Unsigned32 (0..4292967295)
   ACCESS     read-only
   STATUS     mandatory
   DESCRIPTION
     "This attribute counts the current number of entries that this LEC has 
      in its LE ARP table."
::= { lecStatsEntry 10 }

lecPeakArpEntries OBJECT-TYPE
   SYNTAX     Unsigned32 (0..4292967295)
   ACCESS     read-only
   STATUS     mandatory
   DESCRIPTION
     "The attribute is the peak value currArpEntries. In other words, this 
      value is the maximum number of entries that this LEC had in its LE 
      ARP table at any one time."
::= { lecStatsEntry 11 }

lecBadControlFrames OBJECT-TYPE
   SYNTAX     Counter32 
   ACCESS     read-only
   STATUS     mandatory
   DESCRIPTION
     "This attribute counts the control frames discarded by the LEC due 
      to invalid or illegal frame format, and those frames with a STATUS 
      code other than 'Success'. This counter wraps to zero when the 
      maximum value is reached."
::= { lecStatsEntry 12 }

lecProtocolViolations OBJECT-TYPE
   SYNTAX     Counter32 
   ACCESS     read-only
   STATUS     mandatory
   DESCRIPTION
     "This attribute counts the number of responses received by
      the LEC that contained invalid data or non-protocol compliant data.
      This counter wraps to zero when the maximum value is reached."
::= { lecStatsEntry 13 }

lecUnsupportedTlvs OBJECT-TYPE
   SYNTAX     Counter32 
   ACCESS     read-only
   STATUS     mandatory
   DESCRIPTION
     "This attribute counts the number of times an unsupported TLV was 
      received by the LEC in either the Configuration or Join response.
      This counter wraps to zero when the maximum value is reached."
::= { lecStatsEntry 14 }

-- 
-- *** THIS SUBTREE CURRENTLY NOT IMPLEMENTED ***
-- 

-- Lec/n LeArpEntry/<Mac Address>
-- This component defines an entry in the LE_ARP table. Each entry 
-- contains information about the binding of one MAC address to one 
-- ATM address.

lecLeArp OBJECT IDENTIFIER ::= { lec 2 }



lecLeArpRowStatusTable OBJECT-TYPE
   SYNTAX     SEQUENCE OF LecLeArpRowStatusEntry
   ACCESS     not-accessible
   STATUS     mandatory
   DESCRIPTION
     "*** THIS TABLE CURRENTLY NOT IMPLEMENTED ***

      This entry controls the addition and deletion of 
      lecLeArp components."
::= { lecLeArp 1 }

lecLeArpRowStatusEntry OBJECT-TYPE
   SYNTAX     LecLeArpRowStatusEntry
   ACCESS     not-accessible
   STATUS     mandatory
   DESCRIPTION
     "A single entry in the table represents a single 
      lecLeArp component."
   INDEX {
      lecIndex,
      lecLeArpIndex }
::= { lecLeArpRowStatusTable 1 }

LecLeArpRowStatusEntry ::= SEQUENCE {
   lecLeArpRowStatus
      RowStatus,
   lecLeArpComponentName
      DisplayString,
   lecLeArpStorageType
      StorageType,
   lecLeArpIndex
      DashedHexString }

lecLeArpRowStatus OBJECT-TYPE
   SYNTAX     RowStatus 
   ACCESS     read-only
   STATUS     mandatory
   DESCRIPTION
     "This variable is used as the basis for SNMP naming of
      lecLeArp components.
      These components cannot be added nor deleted."
::= { lecLeArpRowStatusEntry 1 }

lecLeArpComponentName OBJECT-TYPE
   SYNTAX     DisplayString 
   ACCESS     read-only
   STATUS     mandatory
   DESCRIPTION
     "This variable provides the component's string name for
      use with the ASCII Console Interface"
::= { lecLeArpRowStatusEntry 2 }

lecLeArpStorageType OBJECT-TYPE
   SYNTAX     StorageType 
   ACCESS     read-only
   STATUS     mandatory
   DESCRIPTION
     "This variable represents the storage type value for the
      lecLeArp tables."
::= { lecLeArpRowStatusEntry 4 }

lecLeArpIndex OBJECT-TYPE
   SYNTAX     DashedHexString (SIZE (6))
   ACCESS     not-accessible
   STATUS     mandatory
   DESCRIPTION
     "This variable represents the index for the lecLeArp tables."
::= { lecLeArpRowStatusEntry 10 }

lecLeArpOperTable OBJECT-TYPE
   SYNTAX     SEQUENCE OF LecLeArpOperEntry
   ACCESS     not-accessible
   STATUS     mandatory
   DESCRIPTION
     "*** THIS TABLE CURRENTLY NOT IMPLEMENTED ***

      This group contains the operational attributes of the LeArpEntry 
      component."
::= { lecLeArp 10 }

lecLeArpOperEntry OBJECT-TYPE
   SYNTAX     LecLeArpOperEntry
   ACCESS     not-accessible
   STATUS     mandatory
   DESCRIPTION
     "An entry in the lecLeArpOperTable."
   INDEX {
      lecIndex,
      lecLeArpIndex }
::= { lecLeArpOperTable 1 }

LecLeArpOperEntry ::= SEQUENCE {
   lecLeArpAtmAddress
      HexString,
   lecLeArpIsRemoteAddress
      INTEGER,
   lecLeArpConnectionId
      Unsigned32 }

lecLeArpAtmAddress OBJECT-TYPE
   SYNTAX     HexString (SIZE (20))
   ACCESS     read-only
   STATUS     mandatory
   DESCRIPTION
     "This attribute indicates the ATM address of the BUS or LEC 
      associated with the MAC address of this entry. If the MAC address 
      is the all-ones broadcast address, the entry is for the BUS."
::= { lecLeArpOperEntry 1 }

lecLeArpIsRemoteAddress OBJECT-TYPE
   SYNTAX     INTEGER  {
                 yes(1),
                 no(2) }
   ACCESS     read-only
   STATUS     mandatory
   DESCRIPTION
     "This attribute indicates whether this entry is for a local or remote 
      MAC address. In this context, 'local' means a MAC address that is 
      local to a LEC, and 'remote' means a MAC address for which the 
      LEC is proxy.
      If yes, the address is believed to be remote, or its local/remote status 
      is unknown.
      If no, the address is believed to be local; that is, registered with the 
      LES by the LEC whose ATM address is atmAddress."
::= { lecLeArpOperEntry 2 }

lecLeArpConnectionId OBJECT-TYPE
   SYNTAX     Unsigned32 (0..1022)
   ACCESS     read-only
   STATUS     mandatory
   DESCRIPTION
     "This attribute indicates the connection identifier associated with this 
      entry. The connection identifier is the instance of the Connection 
      component."
::= { lecLeArpOperEntry 3 }

-- 
-- *** THIS SUBTREE CURRENTLY NOT IMPLEMENTED ***
-- 

-- Lec/n Connection/n
-- This component defines an ATM connection (SVC) that is used by 
-- the LEC.

lecConn OBJECT IDENTIFIER ::= { lec 3 }



lecConnRowStatusTable OBJECT-TYPE
   SYNTAX     SEQUENCE OF LecConnRowStatusEntry
   ACCESS     not-accessible
   STATUS     mandatory
   DESCRIPTION
     "*** THIS TABLE CURRENTLY NOT IMPLEMENTED ***

      This entry controls the addition and deletion of 
      lecConn components."
::= { lecConn 1 }

lecConnRowStatusEntry OBJECT-TYPE
   SYNTAX     LecConnRowStatusEntry
   ACCESS     not-accessible
   STATUS     mandatory
   DESCRIPTION
     "A single entry in the table represents a single 
      lecConn component."
   INDEX {
      lecIndex,
      lecConnIndex }
::= { lecConnRowStatusTable 1 }

LecConnRowStatusEntry ::= SEQUENCE {
   lecConnRowStatus
      RowStatus,
   lecConnComponentName
      DisplayString,
   lecConnStorageType
      StorageType,
   lecConnIndex
      Integer32 }

lecConnRowStatus OBJECT-TYPE
   SYNTAX     RowStatus 
   ACCESS     read-only
   STATUS     mandatory
   DESCRIPTION
     "This variable is used as the basis for SNMP naming of
      lecConn components.
      These components cannot be added nor deleted."
::= { lecConnRowStatusEntry 1 }

lecConnComponentName OBJECT-TYPE
   SYNTAX     DisplayString 
   ACCESS     read-only
   STATUS     mandatory
   DESCRIPTION
     "This variable provides the component's string name for
      use with the ASCII Console Interface"
::= { lecConnRowStatusEntry 2 }

lecConnStorageType OBJECT-TYPE
   SYNTAX     StorageType 
   ACCESS     read-only
   STATUS     mandatory
   DESCRIPTION
     "This variable represents the storage type value for the
      lecConn tables."
::= { lecConnRowStatusEntry 4 }

lecConnIndex OBJECT-TYPE
   SYNTAX     Integer32 (0..1022)
   ACCESS     not-accessible
   STATUS     mandatory
   DESCRIPTION
     "This variable represents the index for the lecConn tables."
::= { lecConnRowStatusEntry 10 }

lecConnOperTable OBJECT-TYPE
   SYNTAX     SEQUENCE OF LecConnOperEntry
   ACCESS     not-accessible
   STATUS     mandatory
   DESCRIPTION
     "*** THIS TABLE CURRENTLY NOT IMPLEMENTED ***

      This group contains the operational status attributes of the 
      Connection component."
::= { lecConn 10 }

lecConnOperEntry OBJECT-TYPE
   SYNTAX     LecConnOperEntry
   ACCESS     not-accessible
   STATUS     mandatory
   DESCRIPTION
     "An entry in the lecConnOperTable."
   INDEX {
      lecIndex,
      lecConnIndex }
::= { lecConnOperTable 1 }

LecConnOperEntry ::= SEQUENCE {
   lecConnRemoteAtmAddress
      HexString,
   lecConnAge
      Unsigned32,
   lecConnType
      INTEGER }

lecConnRemoteAtmAddress OBJECT-TYPE
   SYNTAX     HexString (SIZE (20))
   ACCESS     read-only
   STATUS     mandatory
   DESCRIPTION
     "This attribute indicates the ATM address of the far end."
::= { lecConnOperEntry 1 }

lecConnAge OBJECT-TYPE
   SYNTAX     Unsigned32 (0..4292967295)
   ACCESS     read-only
   STATUS     mandatory
   DESCRIPTION
     "This attribute indicates the age of this connection."
::= { lecConnOperEntry 2 }

lecConnType OBJECT-TYPE
   SYNTAX     INTEGER  {
                 configurationDirectVcc(1),
                 controlDirectVcc(2),
                 controlDistributeVcc(3),
                 dataDirectVcc(4),
                 defaultMulticastSendVcc(5),
                 multicastForward(6) }
   ACCESS     read-only
   STATUS     mandatory
   DESCRIPTION
     "This attribute indicates the type of this connection."
::= { lecConnOperEntry 3 }

lecConnStatsTable OBJECT-TYPE
   SYNTAX     SEQUENCE OF LecConnStatsEntry
   ACCESS     not-accessible
   STATUS     mandatory
   DESCRIPTION
     "*** THIS TABLE CURRENTLY NOT IMPLEMENTED ***

      This group contains the statistical attributes of the Connection 
      component."
::= { lecConn 11 }

lecConnStatsEntry OBJECT-TYPE
   SYNTAX     LecConnStatsEntry
   ACCESS     not-accessible
   STATUS     mandatory
   DESCRIPTION
     "An entry in the lecConnStatsTable."
   INDEX {
      lecIndex,
      lecConnIndex }
::= { lecConnStatsTable 1 }

LecConnStatsEntry ::= SEQUENCE {
   lecConnOutFrames
      Counter32,
   lecConnInFrames
      Counter32 }

lecConnOutFrames OBJECT-TYPE
   SYNTAX     Counter32 
   ACCESS     read-only
   STATUS     mandatory
   DESCRIPTION
     "This attribute counts the frames sent over this connection. This 
      counter wraps to zero when the maximum value is reached."
::= { lecConnStatsEntry 1 }

lecConnInFrames OBJECT-TYPE
   SYNTAX     Counter32 
   ACCESS     read-only
   STATUS     mandatory
   DESCRIPTION
     "This attribute counts the frames received over this connection. This 
      counter wraps to zero when the maximum value is reached."
::= { lecConnStatsEntry 2 }

-- 
-- *** THIS SUBTREE CURRENTLY NOT IMPLEMENTED ***
-- 

-- An AtmConnection component is created for each ATM connection 
-- established by an application. It shows where the data traffic for this 
-- connection is directed.

lecConnAtmCon OBJECT IDENTIFIER ::= { lecConn 2 }



lecConnAtmConRowStatusTable OBJECT-TYPE
   SYNTAX     SEQUENCE OF LecConnAtmConRowStatusEntry
   ACCESS     not-accessible
   STATUS     mandatory
   DESCRIPTION
     "*** THIS TABLE CURRENTLY NOT IMPLEMENTED ***

      This entry controls the addition and deletion of 
      lecConnAtmCon components."
::= { lecConnAtmCon 1 }

lecConnAtmConRowStatusEntry OBJECT-TYPE
   SYNTAX     LecConnAtmConRowStatusEntry
   ACCESS     not-accessible
   STATUS     mandatory
   DESCRIPTION
     "A single entry in the table represents a single 
      lecConnAtmCon component."
   INDEX {
      lecIndex,
      lecConnIndex,
      lecConnAtmConIndex }
::= { lecConnAtmConRowStatusTable 1 }

LecConnAtmConRowStatusEntry ::= SEQUENCE {
   lecConnAtmConRowStatus
      RowStatus,
   lecConnAtmConComponentName
      DisplayString,
   lecConnAtmConStorageType
      StorageType,
   lecConnAtmConIndex
      NonReplicated }

lecConnAtmConRowStatus OBJECT-TYPE
   SYNTAX     RowStatus 
   ACCESS     read-only
   STATUS     mandatory
   DESCRIPTION
     "This variable is used as the basis for SNMP naming of
      lecConnAtmCon components.
      These components cannot be added nor deleted."
::= { lecConnAtmConRowStatusEntry 1 }

lecConnAtmConComponentName OBJECT-TYPE
   SYNTAX     DisplayString 
   ACCESS     read-only
   STATUS     mandatory
   DESCRIPTION
     "This variable provides the component's string name for
      use with the ASCII Console Interface"
::= { lecConnAtmConRowStatusEntry 2 }

lecConnAtmConStorageType OBJECT-TYPE
   SYNTAX     StorageType 
   ACCESS     read-only
   STATUS     mandatory
   DESCRIPTION
     "This variable represents the storage type value for the
      lecConnAtmCon tables."
::= { lecConnAtmConRowStatusEntry 4 }

lecConnAtmConIndex OBJECT-TYPE
   SYNTAX     NonReplicated 
   ACCESS     not-accessible
   STATUS     mandatory
   DESCRIPTION
     "This variable represents the index for the lecConnAtmCon tables."
::= { lecConnAtmConRowStatusEntry 10 }

lecConnAtmConOperTable OBJECT-TYPE
   SYNTAX     SEQUENCE OF LecConnAtmConOperEntry
   ACCESS     not-accessible
   STATUS     mandatory
   DESCRIPTION
     "*** THIS TABLE CURRENTLY NOT IMPLEMENTED ***

      This attribute group contains the operational attributes for the 
      NapAtmConnection component."
::= { lecConnAtmCon 10 }

lecConnAtmConOperEntry OBJECT-TYPE
   SYNTAX     LecConnAtmConOperEntry
   ACCESS     not-accessible
   STATUS     mandatory
   DESCRIPTION
     "An entry in the lecConnAtmConOperTable."
   INDEX {
      lecIndex,
      lecConnIndex,
      lecConnAtmConIndex }
::= { lecConnAtmConOperTable 1 }

LecConnAtmConOperEntry ::= SEQUENCE {
   lecConnAtmConNextHop
      RowPointer }

lecConnAtmConNextHop OBJECT-TYPE
   SYNTAX     RowPointer 
   ACCESS     read-only
   STATUS     mandatory
   DESCRIPTION
     "This attribute shows the component name of the AtmIf Vcc Ep or 
      AtmCon component to which this switched connection is 
      established."
::= { lecConnAtmConOperEntry 1 }




-- 
-- Version and Compliance statements
-- 



-- Object-Group Statement:
-- A list of all current accessible leaf objects.

-- OBJECTS { lecActualLanType,
--           lecUsageState,
--           lecActualV2Capable,
--           lecArpRepliesOut,
--           lecComponentName,
--           lecCurrArpEntries,
--           lecPeakArpEntries,
--           lecConnInFrames,
--           lecAtmAddress,
--           lecUnsupportedTlvs,
--           lecLanName,
--           lecLecId,
--           lecActualMaxFrameSize,
--           lecArpRequestsOut,
--           lecMaxDataSvcs,
--           lecActualLesAddress,
--           lecLanType,
--           lecConnComponentName,
--           lecActualLecsAddress,
--           lecConnAtmConRowStatus,
--           lecCustomerIdentifier,
--           lecConnAtmConNextHop,
--           lecConnAge,
--           lecControlFramesOut,
--           lecLinkToProtocolPort,
--           lecConnStorageType,
--           lecLastFailureResponseCode,
--           lecCurrDataSvcs,
--           lecProtocolViolations,
--           lecArpRequestsIn,
--           lecConnAtmConComponentName,
--           lecConfigurationSource,
--           lecArpRepliesIn,
--           lecConnAtmConStorageType,
--           lecSnmpOperStatus,
--           lecLastFailureState,
--           lecIfIndex,
--           lecActualLanName,
--           lecIlsForwarder,
--           lecControlFramesIn,
--           lecElanId,
--           lecStorageType,
--           lecV2Capable,
--           lecConnOutFrames,
--           lecPeakDataSvcs,
--           lecLeArpRowStatus,
--           lecLeArpStorageType,
--           lecMaxFrameSize,
--           lecLeArpConnectionId,
--           lecMacAddress,
--           lecAdminState,
--           lecOperationalState,
--           lecMaxArpEntries,
--           lecLeArpComponentName,
--           lecLecsAddress,
--           lecInterfaceState,
--           lecIfAdminStatus,
--           lecBadControlFrames,
--           lecConnType,
--           lecLesAddress,
--           lecConnRowStatus,
--           lecLeArpAtmAddress,
--           lecConnRemoteAtmAddress,
--           lecRowStatus,
--           lecLeArpIsRemoteAddress,
--           lecSvcFailures }
-- STATUS  mandatory
-- DESCRIPTION
--   "A list of all current accessible leaf objects."

laneClientGroup OBJECT IDENTIFIER ::= { laneClientMIB 1 }
laneClientGroupBE OBJECT IDENTIFIER ::= { laneClientGroup 5 }
laneClientGroupBE00 OBJECT IDENTIFIER ::= { laneClientGroupBE 1 }
laneClientGroupBE00A OBJECT IDENTIFIER ::= { laneClientGroupBE00 2 }



-- Agent-Capabilities Statement:

-- PRODUCT-RELEASE "Passport Release 7.0 LaneClient."
-- STATUS          mandatory
-- DESCRIPTION     "LaneClient MIB: MIB Version BE00A,
--                  Software Version BG00S4C."
-- SUPPORTS        Nortel-Magellan-Passport-LaneClientMIB
--    INCLUDES     { laneClientGroupBE00A }

laneClientCapabilities OBJECT IDENTIFIER ::= { laneClientMIB 3 }
laneClientCapabilitiesBE OBJECT IDENTIFIER ::= { laneClientCapabilities 5 }
laneClientCapabilitiesBE00 OBJECT IDENTIFIER ::= { laneClientCapabilitiesBE 1 }
laneClientCapabilitiesBE00A OBJECT IDENTIFIER ::= { laneClientCapabilitiesBE00 2 }





END
