-- Documents: 285-516-1.

EICON-MIB-SERVER DEFINITIONS  ::=  BEGIN


IMPORTS
	Counter,  
	Gauge,  
	TimeTicks,
	enterprises
		FROM RFC1155-SMI
	OBJECT-TYPE
		FROM RFC-1212
	TRAP-TYPE
		FROM RFC-1215
	DisplayString, PhysAddress, sysName
		FROM RFC1213-MIB;

eicon           OBJECT IDENTIFIER  ::= { enterprises 434 }
management      OBJECT IDENTIFIER  ::= { eicon 2 }
mibv2           OBJECT IDENTIFIER  ::= { management 2 }
module          OBJECT IDENTIFIER  ::= { mibv2 4 }

OperState ::= INTEGER {
	other (1),              -- none of the following
	disabled (2),           -- not in ready state
	ready (3),              -- in ready state
	active (4),             -- ready and operating
	busy (5)                        -- operating but cannot accept more traffic
	}

AdminState ::= INTEGER {
	start (1),
	stop (2),
	dump (3),
	test (4),
	invalid (5)
	}

 ActionState ::= INTEGER {
	done (1),
	failed (2),
	in-progress (3)
	}

EiconCardType ::= INTEGER {
	ect-NONE (1),
	ect-PC-NA (2),
	ect-PC-DNA (3),
	ect-PC-SPNA (4),
	ect-MC-SPCC (5),
	ect-PC-DPNA (6),
	ect-PC-EC (7),
	ect-PC-ECHSI (8),
	ect-PC-QPNA (9),
	ect-PC-MPNA (10),
	ect-MC-EC (11),
	ect-MC-HSI (12),
	ect-XX-DIGI (13),
	ect-MC-IMC (14),
	ect-PC-IMC (15),
	ect-MC-MPNA (16),       
	ect-PC-HSI1M (17),
	ect-MC-HSI1M (18),
	ect-NB-HSI1M (19),
	ect-PC-EC1M (20),
	ect-MC-EC1M (21),
	ect-NB-EC1M (22),
	ect-NB-IMC (23),
	ect-NB-SPCC (24),
	ect-NB-EC (25),
	ect-PC-ACC8 (26),
	ect-PC-ISDN (27),
	ect-PC-DPNA2M (28),
	ect-PC-MPNA2M (29),
	ect-MC-MPNA2M (30),
	ect-MC-SPCC2 (31),
	ect-PP-IMC (32),
	ect-MC-ISDN (33),
	ect-PP-EC (34),
	ect-PC-HSI2 (35),
	ect-PC-S51 (36),
	ect-PC-S52 (37)
	}

-- Used to indicate that corresponding control parameters are invalid
ControlOnOff ::= INTEGER {
	stop (1),
	start (2),
	invalid (3)
	}


CardRef ::= INTEGER (1..6)      -- EiconCard reference on the server.

PortRef ::= INTEGER (1..48)     -- Port reference on the server.

PortName ::= DisplayString (SIZE (1..15))       -- Port name composed of up to 15 ascii characters.

PositiveInteger ::= INTEGER (0..2147483647)


--      Title

server          OBJECT IDENTIFIER  ::= { mibv2 1 }

--      The server object describes the physical device which hosts the Eicon Communication Server.
--
--      Basic information about the server is included in the system group of the MIB-2:
--              sysName,
--              sysDescr,
--              sysLocation,
--              sysContact,     (may contain more then one name/addr/tel for the contact people)
--              sysUpTime.
--
--      A number of other attributes describe the hardware of the server and Eicon specific software. 
--      The information about the server is contained in the following tables:
--              srvLanCardTable,
--              srvSoftPackageTable.
--

srvAdminStateCtr        OBJECT-TYPE
	SYNTAX  AdminState
	ACCESS  read-write
	STATUS  mandatory
	DESCRIPTION     
		"The administrative state of the server.  This control parameter is modified (set) by 	
		Operator in order to change the state of the server."
	::= { server 1 }

srvOsName               OBJECT-TYPE
	SYNTAX  INTEGER {
		other (1),
		dos (2),
		os2 (3),
		unix (4),
		mac (5),
		windows (6),
		netware (7),
		nt (8)
		}
	ACCESS   read-only 
	STATUS  mandatory
	DESCRIPTION     
		"The name of the Operating System."
	::= { server 2 }

srvOsVersion            OBJECT-TYPE
	SYNTAX  DisplayString (SIZE(0..16))
	ACCESS  read-only 
	STATUS  mandatory
	DESCRIPTION     
		"The version of the Operating System;  e.g. SCO UNIX 3.2 "
	::= { server 3 }

srvNosName              OBJECT-TYPE
	SYNTAX  INTEGER {
		other (1),      -- none of the following
		netWare (2),
		lanManager (3),
		vines (4),
		lanServer (5),
		genericNetBIOS (6)
		}
	ACCESS   read-only 
	STATUS  mandatory
	DESCRIPTION     
		"The name of the Network Operating System."
	::= { server 4 }

srvNosVersion           OBJECT-TYPE
	SYNTAX  DisplayString (SIZE(0..16))
	ACCESS  read-only 
	STATUS  mandatory
	DESCRIPTION     
		"The version of the  Network Operating System;  e.g. NetWare v3.11 "
	::= { server 5 }

srvLanShellInfo         OBJECT-TYPE
	SYNTAX  DisplayString (SIZE(0..16))
	ACCESS  read-only 
	STATUS  mandatory
	DESCRIPTION     
		"The name and version of the  Network Operating System shell."
	::= { server 6 }

srvBusType              OBJECT-TYPE     -- Not supported by Eicon Agent
	SYNTAX  INTEGER {
		other (1),
		isa (2),
		eisa (3),
		mca (4),
		parallelPort (5)
		}
	ACCESS  read-only 
	STATUS  mandatory
	DESCRIPTION     
		"The type of the BUS. "
	::= { server 7 }

srvCpuType              OBJECT-TYPE     -- Not supported by Eicon Agent
	SYNTAX  DisplayString (SIZE(0..16))
	ACCESS  read-only 
	STATUS  mandatory
	DESCRIPTION     
		"The version of the CPU,  e.g. 386 "
	::= { server 8 }

srvCpuSpeed             OBJECT-TYPE     -- Not supported by Eicon Agent
	SYNTAX  PositiveInteger
	ACCESS  read-only 
	STATUS  mandatory
	DESCRIPTION     
		"The CPU speed in MGHz."
	::= { server 9 }

srvStdMemory            OBJECT-TYPE     -- Not supported by Eicon Agent
	SYNTAX  PositiveInteger
	ACCESS  read-only 
	STATUS  mandatory
	DESCRIPTION     
		"The standard memory (in Kilo Bytes)"
	::= { server 10 }

srvExtendMemory OBJECT-TYPE     -- Not supported by Eicon Agent
	SYNTAX  PositiveInteger
	ACCESS  read-only 
	STATUS  mandatory
	DESCRIPTION     
		"The extended memory (in Kilo Bytes)"
	::= { server 11 }

srvExpandedMemory       OBJECT-TYPE     -- Not supported by Eicon Agent
	SYNTAX  PositiveInteger
	ACCESS  read-only 
	STATUS  mandatory
	DESCRIPTION     
		"The expanded memory (in Kilo Bytes)"
	::= { server 12 }

srvVideoAdaptType       OBJECT-TYPE     -- Not supported by Eicon Agent
	SYNTAX  DisplayString (SIZE(0..16))
	ACCESS  read-only 
	STATUS  mandatory
	DESCRIPTION
		"The type of video adapter "
	::= { server 13 }

srvHardDisk             OBJECT-TYPE     -- Not supported by Eicon Agent
	SYNTAX  DisplayString (SIZE(0..16))
	ACCESS  read-only 
	STATUS  mandatory
	DESCRIPTION     
		"The name/type of hard disk"
	::= { server 14 }

srvHardDiskSize         OBJECT-TYPE     -- Not supported by Eicon Agent
	SYNTAX  INTEGER
	ACCESS  read-only 
	STATUS  mandatory
	DESCRIPTION     
		"The size in MB of the hard disk"
	::= { server 15 }

srvNotePad              OBJECT-TYPE
	SYNTAX  DisplayString (SIZE(0..512))
	ACCESS  read-write 
	STATUS  mandatory
	DESCRIPTION     
		"The string used by the Administrator for supplementary information about the Server. It 	
		will be stored by the Agent and retrived from the Agent."
	::= { server 16 }

srvAgentMajorVersion            OBJECT-TYPE
	SYNTAX  INTEGER (0..1000)
	ACCESS  read-only 
	STATUS  mandatory
	DESCRIPTION     
		"The major version of the agent. For exemple, version 3.01,
		 the major version is 3."
	::= { server 17 }

srvAgentMinorVersion            OBJECT-TYPE
	SYNTAX  INTEGER (0..1000)
	ACCESS  read-only 
	STATUS  mandatory
	DESCRIPTION     
		"The minor version of the agent. For exemple, version 3.01,
		 the minor version is 1."
	::= { server 18 }

--      The following variable is not instrumented in the current release of the Agent.
srvAgentMaxOfLostNMPHeartB      OBJECT-TYPE     -- Not supported by Eicon Agent
	SYNTAX  INTEGER
	ACCESS  read-write 
	STATUS  mandatory
	DESCRIPTION     
		"The threshold for the number of lost consecutive NMP heartbeat messages.   If the 	
		number of lost messsages is greater than srvAgentMaxOfLostNMPHeartB,  then Agent        
		will generate a Trap."
	::= { server 19 }

srvAgentHeartBeatPeriod         OBJECT-TYPE     -- Not supported by Eicon Agent
	SYNTAX  INTEGER (60..3600)
	ACCESS  read-write 
	STATUS  mandatory
	DESCRIPTION     
		"The period (in seconds) of the Trap with the server heartbeat message that the Agent 	
		will send to the NMC."
	::= { server 20 }

srvAgentPollFrequency           OBJECT-TYPE
	SYNTAX  INTEGER (60..3600)
	ACCESS  read-write 
	STATUS  mandatory
	DESCRIPTION     
		"The period (in seconds) for the poll request, issued by the agent
	to the server components, to detect state changes and send a trap."
	::= { server 21 }

srvAgentAlarmsFilterValue       OBJECT-TYPE
	SYNTAX  INTEGER
	ACCESS  read-write 
	STATUS  mandatory
	DESCRIPTION     
		"The threshold for the severity value of the alarms.  Agent uses 
		the filter for every Alarm before it is sent to the Manager."
	::= { server 22 }

srvDomainName           OBJECT-TYPE     -- Not supported by Eicon Agent
	SYNTAX  DisplayString (SIZE(0..48))
	ACCESS  read-write 
	STATUS  mandatory
	DESCRIPTION     
		"The name of the administrative/security domain of the Server.  Has to be known 	
		by ECLAN. ECLAN uses this value in the server advertising messages."
	::= { server 23 }

srvDomainConfigDir      OBJECT-TYPE
	SYNTAX  DisplayString (SIZE(0..256))
	ACCESS  read-write 
	STATUS  mandatory
	DESCRIPTION     
		"The path-name in the ESS server of the current default directory for
		all server configuration files. This variable could be set to a new 
		value through the SNMP NM Console before sending the request to the
		Agent to start the EiconCard, ECLAN or the SSM. The Agent will use it
		to find necessary configuration information."
	::= { server 24 }

srvNbOfLanCards OBJECT-TYPE
	SYNTAX  CardRef
	ACCESS  read-only
	STATUS  mandatory
	DESCRIPTION     
		"The number of installed LAN cards "
	::= { server 25 }

srvLanCardTable         OBJECT-TYPE
	SYNTAX  SEQUENCE OF SrvLanCardEntry
	ACCESS  not-accessible
	STATUS  mandatory
	DESCRIPTION
		"The table of local LAN cards."
	::= { server 26 }

srvLanCardEntry         OBJECT-TYPE
	SYNTAX  SrvLanCardEntry
	ACCESS  not-accessible
	STATUS  mandatory
	DESCRIPTION     
		"The information about one LAN card."
	INDEX           { srvLanCardIndex }
	::= { srvLanCardTable 1 }

SrvLanCardEntry ::= SEQUENCE {
	srvLanCardIndex
		CardRef,
	srvLanCardCFGMajorVer   
		INTEGER,
	srvLanCardCFGMinorVer   
		INTEGER,
	srvLanCardNodeAddr
		DisplayString,
	srvLanCardMaxSize
		INTEGER,
	srvLanCardName
		DisplayString,
	srvLanCardShortName     
		DisplayString,
	srvLanCardFrameType     
		DisplayString,
	srvLanCardDrvMajorVer   
		INTEGER,
	srvLanCardDrvMinorVer
		INTEGER,
	srvLanCardMemoryAddr
		INTEGER,
	srvLanCardInterrupt
		INTEGER,
	srvLanCardDMAUsage
		INTEGER
	}

srvLanCardIndex         OBJECT-TYPE
	SYNTAX  CardRef
	ACCESS  read-only
	STATUS  mandatory
	DESCRIPTION     
		"LAN card reference number. "
	::= { srvLanCardEntry 1 }

srvLanCardCFGMajorVer   OBJECT-TYPE
	SYNTAX  INTEGER
	ACCESS  read-only 
	STATUS  mandatory
	DESCRIPTION
		"LAN CFG Major Version.
		This Field is defined by Novell and contains the major version
		number of the configuration table. In the version number
		1.0, 1 is the major version number."   
	::= { srvLanCardEntry 2 }

srvLanCardCFGMinorVer   OBJECT-TYPE
	SYNTAX  INTEGER
	ACCESS  read-only 
	STATUS  mandatory
	DESCRIPTION
		"LAN CFG Minor Version.
		This Field is defined by Novell and contains the minor version
		number of the configuration table. In the version number
		1.0, 0 is the minor version number."   
	::= { srvLanCardEntry 3 }

srvLanCardNodeAddr      OBJECT-TYPE
	SYNTAX  DisplayString (SIZE(0..80))
	ACCESS  read-only 
	STATUS  mandatory
	DESCRIPTION
		" Lan Card Node Address.
		  This Field contains the node address of LAN Board."
	::= { srvLanCardEntry 4 }

srvLanCardMaxSize       OBJECT-TYPE
	SYNTAX  INTEGER
	ACCESS  read-only 
	STATUS  mandatory
	DESCRIPTION     
		"This field contains the maximum send or receive packet
		 size (in bytes) that the LAN board can transmit or receive." 
	::= { srvLanCardEntry 5 }

srvLanCardName  OBJECT-TYPE
	SYNTAX  DisplayString (SIZE(0..80))
	ACCESS  read-only 
	STATUS  mandatory
	DESCRIPTION     
		"Lan Card Name.
		 This field contains a pointer to a byte-length proceded,
		 zero-terminated ASCII description string that is
		 contained in the OSDATA segment and is similar to the 
		 description string in the definition table. For example:
		 NE2000 ETHERNET Driver." 
	::= { srvLanCardEntry 6 }

srvLanCardShortName     OBJECT-TYPE
	SYNTAX  DisplayString (SIZE(0..80))
	ACCESS  read-only 
	STATUS  mandatory
	DESCRIPTION     
		"This field contains a pointer to a string that describes
		 the LAN board in eight bytes or less such as NE2000."
	::= { srvLanCardEntry 7 }

srvLanCardFrameType     OBJECT-TYPE
	SYNTAX  DisplayString (SIZE(0..80))
	ACCESS  read-only 
	STATUS  mandatory
	DESCRIPTION     
		" This field contains a pointer to a string that describes
		  the MLID's frame type. Examples include ETHERNET_802.3
		  and ETHERNET_II. The Independent Manufactuer Support
		  Program (IMSP) assigns strings for the Frame Type. This
		  String is case sensitive, and is a byte length-preceded,
		  zero-terminated ASCII string. "
	::= { srvLanCardEntry 8 }

srvLanCardDrvMajorVer   OBJECT-TYPE
	SYNTAX  INTEGER
	ACCESS  read-only 
	STATUS  mandatory
	DESCRIPTION     
		" This field contain the major version number of the MLID."
	::= { srvLanCardEntry 9 }

srvLanCardDrvMinorVer   OBJECT-TYPE
	SYNTAX  INTEGER
	ACCESS  read-only 
	STATUS  mandatory
	DESCRIPTION     
		" This field contain the minor version number of the MLID."
	::= { srvLanCardEntry 10 }

srvLanCardMemoryAddr    OBJECT-TYPE
	SYNTAX  INTEGER
	ACCESS  read-only
	STATUS  mandatory
	DESCRIPTION
		" This field contains the absolute primary memory address
		  the LAN board used. If not used, this field is set to 0."
	::= { srvLanCardEntry 11 }

srvLanCardInterrupt    OBJECT-TYPE
	SYNTAX  INTEGER
	ACCESS  read-only
	STATUS  mandatory
	DESCRIPTION
		" This field contains the primary interrupt vector
		  number. FFh = not used."
	::= { srvLanCardEntry 12 }

srvLanCardDMAUsage    OBJECT-TYPE
	SYNTAX  INTEGER
	ACCESS  read-only
	STATUS  mandatory
	DESCRIPTION
		" This field contains the primary DMA channel used by
		  the LAN board. FFh = not used."
	::= { srvLanCardEntry 13 }

srvNbOfSoftPackage      OBJECT-TYPE
	SYNTAX  PositiveInteger
	ACCESS  read-only 
	STATUS  mandatory
	DESCRIPTION     
		"The number of entries in the srvSoftPackageTable."
	::= { server 27 }

srvSoftPackageTable     OBJECT-TYPE
	SYNTAX  SEQUENCE OF SrvPackageEntry
	ACCESS  not-accessible
	STATUS  mandatory
	DESCRIPTION
		"The information about the Eicon software installed in the server."
	::= { server 28 }

srvPackageEntry         OBJECT-TYPE
	SYNTAX  SrvPackageEntry
	ACCESS  not-accessible
	STATUS  mandatory
	DESCRIPTION     
		"The information about Eicon's products in the server."
	INDEX           { srvProductIndex }
	::= { srvSoftPackageTable 1 }

SrvPackageEntry ::= SEQUENCE {
	srvProductIndex
	   PositiveInteger,
	srvProductName 
		DisplayString,
	srvProductVersion 
		DisplayString,
	srvProductDate  
		DisplayString,
	srvProductConfigured
		INTEGER 
	}

srvProductIndex         OBJECT-TYPE
	SYNTAX  PositiveInteger
	ACCESS  read-only 
	STATUS  mandatory
	DESCRIPTION     
		"The product reference number"
	::= { srvPackageEntry 1 }

srvProductName          OBJECT-TYPE
	SYNTAX  DisplayString (SIZE(0..16))
	ACCESS  read-only 
	STATUS  mandatory
	DESCRIPTION     
		"The name of the product."
	::= { srvPackageEntry 2 }

srvProductVersion       OBJECT-TYPE
	SYNTAX  DisplayString (SIZE(0..16))
	ACCESS  read-only 
	STATUS  mandatory
	DESCRIPTION     
		"The version of the (Eicon) product."
	::= { srvPackageEntry 3 }

srvProductDate  OBJECT-TYPE
	SYNTAX  DisplayString (SIZE(0..32))
	ACCESS  read-only 
	STATUS  mandatory
	DESCRIPTION
		"The installation date and time of the product."
	::= { srvPackageEntry 4 }
 
srvProductConfigured    OBJECT-TYPE
	SYNTAX   INTEGER {
				yes (1),
				no (2)
				}
	ACCESS  read-only 
	STATUS  mandatory
	DESCRIPTION
		"If the value is yes, the product is configured. If the value is no,
		 the product is installed, but not configured."
	::= { srvPackageEntry 5 }
 
--      The following  object and table contain the server hardware configuration information (cards) which
--      are taken from the current configuration file. The management station can use this information to
--      compare with the actual state of the cards in the server.

srvCfgNbOfEiconCards    OBJECT-TYPE     -- Not supported by Eicon Agent
	SYNTAX  CardRef
	ACCESS  read-only
	STATUS  mandatory
	DESCRIPTION     
		"The number of configured EiconCards (from the current configuration)"
	::= { server 29 }

srvCfgEiconCardTable    OBJECT-TYPE     -- Not supported by Eicon Agent
	SYNTAX  SEQUENCE OF SrvCfgEiconCardEntry
	ACCESS  not-accessible
	STATUS  mandatory
	DESCRIPTION
		"The table of configuration information of EiconCards  (from the current configuration."
	::= { server 30 }

srvCfgEiconCardEntry    OBJECT-TYPE
	SYNTAX  SrvCfgEiconCardEntry
	ACCESS  not-accessible
	STATUS  mandatory
	DESCRIPTION
		"The configuration information about one EiconCard."
	INDEX           { srvCfgECIndex }
	::= { srvCfgEiconCardTable 1 }

SrvCfgEiconCardEntry ::= SEQUENCE {
	srvCfgECIndex
		CardRef,
--      srvCfgECType
--              EiconCardType,
	srvCfgECMemAddr
		INTEGER,
	srvCfgECIoAddr
		INTEGER,
	srvCfgECIntrLevel
		INTEGER,
	srvCfgECNbOfPorts
		PortRef,
	srvCfgECSlotNumber
		INTEGER,
	srvCfgECOptModule
		INTEGER,
	srvCfgECAutoActivate
		INTEGER
	}

srvCfgECIndex           OBJECT-TYPE
	SYNTAX  CardRef
	ACCESS  read-only 
	STATUS  mandatory
	DESCRIPTION     
		"The Id of the EiconCard."
	::= { srvCfgEiconCardEntry 1 }

srvCfgECMemAddr OBJECT-TYPE
	SYNTAX  INTEGER
	ACCESS  read-only 
	STATUS  mandatory
	DESCRIPTION     
		"The EiconCard memory segment address."
	::= { srvCfgEiconCardEntry 2 }

srvCfgECIoAddr          OBJECT-TYPE
	SYNTAX  INTEGER
	ACCESS  read-only 
	STATUS  mandatory
	DESCRIPTION     
		"The EiconCard IO address."
	::= { srvCfgEiconCardEntry 3 }

srvCfgECIntrLevel       OBJECT-TYPE
	SYNTAX  INTEGER
	ACCESS  read-only 
	STATUS  mandatory
	DESCRIPTION     
		"The EiconCard interrupt level."
	::= { srvCfgEiconCardEntry 4 }

srvCfgECNbOfPorts       OBJECT-TYPE
	SYNTAX  PortRef
	ACCESS  read-only 
	STATUS  mandatory
	DESCRIPTION     
		"The number of ports."
	::= { srvCfgEiconCardEntry 5 }

srvCfgECSlotNumber      OBJECT-TYPE
	SYNTAX  INTEGER (1..8)
	ACCESS  read-only 
	STATUS  mandatory
	DESCRIPTION     
		"The slot number for MicroChannel."
	::= { srvCfgEiconCardEntry 6 }

srvCfgECOptModule       OBJECT-TYPE
	SYNTAX  INTEGER {
		mod-DPSM (1),
		mod-HSIM (2),
		mod-None (3)
		}
	ACCESS  read-only 
	STATUS  mandatory
	DESCRIPTION     
		"The optional module for the MPNA card."
	::= { srvCfgEiconCardEntry 7 }

srvCfgECAutoActivate    OBJECT-TYPE
	SYNTAX  INTEGER {
		yes (1),
		no (2)
		}
	ACCESS  read-only 
	STATUS  mandatory
	DESCRIPTION     
		"The auto activation of the X.25 ports when the card starts."
	::= { srvCfgEiconCardEntry 8 }

--      The following  object and table contain the server hardware configuration information (ports) which
--      are taken from the current configuration file.  The management station can use this information to
--      compare with the actual state of the server ports.

srvCfgNbOfPorts         OBJECT-TYPE     -- Not supported by Eicon Agent
	SYNTAX  PortRef
	ACCESS  read-only
	STATUS  mandatory
	DESCRIPTION     
		"The number of configured ports for all EiconCards (from the current configuration)"
	::= { server 31 }

srvCfgPortTable         OBJECT-TYPE     -- Not supported by Eicon Agent
	SYNTAX  SEQUENCE OF SrvCfgPortEntry
	ACCESS  not-accessible
	STATUS  mandatory
	DESCRIPTION
		"The table of configuration information of ports, from the current configuration."
	::= { server 32 }

srvCfgPortEntry OBJECT-TYPE
	SYNTAX  SrvCfgPortEntry
	ACCESS  not-accessible
	STATUS  mandatory
	DESCRIPTION
		"The configuration information about one port."
	INDEX           { srvCfgPortIndex }
	::= { srvCfgPortTable 1 }

SrvCfgPortEntry ::= SEQUENCE {
	srvCfgPortIndex
		PortRef,
	srvCfgPortLanaNo
		PortRef,
	srvCfgPortName
		PortName
	}

srvCfgPortIndex         OBJECT-TYPE
	SYNTAX  PortRef
	ACCESS  read-only 
	STATUS  mandatory
	DESCRIPTION     
		"The index of the port generated by the Agent."
	::= { srvCfgPortEntry 1 }

srvCfgPortLanaNo        OBJECT-TYPE
	SYNTAX  PortRef
	ACCESS  read-only 
	STATUS  mandatory
	DESCRIPTION     
		"The LANA number of the port from the configuration, range: 1..48."
	::= { srvCfgPortEntry 2 }

srvCfgPortName          OBJECT-TYPE
	SYNTAX  PortName
	ACCESS  read-only 
	STATUS  mandatory
	DESCRIPTION     
		"The unique port name."
	::= { srvCfgPortEntry 3 }

srvDescr OBJECT-TYPE
	SYNTAX  DisplayString (SIZE (0..255))
	ACCESS  read-only
	STATUS  mandatory
	DESCRIPTION
		      "A textual description of the entity.  This value
		      should include the full name and version
		      identification of the system's hardware type,
		      software operating-system, and networking
		      software.  It is mandatory that this only contain
		      printable ASCII characters."
	::= { server 33 }

srvObjectID OBJECT-TYPE
	SYNTAX  OBJECT IDENTIFIER
	ACCESS  read-only
	STATUS  mandatory
	DESCRIPTION
		      "The vendor's authoritative identification of the
		      network management subsystem contained in the
		      entity.  This value is allocated within the SMI
		      enterprises subtree (1.3.6.1.4.1) and provides an
		      easy and unambiguous means for determining `what
		      kind of box' is being managed.  For example, if
		      vendor `Flintstones, Inc.' was assigned the
		      subtree 1.3.6.1.4.1.4242, it could assign the
		      identifier 1.3.6.1.4.1.4242.1.1 to its `Fred
		      Router'."
	::= { server 34 }

srvUpTime OBJECT-TYPE
	SYNTAX  TimeTicks
	ACCESS  read-only
	STATUS  mandatory
	DESCRIPTION
		      "The time (in hundredths of a second) since the
		      network management portion of the system was last
		      re-initialized."
	::= { server 35 }

srvContact OBJECT-TYPE
	SYNTAX  DisplayString (SIZE (0..255))
	ACCESS  read-write
	STATUS  mandatory
	DESCRIPTION
		     "The textual identification of the contact person
		      for this managed node, together with information
		      on how to contact this person."
	::= { server 36 }

  srvName OBJECT-TYPE
	SYNTAX  DisplayString (SIZE (0..255))
	ACCESS  read-write
	STATUS  mandatory
	DESCRIPTION
		      "An administratively-assigned name for this
		      managed node.  By convention, this is the node's
		      fully-qualified domain name."
	::= { server 37 }

srvLocation OBJECT-TYPE
	SYNTAX  DisplayString (SIZE (0..255))
	ACCESS  read-write
	STATUS  mandatory
	DESCRIPTION
		      "The physical location of this node (e.g.,
		      `telephone closet, 3rd floor')."
	::= { server 38 }

srvServices OBJECT-TYPE
	SYNTAX  INTEGER (0..127)
	ACCESS  read-only
	STATUS  mandatory
	DESCRIPTION
		      "A value which indicates the set of services that
		      this entity offers primarily.

		      The value is a sum.  This sum initially takes the
		      value zero, Then, for each layer, L, in the range
		      1 through 7, that this node performs transactions
		      for, 2 raised to (L - 1) is added to the sum.  For
		      example, a node which performs primarily routing
		      functions would have a value of 4 (2^(3-1)).  In
		      contrast, a node which is a host offering
		      application services would have a value of 72
		      (2^(4-1) + 2^(7-1)).  Note that in the context of
		      the Internet suite of protocols, values should be
		      calculated accordingly:

			   layer  functionality
			       1  physical (e.g., repeaters)
			       2  datalink/subnetwork (e.g., bridges)
			       3  internet (e.g., IP gateways)
			       4  end-to-end  (e.g., IP hosts)
			       7  applications (e.g., mail relays)

		      For systems including OSI protocols, layers 5 and
		      6 may also be counted."
	::= { server 39 }

srvIfNumber OBJECT-TYPE
	      SYNTAX  INTEGER
	      ACCESS  read-only
	      STATUS  mandatory
	      DESCRIPTION
		      "The number of network interfaces (regardless of
		      their current state) present on this system."
	      ::= { server 40 }


	  -- the Interfaces table

	  -- The Interfaces table contains information on the entity's
	  -- interfaces.  Each interface is thought of as being
	  -- attached to a `subnetwork'.  Note that this term should
	  -- not be confused with `subnet' which refers to an
	  -- addressing partitioning scheme used in the Internet suite
	  -- of protocols.

srvIfTable OBJECT-TYPE
	      SYNTAX  SEQUENCE OF SrvIfEntry
	      ACCESS  not-accessible
	      STATUS  mandatory
	      DESCRIPTION
		      "A list of interface entries.  The number of
		      entries is given by the value of ifNumber."
	      ::= { server 41 }

srvIfEntry OBJECT-TYPE
	      SYNTAX  SrvIfEntry
	      ACCESS  not-accessible
	      STATUS  mandatory
	      DESCRIPTION
		      "An interface entry containing objects at the
		      subnetwork layer and below for a particular
		      interface."
	      INDEX   { srvIfIndex }
	      ::= { srvIfTable 1 }

SrvIfEntry ::=
	      SEQUENCE {
		  srvIfIndex
		      INTEGER,
		  srvIfDescr
		      DisplayString,
		  srvIfType
		      INTEGER,
		  srvIfMtu
		      INTEGER,
		  srvIfSpeed
		      Gauge,
		  srvIfPhysAddress
		      PhysAddress,
		  srvIfAdminStatus
		      INTEGER,
		  srvIfOperStatus
		      INTEGER,
		  srvIfLastChange
		      TimeTicks,
		  srvIfInOctets
		      Counter,
		  srvIfInUcastPkts
		      Counter,
		  srvIfInNUcastPkts
		      Counter,
		  srvIfInDiscards
		      Counter,
		  srvIfInErrors
		      Counter,
		  srvIfInUnknownProtos
		      Counter,
		  srvIfOutOctets
		      Counter,
		  srvIfOutUcastPkts
		      Counter,
		  srvIfOutNUcastPkts
		      Counter,
		  srvIfOutDiscards
		      Counter,
		  srvIfOutErrors
		      Counter,
		  srvIfOutQLen
		      Gauge,
		  srvIfSpecific
		      INTEGER
	      }

	  srvIfIndex OBJECT-TYPE
	      SYNTAX  INTEGER
	      ACCESS  read-only
	      STATUS  mandatory
	      DESCRIPTION
		      "A unique value for each interface.  Its value
		      ranges between 1 and the value of srvIfNumber.  The
		      value for each interface must remain constant at
		      least from one re-initialization of the entity's
		      network management system to the next re-initialization."
	      ::= { srvIfEntry 1 }

srvIfDescr OBJECT-TYPE
	      SYNTAX  DisplayString (SIZE (0..255))
	      ACCESS  read-only
	      STATUS  mandatory
	      DESCRIPTION
		      "A textual string containing information about the
		      interface.  This string should include the name of
		      the manufacturer, the product name and the version
		      of the hardware interface."
	      ::= { srvIfEntry 2 }

srvIfType OBJECT-TYPE
	      SYNTAX  INTEGER {
			  other(1),          -- none of the following
			  regular1822(2),
			  hdh1822(3),
			  ddn-x25(4),
			  rfc877-x25(5),
			  ethernet-csmacd(6),
			  iso88023-csmacd(7),
			  iso88024-tokenBus(8),
			  iso88025-tokenRing(9),
			  iso88026-man(10),
			  starLan(11),
			  proteon-10Mbit(12),
			  proteon-80Mbit(13),
			  hyperchannel(14),
			  fddi(15),
			  lapb(16),
			  sdlc(17),
			  ds1(18),           -- T-1
			  e1(19),            -- european equiv. of T-1
			  basicISDN(20),
			  primaryISDN(21),   -- proprietary serial
			  propPointToPointSerial(22),
			  ppp(23),
			  softwareLoopback(24),
			  eon(25),            -- CLNP over IP [11]
			  ethernet-3Mbit(26),
			  nsip(27),           -- XNS over IP
			  slip(28),           -- generic SLIP
			  ultra(29),          -- ULTRA technologies
			  ds3(30),            -- T-3
			  sip(31),            -- SMDS
			  frame-relay(32),
			  appc(33),
			  snafm(34),
			  snapc(35),
			  xport-iso(36),
			  xport-tgx(37),
			  netview(38),
			  llc(39),
			  snafr(40)
		      }
	      ACCESS  read-only
	      STATUS  mandatory
	      DESCRIPTION
		      "The type of interface, distinguished according to
		      the physical/link protocol(s) immediately `below'
		      the network layer in the protocol stack."
	      ::= { srvIfEntry 3 }

srvIfMtu OBJECT-TYPE
	      SYNTAX  INTEGER
	      ACCESS  read-only
	      STATUS  mandatory
	      DESCRIPTION
		      "The size of the largest datagram which can be
		      sent/received on the interface, specified in
		      octets.  For interfaces that are used for
		      transmitting network datagrams, this is the size
		      of the largest network datagram that can be sent
		      on the interface."
	      ::= { srvIfEntry 4 }

srvIfSpeed OBJECT-TYPE
	      SYNTAX  Gauge
	      ACCESS  read-only
	      STATUS  mandatory
	      DESCRIPTION
		      "An estimate of the interface's current bandwidth
		      in bits per second.  For interfaces which do not
		      vary in bandwidth or for those where no accurate
		      estimation can be made, this object should contain
		      the nominal bandwidth."
	      ::= { srvIfEntry 5 }

srvIfPhysAddress OBJECT-TYPE
	      SYNTAX  PhysAddress
	      ACCESS  read-only
	      STATUS  mandatory
	      DESCRIPTION
		      "The interface's address at the protocol layer
		      immediately `below' the network layer in the
		      protocol stack.  For interfaces which do not have
		      such an address (e.g., a serial line), this object
		      should contain an octet string of zero length."
	      ::= { srvIfEntry 6 }

srvIfAdminStatus OBJECT-TYPE
	      SYNTAX  INTEGER {
			  up(1),       -- ready to pass packets
			  down(2),
			  testing(3)   -- in a test mode
		      }
	      ACCESS  read-write
	      STATUS  mandatory
	      DESCRIPTION
		      "The desired state of the interface.  The
		      testing(3) state indicates that no operational
		      packets can be passed."
	      ::= { srvIfEntry 7 }

srvIfOperStatus OBJECT-TYPE
	      SYNTAX  INTEGER {
			  up(1),       -- ready to pass packets
			  down(2),
			  testing(3)   -- in a test mode
		      }
	      ACCESS  read-only
	      STATUS  mandatory
	      DESCRIPTION
		      "The current operational state of the interface.
		      The testing(3) state indicates that no operational
		      packets can be passed."
	      ::= { srvIfEntry 8 }

srvIfLastChange OBJECT-TYPE
	      SYNTAX  TimeTicks
	      ACCESS  read-only
	      STATUS  mandatory
	      DESCRIPTION
		      "The value of sysUpTime at the time the interface
		      entered its current operational state.  If the
		      current state was entered prior to the last 
		      re-initialization of the local network management
		      subsystem, then this object contains a zero
		      value."
	      ::= { srvIfEntry 9 }

srvIfInOctets OBJECT-TYPE
	      SYNTAX  Counter
	      ACCESS  read-only
	      STATUS  mandatory
	      DESCRIPTION
		      "The total number of octets received on the
		      interface, including framing characters."
	      ::= { srvIfEntry 10 }

srvIfInUcastPkts OBJECT-TYPE
	      SYNTAX  Counter
	      ACCESS  read-only
	      STATUS  mandatory
	      DESCRIPTION
		      "The number of subnetwork-unicast packets
		      delivered to a higher-layer protocol."
	      ::= { srvIfEntry 11 }

srvIfInNUcastPkts OBJECT-TYPE
	      SYNTAX  Counter
	      ACCESS  read-only
	      STATUS  mandatory
	      DESCRIPTION
		      "The number of non-unicast (i.e., subnetwork-
		      broadcast or subnetwork-multicast) packets
		      delivered to a higher-layer protocol."
	      ::= { srvIfEntry 12 }

srvIfInDiscards OBJECT-TYPE
	      SYNTAX  Counter
	      ACCESS  read-only
	      STATUS  mandatory
	      DESCRIPTION
		      "The number of inbound packets which were chosen
		      to be discarded even though no errors had been
		      detected to prevent their being deliverable to a
		      higher-layer protocol.  One possible reason for
		      discarding such a packet could be to free up
		      buffer space."
	      ::= { srvIfEntry 13 }

srvIfInErrors OBJECT-TYPE
	      SYNTAX  Counter
	      ACCESS  read-only
	      STATUS  mandatory
	      DESCRIPTION
		      "The number of inbound packets that contained
		      errors preventing them from being deliverable to a
		      higher-layer protocol."
	      ::= { srvIfEntry 14 }

srvIfInUnknownProtos OBJECT-TYPE
	      SYNTAX  Counter
	      ACCESS  read-only
	      STATUS  mandatory
	      DESCRIPTION
		      "The number of packets received via the interface
		      which were discarded because of an unknown or
		      unsupported protocol."
	      ::= { srvIfEntry 15 }

srvIfOutOctets OBJECT-TYPE
	      SYNTAX  Counter
	      ACCESS  read-only
	      STATUS  mandatory
	      DESCRIPTION
		      "The total number of octets transmitted out of the
		      interface, including framing characters."
	      ::= { srvIfEntry 16 }

srvIfOutUcastPkts OBJECT-TYPE
	      SYNTAX  Counter
	      ACCESS  read-only
	      STATUS  mandatory
	      DESCRIPTION
		      "The total number of packets that higher-level
		      protocols requested be transmitted to a
		      subnetwork-unicast address, including those that
		      were discarded or not sent."
	      ::= { srvIfEntry 17 }

srvIfOutNUcastPkts OBJECT-TYPE
	      SYNTAX  Counter
	      ACCESS  read-only
	      STATUS  mandatory
	      DESCRIPTION
		      "The total number of packets that higher-level
		      protocols requested be transmitted to a non-
		      unicast (i.e., a subnetwork-broadcast or
		      subnetwork-multicast) address, including those
		      that were discarded or not sent."
	      ::= { srvIfEntry 18 }

srvIfOutDiscards OBJECT-TYPE
	      SYNTAX  Counter
	      ACCESS  read-only
	      STATUS  mandatory
	      DESCRIPTION
		      "The number of outbound packets which were chosen
		      to be discarded even though no errors had been
		      detected to prevent them from being transmitted.  One
		      possible reason for discarding such a packet could
		      be to free up buffer space."
	      ::= { srvIfEntry 19 }

srvIfOutErrors OBJECT-TYPE
	      SYNTAX  Counter
	      ACCESS  read-only
	      STATUS  mandatory
	      DESCRIPTION
		      "The number of outbound packets that could not be
		      transmitted because of errors."
	      ::= { srvIfEntry 20 }

srvIfOutQLen OBJECT-TYPE
	      SYNTAX  Gauge
	      ACCESS  read-only
	      STATUS  mandatory
	      DESCRIPTION
		      "The length of the output packet queue (in
		      packets)."
	      ::= { srvIfEntry 21 }

srvIfSpecific OBJECT-TYPE
	      SYNTAX  INTEGER
	      ACCESS  read-only
	      STATUS  mandatory
	      DESCRIPTION
		      "A reference to MIB definitions specific to the
		      particular media being used to realize the
		      interface.  For example, if the interface is
		      realized by an ethernet, then the value of this
		      object refers to a document defining objects
		      specific to ethernet.  If this information is not
		      present, its value should be set to the OBJECT
		      IDENTIFIER { 0 0 }, which is a syntatically valid
		      object identifier, and any conformant
		      implementation of ASN.1 and BER must be able to
		      generate and recognize this value."
	      ::= { srvIfEntry 22 }


srvModulesOperStates     OBJECT-TYPE
	SYNTAX  OCTET STRING (SIZE(0..20))
	ACCESS  read-only
	STATUS  mandatory
	DESCRIPTION
		"This is an array of Operation States for the Eicon modules
		running on the gateway. Each entry will have the syntax
		OperState.
			Array Index
			    0           Server state (Always active)
			    1           EcAppc state
			    2           SSM state
			    3           Router state
			    4           EcPad state
			    5           EcSwitch state
			    6           SLC state
			    7           HPRINT state
			    8           ECLan State

		A value of 0 in these positions means the specific module
	is not loaded."
	      ::= { server 42 }

srvInstallDirName  OBJECT-TYPE
	SYNTAX  DisplayString (SIZE(0..50))
	ACCESS  read-only
	STATUS  mandatory
	DESCRIPTION
		"This is the directory where Eicon's products are installed."
	::= { server 43 }

srvCurrDirName  OBJECT-TYPE
	SYNTAX  DisplayString (SIZE(0..50))
	ACCESS  read-write
	STATUS  mandatory
	DESCRIPTION
		"The entries in srvDirTable are the contents of this
		directory."
	::= { server 44 }

srvDirTable OBJECT-TYPE
	      SYNTAX  SEQUENCE OF SrvDirEntry
	      ACCESS  not-accessible
	      STATUS  mandatory
	      DESCRIPTION
		      "A list of entries for the directory specified in
		srvCurrDirname."
	      ::= { server 45 }

srvDirEntry OBJECT-TYPE
	      SYNTAX  SrvDirEntry
	      ACCESS  not-accessible
	      STATUS  mandatory
	      DESCRIPTION
		      "An directory entry containing the names of files."
	      INDEX   { srvIfIndex }
	      ::= { srvDirTable 1 }

SrvDirEntry ::=
	      SEQUENCE {
		  srvDirIndex
		      INTEGER,
		  srvDirFilename
		      DisplayString,
		  srvDirFileAttribute
		      INTEGER,
		  srvDirFileAccessTime
		      INTEGER,
		  srvDirFileSize
		      INTEGER
		}

srvDirIndex OBJECT-TYPE
	SYNTAX  INTEGER
	ACCESS  read-only
	STATUS  mandatory
	DESCRIPTION
		" The index assigned by the Agent."
	::= { srvDirEntry 1 }

srvDirFilename OBJECT-TYPE
	SYNTAX  DisplayString (SIZE (1..32))
	ACCESS  read-only
	STATUS  mandatory
	DESCRIPTION
		"The file name. "
	::= { srvDirEntry 2 }

srvDirFileAttribute OBJECT-TYPE
	SYNTAX  INTEGER
	ACCESS  read-only
	STATUS  mandatory
	DESCRIPTION
		"The attributes of the file.
			0x0     - Normal
			0x1     - ReadOnly
			0x2     - Hidden
			0x4     - System
			0x10    - Subdirectory
			0x20    - Archive
			0x80    - Share."
	::= { srvDirEntry 3 }

srvDirFileAccessTime OBJECT-TYPE
	SYNTAX  INTEGER
	ACCESS  read-only
	STATUS  mandatory
	DESCRIPTION
		"The time the file is accessed expressed in seconds since 
		Jan 01 1970."
	::= { srvDirEntry 4 }

srvDirFileSize OBJECT-TYPE
	SYNTAX  INTEGER
	ACCESS  read-only
	STATUS  mandatory
	DESCRIPTION
		"The file size in bytes."
	::= { srvDirEntry 5 }

srvTrapHeartbeat                TRAP-TYPE       -- Not supported by Eicon Agent
	ENTERPRISE      eicon
	VARIABLES       { sysName }
	DESCRIPTION
		"The srvTrapHeartbeat trap indicates that the server is still
		active."
	::=  11

srvTrapInternal         TRAP-TYPE
	ENTERPRISE      eicon
	VARIABLES       { sysName }
	DESCRIPTION
		"The generic Internal trap indicates that the Agent
		detected an internal error."
	::=  12


END
