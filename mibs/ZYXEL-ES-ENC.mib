-- **********************************************
-- ZyXEL Communications Corporation
--
-- Enterprise Solution MIB definitions
-- RF MANAGEMENT MIBs
--
-- Copyright by ZyXEL Communications Corp.
-- All rights reserved.
-- **********************************************

ZYXEL-ES-ENC DEFINITIONS ::= BEGIN

IMPORTS

    MODULE-IDENTITY,
    OBJECT-IDENTITY,
    OBJECT-TYPE, IpAddress         FROM SNMPv2-SMI

    OBJECT-GROUP,
    MODULE-COMPLIANCE   FROM SNMPv2-CONF

    esMgmt              FROM ZYXEL-ES-SMI;


--
-- Node: esENC
--

esENC MODULE-IDENTITY
    LAST-UPDATED        "201101310000Z"
    ORGANIZATION    "Enterprise Solution ZyXEL"
    CONTACT-INFO        ""
    DESCRIPTION
        "The sub tree for ENC feature"
    ::= { esMgmt 7 }

enCSrvIPAddr OBJECT-TYPE
    SYNTAX IpAddress
    MAX-ACCESS  read-write
    STATUS      current
    DESCRIPTION
        "ENC Server IP address."
    ::= { esENC 1 }

END
