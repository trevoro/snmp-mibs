--

-- Copyright (c) 1993 Chipcom Corporation.  All Rights Reserved.
--
-- Reproduction of this document is authorized on condition that this
-- copyright notice is included.  This SNMP MIB Specification
-- embodies proprietary intellectual property.  The copyright
-- retains all title and ownership in the specification, including any
-- revisions. 
--
-- It is the intent to encourage the widespread use of this
-- specification in connection with the management of our
-- products. The copyright grants vendor, end-users, and other interested
-- parties a non-exclusive license to use this specification in
-- connection with the management of our products.
--
-- This specification is supplied "AS IS," and no
-- warranty, either express or implied, as to the use, operation,
-- condition, or performance of the specification, is made.
--
-- Copyright text courtesy of Dave Perkins.
--
-- The right to change this MIB without notification is retained.
--


--
-- If you have any questions about this MIB, please call your
-- Technical Support Center, or call 1-800-228-6840.
--

--
-- MIB Version Information:
--
-- Version     Description
------------------------------------------------------------------
--   v1.0      Initial version of the chipmib02 branch.
--   v2.0      Version tracking initiated.
--   v2.1      Version release with TRMM v.2.10
--
-- 

--
-- Agents supporting this MIB:
--	Ethernet Management Module, Software rev: v3.2
--	Ethernet to Ethernet Bridge Module, Software Rev: v2.12
--	Ethernet to Ethernet Bridge Box, Software Rev: v2.12
--	Token Ring Management Module, Software Rev: v2.1
--	Ethernet Interconnect Module, Software Rev: v1.0
--


CHIPTRNET-MIB DEFINITIONS ::= BEGIN

IMPORTS
	enterprises, NetworkAddress, IpAddress,
	Counter, Gauge, TimeTicks, DisplayString
		FROM RFC1155-SMI
	OBJECT-TYPE
		FROM RFC-1212;
-- All representations of MAC addresses in this MIB Module use,
-- as a textual convention (i.e. this convention does not affect
-- their encoding), the data type:

MacAddress ::= OCTET STRING (SIZE (6))    -- a 6 octet address in
                                          -- the "canonical" order
-- defined by IEEE 802.1a, i.e., as if it were transmitted least
-- significant bit first, even though 802.5 (in contrast to other
-- 802.x protocols) requires MAC addresses to be transmitted most
-- significant bit first.
--
-- 16-bit addresses, if needed, are represented by setting their
-- upper 4 octets to all 0's, i.e., AAFF would be represented
-- as 00000000AAFF.

chipcom     	OBJECT IDENTIFIER ::= { enterprises 49 }

chipmib02 	OBJECT IDENTIFIER ::= { chipcom 2 }

--
-- Top level groups
--

chipGen    	OBJECT IDENTIFIER ::= { chipmib02 1 }
chipEcho   	OBJECT IDENTIFIER ::= { chipmib02 2 }
chipProducts   	OBJECT IDENTIFIER ::= { chipmib02 3 }
chipExperiment  OBJECT IDENTIFIER ::= { chipmib02 4 }
chipTTY	        OBJECT IDENTIFIER ::= { chipmib02 5 }
chipTFTP	OBJECT IDENTIFIER ::= { chipmib02 6 }
chipDownload	OBJECT IDENTIFIER ::= { chipmib02 7 }


--
-- Product specific branches.  Also used for sysObjectID.
--

online        	OBJECT IDENTIFIER ::= { chipProducts 1 }
oebm 	      	OBJECT IDENTIFIER ::= { chipProducts 2 }

midnight      	OBJECT IDENTIFIER ::= { chipProducts 3 }
workGroupHub    OBJECT IDENTIFIER ::= { chipProducts 4 }

emm		OBJECT IDENTIFIER ::= { chipProducts 5 }
chipBridge	OBJECT IDENTIFIER ::= { chipProducts 6 }
trmm		OBJECT IDENTIFIER ::= { chipProducts 7 }
fmm		OBJECT IDENTIFIER ::= { chipProducts 8 }
focus1		OBJECT IDENTIFIER ::= { chipProducts 9 }
oeim    	OBJECT IDENTIFIER ::= { chipProducts 10 }





--
-- Experimental Branches
--
-- When RFCs are still in the experimental stage, the MIB
-- is incorporated under the enterprise experimental branch
-- so that changes in the experimental MIB do not affect
-- the released product.  
--
-- As the RFC becomes standard and support is provided by the agents,
-- the support under this branch will be moved to the appropriate
-- standard branch.  That is, the support under this branch
-- for the MIB in question will be removed.
--

chipExpTokenRing OBJECT IDENTIFIER ::= { chipExperiment 1 }
dot1dBridge	OBJECT IDENTIFIER ::= { chipExperiment 14 }

dot5		OBJECT IDENTIFIER ::= { chipExpTokenRing 1}

--
-- ONline Groups 
--

olAgents   	OBJECT IDENTIFIER ::= { online   1 }
olConc    	OBJECT IDENTIFIER ::= { online   2 }
olEnv     	OBJECT IDENTIFIER ::= { online   3 }
olModules 	OBJECT IDENTIFIER ::= { online   4 }
olNets   	OBJECT IDENTIFIER ::= { online   5 }
olGroups   	OBJECT IDENTIFIER ::= { online   6 }
olAlarm   	OBJECT IDENTIFIER ::= { online   7 }

--
-- Value added module attributes 
--

olSpecMods	OBJECT IDENTIFIER ::= { olModules 4 }

--
-- A node for each module type  :
--

ol50nnMCTL  	OBJECT IDENTIFIER ::= { olSpecMods 3 }
ol51nnMMGT  	OBJECT IDENTIFIER ::= { olSpecMods 4 }
ol51nnMFIB  	OBJECT IDENTIFIER ::= { olSpecMods 5 }
ol51nnMUTP  	OBJECT IDENTIFIER ::= { olSpecMods 6 }
ol51nnMTP   	OBJECT IDENTIFIER ::= { olSpecMods 7 }
ol51nnMBNC  	OBJECT IDENTIFIER ::= { olSpecMods 8 }
ol51nnBEE   	OBJECT IDENTIFIER ::= { olSpecMods 9 }
ol51nnRES   	OBJECT IDENTIFIER ::= { olSpecMods 10 }
ol51nnREE   	OBJECT IDENTIFIER ::= { olSpecMods 11 }
ol51nnMAUIF 	OBJECT IDENTIFIER ::= { olSpecMods 12 }
ol51nnMAUIM 	OBJECT IDENTIFIER ::= { olSpecMods 13 }
ol5208MTP   	OBJECT IDENTIFIER ::= { olSpecMods 14 }
ol51nnMFP   	OBJECT IDENTIFIER ::= { olSpecMods 15 }
ol51nnMFBP  	OBJECT IDENTIFIER ::= { olSpecMods 16 }
ol51nnMTPL  	OBJECT IDENTIFIER ::= { olSpecMods 17 }
ol51nnMTPPL 	OBJECT IDENTIFIER ::= { olSpecMods 18 }
ol52nnMTP   	OBJECT IDENTIFIER ::= { olSpecMods 19 }
ol52nnMFR   	OBJECT IDENTIFIER ::= { olSpecMods 20 }
ol51nnMTS   	OBJECT IDENTIFIER ::= { olSpecMods 21 }
ol51nnMFL   	OBJECT IDENTIFIER ::= { olSpecMods 22 }
ol50nnMRCTL 	OBJECT IDENTIFIER ::= { olSpecMods 23 }
ol51nnMFB   	OBJECT IDENTIFIER ::= { olSpecMods 24 }
ol53nnMMGT  	OBJECT IDENTIFIER ::= { olSpecMods 25 }
ol53nnMFBMIC	OBJECT IDENTIFIER ::= { olSpecMods 26 }
ol53nnMFIBST	OBJECT IDENTIFIER ::= { olSpecMods 27 }
ol53nnMSTP  	OBJECT IDENTIFIER ::= { olSpecMods 28 }
ol51nnMTPCL 	OBJECT IDENTIFIER ::= { olSpecMods 29 }
ol52nnBTT 	OBJECT IDENTIFIER ::= { olSpecMods 30 }
ol51nnIx 	OBJECT IDENTIFIER ::= { olSpecMods 31 }
ol52nnMMGT  	OBJECT IDENTIFIER ::= { olSpecMods 32 }
ol50nnMHCTL 	OBJECT IDENTIFIER ::= { olSpecMods 33 }













--
-- Networking groups
--

olNet		OBJECT IDENTIFIER ::= { olNets 1 }
olEnet		OBJECT IDENTIFIER ::= { olNets 2 }
olTRnet 	OBJECT IDENTIFIER ::= { olNets 3 }
olFDDInet 	OBJECT IDENTIFIER ::= { olNets 4 }


--
-- Workgroup Hub
--

hubSysGroup        OBJECT IDENTIFIER ::= { workGroupHub 1 }
hardwareGroup      OBJECT IDENTIFIER ::= { workGroupHub 2 }
softwareGroup      OBJECT IDENTIFIER ::= { workGroupHub 3 }
hubGroup           OBJECT IDENTIFIER ::= { workGroupHub 4 }
boardGroup         OBJECT IDENTIFIER ::= { workGroupHub 5 }
portGroup          OBJECT IDENTIFIER ::= { workGroupHub 6 }
alarmGroup         OBJECT IDENTIFIER ::= { workGroupHub 7 }


--
-- Threshold group
--

olThresh	OBJECT IDENTIFIER ::= { olAlarm 1 }

olThreshControl	OBJECT IDENTIFIER ::= { olThresh 1 }



 -- The olTRnet Group

 -- This group represents information about Token Ring networks.

olTRnetMapState OBJECT-TYPE
	 SYNTAX INTEGER {
		 changing(1),
		 notChanging(2)
		 }
	 ACCESS read-only
	 STATUS mandatory
	 DESCRIPTION
		"The state of the inter-module token ring map. If the map
		is being updated, then the state of the map is changing."
	 ::= { olTRnet 1 }


olTRnetStatsTable OBJECT-TYPE
	SYNTAX SEQUENCE OF OlTRnetStatsEntry
	ACCESS not-accessible
	STATUS mandatory
	DESCRIPTION
		"A list of Token Ring statistics entries counted
		for each network."
	::= { olTRnet 2 }

olTRnetStatsEntry OBJECT-TYPE
	SYNTAX OlTRnetStatsEntry
	ACCESS not-accessible
	STATUS mandatory
	DESCRIPTION
		"A collection of statistics kept for a particular 
		Token Ring interface."	
	INDEX { olTRnetStatsNetID }
	::= { olTRnetStatsTable 1 }

OlTRnetStatsEntry ::=
	SEQUENCE {
		olTRnetStatsNetID
			INTEGER,
		olTRnetStatsLineErrors
			Counter,
		olTRnetStatsBurstErrors
			Counter,
		olTRnetStatsACErrors
			Counter,
		olTRnetStatsLostFrameErrors
			Counter,
		olTRnetStatsCongestionErrors
			Counter,
		olTRnetStatsFrameCopiedErrors
			Counter,
		olTRnetStatsTokenErrors
			Counter,
		olTRnetStatsDuplicateAddresses
			Counter,
		olTRnetStatsBeaconEvents
			Counter,
		olTRnetStatsLastBeaconSender
			OCTET STRING,
		olTRnetStatsLastBeaconNAUN
			OCTET STRING,
		olTRnetStatsLastBeaconTime
			TimeTicks,
		olTRnetStatsLastBeaconAction
			INTEGER,
		olTRnetStatsTotalStations
			INTEGER,
		olTRnetStatsConcStations
			INTEGER,
		olTRnetStatsTotalPorts
			INTEGER,
		olTRnetStatsEnabledPorts
			INTEGER,
		olTRnetStatsActivePorts
			INTEGER
		}

olTRnetStatsNetID OBJECT-TYPE
	SYNTAX INTEGER {
		isolated(2),
		token-ring-1(9),
		token-ring-2(10),
		token-ring-3(11),
		token-ring-4(12),
		token-ring-5(13),
		token-ring-6(14),
		token-ring-7(15)
		}
	ACCESS read-only
	STATUS mandatory
	DESCRIPTION
		"The network index that uniquely identifies this network.
		One of token-ring-1 through token-ring-7 or isolated."
	::= { olTRnetStatsEntry 1 }

olTRnetStatsLineErrors OBJECT-TYPE
	SYNTAX Counter
	ACCESS read-only
	STATUS mandatory
	DESCRIPTION
		"The total number of line errors reported in
		error reporting packets detected by the TRMM."
	::= { olTRnetStatsEntry 2 }

olTRnetStatsBurstErrors OBJECT-TYPE
	SYNTAX Counter
	ACCESS read-only
	STATUS mandatory
	DESCRIPTION
		"The total number of burst errors reported in
		error reporting packets detected by the TRMM."
	::= { olTRnetStatsEntry 3 }

olTRnetStatsACErrors OBJECT-TYPE
	SYNTAX Counter
	ACCESS read-only
	STATUS mandatory
	DESCRIPTION
		"The total number of AC (Address Copied) errors 
		reported in error reporting packets detected by 
		the TRMM."
	::= { olTRnetStatsEntry 4 }

olTRnetStatsLostFrameErrors OBJECT-TYPE
	SYNTAX Counter
	ACCESS read-only
	STATUS mandatory
	DESCRIPTION
		"The total number of lost frame errors reported
		in error reporting packets detected by the TRMM."
	::= { olTRnetStatsEntry 5 }

olTRnetStatsCongestionErrors OBJECT-TYPE
	SYNTAX Counter
	ACCESS read-only
	STATUS mandatory
	DESCRIPTION
		"The total number of receive congestion errors 
		reported in error reporting packets detected by 
		the TRMM."
	::= { olTRnetStatsEntry 6 }

olTRnetStatsFrameCopiedErrors OBJECT-TYPE
	SYNTAX Counter
	ACCESS read-only
	STATUS mandatory
	DESCRIPTION
		"The total number of frame copied errors
		reported in error reporting packets detected by
		the TRMM."
	::= { olTRnetStatsEntry 7 }

olTRnetStatsTokenErrors OBJECT-TYPE
	SYNTAX Counter
	ACCESS read-only
	STATUS mandatory
	DESCRIPTION
		"The total number of token errors reported in
		error reporting packets detected by the TRMM."
	::= { olTRnetStatsEntry 8 }

olTRnetStatsDuplicateAddresses OBJECT-TYPE
	SYNTAX Counter
	ACCESS read-only
	STATUS mandatory
	DESCRIPTION
		"The total number of token errors reported in
		error reporting packets detected by the TRMM."
	::= { olTRnetStatsEntry 9 }

olTRnetStatsBeaconEvents OBJECT-TYPE
	SYNTAX Counter
	ACCESS read-only
	STATUS mandatory
	DESCRIPTION
		"The total number of times that the ring enters
		the beaconing state."
	::= { olTRnetStatsEntry 10 }

olTRnetStatsLastBeaconSender OBJECT-TYPE
	SYNTAX OCTET STRING (SIZE(6))
	ACCESS read-only
	STATUS mandatory
	DESCRIPTION
		"The address of the sender of the last beacon frame
		received on this ring. If no beacon frames have been
		received, this object will be six zero octets."
	::= { olTRnetStatsEntry 11 }

olTRnetStatsLastBeaconNAUN OBJECT-TYPE
	SYNTAX OCTET STRING (SIZE(6))
	ACCESS read-only
	STATUS mandatory
	DESCRIPTION
		"The address of the NAUN in the last beacon frame
		received on this ring. If no beacon frames have been
		received, this object will be six zero octets."
	::= { olTRnetStatsEntry 12 }

olTRnetStatsLastBeaconTime OBJECT-TYPE
	SYNTAX TimeTicks
	ACCESS read-only
	STATUS mandatory
	DESCRIPTION
		"The time in in hundredths of a second since the last 
		beacon event occurred.  For example, if the time  is 500 
		ticks, then this event was seen 5 seconds ago. If no
		beacon events have occurred, then this will be equal
		to the sysUpTime."
	::= { olTRnetStatsEntry 13 }

olTRnetStatsLastBeaconAction OBJECT-TYPE
	SYNTAX INTEGER {
		noAction (1),
		portDisable (2),
		trunkDisable (3),
		moduleIsolate (4)
		}
	ACCESS read-only
	STATUS mandatory
	DESCRIPTION
		"The action (if any) taken to correct the last beacon
		event on the ring."
	::= { olTRnetStatsEntry 14 }

olTRnetStatsTotalStations OBJECT-TYPE
	SYNTAX INTEGER (1..255)
	ACCESS read-only
	STATUS mandatory
	DESCRIPTION
		"The number of stations currently participating in the 802.5 
		MAC protocol on the ring."
	::= { olTRnetStatsEntry 15 }

olTRnetStatsConcStations OBJECT-TYPE
	SYNTAX INTEGER (1..255)
	ACCESS read-only
	STATUS mandatory
	DESCRIPTION
		"The number of stations currently participating in the 802.5 
		MAC protocol on the ring which are connected to ports in
		this concentrator."
	::= { olTRnetStatsEntry 16}

olTRnetStatsTotalPorts OBJECT-TYPE
	SYNTAX INTEGER
	ACCESS read-only
	STATUS mandatory
	DESCRIPTION
		"The total number of ports within this concentrator and
		on this ring regardless of their admin state or status."
	::= { olTRnetStatsEntry 17 }

olTRnetStatsEnabledPorts OBJECT-TYPE
	SYNTAX INTEGER
	ACCESS read-only
	STATUS mandatory
	DESCRIPTION
		"The number of ports within this concentrator and on this ring
		which have olPortAdminState set to enabled."
	::= { olTRnetStatsEntry 18 }

olTRnetStatsActivePorts OBJECT-TYPE
	SYNTAX INTEGER
	ACCESS read-only
	STATUS mandatory
	DESCRIPTION
		"The number of ports within this concentrator and on this ring
		which have olPortAdminState set to enabled and whose 
		olPortStatus has a status of okay."
	::= { olTRnetStatsEntry 19 }

olTRnetStatsStationTable OBJECT-TYPE
	SYNTAX SEQUENCE OF OlTRnetStatsStationEntry
	ACCESS not-accessible
	STATUS mandatory
	DESCRIPTION
		"A list of ring statistics entries."
	::= { olTRnet 3 }

olTRnetStatsStationEntry OBJECT-TYPE
	SYNTAX OlTRnetStatsStationEntry
	ACCESS not-accessible
	STATUS mandatory
	DESCRIPTION
		"A collection of statistics for a particular station
		that has been discovered on a a ring monitored by 
		this device."
	INDEX { olTRnetStatsStationNetID, olTRnetStatsStationAddr }
	::= { olTRnetStatsStationTable 1 }

OlTRnetStatsStationEntry ::= 
	SEQUENCE {
		olTRnetStatsStationNetID
			INTEGER,
		olTRnetStatsStationAddr
			OCTET STRING,
		olTRnetStatsStationSlotIndex
			INTEGER,
		olTRnetStatsStationPortIndex
			INTEGER,
		olTRnetStatsStationNAUNAddress
			OCTET STRING,
		olTRnetStatsStationLineErrors
			Counter,
		olTRnetStatsStationBurstErrors
			Counter,
		olTRnetStatsStationACErrors
			Counter,
		olTRnetStatsStationLostFrameErrors
			Counter,
		olTRnetStatsStationCongestionErrors
			Counter,
		olTRnetStatsStationFrameCopiedErrors
			Counter,
		olTRnetStatsStationTokenErrors
			Counter,
		olTRnetStatsStationDuplicateAddresses
			Counter
		}

olTRnetStatsStationNetID OBJECT-TYPE
	SYNTAX INTEGER {
		isolated(2),
		token-ring-1(9),
		token-ring-2(10),
		token-ring-3(11),
		token-ring-4(12),
		token-ring-5(13),
		token-ring-6(14),
		token-ring-7(15)
		}	
	ACCESS read-only
	STATUS mandatory
	DESCRIPTION
		"The network index that uniquely identifies this network.
		One of token-ring-1 through token-ring-7 or isolated."
	::= { olTRnetStatsStationEntry 1 }

olTRnetStatsStationAddr OBJECT-TYPE
	SYNTAX OCTET STRING (SIZE(6))
	ACCESS read-only
	STATUS mandatory
	DESCRIPTION
		"The physical address of this station."
	::= { olTRnetStatsStationEntry 2 }

olTRnetStatsStationSlotIndex OBJECT-TYPE
	SYNTAX INTEGER {
		slot-1(1),
		slot-2(2),
		slot-3(3),
		slot-4(4),
		slot-5(5),
		slot-6(6),
		slot-7(7),
		slot-8(8),
		slot-9(9),
		slot-10(10),
		slot-11(11),
		slot-12(12),
		slot-13(13),
		slot-14(14),
		slot-15(15),
		slot-16(16),
		slot-17(17),
		external(255)
		}
	ACCESS read-only
	STATUS mandatory
	DESCRIPTION
		"The slot number of the station with this address.
		Addresses with a slot value of external(255) are
		not in this concentrator."
	::= { olTRnetStatsStationEntry 3 }

olTRnetStatsStationPortIndex OBJECT-TYPE
	SYNTAX INTEGER
	ACCESS read-only
	STATUS mandatory
	DESCRIPTION
		"The port number within olTRnetStatsStationSlotIndex's
		slot that received this address. If 
		olTRnetStatsStationSlotIndex has a value of 
		external(255), then the port address will be 255."
	::= { olTRnetStatsStationEntry 4 }

olTRnetStatsStationNAUNAddress OBJECT-TYPE
	SYNTAX OCTET STRING (SIZE(6))
	ACCESS read-only
	STATUS mandatory
	DESCRIPTION
		"The physical address of the nearest active upstream
		neighbor of this station."
	::= { olTRnetStatsStationEntry 5 }

olTRnetStatsStationLineErrors OBJECT-TYPE
	SYNTAX Counter
	ACCESS read-only
	STATUS mandatory
	DESCRIPTION
		"The total number of Line Errors pertaining to this station 
		reported in error reporting packets detected by the TRMM."
	::= { olTRnetStatsStationEntry 6 }

olTRnetStatsStationBurstErrors OBJECT-TYPE
	SYNTAX Counter
	ACCESS read-only
	STATUS mandatory
	DESCRIPTION
		"The total number of burst errors pertaining to this station 
		reported in error reporting packets detected by the TRMM."
	::= { olTRnetStatsStationEntry 7 }

olTRnetStatsStationACErrors OBJECT-TYPE
	SYNTAX Counter
	ACCESS read-only
	STATUS mandatory
	DESCRIPTION
		"The total number of AC (Address Copied)
		errors pertaining to this station reported in
		error reporting packets detected by the TRMM."
	::= { olTRnetStatsStationEntry 8 }

olTRnetStatsStationLostFrameErrors OBJECT-TYPE
	SYNTAX Counter
	ACCESS read-only
	STATUS mandatory
	DESCRIPTION
		"The total number of lost frame errors pertaining to 
		this station reported in error reporting packets
		detected by the TRMM."
	::= { olTRnetStatsStationEntry 9 }

olTRnetStatsStationCongestionErrors OBJECT-TYPE
	SYNTAX Counter
	ACCESS read-only
	STATUS mandatory
	DESCRIPTION
		"The total number of congestion errors pertaining
		to this station reported in error reporting
		packets detected by the TRMM."
	::= { olTRnetStatsStationEntry 10 }

olTRnetStatsStationFrameCopiedErrors OBJECT-TYPE
	SYNTAX Counter
	ACCESS read-only
	STATUS mandatory
	DESCRIPTION
		"The total number of frame copied errors pertaining 
		to this station reported in error reporting packets
		detected by the TRMM."
	::= { olTRnetStatsStationEntry 11 }

olTRnetStatsStationTokenErrors OBJECT-TYPE
	SYNTAX Counter
	ACCESS read-only
	STATUS mandatory
	DESCRIPTION
		"The total number of token errors pertaining to this
		station reported in error reporting packets detected
		by the TRMM."
	::= { olTRnetStatsStationEntry 12 }

olTRnetStatsStationDuplicateAddresses OBJECT-TYPE
	SYNTAX Counter
	ACCESS read-only
	STATUS mandatory
	DESCRIPTION
		"The number of times this station experienced
		a duplicate address error."
	::= { olTRnetStatsStationEntry 13 }


olTRnetStatsPortTable OBJECT-TYPE
	SYNTAX SEQUENCE OF OlTRnetStatsPortEntry
	ACCESS not-accessible
	STATUS mandatory
	DESCRIPTION
		"A list of statistic entries, for ports within the 
		concentrator."
	::= { olTRnet 4 }

olTRnetStatsPortEntry OBJECT-TYPE
	SYNTAX OlTRnetStatsPortEntry
	ACCESS not-accessible
	STATUS mandatory
	DESCRIPTION
		"A collection of statistics for a particular station
		that has been discovered on a a ring monitored by 
		this device."
	INDEX {olTRnetStatsPortSlotIndex, olTRnetStatsPortIndex }
	::= { olTRnetStatsPortTable 1 }

OlTRnetStatsPortEntry ::= 
	SEQUENCE {
		olTRnetStatsPortSlotIndex
			INTEGER,
		olTRnetStatsPortIndex
			INTEGER,
		olTRnetStatsPortNetID
			INTEGER,
		olTRnetStatsPortTotalStations
			INTEGER,
		olTRnetStatsPortAddress
			OCTET STRING,
		olTRnetStatsPortLineErrors
			Counter,
		olTRnetStatsPortBurstErrors
			Counter,
		olTRnetStatsPortACErrors
			Counter,
		olTRnetStatsPortLostFrameErrors
			Counter,
		olTRnetStatsPortCongestionErrors
			Counter,
		olTRnetStatsPortFrameCopiedErrors
			Counter,
		olTRnetStatsPortTokenErrors
			Counter,
		olTRnetStatsPortDuplicateAddresses
			Counter
		}

olTRnetStatsPortSlotIndex OBJECT-TYPE
	SYNTAX INTEGER 
	ACCESS read-only
	STATUS mandatory
	DESCRIPTION
		"The port slot number." 
	::= { olTRnetStatsPortEntry 1 }

olTRnetStatsPortIndex OBJECT-TYPE
	SYNTAX INTEGER
	ACCESS read-only
	STATUS mandatory
	DESCRIPTION
		"The port number within olTRnetStatsPortSlotIndex's slot."
	::= { olTRnetStatsPortEntry 2 }

olTRnetStatsPortNetID OBJECT-TYPE
	SYNTAX INTEGER {
		isolated(2),
		token-ring-1(9),
		token-ring-2(10),
		token-ring-3(11),
		token-ring-4(12),
		token-ring-5(13),
		token-ring-6(14),
		token-ring-7(15)
		}	
	ACCESS read-only
	STATUS mandatory
	DESCRIPTION
		"The network index that uniquely identifies this network.
		One of token-ring-1 through token-ring-7 or isolated."
	::= { olTRnetStatsPortEntry 3 }

olTRnetStatsPortTotalStations OBJECT-TYPE
	SYNTAX INTEGER 
	ACCESS read-only
	STATUS mandatory
	DESCRIPTION
		"The total number of stations attached to this port."
	::= { olTRnetStatsPortEntry 4 }

olTRnetStatsPortAddress OBJECT-TYPE
	SYNTAX OCTET STRING (SIZE(6))
	ACCESS read-only
	STATUS mandatory
	DESCRIPTION
		"The mac address of the station connected to this
		If there are multiple mac addresses for this port,
		then this object will contain the last mac address."
	::= { olTRnetStatsPortEntry 5 }

olTRnetStatsPortLineErrors OBJECT-TYPE
	SYNTAX Counter
	ACCESS read-only
	STATUS mandatory
	DESCRIPTION
		"The total number of Line Errors pertaining to
		this port reported in error reporting
		packets detected by the TRMM."
	::= { olTRnetStatsPortEntry 6 }

olTRnetStatsPortBurstErrors OBJECT-TYPE
	SYNTAX Counter
	ACCESS read-only
	STATUS mandatory
	DESCRIPTION
		"The total number of burst errors pertaining
		to this port reported in error reporting 
		packets detected by the TRMM."
	::= { olTRnetStatsPortEntry 7 }

olTRnetStatsPortACErrors OBJECT-TYPE
	SYNTAX Counter
	ACCESS read-only
	STATUS mandatory
	DESCRIPTION
		"The total number of AC (Address Copied)
		errors pertaining to this port reported in
		error reporting packets detected by the TRMM."
	::= { olTRnetStatsPortEntry 8 }

olTRnetStatsPortLostFrameErrors OBJECT-TYPE
	SYNTAX Counter
	ACCESS read-only
	STATUS mandatory
	DESCRIPTION
		"The total number of lost frame errors pertaining to 
		this port reported in error reporting packets
		detected by the TRMM."
	::= { olTRnetStatsPortEntry 9 }

olTRnetStatsPortCongestionErrors OBJECT-TYPE
	SYNTAX Counter
	ACCESS read-only
	STATUS mandatory
	DESCRIPTION
		"The total number of congestion errors pertaining
		to this port reported in error reporting
		packets detected by the TRMM."
	::= { olTRnetStatsPortEntry 10 }

olTRnetStatsPortFrameCopiedErrors OBJECT-TYPE
	SYNTAX Counter
	ACCESS read-only
	STATUS mandatory
	DESCRIPTION
		"The total number of frame copied errors pertaining 
		to this port reported in error reporting packets
		detected by the TRMM."
	::= { olTRnetStatsPortEntry 11 }

olTRnetStatsPortTokenErrors OBJECT-TYPE
	SYNTAX Counter
	ACCESS read-only
	STATUS mandatory
	DESCRIPTION
		"The total number of token errors pertaining to this
		station reported in error reporting packets detected
		by the TRMM."
	::= { olTRnetStatsPortEntry 12 }

olTRnetStatsPortDuplicateAddresses OBJECT-TYPE
	SYNTAX Counter
	ACCESS read-only
	STATUS mandatory
	DESCRIPTION
		"The number of times this port experienced
		a duplicate address error."
	::= { olTRnetStatsPortEntry 13 }

olTRnetMapSummary 	OBJECT IDENTIFIER ::= { olTRnet 5 }

olTRnetMapSummaryLogicalState OBJECT-TYPE
	SYNTAX INTEGER {
		changing(1),
		notChanging(2)
		}
	ACCESS read-only
	STATUS mandatory
	DESCRIPTION
		"The state of the token ring summary table. If the summary
		is being updated, then the state of the summary is changing."
	::= { olTRnetMapSummary 1 }

olTRnetMapSummaryLogicalLock OBJECT-TYPE
	SYNTAX INTEGER {
		lock(1),
		unlock(2)
		}
	ACCESS read-write
	STATUS mandatory
	DESCRIPTION
		"A semaphore for locking the token ring summary table.
		When locked, updates to the summary will pend until the 
		semaphore is unlocked, so that a valid summary can be read.
		This cannot be set to unlock if olTRnetSummaryLogicalState is 
                changing.
		For complete accuracy, this should be read after being set to
		ensure that the map was not changing when the lock was
		attempted. After the summary information has been recorded,
		the semaphore should be set to unlock to allow changes to
		occur."
	::= { olTRnetMapSummary 2 }

olTRnetMapSummaryTable OBJECT-TYPE
	SYNTAX SEQUENCE OF OlTRnetMapSummaryEntry
	ACCESS not-accessible
	STATUS mandatory
	DESCRIPTION
		"A logical map of the token ring network, starting from the
		agent's specified token ring interface. Each station on the
		map is represented by it's MAC address, slot number and port
		number (8 octets per station). If the port is external
		to the concentrator, the slot number will be 255 and the
		port number will be 0. The map is ordered in the same 
		direction as the token flow. The MAC addresses
		are concatonated into groups of up to 32 addresses per entry.
		The last entry has all-zero MAC addresses padded on the end
		of the entry. All entries before the last one have 32 valid
		addresses. This table supports up to 256 stations."
	::= { olTRnetMapSummary 3 }

olTRnetMapSummaryEntry OBJECT-TYPE
	SYNTAX OlTRnetMapSummaryEntry
	ACCESS not-accessible
	STATUS mandatory
	DESCRIPTION
		"A group of MAC addresses associated with a Token Ring map."
	INDEX { olTRnetMapSummaryNetID, olTRnetMapSummaryIndex }
	::= { olTRnetMapSummaryTable 1 }

OlTRnetMapSummaryEntry ::=
	SEQUENCE {
		olTRnetMapSummaryNetID
			INTEGER,
		olTRnetMapSummaryIndex
			INTEGER,
		olTRnetMapSummary32Stations
			OCTET STRING
		}

olTRnetMapSummaryNetID OBJECT-TYPE
	SYNTAX INTEGER {
		isolated(2),		-- corresponds to ifIndex
		token-ring-1(9),
		token-ring-2(10),
		token-ring-3(11),
		token-ring-4(12),
		token-ring-5(13),
		token-ring-6(14),
		token-ring-7(15)
		}
	ACCESS read-only
	STATUS mandatory
	DESCRIPTION
		"The network index that uniquely identifies this network.
		It can be isolated from the backplane, or on one of seven
		possible backplane token ring networks."
	::= { olTRnetMapSummaryEntry 1 }

olTRnetMapSummaryIndex OBJECT-TYPE
	SYNTAX INTEGER
	ACCESS read-only
	STATUS mandatory
	DESCRIPTION
		"The index into the map array. Possible values are 1 through 8.
		The MAC address of this agent is the first MAC address in
		olTRnetMapSummary32Stations indexed by a 1 in this entry."
	::= { olTRnetMapSummaryEntry 2 }

olTRnetMapSummary32Stations OBJECT-TYPE
	SYNTAX OCTET STRING (SIZE(8..256))
	ACCESS read-only
	STATUS mandatory
	DESCRIPTION
		"A concatonated group of MAC addresses and their associated
		slot and port of stations on the ring. Each entry has the
		eight octets. The first six octets are the MAC address.
		The seventh octet is the slot ID (or 255 if it is external
		to the concentrator). The eighth is the port ID (or 255
		if it is external to the concentrator).
		The MAC addresses are in the same order as the token flow."
	::= { olTRnetMapSummaryEntry 3 }

--
--  Network Traffic
--

olTRTrafTable OBJECT-TYPE
    SYNTAX SEQUENCE OF OlTRTrafEntry
    ACCESS not-accessible
    STATUS mandatory
    DESCRIPTION
	"A list of Token Ring network traffic (non-error) statistics entries.  
	Note that all of the frame and octet counters in this table
	include error frames that have valid length;
	all octet counters exclude framing bits but include FCS octets."
    ::= { olTRnet 6 }

olTRTrafEntry OBJECT-TYPE
    SYNTAX OlTRTrafEntry
    ACCESS not-accessible
    STATUS mandatory
    DESCRIPTION
	"A collection of statistics kept for a particular
	Token Ring interface.
	Note that all of the frame and octet counters in this table
	include error frames that have valid length;
	all octet counters exclude framing bits but include FCS octets."
    INDEX { olTRTrafNetID }
    ::= { olTRTrafTable 1 }

OlTRTrafEntry ::= SEQUENCE {
  olTRTrafNetID			INTEGER,
  olTRTrafTokenRotationTime	INTEGER,
  olTRTrafDropEvents		Counter,
  olTRTrafOctets		Counter,
  olTRTrafFrames		Counter,
  olTRTrafMacOctets		Counter,
  olTRTrafMacFrames		Counter,
  olTRTrafBroadcastFrames	Counter,
  olTRTrafMulticastFrames	Counter,
  olTRTrafFrames18to63Octets    Counter,
  olTRTrafFrames64to127Octets   Counter,
  olTRTrafFrames128to255Octets  Counter,
  olTRTrafFrames256to511Octets  Counter,
  olTRTrafFrames512to1023Octets Counter,
  olTRTrafFrames1024to2047Octets Counter,
  olTRTrafFrames2048to4095Octets Counter,
  olTRTrafFrames4096to8191Octets Counter,
  olTRTrafFrames8192to18000Octets Counter,
  olTRTrafFramesGreaterThan18000Octets	Counter
}

olTRTrafNetID OBJECT-TYPE
        SYNTAX INTEGER {
                isolated(2),
                token-ring-1(9),
                token-ring-2(10),
                token-ring-3(11),
                token-ring-4(12),
                token-ring-5(13),
                token-ring-6(14),
                token-ring-7(15)
                }
        ACCESS read-only
        STATUS mandatory
        DESCRIPTION
                "The network index that uniquely identifies this network.
                One of token-ring-1 through token-ring-7 or isolated."
        ::= { olTRTrafEntry 1 }

olTRTrafTokenRotationTime OBJECT-TYPE
    SYNTAX INTEGER
    ACCESS read-only
    STATUS mandatory
    DESCRIPTION
        "An estimate of the time (in microseconds) that it takes for the
	token to complete a single rotation around the ring."
    ::= { olTRTrafEntry 2 }

olTRTrafDropEvents OBJECT-TYPE
    SYNTAX Counter
    ACCESS read-only
    STATUS mandatory
    DESCRIPTION
        "The total number of events in which frames
        were dropped by the TRMM due to lack of resources.
        Note that this number is not necessarily the number of
        frames dropped; it is just the number of times this
        condition has been detected."
    ::= { olTRTrafEntry 3 }

olTRTrafOctets OBJECT-TYPE
    SYNTAX Counter
    ACCESS read-only
    STATUS mandatory
    DESCRIPTION
        "The total number of octets of data received on the network."
    ::= { olTRTrafEntry 4 }

olTRTrafFrames OBJECT-TYPE
    SYNTAX Counter
    ACCESS read-only
    STATUS mandatory
    DESCRIPTION
        "The total number of frames received."
    ::= { olTRTrafEntry 5 }

olTRTrafMacOctets OBJECT-TYPE
    SYNTAX Counter
    ACCESS read-only
    STATUS mandatory
    DESCRIPTION
        "The total number of octets of data in MAC frames
        received on the network."
    ::= { olTRTrafEntry 6 }

olTRTrafMacFrames OBJECT-TYPE
    SYNTAX Counter
    ACCESS read-only
    STATUS mandatory
    DESCRIPTION
        "The total number of MAC frames received."
    ::= { olTRTrafEntry 7 }

olTRTrafBroadcastFrames OBJECT-TYPE
    SYNTAX Counter
    ACCESS read-only
    STATUS mandatory
    DESCRIPTION
        "The total number of non-MAC frames received that were
        directed to a broadcast address (0xFFFFFFFFFFFF or 0xC000FFFFFFFF)."
    ::= { olTRTrafEntry 8 }

olTRTrafMulticastFrames OBJECT-TYPE
    SYNTAX Counter
    ACCESS read-only
    STATUS mandatory
    DESCRIPTION
        "The total number of non-MAC frames received that were
        directed to a local or global multicast or functional address.
	Note that this number does not include frames directed to
	a broadcast address."
    ::= { olTRTrafEntry 9 }

olTRTrafFrames18to63Octets OBJECT-TYPE
    SYNTAX Counter
    ACCESS read-only
    STATUS mandatory
    DESCRIPTION
	"The total number of non-MAC frames received that were between
	18 and 63 octets in length inclusive."
    ::= { olTRTrafEntry 10 }

olTRTrafFrames64to127Octets OBJECT-TYPE
    SYNTAX Counter
    ACCESS read-only
    STATUS mandatory
    DESCRIPTION
	"The total number of non-MAC frames received that were between
	64 and 127 octets in length inclusive."
    ::= { olTRTrafEntry 11 }

olTRTrafFrames128to255Octets OBJECT-TYPE
    SYNTAX Counter
    ACCESS read-only
    STATUS mandatory
    DESCRIPTION
	"The total number of non-MAC frames received that were between
	128 and 255 octets in length inclusive."
    ::= { olTRTrafEntry 12 }

olTRTrafFrames256to511Octets OBJECT-TYPE
    SYNTAX Counter
    ACCESS read-only
    STATUS mandatory
    DESCRIPTION
	"The total number of non-MAC frames received that were between
	256 and 511 octets in length inclusive."
    ::= { olTRTrafEntry 13 }

olTRTrafFrames512to1023Octets OBJECT-TYPE
    SYNTAX Counter
    ACCESS read-only
    STATUS mandatory
    DESCRIPTION
	"The total number of non-MAC frames received that were between
	512 and 1023 octets in length inclusive."
    ::= { olTRTrafEntry 14 }

olTRTrafFrames1024to2047Octets OBJECT-TYPE
    SYNTAX Counter
    ACCESS read-only
    STATUS mandatory
    DESCRIPTION
	"The total number of non-MAC frames received that were between
	1024 and 2047 octets in length inclusive."
    ::= { olTRTrafEntry 15 }

olTRTrafFrames2048to4095Octets OBJECT-TYPE
    SYNTAX Counter
    ACCESS read-only
    STATUS mandatory
    DESCRIPTION
	"The total number of non-MAC frames received that were between
	2048 and 4095 octets in length inclusive."
    ::= { olTRTrafEntry 16 }

olTRTrafFrames4096to8191Octets OBJECT-TYPE
    SYNTAX Counter
    ACCESS read-only
    STATUS mandatory
    DESCRIPTION
	"The total number of non-MAC frames received that were between
	4096 and 8191 octets in length inclusive."
    ::= { olTRTrafEntry 17 }

olTRTrafFrames8192to18000Octets OBJECT-TYPE
    SYNTAX Counter
    ACCESS read-only
    STATUS mandatory
    DESCRIPTION
	"The total number of non-MAC frames received that were between
	8192 and 18000 octets in length inclusive."
    ::= { olTRTrafEntry 18 }

olTRTrafFramesGreaterThan18000Octets OBJECT-TYPE
    SYNTAX Counter
    ACCESS read-only
    STATUS mandatory
    DESCRIPTION
	"The total number of non-MAC frames received that were
	greater than or equal to 18000 octets in length."
    ::= { olTRTrafEntry 19 }



-- Station and Port Traffic


-- The OlTRTrafControl, OlTRTrafStation, OlTRTrafPort, OlTRTrafTopN, and
-- OlTRTrafTopNSummary Groups

--
-- New stations on the token ring network are discovered by
-- keeping a list of source and destination MAC Addresses seen
-- in good frames.  For each of these addresses, a set of statistics
-- is maintained.  The OlTRTrafStation, OlTRTrafPort, OlTRTrafTopN,
-- and OlTRTrafTopNSummary Groups provide four different ways
-- to retrieve this information.
--
-- Note that the list of stations will include
--	- stations internal to the concentrator on the local ring
--	- stations external to the concentrator on the local ring
-- 	- stations on remote rings
--
-- If the list is full, the least recently used entries not on the local ring
-- will be deleted first, as needed.

-- The olTRTrafStationTable contains entries for each address
-- discovered on a particular interface.  Each entry
-- contains statistical data about that station.  This table
-- is indexed by Network ID and the MAC address of the station.

-- The olTRTrafPortTable contains data in the same format as the
-- olTRTrafStationTable, and contains the same set of stations
-- except that stations external to the concentrator or not on the local ring
-- are omitted.  The olTRTrafPortTable is
-- indexed by Network ID, SlotIndex and PortIndex.

-- The olTRTrafTopNTable is composed of 7 sublists, one for each statistic.
-- Each sublist contains the same set of stations as
-- olTRTrafStationTable.  The stations in each sublist are sorted by
-- the statistic specified in olTRTrafTopNStatistic.
-- The olTRTrafTopNTable is indexed by olTRTrafTopNNetID,
-- by olTRTrafTopNStatistic to identify the sublist,
-- and by olTRTrafTopNIndex (1..N) with index 1 referring to
-- the entry with the highest value of the specifed counter.
-- (See description of olTRTrafTopNTable)

-- The olTRTrafTopNSummaryTable contains the same information as
-- olTRTrafTopNTable, but in a condensed format.

-- Note that table entries may be added, deleted, or resorted at any time.
-- There are three methods available for a management station to address this.

-- METHOD 1
-- Each of the 4 tables has an associated "-LastChangeTime" entry in
-- olTRTrafControlTable.  A management station should read the
-- associated "-LastChangeTime" entry before and after reading a group of
-- table entries.  If the before and after "-LastChangeTimes differ then the
-- management station should repeat the reading of table entries.

-- METHOD 2
-- Use olTRTrafControlLogicalLock and olTRTrafControlLogicalState to ensure
-- that changes don't occur while retrieving table entries.
-- (see description below)

-- METHOD 3
-- Don't worry about table entry changes.  Probably they won't happen while
-- you are reading the table.  The worst that would happen is you might miss
-- a few stations or see the same station twice in the list.




olTRTrafControlTable OBJECT-TYPE
    SYNTAX SEQUENCE OF OlTRTrafControlEntry
    ACCESS not-accessible
    STATUS mandatory
    DESCRIPTION
	"A list entries containing information about 
	olTRTrafStationTable, olTRTrafPortTable, olTRTrafTopNTable, and
	olTRTrafTopNSummaryTable"
    ::= { olTRnet 7 }

olTRTrafControlEntry OBJECT-TYPE
    SYNTAX OlTRTrafControlEntry
    ACCESS not-accessible
    STATUS mandatory
    DESCRIPTION
	"A collection of information about 
	olTRTrafStationTable, olTRTrafPortTable, olTRTrafTopNTable, and
	olTRTrafTopNSummaryTable"
    INDEX { olTRTrafControlNetID }
    ::= { olTRTrafControlTable 1 }

OlTRTrafControlEntry ::= SEQUENCE {
  olTRTrafControlNetID			INTEGER,
  olTRTrafControlLogicalState		INTEGER,
  olTRTrafControlLogicalLock		INTEGER,
  olTRTrafControlClear			INTEGER,
  olTRTrafControlLastClearTime		TimeTicks,
  olTRTrafControlTotalStations		INTEGER,
  olTRTrafControlStationLastChangeTime	TimeTicks,
  olTRTrafControlPortTotalStations	INTEGER,
  olTRTrafControlPortLastChangeTime	TimeTicks,
  olTRTrafControlTopNMaxStations	INTEGER,
  olTRTrafControlTopNTotalStations	INTEGER,
  olTRTrafControlTopNLastChangeTime	TimeTicks,
  olTRTrafControlTopNInterval		INTEGER
}

olTRTrafControlNetID OBJECT-TYPE
        SYNTAX INTEGER {
                isolated(2),
                token-ring-1(9),
                token-ring-2(10),
                token-ring-3(11),
                token-ring-4(12),
                token-ring-5(13),
                token-ring-6(14),
                token-ring-7(15)
                }
        ACCESS read-only
        STATUS mandatory
        DESCRIPTION
                "The network index that uniquely identifies this network.
                One of token-ring-1 through token-ring-7 or isolated."
        ::= { olTRTrafControlEntry 1 }

olTRTrafControlLogicalState OBJECT-TYPE
        SYNTAX INTEGER {
                changing(1),
                notChanging(2)
                }
        ACCESS read-only
        STATUS mandatory
        DESCRIPTION
                "The state of the token ring station traffic tables:
		olTRTrafStationTable, olTRTrafPortTable, olTRTrafTopNTable
		and olTRTrafTopNSummaryTable. If any of the tables associated
		with this olTRTrafControlEntry are being updated,
		then the state is changing(1)."
        ::= { olTRTrafControlEntry 2 }

olTRTrafControlLogicalLock OBJECT-TYPE
        SYNTAX INTEGER {
                lock(1),
                unlock(2)
                }
        ACCESS read-write
        STATUS mandatory
        DESCRIPTION
                "A semaphore for locking the token ring station traffic
		tables: olTRTrafStationTable, olTRTrafPortTable,
		olTRTrafTopNTable, and olTRTrafTopNSummaryTable.
		When the semaphore is locked, adds, deletes, and re-sorting
		the traffic tables associated with this 
		olTRTrafControlEntry will pend until the
                semaphore is unlocked, so that a valid set of entries
		can be read.  Note that the normal incrementing of the traffic
		counters are not affected by the setting of this semaphore.
                This cannot be set to unlock if olTRTrafControlLogicalState is
                changing.
                For complete accuracy, this semaphore
		should be read after being set to
                ensure that the tables were not changing when the lock was
                attempted. After the table information has been recorded,
                the semaphore should be set to unlock to allow changes to
                occur."
        ::= { olTRTrafControlEntry 3 }


olTRTrafControlClear OBJECT-TYPE
  SYNTAX INTEGER {
	  normal(1),
	  clear(2)
  }
  ACCESS read-write
  STATUS mandatory
  DESCRIPTION
	"When the value of this object is set to clear,
	all entries in the token ring station traffic
	tables (olTRTrafStationTable, olTRTrafPortTable,
	olTRTrafTopNTable, and olTRTrafTopNSummaryTable) are cleared."
    ::= { olTRTrafControlEntry 4 }

olTRTrafControlLastClearTime OBJECT-TYPE
  SYNTAX TimeTicks
  ACCESS read-only
  STATUS mandatory
  DESCRIPTION
	"The value of sysUpTime when the token ring station traffic
	tables (olTRTrafStationTable, olTRTrafPortTable,
	olTRTrafTopNTable and olTRTrafTopNSummaryTable) were cleared.
	If never cleared, this value shall be zero (and the token ring
	station traffic tables will contain information collected since
	the XMM was started up)."
    ::= { olTRTrafControlEntry 5 }

olTRTrafControlTotalStations OBJECT-TYPE
  SYNTAX INTEGER
  ACCESS read-only
  STATUS mandatory
  DESCRIPTION
	"The number of stations in the portion of the olTRTrafStationTable
	associated with this olTRTrafControlEntry."
    ::= { olTRTrafControlEntry 6 }

olTRTrafControlStationLastChangeTime OBJECT-TYPE
  SYNTAX TimeTicks
  ACCESS read-only
  STATUS mandatory
  DESCRIPTION
      "The value of sysUpTime when the last entry
      was added to or deleted (or re-sorted)
      from the portion of the olTRTrafStationTable
      associated with this olTRTrafControlEntry.  If no
      additions or deletions have occurred, this value shall be zero."
    ::= { olTRTrafControlEntry 7 }

olTRTrafControlPortTotalStations OBJECT-TYPE
  SYNTAX INTEGER
  ACCESS read-only
  STATUS mandatory
  DESCRIPTION
	"The number of stations in the portion of the olTRTrafPortTable
	associated with this olTRTrafControlEntry."
    ::= { olTRTrafControlEntry 8 }

olTRTrafControlPortLastChangeTime OBJECT-TYPE
  SYNTAX TimeTicks
  ACCESS read-only
  STATUS mandatory
  DESCRIPTION
      "The value of sysUpTime when the last entry
      was added to or deleted (or re-sorted)
      from the portion of the olTRTrafPortTable
      associated with this olTRTrafControlEntry.  If no
      additions or deletions have occurred, this value shall be zero."
    ::= { olTRTrafControlEntry 9 }

olTRTrafControlTopNMaxStations OBJECT-TYPE
  SYNTAX INTEGER
  ACCESS read-write
  STATUS mandatory
  DESCRIPTION
	"Specifies a maximum value for olTRTrafControlTopNTotalStations
	in this olTRTrafControlEntry.  If this value is zero then no  
	maximum value for olTRTrafControlTopNTotalStations is specified."
--	DEFVAL { 0 }
    ::= { olTRTrafControlEntry 10 }

olTRTrafControlTopNTotalStations OBJECT-TYPE
  SYNTAX INTEGER
  ACCESS read-only
  STATUS mandatory
  DESCRIPTION
	"The number of stations (for each statistic) in the portion of 
	the olTRTrafTopNTable and olTRTrafTopNSummaryTable associated
	with this olTRTrafControlEntry.  If olTRTrafControlTopNMaxStations
	is zero or is not less than olTRTrafControlTotalStations then
	olTRTrafControlTopNTotalStations will have the same value as
	olTRTrafControlTotalStations.  Otherwise
	olTRTrafControlTopNTotalStations will
	have the same value as olTRTrafControlTopNMaxStations." 
    ::= { olTRTrafControlEntry 11 }

olTRTrafControlTopNLastChangeTime OBJECT-TYPE
  SYNTAX TimeTicks
  ACCESS read-only
  STATUS mandatory
  DESCRIPTION
      "The value of sysUpTime when the last entry
      was added to or deleted (or re-sorted)
      from the portion of the olTRTrafTopNTable and olTRTrafTopNSummaryTable
      associated with this olTRTrafControlEntry.  
      This is equivalent to the time when 
      the last TopN data collection period ended.
      If no additions or deletions have occurred, this value shall be zero."
    ::= { olTRTrafControlEntry 12 }

olTRTrafControlTopNInterval OBJECT-TYPE
  SYNTAX INTEGER
  ACCESS read-write
  STATUS mandatory
  DESCRIPTION
      "Specifies the length of the TopN data collection period in seconds.
      Minimum length is 5 seconds; maximum is 86400 seconds (24 hours).
      When this value is modified, all associated entries in 
      olTRTrafTopNTable and olTRTrafTopNSummaryTable are deleted and a new
      TopN data collection period is started."
--      DEFVAL {30}
    ::= { olTRTrafControlEntry 13 }



olTRTrafStationTable OBJECT-TYPE
  SYNTAX SEQUENCE OF OlTRTrafStationEntry
  ACCESS not-accessible
  STATUS mandatory
  DESCRIPTION
      "A list of Token Ring station traffic statistics entries
      indexed by Network ID and MAC address.  The table has 
      olTRTrafTotalStations entries.
	Note that all of the frame and octet counters in this table
	include error frames that have valid length;
	all octet counters exclude framing bits but include FCS octets."
  ::= { olTRnet 8 }

olTRTrafStationEntry OBJECT-TYPE
  SYNTAX OlTRTrafStationEntry
  ACCESS not-accessible
  STATUS mandatory
  DESCRIPTION
      "A collection of station statistics for a particular station
      that has been discovered on an interface of this
      device.
	Note that all of the frame and octet counters in this table
	include error frames that have valid length;
	all octet counters exclude framing bits but include FCS octets."
  INDEX { olTRTrafStationNetID,
		olTRTrafStationAddress }
  ::= { olTRTrafStationTable 1 }

OlTRTrafStationEntry ::= SEQUENCE {
  olTRTrafStationNetID			INTEGER,
  olTRTrafStationAddress		MacAddress,
  olTRTrafStationSlotIndex		INTEGER,
  olTRTrafStationPortIndex		INTEGER,
  olTRTrafStationInFrames		Counter,
  olTRTrafStationOutFrames		Counter,
  olTRTrafStationInOctets		Counter,
  olTRTrafStationOutOctets		Counter,
  olTRTrafStationOutErrors		Counter,
  olTRTrafStationOutBroadcastFrames	Counter,
  olTRTrafStationOutMulticastFrames	Counter
}

olTRTrafStationNetID OBJECT-TYPE
        SYNTAX INTEGER {
                isolated(2),
                token-ring-1(9),
                token-ring-2(10),
                token-ring-3(11),
                token-ring-4(12),
                token-ring-5(13),
                token-ring-6(14),
                token-ring-7(15)
                }
        ACCESS read-only
        STATUS mandatory
        DESCRIPTION
                "The network index that uniquely identifies this network.
                One of token-ring-1 through token-ring-7 or isolated."
        ::= { olTRTrafStationEntry 1 }

olTRTrafStationAddress OBJECT-TYPE
  SYNTAX MacAddress
  ACCESS read-only
  STATUS mandatory
  DESCRIPTION
      "The physical address of this station."
  ::= { olTRTrafStationEntry 2 }

olTRTrafStationSlotIndex OBJECT-TYPE
	SYNTAX INTEGER {
		slot-1(1),
		slot-2(2),
		slot-3(3),
		slot-4(4),
		slot-5(5),
		slot-6(6),
		slot-7(7),
		slot-8(8),
		slot-9(9),
		slot-10(10),
		slot-11(11),
		slot-12(12),
		slot-13(13),
		slot-14(14),
		slot-15(15),
		slot-16(16),
		slot-17(17),
		remote-ring(254),
		external(255)
		}
	ACCESS read-only
	STATUS mandatory
	DESCRIPTION
		"The slot number of the station with this address.
		Addresses with a slot value of remote-ring(254) are
		not in this ring.
		Addresses with a slot value of external(255) are
		not in this concentrator."
  ::= { olTRTrafStationEntry 3 }

olTRTrafStationPortIndex OBJECT-TYPE
	SYNTAX INTEGER
	ACCESS read-only
	STATUS mandatory
	DESCRIPTION
		"The port number within olTRTrafSlotIndex's
		slot that received this address.
		If olTRTrafSlotIndex has a value of 
		remote-ring(254), then the port address will be 254.
		If olTRTrafSlotIndex has a value of 
		external(255), then the port address will be 255."
  ::= { olTRTrafStationEntry 4 }

olTRTrafStationInFrames OBJECT-TYPE
  SYNTAX Counter
  ACCESS read-only
  STATUS mandatory
  DESCRIPTION
      "The number of frames transmitted to this address since it was
      added to this table."
  ::= { olTRTrafStationEntry 5 }

olTRTrafStationOutFrames OBJECT-TYPE
  SYNTAX Counter
  ACCESS read-only
  STATUS mandatory
  DESCRIPTION
      "The number of frames transmitted by this address since it was
      added to this table."
  ::= { olTRTrafStationEntry 6 }

olTRTrafStationInOctets OBJECT-TYPE
  SYNTAX Counter
  ACCESS read-only
  STATUS mandatory
  DESCRIPTION
      "The number of octets transmitted to this address since it was
      added to this table."
  ::= { olTRTrafStationEntry 7 }

olTRTrafStationOutOctets OBJECT-TYPE
  SYNTAX Counter
  ACCESS read-only
  STATUS mandatory
  DESCRIPTION
      "The number of octets transmitted by this address since it was
      added to this table."
  ::= { olTRTrafStationEntry 8 }

olTRTrafStationOutErrors OBJECT-TYPE
  SYNTAX Counter
  ACCESS read-only
  STATUS mandatory
  DESCRIPTION
      "The number of error frames transmitted by this
      address since it was added to this table.  Only isolating errors
      (LineErrors, BurstErrors, ACErrors, InternalErrors, and AbortErrors)
      and CongestionErrors are counted."
  ::= { olTRTrafStationEntry 9 }

olTRTrafStationOutBroadcastFrames OBJECT-TYPE
  SYNTAX Counter
  ACCESS read-only
  STATUS mandatory
  DESCRIPTION
      "The number of frames transmitted by this address
      that were directed to the broadcast address since it was
      added to this table."
  ::= { olTRTrafStationEntry 10 }

olTRTrafStationOutMulticastFrames OBJECT-TYPE
  SYNTAX Counter
  ACCESS read-only
  STATUS mandatory
  DESCRIPTION
      "The number of frames transmitted by this address
      that were directed to a multicast address since it was
      added to this table.
      Note that this number does not include frames
      directed to the broadcast address."
  ::= { olTRTrafStationEntry 11 }



olTRTrafPortTable OBJECT-TYPE
  SYNTAX SEQUENCE OF OlTRTrafPortEntry
  ACCESS not-accessible
  STATUS mandatory
  DESCRIPTION
      "A list of Token Ring station traffic statistics entries
      indexed by slot number, and port number.  Note that stations external
      to this concentrator or on another ring are excluded from this table.
	Note that all of the frame and octet counters in this table
	include error frames that have valid length;
	all octet counters exclude framing bits but include FCS octets."
  ::= { olTRnet 9 }

olTRTrafPortEntry OBJECT-TYPE
  SYNTAX OlTRTrafPortEntry
  ACCESS not-accessible
  STATUS mandatory
  DESCRIPTION
      "A collection of station statistics for a particular station
      that has been discovered on an interface of this
      device.
	Note that all of the frame and octet counters in this table
	include error frames that have valid length;
	all octet counters exclude framing bits but include FCS octets.
	include error frames; all octet counters exclude framing bits
	but include FCS octets."
  INDEX { olTRTrafPortSlotIndex, olTRTrafPortPortIndex }
  ::= { olTRTrafPortTable 1 }

OlTRTrafPortEntry ::= SEQUENCE {
  olTRTrafPortSlotIndex           INTEGER,
  olTRTrafPortPortIndex           INTEGER,
  olTRTrafPortNetID               INTEGER,
  olTRTrafPortAddress             MacAddress,
  olTRTrafPortInFrames              Counter,
  olTRTrafPortOutFrames             Counter,
  olTRTrafPortInOctets            Counter,
  olTRTrafPortOutOctets           Counter,
  olTRTrafPortOutErrors           Counter,
  olTRTrafPortOutBroadcastFrames    Counter,
  olTRTrafPortOutMulticastFrames    Counter
}

olTRTrafPortSlotIndex OBJECT-TYPE
	SYNTAX INTEGER
	ACCESS read-only
	STATUS mandatory
	DESCRIPTION
		"The slot number of the station with this address."
  ::= { olTRTrafPortEntry 1 }

olTRTrafPortPortIndex OBJECT-TYPE
	SYNTAX INTEGER
	ACCESS read-only
	STATUS mandatory
	DESCRIPTION
		"The port number within olTRTrafPortSlotIndex's
		slot that received this address."
  ::= { olTRTrafPortEntry 2 }

olTRTrafPortNetID OBJECT-TYPE
        SYNTAX INTEGER {
                isolated(2),
                token-ring-1(9),
                token-ring-2(10),
                token-ring-3(11),
                token-ring-4(12),
                token-ring-5(13),
                token-ring-6(14),
                token-ring-7(15)
                }
        ACCESS read-only
        STATUS mandatory
        DESCRIPTION
                "The network index that uniquely identifies this network.
                One of token-ring-1 through token-ring-7 or isolated."
        ::= { olTRTrafPortEntry 3 }

olTRTrafPortAddress OBJECT-TYPE
  SYNTAX MacAddress
  ACCESS read-only
  STATUS mandatory
  DESCRIPTION
      "The physical address of this station."
  ::= { olTRTrafPortEntry 4 }

olTRTrafPortInFrames OBJECT-TYPE
  SYNTAX Counter
  ACCESS read-only
  STATUS mandatory
  DESCRIPTION
      "The number of frames transmitted to this address since it was
      added to this table."
  ::= { olTRTrafPortEntry 5 }

olTRTrafPortOutFrames OBJECT-TYPE
  SYNTAX Counter
  ACCESS read-only
  STATUS mandatory
  DESCRIPTION
      "The number of frames transmitted by this address since it was
      added to this table."
  ::= { olTRTrafPortEntry 6 }

olTRTrafPortInOctets OBJECT-TYPE
  SYNTAX Counter
  ACCESS read-only
  STATUS mandatory
  DESCRIPTION
      "The number of octets transmitted to this address since it was
      added to this table."
  ::= { olTRTrafPortEntry 7 }

olTRTrafPortOutOctets OBJECT-TYPE
  SYNTAX Counter
  ACCESS read-only
  STATUS mandatory
  DESCRIPTION
      "The number of octets transmitted by this address since it was
      added to this table."
  ::= { olTRTrafPortEntry 8 }

olTRTrafPortOutErrors OBJECT-TYPE
  SYNTAX Counter
  ACCESS read-only
  STATUS mandatory
  DESCRIPTION
      "The number of error frames transmitted by this
      address since it was added to this table.  Only isolating errors
      (LineErrors, BurstErrors, ACErrors, InternalErrors, and AbortErrors)
      and CongestionErrors are counted."
  ::= { olTRTrafPortEntry 9 }

olTRTrafPortOutBroadcastFrames OBJECT-TYPE
  SYNTAX Counter
  ACCESS read-only
  STATUS mandatory
  DESCRIPTION
      "The number of frames transmitted by this address
      that were directed to the broadcast address since it was
      added to this table."
  ::= { olTRTrafPortEntry 10 }

olTRTrafPortOutMulticastFrames OBJECT-TYPE
  SYNTAX Counter
  ACCESS read-only
  STATUS mandatory
  DESCRIPTION
      "The number of frames transmitted by this address
      that were directed to a multicast address since it was
      added to this table.
      Note that this number does not include frames
      directed to the broadcast address."
  ::= { olTRTrafPortEntry 11 }



olTRTrafTopNTable OBJECT-TYPE
  SYNTAX SEQUENCE OF OlTRTrafTopNEntry
  ACCESS not-accessible
  STATUS mandatory
  DESCRIPTION
      "A list of Token Ring station traffic statistics entries indexed by
	olTRTrafTopNNetID, olTRTrafTopNStatistic, and olTRTrafTopNIndex.
	For each Network, the list contains 7 logical sublists - one for 
	each statistic.
	Each of the sublists has olTRTrafControlTopNTotalStations entries.
	For eack Network, the table has 7 times
	olTRTrafTopNControlTotalStations entries.
	All of the counters in this table reflect activity during the last 
	completed TopN data collection period 
	(olTRTrafControlTopNInterval seconds).
	Note that this table will contain no entries 
	if a TopN data collection period has not yet completed since
	olTRTrafControlTopNInterval was modified or since startup.
	Note that all of the frame and octet counters in this table
	include error frames that have valid length;
	all octet counters exclude framing bits but include FCS octets."
  ::= { olTRnet 10 }

olTRTrafTopNEntry OBJECT-TYPE
  SYNTAX OlTRTrafTopNEntry
  ACCESS not-accessible
  STATUS mandatory
  DESCRIPTION
      "A collection of station statistics for a particular station
      that has been discovered on an interface of this
      device.
	Note that all of the frame and octet counters in this table
	include error frames that have valid length;
	all octet counters exclude framing bits but include FCS octets."
  INDEX { olTRTrafTopNNetID,
		olTRTrafTopNStatistic,
		olTRTrafTopNIndex }
  ::= { olTRTrafTopNTable 1 }

OlTRTrafTopNEntry ::= SEQUENCE {
  olTRTrafTopNNetID               INTEGER,
  olTRTrafTopNStatistic		  INTEGER,
  olTRTrafTopNIndex               INTEGER,
  olTRTrafTopNAddress             MacAddress,
  olTRTrafTopNSlotIndex           INTEGER,
  olTRTrafTopNPortIndex           INTEGER,
  olTRTrafTopNInFrames              Counter,
  olTRTrafTopNOutFrames             Counter,
  olTRTrafTopNInOctets            Counter,
  olTRTrafTopNOutOctets           Counter,
  olTRTrafTopNOutErrors           Counter,
  olTRTrafTopNOutBroadcastFrames    Counter,
  olTRTrafTopNOutMulticastFrames    Counter
}

olTRTrafTopNNetID OBJECT-TYPE
        SYNTAX INTEGER {
                isolated(2),
                token-ring-1(9),
                token-ring-2(10),
                token-ring-3(11),
                token-ring-4(12),
                token-ring-5(13),
                token-ring-6(14),
                token-ring-7(15)
                }
        ACCESS read-only
        STATUS mandatory
        DESCRIPTION
                "The network index that uniquely identifies this network.
                One of token-ring-1 through token-ring-7 or isolated."
        ::= { olTRTrafTopNEntry 1 }

olTRTrafTopNStatistic OBJECT-TYPE
  SYNTAX INTEGER {
	  olTRTrafTopNInFrames(1),
	  olTRTrafTopNOutFrames(2),
	  olTRTrafTopNInOctets(3),
	  olTRTrafTopNOutOctets(4),
	  olTRTrafTopNOutErrors(5),
	  olTRTrafTopNOutBroadcastFrames(6),
	  olTRTrafTopNOutMulticastFrames(7)
  }
  ACCESS read-write
  STATUS mandatory
  DESCRIPTION
      "The object representing the statistic for each station that this
      portion of the olTRTrafTopNTable is sorted on."
    ::= { olTRTrafTopNEntry 2 }

olTRTrafTopNIndex OBJECT-TYPE
  SYNTAX INTEGER
  ACCESS read-only
  STATUS mandatory
  DESCRIPTION
      "An index that uniquely identifies an entry in
      the olTRTrafTopN table among those in the same network
      and for the same olTRTrafTopNStatistic.
      This index is between 1 and N, where N is the value of
      olTRTrafControlTopNTotalStations.  Increasing values
      of olTRTrafTopNIndex shall be assigned to entries with
      decreasing values of the object referenced by olTRTrafTopNStatistic."
  ::= { olTRTrafTopNEntry 3 }

olTRTrafTopNAddress OBJECT-TYPE
  SYNTAX MacAddress
  ACCESS read-only
  STATUS mandatory
  DESCRIPTION
      "The physical address of this station."
  ::= { olTRTrafTopNEntry 4 }

olTRTrafTopNSlotIndex OBJECT-TYPE
	SYNTAX INTEGER {
		slot-1(1),
		slot-2(2),
		slot-3(3),
		slot-4(4),
		slot-5(5),
		slot-6(6),
		slot-7(7),
		slot-8(8),
		slot-9(9),
		slot-10(10),
		slot-11(11),
		slot-12(12),
		slot-13(13),
		slot-14(14),
		slot-15(15),
		slot-16(16),
		slot-17(17),
		remote-ring(254),
		external(255)
		}
	ACCESS read-only
	STATUS mandatory
	DESCRIPTION
		"The slot number of the station with this address.
		Addresses with a slot value of remote-ring(254) are
		not in this ring.
		Addresses with a slot value of external(255) are
		not in this concentrator."
  ::= { olTRTrafTopNEntry 5 }

olTRTrafTopNPortIndex OBJECT-TYPE
	SYNTAX INTEGER
	ACCESS read-only
	STATUS mandatory
	DESCRIPTION
		"The port number within olTRTrafTopNSlotIndex's
		slot that received this address.
		If olTRTrafTopNSlotIndex has a value of 
		remote-ring(254), then the port address will be 254.
		If olTRTrafTopNSlotIndex has a value of 
		external(255), then the port address will be 255."
  ::= { olTRTrafTopNEntry 6 }

olTRTrafTopNInFrames OBJECT-TYPE
  SYNTAX Counter
  ACCESS read-only
  STATUS mandatory
  DESCRIPTION
      "The number of frames transmitted to this address
      during the last TopN data collection period."
  ::= { olTRTrafTopNEntry 7 }

olTRTrafTopNOutFrames OBJECT-TYPE
  SYNTAX Counter
  ACCESS read-only
  STATUS mandatory
  DESCRIPTION
      "The number of frames transmitted by this address 
      during the last TopN data collection period."
  ::= { olTRTrafTopNEntry 8 }

olTRTrafTopNInOctets OBJECT-TYPE
  SYNTAX Counter
  ACCESS read-only
  STATUS mandatory
  DESCRIPTION
      "The number of octets transmitted to this address 
      during the last TopN data collection period."
  ::= { olTRTrafTopNEntry 9 }

olTRTrafTopNOutOctets OBJECT-TYPE
  SYNTAX Counter
  ACCESS read-only
  STATUS mandatory
  DESCRIPTION
      "The number of octets transmitted by this address 
      during the last TopN data collection period."
  ::= { olTRTrafTopNEntry 10 }

olTRTrafTopNOutErrors OBJECT-TYPE
  SYNTAX Counter
  ACCESS read-only
  STATUS mandatory
  DESCRIPTION
      "The number of error frames transmitted by this address
      during the last TopN data collection period.  Only isolating errors
      (LineErrors, BurstErrors, ACErrors, InternalErrors, and AbortErrors)
      and CongestionErrors are counted."
  ::= { olTRTrafTopNEntry 11 }

olTRTrafTopNOutBroadcastFrames OBJECT-TYPE
  SYNTAX Counter
  ACCESS read-only
  STATUS mandatory
  DESCRIPTION
      "The number of frames transmitted by this address
      that were directed to the broadcast address 
      during the last TopN data collection period."
  ::= { olTRTrafTopNEntry 12 }

olTRTrafTopNOutMulticastFrames OBJECT-TYPE
  SYNTAX Counter
  ACCESS read-only
  STATUS mandatory
  DESCRIPTION
      "The number of frames transmitted by this address
      that were directed to a multicast address 
      during the last TopN data collection period.
      Note that this number does not include frames
      directed to the broadcast address."
  ::= { olTRTrafTopNEntry 13 }



olTRTrafTopNSummaryTable OBJECT-TYPE
  SYNTAX SEQUENCE OF OlTRTrafTopNSummaryEntry
  ACCESS not-accessible
  STATUS mandatory
  DESCRIPTION
      "A list containing information from olTRTrafTopNTable
	provided for the convenience of network management stations
	that wish to obtain this information in condensed form."
  ::= { olTRnet 11 }

olTRTrafTopNSummaryEntry OBJECT-TYPE
  SYNTAX OlTRTrafTopNSummaryEntry
  ACCESS not-accessible
  STATUS mandatory
  DESCRIPTION
      "A segment of the Top N list for a particular statistic."
  INDEX { olTRTrafTopNSummaryNetID,
		olTRTrafTopNSummaryStatistic,
		olTRTrafTopNSummaryIndex }
  ::= { olTRTrafTopNSummaryTable 1 }

OlTRTrafTopNSummaryEntry ::= SEQUENCE {
  olTRTrafTopNSummaryNetID               INTEGER,
  olTRTrafTopNSummaryStatistic		  INTEGER,
  olTRTrafTopNSummaryIndex               INTEGER,
  olTRTrafTopNSummaryStations		OCTET STRING
}

olTRTrafTopNSummaryNetID OBJECT-TYPE
        SYNTAX INTEGER {
                isolated(2),
                token-ring-1(9),
                token-ring-2(10),
                token-ring-3(11),
                token-ring-4(12),
                token-ring-5(13),
                token-ring-6(14),
                token-ring-7(15)
                }
        ACCESS read-only
        STATUS mandatory
        DESCRIPTION
                "The network index that uniquely identifies this network.
                One of token-ring-1 through token-ring-7 or isolated."
        ::= { olTRTrafTopNSummaryEntry 1 }

olTRTrafTopNSummaryStatistic OBJECT-TYPE
  SYNTAX INTEGER {
	  olTRTrafTopNSummaryInFrames(1),
	  olTRTrafTopNSummaryOutFrames(2),
	  olTRTrafTopNSummaryInOctets(3),
	  olTRTrafTopNSummaryOutOctets(4),
	  olTRTrafTopNSummaryOutErrors(5),
	  olTRTrafTopNSummaryOutBroadcastFrames(6),
	  olTRTrafTopNSummaryOutMulticastFrames(7)
  }
  ACCESS read-write
  STATUS mandatory
  DESCRIPTION
      "The object representing the statistic for each station that this
      portion of the olTRTrafTopNSummaryTable is sorted on."
    ::= { olTRTrafTopNSummaryEntry 2 }

olTRTrafTopNSummaryIndex OBJECT-TYPE
  SYNTAX INTEGER
  ACCESS read-only
  STATUS mandatory
  DESCRIPTION
	"An index that uniquely identifies an entry in
	the olTRTrafTopNSummary table among those in the same network
	and for the same olTRTrafTopNSummaryStatistic.
	The number of entries for this portion of olTRTrafTopNSummaryTable
	is number of entries for the corresponding portion of
	olTRTrafTopNTable divided by 12 (rounded up to the next integer)."
  ::= { olTRTrafTopNSummaryEntry 3 }

olTRTrafTopNSummaryStations OBJECT-TYPE
        SYNTAX OCTET STRING
        ACCESS read-only
        STATUS mandatory
        DESCRIPTION
                "A concatonated list of (up to 12) MAC addresses,
		their associated slot and port, and a statistic value
		for traffic associated with stations on the ring.  Each entry
		has 36 octets. The first 6 octets are the MAC address.
                The 7th octet is the slot ID (or 255 if it is external
                to the concentrator or 254 if it is on a remote ring).
		The 8th is the port ID (or 255 if it is external to the
		concentrator or 254 if it is on a remote ring).
                The 9th through 36th octets contain the values of the
		statistics olTRTrafTopNInFrames, olTRTrafTopNOutFrames,
		olTRTrafTopNInOctets, olTRTrafTopNOutOctets,
		olTRTrafTopNOutErrors, olTRTrafTopNOutBroadcastFrames,
		and olTRTrafTopNOutMulticastFrames.  Each statistic is
		represented in 4 octets, most significant octet first.
                The stations are in order of decreasing values of the
		statistic referenced by olTRTrafTopNStatistic."
        ::= { olTRTrafTopNSummaryEntry 4 }


END
