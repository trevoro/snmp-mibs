--
--  This is a SNMPv1 translation of Digital Equipment Corporation's LAN
--  Emulation Configuration Server MIB.
--
--  Initial translation was done by the tool
--          SMIC (the next generation) version 1.6.31
--
--  The machine-generated MIB was then modified to remove all remaining
--  SNMP version 2 constructs.
--

DEC-LECS-MIB DEFINITIONS ::= BEGIN

IMPORTS

    Counter, TimeTicks
            FROM RFC1155-SMI
    OBJECT-TYPE
            FROM RFC-1212
    decMIBextension
            FROM DECATM-MIB;


decLecsMIB OBJECT IDENTIFIER ::= { decMIBextension 31 }

-- MODULE-IDENTITY
--  LastUpdated
--    9510301200Z
--  OrgName
--    TBD
--  ContactInfo
--    Digital Equipment Corporation
--     550 King Street
--     Littleton, MA  01460
--     United States of America
--  Descr
--    This is a MIB module for managing ATM Emulated
--     LANs and LAN Emulation Configuration Servers.

decElanAdminGroup OBJECT IDENTIFIER ::= { decLecsMIB 1 }
decElanConfGroup OBJECT IDENTIFIER ::= { decLecsMIB 2 }
decElanLecsGroup OBJECT IDENTIFIER ::= { decLecsMIB 3 }
decElanLecsConfGroup OBJECT IDENTIFIER ::= { decElanLecsGroup 1 }
decElanLecsFaultGroup OBJECT IDENTIFIER ::= { decElanLecsGroup 2 }
decElanLecsStatGroup OBJECT IDENTIFIER ::= { decElanLecsGroup 3 }
decElanAdminPolicyVal OBJECT IDENTIFIER ::= { decElanAdminGroup 1 }
assignByAtmAddr OBJECT IDENTIFIER ::= { decElanAdminPolicyVal 1 }
assignByMacAddr OBJECT IDENTIFIER ::= { decElanAdminPolicyVal 2 }
assignByRouteDescriptor OBJECT IDENTIFIER ::= { decElanAdminPolicyVal 3 }
assignByElanName OBJECT IDENTIFIER ::= { decElanAdminPolicyVal 4 }
assignByCompatibility OBJECT IDENTIFIER ::= { decElanAdminPolicyVal 5 }
decLecsMIBConformance OBJECT IDENTIFIER ::= { decLecsMIB 4 }
decLecsMIBGroups OBJECT IDENTIFIER ::= { decLecsMIBConformance 1 }
decLecsMIBCompliances OBJECT IDENTIFIER ::= { decLecsMIBConformance 2 }

-- DecElanLocalIndex ::= INTEGER
-- TEXTUAL-CONVENTION
--  Status
--    mandatory
--  Descr
--    A unique number identifying an
--     Emulated LAN.  This number is only
--     used locally by the agent to
--     distinguish between ELANs.  This
--     number is maintained locally by
--     the agent that is managing the ELANs.

-- DecAtmLaneMask ::= OCTET STRING(SIZE(20))
-- TEXTUAL-CONVENTION
--  Status
--    mandatory
--  Descr
--    A twenty-octet binary string, containing a
--     standard ATM Forum address mask.

-- DecTlvSelectorIndexType ::= INTEGER
-- TEXTUAL-CONVENTION
--  Status
--    mandatory
--  Descr
--    An arbitrary integer used in identifying
--     a set of TLV encodings.  This number
--     is locally managed by the agent.

-- DecPolicySelectorIndexType ::= INTEGER
-- TEXTUAL-CONVENTION
--  Status
--    mandatory
--  Descr
--    An arbitrary integer used in identifying
--     a set of LEC assignment policies.  This
--     number is locally managed by the agent.

-- DecLecsErrLogIndexType ::= INTEGER
-- TEXTUAL-CONVENTION
--  Status
--    mandatory
--  Descr
--    An arbitrary integer used in identifying
--     an error log associated with a LECS.

decElanConfNextId OBJECT-TYPE
    SYNTAX INTEGER
    ACCESS read-only
    STATUS mandatory
    DESCRIPTION
        "The next available ELAN index provided
         by the agent.  The value of this object
         can be used as the index to the
         decElanConfTable during row creation."
    ::= { decElanConfGroup 1 }

decElanConfTable OBJECT-TYPE
    SYNTAX SEQUENCE OF DecElanConfEntry
    ACCESS not-accessible
    STATUS mandatory
    DESCRIPTION
        "This table describes all of the Emulated
         LANs (ELANs) that this agent manages.  An
         emulated LAN is defined by the ELAN name,
         a set of TLVs, and other parameters.
        
         After an ELAN is created, members of the
         ELAN such as a LAN Emulation Server (LES)
         or Client (LEC) can be added to the ELAN,
         using their respective tables."
    ::= { decElanConfGroup 2 }

decElanConfEntry OBJECT-TYPE
    SYNTAX DecElanConfEntry
    ACCESS not-accessible
    STATUS mandatory
    DESCRIPTION
        "Each entry in this table represents an
         Emulated LAN.  Objects elanConfIndex
         and elanConfRowStatus are required
         during row creation and deletion."
    INDEX { decElanConfIndex }
    ::= { decElanConfTable 1 }

DecElanConfEntry ::= SEQUENCE {
    decElanConfIndex INTEGER,
    decElanConfName OCTET STRING,
    decElanConfTlvIndex INTEGER,
    decElanConfLanType INTEGER,
    decElanConfMaxFrameSize INTEGER,
    decElanConfAdminStatus INTEGER,
    decElanConfDefaultElan INTEGER,
    decElanConfRowStatus INTEGER
    }

decElanConfIndex OBJECT-TYPE
    SYNTAX INTEGER
    ACCESS read-only
    STATUS mandatory
    DESCRIPTION
        "A value which uniquely identifies a
         conceptual row in the decElanConfTable.
        
         If the conceptual row identified by this
         value of decElanConfIndex is recreated
         following an agent restart, the same value
         of elanConfIndex must be used to identify
         the recreated row."
    ::= { decElanConfEntry 1 }

decElanConfName OBJECT-TYPE
    SYNTAX OCTET STRING(SIZE(0..32))
    ACCESS read-write
    STATUS mandatory
    DESCRIPTION
        "The name of this Emulated LAN entry.
        
         When this object's length is zero, the
         ELAN name is not specified, and clients
         that are assigned to the ELAN will also
         have zero-length strings for their ELAN
         names."
    REFERENCE
        "LAN Emulation Over ATM Specification -
         version 1.0. C5."
    DEFVAL { "" }
    ::= { decElanConfEntry 2 }

decElanConfTlvIndex OBJECT-TYPE
    SYNTAX INTEGER
    ACCESS read-write
    STATUS mandatory
    DESCRIPTION
        "The value of this object identifies the
         rows in the decLecsTlvTable which apply
         to this ELAN."
    ::= { decElanConfEntry 3 }

decElanConfLanType OBJECT-TYPE
    SYNTAX INTEGER {
        other(1),
        s8023(2),
        s8025(3)
        }
    ACCESS read-write
    STATUS mandatory
    DESCRIPTION
        "The LAN type of this ELAN entry."
    REFERENCE
        "LAN Emulation Over ATM Specification -
         version 1.0. S2."
    DEFVAL { other }
    ::= { decElanConfEntry 4 }

decElanConfMaxFrameSize OBJECT-TYPE
    SYNTAX INTEGER {
        unspecified(1),
        max1516(2),
        max4544(3),
        max9234(4),
        max18190(5)
        }
    ACCESS read-write
    STATUS mandatory
    DESCRIPTION
        "The maximum data frame size of this
         ELAN entry."
    REFERENCE
        "LAN Emulation Over ATM Specification -
         version 1.0. S3."
    DEFVAL { unspecified }
    ::= { decElanConfEntry 5 }

decElanConfAdminStatus OBJECT-TYPE
    SYNTAX INTEGER {
        enabled(1),
        disabled(2)
        }
    ACCESS read-write
    STATUS mandatory
    DESCRIPTION
        "This object is used to enable and disable
         ELANs.  When an ELAN is 'disabled(2)', the
         LECS will not tell clients about the ELAN.
        
         Note that this object has no effect on the
         operation of the LES and the BUS -- or the
         behavior of manually-configured clients."
    DEFVAL { enabled }
    ::= { decElanConfEntry 6 }

decElanConfDefaultElan OBJECT-TYPE
    SYNTAX INTEGER {
        true(1),
        false(2)
        }
    ACCESS read-write
    STATUS mandatory
    DESCRIPTION
        "This object is used to choose which ELANs
         are considered to be default ELANs for the
         purposes of 'assignByCompatibility' policy
         matching.
        
         Clients are matched against default ELANs
         on the basis of LAN Type and Maximum Data
         Frame Size."
    DEFVAL { false }
    ::= { decElanConfEntry 7 }

decElanConfRowStatus OBJECT-TYPE
    SYNTAX INTEGER {
        active(1),
        notInService(2),
        notReady(3),
        createAndGo(4),
        createAndWait(5),
        destroy(6)
        }
    ACCESS read-write
    STATUS mandatory
    DESCRIPTION
        "This object is used to create or delete
         entries in the decElanConfTable."
    REFERENCE
        "RFC 1443, Textual Conventions for Version 2
         of the Simple Network Management Protocol."
    ::= { decElanConfEntry 8 }

decElanLesTable OBJECT-TYPE
    SYNTAX SEQUENCE OF DecElanLesEntry
    ACCESS not-accessible
    STATUS mandatory
    DESCRIPTION
        "This table describes the LESes for the
         ELANs specified in the decElanConfTable.
        
         Each ELAN can have more than one LES
         providing LAN Emulation services.  Each
         LES can only service one ELAN.
        
         The table is indexed by decElanConfIndex,
         which points to the ELAN that this LES is
         providing service to, and decElanLesIndex,
         which uniquely identifies a LES.
        
         This table is only used for configuration
         of ELANs; that is, to say, creating a LES
         in this table does not instantiate a LES
         in the network.  (That is done in the LES
         MIB.)"
    ::= { decElanConfGroup 3 }

decElanLesEntry OBJECT-TYPE
    SYNTAX DecElanLesEntry
    ACCESS not-accessible
    STATUS mandatory
    DESCRIPTION
        "Each entry in this table represents 
         a LES/Emulated LAN pair.  Objects
         decElanLesAtmAddress and decElanLesRowStatus
         are required during row creation."
    INDEX { decElanConfIndex, decElanLesIndex }
    ::= { decElanLesTable 1 }

DecElanLesEntry ::= SEQUENCE {
    decElanLesIndex INTEGER,
    decElanLesAtmAddress OCTET STRING,
    decElanLesRowStatus INTEGER
    }

decElanLesIndex OBJECT-TYPE
    SYNTAX INTEGER
    ACCESS read-only
    STATUS mandatory
    DESCRIPTION
        "An arbitrary number which uniquely
         identifies the LES this entry pertains
         to."
    ::= { decElanLesEntry 1 }

decElanLesAtmAddress OBJECT-TYPE
    SYNTAX OCTET STRING(SIZE(0..20))
    ACCESS read-write
    STATUS mandatory
    DESCRIPTION
        "The ATM address of the LES entry.  If
         a LECS is supported, the value of this
         object is the LES ATM address that the
         LECS returns to a LEC in the CONFIGURE
         response.  If a LECS is not supported,
         this is more or less a place where the
         manager can note which LES ATM address
         must be manually provided to each LEC."
    DEFVAL { "" }
    ::= { decElanLesEntry 2 }

decElanLesRowStatus OBJECT-TYPE
    SYNTAX INTEGER {
        active(1),
        notInService(2),
        notReady(3),
        createAndGo(4),
        createAndWait(5),
        destroy(6)
        }
    ACCESS read-write
    STATUS mandatory
    DESCRIPTION
        "This object is used to create or delete
         entries in this table."
    REFERENCE
        "RFC 1443, Textual Conventions for Version 2
         of the Simple Network Management Protocol."
    ::= { decElanLesEntry 3 }

decElanPolicyTable OBJECT-TYPE
    SYNTAX SEQUENCE OF DecElanPolicyEntry
    ACCESS not-accessible
    STATUS mandatory
    DESCRIPTION
        "This table describes all of the policies
         which the system uses for assigning LECs
         to ELANs.
        
         When a LECS receives a Configure request,
         it checks the policies in this table to
         determine which ELAN and LES the LEC will
         join.  Policies with the highest priority
         (i.e., the smallest decElanPolicyPriority)
         are evaluated first.  Policies which have
         the same priority are evaluated at the same
         time with the AND operation.
        
         This table is indexed by a selector index
         and a policy index.  The policy index
         uniquely identifies a policy, while the
         selector index allows different LECSes to
         use different sets of policies."
    ::= { decElanConfGroup 4 }

decElanPolicyEntry OBJECT-TYPE
    SYNTAX DecElanPolicyEntry
    ACCESS not-accessible
    STATUS mandatory
    DESCRIPTION
        "Each entry in this table represents a
         policy supported by the entity which 
         provides LAN Emulation configuration 
         services.  Each policy can be used to
         evaluate the CONFIGURE request from
         the LEC in determining which ELAN it
         belongs to."
    INDEX { decElanPolicySelectorIndex, decElanPolicyIndex }
    ::= { decElanPolicyTable 1 }

DecElanPolicyEntry ::= SEQUENCE {
    decElanPolicySelectorIndex INTEGER,
    decElanPolicyIndex INTEGER,
    decElanPolicyPriority INTEGER,
    decElanPolicyType OBJECT IDENTIFIER,
    decElanPolicyRowStatus INTEGER
    }

decElanPolicySelectorIndex OBJECT-TYPE
    SYNTAX INTEGER
    ACCESS read-only
    STATUS mandatory
    DESCRIPTION
        "The value of this object indicates
         a group of policies that can be selected
         by an ELAN configuration service
         provider (such as the LECS)."
    ::= { decElanPolicyEntry 1 }

decElanPolicyIndex OBJECT-TYPE
    SYNTAX INTEGER(1..65000)
    ACCESS read-only
    STATUS mandatory
    DESCRIPTION
        "The value of this object uniquely
         identifies a single policy entry in
         this table. "
    ::= { decElanPolicyEntry 2 }

decElanPolicyPriority OBJECT-TYPE
    SYNTAX INTEGER(1..65000)
    ACCESS read-write
    STATUS mandatory
    DESCRIPTION
        "The priority of this policy entry.
         Policies are evaluated by the entity
         which provides ELAN configuration service
         (i.e., LECS) in order of their priorities.
         Policies with the same priority values
         should be evaluated at the same time with
         an AND operation.  That is, to say, if one
         of the policies with the same priority
         is not met, the evaluation should fail.
         The value 1 has the highest priority."
    DEFVAL { 1 }
    ::= { decElanPolicyEntry 3 }

decElanPolicyType OBJECT-TYPE
    SYNTAX OBJECT IDENTIFIER
    ACCESS read-write
    STATUS mandatory
    DESCRIPTION
        "The type of this policy."
    ::= { decElanPolicyEntry 4 }

decElanPolicyRowStatus OBJECT-TYPE
    SYNTAX INTEGER {
        active(1),
        notInService(2),
        notReady(3),
        createAndGo(4),
        createAndWait(5),
        destroy(6)
        }
    ACCESS read-write
    STATUS mandatory
    DESCRIPTION
        "This object is used to create or delete
         entries in the decElanPolicyTable."
    REFERENCE
        "RFC 1443, Textual Conventions for Version 2
         of the Simple Network Management Protocol."
    ::= { decElanPolicyEntry 5 }

decElanLecAtmAddrTable OBJECT-TYPE
    SYNTAX SEQUENCE OF DecElanLecAtmAddrEntry
    ACCESS not-accessible
    STATUS mandatory
    DESCRIPTION
        "This table is used to assign a LEC
         to an ELAN by ATM address.
         When the 'assign by ATM address' policy is
         used, this table is used to specify
         the LEC's ATM address or portion of an ATM
         address.  The ATM address is used by
         the LECS or other entity which serves
         the LANE configuration function to
         determine the ELAN membership.
        
         This table is indexed
         by the decElanConfIndex which points
         to the ELAN this LEC belongs, the
         decElanLesIndex which points to the
         LES this LEC should join, the
         LEC's ATM address and an ATM address
         mask.  Portions of an ATM address
         can be used in determining ELAN
         membership by using both the ATM
         address and the mask."
    ::= { decElanConfGroup 5 }

decElanLecAtmAddrEntry OBJECT-TYPE
    SYNTAX DecElanLecAtmAddrEntry
    ACCESS not-accessible
    STATUS mandatory
    DESCRIPTION
        "Each entry represents a LEC to ELAN
        binding."
    INDEX { decElanConfIndex, decElanLesIndex, decElanLecAtmAddress,
            decElanLecAtmMask }
    ::= { decElanLecAtmAddrTable 1 }

DecElanLecAtmAddrEntry ::= SEQUENCE {
    decElanLecAtmAddress OCTET STRING,
    decElanLecAtmMask OCTET STRING,
    decElanLecAtmRowStatus INTEGER
    }

decElanLecAtmAddress OBJECT-TYPE
    SYNTAX OCTET STRING(SIZE(0..20))
    ACCESS read-only
    STATUS mandatory
    DESCRIPTION
        "The value of this object is the
         ATM address of a LAN Emulation
         client.  This object and the
         object decElanLecAtmMask are used
         to form an ATM address or portion
         of an ATM address to be used
         by the LECS in determining the
         ELAN membership when the policy
         of this LECS is by ATM address."
    ::= { decElanLecAtmAddrEntry 1 }

decElanLecAtmMask OBJECT-TYPE
    SYNTAX OCTET STRING(SIZE(0..20))
    ACCESS read-only
    STATUS mandatory
    DESCRIPTION
        "The ATM address mask associated with
         the object decElanLecAtmAddress.  The value
         of the mask is an ATM address with
         the don't care portion set to zero
         and the valid ATM address portion set to one."
    ::= { decElanLecAtmAddrEntry 2 }

decElanLecAtmRowStatus OBJECT-TYPE
    SYNTAX INTEGER {
        active(1),
        notInService(2),
        notReady(3),
        createAndGo(4),
        createAndWait(5),
        destroy(6)
        }
    ACCESS read-write
    STATUS mandatory
    DESCRIPTION
        "This object is used to create or delete
         entries in this table."
    REFERENCE
        "RFC 1443, Textual Conventions for Version 2
         of the Simple Network Management Protocol."
    ::= { decElanLecAtmAddrEntry 3 }

decElanLecMacAddrTable OBJECT-TYPE
    SYNTAX SEQUENCE OF DecElanLecMacAddrEntry
    ACCESS not-accessible
    STATUS mandatory
    DESCRIPTION
        "This table is used to assign a LEC
         to an ELAN by MAC address.
         When the 'assign by MAC address' policy
         is used, this table is used to specify
         the LEC's ELAN membership by MAC
         address.  This table is indexed
         by the decElanConfIndex which points
         to the ELAN this LEC belongs, the
         decElanLesIndex which points to the
         LES this LEC should join, and the
         LEC's MAC address."
    ::= { decElanConfGroup 6 }

decElanLecMacAddrEntry OBJECT-TYPE
    SYNTAX DecElanLecMacAddrEntry
    ACCESS not-accessible
    STATUS mandatory
    DESCRIPTION
        "Each entry represents a LEC to ELAN
        binding.  Object elanLecMacRowStatus
        is required during row creation or
        deletion."
    INDEX { decElanConfIndex, decElanLesIndex, decElanLecMacAddress }
    ::= { decElanLecMacAddrTable 1 }

DecElanLecMacAddrEntry ::= SEQUENCE {
    decElanLecMacAddress OCTET STRING,
    decElanLecMacRowStatus INTEGER
    }

decElanLecMacAddress OBJECT-TYPE
    SYNTAX OCTET STRING(SIZE(6))
    ACCESS read-only
    STATUS mandatory
    DESCRIPTION
        "The value of this object is the
         MAC address of a LAN Emulation
         client.  When a CONFIGURE request
         is received with this ATM address,
         it will be assigned to the ELAN
         which elanConfIndex is pointing
         to."
    ::= { decElanLecMacAddrEntry 1 }

decElanLecMacRowStatus OBJECT-TYPE
    SYNTAX INTEGER {
        active(1),
        notInService(2),
        notReady(3),
        createAndGo(4),
        createAndWait(5),
        destroy(6)
        }
    ACCESS read-write
    STATUS mandatory
    DESCRIPTION
        "This object is used to create or
         delete entries in this table."
    REFERENCE
        "RFC 1443, Textual Conventions for Version 2
         of the Simple Network Management Protocol."
    ::= { decElanLecMacAddrEntry 2 }

decElanLecRdTable OBJECT-TYPE
    SYNTAX SEQUENCE OF DecElanLecRdEntry
    ACCESS not-accessible
    STATUS mandatory
    DESCRIPTION
        "This table is used to assign a LEC
         to an ELAN by Route Descriptor.
         When the 'by Route Descriptor' policy is 
         used, this table is used to specify
         the LEC's ELAN membership by Route
         Descriptor.  This table is indexed
         by the decElanConfIndex which points
         to the ELAN this LEC belongs, the
         decElanLesIndex which points to the
         LES this LEC should join, and the
         LEC's Route Descriptors."
    ::= { decElanConfGroup 7 }

decElanLecRdEntry OBJECT-TYPE
    SYNTAX DecElanLecRdEntry
    ACCESS not-accessible
    STATUS mandatory
    DESCRIPTION
        "Each entry represents a LEC to ELAN
        binding."
    INDEX { decElanConfIndex, decElanLesIndex, decElanLecRdSegId,
            decElanLecRdBridgeNum }
    ::= { decElanLecRdTable 1 }

DecElanLecRdEntry ::= SEQUENCE {
    decElanLecRdSegId INTEGER,
    decElanLecRdBridgeNum INTEGER,
    decElanLecRdRowStatus INTEGER
    }

decElanLecRdSegId OBJECT-TYPE
    SYNTAX INTEGER(0..4095)
    ACCESS read-only
    STATUS mandatory
    DESCRIPTION
        "The LAN ID portion of the IEEE 802.5
         route descriptor associated with this
         conceptual row."
    ::= { decElanLecRdEntry 1 }

decElanLecRdBridgeNum OBJECT-TYPE
    SYNTAX INTEGER(0..15)
    ACCESS read-only
    STATUS mandatory
    DESCRIPTION
        "The Bridge Number portion of the
         IEEE 802.5 route descriptor associated
         with this conceptual row."
    ::= { decElanLecRdEntry 2 }

decElanLecRdRowStatus OBJECT-TYPE
    SYNTAX INTEGER {
        active(1),
        notInService(2),
        notReady(3),
        createAndGo(4),
        createAndWait(5),
        destroy(6)
        }
    ACCESS read-write
    STATUS mandatory
    DESCRIPTION
        "This object is used to create or
         destroy entries in this table."
    REFERENCE
        "RFC 1443, Textual Conventions for Version 2
         of the Simple Network Management Protocol."
    ::= { decElanLecRdEntry 3 }

decLecsConfNextId OBJECT-TYPE
    SYNTAX INTEGER
    ACCESS read-only
    STATUS mandatory
    DESCRIPTION
        "The next available LECS index.  The
        value of this object can be used as
        the index to the decLecsConfTable during
        creation."
    ::= { decElanLecsConfGroup 1 }

decLecsConfTable OBJECT-TYPE
    SYNTAX SEQUENCE OF DecLecsConfEntry
    ACCESS not-accessible
    STATUS mandatory
    DESCRIPTION
        "This table contains the configuration 
         information of all the LECSes this agent
         manages.  This table can also be
         used to create, delete or configure
         a LECS."
    ::= { decElanLecsConfGroup 2 }

decLecsConfEntry OBJECT-TYPE
    SYNTAX DecLecsConfEntry
    ACCESS not-accessible
    STATUS mandatory
    DESCRIPTION
        "Each entry represents a LECS this
         agent maintains.
        
         Objects decLecsAtmIfIndex, decLecsAtmAddrSpec,
         and decLecsAtmAddrMask cannot be modified
         unless the decLecsAdminStatus is set to
         down(2).  Changes to this object do not take
         effect until the decLecsAdminStatus is set
         to up(1)."
    INDEX { decLecsConfIndex }
    ::= { decLecsConfTable 1 }

DecLecsConfEntry ::= SEQUENCE {
    decLecsConfIndex INTEGER,
    decLecsAtmIfIndex INTEGER,
    decLecsAtmAddrSpec OCTET STRING,
    decLecsAtmAddrMask OCTET STRING,
    decLecsAtmAddrActual OCTET STRING,
    decLecsPolicySelIndex INTEGER,
    decLecsLastInitialized TimeTicks,
    decLecsOperStatus INTEGER,
    decLecsAdminStatus INTEGER,
    decLecsRowStatus INTEGER
    }

decLecsConfIndex OBJECT-TYPE
    SYNTAX INTEGER
    ACCESS read-only
    STATUS mandatory
    DESCRIPTION
        "An arbitrary integer which represents
         a LECS this agent manages.
        
         If the conceptual row identified by this value
         of decLecsConfIndex is recreated following an
         agent restart, the same value of
         decLecsConfIndex must be used to identify the
         recreated row."
    ::= { decLecsConfEntry 1 }

decLecsAtmIfIndex OBJECT-TYPE
    SYNTAX INTEGER
    ACCESS read-write
    STATUS mandatory
    DESCRIPTION
        "The ATM interface on which the LECS receives
         CONFIGURE requests.
        
         This value must match an existing value in
         the ifTable.  This object is set to zero when
         the ATM interface is not specified or the LECS
         uses more than one ATM interface."
    DEFVAL { '0'h }
    ::= { decLecsConfEntry 2 }

decLecsAtmAddrSpec OBJECT-TYPE
    SYNTAX OCTET STRING(SIZE(0..20))
    ACCESS read-write
    STATUS mandatory
    DESCRIPTION
        "An ATM  address specified by  the  
         network or local management that, 
         with the ATM address mask, determines
         a  portion of  the  ATM address  that 
         the  LECS on the designated ATM interface  
         will use  to derive the actual ATM
         address from the network or ILMI.  The
         derived ATM address is specified in the
         object decLecsAtmAddrActual, which is
         used to receive CONFIGURE requests.
         The value of this object, if not
         specified, is defaulted to the 
         well-known LECS ATM address specified
         in the LAN Emulation Spec. 1.0."
    DEFVAL { '4700790000000000000000000000A03E00000100'h }
    ::= { decLecsConfEntry 3 }

decLecsAtmAddrMask OBJECT-TYPE
    SYNTAX OCTET STRING(SIZE(20))
    ACCESS read-write
    STATUS mandatory
    DESCRIPTION
        "The ATM address mask associated with
         the object decLecsAtmAddrSpec.  The value
         of the mask is an ATM address with
         the don't care portion set to zero
         and the valid ATM address portion set to one."
    DEFVAL { 'FFFFFFFFFFFFFFFFFFFFFFFFFFFFFFFFFFFFFFFF'h }
    ::= { decLecsConfEntry 4 }

decLecsAtmAddrActual OBJECT-TYPE
    SYNTAX OCTET STRING(SIZE(0..20))
    ACCESS read-only
    STATUS mandatory
    DESCRIPTION
        "The resulting ATM address at which the   
         LECS is accepting CONFIGURE
         requests on the interface indicated
         by the object decLecsAtmIfIndex.
         This address is the result of the 
         specified ATM address, its mask and 
         interaction through the ILMI  with  the  
         switch.  Note that this object is only 
         valid when the corresponding
         decLecsOperStatus is 'up'."
    ::= { decLecsConfEntry 5 }

decLecsPolicySelIndex OBJECT-TYPE
    SYNTAX INTEGER
    ACCESS read-only
    STATUS mandatory
    DESCRIPTION
        "The set of policies used
         by this LECS in determining
         requesters ELAN membership.
         The policies are defined in
         the decElanPolicyTable.  The value
         of this object must exist in the
         decElanPolicyTable."
    ::= { decLecsConfEntry 6 }

decLecsLastInitialized OBJECT-TYPE
    SYNTAX TimeTicks
    ACCESS read-only
    STATUS mandatory
    DESCRIPTION
        "The time (in hundredths of a second)
         since the LECS was last re-initialized."
    ::= { decLecsConfEntry 7 }

decLecsOperStatus OBJECT-TYPE
    SYNTAX INTEGER {
        other(1),
        up(2),
        down(3)
        }
    ACCESS read-only
    STATUS mandatory
    DESCRIPTION
        " This  object reflects the actual  
        state of  the LECS which  may differ  
        from that   of the  decLecsAdminStatus
        object.   This     can occur    when    
        the  interface ifOperStatus     is   
        'down'   but the   corresponding
        decLecsAdminStatus is 'up'."
    ::= { decLecsConfEntry 8 }

decLecsAdminStatus OBJECT-TYPE
    SYNTAX INTEGER {
        up(1),
        down(2)
        }
    ACCESS read-write
    STATUS mandatory
    DESCRIPTION
        "The desired  state of the  LECS on 
        this interface as prescribed by the 
        operator.   The actions of the agent
        will,  if  at all possible,  eventually  
        result in the desired  state being 
        reflected in the decLecsOperStatus."
    DEFVAL { up }
    ::= { decLecsConfEntry 9 }

decLecsRowStatus OBJECT-TYPE
    SYNTAX INTEGER {
        active(1),
        notInService(2),
        notReady(3),
        createAndGo(4),
        createAndWait(5),
        destroy(6)
        }
    ACCESS read-write
    STATUS mandatory
    DESCRIPTION
        "This object is used to create or
         delete entries in this table."
    REFERENCE
        "RFC 1443, Textual Conventions for Version 2
         of the Simple Network Management Protocol."
    ::= { decLecsConfEntry 10 }

decLecsTlvTable OBJECT-TYPE
    SYNTAX SEQUENCE OF DecLecsTlvEntry
    ACCESS not-accessible
    STATUS mandatory
    DESCRIPTION
        "This table contains all TLVs this
        agent supports.  This includes
        not only the standard TLVs specified
        in the LAN Emulation Spec. 1.0 but
        also the additional parameters
        exchanged between the LECS and LEC.
        This table is indexed by a selector
        index, which allows more than one
        TLV to be selected by an ELAN; and
        the TLV tag, which specifies the type
        of the TLV; and a TLV index which
        is used to distinguish between different
        entries with the same TLV tag."
    ::= { decElanLecsConfGroup 4 }

decLecsTlvEntry OBJECT-TYPE
    SYNTAX DecLecsTlvEntry
    ACCESS not-accessible
    STATUS mandatory
    DESCRIPTION
        "Each entry represents a TLV encoding for use
         with those ELANs whose 'decElanConfTlvIndex'
         equals the 'decLecsTlvSelectorIndex'.
        
         Objects decLecsTlvVal and decLecsTlvRowStatus
         are required during row creation."
    INDEX { decLecsTlvSelectorIndex, decLecsTlvTag, decLecsTlvIndex }
    ::= { decLecsTlvTable 1 }

DecLecsTlvEntry ::= SEQUENCE {
    decLecsTlvSelectorIndex INTEGER,
    decLecsTlvTag OCTET STRING,
    decLecsTlvIndex INTEGER,
    decLecsTlvVal OCTET STRING,
    decLecsTlvRowStatus INTEGER
    }

decLecsTlvSelectorIndex OBJECT-TYPE
    SYNTAX INTEGER
    ACCESS read-only
    STATUS mandatory
    DESCRIPTION
        "The value of this object indicates 
        a group of TLVs that can be selected."
    ::= { decLecsTlvEntry 1 }

decLecsTlvTag OBJECT-TYPE
    SYNTAX OCTET STRING(SIZE(4))
    ACCESS read-only
    STATUS mandatory
    DESCRIPTION
        "The value of this object represents the 
         type of the contents of the decLecsTlvVal 
         field in the entry.  The OUI field
         in this object occupies the first
         ( or most significant )3 octets.  
         The OUI value 00-A0-3E is used for 
         the standard values defined by the ATM 
         Forum specification."
    ::= { decLecsTlvEntry 2 }

decLecsTlvIndex OBJECT-TYPE
    SYNTAX INTEGER(1..2147483647)
    ACCESS read-only
    STATUS mandatory
    DESCRIPTION
        "The index of this TLV encoding entry.  
         The value of this object can be used 
         to distinguish between different entries 
         with the same decLecsTlvTag value."
    ::= { decLecsTlvEntry 3 }

decLecsTlvVal OBJECT-TYPE
    SYNTAX OCTET STRING(SIZE(0..1024))
    ACCESS read-write
    STATUS mandatory
    DESCRIPTION
        "The value of this TLV entry."
    ::= { decLecsTlvEntry 4 }

decLecsTlvRowStatus OBJECT-TYPE
    SYNTAX INTEGER {
        active(1),
        notInService(2),
        notReady(3),
        createAndGo(4),
        createAndWait(5),
        destroy(6)
        }
    ACCESS read-write
    STATUS mandatory
    DESCRIPTION
        "This object is used to create or
         destroy entries in this table"
    ::= { decLecsTlvEntry 5 }

decLecsStatsTable OBJECT-TYPE
    SYNTAX SEQUENCE OF DecLecsStatsEntry
    ACCESS not-accessible
    STATUS mandatory
    DESCRIPTION
        " A (conceptual) table of statistics 
        associated with all
        LECS instances on the device."
    ::= { decElanLecsStatGroup 1 }

decLecsStatsEntry OBJECT-TYPE
    SYNTAX DecLecsStatsEntry
    ACCESS not-accessible
    STATUS mandatory
    DESCRIPTION
        " A (conceptual) row in the 
        decLecsStatsTable which corresponds 
        to the statistics kept by a particular
        instance of a LES."
    INDEX { decLecsConfIndex }
-- Augments decLecsConfEntry
    ::= { decLecsStatsTable 1 }

DecLecsStatsEntry ::= SEQUENCE {
    decLecsStatSuccessful Counter,
    decLecsStatInBadFrames Counter,
    decLecsStatInvalidParam Counter,
    decLecsStatInsufRes Counter,
    decLecsStatAccDenied Counter,
    decLecsStatInvalidReq Counter,
    decLecsStatInvalidDest Counter,
    decLecsStatInvalidAddr Counter,
    decLecsStatNoConf Counter,
    decLecsStatConfError Counter,
    decLecsStatInsufInfo Counter
    }

decLecsStatSuccessful OBJECT-TYPE
    SYNTAX Counter
    ACCESS read-only
    STATUS mandatory
    DESCRIPTION
        "The number of CONFIGURE requests 
        successfully granted since the agent 
        was last initialized."
    ::= { decLecsStatsEntry 1 }

decLecsStatInBadFrames OBJECT-TYPE
    SYNTAX Counter
    ACCESS read-only
    STATUS mandatory
    DESCRIPTION
        "The number of malformed CONFIGURE
        requests dropped by the LECS."
    ::= { decLecsStatsEntry 2 }

decLecsStatInvalidParam OBJECT-TYPE
    SYNTAX Counter
    ACCESS read-only
    STATUS mandatory
    DESCRIPTION
        "The number of CONFIGURE requests 
        rejected due to the invalid request 
        parameters error."
    REFERENCE
        "LAN Emulation Over ATM Spec. v1.0. Table 13"
    ::= { decLecsStatsEntry 3 }

decLecsStatInsufRes OBJECT-TYPE
    SYNTAX Counter
    ACCESS read-only
    STATUS mandatory
    DESCRIPTION
        "The number of CONFIGURE requests rejected due
        to the insufficent resources to grant request 
        error."
    REFERENCE
        "LAN Emulation Over ATM Spec. v1.0. Table 13"
    ::= { decLecsStatsEntry 4 }

decLecsStatAccDenied OBJECT-TYPE
    SYNTAX Counter
    ACCESS read-only
    STATUS mandatory
    DESCRIPTION
        "The number of CONFIGURE requests rejected due
        to the access denied error."
    REFERENCE
        "LAN Emulation Over ATM Spec. v1.0. Table 13"
    ::= { decLecsStatsEntry 5 }

decLecsStatInvalidReq OBJECT-TYPE
    SYNTAX Counter
    ACCESS read-only
    STATUS mandatory
    DESCRIPTION
        "The number of CONFIGURE requests rejected due
        to the invalid requester-id error."
    REFERENCE
        "LAN Emulation Over ATM Spec. v1.0. Table 13"
    ::= { decLecsStatsEntry 6 }

decLecsStatInvalidDest OBJECT-TYPE
    SYNTAX Counter
    ACCESS read-only
    STATUS mandatory
    DESCRIPTION
        "The number of CONFIGURE requests rejected due
        to the invalid destination error."
    REFERENCE
        "LAN Emulation Over ATM Spec. v1.0. Table 13"
    ::= { decLecsStatsEntry 7 }

decLecsStatInvalidAddr OBJECT-TYPE
    SYNTAX Counter
    ACCESS read-only
    STATUS mandatory
    DESCRIPTION
        "The number of CONFIGURE requests rejected due
        to the invalid ATM address error."
    REFERENCE
        "LAN Emulation Over ATM Spec. v1.0. Table 13"
    ::= { decLecsStatsEntry 8 }

decLecsStatNoConf OBJECT-TYPE
    SYNTAX Counter
    ACCESS read-only
    STATUS mandatory
    DESCRIPTION
        "The number of CONFIGURE requests rejected due
        to the LE Client is not recognized error."
    REFERENCE
        "LAN Emulation Over ATM Spec. v1.0. Table 13"
    ::= { decLecsStatsEntry 9 }

decLecsStatConfError OBJECT-TYPE
    SYNTAX Counter
    ACCESS read-only
    STATUS mandatory
    DESCRIPTION
        "The number of CONFIGURE requests rejected due
        to the LE_CONFIGURE error."
    REFERENCE
        "LAN Emulation Over ATM Spec. v1.0. Table 13"
    ::= { decLecsStatsEntry 10 }

decLecsStatInsufInfo OBJECT-TYPE
    SYNTAX Counter
    ACCESS read-only
    STATUS mandatory
    DESCRIPTION
        "The number of CONFIGURE requests rejected due
        to the insufficient information error."
    REFERENCE
        "LAN Emulation Over ATM Spec. v1.0. Table 13"
    ::= { decLecsStatsEntry 11 }

decLecsErrCtlTable OBJECT-TYPE
    SYNTAX SEQUENCE OF DecLecsErrCtlEntry
    ACCESS not-accessible
    STATUS mandatory
    DESCRIPTION
        "This table contains error log control 
         information of all LECS instances.
         This table is an extension to the
         lecsConfTable.  It is used to enable
         or disable error logs for a particular
         LECS entry."
    ::= { decElanLecsFaultGroup 1 }

decLecsErrCtlEntry OBJECT-TYPE
    SYNTAX DecLecsErrCtlEntry
    ACCESS not-accessible
    STATUS mandatory
    DESCRIPTION
        "Each entry represents a LECS entry
        in the decLecsConfTable."
    INDEX { decLecsConfIndex }
-- Augments decLecsConfEntry
    ::= { decLecsErrCtlTable 1 }

DecLecsErrCtlEntry ::= SEQUENCE {
    decLecsErrCtlAdminStatus INTEGER,
    decLecsErrCtlOperStatus INTEGER,
    decLecsErrCtlClearLog INTEGER,
    decLecsErrCtlMaxEntries INTEGER,
    decLecsErrCtlLastEntry INTEGER
    }

decLecsErrCtlAdminStatus OBJECT-TYPE
    SYNTAX INTEGER {
        enable(1),
        disable(2)
        }
    ACCESS read-write
    STATUS mandatory
    DESCRIPTION
        "This object is used to enable/disable error 
         logging for the LECS."
    ::= { decLecsErrCtlEntry 1 }

decLecsErrCtlOperStatus OBJECT-TYPE
    SYNTAX INTEGER {
        other(1),
        active(2),
        outOfRes(3),
        failed(4)
        }
    ACCESS read-only
    STATUS mandatory
    DESCRIPTION
        "This object is used to indicate
        the result of a set operation to the
        object decLecsErrCtlAdminStatus.
        If the error log was successfully
        started, it is in active(2) mode.
        Otherwise, it is set to either
        outOfRes(3) or failed(4) for
        the respective reasons."
    ::= { decLecsErrCtlEntry 2 }

decLecsErrCtlClearLog OBJECT-TYPE
    SYNTAX INTEGER {
        noOp(1),
        clear(2)
        }
    ACCESS read-write
    STATUS mandatory
    DESCRIPTION
        "This object is used to clear the error log
         entries associated with this LECS."
    ::= { decLecsErrCtlEntry 3 }

decLecsErrCtlMaxEntries OBJECT-TYPE
    SYNTAX INTEGER(1..65535)
    ACCESS read-only
    STATUS mandatory
    DESCRIPTION
        "The maximum entries of the error
        log a LECS can support."
    ::= { decLecsErrCtlEntry 4 }

decLecsErrCtlLastEntry OBJECT-TYPE
    SYNTAX INTEGER
    ACCESS read-write
    STATUS mandatory
    DESCRIPTION
        "The index to the last entry in the error
        log table associated with this LECS."
    ::= { decLecsErrCtlEntry 5 }

decLecsErrLogTable OBJECT-TYPE
    SYNTAX SEQUENCE OF DecLecsErrLogEntry
    ACCESS not-accessible
    STATUS mandatory
    DESCRIPTION
        "This table contains error logs
        of the LECS instances enabled
        in the decLecsErrCtlTable.  This table
        is indexed by the LECS instance
        index and an arbitrary integer which
        uniquely identifies an error
        log."
    ::= { decElanLecsFaultGroup 2 }

decLecsErrLogEntry OBJECT-TYPE
    SYNTAX DecLecsErrLogEntry
    ACCESS not-accessible
    STATUS mandatory
    DESCRIPTION
        "Each entry represents a LEC that
         was rejected due to a violation 
         against the policies or an error."
    INDEX { decLecsConfIndex, decLecsErrLogIndex }
    ::= { decLecsErrLogTable 1 }

DecLecsErrLogEntry ::= SEQUENCE {
    decLecsErrLogIndex INTEGER,
    decLecsErrLogAtmAddr OCTET STRING,
    decLecsErrLogErrCode INTEGER,
    decLecsErrLogTime TimeTicks
    }

decLecsErrLogIndex OBJECT-TYPE
    SYNTAX INTEGER
    ACCESS read-only
    STATUS mandatory
    DESCRIPTION
        "An arbitrary integer which uniquely
        identifies an error log entry. This
        number ranges from 1 to the value of 
        the object decLecsErrCtlMaxEntries times
        number of LECS error log capability
        enabled.  The enabling/disabling of
        the error log capability is done in
        the decLecsErrCtlTable."
    ::= { decLecsErrLogEntry 1 }

decLecsErrLogAtmAddr OBJECT-TYPE
    SYNTAX OCTET STRING(SIZE(0..20))
    ACCESS read-only
    STATUS mandatory
    DESCRIPTION
        "The ATM address of the requester
        which sends the CONFIGURE request
        and causes the error to occur. 
        The corresponding error code is
        specified in the object decLecsErrLogErrCode."
    ::= { decLecsErrLogEntry 2 }

decLecsErrLogErrCode OBJECT-TYPE
    SYNTAX INTEGER(0..22)
    ACCESS read-only
    STATUS mandatory
    DESCRIPTION
        "The Error code which indicates the
        cause of the error triggered by the
        CONFIGURE request sent by the
        requester indicated by the value of
        the object decLecsErrLogAtmAddr."
    ::= { decLecsErrLogEntry 3 }

decLecsErrLogTime OBJECT-TYPE
    SYNTAX TimeTicks
    ACCESS read-only
    STATUS mandatory
    DESCRIPTION
        "The sysUpTime when this entry was logged by
         the LECS."
    ::= { decLecsErrLogEntry 4 }

decElanCConfGroup OBJECT IDENTIFIER ::= { decLecsMIBGroups 1 }
-- OBJECT-GROUP
--  Status
--    mandatory
--  Descr
--    A collection of objects providing configuration
--     information about an Emulated LAN.
--  objects
--    decElanConfNextId, decElanConfName, decElanConfTlvIndex, 
--    decElanConfLanType, decElanConfMaxFrameSize, 
--    decElanConfAdminStatus, decElanConfDefaultElan, 
--    decElanConfRowStatus, decElanLesAtmAddress, 
--    decElanLesRowStatus, decElanPolicyPriority, decElanPolicyType, 
--    decElanPolicyRowStatus

decElanLecAssignByAtmGroup OBJECT IDENTIFIER ::= { decLecsMIBGroups 2 }
-- OBJECT-GROUP
--  Status
--    mandatory
--  Descr
--    A collection of objects providing ATM addresses
--    of LECs.
--  objects
--    decElanLecAtmRowStatus

decElanLecAssignByMacGroup OBJECT IDENTIFIER ::= { decLecsMIBGroups 3 }
-- OBJECT-GROUP
--  Status
--    mandatory
--  Descr
--    A collection of objects providing MAC addresses
--    of LECs.
--  objects
--    decElanLecMacRowStatus

decElanLecAssignByRdGroup OBJECT IDENTIFIER ::= { decLecsMIBGroups 4 }
-- OBJECT-GROUP
--  Status
--    mandatory
--  Descr
--    A collection of objects providing Route Descriptors
--    of LECs.
--  objects
--    decElanLecRdRowStatus

decLecsCStatGroup OBJECT IDENTIFIER ::= { decLecsMIBGroups 5 }
-- OBJECT-GROUP
--  Status
--    mandatory
--  Descr
--    A collection of objects providing information
--    about LECS statistics.
--  objects
--    decLecsStatSuccessful, decLecsStatInBadFrames, 
--    decLecsStatInvalidParam, decLecsStatInsufRes, 
--    decLecsStatAccDenied, decLecsStatInvalidReq, 
--    decLecsStatInvalidDest, decLecsStatInvalidAddr, 
--    decLecsStatNoConf, decLecsStatConfError, decLecsStatInsufInfo

decLecsCGroup OBJECT IDENTIFIER ::= { decLecsMIBGroups 6 }
-- OBJECT-GROUP
--  Status
--    mandatory
--  Descr
--    A group of objects used for LECS
--    management only.
--  objects
--    decLecsConfNextId, decLecsAtmIfIndex, decLecsAtmAddrSpec, 
--    decLecsAtmAddrMask, decLecsAtmAddrActual, 
--    decLecsPolicySelIndex, decLecsTlvVal, decLecsTlvRowStatus, 
--    decLecsLastInitialized, decLecsOperStatus, decLecsAdminStatus, 
--    decLecsRowStatus

decLecsCFaultGroup OBJECT IDENTIFIER ::= { decLecsMIBGroups 7 }
-- OBJECT-GROUP
--  Status
--    mandatory
--  Descr
--    A group of objects used for LECS
--     fault management only.
--  objects
--    decLecsErrCtlAdminStatus, decLecsErrCtlOperStatus, 
--    decLecsErrCtlClearLog, decLecsErrCtlMaxEntries, 
--    decLecsErrCtlLastEntry, decLecsErrLogTime, decLecsErrLogIndex, 
--    decLecsErrLogAtmAddr, decLecsErrLogErrCode

decLecsMIBCompliance OBJECT IDENTIFIER ::= { decLecsMIBCompliances 1 }
-- MODULE-COMPLIANCE
--  Status
--    mandatory
--  Descr
--    The compliance statement for SNMP
--    entities which implement the DEC LECS MIB.
--  Module
--    >>current<<
--   MandGroup
--    decElanCConfGroup
--   OptGroup
--    decElanLecAssignByAtmGroup
--   OptGroup
--    decElanLecAssignByMacGroup
--   OptGroup
--    decElanLecAssignByRdGroup
--   OptGroup
--    decLecsCStatGroup
--   OptGroup
--    decLecsCGroup
--   OptGroup
--    decLecsCFaultGroup
--   ObjVar
--    decElanConfName
--   ObjVar
--    decElanConfTlvIndex
--   ObjVar
--    decElanConfLanType
--   ObjVar
--    decElanConfMaxFrameSize
--   ObjVar
--    decElanConfAdminStatus
--   ObjVar
--    decElanConfDefaultElan
--   ObjVar
--    decElanConfRowStatus
--   ObjVar
--    decElanLesAtmAddress
--   ObjVar
--    decElanLesRowStatus
--   ObjVar
--    decElanPolicyPriority
--   ObjVar
--    decElanPolicyType
--   ObjVar
--    decElanPolicyRowStatus
--   ObjVar
--    decElanLecAtmRowStatus
--   ObjVar
--    decElanLecMacRowStatus
--   ObjVar
--    decElanLecRdRowStatus
--   ObjVar
--    decLecsAtmIfIndex
--   ObjVar
--    decLecsAtmAddrSpec
--   ObjVar
--    decLecsAtmAddrMask
--   ObjVar
--    decLecsAdminStatus
--   ObjVar
--    decLecsRowStatus
--   ObjVar
--    decLecsTlvVal
--   ObjVar
--    decLecsTlvRowStatus


END
