ACC-IPROUTING DEFINITIONS ::= BEGIN

    IMPORTS
	 OBJECT-TYPE, IpAddress, TimeTicks, Gauge, Counter FROM RFC1155-SMI
         accTrapLogSeqNum FROM ACC-SYSTEM
	 accBRG, DisplayString, RowStatus, IfIndex, SmdsAddress
             FROM ACC-MIB;
-- IP Routing Group
     accIpRoutingTable  OBJECT-TYPE
			SYNTAX SEQUENCE OF AccIpRoutingEntry
			ACCESS not-accessible
			STATUS mandatory
			DESCRIPTION
			 " Widening of standard IP routing table
			   Entries are added/deleted in conjunction with
			      operations on the standard routing table."
			::= { accBRG 12 }
        accIpRoutingEntry OBJECT-TYPE
                        SYNTAX AccIpRoutingEntry
                        ACCESS not-accessible
                        STATUS mandatory
                        DESCRIPTION
                         " Additional information about a route."
                        INDEX { ipRouteDest }
                        ::= { accIpRoutingTable 1 }
		AccIpRoutingEntry ::= SEQUENCE {
			accIpRouteDestSubnet	IpAddress
			}
	  accIpRouteDestSubnet	OBJECT-TYPE   
			SYNTAX	IpAddress
			ACCESS	read-write
			STATUS	mandatory
			DESCRIPTION
                         " Subnet mask of destination "
			::= { accIpRoutingEntry 2 }

END
