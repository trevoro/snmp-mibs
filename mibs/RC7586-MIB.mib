-- *****************************************************************
-- RC7586.mib:  Codan's 7586 Controller product MIB
--
-- Created by Magdalena Raltcheva
--
-- Copyright (c) 2009 by Codan Limited.
-- All rights reserved.
--
-- *****************************************************************

RC7586-MIB DEFINITIONS ::= BEGIN

IMPORTS
	MODULE-IDENTITY, OBJECT-TYPE,
	NOTIFICATION-TYPE,
	Integer32, TimeTicks,
	IpAddress, Gauge32, Counter32		FROM SNMPv2-SMI
	DisplayString, DateAndTime,
	TEXTUAL-CONVENTION,
	TestAndIncr,TimeInterval, TruthValue			FROM SNMPv2-TC
	satcomMibs 							FROM CODAN-SMI;

rc7586MIB MODULE-IDENTITY
   LAST-UPDATED "200905130000Z"
   ORGANIZATION "Codan Limited."
   CONTACT-INFO
        "       Magda Raltcheva
        Postal: Codan Limited
                81 Graves St.
                Newton 5074
                Australia
        Tel:    +61-8-83050311
        Fax:    +61-8-83050411
        Web:	www.codan.com.au"

	DESCRIPTION
		"The Structure of Management Information for the
		 Codan enterprise.	
		 Copyright(c) 2009 All rights reserved"

	REVISION      "200905130000Z"
	DESCRIPTION
		"1.0 Initial version of this MIB module."
        ::= { satcomMibs 2 }   -- assigned by IANA


-- ***##############################################################***
--              CodanMIB Textual Convention Definitions
-- ***##############################################################***

ComponentRevision ::= TEXTUAL-CONVENTION
    DISPLAY-HINT "vxx.yy"
    STATUS      current
    DESCRIPTION
        "The hex value in the first octet - xx - represents the major revision no.
        and the hex value in the second octet - yy - represents the minor revision no."
    SYNTAX      DisplayString(SIZE(2))


-- ***##############################################################***
--              CodanMIB Textual Convention Definitions for 7586 Controller
-- ***##############################################################***


FaultStatus7586 ::= TEXTUAL-CONVENTION
    STATUS       current
    DESCRIPTION
        "Describes all the possible faults in the system as a bit pattern."
    SYNTAX      BITS {                   
                    dc1fault(0),
                    dc2fault(1), 
					buc1fault(2),
					buc2fault(3),
					lnb1fault(4),
					lnb2fault(5),
					txswfault(6),
					rxswfault(7),
					internalfault(8),
					ref10mhzfault(9)
					}

-- ***##############################################################***
--              CodanMIB Textual Convention Definitions for RBUC
-- ***##############################################################***




-- ***##############################################################***
--              Devices within the 7586 Controller MIB
-- ***##############################################################***

buc1				OBJECT IDENTIFIER ::= { rc7586MIB 1 }
buc2				OBJECT IDENTIFIER ::= { rc7586MIB 2 }
ctrl				OBJECT IDENTIFIER ::= { rc7586MIB 3 }

---------------------------  7586 Controller --------------------------

-- ***##############################################################***
--              Groups within the 7586 Controller MIB
-- ***##############################################################***

settings			OBJECT IDENTIFIER ::= { ctrl 1 }
status				OBJECT IDENTIFIER ::= { ctrl 2 }
info				OBJECT IDENTIFIER ::= { ctrl 3 }

--------------  Settings group 

operationalMode OBJECT-TYPE
    SYNTAX      INTEGER (0..2)
    MAX-ACCESS  read-write
    STATUS      current
    DESCRIPTION
        "Sets 7586 operational mode - Auto, Manual Stream1, Stream2."
    ::= { settings 1 }

onlineStream OBJECT-TYPE
    SYNTAX      INTEGER (1..2)
    MAX-ACCESS  read-write
    STATUS      current
    DESCRIPTION
        "Sets the online stream."
    ::= { settings 2 }

waveguideSwitch OBJECT-TYPE
    SYNTAX      INTEGER (0..2)				
    MAX-ACCESS  read-write
    STATUS      current
    DESCRIPTION
        "Sets Waveguide switch Rx+Tx, Rx/Tx and Tx Only."
    ::= { settings 3 }

startupTime OBJECT-TYPE
    SYNTAX      INTEGER (0..50)
	UNITS      "s"
    MAX-ACCESS  read-write
    STATUS      current
    DESCRIPTION
        "Sets Startup time."
    ::= { settings 4 }

lnbCurrentLimit OBJECT-TYPE
    SYNTAX      DisplayString
	UNITS      "mA"
    MAX-ACCESS  read-write
    STATUS      current
    DESCRIPTION
        "Sets LNB current limits."
    ::= { settings 5 }


ledState OBJECT-TYPE
    SYNTAX      INTEGER (0..1)
    MAX-ACCESS  read-write
    STATUS      current
    DESCRIPTION
        "Sets 7586 LED."
    ::= { settings 6 }

refSource OBJECT-TYPE
    SYNTAX      INTEGER (0..3)
    MAX-ACCESS  read-write
    STATUS      current
    DESCRIPTION
        "Sets 7586 reference state."
    ::= { settings 7 }

refTrim OBJECT-TYPE
    SYNTAX      DisplayString
    MAX-ACCESS  read-write
    STATUS      current
    DESCRIPTION
        "Sets 7586 reference trim."
    ::= { settings 8 }

refThresh OBJECT-TYPE
    SYNTAX      DisplayString
	UNITS      "dBm"
    MAX-ACCESS  read-write
    STATUS      current
    DESCRIPTION
        "Sets 7586 reference alarm treshold."
    ::= { settings 9 }

refPwr OBJECT-TYPE
    SYNTAX      DisplayString
	UNITS      "dBm"
    MAX-ACCESS  read-only
    STATUS      current
    DESCRIPTION
        "Gets 7586 reference power."
    ::= { settings 10 }

-- Network - read only

ipAddr OBJECT-TYPE
    SYNTAX      DisplayString
    MAX-ACCESS  read-only
    STATUS      current
    DESCRIPTION
        "Gets the 7586 IP address."
    ::= { settings 11 }

macAddress OBJECT-TYPE
    SYNTAX      DisplayString
    MAX-ACCESS  read-only
    STATUS      current
    DESCRIPTION
        "Gets the 7586 MAC address."
    ::= { settings 12 }

netmask OBJECT-TYPE
    SYNTAX      DisplayString
    MAX-ACCESS  read-only
    STATUS      current
    DESCRIPTION
        "Gets the 7586 netmask."
    ::= { settings 13 }

gateway OBJECT-TYPE
    SYNTAX      DisplayString
    MAX-ACCESS  read-only
    STATUS      current
    DESCRIPTION
        "Gets the 7586 gateway address."
    ::= { settings 14 }

--------------  Status group 

lnbCurrent OBJECT-TYPE
    SYNTAX      DisplayString
	UNITS      "mA"
    MAX-ACCESS  read-only
    STATUS      current
    DESCRIPTION
        "Sets 7586 LNB current."
    ::= { status 1 }

lnbVoltage OBJECT-TYPE
    SYNTAX      DisplayString
	UNITS      "V"
    MAX-ACCESS  read-only
    STATUS      current
    DESCRIPTION
        "Sets 7586 LNB voltage."
    ::= { status 2 }

faults OBJECT-TYPE
    SYNTAX      INTEGER
    MAX-ACCESS  read-only
    STATUS      current
    DESCRIPTION
        "Gets the current fault status."
    ::= { status 3}

------------------ Info group 

idInfo  OBJECT-TYPE 
    SYNTAX     DisplayString
    MAX-ACCESS read-only
    STATUS     current
    DESCRIPTION
    "Gets the module firmware revision, serial number and model. This string
    will have a zero length if the revision is unknown."
    ::= { info 1 }


---------------------------  RBUCs ------------------------------------

-- ***##############################################################***
--              Groups within the BUC1,BUC2 MIB
-- ***##############################################################***

buc1Configuration	OBJECT IDENTIFIER ::= { buc1 1 }
buc1Status			OBJECT IDENTIFIER ::= { buc1 2 }
buc1Info			OBJECT IDENTIFIER ::= { buc1 3 }

buc2Configuration	OBJECT IDENTIFIER ::= { buc2 1 }
buc2Status			OBJECT IDENTIFIER ::= { buc2 2 }
buc2Info			OBJECT IDENTIFIER ::= { buc2 3 }


-- ####################################################################
-- *** RBUC Configuration groups - run time changing settings ***
-- ####################################################################

-- *** Configuration groups -  ***
buc1TxSettings          OBJECT IDENTIFIER ::= { buc1Configuration 1 }
buc1PktProtocol			OBJECT IDENTIFIER ::= { buc1Configuration 2 }
buc1RCSetting	        OBJECT IDENTIFIER ::= { buc1Configuration 3 }
buc1Freqs				OBJECT IDENTIFIER ::= { buc1Configuration 4 }
buc1Misc				OBJECT IDENTIFIER ::= { buc1Configuration 5 }

buc2TxSettings          OBJECT IDENTIFIER ::= { buc2Configuration 1 }
buc2PktProtocol			OBJECT IDENTIFIER ::= { buc2Configuration 2 }
buc2RCSetting	        OBJECT IDENTIFIER ::= { buc2Configuration 3 }
buc2Freqs				OBJECT IDENTIFIER ::= { buc2Configuration 4 }
buc2Misc				OBJECT IDENTIFIER ::= { buc2Configuration 5 }

-- Tx Settings Group

buc1TxOn OBJECT-TYPE
    SYNTAX      INTEGER (0..1)
    MAX-ACCESS  read-write
    STATUS      current
    DESCRIPTION
        "Sets Tx on/off. Respond -1 if buc1 not connected."
    ::= { buc1TxSettings 1 }

buc2TxOn OBJECT-TYPE
    SYNTAX      INTEGER (0..1)
    MAX-ACCESS  read-write
    STATUS      current
    DESCRIPTION
        "Sets Tx on/off. Respond -1 if buc2 not connected."
    ::= { buc2TxSettings 1 }

buc1TxDefault OBJECT-TYPE
    SYNTAX      INTEGER (0..1)
    MAX-ACCESS  read-write
    STATUS      current
    DESCRIPTION
        "Sets Tx default 1-last 0-off. Respond -1 if buc1 not connected."
    ::= { buc1TxSettings 2 }

buc2TxDefault OBJECT-TYPE
    SYNTAX      INTEGER (0..1)
    MAX-ACCESS  read-write
    STATUS      current
    DESCRIPTION
        "Sets Tx default 1-last 0-off. Respond -1 if buc2 not connected."
    ::= { buc2TxSettings 2 }

buc1TxAttenuator OBJECT-TYPE
    SYNTAX      INTEGER (0..15)
    UNITS      "dBm"
    MAX-ACCESS  read-write
    STATUS      current
    DESCRIPTION
        "Sets/Gets Tx attenuation value in 1dBm steps. Respond -1 if buc1 not connected."
    ::= { buc1TxSettings 3 }

buc2TxAttenuator OBJECT-TYPE
    SYNTAX      INTEGER (0..15)
    UNITS      "dBm"
    MAX-ACCESS  read-write
    STATUS      current
    DESCRIPTION
        "Sets/Gets Tx attenuation value in 1dBm steps. Respond -1 if buc2 not connected."
    ::= { buc2TxSettings 3 }

-- Packet Protocol Settings Group

buc1Protocol	OBJECT-TYPE
    SYNTAX      INTEGER (0..4)
    MAX-ACCESS  read-write
    STATUS      current
    DESCRIPTION
        "Sets/Gets packet protocol 0 - ASCII, 1 - CODAN, 2 - SAbus, 3 - Comstream, 4 - NDSatcom. Respond -1 if buc1 not connected."
    ::= { buc1PktProtocol 1 }

buc2Protocol	OBJECT-TYPE
    SYNTAX      INTEGER (0..4)
    MAX-ACCESS  read-write
    STATUS      current
    DESCRIPTION
        "Sets/Gets packet protocol 0 - ASCII, 1 - CODAN, 2 - SAbus, 3 - Comstream, 4 - NDSatcom. Respond -1 if buc2 not connected."
    ::= { buc2PktProtocol 1 }

buc1Address		OBJECT-TYPE
    SYNTAX      INTEGER
    MAX-ACCESS  read-write
    STATUS      current
    DESCRIPTION
        "Sets/Gets packet address: 0-31 NDSatcom ...Respond -1 if buc1 not connected. "
    ::= { buc1PktProtocol 2 }

buc2Address		OBJECT-TYPE
    SYNTAX      INTEGER
    MAX-ACCESS  read-write
    STATUS      current
    DESCRIPTION
        "Sets/Gets packet address: 0-31 NDSatcom ...Respond -1 if buc2 not connected."
    ::= { buc2PktProtocol 2 }

-- Redundancy Controller Group

buc1Mode OBJECT-TYPE
    SYNTAX      INTEGER (0..2)
    MAX-ACCESS  read-write
    STATUS      current
    DESCRIPTION
        "Sets/Gets redundancy mode 0-none, 1-warm, 2-hot. Respond -1 if buc1 not connected."
    ::= { buc1RCSetting 1 }

buc2Mode OBJECT-TYPE
    SYNTAX      INTEGER (0..2)
    MAX-ACCESS  read-write
    STATUS      current
    DESCRIPTION
        "Sets/Gets redundancy mode 0-none, 1-warm, 2-hot. Respond -1 if buc2 not connected."
    ::= { buc2RCSetting 1 }

buc1OnLine OBJECT-TYPE
    SYNTAX      TruthValue
    MAX-ACCESS  read-write
    STATUS      current
    DESCRIPTION
        "Sets/Gets redundancy mode on on/off line state. Respond -1 if buc1 not connected."
    ::= { buc1RCSetting 2 }

buc2OnLine OBJECT-TYPE
    SYNTAX      TruthValue
    MAX-ACCESS  read-write
    STATUS      current
    DESCRIPTION
        "Sets/Gets redundancy mode on on/off line state. Respond -1 if buc2 not connected."
    ::= { buc2RCSetting 2 }


-- Frequency Group 

buc1RFFreq OBJECT-TYPE
    SYNTAX      INTEGER
    UNITS      "MHz"
    MAX-ACCESS  read-write
    STATUS      current
    DESCRIPTION
        "Sets/Gets the RBUC RF frequency. Respond -1 if buc1 not connected."
    ::= { buc1Freqs 1 }

buc2RFFreq OBJECT-TYPE
    SYNTAX      INTEGER
    UNITS      "MHz"
    MAX-ACCESS  read-write
    STATUS      current
    DESCRIPTION
        "Sets/Gets the RBUC RF frequency. Respond -1 if buc2 not connected."
    ::= { buc2Freqs 1 }

buc1IFFreq OBJECT-TYPE
    SYNTAX      INTEGER
    UNITS      "MHz"
    MAX-ACCESS  read-write
    STATUS      current
    DESCRIPTION
        "Sets/Gets the RBUC IF frequency. Respond -1 if buc1 not connected."
    ::= { buc1Freqs 2 }

buc2IFFreq OBJECT-TYPE
    SYNTAX      INTEGER
    UNITS      "MHz"
    MAX-ACCESS  read-write
    STATUS      current
    DESCRIPTION
        "Sets/Gets the RBUC IF frequency. Respond -1 if buc2 not connected."
    ::= { buc2Freqs 2 }

buc1LOFreq OBJECT-TYPE
    SYNTAX      INTEGER
    UNITS      "MHz"
    MAX-ACCESS  read-write
    STATUS      current
    DESCRIPTION
        "Sets/Gets the RBUC LO frequency. Respond -1 if buc1 not connected."
    ::= { buc1Freqs 3 }

buc2LOFreq OBJECT-TYPE
    SYNTAX      INTEGER
    UNITS      "MHz"
    MAX-ACCESS  read-write
    STATUS      current
    DESCRIPTION
        "Sets/Gets the RBUC LO frequency. Respond -1 if buc2 not connected."
    ::= { buc2Freqs 3 }

-- Miscellaneous Group

buc1SerIf OBJECT-TYPE
    SYNTAX      DisplayString
    MAX-ACCESS  read-write
    STATUS      current
    DESCRIPTION
        "Sets/Gets serial interface - rate, length, parity, stop, terminate RS422/485.
	**** No respond - message if buc1 not connected."
    ::= { buc1Misc 1 }

buc2SerIf OBJECT-TYPE
    SYNTAX      DisplayString
    MAX-ACCESS  read-write
    STATUS      current
    DESCRIPTION
        "Sets/Gets serial interface - rate, length, parity, stop, terminate RS422/485.
	**** No respond - message if buc2 not connected."
    ::= { buc2Misc 1 }

buc1PwrAlarmThresh OBJECT-TYPE
    SYNTAX		DisplayString 
    UNITS      "dB"
    MAX-ACCESS  read-write
    STATUS      current
    DESCRIPTION
        "Sets/Gets power alarm threshold.
	**** No respond - message if buc1 not connected."
    ::= { buc1Misc 2 }

buc2PwrAlarmThresh OBJECT-TYPE
    SYNTAX		DisplayString 
    UNITS      "dB"
    MAX-ACCESS  read-write
    STATUS      current
    DESCRIPTION
        "Sets/Gets power alarm threshold.
	**** No respond - message if buc2 not connected."
    ::= { buc2Misc 2 }

buc1BurstPwrThresh OBJECT-TYPE
    SYNTAX      DisplayString
    UNITS      "dB"
    MAX-ACCESS  read-write
    STATUS      current
    DESCRIPTION
        "Sets/Gets burst power threshold.
	**** No respond - message if buc1 not connected."
    ::= { buc1Misc 3 }

buc2BurstPwrThresh OBJECT-TYPE
    SYNTAX      DisplayString
    UNITS      "dB"
    MAX-ACCESS  read-write
    STATUS      current
    DESCRIPTION
        "Sets/Gets burst power threshold.
	**** No respond - message if buc2 not connected."
    ::= { buc2Misc 3 }

buc1RefSource OBJECT-TYPE
    SYNTAX		DisplayString
    MAX-ACCESS  read-write
    STATUS      current
    DESCRIPTION
        "Sets/Gets reference source 0-external, 1-internal (Only for RBUC).
	**** No respond - message if buc1 not connected."
    ::= { buc1Misc 4 }

buc2RefSource OBJECT-TYPE
    SYNTAX		DisplayString
    MAX-ACCESS  read-write
    STATUS      current
    DESCRIPTION
        "Sets/Gets reference source 0-external, 1-internal (Only for RBUC).
	**** No respond - message if buc2 not connected."
    ::= { buc2Misc 4 }

buc1LEDState OBJECT-TYPE
    SYNTAX		DisplayString
    MAX-ACCESS  read-write
    STATUS      current
    DESCRIPTION
        "Sets/Gets LEDs status on/off (Only for RBUC).
	**** No respond - message if buc1 not connected."
    ::= { buc1Misc 5 }

buc2LEDState OBJECT-TYPE
    SYNTAX		DisplayString
    MAX-ACCESS  read-write
    STATUS      current
    DESCRIPTION
        "Sets/Gets LEDs status on/off (Only for RBUC).
	**** No respond - message if buc2 not connected."
    ::= { buc2Misc 5 }



-- ####################################################################
-- *** RBUC Status  Group ***
-- ####################################################################

buc1PaStatus OBJECT-TYPE
    SYNTAX      INTEGER (0..1)
    MAX-ACCESS  read-only
    STATUS      current
    DESCRIPTION
        "Gets to 1 when PA is on. Respond -1 if buc1 not connected."
    ::= { buc1Status 1 }

buc2PaStatus OBJECT-TYPE
    SYNTAX      INTEGER (0..1)
    MAX-ACCESS  read-only
    STATUS      current
    DESCRIPTION
        "Gets to 1 when PA is on. Respond -1 if buc2 not connected."
    ::= { buc2Status 1 }

buc1TxPower OBJECT-TYPE
    SYNTAX      DisplayString
    UNITS      "dB"
    MAX-ACCESS  read-only
    STATUS      current
    DESCRIPTION
        "Gets Tx power format x.x dB.
	**** No respond - message if buc1 not connected."
    ::= { buc1Status 2}

buc2TxPower OBJECT-TYPE
    SYNTAX      DisplayString
    UNITS      "dB"
    MAX-ACCESS  read-only
    STATUS      current
    DESCRIPTION
        "Gets Tx power format x.x dB.
	**** No respond - message if buc2 not connected."
    ::= { buc2Status 2}

buc1TxBurstPower OBJECT-TYPE
    SYNTAX      DisplayString
    UNITS      "dB"
    MAX-ACCESS  read-only
    STATUS      current
    DESCRIPTION
        "Gets Tx power. Format is x.x,y.y,z.z, where x.x is current burst 
	power, y.y is min and z.z is max burts power.
	**** No respond - message if buc1 not connected."
    ::= { buc1Status 3}

buc2TxBurstPower OBJECT-TYPE
    SYNTAX      DisplayString
    UNITS      "dB"
    MAX-ACCESS  read-only
    STATUS      current
    DESCRIPTION
        "Gets Tx power. Format is x.x,y.y,z.z, where x.x is current burst 
	power, y.y is min and z.z is max burts power.
	**** No respond - message if buc2 not connected."
    ::= { buc2Status 3}

buc1Faults OBJECT-TYPE
    SYNTAX      INTEGER
    MAX-ACCESS  read-only
    STATUS      current
    DESCRIPTION
        "Gets the current fault status. Format - Bit0 PA fault, Bit1 Fan fault,
	Bit2 Power fault, Bit3 Temp fault, Bit4 10MHz fault, Bit5 Internal fault
	Bit6 LNB fault, Bit7 Red'cy Cont fault.
	Respond -1 if buc2 not connected."
    ::= { buc1Status 4}

buc2Faults OBJECT-TYPE
    SYNTAX      INTEGER
    MAX-ACCESS  read-only
    STATUS      current
    DESCRIPTION
        "Gets the current fault status. Format - Bit0 PA fault, Bit1 Fan fault,
	Bit2 Power fault, Bit3 Temp fault, Bit4 10MHz fault, Bit5 Internal fault
	Bit6 LNB fault, Bit7 Red'cy Cont fault.
	Respond -1 if buc2 not connected."
    ::= { buc2Status 4}

buc1LatchedFaults OBJECT-TYPE
    SYNTAX      INTEGER
    MAX-ACCESS  read-only
    STATUS      current
    DESCRIPTION
        "Gets the current latched faults. Format is same as Faults. Respond -1 if buc2 not connected."
    ::= { buc1Status 5}

buc2LatchedFaults OBJECT-TYPE
    SYNTAX      INTEGER
    MAX-ACCESS  read-only
    STATUS      current
    DESCRIPTION
        "Gets the current latched faults. Format is same as Faults. Respond -1 if buc2 not connected."
    ::= { buc2Status 5}

buc1Temperature OBJECT-TYPE
    SYNTAX      DisplayString
    MAX-ACCESS  read-only
    STATUS      current
    DESCRIPTION
        "Gets the BUC temperature. Format is x.x.
	**** No respond - message if buc1 not connected."
    ::= { buc1Status 6}

buc2Temperature OBJECT-TYPE
    SYNTAX      DisplayString
    MAX-ACCESS  read-only
    STATUS      current
    DESCRIPTION
        "Gets the BUC temperature. Format is x.x.
	**** No respond - message if buc2 not connected."
    ::= { buc2Status 6}

buc1MinMaxTemperature OBJECT-TYPE
    SYNTAX      DisplayString
    MAX-ACCESS  read-only
    STATUS      current
    DESCRIPTION
        "Gets the BUC temperature. Format is x.x,y.y where x.x is max
	and y.y is min temperature.
	**** No respond - message if buc1 not connected."
    ::= { buc1Status 7}

buc2MinMaxTemperature OBJECT-TYPE
    SYNTAX      DisplayString
    MAX-ACCESS  read-only
    STATUS      current
    DESCRIPTION
        "Gets the BUC temperature. Format is x.x,y.y where x.x is max
	and y.y is min temperature.
	**** No respond - message if buc2 not connected."
    ::= { buc2Status 7}

buc1SystemSetting OBJECT-TYPE
    SYNTAX      INTEGER (0..2047)
    MAX-ACCESS  read-only
    STATUS      current
    DESCRIPTION
        "Gets the current system status. Format is 
	Bit0 - PA state, Bit1 - RS232 Tx, Bit2 - FSK Tx, Bit3 - RS485 Tx
	Bit4 - Redundancy mode, Bit5 - Online,
	Bit6..Bit7 - Redundancy cold or hot mode, Bit8 - HTTP Tx, Bit9 - TELNET Tx,
	Bit10 - SNMP Tx.
	Respond -1 if buc1 not connected."
    ::= { buc1Status 8}

buc2SystemSetting OBJECT-TYPE
    SYNTAX      INTEGER (0..2047)
    MAX-ACCESS  read-only
    STATUS      current
    DESCRIPTION
        "Gets the current system status. Format is 
	Bit0 - PA state, Bit1 - RS232 Tx, Bit2 - FSK Tx, Bit3 - RS485 Tx
	Bit4 - Redundancy mode, Bit5 - Online,
	Bit6..Bit7 - Redundancy cold or hot mode, Bit8 - HTTP Tx, Bit9 - TELNET Tx,
	Bit10 - SNMP Tx.
	Respond -1 if buc2 not connected."
    ::= { buc2Status 8}


buc1SystemPoll OBJECT-TYPE
    SYNTAX      INTEGER  (0..3)
    MAX-ACCESS  read-only
    STATUS      current
    DESCRIPTION
        "Gets the system poll status. Format is
	Bit0 - Fault, Bit1 - System change.
	Respond -1 if buc1 not connected."
    ::= { buc1Status 9}

buc2SystemPoll OBJECT-TYPE
    SYNTAX      INTEGER  (0..3)
    MAX-ACCESS  read-only
    STATUS      current
    DESCRIPTION
        "Gets the system poll status. Format is
	Bit0 - Fault, Bit1 - System change.
	Respond -1 if buc2 not connected."
    ::= { buc2Status 9}

buc1DeviceType OBJECT-TYPE
    SYNTAX      DisplayString
    MAX-ACCESS  read-only
    STATUS      current
    DESCRIPTION
        "Gets the device type. Format is X,Y where X is the model and 
	Y is software version.
	**** No respond - message if buc1 not connected."
    ::= { buc1Status 10}

buc2DeviceType OBJECT-TYPE
    SYNTAX      DisplayString
    MAX-ACCESS  read-only
    STATUS      current
    DESCRIPTION
        "Gets the device type. Format is X,Y where X is the model and 
	Y is software version.
	**** No respond - message if buc2 not connected."
    ::= { buc2Status 10}

buc1Gateway OBJECT-TYPE
    SYNTAX      DisplayString
    MAX-ACCESS  read-only
    STATUS      current
    DESCRIPTION
        "Gets the BUC gateway address (Only for RBUC).
	**** No respond - message if buc1 not connected."
    ::= { buc1Status 11}

buc2Gateway OBJECT-TYPE
    SYNTAX      DisplayString
    MAX-ACCESS  read-only
    STATUS      current
    DESCRIPTION
        "Gets the BUC gateway address (Only for RBUC).
	**** No respond - message if buc2 not connected."
    ::= { buc2Status 11}

buc1IpAddress OBJECT-TYPE
    SYNTAX      DisplayString
    MAX-ACCESS  read-only
    STATUS      current
    DESCRIPTION
        "Gets the BUC IP address (Only for RBUC).
	**** No respond - message if buc1 not connected."
    ::= { buc1Status 12}

buc2IpAddress OBJECT-TYPE
    SYNTAX      DisplayString
    MAX-ACCESS  read-only
    STATUS      current
    DESCRIPTION
        "Gets the BUC IP address (Only for RBUC).
	**** No respond - message if buc2 not connected."
    ::= { buc2Status 12}

buc1MACAddress OBJECT-TYPE
    SYNTAX      DisplayString
    MAX-ACCESS  read-only
    STATUS      current
    DESCRIPTION
        "Gets the BUC MAC address (Only for RBUC).
	**** No respond - message if buc1 not connected."
    ::= { buc1Status 13}

buc2MACAddress OBJECT-TYPE
    SYNTAX      DisplayString
    MAX-ACCESS  read-only
    STATUS      current
    DESCRIPTION
        "Gets the BUC MAC address (Only for RBUC).
	**** No respond - message if buc2 not connected."
    ::= { buc2Status 13}

buc1Netmask OBJECT-TYPE
    SYNTAX      DisplayString
    MAX-ACCESS  read-only
    STATUS      current
    DESCRIPTION
        "Gets the BUC netmask (Only for RBUC).
	**** No respond - message if buc1 not connected."
    ::= { buc1Status 14}

buc2Netmask OBJECT-TYPE
    SYNTAX      DisplayString
    MAX-ACCESS  read-only
    STATUS      current
    DESCRIPTION
        "Gets the BUC netmask (Only for RBUC).
	**** No respond - message if buc2 not connected."
    ::= { buc2Status 14}

buc1RefPower OBJECT-TYPE
    SYNTAX      DisplayString
    MAX-ACCESS  read-only
    STATUS      current
    DESCRIPTION
        "Gets the BUC reference power.
	**** No respond - message if buc1 not connected."
    ::= { buc1Status 15}

buc2RefPower OBJECT-TYPE
    SYNTAX      DisplayString
    MAX-ACCESS  read-only
    STATUS      current
    DESCRIPTION
        "Gets the BUC reference power.
	**** No respond - message if buc2 not connected."
    ::= { buc2Status 15}

buc1Config OBJECT-TYPE
    SYNTAX      DisplayString
    MAX-ACCESS  read-only
    STATUS      current
    DESCRIPTION
        "Gets the BUC configuration.
	**** No respond - message if buc1 not connected."
    ::= { buc1Status 16}

buc2Config OBJECT-TYPE
    SYNTAX      DisplayString
    MAX-ACCESS  read-only
    STATUS      current
    DESCRIPTION
        "Gets the BUC configuration.
	**** No respond - message if buc2 not connected."
    ::= { buc2Status 16}

buc1BuildStandard OBJECT-TYPE
    SYNTAX      DisplayString
    MAX-ACCESS  read-only
    STATUS      current
    DESCRIPTION
        "Gets the BUC build standard.
	**** No respond - message if buc1 not connected."
    ::= { buc1Status 17}

buc2BuildStandard OBJECT-TYPE
    SYNTAX      DisplayString
    MAX-ACCESS  read-only
    STATUS      current
    DESCRIPTION
        "Gets the BUC build standard. 
	**** No respond - message if buc2 not connected."
    ::= { buc2Status 17}


-- ####################################################################
-- *** RBUC Info groups - version, model serial No ***
-- ####################################################################


buc1IdInfo  OBJECT-TYPE
    SYNTAX     DisplayString
    MAX-ACCESS read-only
    STATUS     current
    DESCRIPTION
    "Gets the module firmware revision, serial number and model. This string
    will have a zero length if the revision is unknown.
	**** No respond - message if buc1 not connected."
    ::= { buc1Info 1 }

buc2IdInfo  OBJECT-TYPE
    SYNTAX     DisplayString
    MAX-ACCESS read-only
    STATUS     current
    DESCRIPTION
    "Gets the module firmware revision, serial number and model. This string
    will have a zero length if the revision is unknown.
	**** No respond - message if buc2 not connected."
    ::= { buc2Info 1 }

buc1Limits  OBJECT-TYPE
    SYNTAX     DisplayString
    MAX-ACCESS read-only
    STATUS     current
    DESCRIPTION
    "Gets the limit data for the BUC. Format is:
	Power meter MIN/MAX , IF,RF and LO frequencies.
	This string will have a zero length if the revision is unknown.
	**** No respond - message if buc1 not connected."
    ::= { buc1Info 2 }

buc2Limits  OBJECT-TYPE
    SYNTAX     DisplayString
    MAX-ACCESS read-only
    STATUS     current
    DESCRIPTION
    "Gets the limit data for the BUC. Format is:
	Power meter MIN/MAX , IF,RF and LO frequencies.
	This string will have a zero length if the revision is unknown.
	**** No respond - message if buc2 not connected."
    ::= { buc2Info 2 }

buc1PktProtocolsInfo  OBJECT-TYPE
    SYNTAX     DisplayString
    MAX-ACCESS read-only
    STATUS     current
    DESCRIPTION
    "Gets supported packet protocols and the corresponding address ranges.
	**** No respond - message if buc1 not connected."
    ::= { buc1Info 3 }

buc2PktProtocolsInfo  OBJECT-TYPE
    SYNTAX     DisplayString
    MAX-ACCESS read-only
    STATUS     current
    DESCRIPTION
    "Gets supported packet protocols and the corresponding address ranges.
	**** No respond - message if buc2 not connected."
    ::= { buc2Info 3 }


END
