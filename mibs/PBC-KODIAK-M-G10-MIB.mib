--
-- PBC-KODIAK-M-G10-MIB.mib
-- MIB generated by MG-SOFT Visual MIB Builder Version 3.0 Build 253
-- Wednesday, September 25, 2002 at 17:45:33
--

	PBC-KODIAK-M-G10-MIB DEFINITIONS ::= BEGIN
 
		IMPORTS
			pbcModuleRegs, pbcProducts, pbcCaps, pbcReqs			
				FROM PBC-ENT-MIB			
			pbcCardIfCardIndex			
				FROM PBC-GENERIC-MIB			
			OBJECT-GROUP, MODULE-COMPLIANCE			
				FROM SNMPv2-CONF			
			Integer32, Unsigned32, OBJECT-TYPE, MODULE-IDENTITY			
				FROM SNMPv2-SMI			
			DateAndTime			
				FROM SNMPv2-TC;
	
	
		pbcKodiakMG10Mib MODULE-IDENTITY 
			LAST-UPDATED "200106211721Z"		-- June 21, 2001 at 17:21 GMT
			ORGANIZATION 
				"Pacific Broadband Communications"
			CONTACT-INFO 
				"Contact-info."
			DESCRIPTION 
				"MIB Module for the Kodiak M-G10 CMTS."
			::= { pbcModuleRegs 3 }
		
	
	
--
-- Node definitions
--
	
		-- 1.3.6.1.4.1.5987.3.1
		pbcKodiakMG10Cmts OBJECT IDENTIFIER ::= { pbcProducts 1 }
		
		-- 1.3.6.1.4.1.5987.3.1.1
		pbcG10SystemEnvMon OBJECT IDENTIFIER ::= { pbcKodiakMG10Cmts 1 }
		
		-- 1.3.6.1.4.1.5987.3.1.1.1
		sytemEnvMonObjects OBJECT IDENTIFIER ::= { pbcG10SystemEnvMon 1 }
		
		-- 1.3.6.1.4.1.5987.3.1.1.1.1
		systemEnvMonPowerSupply OBJECT IDENTIFIER ::= { sytemEnvMonObjects 1 }
		
		-- 1.3.6.1.4.1.5987.3.1.1.1.1.1
		systemEnvMonPowerSupplyEntityIndex OBJECT-TYPE
			SYNTAX Integer32
			MAX-ACCESS read-write
			STATUS current
			DESCRIPTION
				"entPhysicalIndex of this card's entry in the Entity MIB's
				(RFC2737) entPhysicalTable or '0', if none."
			::= { systemEnvMonPowerSupply 1 }
		
		-- 1.3.6.1.4.1.5987.3.1.1.1.1.2
		systemEnvMonPowerSupplyStatus OBJECT-TYPE
			SYNTAX INTEGER
				{
				normal(1),
				degraded(2),
				failed(3)
				}
			MAX-ACCESS read-write
			STATUS current
			DESCRIPTION
				"Description."
			::= { systemEnvMonPowerSupply 2 }
		
		-- 1.3.6.1.4.1.5987.3.1.1.1.3
		systemEnvMonTemperature OBJECT IDENTIFIER ::= { sytemEnvMonObjects 3 }
		
		-- 1.3.6.1.4.1.5987.3.1.1.1.3.1
		systemEnvMonAmbientTemperatureHighThreshold OBJECT-TYPE
			SYNTAX Integer32
			MAX-ACCESS read-write
			STATUS current
			DESCRIPTION
				"If the ambient temperature exceeds this value, a warning notification
				will be generated.  The user may use this feature to be alerted to
				problems with the HVAC at the installed location."
			::= { systemEnvMonTemperature 1 }
		
		-- 1.3.6.1.4.1.5987.3.1.1.1.3.2
		systemEnvMonAmbientTemperatureLowThreshold OBJECT-TYPE
			SYNTAX Integer32
			MAX-ACCESS read-write
			STATUS current
			DESCRIPTION
				"If the ambient temperature falls below this value, a warning
				notification will be generated.  The user may use this feature
				to be alerted to problems with the HVAC at the installed location."
			::= { systemEnvMonTemperature 2 }
		
		-- 1.3.6.1.4.1.5987.3.1.1.1.3.3
		systemEnvMonAmbientTermperatureNumEntries OBJECT-TYPE
			SYNTAX Unsigned32
			MAX-ACCESS read-only
			STATUS current
			DESCRIPTION
				"Number of entries in the temperature
				monitoring status table."
			::= { systemEnvMonTemperature 3 }
		
		-- 1.3.6.1.4.1.5987.3.1.1.1.3.4
		systemEnvMonAmbientTemperatureTable OBJECT-TYPE
			SYNTAX SEQUENCE OF SystemEnvMonAmbientTemperatureEntry
			MAX-ACCESS not-accessible
			STATUS current
			DESCRIPTION
				"Table of temperature status maintained
				by the system/chassis environment monitor."
			::= { systemEnvMonTemperature 4 }
		
		-- 1.3.6.1.4.1.5987.3.1.1.1.3.4.1
		systemEnvMonAmbientTemperatureEntry OBJECT-TYPE
			SYNTAX SystemEnvMonAmbientTemperatureEntry
			MAX-ACCESS not-accessible
			STATUS current
			DESCRIPTION
				"An entry in the temperature status table representing the status
				of ambient temperature monitoring on one module (card).  The index
				is the same as that used in the pbcCardTable."
			INDEX { pbcCardIfCardIndex }
			::= { systemEnvMonAmbientTemperatureTable 1 }
		
		SystemEnvMonAmbientTemperatureEntry ::=
			SEQUENCE { 
				systemEnvMonAmbientTemperature
					Integer32
			 }

		-- 1.3.6.1.4.1.5987.3.1.1.1.3.4.1.1
		systemEnvMonAmbientTemperature OBJECT-TYPE
			SYNTAX Integer32
			MAX-ACCESS read-only
			STATUS current
			DESCRIPTION
				"Current temperature at the monitoring point for this module (card)."
			::= { systemEnvMonAmbientTemperatureEntry 1 }
		
		-- 1.3.6.1.4.1.5987.3.1.1.1.5
		systemEnvMonFanTrayStatusNumEntries OBJECT-TYPE
			SYNTAX Unsigned32
			MAX-ACCESS read-only
			STATUS current
			DESCRIPTION
				"Number of entries in the fan status
				monitoring table."
			::= { sytemEnvMonObjects 5 }
		
		-- 1.3.6.1.4.1.5987.3.1.1.1.6
		systemEnvMonFanTrayStatusTable OBJECT-TYPE
			SYNTAX SEQUENCE OF SystemEnvMonFanTrayStatusEntry
			MAX-ACCESS not-accessible
			STATUS current
			DESCRIPTION
				"Table of fan status maintained by the system
				environment monitor."
			::= { sytemEnvMonObjects 6 }
		
		-- 1.3.6.1.4.1.5987.3.1.1.1.6.1
		systemEnvMonFanTrayStatusEntry OBJECT-TYPE
			SYNTAX SystemEnvMonFanTrayStatusEntry
			MAX-ACCESS not-accessible
			STATUS current
			DESCRIPTION
				"An entry in the temperature status table
				representing the status of one monitoring
				point."
			INDEX { systemEnvMonFanStatusIndex }
			::= { systemEnvMonFanTrayStatusTable 1 }
		
		SystemEnvMonFanTrayStatusEntry ::=
			SEQUENCE { 
				systemEnvMonFanTrayStatusIndex
					Unsigned32,
				systemEnvMonFanTrayStatusEntityIndex
					Unsigned32
			 }

		-- 1.3.6.1.4.1.5987.3.1.1.1.6.1.1
		systemEnvMonFanTrayStatusIndex OBJECT-TYPE
			SYNTAX Unsigned32
			MAX-ACCESS read-only
			STATUS current
			DESCRIPTION
				"Chassis-assigned ndex number of this fan tray."
			::= { systemEnvMonFanTrayStatusEntry 1 }
		
		-- 1.3.6.1.4.1.5987.3.1.1.1.6.1.2
		systemEnvMonFanTrayStatusEntityIndex OBJECT-TYPE
			SYNTAX Unsigned32
			MAX-ACCESS read-only
			STATUS current
			DESCRIPTION
				"entPhysicalIndex of this fan tray's entry in the Entity MIB's
				(RFC2737) entPhysicalTable or '0', if none.
				"
			::= { systemEnvMonFanTrayStatusEntry 2 }
		
		-- 1.3.6.1.4.1.5987.3.1.1.1.7
		systemEnvMonFanStatusNumEntries OBJECT-TYPE
			SYNTAX Integer32
			MAX-ACCESS read-only
			STATUS current
			DESCRIPTION
				"Number of fan entries in the fan status table."
			::= { sytemEnvMonObjects 7 }
		
		-- 1.3.6.1.4.1.5987.3.1.1.1.8
		systemEnvMonFanStatusTable OBJECT-TYPE
			SYNTAX SEQUENCE OF SystemEnvMonFanStatusEntry
			MAX-ACCESS not-accessible
			STATUS current
			DESCRIPTION
				"Table with individual fan speeds for the fans in each tray."
			::= { sytemEnvMonObjects 8 }
		
		-- 1.3.6.1.4.1.5987.3.1.1.1.8.1
		systemEnvMonFanStatusEntry OBJECT-TYPE
			SYNTAX SystemEnvMonFanStatusEntry
			MAX-ACCESS not-accessible
			STATUS current
			DESCRIPTION
				"Fan speed and thresholds for one fan."
			INDEX { systemEnvMonFanTrayStatusIndex, systemEnvMonFanStatusIndex }
			::= { systemEnvMonFanStatusTable 1 }
		
		SystemEnvMonFanStatusEntry ::=
			SEQUENCE { 
				systemEnvMonFanStatusIndex
					Unsigned32,
				systemEnvMonFanStatusSpeed
					Integer32
			 }

		-- 1.3.6.1.4.1.5987.3.1.1.1.8.1.1
		systemEnvMonFanStatusIndex OBJECT-TYPE
			SYNTAX Unsigned32
			MAX-ACCESS read-only
			STATUS current
			DESCRIPTION
				"Description."
			::= { systemEnvMonFanStatusEntry 1 }
		
		-- 1.3.6.1.4.1.5987.3.1.1.1.8.1.2
		systemEnvMonFanStatusSpeed OBJECT-TYPE
			SYNTAX Integer32
			MAX-ACCESS read-only
			STATUS current
			DESCRIPTION
				"Current speed of the fan."
			::= { systemEnvMonFanStatusEntry 2 }
		
		-- 1.3.6.1.4.1.5987.3.1.2
		pbcG10SystemConformance OBJECT IDENTIFIER ::= { pbcKodiakMG10Cmts 2 }
		
		-- 1.3.6.1.4.1.5987.3.1.2.1
		pbcG10SystemGroups OBJECT IDENTIFIER ::= { pbcG10SystemConformance 1 }
		
		-- 1.3.6.1.4.1.5987.3.1.2.1.1
		pbcSystemEnvMonGroup OBJECT-GROUP
			OBJECTS { systemEnvMonFanStatusNumEntries, systemEnvMonFanStatusIndex, systemEnvMonPowerSupplyEntityIndex, systemEnvMonPowerSupplyStatus, systemEnvMonAmbientTermperatureNumEntries, 
				systemEnvMonAmbientTemperature, systemEnvMonFanTrayStatusNumEntries, systemEnvMonFanTrayStatusIndex, systemEnvMonFanTrayStatusEntityIndex, systemEnvMonFanStatusSpeed, 
				systemEnvMonAmbientTemperatureLowThreshold, systemEnvMonAmbientTemperatureHighThreshold }
			STATUS current
			DESCRIPTION 
				"Objects associated with system environment monitoring."
			::= { pbcG10SystemGroups 1 }
		
		-- 1.3.6.1.4.1.5987.3.1.2.1.2
		pbcG10RedundancyGroup OBJECT-GROUP
			OBJECTS { pbcG10CmtsDMRGroupIndex, pbcG10CmtsDMRGroupSlotNbr, pbcG10CmtsDMRGroupDmCardIndex, pbcG10CmtsDMRGroupImCardIndex, pbcG10CmtsDMRGroupRole, 
				pbcG10CmtsDMRGroupStatus, pbcG10CmtsDMRGroupAlias, pbcG10CmtsDMRGroupAction, pbcG10CmtsDMRGroupSwitchIn, pbcG10CmtsDMRGroupSwitchAt, 
				pbcG10CmtsDMRGroupFreeze, pbcG10CmtsCCMPrimarySlot, pbcG10CmtsCCMAction, pbcG10CmtsCCMSwitchIn, pbcG10CmtsCCMSwitchAt, 
				pbcG10CmtsNICRedundancyEnable, pbcG10CmtsNicDmConnectivityDmCardSlotNumber, pbcG10CmtsNicDmConnectivityConnectTo }
			STATUS current
			DESCRIPTION 
				"Objects associated with DM, NIC and CCM Module Redundancy."
			::= { pbcG10SystemGroups 2 }
		
		-- 1.3.6.1.4.1.5987.3.1.2.3
		pbcG10SystemCompliance OBJECT IDENTIFIER ::= { pbcG10SystemConformance 3 }
		
		-- 1.3.6.1.4.1.5987.3.1.2.3.1
		pbcG10SystemBasicCompliance MODULE-COMPLIANCE
			STATUS current
			DESCRIPTION 
				"Group support required for basic G10 level compliance."
			MODULE -- this module
				MANDATORY-GROUPS { pbcSystemEnvMonGroup }
			::= { pbcG10SystemCompliance 1 }
		
		-- 1.3.6.1.4.1.5987.3.1.2.3.2
		pbcG10RedundancyCompliance MODULE-COMPLIANCE
			STATUS current
			DESCRIPTION 
				"Group support required for G10 Redundancy compliance."
			MODULE -- this module
				MANDATORY-GROUPS { pbcG10RedundancyGroup }
			::= { pbcG10SystemCompliance 2 }
		
		-- 1.3.6.1.4.1.5987.3.1.3
		pbcG10DMRedundancy OBJECT IDENTIFIER ::= { pbcKodiakMG10Cmts 3 }
		
		-- 1.3.6.1.4.1.5987.3.1.3.1
		pbcG10CmtsDMRGroupTable OBJECT-TYPE
			SYNTAX SEQUENCE OF PbcG10CmtsDMRGroupEntry
			MAX-ACCESS not-accessible
			STATUS current
			DESCRIPTION
				"Table Containing the status of various DOCSIS Module Redunduncy Groups. 
				If ths are no DM Reundandancy Groups present on the G10 CMTS, this table 
				is empty."
			::= { pbcG10DMRedundancy 1 }
		
		-- 1.3.6.1.4.1.5987.3.1.3.1.1
		pbcG10CmtsDMRGroupEntry OBJECT-TYPE
			SYNTAX PbcG10CmtsDMRGroupEntry
			MAX-ACCESS not-accessible
			STATUS current
			DESCRIPTION
				"An entry describing the status of various DOCSIS Module Redundancy 
				Groups."
			INDEX { pbcG10CmtsDMRGroupIndex, pbcG10CmtsDMRGroupSlotNbr }
			::= { pbcG10CmtsDMRGroupTable 1 }
		
		PbcG10CmtsDMRGroupEntry ::=
			SEQUENCE { 
				pbcG10CmtsDMRGroupIndex
					Unsigned32,
				pbcG10CmtsDMRGroupSlotNbr
					Unsigned32,
				pbcG10CmtsDMRGroupDmCardIndex
					Unsigned32,
				pbcG10CmtsDMRGroupImCardIndex
					Unsigned32,
				pbcG10CmtsDMRGroupRole
					INTEGER,
				pbcG10CmtsDMRGroupStatus
					INTEGER,
				pbcG10CmtsDMRGroupAlias
					Unsigned32,
				pbcG10CmtsDMRGroupAction
					INTEGER,
				pbcG10CmtsDMRGroupSwitchIn
					Unsigned32,
				pbcG10CmtsDMRGroupSwitchAt
					DateAndTime
			 }

		-- 1.3.6.1.4.1.5987.3.1.3.1.1.1
		pbcG10CmtsDMRGroupIndex OBJECT-TYPE
			SYNTAX Unsigned32
			MAX-ACCESS accessible-for-notify
			STATUS current
			DESCRIPTION
				"An Unique identifier that identifies a DOCSIS Module Redundancy Group.
				Its value is the same as the slot number that contains the Standby 
				DOCSIS Module within the Redundancy Group. All entries with the same 
				value of pbcG10CmtsDMRGroupIndex belong to the same DM Redundancy Group."
			::= { pbcG10CmtsDMRGroupEntry 1 }
		
		-- 1.3.6.1.4.1.5987.3.1.3.1.1.2
		pbcG10CmtsDMRGroupSlotNbr OBJECT-TYPE
			SYNTAX Unsigned32
			MAX-ACCESS accessible-for-notify
			STATUS current
			DESCRIPTION
				"The slot number of the corresponding DOCSIS Module."
			::= { pbcG10CmtsDMRGroupEntry 2 }
		
		-- 1.3.6.1.4.1.5987.3.1.3.1.1.3
		pbcG10CmtsDMRGroupDmCardIndex OBJECT-TYPE
			SYNTAX Unsigned32
			MAX-ACCESS read-only
			STATUS current
			DESCRIPTION
				"The index in the pbcCardTable for the corresponding DOCSIS Module.
				If the DOCSIS Module is not present in the system, this value is 
				reported as 0."
			::= { pbcG10CmtsDMRGroupEntry 3 }
		
		-- 1.3.6.1.4.1.5987.3.1.3.1.1.4
		pbcG10CmtsDMRGroupImCardIndex OBJECT-TYPE
			SYNTAX Unsigned32
			MAX-ACCESS read-only
			STATUS current
			DESCRIPTION
				"The index in the pbcCardTable for the corresponding Real I/O Module.
				The corresponding Rear I/O Module MUST always be present in the 
				system, or else this entry will not even exist in this table."
			::= { pbcG10CmtsDMRGroupEntry 4 }
		
		-- 1.3.6.1.4.1.5987.3.1.3.1.1.5
		pbcG10CmtsDMRGroupRole OBJECT-TYPE
			SYNTAX INTEGER
				{
				active(1),
				standby(2),
				excluded(3)
				}
			MAX-ACCESS read-only
			STATUS current
			DESCRIPTION
				"The role of this DOCSIS Module in the Redundancy Group. 
				The active (1) role corresponds to a DOCSIS Module where the 
				external R/F connections terminate and is normally serving 
				the subscribers.  The standby (2) role corresponds to a DOCSIS 
				Module that is in a standby mode, and to which the R/F from an 
				active module can be directed in the event of a failure of an 
				active module within the redundancy group. The excluded (3) 
				role implies that the corresponding DOCSIS Module has been instructed 
				by the operator to be excluded from being a member of the 
				Redundancy Group."
			::= { pbcG10CmtsDMRGroupEntry 5 }
		
		-- 1.3.6.1.4.1.5987.3.1.3.1.1.6
		pbcG10CmtsDMRGroupStatus OBJECT-TYPE
			SYNTAX INTEGER
				{
				notPresent(1),
				offline(2),
				online(3),
				failed(4),
				covering(5)
				}
			MAX-ACCESS read-only
			STATUS current
			DESCRIPTION
				"Defines the operational status of the corresponding DOCSIS Module card. 
				
				The notPresent (1) status implies that the DOCSIS Module has been 
				removed from the system, or was never present in the system. 
				
				The offline (2) status implies that an operator has shutdown the 
				card either through the CLI, or through the pbcCardTable.
				
				The online (3) status means that an active DOCSIS Module is 
				functioning normally; or for a standby card it implies that the DOCSIS 
				Module is functioning normally and is ready to cover an active module 
				in the event of a failure.
				
				The failed (4) status implies that a failure had been detected 
				previously. 
				
				The covering (5) status applies only to a standby module and implies 
				that it is covering for a failed module
				"
			::= { pbcG10CmtsDMRGroupEntry 6 }
		
		-- 1.3.6.1.4.1.5987.3.1.3.1.1.7
		pbcG10CmtsDMRGroupAlias OBJECT-TYPE
			SYNTAX Unsigned32
			MAX-ACCESS read-only
			STATUS current
			DESCRIPTION
				"For a module in the standby role, this object has a value of 0 if it 
				is not covering any active modules, else it identifies the slot 
				number of the DOCSIS Module that it is covering. For a module in an 
				active role, this object has a value of 0 if it has not failed, or is 
				not being covered by a standby in case of failure, else it identifies 
				the slot number of the standby DOCSIS Module that is covering this 
				module"
			::= { pbcG10CmtsDMRGroupEntry 7 }
		
		-- 1.3.6.1.4.1.5987.3.1.3.1.1.8
		pbcG10CmtsDMRGroupAction OBJECT-TYPE
			SYNTAX INTEGER
				{
				none(1),
				excluded(2),
				include(3),
				switchIn(4),
				switchAt(5)
				}
			MAX-ACCESS read-only
			STATUS current
			DESCRIPTION
				"This object allows the operator to take certain actions on the 
				corresponding DOCSIS Module.
				
				Action none (1) has no effect on the DOCSIS Module. 
				
				The exclude (2) action excludes the module as a member of the 
				Redundancy Group. When an active module has been excluded from a 
				Redundancy Group, it can no longer be covered by a standby in 
				the event of a failure. Action exclude (2) cannot be applied on a 
				standby module.
				
				The include (3) action nullifies the effect of a previous exclude (2) 
				action. If no exclude (2) action had been taken before for this 
				DOCSIS Module, the include (3) action has no effect.
				
				The switchIn (4) action schedules an active module to switch to 
				standby module, or a standby module to switch back to the active 
				module it is covering within the time-period specified by 
				pbcG10CmtsDMRGroupSwitchIn object. For more details, refer to the 
				description of that object.
				
				The switchAt (5) action schedules an active module to switch to 
				standby module, or a standby module to switch back to the active 
				module it is covering at a date and time specified by 
				pbcG10CmtsDMRGroupSwitchAt object. For more details, refer to 
				the description of that object.
				
				When read back, this object always returns the value none(1)
				"
			::= { pbcG10CmtsDMRGroupEntry 8 }
		
		-- 1.3.6.1.4.1.5987.3.1.3.1.1.9
		pbcG10CmtsDMRGroupSwitchIn OBJECT-TYPE
			SYNTAX Unsigned32
			MAX-ACCESS read-write
			STATUS current
			DESCRIPTION
				"When read, this object specifies the time in seconds relative to the 
				current time when a switchover is scheduled for this module, or 0 if 
				no switchover has been scheduled. For an active module, the switchover 
				implies a forced fail-over to the standby module, and for a standby 
				module the switchover implies handing control back to the active module 
				it is covering, if any.
				
				When written to in conjunction with a value of switchIn (4) for the 
				object pbcG10CmtsDMRGroupAction, it specifies a time in seconds in 
				which a switchover MUST take place. A value of 0 implies that switchover 
				be started immediately.
				"
			::= { pbcG10CmtsDMRGroupEntry 9 }
		
		-- 1.3.6.1.4.1.5987.3.1.3.1.1.10
		pbcG10CmtsDMRGroupSwitchAt OBJECT-TYPE
			SYNTAX DateAndTime
			MAX-ACCESS read-write
			STATUS current
			DESCRIPTION
				"When read, this object specifies the time when a switchover is scheduled 
				for this module, or an NULL (Hex String 00 00 00 00 00 00 00 00) value 
				if no switchover has been scheduled. For an active module, the 
				switchover implies a forced fail-over to the standby module, and for a 
				standby module the switchover implies handing control back to the active 
				module it is covering, if any.
				
				When written to in conjunction with a value of switchAt (4) for the 
				object pbcG10CmtsDMRGroupAction, it specifies a date and time on which 
				a switchover MUST take place. A value of NULL 
				(Hex String 00 00 00 00 00 00 00 00) implies that switchover be started 
				immediately
				"
			::= { pbcG10CmtsDMRGroupEntry 10 }
		
		-- 1.3.6.1.4.1.5987.3.1.3.2
		pbcG10CmtsDMRGroupFreeze OBJECT-TYPE
			SYNTAX INTEGER
				{
				freeze(1),
				nofreeze(2)
				}
			MAX-ACCESS read-write
			STATUS current
			DESCRIPTION
				"Writing freeze (1) would disallow all the Redundancy configuration 
				changes. To be able to make configuration changes, this value has 
				to be nofreeze (2)."
			DEFVAL { nofreeze }
			::= { pbcG10DMRedundancy 2 }
		
		-- 1.3.6.1.4.1.5987.3.1.4
		pbcG10CmtsCCMRedundancy OBJECT IDENTIFIER ::= { pbcKodiakMG10Cmts 4 }
		
		-- 1.3.6.1.4.1.5987.3.1.4.1
		pbcG10CmtsCCMRedundancyObject OBJECT IDENTIFIER ::= { pbcG10CmtsCCMRedundancy 1 }
		
		-- 1.3.6.1.4.1.5987.3.1.4.1.1
		pbcG10CmtsCCMPrimarySlot OBJECT-TYPE
			SYNTAX Unsigned32
			MAX-ACCESS read-only
			STATUS current
			DESCRIPTION
				"Identifies the slot number of the CCM Module that is currently in the 
				primary role.
				"
			::= { pbcG10CmtsCCMRedundancyObject 1 }
		
		-- 1.3.6.1.4.1.5987.3.1.4.1.2
		pbcG10CmtsCCMAction OBJECT-TYPE
			SYNTAX INTEGER
				{
				none(1),
				switchIn(2),
				switchAt(3)
				}
			MAX-ACCESS read-write
			STATUS current
			DESCRIPTION
				"This object allows the operator to take certain actions on the CCM 
				Module.
				
				Action none (1) has no effect on the CCM Module. 
				 
				The switchIn (2) action schedules the primary CCM to switch to standby 
				or standby CCM to primary within the time-period specified by 
				pbcG10CmtsCcmSwitchIn object. For more details, refer to the description 
				of that object.
				
				The switchAt (3) action schedules the primary CCM to switch to standby 
				or standby CCM to primary at a date and time specified by 
				pbcG10CmtsCcmSwitchAt object. For more details, refer to the description 
				of that object.
				
				When read back, this object always returns the value none (1).
				"
			::= { pbcG10CmtsCCMRedundancyObject 2 }
		
		-- 1.3.6.1.4.1.5987.3.1.4.1.3
		pbcG10CmtsCCMSwitchIn OBJECT-TYPE
			SYNTAX Unsigned32
			MAX-ACCESS read-write
			STATUS current
			DESCRIPTION
				"When read, this object specifies the time in seconds relative to the 
				current time when a switchover is scheduled for the currently active 
				CCM module, or 0 if no switchover has been scheduled.
				
				When written to in conjunction with a value of switchIn (2) for the 
				object pbcG10CmtsCCMAction, it specifies a time in seconds in which 
				a switchover MUST take place. A value of 0 implies that switchover be 
				started immediately."
			::= { pbcG10CmtsCCMRedundancyObject 3 }
		
		-- 1.3.6.1.4.1.5987.3.1.4.1.4
		pbcG10CmtsCCMSwitchAt OBJECT-TYPE
			SYNTAX DateAndTime
			MAX-ACCESS read-write
			STATUS current
			DESCRIPTION
				"When read, this object specifies the time when a switchover is scheduled 
				for the currently active CCM module, or an NULL 
				(Hex String 00 00 00 00 00 00 00 00) value if no switchover has been 
				scheduled.
				
				When written to in conjunction with a value of switchAt (3) for the 
				object pbcG10CmtsCcmAction, it specifies a date and time at which a 
				switchover MUST take place. A value of NULL 
				(Hex String 00 00 00 00 00 00 00 00) implies that switchover be started 
				immediately."
			::= { pbcG10CmtsCCMRedundancyObject 4 }
		
		-- 1.3.6.1.4.1.5987.3.1.5
		pbcG10CmtsNICRedundancy OBJECT IDENTIFIER ::= { pbcKodiakMG10Cmts 5 }
		
		-- 1.3.6.1.4.1.5987.3.1.5.1
		pbcG10CmtsNICRedundancyObject OBJECT IDENTIFIER ::= { pbcG10CmtsNICRedundancy 1 }
		
		-- 1.3.6.1.4.1.5987.3.1.5.1.1
		pbcG10CmtsNICRedundancyEnable OBJECT-TYPE
			SYNTAX INTEGER
				{
				enable(1),
				disable(2)
				}
			MAX-ACCESS read-write
			STATUS current
			DESCRIPTION
				"Enable/Disable NIC Redundancy for the whole system."
			::= { pbcG10CmtsNICRedundancyObject 1 }
		
		-- 1.3.6.1.4.1.5987.3.1.5.1.2
		pbcG10CmtsNicDmConnectivityTable OBJECT-TYPE
			SYNTAX SEQUENCE OF PbcG10CmtsNicDmConnectivityEntry
			MAX-ACCESS not-accessible
			STATUS current
			DESCRIPTION
				"Table containing information about connectivity between DOCSIS and NIC 
				modules. For every DOCSIS Module in the system there is two entries in 
				this table (One for oddCableInterface and the other for 
				evenCableInterface)."
			::= { pbcG10CmtsNICRedundancyObject 2 }
		
		-- 1.3.6.1.4.1.5987.3.1.5.1.2.1
		pbcG10CmtsNicDmConnectivityEntry OBJECT-TYPE
			SYNTAX PbcG10CmtsNicDmConnectivityEntry
			MAX-ACCESS not-accessible
			STATUS current
			DESCRIPTION
				"An entry describing the status of connectivity between DOCSIS Modules 
				and NIC modules.
				"
			INDEX { pbcG10CmtsNicDmConnectivityDmIndex, pbcG10CmtsNicDmConnectivityCableInterfaceIndex }
			::= { pbcG10CmtsNicDmConnectivityTable 1 }
		
		PbcG10CmtsNicDmConnectivityEntry ::=
			SEQUENCE { 
				pbcG10CmtsNicDmConnectivityDmIndex
					Unsigned32,
				pbcG10CmtsNicDmConnectivityCableInterfaceIndex
					INTEGER,
				pbcG10CmtsNicDmConnectivityDmCardSlotNumber
					Unsigned32,
				pbcG10CmtsNicDmConnectivityConnectTo
					INTEGER
			 }

		-- 1.3.6.1.4.1.5987.3.1.5.1.2.1.1
		pbcG10CmtsNicDmConnectivityDmIndex OBJECT-TYPE
			SYNTAX Unsigned32
			MAX-ACCESS not-accessible
			STATUS current
			DESCRIPTION
				"A unique identifier that identifies a DOCSIS Module."
			::= { pbcG10CmtsNicDmConnectivityEntry 1 }
		
		-- 1.3.6.1.4.1.5987.3.1.5.1.2.1.2
		pbcG10CmtsNicDmConnectivityCableInterfaceIndex OBJECT-TYPE
			SYNTAX INTEGER
				{
				oddCableInterface(1),
				evenCableInterface(2)
				}
			MAX-ACCESS not-accessible
			STATUS current
			DESCRIPTION
				"Cable Connectivity mode index to differentiate between Odd and Even 
				cable interfaces in the DOCSIS Module.
				
				1. oddCableInterfaces (1) meaning all odd numbered cable interfaces in 
				the DOCSIS Modules are connected to the NIC modules specified by the 
				pbcCmtsDmConnectTo.
				
				2. evenCableInterfaces (2) meaning all even numbered cable interfaces in 
				the DOCSIS  Modulesare connected to the NIC modules specified by the 
				pbcCmtsDmConnectTo.
				"
			::= { pbcG10CmtsNicDmConnectivityEntry 2 }
		
		-- 1.3.6.1.4.1.5987.3.1.5.1.2.1.3
		pbcG10CmtsNicDmConnectivityDmCardSlotNumber OBJECT-TYPE
			SYNTAX Unsigned32
			MAX-ACCESS read-write
			STATUS current
			DESCRIPTION
				"Slot Number where the DOCSIS Modules resides in the chassis."
			::= { pbcG10CmtsNicDmConnectivityEntry 3 }
		
		-- 1.3.6.1.4.1.5987.3.1.5.1.2.1.4
		pbcG10CmtsNicDmConnectivityConnectTo OBJECT-TYPE
			SYNTAX INTEGER
				{
				nic5(1),
				nic9(2),
				rf45a(3),
				rf45b(4)
				}
			MAX-ACCESS read-write
			STATUS current
			DESCRIPTION
				"The DOCSIS Module connects to the NIC module in slot 5 if 
				pbcG10CmtsNicDmConnectivityConnectTo is nic5 (1), 
				or NIC module in slot 9 if pbcG10CmtsNicDmConnectivityConnectTo is 
				nic9 (2). 
				
				or RJ45 Port-a if pbcG10CmtsNicDmConnectivityConnectTo is rj45a (3).
				 
				or RJ45 Port-b if pbcG10CmtsNicDmConnectivityConnectTo is rj45b (4). 
				
				"
			::= { pbcG10CmtsNicDmConnectivityEntry 4 }
		
	
	END

--
-- PBC-KODIAK-M-G10-MIB.mib
--
