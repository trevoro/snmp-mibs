USR-TRACEROUTE-MIB DEFINITIONS ::= BEGIN
        IMPORTS
          OBJECT-TYPE, MODULE-IDENTITY, Integer32, IpAddress
                FROM SNMPv2-SMI
          RowStatus
                FROM SNMPv2-TC
          common, DisplayString, UsrConfigStatus 
                FROM USR-DEFINITIONS-MIB;
usrTraceroute MODULE-IDENTITY
        LAST-UPDATED "200205051800Z"
        ORGANIZATION "CommWorks Corporation, a 3Com Company"
        CONTACT-INFO "Customer Support"
        DESCRIPTION
           "The commWorks enterprise defined MIB objects for TraceRoute"
--      REVISION  "200205051800Z"
--      DESCRIPTION "Converted to SNMPv2"
       ::= { common 40 }
--
-- Traceroute managed objects
--
usrTracerouteBase OBJECT IDENTIFIER ::= { usrTraceroute 1 }
--
-- Base Objects
--
usrTracerouteIndexNext OBJECT-TYPE
    SYNTAX  Integer32
    MAX-ACCESS  read-only
    STATUS      current
    DESCRIPTION
     "This object contains an appropriate value that can be used for
      'usrTracerouteIndex' when creating a new row in the Traceroute
      Table'. If the value 0 is returned, it indicates that the table
      contains the maximum number of rows and thus it is not possible to add
      another one."
    ::= { usrTracerouteBase 1 }
usrTracerouteIndexNRows OBJECT-TYPE
    SYNTAX  Integer32
    MAX-ACCESS  read-only
    STATUS      current
    DESCRIPTION
     "Number of rows currently present in the Traceroute table."
    ::= { usrTracerouteBase 2 }
usrTracerouteMaxRows OBJECT-TYPE
    SYNTAX  Integer32 (1..255)
    MAX-ACCESS  read-write
    STATUS      current
    DESCRIPTION
     "Maximum number of rows allowed in the Traceroute table.
      Note that setting this object to a number which is smaller than the
      current number of rows will NOT cause any row deletions - rather, the
      effect of such an action will be noted in future attempts at row creation."
    DEFVAL  { 20 }
    --CONFIGURABLE
    ::= { usrTracerouteBase 3 }
usrTracerouteConfigFileName OBJECT-TYPE
    SYNTAX  DisplayString
    MAX-ACCESS  read-only
    STATUS      current
    DESCRIPTION
     "The name of a ConfigFile to read/write  permanent database records.
     If the value of this object is an empty string, then the Traceroute
     process uses the default name `@file://TracerouteProcess.cfg'."
    ::= { usrTracerouteBase 4 }
usrTracerouteCFMStatusFlag  OBJECT-TYPE
    SYNTAX  UsrConfigStatus
    MAX-ACCESS  read-write
    STATUS      current
    DESCRIPTION
     "Setting the value of this object to `save' causes the values of the
     Remote Ping Group to be written out to the current config file, which
     is stored in the usrTracerouteConfigFileName object. While the new
     ConfigFile is being written, the Remote Ping process will set the value
     of this flag set to `saving''. Any attempts to set the value while it
     is  not `normal' (i.e. the file is currently being written to the
     ConfigFile) while result in a badValue error being returned. Setting
     the value to `normal' will result in no action."
    ::= { usrTracerouteBase 5 }
usrTracerouteTable OBJECT-TYPE
    SYNTAX  SEQUENCE OF UsrTracerouteEntry
    MAX-ACCESS  not-accessible
    STATUS      current
    DESCRIPTION
     "A table of traceroute entries."
    ::= { usrTraceroute 2 }
usrTracerouteEntry OBJECT-TYPE
    SYNTAX  UsrTracerouteEntry
    MAX-ACCESS  not-accessible
    STATUS      current
    DESCRIPTION
     "A list of fields defining this traceroute"
    INDEX   { usrTracerouteIndex }
    ::= { usrTracerouteTable 1 }
UsrTracerouteEntry ::= SEQUENCE {
    usrTracerouteIndex                      Integer32,
    usrTracerouteDestination                DisplayString (SIZE (1..255)),
    usrTracerouteResolvedIPAddress          IpAddress,
    usrTracerouteHopTimeout                 Integer32(1..60),
    usrTracerouteHopProbes                  Integer32(1..10),
    usrTracerouteMaxHops                    Integer32(1..255),
    usrTracerouteUDPPort                    Integer32(1..65000),
    usrTracerouteDataSize                   Integer32(1..8184),
    usrTracerouteHopCount                   Integer32,
    usrTracerouteState                      INTEGER,
    usrTracerouteRowStatus                  RowStatus
}
usrTracerouteIndex OBJECT-TYPE
    SYNTAX  Integer32
    MAX-ACCESS  not-accessible
    STATUS      current
    DESCRIPTION
     "A unique index identifying this entry in the table."
    ::= { usrTracerouteEntry 1 }
usrTracerouteDestination OBJECT-TYPE
    SYNTAX  DisplayString (SIZE (1..255))
    MAX-ACCESS  read-write
    STATUS      current
    DESCRIPTION
     "The host name or IP address (in dot notation) of the target
      destination being traced by this row. A row cannot be activated
      unless this object has a length greater than zero.
      Router DNS services will always be used to resolve (names) and/or
	  verify addresses in dot notation.  If DNS fails, the object 
	  usrTracerouteRowState will indicate 'dnsFailed' or 'badAddress'.
      This object cannot be modified whenever usrTracerouteRowStatus is
      'active'."
    DEFVAL  { "" }
    ::= { usrTracerouteEntry 2 }
usrTracerouteResolvedIPAddress OBJECT-TYPE
    SYNTAX  IpAddress
    MAX-ACCESS  read-only
    STATUS      current
    DESCRIPTION
     "The IP address resolved from the destination address string.
      If an IP address was set in the destination field it will
      be reflected here as well.
      If an address cannot be resolved, this object returns zero and the
      state field is set to dnsFail"
    ::= { usrTracerouteEntry 3 }
usrTracerouteHopTimeout OBJECT-TYPE
    SYNTAX  Integer32(1..60)
    MAX-ACCESS  read-write
    STATUS      current
    DESCRIPTION
     "Amount of time in seconds before retrying a hop.  This object cannot 
	  be modified whenever usrTracerouteRowStatus is 'active'."
    DEFVAL  { 3 }
    ::= { usrTracerouteEntry 4 }
usrTracerouteHopProbes OBJECT-TYPE
    SYNTAX  Integer32(1..10)
    MAX-ACCESS  read-write
    STATUS      current
    DESCRIPTION
     "The maixmum number of times to try to discern a hop before moving 
	  on to the next hop"
    DEFVAL  { 3 }
    ::= { usrTracerouteEntry 5 }
usrTracerouteMaxHops OBJECT-TYPE
    SYNTAX  Integer32(1..255)
    MAX-ACCESS  read-write
    STATUS      current
    DESCRIPTION
     "The maixmum number of hops to trace before quitting."
    DEFVAL  { 30 }
    ::= { usrTracerouteEntry 6 }
usrTracerouteUDPPort OBJECT-TYPE
    SYNTAX  Integer32(1..65000)
    MAX-ACCESS  read-write
    STATUS      current
    DESCRIPTION
     "The UDP port value to use when attempting to find the route"
    DEFVAL  { 33434 }
    ::= { usrTracerouteEntry 7 }
usrTracerouteDataSize OBJECT-TYPE
    SYNTAX  Integer32(1..8184)
    MAX-ACCESS  read-write
    STATUS      current
    DESCRIPTION
     "The maixmum number of hops to trace before quitting."
    DEFVAL  { 1 }
    ::= { usrTracerouteEntry 8 }
usrTracerouteHopCount OBJECT-TYPE
    SYNTAX  Integer32
    MAX-ACCESS  read-only
    STATUS      current
    DESCRIPTION
     "The number of hops taken to get to the destination."
    ::= { usrTracerouteEntry 9 }
usrTracerouteState OBJECT-TYPE
    SYNTAX  INTEGER {
      notActive(1),        -- this row is not active.
      waitingDns(2),       -- waiting for DNS resolution.
      dnsFailed(3),        -- destination address could not be resolved.
      badAddress(4),       -- the resolved IP address is illegal.
      hopsExceeded(5),     -- the maximum number of hops was exceeded
      destUnreachable(6),  -- a route to the host could not be found
      tracing(7),          -- performing traceroute
      completed(8),        -- traceroute completed successfully
	  resourceFailure(9)   -- there was not enough resources to complete the command
    }
    MAX-ACCESS  read-only
    STATUS      current
    DESCRIPTION
     "The state of the 'traceroute' process associated with this row.
      Before this row is activated, this object will have the value
      'notActive(1)'.
      Upon activation, if DNS resolution is needed, the object will
      receive the value 'waitingDns(2)'. If DNS times out or otherwise
      fails, this object will receive the value 'dnsFailed(3)'.
      If the resolved IP address is not legal, this object value will be
      'badAddress(4)'.
      If the a timeout occurs or the hop count is exceeded, the value will
      be 'hopTimeout(6)' or 'hopsExceeded(7)'.
	  If a route to the host could not be found, a 'destUnreachable(8)'
	  value will be returned.
      If none of the above fails, the first traceroute command will be sent
      and this object will indicate the value 'tracing(9)'.
      After the completes this object will receive the value
      completed(10)'."
    ::= { usrTracerouteEntry 10 }
usrTracerouteRowStatus OBJECT-TYPE
    SYNTAX          RowStatus
    MAX-ACCESS          read-write
    STATUS              current
    DESCRIPTION
     "This object is used to create, modify or delete a row in this table.
      Setting this object to 'createAndWait' creates the row with default
      values. Right after creation the value of this object will be
      'notReady'.
      When all parameters are given proper values, this object
      will return the value 'notInService', at which point the client can
      set the object to 'active' to activate the row.
      Modifying this object from 'active' to 'notInService' will cancel any
      on-going traceroute and remove entries for it from the usrTracerouteHopTable.
      Setting the object to 'active' again will start a new traceroute with the
      supplied parameters
      Setting this object to 'destroy' will stop any on-going activity and
      delete the row."
    DEFVAL  { createAndWait }
    ::= { usrTracerouteEntry 11 }
usrTracerouteHopTable OBJECT-TYPE
    SYNTAX  SEQUENCE OF UsrTracerouteHopEntry
    MAX-ACCESS  not-accessible
    STATUS      current
    DESCRIPTION
     "A table of traceroute hop entries."
    ::= { usrTraceroute 3 }
usrTracerouteHopEntry OBJECT-TYPE
    SYNTAX  UsrTracerouteHopEntry
    MAX-ACCESS  not-accessible
    STATUS      current
    DESCRIPTION
     "A list of fields containing the hop information for all traceroute instances"
    INDEX   { usrTracerouteTableIndex, usrTracerouteHopIndex }
    ::= { usrTracerouteHopTable 1 }
UsrTracerouteHopEntry ::= SEQUENCE {
    usrTracerouteTableIndex                 Integer32,
    usrTracerouteHopIndex                   Integer32,
    usrTracerouteHopIPAddress               IpAddress,
    usrTracerouteHopRoundTripTime           Integer32
}
usrTracerouteTableIndex OBJECT-TYPE
    SYNTAX  Integer32
    MAX-ACCESS  not-accessible
    STATUS      current
    DESCRIPTION
     "The index into the usrTracerouteTable corresponding to this hop."
    ::= { usrTracerouteHopEntry 1 }
usrTracerouteHopIndex OBJECT-TYPE
    SYNTAX  Integer32
    MAX-ACCESS  not-accessible
    STATUS      current
    DESCRIPTION
     "The hop number corresponding to the usrTracerouteHopIPAddress in this row."
    ::= { usrTracerouteHopEntry 2 }
usrTracerouteHopIPAddress OBJECT-TYPE
    SYNTAX  IpAddress
    MAX-ACCESS  read-only
    STATUS      current
    DESCRIPTION
     "The IP address for a hop.  An address of zero means that there was no response
	  from that hop."
    ::= { usrTracerouteHopEntry 3 }
usrTracerouteHopRoundTripTime OBJECT-TYPE
    SYNTAX  Integer32
    MAX-ACCESS  read-only
    STATUS      current
    DESCRIPTION
     "Round trip time for this hop in milliseconds."
    ::= { usrTracerouteHopEntry 4 }
END     -- End of USR-TRACEROUTE-MIB DEFINITIONS
