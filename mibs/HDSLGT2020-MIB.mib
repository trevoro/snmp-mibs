-- Copyright 1998 General DataComm Inc., Inc. All Rights Reserved.
--
-- Reproduction of this document is authorized on condition that the
-- foregoing copyright notice is included. This General DataComm, GDC,
-- SNMP Management Information Base Specification embodies GDCs'
-- confidential and proprietary intellectual property. GDC retains all
-- title and ownership in the Specification, including any revisions.
--
-- It is GDCs intent to encourage the widespread use of this Specification
-- in connection with the management of GDC's products. GDC grants vendors,
-- end-users, and other interested parties a non-exclusive license to use
-- this Specification in connection with the management of GDC's products.
--
-- This Specification is supplied "AS IS," and GDC makes no warranty,
-- either expressed or implied, as to the use operation, condition, or
-- performance of the Specification.

-- Revision History
-- Version   Date	Name		Description
-- 1.00A     14-Oct-98  C. Amorossi     Initial Revision

HDSLGT2020-MIB DEFINITIONS ::= BEGIN

IMPORTS
	OBJECT-TYPE			FROM RFC-1212
	DisplayString			FROM RFC1213-MIB
	hdslGT2020                       FROM GDCHDSL-MIB;

hdslGT2020System          OBJECT IDENTIFIER ::= { hdslGT2020 1 }
hdslGT2020Version         OBJECT IDENTIFIER ::= { hdslGT2020System 1 }

-- This mib is a subset of the HDSL mib for the GT2020 product.

-- ***************************************************************************
-- The interfaces are defined as follows:
--	Unit	0
--	E1	1
--	Loop1	2
--	Loop2   3
-- ***************************************************************************

gdcGT2020SystemMIBversion OBJECT-TYPE
     	SYNTAX DisplayString (SIZE (5))
     	ACCESS read-only
     	STATUS mandatory
     	DESCRIPTION
     		"Identifies the version of the MIB. The format of the version
     		is x.yzT, where 'x' identifies the major revision number, 'y'
     		identifies the minor revision number, 'z' identifies the
     		typographical revision, and T identifies the test revision.
     		Acceptable values for the individual revision components are
     		as follows:
 
     		x: 1 - 9
     		y: 0 - 9
     		z: 0 - 9
     		T: A - Z
 
     		Upon formal release, no designation for the test revision will
     		be present."
     	::= { hdslGT2020Version 1 }

-- ********************************************************************
-- GDC Hdsl Alarm Object Identifier Definitions
-- ********************************************************************
hdslGT2020Alarms                OBJECT IDENTIFIER ::= { hdslGT2020 2 }

hdslGT2020NoResponseAlm	 	OBJECT IDENTIFIER ::= { hdslGT2020Alarms 1 }
hdslGT2020DiagRxErrAlm		OBJECT IDENTIFIER ::= { hdslGT2020Alarms 2 }
hdslGT2020PowerUpAlm		OBJECT IDENTIFIER ::= { hdslGT2020Alarms 3 }
hdslGT2020UnitFailure           OBJECT IDENTIFIER ::= { hdslGT2020Alarms 4 }
hdslGT2020ChecksumCorrupt       OBJECT IDENTIFIER ::= { hdslGT2020Alarms 5 }
hdslGT2020LossofSignal		OBJECT IDENTIFIER ::= { hdslGT2020Alarms 6 }
hdslGT2020UnavailableSec	OBJECT IDENTIFIER ::= { hdslGT2020Alarms 7 }
hdslGT2020ErrorSec		OBJECT IDENTIFIER ::= { hdslGT2020Alarms 8 }
hdslGT2020LossofSyncWord	OBJECT IDENTIFIER ::= { hdslGT2020Alarms 9 }
hdslGT2020LossofFrameAlign	OBJECT IDENTIFIER ::= { hdslGT2020Alarms 10 }
hdslGT2020AllOnes		OBJECT IDENTIFIER ::= { hdslGT2020Alarms 11 }
hdslGT2020RemoteLossofSig	OBJECT IDENTIFIER ::= { hdslGT2020Alarms 12 }
hdslGT2020RemoteAlarmInd	OBJECT IDENTIFIER ::= { hdslGT2020Alarms 13 }
hdslGT2020MajorBER      	OBJECT IDENTIFIER ::= { hdslGT2020Alarms 14 }
hdslGT2020MinorBER		OBJECT IDENTIFIER ::= { hdslGT2020Alarms 15 }
 
 
-- ALARM			Maskable	Valid Interfaces
--===============================================================
--hdslGT2020NoResponseAlm	No		Unit
--hdslGT2020DiagRxErrAlm        No              Unit
--hdslGT2020PowerUpAlm		No		Unit
--hdslGT2020UnitFailure         No              Unit
--hdslGT2020ChecksumCorrupt     No              Unit
--hdslGT2020LossofSignal	Yes		E1, L1, L2 
--hdslGT2020UnavailableSec	Yes		E1, L1, L2
--hdslGT2020ErrorSec		Yes		E1, L1, L2
--hdslGT2020LossofSyncWord	Yes		L1, L2
--hdslGT2020LossofFrameAlign	Yes		E1
--hdslGT2020AllOnes		Yes		E1
--hdslGT2020RemoteLossofSig	Yes		E1
--hdslGT2020RemoteAlarmInd	Yes		E1 
--hdslGT2020MajorBER		Yes		L1, L2
--hdslGT2020MinorBER		Yes		L1, L2


END
