--
-- Juniper Enterprise Specific MPLS Traps for SNMP V1
--
-- Copyright (c) 1998-2000, Juniper Networks, Inc.
-- All rights reserved.
--
-- The contents of this document are subject to change without notice.
--

JUNIPER-V1-TRAPS-MPLS

DEFINITIONS ::= BEGIN

IMPORTS
    enterprises         FROM RFC1155-SMI
    TRAP-TYPE           FROM RFC-1215;


--  The following chassis objects are from Juniper Chassis MIB

    juniperMIB          OBJECT IDENTIFIER ::= { enterprises 2636 }

    jnxMibs             OBJECT IDENTIFIER ::= { juniperMIB 3 }


--  The following MPLS objects are from Juniper MPLS MIB

    mpls                OBJECT IDENTIFIER ::= { jnxMibs 2 }

    mplsLspList         OBJECT IDENTIFIER ::= { mpls 3 }

    mplsLspEntry        OBJECT IDENTIFIER ::= { mplsLspList 1 }
    mplsLspName	        OBJECT IDENTIFIER ::= { mplsLspEntry 1 }
    mplsPathName        OBJECT IDENTIFIER ::= { mplsLspEntry 17 }


--
--  MPLS traps
--
	
    mplsLspUpV1 TRAP-TYPE
        ENTERPRISE      juniperMIB
        VARIABLES {
                    mplsLspName,
                    mplsPathName  -- LspPath
                  }
        DESCRIPTION
                "An mplsLspUp trap signifies that the 
                specified LSP is up. The current active
                path for the LSP is mplsPathName."
        ::= 1

    
    mplsLspDownV1 TRAP-TYPE
        ENTERPRISE      juniperMIB
        VARIABLES { 
                    mplsLspName,
                    mplsPathName  -- LspPath
                  }
        DESCRIPTION
                "An mplsLspDown trap signifies that the 
                specified LSP is down, because the current
                active path mplsPathName went down."
        ::= 2

    
    mplsLspChangeV1 TRAP-TYPE
        ENTERPRISE      juniperMIB
        VARIABLES { 
                    mplsLspName,
                    mplsPathName  -- toLspPath
                  }
        DESCRIPTION
                "An mplsLspChange trap signifies that the
                the specified LSP has switched traffic to 
                the new active path 'toLspPath'. The LSP maintains
                up state before and after the switch over" 
        ::= 3


END
