CORIOLIS-MIB

          DEFINITIONS ::= BEGIN  

          IMPORTS
            enterprises
            FROM RFC1155-SMI;

          coriolisMibs OBJECT IDENTIFIER ::= { enterprises 5812 }

--            MODULE-IDENTITY
--            LAST-UPDATED "0004100000Z"
--            ORGANIZATION "Coriolis Networks"
--            CONTACT-INFO
--               " Network Management Division,
--                 Postal: 330 Codman Hill Road,
--                         Boxboro, MA 01719
--                 Tel: + 1 978 264 1904
--                 Fax: + 1 978 264 1929"
--
--          DESCRIPTION
--            "This module defines the proprietary mibs of Coriolis Networks.
--             It is just a listing of the name of the mibs, each mib is actually
--             defined in the module for the individual mib. e.g. The node mib is
--             defined in the module node.mib" 




          device         OBJECT IDENTIFIER ::= { coriolisMibs 1 }

          card           OBJECT IDENTIFIER ::= { coriolisMibs 2 }

          port           OBJECT IDENTIFIER ::= { coriolisMibs 3 }

          ring           OBJECT IDENTIFIER ::= { coriolisMibs 4 }

	      ne             OBJECT IDENTIFIER ::= { coriolisMibs 5 }

		  circuit        OBJECT IDENTIFIER ::= { coriolisMibs 6 }

		  routing        OBJECT IDENTIFIER ::= { coriolisMibs 7 }

         interfaces    OBJECT IDENTIFIER ::= { coriolisMibs 8 }

	eventlog	OBJECT IDENTIFIER ::= { coriolisMibs 9 }	

          END
