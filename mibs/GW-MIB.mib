--******************************************************************
--*
--*         Copyright (c) 1993, 1999 by 3Com Corporation
--*                    All Rights Reserved
--*
--*    $Revision:   7.0  $
--*    $Date:   Jul 15 1999 15:12:48  $
--*
--*    3COM GW MIB
--*
--******************************************************************


GW-MIB DEFINITIONS ::= BEGIN

IMPORTS
   enterprises,
   experimental,
   IpAddress,
   TimeTicks,
   Gauge,
   Counter
      FROM RFC1155-SMI
   DisplayString
      FROM RFC1213-MIB
   OBJECT-TYPE
      FROM RFC-1212;


usr OBJECT IDENTIFIER ::= { enterprises 429 }

nas OBJECT IDENTIFIER ::= { usr 1 }

gw OBJECT IDENTIFIER ::= { nas 18 }

-- The Gateway Card Trap Enable Group

gwTe OBJECT IDENTIFIER ::= { gw 1 }

gwTeTable OBJECT-TYPE
SYNTAX SEQUENCE OF GwTeEntry
ACCESS not-accessible
STATUS mandatory
DESCRIPTION
"Table containing objects to enable traps on the Gateway 
Cards in the chassis."
::= { gwTe 1 }

gwTeEntry OBJECT-TYPE
SYNTAX GwTeEntry
ACCESS not-accessible
STATUS mandatory
DESCRIPTION
"There is one entry for each Gateway Card in the chassis."
INDEX { gwTeIndex }
::= { gwTeTable 1 }

GwTeEntry ::=
SEQUENCE {
gwTeIndex
    INTEGER,
gwTegwNetworkFailed
    INTEGER,
gwTegwNetworkRestored
    INTEGER,
gwTegwIPAddress
    IpAddress,
gwTeArNetFailed
    OCTET STRING,
gwTeArNetRestored
    OCTET STRING
}

gwTeIndex OBJECT-TYPE
SYNTAX INTEGER
ACCESS read-only
STATUS mandatory
DESCRIPTION
"A unique index identifying the Gateway Card to which the 
trap enable objects pertain."
::= { gwTeEntry 1 }

gwTegwNetworkFailed OBJECT-TYPE
SYNTAX INTEGER{
  enableTrap(1),
  disableAll(2),
  enableLog(3),
  enableAll(4)
}
ACCESS read-write
STATUS mandatory
DESCRIPTION
"Enable generation of an SNMP trap upon detection of an 
network failure of the specified gateway."
::= { gwTeEntry 2 }

gwTegwNetworkRestored OBJECT-TYPE
SYNTAX INTEGER{
  enableTrap(1),
  disableAll(2),
  enableLog(3),
  enableAll(4)
}
ACCESS read-write
STATUS mandatory
DESCRIPTION
"Enable generation of an SNMP trap upon detection of an 
network restore of the specified gateway."
::= { gwTeEntry 3 }

gwTegwIPAddress OBJECT-TYPE
SYNTAX IpAddress
ACCESS read-only
STATUS mandatory
DESCRIPTION
"The Gateway IP Address."
::= { gwTeEntry 4 }

gwTeArNetFailed OBJECT-TYPE
SYNTAX OCTET STRING (SIZE(0..40))
ACCESS read-write
STATUS mandatory
DESCRIPTION
"This script is triggered when a Gateway NAC sends the NMC a 
network fail event."
::= { gwTeEntry 5 }

gwTeArNetRestored OBJECT-TYPE
SYNTAX OCTET STRING (SIZE(0..40))
ACCESS read-write
STATUS mandatory
DESCRIPTION
"This script is triggered when a Gateway NAC sends the NMC a 
network restored event."
::= { gwTeEntry 6 }

END
