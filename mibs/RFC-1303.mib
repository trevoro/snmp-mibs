-- WinAgents MIB Extraction Wizard
-- Extracted from rfc1303.txt 16.03.2005 20:20:15

RFC-1303 DEFINITIONS ::= BEGIN

--    IMPORTS
--        ObjectName, ObjectSyntax
--            FROM RFC1155-SMI
--        DisplayString
--            FROM RFC1213-MIB;

-- MIB Extraction: All MACRO definitions are predefined by compiler
-- commented by MIB Extraction:     MODULE-CONFORMANCE MACRO ::=
-- commented by MIB Extraction:     BEGIN
-- commented by MIB Extraction:         TYPE NOTATION ::=
-- commented by MIB Extraction:                           "LAST-UPDATED"
-- commented by MIB Extraction:                               value(update      UTCTime)
-- commented by MIB Extraction:                           "PRODUCT-RELEASE"
-- commented by MIB Extraction:                               value(release     DisplayString)
-- commented by MIB Extraction:                           "DESCRIPTION"
-- commented by MIB Extraction:                               value(description DisplayString)
-- commented by MIB Extraction:                           ModulePart
-- commented by MIB Extraction:
-- commented by MIB Extraction:         VALUE NOTATION ::=       agent's sysObjectID
-- commented by MIB Extraction:                           value(VALUE ObjectName)
-- commented by MIB Extraction:
-- commented by MIB Extraction:         ModulePart ::=    Modules
-- commented by MIB Extraction:                         | empty
-- commented by MIB Extraction:
-- commented by MIB Extraction:         Modules ::=       Module
-- commented by MIB Extraction:                         | Modules Module
-- commented by MIB Extraction:
-- commented by MIB Extraction:         Module ::=                    name of module
-- commented by MIB Extraction:                           "SUPPORTS" ModuleName
-- commented by MIB Extraction:                           "INCLUDES" "{" Groups "}"
-- commented by MIB Extraction:                           VariationPart
-- commented by MIB Extraction:
-- commented by MIB Extraction:         ModuleName ::=    identifier ModuleIdentifier
-- commented by MIB Extraction:
-- commented by MIB Extraction:         ModuleIdentifier ::=
-- commented by MIB Extraction:                           value (moduleID OBJECT IDENTIFIER)
-- commented by MIB Extraction:                         | empty
-- commented by MIB Extraction:
-- commented by MIB Extraction:         Groups ::=        Group
-- commented by MIB Extraction:                         | Groups "," Group
-- commented by MIB Extraction:
-- commented by MIB Extraction:         Group ::=         value(group OBJECT IDENTIFIER)
-- commented by MIB Extraction:
-- commented by MIB Extraction:         VariationPart ::= Variations
-- commented by MIB Extraction:                         | empty
-- commented by MIB Extraction:
-- commented by MIB Extraction:         Variations ::=    Variation
-- commented by MIB Extraction:                         | Variations Variation
-- commented by MIB Extraction:
-- commented by MIB Extraction:         Variation ::=     "VARIATION" value(object ObjectName)
-- commented by MIB Extraction:                           Syntax WriteSyntax Access
-- commented by MIB Extraction:                           Creation DefaultValue
-- commented by MIB Extraction:                           "DESCRIPTION"
-- commented by MIB Extraction:                               value(limitext DisplayString)
-- commented by MIB Extraction:
-- commented by MIB Extraction:          must be a refinement for object's SYNTAX
-- commented by MIB Extraction:         Syntax ::=        "SYNTAX" type(SYNTAX)
-- commented by MIB Extraction:                         | empty
-- commented by MIB Extraction:
-- commented by MIB Extraction:          must be a refinement for object's SYNTAX
-- commented by MIB Extraction:         WriteSyntax ::=   "WRITE-SYNTAX" type(WriteSYNTAX)
-- commented by MIB Extraction:                         | empty
-- commented by MIB Extraction:
-- commented by MIB Extraction:         Access ::=        "ACCESS" AccessValue
-- commented by MIB Extraction:                         | empty
-- commented by MIB Extraction:
-- commented by MIB Extraction:         AccessValue ::=   "read-only"
-- commented by MIB Extraction:                         | "read-write"
-- commented by MIB Extraction:                         | "write-only"
-- commented by MIB Extraction:                         | "not-accessible"
-- commented by MIB Extraction:
-- commented by MIB Extraction:         Creation ::=      "CREATION-REQUIRES" "{" Cells "}"
-- commented by MIB Extraction:
-- commented by MIB Extraction:         Cells ::=         Cell
-- commented by MIB Extraction:                         | Cells "," Cell
-- commented by MIB Extraction:
-- commented by MIB Extraction:         Cell ::=          value(cell ObjectName)
-- commented by MIB Extraction:
-- commented by MIB Extraction:         DefaultValue ::=  "DEFVAL"
-- commented by MIB Extraction:                           "{" value (defval ObjectSyntax) "}"
-- commented by MIB Extraction:                         | empty
-- commented by MIB Extraction:
-- commented by MIB Extraction:     END

END
