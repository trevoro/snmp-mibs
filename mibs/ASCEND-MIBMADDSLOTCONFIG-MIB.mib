--			Ascend mibmaddslotconfig MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBMADDSLOTCONFIG-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibmaddSlotConfig  OBJECT IDENTIFIER ::= { configuration 163}

	-- The mibmaddSlotConfig table
	--
	-- This table contains parameters for the mibmaddSlotConfig profile
	--

    mibmaddSlotConfigTable	OBJECT-TYPE
	SYNTAX		SEQUENCE OF MibmaddSlotConfigEntry
	ACCESS		not-accessible
	STATUS		mandatory
	DESCRIPTION	"A list of mibmaddSlotConfig profile entries."
	::= { mibmaddSlotConfig 1 }

    mibmaddSlotConfigEntry	OBJECT-TYPE
	SYNTAX		MibmaddSlotConfigEntry
	ACCESS		not-accessible
	STATUS		mandatory
	DESCRIPTION	"A mibmaddSlotConfig entry containing objects that
			 maps to the parameters of mibmaddSlotConfig profile."
	INDEX		{ maddSlotConfig-Shelf-o, maddSlotConfig-Slot-o, maddSlotConfig-Item-o }
	::= { mibmaddSlotConfigTable 1 }

    MibmaddSlotConfigEntry ::=
	SEQUENCE {
	    maddSlotConfig-Shelf-o
		INTEGER,
	    maddSlotConfig-Slot-o
		INTEGER,
	    maddSlotConfig-Item-o
		INTEGER,
	    maddSlotConfig-SlotAddress-Shelf
		INTEGER,
	    maddSlotConfig-SlotAddress-Slot
		INTEGER,
	    maddSlotConfig-SlotAddress-ItemNumber
		INTEGER,
	    maddSlotConfig-Subtype
		INTEGER,
	    maddSlotConfig-Action-o
		INTEGER
	}

    maddSlotConfig-Shelf-o	OBJECT-TYPE
	SYNTAX	INTEGER
	ACCESS	read-only
	STATUS	mandatory
	DESCRIPTION	""
	::= { mibmaddSlotConfigEntry 1 }

    maddSlotConfig-Slot-o	OBJECT-TYPE
	SYNTAX	INTEGER
	ACCESS	read-only
	STATUS	mandatory
	DESCRIPTION	""
	::= { mibmaddSlotConfigEntry 2 }

    maddSlotConfig-Item-o	OBJECT-TYPE
	SYNTAX	INTEGER
	ACCESS	read-only
	STATUS	mandatory
	DESCRIPTION	""
	::= { mibmaddSlotConfigEntry 3 }

    maddSlotConfig-SlotAddress-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { mibmaddSlotConfigEntry 4 }

    maddSlotConfig-SlotAddress-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { mibmaddSlotConfigEntry 5 }

    maddSlotConfig-SlotAddress-ItemNumber	OBJECT-TYPE
	SYNTAX	INTEGER
	ACCESS	read-write
	STATUS	mandatory
	DESCRIPTION	"A number that specifies an addressable entity within the context of shelf and slot."
	::= { mibmaddSlotConfigEntry 6 }

    maddSlotConfig-Subtype	OBJECT-TYPE
	SYNTAX	INTEGER {
		    n-288UnivPorts (1),
		    n-480VoipPorts (2),
		    n-192Ip2ipPorts (3)
		}
	ACCESS	read-write
	STATUS	mandatory
	DESCRIPTION	"The madd3 software-subtype to boot."
	::= { mibmaddSlotConfigEntry 7 }

    maddSlotConfig-Action-o	OBJECT-TYPE
	SYNTAX	INTEGER {
		    noAction (1),
		    createProfile (2),
		    deleteProfile (3)
		}
	ACCESS	read-write
	STATUS	mandatory
	DESCRIPTION	""
	::= { mibmaddSlotConfigEntry 8 }

END
