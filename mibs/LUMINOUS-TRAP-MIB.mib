LUMINOUS-TRAP-MIB DEFINITIONS ::= BEGIN
     IMPORTS
             
             TRAP-TYPE, enterprises                        FROM RFC-1215
             lumDownLoadStatus                FROM LUMINOUS-SYSTEM-MIB 

             
             lumShelfPlane, lumSlotID, lumCardOperState, lumCardType  
                                              FROM LUMINOUS-TC-MIB

             lumProvisionAlarmType, lumAlarmCardAlarmType, 
             lumSysconAlarmType, lumT1AlarmType, lumTEN100AlarmType,
             lumSonetAlarmType, lumRingCardAlarmType, 
             lumUtilityAlarmType, lumEquipmentAlarmType,
             lumAlarmSlotId,  lumAlarmPortId, lumAlarmStatus,
             lumDataFlowAlarmType,  lumDataBaseAlarmType,
             lumPPPAlarmType 
                                    FROM LUMINOUS-SYSTEM-MIB

             lumTdmLocalCardSlotId ,
             lumTdmLocalPortNumber,
             lumTdmConnectNodeIP,
             lumTdmConnectCardSlotId,
             lumTdmConnectPortNumber,         
             lumTdmConnectionUpTime,
             lumTdmConnectionStatus,
             lumDPLocalCardSlotId,
             lumDPLocalPortNumber,
             lumDPConnectNumber,
             lumDPConnectNodeIP,
             lumDPConnectCardSlotId,
             lumDPConnectPortNumber,
             lumDPConnectionUpTime,
             lumDPConnectionStatus      FROM  LUMINOUS-PROVISIONING-MIB

             lumLinkIngressNodeIP       FROM  LUMINOUS-TOPOLOGY-MIB;


-- IANA-registered  Luminous Network Enterprise Number of 4614
--

     luminous OBJECT IDENTIFIER ::= { enterprises 4614}

     

     lumCardInserted TRAP-TYPE
              ENTERPRISE  luminous 
              VARIABLES   { lumShelfPlane, lumSlotID, lumCardType }
              DESCRIPTION
                          "Issues when a card is inserted
                           into the shelf's slot."
              ::= 1


     lumCardRemoved TRAP-TYPE
              ENTERPRISE  luminous 
              VARIABLES   { lumShelfPlane, lumSlotID }
              DESCRIPTION
                          "Issued when a card is removed
                           from the shelf."
              ::= 2

     lumCardStateChange TRAP-TYPE
              ENTERPRISE  luminous 
              VARIABLES   { lumShelfPlane, lumSlotID, lumCardOperState, lumCardType}
              DESCRIPTION
                          "Issued when card's operational
                           state changes."
              ::= 3

     lumDownloadComplete TRAP-TYPE
              ENTERPRISE  luminous 
              VARIABLES   { lumShelfPlane, lumSlotID, lumDownLoadStatus}
              DESCRIPTION
                          "Issued when card's operational
                           state changes."
              ::= 4



      lumProvisionAlarm TRAP-TYPE
              ENTERPRISE  luminous 
              VARIABLES   { lumProvisionAlarmType, 
                            lumAlarmStatus, lumAlarmSlotId }
              DESCRIPTION
                          "For event related to provisioning fault."
              ::= 5

      lumAlarmCardAlarm TRAP-TYPE
              ENTERPRISE  luminous 
              VARIABLES   { lumAlarmCardAlarmType,  
                            lumAlarmStatus, lumAlarmSlotId }
              DESCRIPTION
                          "User defined alarms from the Alarm card."
              ::= 6

       lumSysconAlarm TRAP-TYPE
              ENTERPRISE  luminous 
              VARIABLES   { lumSysconAlarmType, 
                            lumAlarmStatus, lumAlarmSlotId }
              DESCRIPTION
                          "For event related to the syscon cards."
              ::= 7

       lumT1Alarm TRAP-TYPE
              ENTERPRISE  luminous 
              VARIABLES   { lumT1AlarmType, lumAlarmStatus,
                            lumAlarmSlotId, lumAlarmPortId}
              DESCRIPTION
                          "For event related to the T1 Line cards."
              ::= 8

       lumTEN100Alarm TRAP-TYPE
              ENTERPRISE  luminous 
              VARIABLES   { lumTEN100AlarmType, lumAlarmStatus,
                            lumAlarmSlotId, lumAlarmPortId}
              DESCRIPTION
                          "For event related to TEN100 line cards."
              ::= 9

        lumSonetAlarm TRAP-TYPE
              ENTERPRISE  luminous 
              VARIABLES   { lumSonetAlarmType, lumAlarmStatus,
                            lumAlarmSlotId, lumAlarmPortId}
              DESCRIPTION
                          "For event related to the Sonet layer on the i
                           Sonet uplink cards."
              ::= 10

        lumRingCardAlarm TRAP-TYPE
              ENTERPRISE  luminous 
              VARIABLES   { lumRingCardAlarmType, lumAlarmStatus,
                            lumAlarmSlotId, lumAlarmPortId}
              DESCRIPTION
                          "For event related to the Ring cards."
              ::= 11

 
        lumUtilityAlarm TRAP-TYPE
              ENTERPRISE  luminous 
              VARIABLES   { lumUtilityAlarmType, lumAlarmStatus }
              DESCRIPTION
                          "For event related to the utility card."
              ::= 12


        lumEquipmentAlarm TRAP-TYPE
              ENTERPRISE  luminous 
              VARIABLES   { lumEquipmentAlarmType, lumAlarmStatus,
                            lumAlarmSlotId }
              DESCRIPTION
                          "For event related to the equipment.
                           When the lumAlarmSlotId is 0, the
                           alarm applys to the entire chassis."
              ::= 13


        
        lumDataFlowAlarm TRAP-TYPE
              ENTERPRISE  luminous 
              VARIABLES   { lumDataFlowAlarmType, lumAlarmStatus }
              DESCRIPTION
                          "For event related to data flow."
              ::= 14

        
         lumDataBaseAlarm TRAP-TYPE
              ENTERPRISE  luminous
              VARIABLES   { lumDataBaseAlarmType, lumAlarmStatus }
              DESCRIPTION
                       "For event related to data base operation."
              ::= 15

         lumTdmCrossConnectChange TRAP-TYPE
              ENTERPRISE  luminous 
              VARIABLES   { lumTdmLocalCardSlotId ,
                            lumTdmLocalPortNumber,
                            lumTdmConnectNodeIP,
                            lumTdmConnectCardSlotId,
                            lumTdmConnectPortNumber,         
                            lumTdmConnectionUpTime,
                            lumTdmConnectionStatus }
              DESCRIPTION
                          "Issued when TDM crossconnect
                           is added/changed/removed."
              ::= 16


         lumDPProvisioningChange TRAP-TYPE
              ENTERPRISE  luminous 
              VARIABLES   {  
                            lumDPLocalCardSlotId,
                            lumDPLocalPortNumber,
                            lumDPConnectNumber,
                            lumDPConnectNodeIP,
                            lumDPConnectCardSlotId,
                            lumDPConnectPortNumber,
                            lumDPConnectionUpTime,
                            lumDPConnectionStatus }
              DESCRIPTION
                          "Issued after a provisioning
                           is added/changed/removed."
              ::= 17


     lumNeighborNodeDiscovered TRAP-TYPE
              ENTERPRISE  luminous 
              VARIABLES   { lumLinkIngressNodeIP }
              DESCRIPTION
                          "Issued when the node is discovered
                           by its neighbor."
              ::= 18


     lumNeighborNodeLost TRAP-TYPE
              ENTERPRISE  luminous 
              VARIABLES   { lumLinkIngressNodeIP }
              DESCRIPTION
                          "Issued when contact with the node is lost
                           by its neighbor."
              ::= 19

       
      lumPPPAlarm TRAP-TYPE
              ENTERPRISE  luminous
              VARIABLES   { lumPPPAlarmType, lumAlarmStatus,
                            lumAlarmSlotId, lumAlarmPortId}
              DESCRIPTION
                          "For event related to the PPP layer on the 
                           Sonet uplink cards."
              ::= 20
               
END
