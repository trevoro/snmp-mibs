USR-SS7-MIB DEFINITIONS ::= BEGIN
    IMPORTS
        OBJECT-TYPE, MODULE-IDENTITY, NOTIFICATION-TYPE,
        IpAddress, Integer32
			FROM  SNMPv2-SMI
        DateAndTime
            FROM  SNMPv2-TC
        common
            FROM USR-DEFINITIONS-MIB;
usrSS7   MODULE-IDENTITY
         LAST-UPDATED "200205011925Z"
         ORGANIZATION "CommWorks Corporation, a 3Com Company"
         CONTACT-INFO "Customer Support"
         DESCRIPTION
                 "The commWorks enterprise defined MIB objects for SS7."
--       REVISION "200205011925Z"
--       DESCRIPTION "Converted to SNMPv2"
     ::= { common 77 }
usrSS7Protocol OBJECT-TYPE
    SYNTAX  INTEGER {
        slapv2(1),
        ipdc(2)
        }
   	  MAX-ACCESS      read-write
   	  STATUS          current
	  DESCRIPTION " protocol being serviced:- HSS7I_SLAP_V2 or HSS7I_IPDC."
        --CONFIGURABLE
      ::= {usrSS7 1}
usrSS7LANStartMethod OBJECT-TYPE
   	  SYNTAX      INTEGER {
	  	auto(1),
		manual(2)
	   }
   	  MAX-ACCESS      read-write
   	  STATUS          current
	  DESCRIPTION "method to bring up TCP/IP connection to SS7GWP - HSS7I_LS_AUTO or HSS7I_LS_MANUAL."
        --CONFIGURABLE
      ::= {usrSS7 2}
usrSS7SLAPgatewayIPAddress OBJECT-TYPE
   	  SYNTAX      IpAddress
   	  MAX-ACCESS      read-write
   	  STATUS          current
	  DESCRIPTION "The IP address of the SLAP SS7 gateway."
        --CONFIGURABLE
      ::= {usrSS7 3}
usrSS7SLAPgatewayPort OBJECT-TYPE
   	  SYNTAX      Integer32
   	  MAX-ACCESS      read-write
   	  STATUS          current
	  DESCRIPTION "The TCP port# of the SLAP SS7 gateway."
        --CONFIGURABLE
      ::= {usrSS7 4}
usrSS7SLAPHeartbeatTimerNearEnd OBJECT-TYPE
   	  SYNTAX      Integer32
   	  MAX-ACCESS      read-write
   	  STATUS          current
	  DESCRIPTION "The heartbeat timer settings."
        --CONFIGURABLE
      ::= {usrSS7 5}
usrSS7SLAPChassisID OBJECT-TYPE
   	  SYNTAX      Integer32
   	  MAX-ACCESS      read-write
   	  STATUS          current
	  DESCRIPTION "uniquely identify the TCH in a WAN." 
        --CONFIGURABLE
      ::= {usrSS7 6}
usrSS7SLAPNumberOfConnectionRetries OBJECT-TYPE
   	  SYNTAX      Integer32
   	  MAX-ACCESS      read-write
   	  STATUS          current
	  DESCRIPTION "number of socket connection retries after lost it"
        --CONFIGURABLE
      ::= {usrSS7 7}
usrSS7SLAPConnectionRetryInterval OBJECT-TYPE
   	  SYNTAX      Integer32
   	  MAX-ACCESS      read-write
   	  STATUS          current
	  DESCRIPTION "socket connection retry interval after it is lost"
        --CONFIGURABLE
      ::= {usrSS7 8}
usrSS7SLAPAllowedMissedHeartBeats OBJECT-TYPE
   	  SYNTAX      Integer32
   	  MAX-ACCESS      read-write
   	  STATUS          current
	  DESCRIPTION "number of heartbeat missed from gw before action taken."
        --CONFIGURABLE
      ::= {usrSS7 9}
--  The following are the IPDC mibs which are not supported now..
--  remove the comments when they are supported..
-- 
-- usrSS7IPDCPrimaryIpAddress OBJECT-TYPE
--   	  SYNTAX      IpAddress
--   	  MAX-ACCESS      read-write
--   	  STATUS          current
--	  DESCRIPTION " primary IP address to Soft Switch."
--        CONFIGURABLE
--      ::= {usrSS7 10}
--
-- usrSS7IPDCPrimaryPort OBJECT-TYPE
--   	  SYNTAX      Integer32
--   	  MAX-ACCESS      read-write
--   	  STATUS          current
--	  DESCRIPTION " primary port to Soft Switch."
--       CONFIGURABLE
--      ::= {usrSS7 11}
--
-- usrSS7IPDCSecondaryIpAddress OBJECT-TYPE
--    	  SYNTAX      IpAddress
--    	  MAX-ACCESS      read-write
--    	  STATUS          current
-- 	  DESCRIPTION " Secondary IP address to Soft Switch."
--         CONFIGURABLE
--       ::= {usrSS7 12}
--
-- usrSS7IPDCSecondaryPort OBJECT-TYPE
--    	  SYNTAX      Integer32
--    	  MAX-ACCESS      read-write
--    	  STATUS          current
-- 	  DESCRIPTION " Secondary port to Soft Switch."
--         CONFIGURABLE
--       ::= {usrSS7 13}
--
-- usrSS7IPDCBayNumber OBJECT-TYPE
--    	  SYNTAX      Integer32
--    	  MAX-ACCESS      read-write
--    	  STATUS          current
-- 	  DESCRIPTION " Bay Number is an 8 bytes alphanumeric quantity which identifies the rack"
--       CONFIGURABLE
--      ::= {usrSS7 14}
--
-- usrSS7IPDCSystemType OBJECT-TYPE
-- 	  SYNTAX      Integer32
-- 	  MAX-ACCESS      read-write
--  	  STATUS          current
--	  DESCRIPTION "type of system by L3."
--       CONFIGURABLE
--      ::= {usrSS7 15}
usrSS7StatSBUSXmitPacketsOKCount OBJECT-TYPE
   	  SYNTAX      Integer32
   	  MAX-ACCESS      read-only
   	  STATUS          current
	  DESCRIPTION "the number of successful packets transmitted over the pBus connection."
      ::= {usrSS7 16}
usrSS7StatSBUSXmitPacketsFailCount OBJECT-TYPE
   	  SYNTAX      Integer32
   	  MAX-ACCESS      read-only
   	  STATUS          current
	  DESCRIPTION "the number of packets failed to transmit over the pBus connection."
      ::= {usrSS7 17}
usrSS7StatSBUSRcvdPacketsOKCount OBJECT-TYPE
   	  SYNTAX      Integer32
   	  MAX-ACCESS      read-only
   	  STATUS          current
	  DESCRIPTION "the number of successful packets received over the pBus connection."
      ::= {usrSS7 18}
usrSS7StatSBUSRcvdmitPacketsFailCount OBJECT-TYPE
   	  SYNTAX      Integer32
   	  MAX-ACCESS      read-only
   	  STATUS          current
	  DESCRIPTION "the number of packets rejected by the pBus/Sbus client application."
      ::= {usrSS7 19}
usrSS7StatGWXmitByetsCount OBJECT-TYPE
   	  SYNTAX      Integer32
   	  MAX-ACCESS      read-only
   	  STATUS          current
	  DESCRIPTION "the number of successful bytes transmitted over the SS7 GW connection."
      ::= {usrSS7 20}
usrSS7StatGWXmitPacketsCount OBJECT-TYPE
   	  SYNTAX      Integer32
   	  MAX-ACCESS      read-only
   	  STATUS          current
	  DESCRIPTION "the number of packets transmited to the SS7 GW connection."
      ::= {usrSS7 21}
usrSS7StatGWRcvdBytesCount OBJECT-TYPE
   	  SYNTAX      Integer32
   	  MAX-ACCESS      read-only
   	  STATUS          current
	  DESCRIPTION "the number of Bytes received over the SS7 GW connection."
      ::= {usrSS7 22}
usrSS7StatGWRcvdPacketsCount OBJECT-TYPE
   	  SYNTAX      Integer32
   	  MAX-ACCESS      read-only
   	  STATUS          current
	  DESCRIPTION "the number of packets from SS7 GW."
      ::= {usrSS7 23}
usrSS7GWConnectionState OBJECT-TYPE
   	  SYNTAX      Integer32
   	  MAX-ACCESS      read-only
   	  STATUS          current
	  DESCRIPTION "the state of the SS7 GW connection UP/DOWN"
      ::= {usrSS7 24}
usrSS7SLAPSecondaryGatewayIPAddress OBJECT-TYPE
   	  SYNTAX      IpAddress
   	  MAX-ACCESS      read-write
   	  STATUS          current
	  DESCRIPTION "The IP address of the SLAP SS7 gateway."
        --CONFIGURABLE
      ::= {usrSS7 25}
usrSS7SLAPSecondaryGatewayPort OBJECT-TYPE
   	  SYNTAX      Integer32
   	  MAX-ACCESS      read-write
   	  STATUS          current
	  DESCRIPTION "The TCP port# of the SLAP SS7 gateway."
        --CONFIGURABLE
      ::= {usrSS7 26}
usrSS7SLAPHeartbeatTimerFarEnd OBJECT-TYPE
   	  SYNTAX      Integer32
   	  MAX-ACCESS      read-write
   	  STATUS          current
	  DESCRIPTION "The heartbeat timer settings."
        --CONFIGURABLE
      ::= {usrSS7 27}
usrSS7SlotTable OBJECT-TYPE
        SYNTAX SEQUENCE OF UsrSS7SlotEntry
        MAX-ACCESS not-accessible
        STATUS     current
        DESCRIPTION
                  "A table containing one row per slot in the chassis.  Each
           row describes the characteristics of the slot"
    ::= { usrSS7 28 }
    usrSS7SlotEntry OBJECT-TYPE
         SYNTAX  UsrSS7SlotEntry
         MAX-ACCESS  not-accessible
         STATUS      current
         DESCRIPTION
            "slot access table"
         INDEX   { usrSS7Slot }
    ::= { usrSS7SlotTable 1 }
    UsrSS7SlotEntry ::=
         SEQUENCE {
         usrSS7Slot
            Integer32,
         usrSS7SlotOwner
            INTEGER,
         usrSS7SlotType
            INTEGER,
		 usrSS7SlotConnectionStatus
			Integer32,
		 usrSS7SlotTrace
			INTEGER,
		 usrSS7SlotConnectToSlot
			Integer32,
		 usrSS7SlotDisconnectToSlot
			Integer32,
		 usrSS7ENFASLinkDownCause
			INTEGER,
    	usrSS7SlotStatSBUSXmitPacketsOKCount
            Integer32,
    	usrSS7SlotStatSBUSXmitPacketsFailCount
            Integer32,
    	usrSS7SlotStatSBUSRcvdPacketsOKCount
            Integer32,
       	usrSS7SlotStatSBUSRcvdmitPacketsFailCount
            Integer32
         }
	usrSS7Slot OBJECT-TYPE
         SYNTAX  Integer32
	 MAX-ACCESS  not-accessible
         STATUS      current
         DESCRIPTION
            "The slot number of this row."
	::= { usrSS7SlotEntry 1 }
	usrSS7SlotOwner OBJECT-TYPE
		SYNTAX   INTEGER {
			no(1),
			yes(2)
			}
         MAX-ACCESS   read-write
         STATUS       current
         DESCRIPTION
            "An indication if this slot's card has this Gateway card assigned
             as the owning gateway"
        --CONFIGURABLE
    ::= { usrSS7SlotEntry 2 }
	usrSS7SlotType OBJECT-TYPE
		SYNTAX   INTEGER {
			static(1),
			dynamic(2)
			}
         MAX-ACCESS   read-write
         STATUS       current
         DESCRIPTION
            "An indicator that tells if this slot's (row's) data was
             created statically by configuration, or dynamically by
             the receipt of chassis awareness information from the
             NMC.  Only static entries are saved to the configuration
             file.  Dynamic entries are saved as static entries with 
             an empty card type. If dynamic information is learned
             it replaces the information in a static entry.  A dynamic
             entry cannot be changed through the CLI or an SNMP set."
        --CONFIGURABLE
         ::= { usrSS7SlotEntry 3 }
	usrSS7SlotConnectionStatus OBJECT-TYPE
		 SYNTAX  Integer32
         MAX-ACCESS  read-only
         STATUS      current
         DESCRIPTION
            "The status of the sbus connection to HDM at this slot."
    ::= { usrSS7SlotEntry 4 }
   usrSS7SlotTrace    OBJECT-TYPE
			SYNTAX   INTEGER {
				enable(1),
				disable(0)
				}
			MAX-ACCESS  read-write
            STATUS      current
            DESCRIPTION
                "SBUS Side SS7 Trace.  enable(1) disable(2) "
   ::= { usrSS7SlotEntry 5 }
   usrSS7SlotConnectToSlot    OBJECT-TYPE
			SYNTAX   Integer32 
			MAX-ACCESS  read-write
            STATUS      current
            DESCRIPTION
                "The Command to connect Hiper Arc to a SS7 channel in the given slot"
   ::= { usrSS7SlotEntry 6 }
   usrSS7SlotDisconnectToSlot    OBJECT-TYPE
			SYNTAX   Integer32 
			MAX-ACCESS  read-write
            STATUS      current
            DESCRIPTION
                "The Command to connect Hiper Arc to a SS7 channel in the given slot"
   ::= { usrSS7SlotEntry 7 }
	usrSS7ENFASLinkDownCause OBJECT-TYPE
			SYNTAX   INTEGER {
				none(0),
				missingHDM(1),
				lostGWConnection(2),
				pBusError(3),
				manualDisconnect(4)
				}
			MAX-ACCESS  read-only
		  STATUS          current
		  DESCRIPTION "The status of the SLAP Connection to the Secondary SS7 gateway."
		  ::= {usrSS7SlotEntry 8 }
	usrSS7SlotStatSBUSXmitPacketsOKCount OBJECT-TYPE
		  SYNTAX      Integer32
		  MAX-ACCESS      read-only
		  STATUS          current
		  DESCRIPTION "the number of successful packets transmitted over the pBus connection."
		  ::= {usrSS7SlotEntry 9}
	usrSS7SlotStatSBUSXmitPacketsFailCount OBJECT-TYPE
		  SYNTAX      Integer32
		  MAX-ACCESS      read-only
		  STATUS          current
		  DESCRIPTION "the number of packets failed to transmit over the pBus connection."
		  ::= {usrSS7SlotEntry 10}
	usrSS7SlotStatSBUSRcvdPacketsOKCount OBJECT-TYPE
		  SYNTAX      Integer32
		  MAX-ACCESS      read-only
		  STATUS          current
		  DESCRIPTION "the number of successful packets received over the pBus connection."
		  ::= {usrSS7SlotEntry 11}
	usrSS7SlotStatSBUSRcvdmitPacketsFailCount OBJECT-TYPE
		  SYNTAX      Integer32
		  MAX-ACCESS      read-only
		  STATUS          current
		  DESCRIPTION "the number of packets rejected by the pBus/Sbus client application."
		  ::= {usrSS7SlotEntry 12}
    usrSS7CountersResetTime    OBJECT-TYPE
            SYNTAX      DateAndTime
            MAX-ACCESS  read-write
            STATUS      current
            DESCRIPTION
                "Daily time we reset all the sbus statistics counters."
   ::= { usrSS7 29 }
   usrSS7GWCountersResetTime    OBJECT-TYPE
            SYNTAX      DateAndTime
            MAX-ACCESS  read-write
            STATUS      current
            DESCRIPTION
                "Daily time we reset all the SS7 GW connection  statistics counters."
   ::= { usrSS7 30 }
   usrSS7ConnectToGW    OBJECT-TYPE
            SYNTAX  OCTET STRING (SIZE (12))
            MAX-ACCESS  read-write
            STATUS      current
            DESCRIPTION
                "Command to connect to the  SS7 GW manual mode"
   ::= { usrSS7 31 }
   usrSS7SlapTrace    OBJECT-TYPE
			SYNTAX   INTEGER {
				enable(1),
				disable(0)
				}
			MAX-ACCESS  read-write
            STATUS      current
            DESCRIPTION
                "SLAP Side SS7 Trace.  enable(1) disable(2) "
        --CONFIGURABLE
   ::= { usrSS7 32 }
   usrSS7TraceOutput    OBJECT-TYPE
			SYNTAX   INTEGER {
				screen(1),
				syslog(2)
				}
			MAX-ACCESS  read-write
            STATUS      current
            DESCRIPTION
                "The place where SS7 Trace output is send to. either to the console or syslog "
        --CONFIGURABLE
   ::= { usrSS7 33 }
   usrSS7DisconnectToGW    OBJECT-TYPE
            SYNTAX  OCTET STRING (SIZE (12))
            MAX-ACCESS  read-write
            STATUS      current
            DESCRIPTION
                "Command to disconnect the the existing conection to SS7 GW.
				this will tear down all the sbus connections to HDMs "
   ::= { usrSS7 34 }
   usrSS7SendHeartBeat    OBJECT-TYPE
            SYNTAX  OCTET STRING (SIZE (12))
            MAX-ACCESS  read-write
            STATUS      current
            DESCRIPTION
                "Command to send a heartbeat to the existing conection to SS7 GW."
   ::= { usrSS7 35 }
   usrSS7MissedHeartBeatsCounter    OBJECT-TYPE
            SYNTAX  Integer32
            MAX-ACCESS  read-only
            STATUS      current
            DESCRIPTION
                "Command to send a heartbeat to the existing conection to SS7 GW."
   ::= { usrSS7 36 }
	usrSS7SLAPPrimaryGatewayConnectionStatus OBJECT-TYPE
			SYNTAX   INTEGER {
				up(1),
				down(2)
				}
			MAX-ACCESS  read-only
		  STATUS          current
		  DESCRIPTION "The status of the SLAP Connection to the Primary SS7 gateway."
		  ::= {usrSS7 37 }
	usrSS7SLAPSecondaryGatewayConnectionStatus OBJECT-TYPE
			SYNTAX   INTEGER {
				up(1),
				down(2)
				}
			MAX-ACCESS  read-only
		  STATUS          current
		  DESCRIPTION "The status of the SLAP Connection to the Secondary SS7 gateway."
		  ::= {usrSS7 38 }
	usrSS7SLAPPrimaryLinkDownCause OBJECT-TYPE
			SYNTAX   INTEGER {
				none(0),
				heartbeatExpired(1),
				socketError(2),
				physicalLinkCut(3),
				manualDisconect(4)
				}
			MAX-ACCESS  read-only
		  STATUS          current
		  DESCRIPTION "The status of the SLAP Connection to the Secondary SS7 gateway."
		  ::= {usrSS7 39 }
	usrSS7SLAPSecondaryLinkDownCause OBJECT-TYPE
			SYNTAX   INTEGER {
				none(0),
				heartbeatExpired(1),
				socketError(2),
				physicalLinkCut(3),
				manualDisconect(4)
				}
			MAX-ACCESS  read-only
		  STATUS          current
		  DESCRIPTION "The status of the SLAP Connection to the Secondary SS7 gateway."
		  ::= {usrSS7 40 }
	usrSS7SLAPUpTrap OBJECT-TYPE
			SYNTAX   INTEGER {
				enable(1),
				disable(0)
				}
			MAX-ACCESS  read-write
		  STATUS          current
		  DESCRIPTION "if enabled sends TRAP each time the SLAP connection
                       to the gateway goes UP."
        --CONFIGURABLE
		  ::= {usrSS7 41 }
	usrSS7SLAPDownTrap OBJECT-TYPE
			SYNTAX   INTEGER {
				enable(1),
				disable(0)
				}
			MAX-ACCESS  read-write
		  STATUS          current
		  DESCRIPTION "if enabled sends TRAP each time the SLAP connection 
                       to the gateway goes Down."
        --CONFIGURABLE
		  ::= {usrSS7 42 }
	usrSS7ENFASUpTrap OBJECT-TYPE
			SYNTAX   INTEGER {
				enable(1),
				disable(0)
				}
			MAX-ACCESS  read-write
		  STATUS          current
		  DESCRIPTION "if enabled sends TRAP each time the ENFAS connection to the
                       HDM goes Up."
        --CONFIGURABLE
		  ::= {usrSS7 43 }
	usrSS7ENFASDownTrap OBJECT-TYPE
			SYNTAX   INTEGER {
				enable(1),
				disable(0)
				}
			MAX-ACCESS  read-write
		  STATUS          current
		  DESCRIPTION "if enabled sends TRAP each time the ENFAS connection to the
                       HDM goes Down."
        --CONFIGURABLE
		  ::= {usrSS7 44 }
	usrSS7DropCallFlag OBJECT-TYPE
			SYNTAX   INTEGER {
				enable(1),
				disable(2)
				}
			MAX-ACCESS  read-write
		  STATUS          current
		  DESCRIPTION "if enabled, drops all the calls, if the connection the GW is gone.
                       after the timer expires ."
        --CONFIGURABLE
		  ::= {usrSS7 45 }
	usrSS7DropCallTimer OBJECT-TYPE
			SYNTAX   Integer32 
			MAX-ACCESS  read-write
		  STATUS        current
		  DESCRIPTION "When timer expires drops all the calls, when looses GW connection"
        --CONFIGURABLE
		  ::= {usrSS7 46 }
    usrSS7Traps OBJECT IDENTIFIER ::= { usrSS7 47 }
	usrSS7SLAPGatewayDownTrap NOTIFICATION-TYPE
        OBJECTS {
                usrSS7SLAPChassisID,
                usrSS7SLAPgatewayIPAddress,
                usrSS7SLAPgatewayPort,
				usrSS7SLAPPrimaryLinkDownCause
                }
        STATUS  current
        DESCRIPTION     "This trap is generated when 
			SLAP connection to the SS7 Gateway goes down."
        --#TYPE    "SS7 Gateway Event"
        --#SUMMARY "Gateway %d failure, cause %d"
        --#ARGUMENTS { 1 3 }
        --#SEVERITY MAJOR
        --#STATE    OPERATIONAL
        --#PROBABLECAUSE "badSocketConnectionOrConfiguration"
        ::= { usrSS7Traps 1 }
	usrSS7SLAPGatewayUPTrap NOTIFICATION-TYPE
        OBJECTS {
                usrSS7SLAPChassisID,
                usrSS7SLAPgatewayIPAddress,
                usrSS7SLAPgatewayPort
                }
        STATUS  current
        DESCRIPTION     "This trap is generated when 
			SLAP connection to the SS7 Gateway is restored."
        --#TYPE    "SS7 Gateway Event"
        --#SUMMARY "Gateway %d conection restored"
        --#ARGUMENTS { 1 }
        --#SEVERITY CLEARED
        --#STATE    OPERATIONAL
        --#PROBABLECAUSE ""
        ::= { usrSS7Traps 2 }
	usrSS7ENFASConnectionDownTrap NOTIFICATION-TYPE
        OBJECTS {
                usrSS7SLAPChassisID,
                usrSS7Slot,
				usrSS7ENFASLinkDownCause
                }
        STATUS  current
        DESCRIPTION     "This trap is generated when 
			ENFAS  connection to the HiperDSP slot is Down."
        --#TYPE    "SS7 ENFAS connection event"
        --#SUMMARY "ENFAS connection for chassis %d, slot %d failure, cause %d"
        --#ARGUMENTS { 0 1 2 }
        --#SEVERITY MAJOR
        --#STATE    OPERATIONAL
        --#PROBABLECAUSE "badConnectionOrConfiguration"
        ::= { usrSS7Traps 3 }
	usrSS7ENFASConnectionUPTrap NOTIFICATION-TYPE
        OBJECTS {
                usrSS7SLAPChassisID,
                usrSS7Slot
                }
        STATUS  current
        DESCRIPTION     "This trap is generated when 
			ENFAS  connection to the HiperDSP slot is restored."
        --#TYPE    "SS7 ENFAS connection event"
        --#SUMMARY "ENFAS connection for chassis %d, slot %d restored"
        --#ARGUMENTS { 0 1 }
        --#SEVERITY CLEARED
        --#STATE    OPERATIONAL
        --#PROBABLECAUSE ""
        ::= { usrSS7Traps 4 }
END         -- End USR-SS7-MIB definitions
-- *********************************************************************
--
--     usr_betasite.mib - 
--		
--
--	Description:	This module contains MIB definitions for the 
--      		Beta Site specific mibs. 
--
--	Author:	Sachin Natu
--
