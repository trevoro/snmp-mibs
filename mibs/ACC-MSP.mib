ACC-MSP DEFINITIONS ::= BEGIN

    IMPORTS
	 OBJECT-TYPE, IpAddress, TimeTicks, Gauge, Counter FROM RFC1155-SMI
	 TRAP-TYPE FROM RFC-1215
         accTrapLogSeqNum FROM ACC-SYSTEM
	accBRG, DisplayString, RowStatus, IfIndex, SmdsAddress
             FROM ACC-MIB;

-- MSP Group
    -- ACC MSP branch
    accMsp 			OBJECT IDENTIFIER ::= { accBRG 76 }
    accMspGeneralScalars	OBJECT IDENTIFIER ::= { accMsp 1 }
    accMspNeighbor		OBJECT IDENTIFIER ::= { accMsp 2 }
-- START CFG_TRAP_ENHANCEMENTS
-- Msp Traps Branch Enterprise
      accMspTraps OBJECT IDENTIFIER     ::= { accMsp 3 }
       accMspTrapMsg     OBJECT-TYPE
        SYNTAX          DisplayString
        ACCESS          read-only
        STATUS          mandatory
        DESCRIPTION
        " Enterprise Trap Message for Msp"
        ::= { accMspTraps 1 }
-- END CFG_TRAP_ENHANCEMENTS 
    --
    --  ACC MSP objects
    --
    accMspAdminState OBJECT-TYPE
	SYNTAX  INTEGER {
		    enabled(1),
		    disabled(2)
		}
	ACCESS  read-write
	STATUS  mandatory
	DESCRIPTION
	     "MSP Adminstrative state."
	DEFVAL { disabled }
	::= { accMspGeneralScalars 1 }
    accMspMode OBJECT-TYPE
	SYNTAX  INTEGER {
			wait(1),
			acknowledge(2)
			}
	ACCESS  read-write
	STATUS  mandatory
	DESCRIPTION
	     "MSP Mode : WAIT means that MSP requires its neighbors to 
	     respond only if they want the call. ACKNOWLEDGE causes all 
	     the MSP neighbors to respond to every request"
	DEFVAL { wait }
	::= { accMspGeneralScalars 2 }
    accMspDelivery OBJECT-TYPE
	SYNTAX	INTEGER {
			multicast(1),
			limited-broadcast(2)
			}
	ACCESS	read-write
	STATUS	mandatory
	DESCRIPTION
	     "Sets the delivery mechanism for MSP packets."
	DEFVAL { multicast }
	::= { accMspGeneralScalars 3 }
    accMspGroupId OBJECT-TYPE
	SYNTAX  INTEGER (0..16777216)
	ACCESS  read-write
	STATUS  mandatory
	DESCRIPTION
	     "MSP Group Identifier, should be the same value on all 
	     MSP NASs."
	DEFVAL { 0 }
	::= { accMspGeneralScalars 4 }
    accMspInterfaceAddress OBJECT-TYPE
        SYNTAX  IpAddress
        ACCESS  read-write
        STATUS  mandatory
        DESCRIPTION
             "The interface address in which the MSP protocol is to 
	     operate over"
        DEFVAL { 0 }
        ::= { accMspGeneralScalars 5 }
    accMspUdpPort OBJECT-TYPE
	SYNTAX  INTEGER (1..65535)
        ACCESS  read-write
        STATUS  mandatory
        DESCRIPTION
             "Changes the default UDP port number that MSP uses when 
	     sending and listening for MSP packets."
        DEFVAL { 2748 }
        ::= { accMspGeneralScalars 6 }
    accMspMaximumTimeout OBJECT-TYPE
        SYNTAX  INTEGER (50..100000)
        ACCESS  read-write
        STATUS  mandatory
        DESCRIPTION
             "Maximum amount of time MSP will wait for an MSP neighbor 
	     to respond to a request."
        DEFVAL { 200 }
        ::= { accMspGeneralScalars 7 }
    accMspMaximumRetransmissions OBJECT-TYPE
        SYNTAX  INTEGER (0..10)
        ACCESS  read-write
        STATUS  mandatory
        DESCRIPTION
             "Used to configure the maximum number of retransmissions 
	     that MSP will send to an MSP neighbor before designating 
	     the neighbors as 'non-responding'."
        DEFVAL { 3 }
        ::= { accMspGeneralScalars 8 }
    accMspMaximumHistorySize OBJECT-TYPE
        SYNTAX  INTEGER (1..256)
        ACCESS  read-write
        STATUS  mandatory
        DESCRIPTION
             "Used to configure the maximum history buffer size.  Must 
	     be in powers of 2."
        DEFVAL { 32 }
        ::= { accMspGeneralScalars 9 }
    accMspMessageLevel OBJECT-TYPE
        SYNTAX  INTEGER (1..7)
        ACCESS  read-write
        STATUS  mandatory
        DESCRIPTION
             "Used to set the message level for MSP.  7 being most 
	     robust."
        DEFVAL { 1 }
        ::= { accMspGeneralScalars 10 }
    accMspDebugMask OBJECT-TYPE
        SYNTAX  INTEGER (0..255)
        ACCESS  read-write
        STATUS  mandatory
        DESCRIPTION
             "Used to selectively enable and disable MSP trap messages 
	     used for debugging.  The debug messages are different from 
	     regular traps."
        DEFVAL { 255 }
        ::= { accMspGeneralScalars 11 }
    accMspStatInPackets OBJECT-TYPE
        SYNTAX  Counter
        ACCESS  read-only
        STATUS  mandatory
        DESCRIPTION
             "Indicates the total number of MSP packets received from 
	     all MSP neighbors, both unicast and multicast packets."
        ::= { accMspGeneralScalars 12 }
    accMspStatOutPackets OBJECT-TYPE
        SYNTAX  Counter
        ACCESS  read-only
        STATUS  mandatory
        DESCRIPTION
             "Indicates the total number of MSP packets sent, including
	     both unicast and multicast packets."
        ::= { accMspGeneralScalars 13 }
    accMspStatInQueries OBJECT-TYPE
        SYNTAX  Counter
        ACCESS  read-only
        STATUS  mandatory
        DESCRIPTION
             "Indicates the number of MSP Query Requests that have been 
	     received from MSP neighbors."
        ::= { accMspGeneralScalars 14 }
    accMspStatOutQueries OBJECT-TYPE
        SYNTAX  Counter
        ACCESS  read-only
        STATUS  mandatory
        DESCRIPTION
             "Indicates the number of MSP Query requests that have been
	     sent by this RAC.  A MSP Query request is sent for each new
	     Multilink call that the RAC receives."
        ::= { accMspGeneralScalars 15 }
    accMspStatInAcks OBJECT-TYPE
        SYNTAX  Counter
        ACCESS  read-only
        STATUS  mandatory
        DESCRIPTION
             "Indicates the number of MSP acknowledge packets received by 
	     this RAC"
        ::= { accMspGeneralScalars 16 }
    accMspStatOutAcks OBJECT-TYPE
        SYNTAX  Counter
        ACCESS  read-only
        STATUS  mandatory
        DESCRIPTION
             "Indicates the number of MSP acknowledges sent by this RAC."
        ::= { accMspGeneralScalars 17 }
    accMspStatInRequests OBJECT-TYPE
        SYNTAX  Counter
        ACCESS  read-only
        STATUS  mandatory
        DESCRIPTION
             "Indicates the number of times a MSP neighbor has requested a 
	     remote client session from this RAC."
        ::= { accMspGeneralScalars 18 }
    accMspStatOutRequests OBJECT-TYPE
        SYNTAX  Counter
        ACCESS  read-only
        STATUS  mandatory
        DESCRIPTION
             "Indicates the number of times This RAC has requested a 
	     remote client session from a MSP neighbor."
        ::= { accMspGeneralScalars 19 }
    accMspStatInDiscards OBJECT-TYPE
        SYNTAX  Counter
        ACCESS  read-only
        STATUS  mandatory
        DESCRIPTION
             "Indicates the number of times the local MSP protocol has 
	     discarded MSP packets.This counter increases if MSP receives 
	     a MSP packet that is not a member of its group. This counter 
	     will also increase whenever a MSP packet fails to be 
	     processed."
        ::= { accMspGeneralScalars 20 }
    accMspStatProcessingErrors OBJECT-TYPE
        SYNTAX  Counter
        ACCESS  read-only
        STATUS  mandatory
        DESCRIPTION
             "Indicates the number of times the MSP protocol has failed to
	     process a MSP packet. Failures arise from conditions where the 
	     packet could not be correctly processed, possibly because of 
	     resource limitations."
        ::= { accMspGeneralScalars 21 }
    accMspStatNotForMes OBJECT-TYPE
        SYNTAX  Counter
        ACCESS  read-only
        STATUS  mandatory
        DESCRIPTION
             "Indicates number of times an MSP acknowledgment to a query not 
	     generated by this RAC has been received by this MSP protocol 
	     entity. This is normal for piggybacked responses, which are 
	     broadcast to the entire MSP community comprising the virtual 
	     machine."
        ::= { accMspGeneralScalars 22 }
    accMspStatProtocolErrors OBJECT-TYPE
        SYNTAX  Counter
        ACCESS  read-only
        STATUS  mandatory
        DESCRIPTION
             "Indicates the number of times this MSP protocol entity has
	     encountered MSP protocol errors in processing a MSP packet."
        ::= { accMspGeneralScalars 23 }
    accMspStatInQueryPiggys OBJECT-TYPE
        SYNTAX  Counter
        ACCESS  read-only
        STATUS  mandatory
        DESCRIPTION
             "Along with Out Query Piggy, In Ack Piggy, and Out Ack Piggy 
	     indicates how well MSP is operating. As MSP activity increases,
	     the MSP protocol is designed to piggyback Query Requests and 
	     Query Acknowledgments in the same response packet to optimize 
	     network traffic and to address scaling issues."
        ::= { accMspGeneralScalars 24 }
    accMspStatOutQueryPiggys OBJECT-TYPE
        SYNTAX  Counter
        ACCESS  read-only
        STATUS  mandatory
        DESCRIPTION
             "Along with Out Query Piggy, In Ack Piggy, and Out Ack Piggy 
	     indicates how well MSP is operating. As MSP activity increases,
	     the MSP protocol is designed to piggyback Query Requests and 
	     Query Acknowledgments in the same response packet to optimize 
	     network traffic and to address scaling issues."
        ::= { accMspGeneralScalars 25 }
    accMspStatInAckPiggys OBJECT-TYPE
        SYNTAX  Counter
        ACCESS  read-only
        STATUS  mandatory
        DESCRIPTION
             "Along with Out Query Piggy, In Ack Piggy, and Out Ack Piggy 
	     indicates how well MSP is operating. As MSP activity increases,
	     the MSP protocol is designed to piggyback Query Requests and 
	     Query Acknowledgments in the same response packet to optimize 
	     network traffic and to address scaling issues."
        ::= { accMspGeneralScalars 26 }
    accMspStatOutAckPiggys OBJECT-TYPE
        SYNTAX  Counter
        ACCESS  read-only
        STATUS  mandatory
        DESCRIPTION
             "Along with Out Query Piggy, In Ack Piggy, and Out Ack Piggy 
	     indicates how well MSP is operating. As MSP activity increases,
	     the MSP protocol is designed to piggyback Query Requests and 
	     Query Acknowledgments in the same response packet to optimize 
	     network traffic and to address scaling issues."
        ::= { accMspGeneralScalars 27 }
    accMspStatQueryTimeouts OBJECT-TYPE
        SYNTAX  Counter
        ACCESS  read-only
        STATUS  mandatory
        DESCRIPTION
             "Indicates the number of times the local MSP protocol entity 
	     has timed out while waiting for a query response. This is 
	     normal in TIMEOUT mode of operation. However, if an excessive 
	     number of timeouts are indicated in ACKNOWLEDGE mode, there 
	     may be a problem with a particular RAC or excessive network 
	     traffic may be resulting in lost packets."
        ::= { accMspGeneralScalars 28 }
    accMspStatMemoryFails OBJECT-TYPE
        SYNTAX  Counter
        ACCESS  read-only
        STATUS  mandatory
        DESCRIPTION
             "Indicates the number of times this MSP protocol entity has 
	     failed to acquire memory when performing its protocol 
	     operations."
        ::= { accMspGeneralScalars 29 }
    accMspStatAverageQueryClosure OBJECT-TYPE
        SYNTAX  Gauge
        ACCESS  read-only
        STATUS  mandatory
        DESCRIPTION
             "Indicates the average time to close a MSP Query Request. When
	     in TIMEOUT mode, this value coincides with the configured 
	     maximum timeout parameter value. The default value for this 
	     parameter is 100 ms. In ACKNOWLEDGE mode, this value varies 
	     and usually is a good indicator of MSP responsiveness. A 'good' 
	     response time would be less than the configured timeout 
	     interval."
        ::= { accMspGeneralScalars 30 }
    accMspStatCurrentTimeout OBJECT-TYPE
        SYNTAX  Gauge
        ACCESS  read-only
        STATUS  mandatory
        DESCRIPTION
             "indicates the current timeout value being used. In TIMEOUT mode,
	     this will always be the maximum timeout value. In ACKNOWLEDGE mode, 
	     this value varies, but in steady state, it should be close to 
	     the Average Closure interval. If it is not, and this value continues 
	     to vary, it may indicate MSP activity problems such as high packet 
	     loss due to network congestion."
        ::= { accMspGeneralScalars 31 }
    --
    --		The MSP Neighbor Table
    --
    accMspNeighborTable OBJECT-TYPE
	SYNTAX  SEQUENCE OF AccMspNeighborEntry
	ACCESS		not-accessible
	STATUS		mandatory
	DESCRIPTION
	     "Displays all active MSP Neighbors."
    ::= { accMspNeighbor 1 }
    accMspNeighborEntry OBJECT-TYPE
	SYNTAX  AccMspNeighborEntry
	ACCESS  not-accessible
	STATUS  mandatory
        DESCRIPTION
	     ""
	INDEX   { accMspNeighborAddress }
	::= { accMspNeighborTable 1 }
    AccMspNeighborEntry ::= SEQUENCE {
	accMspNeighborAddress		IpAddress,
	accMspNeighborIDs		Counter,
	accMspNeighborVersions		Counter,
	accMspNeighborStates		Counter,
	accMspNeighborAckTimeOuts	Counter,
	accMspNeighborRetransmissions	Counter
	}
    accMspNeighborAddress OBJECT-TYPE
	SYNTAX  IpAddress
	ACCESS  read-only
	STATUS  mandatory
	DESCRIPTION
	     "The remote IP Address of the MSP Neighbor."
	::= { accMspNeighborEntry 1 }
    accMspNeighborIDs OBJECT-TYPE
	SYNTAX  Counter
	ACCESS read-only
	STATUS  mandatory
	DESCRIPTION
	     "Number of times the MSP Neighbor failed to respond to 
	     an MSP request"
	::= { accMspNeighborEntry 2 }
    accMspNeighborVersions OBJECT-TYPE
	SYNTAX  Counter
	ACCESS read-only
	STATUS  mandatory
	DESCRIPTION
	     ""
	::= { accMspNeighborEntry 3 }
    accMspNeighborStates OBJECT-TYPE
	SYNTAX  Counter
	ACCESS read-only
	STATUS  mandatory
	DESCRIPTION
	     ""
	::= { accMspNeighborEntry 4 }
    accMspNeighborAckTimeOuts OBJECT-TYPE
	SYNTAX  Counter
	ACCESS read-only
	STATUS  mandatory
	DESCRIPTION
	     ""
	::= { accMspNeighborEntry 5 }
    accMspNeighborRetransmissions OBJECT-TYPE
	SYNTAX  Counter
	ACCESS read-only
	STATUS  mandatory
	DESCRIPTION
	     ""
	::= { accMspNeighborEntry 6 }

        accMspIpBindTrap TRAP-TYPE
        ENTERPRISE   accMspTraps 
        VARIABLES  { accMspTrapMsg,
                     accMspInterfaceAddress ,
                      accTrapLogSeqNum}
        DESCRIPTION
                   "When the MSP multi cast binding to a IP is
                   attempted, if this fails then this trap is generated.
SEVERITY-DEFAULT: Warning 
EVENTTYPE-DEFAULT: 10 
ADDITIONAL-TEXT-VARIABLES: { accTrapLogSeqNum,accMspTrapMsg }
PCAUSE-DEFAULT: 7 " 
 
        ::= 1
        accMspInvIntfAddrTrap TRAP-TYPE
        ENTERPRISE   accMspTraps 
        VARIABLES  { accMspTrapMsg,
                     accMspInterfaceAddress ,
                      accTrapLogSeqNum}
        DESCRIPTION
                   "if The MSP interface address is not 0.0.0.0 then only
                it is a valid interface address. So, if this check fails
                this trap is generated
SEVERITY-DEFAULT: Warning 
EVENTTYPE-DEFAULT: 10 
ADDITIONAL-TEXT-VARIABLES: { accTrapLogSeqNum,accMspTrapMsg }
PCAUSE-DEFAULT: 7 " 
 
        ::= 2
        accMspShutdownTrap TRAP-TYPE
        ENTERPRISE   accMspTraps 
        VARIABLES  { accMspTrapMsg,
                     accMspNeighborAddress ,
                      accTrapLogSeqNum}
        DESCRIPTION
                   "While creating a MSP neighbor, if the  allocation
                     to that fails due to allocc failure, then this is
                     REAL bad situation as this could break the hello
                     protocol. MSP has to be SHUTDOWN
SEVERITY-DEFAULT: Major 
EVENTTYPE-DEFAULT: 10 
ADDITIONAL-TEXT-VARIABLES: { accTrapLogSeqNum,accMspTrapMsg }
PCAUSE-DEFAULT: 32 " 
 
         ::= 3
END
