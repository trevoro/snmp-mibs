Wellfleet-DVMRP-MIB DEFINITIONS ::= BEGIN

-- Created by mdl2asn version 3.1
-- Creation date: Wed Aug 30 16:40:29 EDT 1995
-- Added GenId, MajorVersion, MinorVersion, and Capabilities to the Neighbor
-- table to compiliant to draft-thaler-dvmrp-mib-03. 01/24/97 by sshieh. 


    IMPORTS

      IpAddress, Counter, Gauge
        FROM RFC1155-SMI
      OBJECT-TYPE
        FROM RFC-1212
      wfDvmrpGroup
        FROM Wellfleet-COMMON-MIB;


    wfDvmrpBase	OBJECT IDENTIFIER ::= { wfDvmrpGroup 1 }

    wfDvmrpBaseCreate OBJECT-TYPE
        SYNTAX	INTEGER {
    		    created(1),
    		    deleted(2)
    		}
        ACCESS	read-write
        STATUS	mandatory
        DESCRIPTION
                "This entry will provide the base configuration for the DVMRP
                multicast support on the router."
        DEFVAL	{ created }
        ::= { wfDvmrpBase 1 }

    wfDvmrpBaseEnable OBJECT-TYPE
        SYNTAX	INTEGER {
    		    enabled(1),
    		    disabled(2)
    		}
        ACCESS	read-write
        STATUS	mandatory
        DESCRIPTION
                "Enable or disable DVMRP support in router"
        DEFVAL	{ enabled }
        ::= { wfDvmrpBase 2 }

    wfDvmrpBaseState OBJECT-TYPE
        SYNTAX	INTEGER {
    		    up(1),
    		    down(2),
    		    init(3),
    		    notpres(4)
    		}
        ACCESS	read-only
        STATUS	mandatory
        DESCRIPTION
                "State of DVMRP base module"
        DEFVAL	{ notpres }
        ::= { wfDvmrpBase 3 }

    wfDvmrpBaseFullUpdateInterval OBJECT-TYPE
        SYNTAX	INTEGER(10..2000)
        ACCESS	read-write
        STATUS	mandatory
        DESCRIPTION
                "Full update interval. This value specifies, in seconds, how
                often routing messages containing complete routing tables are
                sent."
        DEFVAL	{ 60 }
        ::= { wfDvmrpBase 4 }

    wfDvmrpBaseTriggeredUpdateInterval OBJECT-TYPE
        SYNTAX	INTEGER(5..1000)
        ACCESS	read-write
        STATUS	mandatory
        DESCRIPTION
                "Triggered update interval. This value specifies, in seconds,
                how often triggered routing messages are sent; this represents
                the minimum amount of time between these type of messages.
                Triggered updates are sent between full update; the timers
                restart when a full update is sent so this value should be less
                than the full update rate."
        DEFVAL	{ 5 }
        ::= { wfDvmrpBase 5 }

    wfDvmrpBaseLeafTimeout OBJECT-TYPE
        SYNTAX	INTEGER(25..4000)
        ACCESS	read-write
        STATUS	mandatory
        DESCRIPTION
                "Leaf timeout. This value specifies, in seconds, the
                virtual interface hold down timer."
        DEFVAL	{ 200 }
        ::= { wfDvmrpBase 6 }

    wfDvmrpBaseNeighborTimeout OBJECT-TYPE
        SYNTAX	INTEGER(35..8000)
        ACCESS	read-write
        STATUS	mandatory
        DESCRIPTION
                "Neighbor timeout. This value specifies, in seconds, how
                long a router neighbor is considered 'up' without confirmation."
        DEFVAL	{ 35 }
        ::= { wfDvmrpBase 7 }

    wfDvmrpBaseRouteExpirationTimeout OBJECT-TYPE
        SYNTAX	INTEGER(20..4000)
        ACCESS	read-write
        STATUS	mandatory
        DESCRIPTION
                "Route Expiration timeout. This value specifies, in
                seconds, how long a route is considered valid without
                confirmation; this represents the duration of time that this
                route will be used."
        DEFVAL	{ 140 }
        ::= { wfDvmrpBase 8 }

    wfDvmrpBaseGarbageTimeout OBJECT-TYPE
        SYNTAX	INTEGER(40..8000)
        ACCESS	read-write
        STATUS	mandatory
        DESCRIPTION
                "Garbage timeout. This value specifies, in seconds, how
                long a route exists without confirmation; this represents the
                duration of time that this route will be included in routing
                updates. This value must be greater than the route expiration
                timeout."
        DEFVAL	{ 260 }
        ::= { wfDvmrpBase 9 }

    wfDvmrpBaseEstimatedRoutes OBJECT-TYPE
        SYNTAX	INTEGER(10..2147483647)
        ACCESS	read-write
        STATUS	mandatory
        DESCRIPTION
                "Estimated number of routes, per slot. This is used for
                pre-allocating routing tables. Note that routes are kept on a
                per-source network basis, independent of multicast group. This number
                must include a route for every local network that has a CCT configured
                for multicasting."
        DEFVAL	{ 25 }
        ::= { wfDvmrpBase 10 }

    wfDvmrpBaseNeighborProbeInterval OBJECT-TYPE
        SYNTAX	INTEGER(5..30)
        ACCESS	read-write
        STATUS	mandatory
        DESCRIPTION
                "Neighbor probe interval: how often to send a probe on VIFs"
        DEFVAL	{ 10 }
        ::= { wfDvmrpBase 11 }

    wfDvmrpBaseRouteSwitchTimeout OBJECT-TYPE
        SYNTAX	INTEGER(20..2000)
        ACCESS	read-write
        STATUS	mandatory
        DESCRIPTION
                "Route switch timeout. How long to wait, without receiving a subsequent route update
                from the original neighbor, before switching to a different neighbor."
        DEFVAL	{ 140 }
        ::= { wfDvmrpBase 12 }

    wfDvmrpBaseActualRoutes OBJECT-TYPE
        SYNTAX	INTEGER
        ACCESS	read-only
        STATUS	mandatory
        DESCRIPTION
                "Count of number of entries currently in route table"
        ::= { wfDvmrpBase 13 }

    wfDvmrpBaseDebugLevel OBJECT-TYPE
        SYNTAX Gauge(0..4294967295)	
        ACCESS	read-write
        STATUS	mandatory
        DESCRIPTION
             "Turn DVMRP log ON or OFF for DVMRP debuging messages
             The levels are:
             NO_DISPLAY_LOG              0x0001    - Reserved 
             ROUTE_UPDATE_LOG            0x0002    - Displays all routing table events
             CACHE_ADD_LOG               0x0004    - Displays events relating to addition of
                                                     cache entry by the cache gate
             CACHE_DELETE_LOG            0x0008    - Displays all events relating to deletion
                                                     of cache entry
             CACHE_CHANGE_LOG            0x0010    - Displays all events relating to updates of
                                                     cache entries
             CACHE_DATA_LOG              0x0020    - obsolete 
             PRUNE_MSG_LOG               0x0040    - Display router received pruning related
                                                     messages, including prunes, grafts,
                                                     graft_acks, and neighbor reset
             PRUNE_XMIT_LOG              0x0080    - Display a messaged when a initial prune
                                                     state is established for a (src, group).
             IGMP_COM_LOG                0x0100    - Display communication events between IGMP 
                                                     and DVMRP, events including some hosts
                                                     joining a group, and all hosts leaving a
                                                     group.
             DVMRP_XMIT_LOG              0x0200    - Display transmission events by the router,
                                                     e.g, prune, grafts...
             CACHE_NO_GH_LOG             0x0400    - Display buffer forwarding to non-existing main or remote cache gate.
             CACHE_DBG_LOG               0x0800    - Display general debugging messaages
             MEM_DBG_LOG                 0x1000    - Display dvmrp memory usage activities
             INTEROP_DBG_LOG             0x2000    - Display dvmrp mospf debug 
             CACHE_BASE_ADD_LOG          0x4000    - Obsolete  
             CACHE_VIF_ADD_LOG           0x8000    - Obsolete 
             CACHE_BASE_DELETE_LOG       0x10000   - Obsolete 
             CACHE_VIF_DELETE_LOG        0x20000   - Obsolete 
             MTRACE_UPDATE_LOG           0x40000   - Displays mtrace update info
             NEIGHBOR_UPDATE_LOG         0x80000   - Display events relating to 
                                                     addition, deletion and update of 
                                                     neighbor's info 
             MTM_INTERFACE_LOG           0x100000  - Display events relating to MTM-DVMRP
                                                     interface, events as  MTM inbound, 
                                                     outbound interact with DVMRP and entries 
                                                     deletion/addition.
             ROUTE_ADD_LOG               0x200000  - 
             ROUTE_DEL_LOG               0x400000  -
             REMOTE_CACHE_ADD_LOG        0x800000  - Display addition event for the
                                                     outgoing interface of (source, group) 
                                                     cache entry
             REMOTE_CACHE_DELETE_LOG     0x1000000 - Display deletion event for the 
                                                     outgoing interface of (source, group)
                                                     cache entry  
             RX_CONFLICT_ROUTE_INFO_LOG  0x2000000 - Display received conflict 
                                                     route information"
	DEFVAL  { 1 }
        ::= { wfDvmrpBase 14 }

    wfDvmrpBasePruningEnable OBJECT-TYPE
        SYNTAX	INTEGER {
    		    enabled(1),
    		    disabled(2)
    		}
        ACCESS	read-write
        STATUS	mandatory
        DESCRIPTION
                "Enable or Disable Pruning functionality at the Base level"
        DEFVAL	{ enabled }
        ::= { wfDvmrpBase 15 }

    wfDvmrpBaseFragmentMtuThreshold OBJECT-TYPE
        SYNTAX	INTEGER(910..2147483647)
        ACCESS	read-write
        STATUS	obsolete
        DESCRIPTION
                "the default value is the CSMACD_MTU, and the MINiMUN is
                X25_DDN_MTU. Both are taken from dp.h"
        DEFVAL	{ 1514 }
        ::= { wfDvmrpBase 16 }

    wfDvmrpBaseMaxRoutes OBJECT-TYPE
        SYNTAX	INTEGER
        ACCESS	read-write
        STATUS	mandatory
        DESCRIPTION
                "Max number of routes, per slot. This is used to limit
                the size of routing tables. Note that routes are kept on a
                per-source network basis, independent of multicast group. This number
                must include a route for every local network that has a CCT configured
                for multicasting."
        ::= { wfDvmrpBase 17 }

    wfDvmrpBasePolicyEnable OBJECT-TYPE
        SYNTAX	INTEGER {
    		    enabled(1),
    		    disabled(2)
    		}
        ACCESS	read-write
        STATUS  obsolete	
        DESCRIPTION
                "Enable or Disable route policy functionality at the Base level"
        DEFVAL	{ disabled }
        ::= { wfDvmrpBase 18 }

    wfDvmrpBaseHolddownEnable OBJECT-TYPE
        SYNTAX	INTEGER {
    		    enabled(1),
    		    disabled(2)
    		}
        ACCESS	read-write
        STATUS	mandatory
        DESCRIPTION
                "Enable or Disable holddown of deleted routes."
        DEFVAL	{ disabled }
        ::= { wfDvmrpBase 19 }

    wfDvmrpCircuitEntryTable OBJECT-TYPE
        SYNTAX	SEQUENCE OF WfDvmrpCircuitEntry
        ACCESS	not-accessible
        STATUS	mandatory
        DESCRIPTION
                "Circuit virtual interfaces (aka physical VIFs)"
        ::= { wfDvmrpGroup 2 }

    wfDvmrpCircuitEntry OBJECT-TYPE
        SYNTAX	WfDvmrpCircuitEntry
        ACCESS	not-accessible
        STATUS	mandatory
        DESCRIPTION
                "One instance of this object exists for every CCT that supports
                this feature. The instance ID for this object will be the circuit
                number."
        INDEX	{ wfDvmrpCircuitCCT }
        ::= { wfDvmrpCircuitEntryTable 1 }

    WfDvmrpCircuitEntry ::= SEQUENCE {
    	    wfDvmrpCircuitCreate
    		INTEGER,
    	    wfDvmrpCircuitEnable
    		INTEGER,
    	    wfDvmrpCircuitState
    		INTEGER,
    	    wfDvmrpCircuitCCT
    		INTEGER,
    	    wfDvmrpCircuitRouteEnable
    		INTEGER,
    	    wfDvmrpCircuitMetric
    		INTEGER,
    	    wfDvmrpCircuitRouteThreshold
    		INTEGER,
    	    wfDvmrpCircuitInPkts
    		Counter,
    	    wfDvmrpCircuitOutPkts
    		Counter,
    	    wfDvmrpCircuitInRouteUpdates
    		Counter,
    	    wfDvmrpCircuitOutRouteUpdates
    		Counter,
    	    wfDvmrpCircuitInPktDiscards
    		Counter,
    	    wfDvmrpCircuitOutPktDiscards
    		Counter,
    	    wfDvmrpCircuitFwdCacheSize
    		INTEGER,
    	    wfDvmrpCircuitFwdCacheTTL
    		INTEGER,
    	    wfDvmrpCircuitAdvertiseSelf
    		INTEGER,
    	    wfDvmrpCircuitFwdCacheEntries
    		INTEGER,
    	    wfDvmrpCircuitInPrunePkts
    		Counter,
    	    wfDvmrpCircuitOutPrunePkts
    		Counter,
    	    wfDvmrpCircuitInGraftPkts
    		Counter,
    	    wfDvmrpCircuitOutGraftPkts
    		Counter,
    	    wfDvmrpCircuitInGraftAckPkts
    		Counter,
    	    wfDvmrpCircuitOutGraftAckPkts
    		Counter,
            wfDvmrpCircuitDefaultRouteSupply
                INTEGER,
            wfDvmrpCircuitDefaultRouteListen
                INTEGER,
            wfDvmrpCircuitReportDependProbe
                INTEGER,
            wfDvmrpCircuitPruneLifeTime
                INTEGER,
            wfDvmrpCircuitAcceptAggregateRoutes
                INTEGER,
            wfDvmrpCircuitAnnounceAggregatedRoutes
                INTEGER
        }

    wfDvmrpCircuitCreate OBJECT-TYPE
        SYNTAX	INTEGER {
    		    created(1),
    		    deleted(2)
    		}
        ACCESS	read-write
        STATUS	mandatory
        DESCRIPTION
                "Create or delete"
        DEFVAL	{ created }
        ::= { wfDvmrpCircuitEntry 1 }

    wfDvmrpCircuitEnable OBJECT-TYPE
        SYNTAX	INTEGER {
    		    enabled(1),
    		    disabled(2)
    		}
        ACCESS	read-write
        STATUS	mandatory
        DESCRIPTION
                "Enable or disable DVMRP on this circuit"
        DEFVAL	{ enabled }
        ::= { wfDvmrpCircuitEntry 2 }

    wfDvmrpCircuitState OBJECT-TYPE
        SYNTAX	INTEGER {
    		    up(1),
    		    down(2),
    		    init(3),
    		    invalid(4),
    		    notpres(5)
    		}
        ACCESS	read-only
        STATUS	mandatory
        DESCRIPTION
                "The current state of the DVMRP interface. Invalid
                indicates an error in processing the configuration record."
        DEFVAL	{ notpres }
        ::= { wfDvmrpCircuitEntry 3 }

    wfDvmrpCircuitCCT OBJECT-TYPE
        SYNTAX	INTEGER
        ACCESS	read-only
        STATUS	mandatory
        DESCRIPTION
                "This circuit number."
        ::= { wfDvmrpCircuitEntry 4 }

    wfDvmrpCircuitRouteEnable OBJECT-TYPE
        SYNTAX	INTEGER {
    		    enabled(1),
    		    disabled(2)
    		}
        ACCESS	read-write
        STATUS	mandatory
        DESCRIPTION
                "Enable/disble this circuit for routing. If enabled, this
                circuit will be used to propogate routing information,
                information about this circuit will be incorporated into routing
                updates, and multicast datagrams will be forwarded 'in native
                mode' (e.g. as multicast datagrams) via this circuit. If
                disabled, this circuit exists only to support unicast tunnels; in
                this case, all other paramters are ignored."
        DEFVAL	{ enabled }
        ::= { wfDvmrpCircuitEntry 5 }

    wfDvmrpCircuitMetric OBJECT-TYPE
        SYNTAX	INTEGER(1..31)
        ACCESS	read-write
        STATUS	mandatory
        DESCRIPTION
                "Metric. This value represents the cost of this interface;
                the cost of using this hop. This value must be smaller than the
                route infinity value"
        DEFVAL	{ 1 }
        ::= { wfDvmrpCircuitEntry 6 }

    wfDvmrpCircuitRouteThreshold OBJECT-TYPE
        SYNTAX	INTEGER(1..254)
        ACCESS	read-write
        STATUS	mandatory
        DESCRIPTION
                "Threshold. This value can be used to filter out datagrams
                that are being forwarded to a neighboring router; if the IP TTL
                is not >= the threshold, the datagram is dropped by this router"
        DEFVAL	{ 1 }
        ::= { wfDvmrpCircuitEntry 7 }

    wfDvmrpCircuitInPkts OBJECT-TYPE
        SYNTAX	Counter
        ACCESS	read-only
        STATUS	mandatory
        DESCRIPTION
                "Number of datagrams received on this interface"
        ::= { wfDvmrpCircuitEntry 8 }

    wfDvmrpCircuitOutPkts OBJECT-TYPE
        SYNTAX	Counter
        ACCESS	read-only
        STATUS	mandatory
        DESCRIPTION
                "Number of datagrams send on this interface"
        ::= { wfDvmrpCircuitEntry 9 }

    wfDvmrpCircuitInRouteUpdates OBJECT-TYPE
        SYNTAX	Counter
        ACCESS	read-only
        STATUS	mandatory
        DESCRIPTION
                "Number of DVMRP route update messages received"
        ::= { wfDvmrpCircuitEntry 10 }

    wfDvmrpCircuitOutRouteUpdates OBJECT-TYPE
        SYNTAX	Counter
        ACCESS	read-only
        STATUS	mandatory
        DESCRIPTION
                "Number of DVMRP route update messages sent"
        ::= { wfDvmrpCircuitEntry 11 }

    wfDvmrpCircuitInPktDiscards OBJECT-TYPE
        SYNTAX	Counter
        ACCESS	read-only
        STATUS	mandatory
        DESCRIPTION
                "Number of inbound datagrams discarded due to route not found"
        ::= { wfDvmrpCircuitEntry 12 }

    wfDvmrpCircuitOutPktDiscards OBJECT-TYPE
        SYNTAX	Counter
        ACCESS	read-only
        STATUS	mandatory
        DESCRIPTION
                "Number of outbound datagrams discarded due to route not found"
        ::= { wfDvmrpCircuitEntry 13 }

    wfDvmrpCircuitFwdCacheSize OBJECT-TYPE
        SYNTAX	INTEGER(32..512)
        ACCESS	read-write
        STATUS	mandatory
        DESCRIPTION
                "Maximum number of entries allowed in the Forwarding table
                at one time.  there is a Forwarding table per vif"
        DEFVAL	{ 32 }
        ::= { wfDvmrpCircuitEntry 14 }

    wfDvmrpCircuitFwdCacheTTL OBJECT-TYPE
        SYNTAX	INTEGER(0..86400)
        ACCESS	read-write
        STATUS	mandatory
        DESCRIPTION
                "The time_to_live for the Forwarding table entries in seconds ."
        DEFVAL	{ 7200 }
        ::= { wfDvmrpCircuitEntry 15 }

    wfDvmrpCircuitAdvertiseSelf OBJECT-TYPE
        SYNTAX	INTEGER {
    		    enabled(1),
    		    disabled(2)
    		}
        ACCESS	read-write
        STATUS	mandatory
        DESCRIPTION
                "If enabled the router will advertise itself as one of
                the source net. If not enabled the router will not advertise
                itself as one of the source net."
        DEFVAL	{ enabled }
        ::= { wfDvmrpCircuitEntry 16 }

    wfDvmrpCircuitFwdCacheEntries OBJECT-TYPE
        SYNTAX	INTEGER
        ACCESS	read-only
        STATUS	mandatory
        DESCRIPTION
                "The most up to date number of entries in the forwarding cache"
        ::= { wfDvmrpCircuitEntry 17 }

    wfDvmrpCircuitInPrunePkts OBJECT-TYPE
        SYNTAX	Counter
        ACCESS	read-only
        STATUS	mandatory
        DESCRIPTION
                "Number of PRUNE datagrams received on this interface"
        ::= { wfDvmrpCircuitEntry 18 }

    wfDvmrpCircuitOutPrunePkts OBJECT-TYPE
        SYNTAX	Counter
        ACCESS	read-only
        STATUS	mandatory
        DESCRIPTION
                "Number of PRUNE datagrams send on this interface"
        ::= { wfDvmrpCircuitEntry 19 }

    wfDvmrpCircuitInGraftPkts OBJECT-TYPE
        SYNTAX	Counter
        ACCESS	read-only
        STATUS	mandatory
        DESCRIPTION
                "Number of GRAFT datagrams received on this interface"
        ::= { wfDvmrpCircuitEntry 20 }

    wfDvmrpCircuitOutGraftPkts OBJECT-TYPE
        SYNTAX	Counter
        ACCESS	read-only
        STATUS	mandatory
        DESCRIPTION
                "Number of GRAFT datagrams send on this interface"
        ::= { wfDvmrpCircuitEntry 21 }

    wfDvmrpCircuitInGraftAckPkts OBJECT-TYPE
        SYNTAX	Counter
        ACCESS	read-only
        STATUS	mandatory
        DESCRIPTION
                "Number of GRAFT_ACK datagrams received on this interface"
        ::= { wfDvmrpCircuitEntry 22 }

    wfDvmrpCircuitOutGraftAckPkts OBJECT-TYPE
        SYNTAX	Counter
        ACCESS	read-only
        STATUS	mandatory
        DESCRIPTION
                "Number of GRAFT_ACK datagrams send on this interface"
        ::= { wfDvmrpCircuitEntry 23 }

    wfDvmrpCircuitDefaultRouteSupply OBJECT-TYPE
        SYNTAX  INTEGER {
                enabled(1),
                disabled(2),
                generate(3)
                }
        ACCESS  read-write
        STATUS  mandatory
        DESCRIPTION
                "enabled : Send the default route, 0.0.0.0 if learned, 
                           form  this interface.
                 disabled: no default route is sent from this interface.
                 generate: generate default route, 0.0.0.0 from this
                           interface."
        DEFVAL  { enabled }
        ::= { wfDvmrpCircuitEntry 24 }

    wfDvmrpCircuitDefaultRouteListen OBJECT-TYPE
        SYNTAX  INTEGER {
                enabled(1),
                disabled(2)
                }
        ACCESS  read-write
        STATUS  mandatory
        DESCRIPTION
                "Receive the default route, 0.0.0.0 on this interface"
        DEFVAL  { enabled }
        ::= { wfDvmrpCircuitEntry 25 }

    wfDvmrpCircuitReportDependProbe OBJECT-TYPE
        SYNTAX  INTEGER {
                enabled(1),
                disabled(2)
                }
        ACCESS  read-write
        STATUS  mandatory
        DESCRIPTION
                "This is to control accepting the route report. According to 
                 the protocol, dvmrp should send probe packet before sending
                 the route report packet to the neighbors. But some vendor
                 implementation did not send probes before sending reports.
                 Enable: only process the routes from the neighbor sending
                 probes. Disable: No Dependency (no restriction)."
        DEFVAL  { disabled }
        ::= { wfDvmrpCircuitEntry 26 }


    wfDvmrpCircuitPruneLifeTime OBJECT-TYPE
        SYNTAX  INTEGER(0..86400)
        ACCESS  read-write
        STATUS  mandatory
        DESCRIPTION
                "The life time of the prune message the router sends
                 to its neighbor in seconds."
        DEFVAL  { 7200 }
        ::= { wfDvmrpCircuitEntry 27 }


    wfDvmrpCircuitAcceptAggregateRoutes OBJECT-TYPE
        SYNTAX  INTEGER
        ACCESS  read-only
        STATUS  mandatory
        DESCRIPTION
                "Count of number of routes received have been
                 aggregated to the specific aggregate route currently
                 in route table for this interface."
        ::= { wfDvmrpCircuitEntry 28 }
 
    wfDvmrpCircuitAnnounceAggregatedRoutes OBJECT-TYPE 
        SYNTAX  INTEGER
        ACCESS  read-only
        STATUS  mandatory
        DESCRIPTION
                "Count of number of routes  have been aggregated to 
                 the specific aggregate route for advertisement currently
                 in route table for this interface."
        ::= { wfDvmrpCircuitEntry 29 }


    wfDvmrpTunnelEntryTable OBJECT-TYPE
        SYNTAX	SEQUENCE OF WfDvmrpTunnelEntry
        ACCESS	not-accessible
        STATUS	mandatory
        DESCRIPTION
                "Tunnel virtual interfaces"
        ::= { wfDvmrpGroup 3 }

    wfDvmrpTunnelEntry OBJECT-TYPE
        SYNTAX	WfDvmrpTunnelEntry
        ACCESS	not-accessible
        STATUS	mandatory
        DESCRIPTION
                "This object is used to specify the set of 'multicast tunnels',
                unicast pipes that are used to send IP multicast datagrams to
                remote network multicast routers via intermediate routers that
                may not support this style of IP multicasting. One instance of
                this object exists for every separate tunnel destination. The
                instance identifier is the IP address of the
                remote router neighbor and the local circuit number."
        INDEX	{ wfDvmrpTunnelCCT,
    		  wfDvmrpTunnelLocalRouterIpAddress,
    		  wfDvmrpTunnelRemoteRouterIpAddress }
        ::= { wfDvmrpTunnelEntryTable 1 }

    WfDvmrpTunnelEntry ::= SEQUENCE {
    	    wfDvmrpTunnelCreate
    		INTEGER,
    	    wfDvmrpTunnelEnable
    		INTEGER,
    	    wfDvmrpTunnelState
    		INTEGER,
    	    wfDvmrpTunnelCCT
    		INTEGER,
    	    wfDvmrpTunnelRemoteRouterIpAddress
    		IpAddress,
    	    wfDvmrpTunnelEncapsMode
    		INTEGER,
    	    wfDvmrpTunnelMetric
    		INTEGER,
    	    wfDvmrpTunnelThreshold
    		INTEGER,
    	    wfDvmrpTunnelInPkts
    		Counter,
    	    wfDvmrpTunnelOutPkts
    		Counter,
    	    wfDvmrpTunnelInRouteUpdates
    		Counter,
    	    wfDvmrpTunnelOutRouteUpdates
    		Counter,
    	    wfDvmrpTunnelInPktDiscards
    		Counter,
    	    wfDvmrpTunnelOutPktDiscards
    		Counter,
    	    wfDvmrpTunnelLocalRouterIpAddress
    		IpAddress,
    	    wfDvmrpTunnelFwdCacheSize
    		INTEGER,
    	    wfDvmrpTunnelFwdCacheTTL
    		INTEGER,
    	    wfDvmrpTunnelFwdCacheEntries
    		INTEGER,
    	    wfDvmrpTunnelInPrunePkts
    		Counter,
    	    wfDvmrpTunnelOutPrunePkts
    		Counter,
    	    wfDvmrpTunnelInGraftPkts
    		Counter,
    	    wfDvmrpTunnelOutGraftPkts
    		Counter,
    	    wfDvmrpTunnelInGraftAckPkts
    		Counter,
    	    wfDvmrpTunnelOutGraftAckPkts
    		Counter,
            wfDvmrpTunnelDefaultRouteSupply
            	INTEGER,
            wfDvmrpTunnelDefaultRouteListen
            	INTEGER,
            wfDvmrpTunnelCtrlMsgMode		
                INTEGER,
            wfDvmrpTunnelReportDependProbe
                INTEGER,
            wfDvmrpTunnelPruneLifeTime
                INTEGER,
            wfDvmrpTunnelAcceptAggregateRoutes
                INTEGER,
            wfDvmrpTunnelAnnounceAggregatedRoutes
                INTEGER
        }

    wfDvmrpTunnelCreate OBJECT-TYPE
        SYNTAX	INTEGER {
    		    created(1),
    		    deleted(2)
    		}
        ACCESS	read-write
        STATUS	mandatory
        DESCRIPTION
                "create/delete"
        DEFVAL	{ created }
        ::= { wfDvmrpTunnelEntry 1 }

    wfDvmrpTunnelEnable OBJECT-TYPE
        SYNTAX	INTEGER {
    		    enabled(1),
    		    disabled(2)
    		}
        ACCESS	read-write
        STATUS	mandatory
        DESCRIPTION
                "enable/disable this tunnel interface"
        DEFVAL	{ enabled }
        ::= { wfDvmrpTunnelEntry 2 }

    wfDvmrpTunnelState OBJECT-TYPE
        SYNTAX	INTEGER {
    		    up(1),
    		    down(2),
    		    init(3),
    		    invalid(4),
    		    notpres(5)
    		}
        ACCESS	read-only
        STATUS	mandatory
        DESCRIPTION
                "The current state of the DVMRP tunnel interface. Invalid
                indicates an error in processing the configuration record."
        DEFVAL	{ notpres }
        ::= { wfDvmrpTunnelEntry 3 }

    wfDvmrpTunnelCCT OBJECT-TYPE
        SYNTAX	INTEGER
        ACCESS	read-only
        STATUS	mandatory
        DESCRIPTION
                "The multicast circuit associated with this tunnel."
        ::= { wfDvmrpTunnelEntry 4 }

    wfDvmrpTunnelRemoteRouterIpAddress OBJECT-TYPE
        SYNTAX	IpAddress
        ACCESS	read-only
        STATUS	mandatory
        DESCRIPTION
                "(unicast) IP address of remote network router neighbor."
        ::= { wfDvmrpTunnelEntry 5 }

    wfDvmrpTunnelEncapsMode OBJECT-TYPE
        SYNTAX	INTEGER {
    		    ip-in-ip(1),
    		    lssr(2)
    		}
        ACCESS	read-write
        STATUS	mandatory
        DESCRIPTION
                "Will these tunnelled datagrams be encapsulated within an IP datagram, or will
                they be loosely encapsulated using the LSSR option (for the latter, refer to
                RFC 1075; this is needed for backward compatibility)"
        DEFVAL	{ ip-in-ip }
        ::= { wfDvmrpTunnelEntry 6 }

    wfDvmrpTunnelMetric OBJECT-TYPE
        SYNTAX	INTEGER(1..31)
        ACCESS	read-write
        STATUS	mandatory
        DESCRIPTION
                "Cost of using this tunnel"
        DEFVAL	{ 1 }
        ::= { wfDvmrpTunnelEntry 7 }

    wfDvmrpTunnelThreshold OBJECT-TYPE
        SYNTAX	INTEGER(1..254)
        ACCESS	read-write
        STATUS	mandatory
        DESCRIPTION
                "Threshold for forwarding through this tunnel; if TTL < threshold, the
                datagram is dropped."
        DEFVAL	{ 1 }
        ::= { wfDvmrpTunnelEntry 8 }

    wfDvmrpTunnelInPkts OBJECT-TYPE
        SYNTAX	Counter
        ACCESS	read-only
        STATUS	mandatory
        DESCRIPTION
                "Number of datagrams received on this interface"
        ::= { wfDvmrpTunnelEntry 9 }

    wfDvmrpTunnelOutPkts OBJECT-TYPE
        SYNTAX	Counter
        ACCESS	read-only
        STATUS	mandatory
        DESCRIPTION
                "Number of datagrams send on this interface"
        ::= { wfDvmrpTunnelEntry 10 }

    wfDvmrpTunnelInRouteUpdates OBJECT-TYPE
        SYNTAX	Counter
        ACCESS	read-only
        STATUS	mandatory
        DESCRIPTION
                "Number of DVMRP route update messages received"
        ::= { wfDvmrpTunnelEntry 11 }

    wfDvmrpTunnelOutRouteUpdates OBJECT-TYPE
        SYNTAX	Counter
        ACCESS	read-only
        STATUS	mandatory
        DESCRIPTION
                "Number of DVMRP route update messages sent"
        ::= { wfDvmrpTunnelEntry 12 }

    wfDvmrpTunnelInPktDiscards OBJECT-TYPE
        SYNTAX	Counter
        ACCESS	read-only
        STATUS	mandatory
        DESCRIPTION
                "Number of inbound datagrams discarded due to route not found or due to
                invalid inner address (dest address != multicast)"
        ::= { wfDvmrpTunnelEntry 13 }

    wfDvmrpTunnelOutPktDiscards OBJECT-TYPE
        SYNTAX	Counter
        ACCESS	read-only
        STATUS	mandatory
        DESCRIPTION
                "Number of outbound datagrams discarded due to route not found"
        ::= { wfDvmrpTunnelEntry 14 }

    wfDvmrpTunnelLocalRouterIpAddress OBJECT-TYPE
        SYNTAX	IpAddress
        ACCESS	read-only
        STATUS	mandatory
        DESCRIPTION
                "(unicast) IP address of local network router. To support multinet."
        ::= { wfDvmrpTunnelEntry 15 }

    wfDvmrpTunnelFwdCacheSize OBJECT-TYPE
        SYNTAX	INTEGER(32..512)
        ACCESS	read-write
        STATUS	mandatory
        DESCRIPTION
                "Maximum number of entries allowed in the Forwarding table
                at one time.  there is a Forwarding table per vif"
        DEFVAL	{ 32 }
        ::= { wfDvmrpTunnelEntry 16 }

    wfDvmrpTunnelFwdCacheTTL OBJECT-TYPE
        SYNTAX	INTEGER(0..86400)
        ACCESS	read-write
        STATUS	mandatory
        DESCRIPTION
                "The time_to_live for the Forwarding table entries in seconds ."
        DEFVAL	{ 7200 }
        ::= { wfDvmrpTunnelEntry 17 }

    wfDvmrpTunnelFwdCacheEntries OBJECT-TYPE
        SYNTAX	INTEGER
        ACCESS	read-only
        STATUS	mandatory
        DESCRIPTION
                "The most up to date number of entries in the forwarding cache"
        ::= { wfDvmrpTunnelEntry 18 }

    wfDvmrpTunnelInPrunePkts OBJECT-TYPE
        SYNTAX	Counter
        ACCESS	read-only
        STATUS	mandatory
        DESCRIPTION
                "Number of PRUNE datagrams received on this interface"
        ::= { wfDvmrpTunnelEntry 19 }

    wfDvmrpTunnelOutPrunePkts OBJECT-TYPE
        SYNTAX	Counter
        ACCESS	read-only
        STATUS	mandatory
        DESCRIPTION
                "Number of PRUNE datagrams send on this interface"
        ::= { wfDvmrpTunnelEntry 20 }

    wfDvmrpTunnelInGraftPkts OBJECT-TYPE
        SYNTAX	Counter
        ACCESS	read-only
        STATUS	mandatory
        DESCRIPTION
                "Number of GRAFT datagrams received on this interface"
        ::= { wfDvmrpTunnelEntry 21 }

    wfDvmrpTunnelOutGraftPkts OBJECT-TYPE
        SYNTAX	Counter
        ACCESS	read-only
        STATUS	mandatory
        DESCRIPTION
                "Number of GRAFT datagrams send on this interface"
        ::= { wfDvmrpTunnelEntry 22 }

    wfDvmrpTunnelInGraftAckPkts OBJECT-TYPE
        SYNTAX	Counter
        ACCESS	read-only
        STATUS	mandatory
        DESCRIPTION
                "Number of GRAFT_ACK datagrams received on this interface"
        ::= { wfDvmrpTunnelEntry 23 }

    wfDvmrpTunnelOutGraftAckPkts OBJECT-TYPE
        SYNTAX	Counter
        ACCESS	read-only
        STATUS	mandatory
        DESCRIPTION
                "Number of GRAFT_ACK datagrams send on this interface"
        ::= { wfDvmrpTunnelEntry 24 }

    wfDvmrpTunnelDefaultRouteSupply OBJECT-TYPE
        SYNTAX  INTEGER {
                enabled(1),
                disabled(2),
                generate(3)
                }
        ACCESS  read-write
        STATUS  mandatory
        DESCRIPTION
                "Send the default route, 0.0.0.0 on this interface"
        DEFVAL  { disabled }
        ::= { wfDvmrpTunnelEntry 25 }

    wfDvmrpTunnelDefaultRouteListen OBJECT-TYPE
        SYNTAX  INTEGER {
                enabled(1),
                disabled(2)
                }
        ACCESS  read-write
        STATUS  mandatory
        DESCRIPTION
                "Receive the default route, 0.0.0.0 on this interface"
        DEFVAL  { disabled }
        ::= { wfDvmrpTunnelEntry 26}

    wfDvmrpTunnelCtrlMsgMode OBJECT-TYPE
        SYNTAX  INTEGER {
                native(1),
                ip-in-ip(2)
                }
        ACCESS  read-write
        STATUS  mandatory
        DESCRIPTION
                "Dvmrp tunneling control messages encapsulated type. 
                 noencaps is the mode that control messages are sent in regular
                 igmp packets with ip protocol type set to IP_PROTOCOL_IGMP.
                 encaps is the mode that control messages are encapsed inside
                 ip packets with ip protocol type set to IP_PROTOCOL_IPINIP.
                 All DVMRP messages sent across tunnels will be encapsulated
                 in the same way as data packets in this mode."  
	DEFVAL  { native }
        ::= { wfDvmrpTunnelEntry 27}

    wfDvmrpTunnelReportDependProbe OBJECT-TYPE
        SYNTAX  INTEGER {
                enabled(1),
                disabled(2)
                }
        ACCESS  read-write
        STATUS  mandatory
        DESCRIPTION
                "This is to control accepting the route report. According to 
                 the protocol, dvmrp should send probe packet before sending
                 the route report packet to the neighbors. But some vendor
                 implementations do not send probes before sending reports.
                 Enable: only process the routes from the neighbor sending
                 probes. Disable: No Dependency (no restriction)."
        DEFVAL  { disabled }
        ::= { wfDvmrpTunnelEntry 28 }

    wfDvmrpTunnelPruneLifeTime OBJECT-TYPE
        SYNTAX  INTEGER(0..86400)
        ACCESS  read-write
        STATUS  mandatory
        DESCRIPTION
                "The life time of the prune message the router send 
                 to its neighbor in seconds."
        DEFVAL  { 7200 }
        ::= { wfDvmrpTunnelEntry 29 }


    wfDvmrpTunnelAcceptAggregateRoutes OBJECT-TYPE
        SYNTAX  INTEGER
        ACCESS  read-only
        STATUS  mandatory
        DESCRIPTION
                "Count of number of routes received have been
                 aggregated to the specific aggregate route currently
                 in route table for this interface."
        ::= { wfDvmrpTunnelEntry 30 }
 
    wfDvmrpTunnelAnnounceAggregatedRoutes OBJECT-TYPE 
        SYNTAX  INTEGER
        ACCESS  read-only
        STATUS  mandatory
        DESCRIPTION
                "Count of number of routes  have been aggregated to 
                 the specific aggregate route for advertisement currently
                 in route table for this interface."
        ::= { wfDvmrpTunnelEntry 31 }


    wfDvmrpRouteEntryTable OBJECT-TYPE
        SYNTAX	SEQUENCE OF WfDvmrpRouteEntry
        ACCESS	not-accessible
        STATUS	mandatory
        DESCRIPTION
                "MIB proxy: main DVMRP routing table"
        ::= { wfDvmrpGroup 4 }

    wfDvmrpRouteEntry OBJECT-TYPE
        SYNTAX	WfDvmrpRouteEntry
        ACCESS	not-accessible
        STATUS	mandatory
        DESCRIPTION
                "Supported by mib proxy. One entry exists for each active route."
        INDEX	{ wfDvmrpRouteSourceNetwork }
        ::= { wfDvmrpRouteEntryTable 1 }

    WfDvmrpRouteEntry ::= SEQUENCE {
    	    wfDvmrpRouteSourceNetwork
    		IpAddress,
    	    wfDvmrpRouteSourceMask
    		IpAddress,
    	    wfDvmrpRouteNextHopRouter
    		IpAddress,
    	    wfDvmrpRouteNextHopInterfaceCCT
    		INTEGER,
    	    wfDvmrpRouteNextHopInterfaceTunnelId
    		IpAddress,
    	    wfDvmrpRouteNextHopInterfaceLocalTunnelId
    		IpAddress,
    	    wfDvmrpRouteTimer
    		INTEGER,
    	    wfDvmrpRouteState
    		INTEGER,
    	    wfDvmrpRouteMetric
    		INTEGER,
    	    wfDvmrpRouteProtocol
    		INTEGER,
            wfDvmrpRouteType
                INTEGER,
            wfDvmrpRouteAggregatedType
                INTEGER
        }

    wfDvmrpRouteSourceNetwork OBJECT-TYPE
        SYNTAX	IpAddress
        ACCESS	read-only
        STATUS	mandatory
        DESCRIPTION
                "A source of multicast datagrams"
        ::= { wfDvmrpRouteEntry 1 }

    wfDvmrpRouteSourceMask OBJECT-TYPE
        SYNTAX	IpAddress
        ACCESS	read-only
        STATUS	mandatory
        DESCRIPTION
                "Mask for the specified source network"
        ::= { wfDvmrpRouteEntry 2 }

    wfDvmrpRouteNextHopRouter OBJECT-TYPE
        SYNTAX	IpAddress
        ACCESS	read-only
        STATUS	mandatory
        DESCRIPTION
                "Next hop multicast router to the specified source
                network; we consider this neighboring router to be on the
                shortest path to the source. Note that this neighboring router
                may be a tunnel endpoint."
        ::= { wfDvmrpRouteEntry 3 }

    wfDvmrpRouteNextHopInterfaceCCT OBJECT-TYPE
        SYNTAX	INTEGER
        ACCESS	read-only
        STATUS	mandatory
        DESCRIPTION
                "Next hop interface (CCT) to the specified source router; we
                consider this interface to be on the shortest path to the source."
        ::= { wfDvmrpRouteEntry 4 }

    wfDvmrpRouteNextHopInterfaceTunnelId OBJECT-TYPE
        SYNTAX	IpAddress
        ACCESS	read-only
        STATUS	mandatory
        DESCRIPTION
                "Next hop interface (tunnel id) to the specified source router; we
                consider this interface to be on the shortest path to the source."
        ::= { wfDvmrpRouteEntry 5 }

    wfDvmrpRouteNextHopInterfaceLocalTunnelId OBJECT-TYPE
        SYNTAX	IpAddress
        ACCESS	read-only
        STATUS	mandatory
        DESCRIPTION
                "Next hop interface (local tunnel id) to the specified source router; we
                consider this interface to be on the shortest path to the source."
        ::= { wfDvmrpRouteEntry 6 }

    wfDvmrpRouteTimer OBJECT-TYPE
        SYNTAX	INTEGER
        ACCESS	read-only
        STATUS	mandatory
        DESCRIPTION
                "route timer"
        ::= { wfDvmrpRouteEntry 7 }

    wfDvmrpRouteState OBJECT-TYPE
        SYNTAX	INTEGER
        ACCESS	read-only
        STATUS	mandatory
        DESCRIPTION
                "Set of flags indicating state of entry. Note that the
                router uses this field as a bit mask.
                          0x8000 Network is local to this router
                          0x4000 Route is being timed
                          0x2000 Route is garbaged"
        ::= { wfDvmrpRouteEntry 8 }

    wfDvmrpRouteMetric OBJECT-TYPE
        SYNTAX	INTEGER
        ACCESS	read-only
        STATUS	mandatory
        DESCRIPTION
                "current route metric"
        ::= { wfDvmrpRouteEntry 9 }

    wfDvmrpRouteProtocol OBJECT-TYPE
        SYNTAX	INTEGER
        ACCESS	read-only
        STATUS	mandatory
        DESCRIPTION
                "current route protocol dvmrp (2) or mospf (4) or internal (6) 
                 which is the route from unicast and  incoming interface no i
                 dvmrp configure, if dvmrp is configured then the protocol will
                 be set to 2, see wfIgmpRoutingProtocol"
        ::= { wfDvmrpRouteEntry 10 }

    wfDvmrpRouteType OBJECT-TYPE
        SYNTAX	INTEGER
        ACCESS	read-only
        STATUS	mandatory
        DESCRIPTION
                 "The orginal route source from. If it is from 
                  pure dvmrp route (0x0001)
                  unicast best route (0x0002) 
                  unciast route but has dvmrp interface (0x0003)
                  ospf(0x0004)
                  ospf best route (0x0006)
                  ospf ase route (0x0008)"
        ::= { wfDvmrpRouteEntry 11 }

    wfDvmrpRouteAggregatedType OBJECT-TYPE
        SYNTAX  INTEGER
        ACCESS  read-only
        STATUS  mandatory
        DESCRIPTION
                  "Route Aggregated types :
                   0 - normal route
                   1 - inbound aggregated route
                   2 - outbound aggregated route
                   4 - inbound aggregate route
                   8 - outbound aggregate route"
        ::= { wfDvmrpRouteEntry 12 }


    wfDvmrpRouteInterfaceEntryTable OBJECT-TYPE
        SYNTAX	SEQUENCE OF WfDvmrpRouteInterfaceEntry
        ACCESS	not-accessible
        STATUS	mandatory
        DESCRIPTION
                "MIB proxy: DVMRP VIF routing table"
        ::= { wfDvmrpGroup 5 }

    wfDvmrpRouteInterfaceEntry OBJECT-TYPE
        SYNTAX	WfDvmrpRouteInterfaceEntry
        ACCESS	not-accessible
        STATUS	mandatory
        DESCRIPTION
                "Supported by mib proxy. One entry exists for each virtual interface on
                an active route. It is associated with a route via the source network/
                net mask fields. The instance ID includes tunnel ID, which is 0 for
                non-tunnel interfaces."
        INDEX	{ wfDvmrpRouteInterfaceSourceNetwork,
    		  wfDvmrpRouteInterfaceParentCCT,
    		  wfDvmrpRouteInterfaceParentLocalTunnelId,
    		  wfDvmrpRouteInterfaceParentTunnelId }
        ::= { wfDvmrpRouteInterfaceEntryTable 1 }

    WfDvmrpRouteInterfaceEntry ::= SEQUENCE {
    	    wfDvmrpRouteInterfaceSourceNetwork
    		IpAddress,
    	    wfDvmrpRouteInterfaceSourceMask
    		IpAddress,
    	    wfDvmrpRouteInterfaceNextHopInterfaceCCT
    		INTEGER,
    	    wfDvmrpRouteInterfaceNextHopInterfaceLocalTunnelId
    		IpAddress,
    	    wfDvmrpRouteInterfaceNextHopInterfaceTunnelId
    		IpAddress,
    	    wfDvmrpRouteInterfaceState
    		INTEGER,
    	    wfDvmrpRouteInterfaceDominantRouter
    		IpAddress,
    	    wfDvmrpRouteInterfaceSubordinateRouter
    		IpAddress,
    	    wfDvmrpRouteInterfaceHoldDownTimer
    		INTEGER,
    	    wfDvmrpRouteInterfaceSPInDiscards
    		Counter,
    	    wfDvmrpRouteInterfaceSPOutDiscards
    		Counter,
    	    wfDvmrpRouteInterfaceThresholdOutDiscards
    		Counter,
    	    wfDvmrpRouteInterfaceInSuccessfulPkts
    		Counter,
    	    wfDvmrpRouteInterfaceOutSuccessfulPkts
    		Counter,
    	    wfDvmrpRouteInterfaceParentCCT
    		INTEGER,
    	    wfDvmrpRouteInterfaceParentLocalTunnelId
    		IpAddress,
    	    wfDvmrpRouteInterfaceParentTunnelId
    		IpAddress
        }

    wfDvmrpRouteInterfaceSourceNetwork OBJECT-TYPE
        SYNTAX	IpAddress
        ACCESS	read-only
        STATUS	mandatory
        DESCRIPTION
                "A source of multicast datagrams"
        ::= { wfDvmrpRouteInterfaceEntry 1 }

    wfDvmrpRouteInterfaceSourceMask OBJECT-TYPE
        SYNTAX	IpAddress
        ACCESS	read-only
        STATUS	mandatory
        DESCRIPTION
                "Mask for the specified source network"
        ::= { wfDvmrpRouteInterfaceEntry 2 }

    wfDvmrpRouteInterfaceNextHopInterfaceCCT OBJECT-TYPE
        SYNTAX	INTEGER
        ACCESS	read-only
        STATUS	mandatory
        DESCRIPTION
                "circuit number with which this route is associated"
        ::= { wfDvmrpRouteInterfaceEntry 3 }

    wfDvmrpRouteInterfaceNextHopInterfaceLocalTunnelId OBJECT-TYPE
        SYNTAX	IpAddress
        ACCESS	read-only
        STATUS	mandatory
        DESCRIPTION
                "Tunnel ID for tunnelled interfaces. This value is zero
                for non-tunnelled interfaces, otherwise it contains the local IP
                address of the tunnel."
        ::= { wfDvmrpRouteInterfaceEntry 4 }

    wfDvmrpRouteInterfaceNextHopInterfaceTunnelId OBJECT-TYPE
        SYNTAX	IpAddress
        ACCESS	read-only
        STATUS	mandatory
        DESCRIPTION
                "Tunnel ID for tunnelled interfaces. This value is zero
                for non-tunnelled interfaces, otherwise it contains the remote IP
                address of the tunnel."
        ::= { wfDvmrpRouteInterfaceEntry 5 }

    wfDvmrpRouteInterfaceState OBJECT-TYPE
        SYNTAX	INTEGER
        ACCESS	read-only
        STATUS	mandatory
        DESCRIPTION
                "state of interface for this route. Note that the router
                uses this field as a bit mask.
                          0x8000 - interface is leaf
                          0x4000 - interface is child
                          0x2000 - interface is in hold-down state
                          0x1000 - interface has loop neighbor for this route"
        ::= { wfDvmrpRouteInterfaceEntry 6 }

    wfDvmrpRouteInterfaceDominantRouter OBJECT-TYPE
        SYNTAX	IpAddress
        ACCESS	read-only
        STATUS	mandatory
        DESCRIPTION
                "dominant router address for virtual interface"
        ::= { wfDvmrpRouteInterfaceEntry 7 }

    wfDvmrpRouteInterfaceSubordinateRouter OBJECT-TYPE
        SYNTAX	IpAddress
        ACCESS	read-only
        STATUS	mandatory
        DESCRIPTION
                "subordinate router address for virtual interface"
        ::= { wfDvmrpRouteInterfaceEntry 8 }

    wfDvmrpRouteInterfaceHoldDownTimer OBJECT-TYPE
        SYNTAX	INTEGER
        ACCESS	read-only
        STATUS	mandatory
        DESCRIPTION
                "Current value of hold down timer, used to determine if
                interface is for leaf or non-leaf network. Non-leaf network means
                that a local network router considers us to be in the shortest
                path to the source (they have sent us a route update with metric
                >= infinity)."
        ::= { wfDvmrpRouteInterfaceEntry 9 }

    wfDvmrpRouteInterfaceSPInDiscards OBJECT-TYPE
        SYNTAX	Counter
        ACCESS	read-only
        STATUS  obsolete	
        DESCRIPTION
                "Count of inbound packets discarded because interface not on shortest path"
        ::= { wfDvmrpRouteInterfaceEntry 10 }

    wfDvmrpRouteInterfaceSPOutDiscards OBJECT-TYPE
        SYNTAX	Counter
        ACCESS	read-only
        STATUS  obsolete	
        DESCRIPTION
                "Count of outbound packets discarded because interface not on shortest path"
        ::= { wfDvmrpRouteInterfaceEntry 11 }

    wfDvmrpRouteInterfaceThresholdOutDiscards OBJECT-TYPE
        SYNTAX	Counter
        ACCESS	read-only
        STATUS  obsolete	
        DESCRIPTION
                "Count of outbound packets discarded because of threshold"
        ::= { wfDvmrpRouteInterfaceEntry 12 }

    wfDvmrpRouteInterfaceInSuccessfulPkts OBJECT-TYPE
        SYNTAX	Counter
        ACCESS	read-only
        STATUS  obsolete	
        DESCRIPTION
                "Count of inbound packets accepted for forwarding"
        ::= { wfDvmrpRouteInterfaceEntry 13 }

    wfDvmrpRouteInterfaceOutSuccessfulPkts OBJECT-TYPE
        SYNTAX	Counter
        ACCESS	read-only
        STATUS  obsolete	
        DESCRIPTION
                "Count of outbound packets accepted for forwarding"
        ::= { wfDvmrpRouteInterfaceEntry 14 }

    wfDvmrpRouteInterfaceParentCCT OBJECT-TYPE
        SYNTAX	INTEGER
        ACCESS	read-only
        STATUS	mandatory
        DESCRIPTION
                "circuit number with which this route is associated;parent VIF"
        ::= { wfDvmrpRouteInterfaceEntry 15 }

    wfDvmrpRouteInterfaceParentLocalTunnelId OBJECT-TYPE
        SYNTAX	IpAddress
        ACCESS	read-only
        STATUS	mandatory
        DESCRIPTION
                "Tunnel ID for tunnelled interfaces. This value is zero
                for non-tunnelled interfaces, otherwise it contains the local IP
                address of the tunnel; parent VIF."
        ::= { wfDvmrpRouteInterfaceEntry 16 }

    wfDvmrpRouteInterfaceParentTunnelId OBJECT-TYPE
        SYNTAX	IpAddress
        ACCESS	read-only
        STATUS	mandatory
        DESCRIPTION
                "Tunnel ID for tunnelled interfaces. This value is zero
                for non-tunnelled interfaces, otherwise it contains the remote IP
                address of the tunnel; parent VIF."
        ::= { wfDvmrpRouteInterfaceEntry 17 }

    wfDvmrpNeighboringRouterEntryTable OBJECT-TYPE
        SYNTAX	SEQUENCE OF WfDvmrpNeighboringRouterEntry
        ACCESS	not-accessible
        STATUS	mandatory
        DESCRIPTION
                "MIB proxy: DVMRP neighbor table"
        ::= { wfDvmrpGroup 6 }

    wfDvmrpNeighboringRouterEntry OBJECT-TYPE
        SYNTAX	WfDvmrpNeighboringRouterEntry
        ACCESS	not-accessible
        STATUS	mandatory
        DESCRIPTION
                "This entry is used to indentify the known neighboring routers for
                a circuit. This object will be indentified by circuit number,
                tunnel id (to identify local interface), and the IP address of the neighbor. "
        INDEX	{ wfDvmrpNeighboringRouterCCT,
    		  wfDvmrpNeighboringRouterLocalTunnelId,
    		  wfDvmrpNeighboringRouterTunnelId,
    		  wfDvmrpNeighboringRouterIpAddr }
        ::= { wfDvmrpNeighboringRouterEntryTable 1 }

    WfDvmrpNeighboringRouterEntry ::= SEQUENCE {
    	    wfDvmrpNeighboringRouterCCT
    		INTEGER,
    	    wfDvmrpNeighboringRouterLocalTunnelId
    		IpAddress,
    	    wfDvmrpNeighboringRouterTunnelId
    		IpAddress,
    	    wfDvmrpNeighboringRouterIpAddr
    		IpAddress,
    	    wfDvmrpNeighboringRouterState
    		INTEGER,
    	    wfDvmrpNeighboringRouterTimer
    		INTEGER,
    	    wfDvmrpNeighboringRouterGenId
    		INTEGER,
    	    wfDvmrpNeighboringRouterMajorVersion
    		INTEGER,
    	    wfDvmrpNeighboringRouterMinorVersion
    		INTEGER,
    	    wfDvmrpNeighboringRouterCapabilities
    		INTEGER
        }

    wfDvmrpNeighboringRouterCCT OBJECT-TYPE
        SYNTAX	INTEGER
        ACCESS	read-only
        STATUS	mandatory
        DESCRIPTION
                "Local circuit number"
        ::= { wfDvmrpNeighboringRouterEntry 1 }

    wfDvmrpNeighboringRouterLocalTunnelId OBJECT-TYPE
        SYNTAX	IpAddress
        ACCESS	read-only
        STATUS	mandatory
        DESCRIPTION
                "Tunnel Id for interface. This value is zero for non-
                tunnelled interfaces, otherwise it contains the IP address of the
                local tunnel endpoint."
        ::= { wfDvmrpNeighboringRouterEntry 2 }

    wfDvmrpNeighboringRouterTunnelId OBJECT-TYPE
        SYNTAX	IpAddress
        ACCESS	read-only
        STATUS	mandatory
        DESCRIPTION
                "Tunnel Id for interface. This value is zero for non-
                tunnelled interfaces, otherwise it contains the IP address of the
                remote tunnel endpoint."
        ::= { wfDvmrpNeighboringRouterEntry 3 }

    wfDvmrpNeighboringRouterIpAddr OBJECT-TYPE
        SYNTAX	IpAddress
        ACCESS	read-only
        STATUS	mandatory
        DESCRIPTION
                "IP address of neighboring router"
        ::= { wfDvmrpNeighboringRouterEntry 4 }

    wfDvmrpNeighboringRouterState OBJECT-TYPE
        SYNTAX	INTEGER
        ACCESS	read-only
        STATUS	mandatory
        DESCRIPTION
                "State of neighbor. The router uses this as a bit mask.
                0x8000 - Neighbor is being timed"
        ::= { wfDvmrpNeighboringRouterEntry 5 }

    wfDvmrpNeighboringRouterTimer OBJECT-TYPE
        SYNTAX	INTEGER
        ACCESS	read-only
        STATUS	mandatory
        DESCRIPTION
                "Current value of neighbor timer"
        ::= { wfDvmrpNeighboringRouterEntry 6 }

    wfDvmrpNeighboringRouterGenId OBJECT-TYPE
        SYNTAX	INTEGER
        ACCESS	read-only
        STATUS	mandatory
        DESCRIPTION
                "The neighboring router's generation identifier."
        ::= { wfDvmrpNeighboringRouterEntry 7 }

    wfDvmrpNeighboringRouterMajorVersion OBJECT-TYPE
        SYNTAX	INTEGER(0..255)
        ACCESS	read-only
        STATUS	mandatory
        DESCRIPTION
                "The neighboring router's major DVMRP version number."
        ::= { wfDvmrpNeighboringRouterEntry 8 }

    wfDvmrpNeighboringRouterMinorVersion OBJECT-TYPE
        SYNTAX	INTEGER(0..255)
        ACCESS	read-only
        STATUS	mandatory
        DESCRIPTION
                "The neighboring router's minor DVMRP version number."
        ::= { wfDvmrpNeighboringRouterEntry 9 }

    wfDvmrpNeighboringRouterCapabilities OBJECT-TYPE
        SYNTAX	INTEGER
        ACCESS	read-only
        STATUS	mandatory
        DESCRIPTION
                "This object describes the neighboring router's capabilities.
                 The leaf bit indicates that the neighbor has only one 
                 interface with neighbors.  The prune bit indicates that the
                 neighbor supports pruning.  The generationID bit indicates
                 that the neighbor sends its generationID in Probe messages.
                 The mtrace bit indicates that the neighbor can handle
                 mtrace requests."
        ::= { wfDvmrpNeighboringRouterEntry 10 }


    END  -- Wellfleet-DVMRP-MIB
