-- This is the MIB for TAVVE Software Co.
-- Version 1.2

-- Copyright 1997-2000 Tavve Software Co.  All Rights Reserved.
-- Reproduction of this document is authorized on
-- condition that this copyright notice is included.
-- This MIB document embodies Tavve Software Co.'s proprietary
-- intellectual property.  Tavve Software Co. retains all
-- title and ownership in this MIB, including any
-- revisions.
--
-- It is Tavve Software Co.'s intent to encourage the widespread
-- use of this MIB in connection with the management of
-- Tavve Software Co. products. Tavve Software Co. grants vendors,
-- end-users, and other interested parties a non-exclusive
-- license to use this MIB in connection with the
-- management of Tavve Software Co. products.
--
-- This MIB document is supplied "AS IS," and Tavve Software Co.
-- makes no warranty, either express or implied, as to the
-- use operation, condition, or performance of the MIB.

TAVVE-MIB DEFINITIONS ::= BEGIN

           IMPORTS
                   enterprises, IpAddress, Counter, TimeTicks
                       FROM RFC1155-SMI
                   DisplayString
                       FROM RFC1213-MIB
                   MacAddress
                       FROM RFC1286-MIB
                   TRAP-TYPE
                       FROM RFC-1215
                   OBJECT-TYPE
                           FROM RFC-1212;

	tavve		OBJECT IDENTIFIER ::= { enterprises 2668 }
	traps		OBJECT IDENTIFIER ::= { tavve 1 }
	agents		OBJECT IDENTIFIER ::= { tavve 2 }
	products	OBJECT IDENTIFIER ::= { traps 1 }
	custom	OBJECT IDENTIFIER ::= { traps 2 }
	eventWatch	OBJECT IDENTIFIER ::= { products 1 }
	tcpdmon	OBJECT IDENTIFIER ::= { products 2 }
	ciscotrap	OBJECT IDENTIFIER ::= { products 3 }
	wwwmon	OBJECT IDENTIFIER ::= { products 4 }
	agentmon	OBJECT IDENTIFIER ::= { products 5 }
	remote		OBJECT IDENTIFIER ::= { products 6 }
	global		OBJECT IDENTIFIER ::= { products 7 }
	portmon	OBJECT IDENTIFIER ::= { products 8 }
	syslogtrap	OBJECT IDENTIFIER ::= { products 9 }
	atmmon		OBJECT IDENTIFIER ::= { products 10 }
	xmon		OBJECT IDENTIFIER ::= { products 12 }

--
-- PRODUCTS
--

----------------------------------------------
----------------------------------------------
-- 
-- EventWatch
-- 
----------------------------------------------
----------------------------------------------

--
-- Variables used by traps
--

tscEwSourceNode OBJECT-TYPE
	SYNTAX  DisplayString
	ACCESS  read-only
	STATUS  optional
	DESCRIPTION
		"The address of the node that was originally reported 
		down."
	::= { eventWatch 1 }

tscEwFaultAddr OBJECT-TYPE
	SYNTAX  DisplayString
	ACCESS  read-only
	STATUS  optional
	DESCRIPTION
		"The IP address of the node that was is the root cause."
	::= { eventWatch 2 }

tscEwFaultTimes OBJECT-TYPE
	SYNTAX  DisplayString
	ACCESS  read-only
	STATUS  optional
	DESCRIPTION
		"A string with two time stamps in it:
			1) the current time
			2) the time the original failure was reported
		The time is printed in Unix time (seconds since Jan 1, 1970)."
	::= { eventWatch 3 }

tscEwSourceAddr OBJECT-TYPE
	SYNTAX  DisplayString
	ACCESS  read-only
	STATUS  optional
	DESCRIPTION
		"The address of the node being reported."
	::= { eventWatch 6 }

tscEwGroupName OBJECT-TYPE
	SYNTAX  DisplayString
	ACCESS  read-only
	STATUS  optional
	DESCRIPTION
		"The group name (as defined to EventWatch to which
		this node belongs."
	::= { eventWatch 7 }

tscEwSourceName OBJECT-TYPE
	SYNTAX  DisplayString
	ACCESS  read-only
	STATUS  optional
	DESCRIPTION
		"The name of the node being reported."
	::= { eventWatch 8 }

tscEwSourceProtocol OBJECT-TYPE
	SYNTAX  DisplayString
	ACCESS  read-only
	STATUS  optional
	DESCRIPTION
		"The protocol of the node being reported, e.g. IP."
	::= { eventWatch 9 }

tscEwFaultName OBJECT-TYPE
	SYNTAX  DisplayString
	ACCESS  read-only
	STATUS  optional
	DESCRIPTION
		"The name of the fault being reported."
	::= { eventWatch 10 }

tscEwFaultProtocol OBJECT-TYPE
	SYNTAX  DisplayString
	ACCESS  read-only
	STATUS  optional
	DESCRIPTION
		"The protocol of the fault being reported, e.g. IP."
	::= { eventWatch 11 }

tscEwUserThreshold OBJECT-TYPE
	SYNTAX  INTEGER
	ACCESS  read-only
	STATUS  optional
	DESCRIPTION
		"The value of the user defined threshold."
	::= { eventWatch 12 }

tscEwSlaValue OBJECT-TYPE
	SYNTAX  INTEGER
	ACCESS  read-only
	STATUS  optional
	DESCRIPTION
		"The value of the group availability."
	::= { eventWatch 13 }

tscEwReportHost OBJECT-TYPE
	SYNTAX  DisplayString
	ACCESS  read-only
	STATUS  optional
	DESCRIPTION
		"The name of the EventWatch host reporting the problem.
		Make sure all the Remote box names are resolvable."
	::= { eventWatch 14 }

tscEwDownTime OBJECT-TYPE
	SYNTAX  INTEGER
	ACCESS  read-only
	STATUS  optional
	DESCRIPTION
		"The amount of time (in seconds) the device in question was down."
	::= { eventWatch 15 }

tscEwEventTime OBJECT-TYPE
	SYNTAX  INTEGER
	ACCESS  read-only
	STATUS  optional
	DESCRIPTION
		"The time (Unix time) when this event occurred."
	::= { eventWatch 16 }

tscEwDescr OBJECT-TYPE
	SYNTAX  DisplayString
	ACCESS  read-only
	STATUS  optional
	DESCRIPTION
		"The textual description of the entity."
	::= { eventWatch 17 }

--
-- Trap Definitions
--

tscEwSourceDown TRAP-TYPE
	ENTERPRISE  eventWatch
	VARIABLES   { 
		tscEwFaultAddr,
		tscEwFaultName,
		tscEwFaultProtocol,
		tscEwGroupName,
		tscEwReportHost,
		tscEwEventTime,
		tscEwDescr
		}
	DESCRIPTION
		"Device is verified down.

		This trap is sent after EventWatch verifies
		a device is down and it is not correlated to a problem
		in the network.

		This trap configured with source-down-trap.

		The bound variables contain the address of the fault,
		its name, and its protocol."
		--#SUMMARY "Root cause failure: %s %s (%s) %s"
		--#ARGUMENTS { 2, 1, 0, 6 }
		--#SEVERITY CRITICAL
		--#STATE NONOPERATIONAL
		--#SLOTMAP origin $V1
		--#SLOTMAP hostname $V2
		--#SLOTMAP protocol $V3
		--#SLOTMAP reporthost $V5
	::= 1

tscEwInferredDown TRAP-TYPE
	ENTERPRISE  eventWatch
	VARIABLES   {
		tscEwFaultAddr,
		tscEwSourceNode,
		tscEwFaultName,
		tscEwFaultProtocol,
		tscEwSourceName,
		tscEwSourceProtocol,
		tscEwGroupName,
		tscEwReportHost,
		tscEwEventTime
		}
	DESCRIPTION
		"Device is verified down.

		This trap is sent after EventWatch verifies
		a device is down and it is not correlated to a problem
		in the network.

		This trap configured with behind-down-trap."
		--#SUMMARY "%s %s (%s) is unreachable because %s %s (%s) is down."
		--#ARGUMENTS { 5, 4, 1, 3, 2, 0 }
		--#SEVERITY WARNING
		--#SLOTMAP origin $V1
		--#SLOTMAP hostname $V3
		--#SLOTMAP protocol $V4
		--#SLOTMAP source $V2
		--#SLOTMAP reporthost $V8
	::= 2

tscEwSourceUp TRAP-TYPE
	ENTERPRISE  eventWatch
	VARIABLES   { 
		tscEwFaultAddr,
		tscEwFaultName,
		tscEwFaultProtocol,
		tscEwGroupName,
		tscEwReportHost,
		tscEwEventTime
		}
	DESCRIPTION
		"Device is back up.

		This trap complements trap 1 to report that the source
		node is back up.

		This trap configured with source-up-trap."
		--#SUMMARY "Root cause failure restored: %s %s (%s)"
		--#ARGUMENTS { 2, 1, 0 }
		--#SEVERITY INFORMATIONAL
		--#SLOTMAP origin $V1
		--#SLOTMAP hostname $V2
		--#SLOTMAP protocol $V3
		--#SLOTMAP reporthost $V5
	::= 3

tscEwInferredUp TRAP-TYPE
	ENTERPRISE  eventWatch
	VARIABLES   {
		tscEwFaultAddr,
		tscEwSourceNode,
		tscEwFaultName,
		tscEwFaultProtocol,
		tscEwSourceName,
		tscEwSourceProtocol,
		tscEwGroupName,
		tscEwReportHost,
		tscEwEventTime
		}
	DESCRIPTION
		"Device is verified up.

		This trap complements trap 2 to report that the root cause
		node is back up.

		This trap configured with behind-up-trap."
		--#SUMMARY "%s %s (%s) is reachable again because %s %s (%s) is up."
		--#ARGUMENTS { 5, 4, 1, 3, 2, 0 }
		--#SEVERITY INFORMATIONAL
		--#SLOTMAP origin $V1
		--#SLOTMAP hostname $V3
		--#SLOTMAP protocol $V4
		--#SLOTMAP source $V2
		--#SLOTMAP reporthost $V8
	::= 4

tscEwNodeDown TRAP-TYPE
	ENTERPRISE  eventWatch
	VARIABLES   {
		tscEwSourceAddr,
		tscEwGroupName,
		tscEwSourceName,
		tscEwSourceProtocol,
		tscEwReportHost,
		tscEwEventTime
		}
	DESCRIPTION
		"Device is verified down.

		This trap is issued when EventWatch is reporting the 
		node down.  Note this is the root cause node.

		This trap configured with level/trap."
		--#SUMMARY "%s verified down.  Group: %s."
		--#ARGUMENTS { 0, 1 }
		--#SEVERITY INFORMATIONAL
		--#SLOTMAP origin $V1
		--#SLOTMAP hostname $V3
		--#SLOTMAP protocol $V4
		--#SLOTMAP groupname $V2
		--#SLOTMAP reporthost $V5
	::= 5

tscEwNodeUp TRAP-TYPE
	ENTERPRISE  eventWatch
	VARIABLES   {
		tscEwSourceAddr,
		tscEwGroupName,
		tscEwSourceName,
		tscEwSourceProtocol,
		tscEwReportHost,
		tscEwEventTime
		}
	DESCRIPTION
		"Device is back up after being verified down.

		This trap configured with level/trap."
		--#SUMMARY "%s reported back up.  Group: %s."
		--#ARGUMENTS { 0, 1 }
		--#SEVERITY INFORMATIONAL
		--#SLOTMAP origin $V1
		--#SLOTMAP hostname $V3
		--#SLOTMAP protocol $V4
		--#SLOTMAP groupname $V2
		--#SLOTMAP reporthost $V5
	::= 6

tscEwSlaThres TRAP-TYPE
	ENTERPRISE  eventWatch
	VARIABLES   { tscEwGroupName,
		tscEwUserThreshold,
		tscEwSlaValue
		}
	DESCRIPTION
		"The availability of this group or host fell below the user configured threshold.

		This trap configured with level/trap."
		--#SUMMARY "%s fell below configured %s availability threshold with availability of %s."
		--#ARGUMENTS { 0, 1 , 2 }
		--#SEVERITY INFORMATIONAL
		--#SLOTMAP groupname $V1
		--#SLOTMAP userthreshold $V2
		--#SLOTMAP slavalue $V3
	::= 7

tscEwRemoteSourceDown TRAP-TYPE
	ENTERPRISE  eventWatch
	VARIABLES   { 
		tscEwFaultAddr,
		tscEwFaultName,
		tscEwFaultProtocol,
		tscEwGroupName,
		tscEwReportHost,
		tscEwEventTime
		}
	DESCRIPTION
		"Device is verified down by Remote.

		This trap is sent after EventWatch on Remote verifies
		a device is down and it is not correlated to a problem
		in the network.

		This trap configured with source-down-trap.

		The bound variables contain the address of the fault,
		its name, and its protocol."
		--#SUMMARY "Root cause failure: %s %s (%s)"
		--#ARGUMENTS { 2, 1, 0 }
		--#SEVERITY CRITICAL
		--#STATE NONOPERATIONAL
		--#SLOTMAP origin $V1
		--#SLOTMAP hostname $V2
		--#SLOTMAP protocol $V3
		--#SLOTMAP reporthost $V5
	::= 11

tscEwRemoteInferredDown TRAP-TYPE
	ENTERPRISE  eventWatch
	VARIABLES   { 
		tscEwFaultAddr,
		tscEwSourceNode,
		tscEwFaultName,
		tscEwFaultProtocol,
		tscEwSourceName,
		tscEwSourceProtocol,
		tscEwGroupName,
		tscEwReportHost,
		tscEwEventTime
		}
	DESCRIPTION
		"Device is verified down by Remote.

		This trap is sent after EventWatch on Remote verifies
		a device is down and it is not correlated to a problem
		in the network.

		This trap configured with behind-down-trap."
		--#SUMMARY "%s %s (%s) is unreachable because %s %s (%s) is down."
		--#ARGUMENTS { 5, 4, 1, 3, 2, 0 }
		--#SEVERITY WARNING
		--#SLOTMAP origin $V1
		--#SLOTMAP hostname $V3
		--#SLOTMAP protocol $V4
		--#SLOTMAP source $V2
		--#SLOTMAP reporthost $V8
	::= 12

tscEwRemoteSourceUp TRAP-TYPE
	ENTERPRISE  eventWatch
	VARIABLES   { 
		tscEwFaultAddr,
		tscEwFaultName,
		tscEwFaultProtocol,
		tscEwGroupName,
		tscEwReportHost,
		tscEwDownTime,
		tscEwEventTime
		}
	DESCRIPTION
		"Device is back up, reported by Remote.

		This trap complements trap 1 to report that the source
		node is back up on Remote.

		This trap configured with source-up-trap."
		--#SUMMARY "Root cause failure restored: %s %s (%s)"
		--#ARGUMENTS { 2, 1, 0 }
		--#SEVERITY INFORMATIONAL
		--#SLOTMAP origin $V1
		--#SLOTMAP hostname $V2
		--#SLOTMAP protocol $V3
		--#SLOTMAP reporthost $V5
	::= 13

tscEwRemoteInferredUp TRAP-TYPE
	ENTERPRISE  eventWatch
	VARIABLES   { 
		tscEwFaultAddr,
		tscEwSourceNode,
		tscEwFaultName,
		tscEwFaultProtocol,
		tscEwSourceName,
		tscEwSourceProtocol,
		tscEwGroupName,
		tscEwReportHost,
		tscEwDownTime,
		tscEwEventTime
		}
	DESCRIPTION
		"Device is verified up by Remote.

		This trap complements trap 2 to report that the root cause
		node is back up on Remote.

		This trap configured with behind-up-trap."
		--#SUMMARY "%s %s (%s) is reachable again because %s %s (%s) is up."
		--#ARGUMENTS { 5, 4, 1, 3, 2, 0 }
		--#SEVERITY INFORMATIONAL
		--#SLOTMAP origin $V1
		--#SLOTMAP hostname $V3
		--#SLOTMAP protocol $V4
		--#SLOTMAP source $V2
		--#SLOTMAP reporthost $V8
	::= 14

tscEwRemoteNodeDown TRAP-TYPE
	ENTERPRISE  eventWatch
	VARIABLES   { 
		tscEwSourceAddr,
		tscEwGroupName,
		tscEwSourceName,
		tscEwSourceProtocol,
		tscEwReportHost,
		tscEwEventTime
		}
	DESCRIPTION
		"Device is verified down by Remote.

		This trap is issued when EventWatch is reporting the 
		node down.  Note this is the root cause node.

		This trap configured with level/trap."
		--#SUMMARY "%s verified down.  Group: %s."
		--#ARGUMENTS { 0, 1 }
		--#SEVERITY INFORMATIONAL
		--#SLOTMAP origin $V1
		--#SLOTMAP hostname $V3
		--#SLOTMAP protocol $V4
		--#SLOTMAP groupname $V2
		--#SLOTMAP reporthost $V5
	::= 15

tscEwRemoteNodeUp TRAP-TYPE
	ENTERPRISE  eventWatch
	VARIABLES   { 
		tscEwSourceAddr,
		tscEwGroupName,
		tscEwSourceName,
		tscEwSourceProtocol,
		tscEwReportHost,
		tscEwEventTime
		}
	DESCRIPTION
		"Device is back up after being verified down by Remote.

		This trap configured with level/trap."
		--#SUMMARY "%s reported back up.  Group: %s."
		--#ARGUMENTS { 0, 1 }
		--#SEVERITY INFORMATIONAL
		--#SLOTMAP origin $V1
		--#SLOTMAP hostname $V3
		--#SLOTMAP protocol $V4
		--#SLOTMAP groupname $V2
		--#SLOTMAP reporthost $V5
	::= 16

tscEwTestTrap TRAP-TYPE
        ENTERPRISE  eventWatch
        VARIABLES   {
                tscEwEventTime,
                tscEwGroupName,
                tscEwSourceProtocol,
                tscEwSourceName,
                tscEwSourceAddr,
                tscEwDescr
                }
        DESCRIPTION
                "EventWatch Test Notification. 

                This trap is sent to EventWatch.
                It is used to verify that EventWatch can receive and send traps.

                This trap configured with test-trap. 

                The bound variables contain the address of the device,
                its name, and its protocol."
                --#SUMMARY "Test trap only. Group: %s"
                --#ARGUMENTS { 2, 3, 4, 5 }
                --#SEVERITY INFORMAIONAL
                --#STATE UNKNOWN
                --#SLOTMAP groupname $V2
                --#SLOTMAP protocol $V3
                --#SLOTMAP hostname $V4
                --#SLOTMAP origin $V5
        ::= 91

tscEwTestTrapRecv TRAP-TYPE
        ENTERPRISE  eventWatch
        VARIABLES   {
                tscEwGroupName,
                tscEwSourceProtocol,
                tscEwSourceName,
                tscEwSourceAddr,
                tscEwEventTime,
                tscEwDescr
                }
        DESCRIPTION
                "EventWatch Test Notification.

                This trap is sent after EventWatch receives it.
                The status of the device reported is not actually verified.

                This trap configured with test-trap.

                The bound variables contain the address of the device,
                its name, and its protocol."
                --#SUMMARY "Test trap only. Group: %s"
                --#ARGUMENTS { 1, 2, 3, 4 }
                --#SEVERITY INFORMAIONAL
                --#STATE UNKNOWN
                --#SLOTMAP groupname $V1
                --#SLOTMAP protocol $V2
                --#SLOTMAP hostname $V3
                --#SLOTMAP origin $V4
        ::= 92

----------------------------------------------
----------------------------------------------
--
-- TcpdMon
--
----------------------------------------------
----------------------------------------------

--
-- Variables used by traps
--
tscTcpSourceNode OBJECT-TYPE
	SYNTAX  DisplayString
	ACCESS  read-only
	STATUS  optional
	DESCRIPTION
		"The address of the node on which the TCP reported."
	::= { tcpdmon 1 }

tscTCPPortName OBJECT-TYPE
	SYNTAX  DisplayString
	ACCESS  read-only
	STATUS  optional
	DESCRIPTION
		"The Service Name of this particular port."
	::= { tcpdmon 2 }

tscTCPPortNumber OBJECT-TYPE
	SYNTAX  DisplayString
	ACCESS  read-only
	STATUS  optional
	DESCRIPTION
                "The Service Number of this particular port."
	::= { tcpdmon 3 }

tscTCPTime OBJECT-TYPE
	SYNTAX  DisplayString
	ACCESS  read-only
	STATUS  optional
	DESCRIPTION
		"The time at which the event occurred."
	::= { tcpdmon 4 }

--
-- Trap Definitions
--

----------------------------------------------
----------------------------------------------
--
-- CiscoTrap
--
----------------------------------------------
----------------------------------------------

--
-- Variables used by traps
--

tscCtLogMessage OBJECT-TYPE
	SYNTAX  DisplayString
	ACCESS  read-only
	STATUS  optional
	DESCRIPTION
		"The message from log file suitable for logging.
		Format is: 
			month day, time : facility-severity-mnemonic: message"
	::= { ciscotrap 1 }

tscCtFacility OBJECT-TYPE
	SYNTAX  DisplayString
	ACCESS  read-only
	STATUS  optional
	DESCRIPTION
		"The Cisco facility from log message, e.g. IP, PIX."
	::= { ciscotrap 2 }

tscCtSeverity OBJECT-TYPE
	SYNTAX  DisplayString
	ACCESS  read-only
	STATUS  optional
	DESCRIPTION
		"The Cisco severity from log message, e.g. 0, 1, 2, 3, 4, 5, 6, 7, 8."
	::= { ciscotrap 3 }

tscCtMnemonic OBJECT-TYPE
	SYNTAX  DisplayString
	ACCESS  read-only
	STATUS  optional
	DESCRIPTION
		"The Cisco Mnemonic from log message, e.g. DUPADDR."
	::= { ciscotrap 4 }

tscCtMessage OBJECT-TYPE
	SYNTAX  DisplayString
	ACCESS  read-only
	STATUS  optional
	DESCRIPTION
		"The Cisco message from log message (stripped of time
		stamp, facility, severity, mnemonic"
	::= { ciscotrap 5 }

--
-- Trap Definitions
--

tscCtSeverity0 TRAP-TYPE
	ENTERPRISE  ciscotrap
	VARIABLES   { 
		tscCtLogMessage,
		tscCtFacility,
		tscCtSeverity,
		tscCtMnemonic,
		tscCtMessage
		}
	DESCRIPTION
		"Cisco device reporting a severity 0 event."
		--#SUMMARY "%s"
		--#ARGUMENTS { 0 }
		--#SEVERITY CRITICAL
		--#SLOTMAP origin $A
		--#SLOTMAP facility $V2
		--#SLOTMAP severity $V3
		--#SLOTMAP mnemonic $V4
		--#SLOTMAP message  $V5
	::= 10

tscCtSeverity1 TRAP-TYPE
	ENTERPRISE  ciscotrap
	VARIABLES   { 
		tscCtLogMessage,
		tscCtFacility,
		tscCtSeverity,
		tscCtMnemonic,
		tscCtMessage
		}
	DESCRIPTION
		"Cisco device reporting a severity 1 event."
		--#SUMMARY "%s"
		--#ARGUMENTS { 0 }
		--#SEVERITY CRITICAL
		--#SLOTMAP origin $A
		--#SLOTMAP facility $V2
		--#SLOTMAP severity $V3
		--#SLOTMAP mnemonic $V4
		--#SLOTMAP message  $V5
	::= 11

tscCtSeverity2 TRAP-TYPE
	ENTERPRISE  ciscotrap
	VARIABLES   { 
		tscCtLogMessage,
		tscCtFacility,
		tscCtSeverity,
		tscCtMnemonic,
		tscCtMessage
		}
	DESCRIPTION
		"Cisco device reporting a severity 2 event."
		--#SUMMARY "%s"
		--#ARGUMENTS { 0 }
		--#SEVERITY CRITICAL
		--#SLOTMAP origin $A
		--#SLOTMAP facility $V2
		--#SLOTMAP severity $V3
		--#SLOTMAP mnemonic $V4
		--#SLOTMAP message  $V5
	::= 12

tscCtSeverity3 TRAP-TYPE
	ENTERPRISE  ciscotrap
	VARIABLES   { 
		tscCtLogMessage,
		tscCtFacility,
		tscCtSeverity,
		tscCtMnemonic,
		tscCtMessage
		}
	DESCRIPTION
		"Cisco device reporting a severity 3 event."
		--#SUMMARY "%s"
		--#ARGUMENTS { 0 }
		--#SEVERITY CRITICAL
		--#SLOTMAP origin $A
		--#SLOTMAP facility $V2
		--#SLOTMAP severity $V3
		--#SLOTMAP mnemonic $V4
		--#SLOTMAP message  $V5
	::= 13

tscCtSeverity4 TRAP-TYPE
	ENTERPRISE  ciscotrap
	VARIABLES   { 
		tscCtLogMessage,
		tscCtFacility,
		tscCtSeverity,
		tscCtMnemonic,
		tscCtMessage
		}
	DESCRIPTION
		"Cisco device reporting a severity 4 event."
		--#SUMMARY "%s"
		--#ARGUMENTS { 0 }
		--#SEVERITY CRITICAL
		--#SLOTMAP origin $A
		--#SLOTMAP facility $V2
		--#SLOTMAP severity $V3
		--#SLOTMAP mnemonic $V4
		--#SLOTMAP message  $V5
	::= 14

tscCtSeverity5 TRAP-TYPE
	ENTERPRISE  ciscotrap
	VARIABLES   { 
		tscCtLogMessage,
		tscCtFacility,
		tscCtSeverity,
		tscCtMnemonic,
		tscCtMessage
		}
	DESCRIPTION
		"Cisco device reporting a severity 5 event."
		--#SUMMARY "%s"
		--#ARGUMENTS { 0 }
		--#SEVERITY CRITICAL
		--#SLOTMAP origin $A
		--#SLOTMAP facility $V2
		--#SLOTMAP severity $V3
		--#SLOTMAP mnemonic $V4
		--#SLOTMAP message  $V5
	::= 15

tscCtSeverity6 TRAP-TYPE
	ENTERPRISE  ciscotrap
	VARIABLES   { 
		tscCtLogMessage,
		tscCtFacility,
		tscCtSeverity,
		tscCtMnemonic,
		tscCtMessage
		}
	DESCRIPTION
		"Cisco device reporting a severity 6 event."
		--#SUMMARY "%s"
		--#ARGUMENTS { 0 }
		--#SEVERITY CRITICAL
		--#SLOTMAP origin $A
		--#SLOTMAP facility $V2
		--#SLOTMAP severity $V3
		--#SLOTMAP mnemonic $V4
		--#SLOTMAP message  $V5
	::= 16

tscCtSeverity7 TRAP-TYPE
	ENTERPRISE  ciscotrap
	VARIABLES   { 
		tscCtLogMessage,
		tscCtFacility,
		tscCtSeverity,
		tscCtMnemonic,
		tscCtMessage
		}
	DESCRIPTION
		"Cisco device reporting a severity 7 event."
		--#SUMMARY "%s"
		--#ARGUMENTS { 0 }
		--#SEVERITY CRITICAL
		--#SLOTMAP origin $A
		--#SLOTMAP facility $V2
		--#SLOTMAP severity $V3
		--#SLOTMAP mnemonic $V4
		--#SLOTMAP message  $V5
	::= 17

tscCtSeverity8 TRAP-TYPE
	ENTERPRISE  ciscotrap
	VARIABLES   { 
		tscCtLogMessage,
		tscCtFacility,
		tscCtSeverity,
		tscCtMnemonic,
		tscCtMessage
		}
	DESCRIPTION
		"Cisco device reporting a severity 8 event."
		--#SUMMARY "%s"
		--#ARGUMENTS { 0 }
		--#SEVERITY CRITICAL
		--#SLOTMAP origin $A
		--#SLOTMAP facility $V2
		--#SLOTMAP severity $V3
		--#SLOTMAP mnemonic $V4
		--#SLOTMAP message  $V5
	::= 18

----------------------------------------------
----------------------------------------------
--
-- WwwMon
--
----------------------------------------------
----------------------------------------------

--
-- Variables used by traps
--

wwwmonServerName OBJECT-TYPE
	SYNTAX  DisplayString
	ACCESS  read-only
	STATUS  optional
	DESCRIPTION
		"This is the web server's hostname"
	::= { wwwmon 1 }

wwwmonServerPort OBJECT-TYPE
	SYNTAX  INTEGER
	ACCESS  read-only
	STATUS  optional
	DESCRIPTION
		"This is the web server port number."
	::= { wwwmon 2 }

wwwmonServerURL OBJECT-TYPE
	SYNTAX  DisplayString
	ACCESS  read-only
	STATUS  optional
	DESCRIPTION
		"This is the URL passed to the web server"
	::= { wwwmon 3 }

wwwmonServerStatus OBJECT-TYPE
	SYNTAX  DisplayString
	ACCESS  read-only
	STATUS  optional
	DESCRIPTION
		"This is the web server's status for the HEAD request."
	::= { wwwmon 4 }

--
-- Trap Definitions
--

wwwmonUp TRAP-TYPE
	ENTERPRISE  wwwmon
	VARIABLES   { 
		wwwmonServerName,
		wwwmonServerPort,
		wwwmonServerURL,
		wwwmonServerStatus
		}
	DESCRIPTION
		"Wwwmon reporting the status change to Up from a web page query."
		--#SUMMARY "%s status serving web pages: Up"
		--#ARGUMENTS { 0 }
		--#SEVERITY INFORMATIONAL
		--#SLOTMAP origin $V1
	::= 101

wwwmonTimeout TRAP-TYPE
	ENTERPRISE  wwwmon
	VARIABLES   { 
		wwwmonServerName,
		wwwmonServerPort,
		wwwmonServerURL,
		wwwmonServerStatus
		}
	DESCRIPTION
		"Wwwmon reporting the status change to Timeout from a web page query."
		--#SUMMARY "%s status serving web pages: Timeout"
		--#ARGUMENTS { 0 }
		--#SEVERITY INFORMATIONAL
		--#SLOTMAP origin $V1
	::= 102

wwwmonRefd TRAP-TYPE
	ENTERPRISE  wwwmon
	VARIABLES   { 
		wwwmonServerName,
		wwwmonServerPort,
		wwwmonServerURL,
		wwwmonServerStatus
		}
	DESCRIPTION
		"Wwwmon reporting the status change to Refused from a web page query."
		--#SUMMARY "%s status serving web pages: Refused"
		--#ARGUMENTS { 0 }
		--#SEVERITY CRITICAL
		--#SLOTMAP origin $V1
	::= 103

wwwmonUnknown TRAP-TYPE
	ENTERPRISE  wwwmon
	VARIABLES   { 
		wwwmonServerName,
		wwwmonServerPort,
		wwwmonServerURL,
		wwwmonServerStatus
		}
	DESCRIPTION
		"Wwwmon reporting the status change to Unknown from a web page query."
		--#SUMMARY "%s status serving web pages: Unknown"
		--#ARGUMENTS { 0 }
		--#SEVERITY INFORMATIONAL
		--#SLOTMAP origin $V1
	::= 104

wwwmonBusy TRAP-TYPE
	ENTERPRISE  wwwmon
	VARIABLES   { 
		wwwmonServerName,
		wwwmonServerPort,
		wwwmonServerURL,
		wwwmonServerStatus
		}
	DESCRIPTION
		"Wwwmon reporting the status change to Busy from a web page query."
		--#SUMMARY "%s status serving web pages: Busy"
		--#ARGUMENTS { 0 }
		--#SEVERITY CRITICAL
		--#SLOTMAP origin $V1
	::= 105

wwwmonInfo TRAP-TYPE
	ENTERPRISE  wwwmon
	VARIABLES   { 
		wwwmonServerName,
		wwwmonServerPort,
		wwwmonServerURL,
		wwwmonServerStatus
		}
	DESCRIPTION
		"Wwwmon reporting the status change to HTTP-Info from a web page query."
		--#SUMMARY "%s status serving web pages: HTTP-Info"
		--#ARGUMENTS { 0 }
		--#SEVERITY INFORMATIONAL
		--#SLOTMAP origin $V1
	::= 106

wwwmonRedirect TRAP-TYPE
	ENTERPRISE  wwwmon
	VARIABLES   { 
		wwwmonServerName,
		wwwmonServerPort,
		wwwmonServerURL,
		wwwmonServerStatus
		}
	DESCRIPTION
		"Wwwmon reporting the status change to HTTP-Redirect from a web page query."
		--#SUMMARY "%s status serving web pages: HTTP-Redirect"
		--#ARGUMENTS { 0 }
		--#SEVERITY INFORMATIONAL
		--#SLOTMAP origin $V1
	::= 107

wwwmonClient TRAP-TYPE
	ENTERPRISE  wwwmon
	VARIABLES   { 
		wwwmonServerName,
		wwwmonServerPort,
		wwwmonServerURL,
		wwwmonServerStatus
		}
	DESCRIPTION
		"Wwwmon reporting the status change to HTTP-Client-Err from a web page query."
		--#SUMMARY "%s status serving web pages: HTTP-Client-Err"
		--#ARGUMENTS { 0 }
		--#SEVERITY INFORMATIONAL
		--#SLOTMAP origin $V1
	::= 108

wwwmonServer TRAP-TYPE
	ENTERPRISE  wwwmon
	VARIABLES   { 
		wwwmonServerName,
		wwwmonServerPort,
		wwwmonServerURL,
		wwwmonServerStatus
		}
	DESCRIPTION
		"Wwwmon reporting the status change to HTTP-Server-Err from a web page query."
		--#SUMMARY "%s status serving web pages: HTTP-Server-Err"
		--#ARGUMENTS { 0 }
		--#SEVERITY INFORMATIONAL
		--#SLOTMAP origin $V1
	::= 109

----------------------------------------------
----------------------------------------------
--
-- AgentMon
--
----------------------------------------------
----------------------------------------------

--
-- Variables used by traps
--

--
-- Trap Definitions
--

----------------------------------------------
----------------------------------------------
--
-- eProbe (remote)
--
----------------------------------------------
----------------------------------------------
--
-- Variables used by traps
--

tscRemoteSourceNode OBJECT-TYPE
	SYNTAX  DisplayString
	ACCESS  read-only
	STATUS  optional
	DESCRIPTION
		"The hostname of the node being reported."
	::= { remote 1 }

tscRemoteValue OBJECT-TYPE
	SYNTAX  INTEGER
	ACCESS  read-only
	STATUS  optional
	DESCRIPTION
		"The value of a variable a thresold was set against."
	::= { remote 2 }

tscRemoteThreshold OBJECT-TYPE
	SYNTAX  INTEGER
	ACCESS  read-only
	STATUS  optional
	DESCRIPTION
		"The value of a user-defined thresold."
	::= { remote 3 }

tscRemoteRearm OBJECT-TYPE
	SYNTAX  INTEGER
	ACCESS  read-only
	STATUS  optional
	DESCRIPTION
		"The value of a user-defined rearm."
	::= { remote 4 }

tscRemoteSourceAddr OBJECT-TYPE
	SYNTAX  DisplayString
	ACCESS  read-only
	STATUS  optional
	DESCRIPTION
		"The address of the node being reported."
	::= { remote 5 }

tscRemoteName OBJECT-TYPE
	SYNTAX  DisplayString
	ACCESS  read-only
	STATUS  optional
	DESCRIPTION
		"The hostname of this reporting system."
	::= { remote 6 }

tscRemoteSourceNode2 OBJECT-TYPE
	SYNTAX  DisplayString
	ACCESS  read-only
	STATUS  optional
	DESCRIPTION
		"Another hostname being reported."
	::= { remote 7 }

tscRemoteSourceProtocol OBJECT-TYPE
	SYNTAX  DisplayString
	ACCESS  read-only
	STATUS  optional
	DESCRIPTION
		"The network protocol of the node being reported."
	::= { remote 8 }

tscRemoteProcName OBJECT-TYPE
	SYNTAX  DisplayString
	ACCESS  read-only
	STATUS  optional
	DESCRIPTION
		"The eProbe process name being reported."
	::= { remote 9 }

tscRemoteFsDevice OBJECT-TYPE
	SYNTAX  DisplayString
	ACCESS  read-only
	STATUS  optional
	DESCRIPTION
		"The file system logical device."
	::= { remote 10 }

tscRemoteFsName OBJECT-TYPE
	SYNTAX  DisplayString
	ACCESS  read-only
	STATUS  optional
	DESCRIPTION
		"The file system name (mount point)."
	::= { remote 11 }

tscRemoteIfIndex OBJECT-TYPE
	SYNTAX  DisplayString
	ACCESS  read-only
	STATUS  optional
	DESCRIPTION
		"The relevant ifIndex."
	::= { remote 12 }

tscRemoteChassis OBJECT-TYPE
	SYNTAX  DisplayString
	ACCESS  read-only
	STATUS  optional
	DESCRIPTION
		"The relevant chassis #."
	::= { remote 13 }

tscRemoteSlot OBJECT-TYPE
	SYNTAX  DisplayString
	ACCESS  read-only
	STATUS  optional
	DESCRIPTION
		"The relevant slot #."
	::= { remote 14 }

tscRemotePosition OBJECT-TYPE
	SYNTAX  DisplayString
	ACCESS  read-only
	STATUS  optional
	DESCRIPTION
		"The relevant port position #."
	::= { remote 15 }

tscRemoteDescription OBJECT-TYPE
	SYNTAX  DisplayString
	ACCESS  read-only
	STATUS  optional
	DESCRIPTION
		"The relevant description."
	::= { remote 16 }

tscRemoteRecno OBJECT-TYPE
	SYNTAX  DisplayString
	ACCESS  read-only
	STATUS  optional
	DESCRIPTION
		"The relevant database record number."
	::= { remote 17 }

tscRemoteOldValue OBJECT-TYPE
	SYNTAX  INTEGER
	ACCESS  read-only
	STATUS  optional
	DESCRIPTION
		"The old value of a variable a thresold was set against."
	::= { remote 18 }

tscRemoteTrapOID OBJECT-TYPE
	SYNTAX  DisplayString
	ACCESS  read-only
	STATUS  optional
	DESCRIPTION
		"The enterprise OID of trap being encapsulated."
	::= { remote 19 }

tscRemoteTrapGeneric OBJECT-TYPE
	SYNTAX  DisplayString
	ACCESS  read-only
	STATUS  optional
	DESCRIPTION
		"The generic of trap being encapsulated."
	::= { remote 20 }

tscRemoteTrapSpecific OBJECT-TYPE
	SYNTAX  DisplayString
	ACCESS  read-only
	STATUS  optional
	DESCRIPTION
		"The specific of trap being encapsulated."
	::= { remote 21 }

tscRemoteTrapTimestamp OBJECT-TYPE
	SYNTAX  DisplayString
	ACCESS  read-only
	STATUS  optional
	DESCRIPTION
		"The timestamp of trap being encapsulated."
	::= { remote 22 }

tscRemoteTrapCommunity OBJECT-TYPE
	SYNTAX  DisplayString
	ACCESS  read-only
	STATUS  optional
	DESCRIPTION
		"The community of trap being encapsulated."
	::= { remote 23 }

tscRemoteTimestamp OBJECT-TYPE
	SYNTAX  DisplayString
	ACCESS  read-only
	STATUS  optional
	DESCRIPTION
		"A timestamp for this event."
	::= { remote 24 }

tscRemoteDomain OBJECT-TYPE
	SYNTAX  DisplayString
	ACCESS  read-only
	STATUS  optional
	DESCRIPTION
		"An ePROBE domain for this event."
	::= { remote 25 }

--
-- Trap Definitions
--

tscIfDown TRAP-TYPE
	ENTERPRISE  remote
	VARIABLES   { 
		tscRemoteSourceNode,
		tscRemoteSourceAddr,
		tscRemoteSourceProtocol,
		tscRemoteName,
		tscRemoteIfIndex
		}
	DESCRIPTION
		"Interface is not reachable.

		This trap is sent after tpingd determines
		that an interface is no longer reachable.

		The bound variables contain the address of the device."
		--#SUMMARY "Interface %s (%s) down"
		--#ARGUMENTS { 0, 1 }
		--#SEVERITY CRITICAL
		--#STATE NONOPERATIONAL
		--#SLOTMAP origin $V2
		--#SLOTMAP hostname $V1
		--#SLOTMAP protocol $V3
		--#SLOTMAP reporthost $V4
	::= 1

tscIfUp TRAP-TYPE
	ENTERPRISE  remote
	VARIABLES   { 
		tscRemoteSourceNode,
		tscRemoteSourceAddr,
		tscRemoteSourceProtocol,
		tscRemoteName,
		tscRemoteIfIndex
		}
	DESCRIPTION
		"Interface is reachable.

		This trap is sent after tpingd determines
		that an interface is now reachable.

		The bound variables contain the address of the device."
		--#SUMMARY "Interface %s (%s) up"
		--#ARGUMENTS { 0, 1 }
		--#SEVERITY INFORMATIONAL
		--#SLOTMAP origin $V2
		--#SLOTMAP hostname $V1
		--#SLOTMAP protocol $V3
		--#SLOTMAP reporthost $V4
	::= 2

tscIfLatThreshold TRAP-TYPE
	ENTERPRISE  remote
	VARIABLES   { 
		tscRemoteSourceNode,
		tscRemoteValue,
		tscRemoteThreshold,
		tscRemoteName
		}
	DESCRIPTION
		"A user-defined interface latency threshold was exceeded.

		This trap is sent after tpingd determines
		that a user-defined interface latency threshold was 
		exceeded for this device.

		The bound variables contain the address of the device,
		the value of the interface latency,
		the value of the user-defined threshold."
		--#SUMMARY "Interface latency threshold reached for %s. Value %d. Threshold %d."
		--#ARGUMENTS { 0, 1, 2 }
		--#SEVERITY INFORMATIONAL
		--#SLOTMAP origin $V1
		--#SLOTMAP iflatvalue $V2
		--#SLOTMAP iflatthreshold $V3
		--#SLOTMAP reporthost $V4
	::= 3

tscIfLatRearm TRAP-TYPE
	ENTERPRISE  remote
	VARIABLES   { 
		tscRemoteSourceNode,
		tscRemoteValue,
		tscRemoteRearm,
		tscRemoteName
		}
	DESCRIPTION
		"A user-defined interface latency threshold was rearmed.

		This trap is sent after tpingd determines
		that a user-defined interface latency threshold was 
		rearmed for this device.

		The bound variables contain the address of the device,
		the value of the interface latency,
		the value of the user-defined rearm."
		--#SUMMARY "Interface latency threshold rearmed for %s. Value %d. Rearm %d."
		--#ARGUMENTS { 0, 1, 2 }
		--#SEVERITY INFORMATIONAL
		--#SLOTMAP origin $V1
		--#SLOTMAP iflatvalue $V2
		--#SLOTMAP iflatrearm $V3
		--#SLOTMAP reporthost $V4
	::= 4

tscIfUnknown TRAP-TYPE
	ENTERPRISE  remote
	VARIABLES   { 
		tscRemoteSourceNode,
		tscRemoteSourceAddr,
		tscRemoteSourceProtocol,
		tscRemoteName,
		tscRemoteIfIndex
		}
	DESCRIPTION
		"Interface status is unknown.

		This trap is sent after tpingd determines
		that an interface is no longer known.

		The bound variables contain the address of the device."
		--#SUMMARY "Interface %s (%s) unknown"
		--#ARGUMENTS { 0, 1 }
		--#SEVERITY CRITICAL
		--#STATE NONOPERATIONAL
		--#SLOTMAP origin $V2
		--#SLOTMAP hostname $V1
		--#SLOTMAP protocol $V3
		--#SLOTMAP reporthost $V4
	::= 5

tscNodeDown TRAP-TYPE
	ENTERPRISE  remote
	VARIABLES   { 
		tscRemoteSourceNode,
		tscRemoteValue,
		tscRemoteName
		}
	DESCRIPTION
		"Node is down.

		This trap is sent after ipmon determines
		that all interfaces on a node are down.

		The bound variables contain the address of the device."
		--#SUMMARY "Node %s down"
		--#ARGUMENTS { 0 }
		--#SEVERITY CRITICAL
		--#STATE NONOPERATIONAL
		--#SLOTMAP hostname $V1
		--#SLOTMAP reporthost $V3
	::= 6

tscNodeMarginal TRAP-TYPE
	ENTERPRISE  remote
	VARIABLES   { 
		tscRemoteSourceNode,
		tscRemoteValue,
		tscRemoteName
		}
	DESCRIPTION
		"Node is marginal.

		This trap is sent after ipmon determines
		that some interfaces on the node are down
		and some interfaces on the node are up.

		The bound variables contain the address of the device."
		--#SUMMARY "Node %s marginal"
		--#ARGUMENTS { 0 }
		--#SEVERITY WARNING
		--#SLOTMAP hostname $V1
		--#SLOTMAP reporthost $V3
	::= 7

tscNodeUp TRAP-TYPE
	ENTERPRISE  remote
	VARIABLES   { 
		tscRemoteSourceNode,
		tscRemoteValue,
		tscRemoteName
		}
	DESCRIPTION
		"Node is up.

		This trap is sent after ipmon determines
		that all interfaces on a node are up.

		The bound variables contain the address of the device."
		--#SUMMARY "Node %s down"
		--#ARGUMENTS { 0 }
		--#SEVERITY NORMAL
		--#STATE OPERATIONAL
		--#SLOTMAP hostname $V1
		--#SLOTMAP reporthost $V3
	::= 8

tscNodeUnknown TRAP-TYPE
	ENTERPRISE  remote
	VARIABLES   { 
		tscRemoteSourceNode,
		tscRemoteValue,
		tscRemoteName
		}
	DESCRIPTION
		"Node is unknown.

		This trap is sent after ipmon determines
		that all interfaces on a node are unknown.

		The bound variables contain the address of the device."
		--#SUMMARY "Node %s unknown"
		--#ARGUMENTS { 0 }
		--#SEVERITY UNKNOWN
		--#SLOTMAP hostname $V1
		--#SLOTMAP reporthost $V3
	::= 9

tscNewNode TRAP-TYPE
	ENTERPRISE  remote
	VARIABLES   { 
		tscRemoteSourceNode,
		tscRemoteSourceAddr,
		tscRemoteName
		}
	DESCRIPTION
		"A new node has been discovered by this system."
		--#SUMMARY "(%s) New node %s"
		--#ARGUMENTS { 2,1 }
		--#SEVERITY INFORMATIONAL
		--#SLOTMAP hostname $V1
		--#SLOTMAP origin $V2
		--#SLOTMAP reporthost $V3
	::= 10

tscNameChange TRAP-TYPE
	ENTERPRISE  remote
	VARIABLES   { 
		tscRemoteSourceNode,
		tscRemoteSourceNode2,
		tscRemoteSourceAddr,
		tscRemoteName
		}
	DESCRIPTION
		"A node name has changed"
		--#SUMMARY "(%s) Node Name Changed to %s (was %s)"
		--#ARGUMENTS { 3,0,1 }
		--#SEVERITY INFORMATIONAL
		--#SLOTMAP hostname $V1
		--#SLOTMAP origin $V3
		--#SLOTMAP reporthost $V4
	::= 11

tscIfDelete TRAP-TYPE
	ENTERPRISE  remote
	VARIABLES   { 
		tscRemoteSourceNode,
		tscRemoteSourceAddr,
		tscRemoteSourceProtocol,
		tscRemoteName
		}
	DESCRIPTION
		"Interface is deleted

		This trap is sent after tpingd determines
		that an interface has been deleted.

		The bound variables contain the address of the device."
		--#SUMMARY "Interface %s Deleted"
		--#ARGUMENTS { 0 }
		--#SEVERITY INFORMATIONAL
		--#SLOTMAP origin $V2
		--#SLOTMAP hostname $V1
		--#SLOTMAP protocol $V3
		--#SLOTMAP reporthost $V4
	::= 12

tscNodeAdded TRAP-TYPE
	ENTERPRISE  remote
	VARIABLES   { 
		tscRemoteSourceNode,
		tscRemoteRecno,
		tscRemoteName
		}
	DESCRIPTION
		"Node is added.

		This trap is sent when scannode determines
		that a node is new in the nodedb."
		--#SUMMARY "Node %s Added"
		--#ARGUMENTS { 0 }
		--#SEVERITY INFORMATIONAL
	::= 13

tscInterfaceAdded TRAP-TYPE
	ENTERPRISE  remote
	VARIABLES   { 
		tscRemoteSourceNode,
		tscRemoteIfIndex,
		tscRemoteName
		}
	DESCRIPTION
		"An interface on a node is added.

		This trap is sent when scannode determines
		that an interface is new in the ifdb."
		--#SUMMARY "Interface %s(%s) Added"
		--#ARGUMENTS { 0, 1 }
		--#SEVERITY INFORMATIONAL
	::= 14

tscNodeDeleted TRAP-TYPE
	ENTERPRISE  remote
	VARIABLES   { 
		tscRemoteSourceNode,
		tscRemoteName
		}
	DESCRIPTION
		"Node is deleted.

		This trap is sent when scannode determines
		that a node is removed from the nodedb."
		--#SUMMARY "Node %s Deleted"
		--#ARGUMENTS { 0 }
		--#SEVERITY INFORMATIONAL
	::= 15

tscInterfaceDeleted TRAP-TYPE
	ENTERPRISE  remote
	VARIABLES   { 
		tscRemoteSourceNode,
		tscRemoteIfIndex,
		tscRemoteName
		}
	DESCRIPTION
		"An interface on a node is removed.

		This trap is sent when scannode determines
		that an interface is removed from the ifdb."
		--#SUMMARY "Interface %s(%s) Deleted"
		--#ARGUMENTS { 0, 1 }
		--#SEVERITY INFORMATIONAL
	::= 16

tscHostnameChanged TRAP-TYPE
	ENTERPRISE  remote
	VARIABLES   { 
		tscRemoteOldValue,
		tscRemoteValue,
		tscRemoteRecno,
		tscRemoteName
		}
	DESCRIPTION
		"A hostname change has been detected.

		This trap is sent when scannode determines
		that a new hostname is being used for a formerly
		different named node."
		--#SUMMARY "Host %s renamed to %s"
		--#ARGUMENTS { 0, 1 }
		--#SEVERITY INFORMATIONAL
	::= 17

tscSysObjectIDChanged TRAP-TYPE
	ENTERPRISE  remote
	VARIABLES   { 
		tscRemoteSourceNode,
		tscRemoteValue,
		tscRemoteRecno,
		tscRemoteName
		}
	DESCRIPTION
		"The sysObjectID on the device changed.

		This trap is sent when scannode determines
		that a new sysObjectID was detected for a host."
		--#SUMMARY "sysObjectID changed."
		--#ARGUMENTS { }
		--#SEVERITY INFORMATIONAL
	::= 18

tscProcFail TRAP-TYPE
	ENTERPRISE  remote
	VARIABLES   { 
		tscRemoteName,
		tscRemoteProcName
		}
	DESCRIPTION
		"A key eProbe process has failed."
		--#SUMMARY "(%s) eProbe process %s failed."
		--#ARGUMENTS { 0, 1 }
		--#SEVERITY CRITICAL
		--#SLOTMAP hostname $V1
		--#SLOTMAP procname $V2
	::= 21

tscProcStop TRAP-TYPE
	ENTERPRISE  remote
	VARIABLES   { 
		tscRemoteName,
		tscRemoteProcName
		}
	DESCRIPTION
		"A key eProbe process has stopped (deliberate)."
		--#SUMMARY "(%s) eProbe process %s stopped."
		--#ARGUMENTS { 0, 1 }
		--#SEVERITY CRITICAL
		--#SLOTMAP hostname $V1
		--#SLOTMAP procname $V2
	::= 22

tscProcStart TRAP-TYPE
	ENTERPRISE  remote
	VARIABLES   { 
		tscRemoteName,
		tscRemoteProcName
		}
	DESCRIPTION
		"A key eProbe process has started."
		--#SUMMARY "(%s) eProbe process %s started."
		--#ARGUMENTS { 0, 1 }
		--#SEVERITY CRITICAL
		--#SLOTMAP hostname $V1
		--#SLOTMAP procname $V2
	::= 23

tscFsFull TRAP-TYPE
	ENTERPRISE  remote
	VARIABLES   { 
		tscRemoteName,
		tscRemoteFsDevice,
		tscRemoteFsName,
		tscRemoteValue
		}
	DESCRIPTION
		"A file system is getting full.  It has reached a particular
		level of capacity (%)."
		--#SUMMARY "(%s) eProbe file system %s is %d%% full."
		--#ARGUMENTS { 0, 2, 3 }
		--#SEVERITY CRITICAL
		--#SLOTMAP hostname $V1
		--#SLOTMAP fsname $V3
		--#SLOTMAP threshold $V4
	::= 24

tscVoidWarranty TRAP-TYPE
	ENTERPRISE  remote
	VARIABLES   { 
		tscRemoteName
		}
	DESCRIPTION
		"The eProbe admin has elected for root access to the device
		and understands this voids the warranty."
		--#SUMMARY "(%s) eProbe root access enabled.  eProbe warranty voided."
		--#ARGUMENTS { 0}
		--#SEVERITY INFORMATIONAL
		--#SLOTMAP hostname $V1
	::= 25

tscSysNameChanged TRAP-TYPE
	ENTERPRISE  remote
	VARIABLES   { 
		tscRemoteOldValue,
		tscRemoteValue,
		tscRemoteRecno,
		tscRemoteName
		}
	DESCRIPTION
		"The sysName on the device changed.

		This trap is sent when scannode determines
		that a new sysName was detected for a host."
		--#SUMMARY "sysName changed to %s."
		--#ARGUMENTS { 1 }
		--#SEVERITY INFORMATIONAL
	::= 26

tscSysDescrChanged TRAP-TYPE
	ENTERPRISE  remote
	VARIABLES   { 
		tscRemoteOldValue,
		tscRemoteValue,
		tscRemoteRecno,
		tscRemoteName
		}
	DESCRIPTION
		"The sysDescr on the device changed.

		This trap is sent when scannode determines
		that a new sysDescr was detected for a host."
		--#SUMMARY "sysDescr changed."
		--#ARGUMENTS { }
		--#SEVERITY INFORMATIONAL
	::= 27

tscSysLocationChanged TRAP-TYPE
	ENTERPRISE  remote
	VARIABLES   { 
		tscRemoteOldValue,
		tscRemoteValue,
		tscRemoteRecno,
		tscRemoteName
		}
	DESCRIPTION
		"The sysLocation on the device changed.

		This trap is sent when scannode determines
		that a new sysLocation was detected for a host."
		--#SUMMARY "sysLocation changed."
		--#ARGUMENTS { }
		--#SEVERITY INFORMATIONAL
	::= 28

tscSysContactChanged TRAP-TYPE
	ENTERPRISE  remote
	VARIABLES   { 
		tscRemoteOldValue,
		tscRemoteValue,
		tscRemoteRecno,
		tscRemoteName
		}
	DESCRIPTION
		"The sysContact on the device changed.

		This trap is sent when scannode determines
		that a new sysContact was detected for a host."
		--#SUMMARY "sysContact changed."
		--#ARGUMENTS { }
		--#SEVERITY INFORMATIONAL
	::= 29

tscManage TRAP-TYPE
	ENTERPRISE  remote
	VARIABLES   { 
		tscRemoteSourceNode
		}
	DESCRIPTION
		"A node is now managed.

		This trap is sent after tmanage switches
		the status of the node to managed.

		The bound variable contain the name of the device."
		--#SUMMARY "Node %s managed"
		--#ARGUMENTS { 0 }
		--#SEVERITY INFORMATIONAL
		--#SLOTMAP hostname $V1
	::= 50

tscUnmanage TRAP-TYPE
	ENTERPRISE  remote
	VARIABLES   { 
		tscRemoteSourceNode
		}
	DESCRIPTION
		"A node is now unmanaged.

		This trap is sent after tunmanage switches
		the status of the node to unmanaged.

		The bound variable contain the name of the device."
		--#SUMMARY "Node %s unmanaged"
		--#ARGUMENTS { 0 }
		--#SEVERITY INFORMATIONAL
		--#SLOTMAP hostname $V1
	::= 51

tscIfManage TRAP-TYPE
	ENTERPRISE  remote
	VARIABLES   { 
		tscRemoteIfIndex,
		tscRemoteDescription
		}
	DESCRIPTION
		"An interface is now managed.

		This trap is sent after tmanage switches
		the status of the interface to managed.

		The bound variables contain the ifIndex, ifDescr."
		--#SUMMARY "Interface %s (%s) managed"
		--#ARGUMENTS { 0, 1 }
		--#SEVERITY INFORMATIONAL
	::= 52

tscIfUnmanage TRAP-TYPE
	ENTERPRISE  remote
	VARIABLES   { 
		tscRemoteIfIndex,
		tscRemoteDescription
		}
	DESCRIPTION
		"An interface is now unmanaged.

		This trap is sent after tunmanage switches
		the status of the interface to unmanaged.

		The bound variables contain the ifIndex, ifDescr."
		--#SUMMARY "Interface %s (%s) unmanaged"
		--#ARGUMENTS { 0, 1 }
		--#SEVERITY INFORMATIONAL
	::= 53

tscNetManage TRAP-TYPE
	ENTERPRISE  remote
	VARIABLES   { 
		tscRemoteIfIndex,
		tscRemoteDescription
		}
	DESCRIPTION
		"A subnet is now managed.

		This trap is sent after tmanage switches
		the status of the subnet to managed."
		--#SUMMARY "Subnet managed"
		--#ARGUMENTS { }
		--#SEVERITY INFORMATIONAL
	::= 54

tscNetUnmanage TRAP-TYPE
	ENTERPRISE  remote
	VARIABLES   { 
		tscRemoteIfIndex,
		tscRemoteDescription
		}
	DESCRIPTION
		"A subnet is now unmanaged.

		This trap is sent after tunmanage switches
		the status of the subnet to unmanaged."
		--#SUMMARY "Subnet unmanaged"
		--#ARGUMENTS { }
		--#SEVERITY INFORMATIONAL
	::= 55

tscPortManage TRAP-TYPE
	ENTERPRISE  remote
	VARIABLES   { 
		tscRemoteIfIndex,
		tscRemoteChassis,
		tscRemoteSlot,
		tscRemotePosition
		}
	DESCRIPTION
		"An interface is now managed.

		This trap is sent after tmanage switches
		the status of the interface to managed.

		The bound variables contain the ifIndex, chassis, slot, and positon."
		--#SUMMARY "Port %s managed. Slot %s, Port %s"
		--#ARGUMENTS { 0, 2, 3 }
		--#SEVERITY INFORMATIONAL
	::= 56

tscPortUnmanage TRAP-TYPE
	ENTERPRISE  remote
	VARIABLES   { 
		tscRemoteIfIndex,
		tscRemoteChassis,
		tscRemoteSlot,
		tscRemotePosition
		}
	DESCRIPTION
		"An interface is now unmanaged.

		This trap is sent after tunmanage switches
		the status of the interface to unmanaged.

		The bound variables contain the ifIndex, chassis, slot, and positon."
		--#SUMMARY "Port %s unmanaged. Slot %s, Port %s"
		--#ARGUMENTS { 0, 2, 3 }
		--#SEVERITY INFORMATIONAL
	::= 57

tscFwdTrap TRAP-TYPE
	ENTERPRISE  remote
	VARIABLES   { 
		tscRemoteName,
		tscRemoteSourceNode,
		tscRemoteSourceAddr,
		tscRemoteTrapOID,
		tscRemoteTrapGeneric,
		tscRemoteTrapSpecific,
		tscRemoteTrapTimestamp,
		tscRemoteTrapCommunity,
		tscRemoteDescription,
		tscRemoteValue
		}
	DESCRIPTION
		"Ensapsulate a trap within this trap.

		This trap is sent by ePROBE when forwarding traps with
		ensapsulation mode on.  In particular, this makes sure
		forwarded traps do not have source agent IP address which
		messes up the NMS in duplicate IP environments.

		The bound variables contain the details of the oringal 
		trap: agent IP address, agent hostname, enterprise OID,
		generic, specific, timestamp, community, log message,
		and variables."
		--#SUMMARY "ePROBE: %s: %s %s"
		--#ARGUMENTS { 0, 1, 8 }
		--#SEVERITY INFORMATIONAL
	::= 60

tscRedPeerAdd TRAP-TYPE
	ENTERPRISE  remote
	VARIABLES   { 
		tscRemoteName,
		tscRemoteSourceNode,
		tscRemoteDomain,
		tscRemoteTimestamp
		}
	DESCRIPTION
		"Report a redundant peer has been added."
		--#SUMMARY "ePROBE %s peer %s has been added"
		--#ARGUMENTS { 0, 1 }
		--#SEVERITY INFORMATIONAL
	::= 61

tscRedPeerRm TRAP-TYPE
	ENTERPRISE  remote
	VARIABLES   { 
		tscRemoteName,
		tscRemoteSourceNode,
		tscRemoteDomain,
		tscRemoteTimestamp
		}
	DESCRIPTION
		"Report a redundant peer has been removed."
		--#SUMMARY "ePROBE %s peer %s has been removed"
		--#ARGUMENTS { 0, 1 }
		--#SEVERITY INFORMATIONAL
	::= 62

tscRedPeerUp TRAP-TYPE
	ENTERPRISE  remote
	VARIABLES   { 
		tscRemoteName,
		tscRemoteSourceNode,
		tscRemoteDomain,
		tscRemoteTimestamp
		}
	DESCRIPTION
		"Report a redundant peer is now up."
		--#SUMMARY "ePROBE %s peer %s is up"
		--#ARGUMENTS { 0, 1 }
		--#SEVERITY INFORMATIONAL
	::= 63

tscRedPeerUnavail TRAP-TYPE
	ENTERPRISE  remote
	VARIABLES   { 
		tscRemoteName,
		tscRemoteSourceNode,
		tscRemoteDomain,
		tscRemoteTimestamp
		}
	DESCRIPTION
		"Report a redundant peer is now unavailable."
		--#SUMMARY "ePROBE %s peer %s is unavailable"
		--#ARGUMENTS { 0, 1 }
		--#SEVERITY INFORMATIONAL
	::= 64

tscRedPeerDown TRAP-TYPE
	ENTERPRISE  remote
	VARIABLES   { 
		tscRemoteName,
		tscRemoteSourceNode,
		tscRemoteDomain,
		tscRemoteTimestamp
		}
	DESCRIPTION
		"Report a redundant peer is now down."
		--#SUMMARY "ePROBE %s peer %s is down"
		--#ARGUMENTS { 0, 1 }
		--#SEVERITY INFORMATIONAL
	::= 65

tscRemoteNoStatus TRAP-TYPE
	ENTERPRISE  remote
	VARIABLES   { 
		tscEwFaultAddr,
		tscEwFaultName,
		tscEwFaultProtocol,
		tscEwGroupName,
		tscEwReportHost,
		tscEwEventTime
		}
	DESCRIPTION
		"ePROBE is inferred down because it has not reported
		in to NMS.

		This trap is sent by ePdaemon.

		This trap has bindings in alignment with remote source down
		trap"
		--#SUMMARY "ePROBE %s not responding."
		--#ARGUMENTS { 2 }
		--#SEVERITY CRITICAL
		--#STATE NONOPERATIONAL
		--#SLOTMAP origin $V1
		--#SLOTMAP hostname $V2
		--#SLOTMAP protocol $V3
		--#SLOTMAP reporthost $V5
	::= 68

tscRemoteAlive TRAP-TYPE
	ENTERPRISE  remote
	VARIABLES   { 
		tscEwFaultAddr,
		tscEwFaultName,
		tscEwFaultProtocol,
		tscEwGroupName,
		tscEwReportHost,
		tscEwEventTime
		}
	DESCRIPTION
		"ePROBE is inferred up because it has again reported
		in to NMS.

		This trap is sent by ePdaemon.

		This trap has bindings in alignment with remote source up
		trap"
		--#SUMMARY "ePROBE %s alive."
		--#ARGUMENTS { 2 }
		--#SEVERITY CRITICAL
		--#STATE NONOPERATIONAL
		--#SLOTMAP origin $V1
		--#SLOTMAP hostname $V2
		--#SLOTMAP protocol $V3
		--#SLOTMAP reporthost $V5
	::= 69

----------------------------------------------
----------------------------------------------
--
-- portmon (Port Monitoring/Management)
--
----------------------------------------------
----------------------------------------------

--
-- Variables used by traps
--

tscPmOldValue OBJECT-TYPE
	SYNTAX  DisplayString
	ACCESS  read-only
	STATUS  optional
	DESCRIPTION
		"The old value (before the change)."
	::= { portmon 1 }

tscPmValue OBJECT-TYPE
	SYNTAX  DisplayString
	ACCESS  read-only
	STATUS  optional
	DESCRIPTION
		"The (new) value (after the change)."
	::= { portmon 2 }

tscPmIndex OBJECT-TYPE
	SYNTAX  INTEGER
	ACCESS  read-only
	STATUS  optional
	DESCRIPTION
		"The ifIndex for the port being reported."
	::= { portmon 3 }

tscPmChassis OBJECT-TYPE
	SYNTAX  INTEGER
	ACCESS  read-only
	STATUS  optional
	DESCRIPTION
		"The chassis # for the port being reported."
	::= { portmon 4 }

tscPmSlot OBJECT-TYPE
	SYNTAX  INTEGER
	ACCESS  read-only
	STATUS  optional
	DESCRIPTION
		"The slot number inside chassis for the port being reported."
	::= { portmon 5 }

tscPmPos OBJECT-TYPE
	SYNTAX  INTEGER
	ACCESS  read-only
	STATUS  optional
	DESCRIPTION
		"The port # or port position in slot for the port being reported."
	::= { portmon 6 }

tscPmStatus OBJECT-TYPE
	SYNTAX  DisplayString
	ACCESS  read-only
	STATUS  optional
	DESCRIPTION
		"The (new) status of the port."
	::= { portmon 7 }

tscPmName OBJECT-TYPE
	SYNTAX  DisplayString
	ACCESS  read-only
	STATUS  optional
	DESCRIPTION
		"The user defined name of the port."
	::= { portmon 8 }

tscPmTime OBJECT-TYPE
	SYNTAX  DisplayString
	ACCESS  read-only
	STATUS  optional
	DESCRIPTION
		"The (Unix) time of the status change."
	::= { portmon 9 }


--
-- Trap Definitions
--

tscPmNameChange TRAP-TYPE
	ENTERPRISE  portmon
	VARIABLES   { 
		tscPmOldValue,
		tscPmValue,
		tscPmIndex,
		tscPmChassis,
		tscPmSlot,
		tscPmPos
		}
	DESCRIPTION
		"The port name has changed.

		This trap is sent after a port configuration check
		determined that the port name has changed."

		--#SUMMARY "Port %s Name changed. Port %s,%s,%s. Value %s -> %s"
		--#ARGUMENTS { 2, 3, 4, 5, 0, 1 }
		--#SEVERITY INFORMATIONAL
	::= 1

tscPmTypeChange TRAP-TYPE
	ENTERPRISE  portmon
	VARIABLES   { 
		tscPmOldValue,
		tscPmValue,
		tscPmIndex,
		tscPmChassis,
		tscPmSlot,
		tscPmPos
		}
	DESCRIPTION
		"The port type has changed.

		This trap is sent after a port configuration check
		determined that the port type has changed."

		--#SUMMARY "Port %s Type changed. Port %s,%s,%s. Value %s -> %s"
		--#ARGUMENTS { 2, 3, 4, 5, 0, 1 }
		--#SEVERITY INFORMATIONAL
	::= 2

tscPmSpeedChange TRAP-TYPE
	ENTERPRISE  portmon
	VARIABLES   { 
		tscPmOldValue,
		tscPmValue,
		tscPmIndex,
		tscPmChassis,
		tscPmSlot,
		tscPmPos
		}
	DESCRIPTION
		"The port speed has changed.

		This trap is sent after a port configuration check
		determined that the port speed has changed."

		--#SUMMARY "Port %s Speed changed. Port %s,%s,%s. Value %s -> %s"
		--#ARGUMENTS { 2, 3, 4, 5, 0, 1 }
		--#SEVERITY INFORMATIONAL
	::= 3

tscPmDuplexChange TRAP-TYPE
	ENTERPRISE  portmon
	VARIABLES   { 
		tscPmOldValue,
		tscPmValue,
		tscPmIndex,
		tscPmChassis,
		tscPmSlot,
		tscPmPos
		}
	DESCRIPTION
		"The port duplex has changed.

		This trap is sent after a port configuration check
		determined that the port duplex has changed."

		--#SUMMARY "Port %s Duplex changed. Port %s,%s,%s. Value %s -> %s"
		--#ARGUMENTS { 2, 3, 4, 5, 0, 1 }
		--#SEVERITY INFORMATIONAL
	::= 4

tscPmVlanChange TRAP-TYPE
	ENTERPRISE  portmon
	VARIABLES   { 
		tscPmOldValue,
		tscPmValue,
		tscPmIndex,
		tscPmChassis,
		tscPmSlot,
		tscPmPos
		}
	DESCRIPTION
		"The port VLAN has changed.

		This trap is sent after a port configuration check
		determined that the port VLAN has changed."

		--#SUMMARY "Port %s VLAN changed. Port %s,%s,%s. Value %s -> %s"
		--#ARGUMENTS { 2, 3, 4, 5, 0, 1 }
		--#SEVERITY INFORMATIONAL
	::= 5

tscPmNewPort TRAP-TYPE
	ENTERPRISE  portmon
	VARIABLES   { 
		tscPmIndex,
		tscPmChassis,
		tscPmSlot,
		tscPmPos
		}
	DESCRIPTION
		"A new port has been discovered.

		This trap is sent after a port configuration check
		determined that a new port is present"

		--#SUMMARY "Port %s Added. Port %s,%s,%s."
		--#ARGUMENTS { 0, 1, 2, 3 }
		--#SEVERITY INFORMATIONAL
	::= 100

tscPmPortFault TRAP-TYPE
	ENTERPRISE  portmon
	VARIABLES   { 
		tscPmIndex,
		tscPmChassis,
		tscPmSlot,
		tscPmPos,
		tscPmStatus,
		tscPmName,
		tscPmTime
		}
	DESCRIPTION
		"The status of a port has gone critical.

		This trap is sent after a port status check
		determined that the port is not functioning."

		--#SUMMARY "Port %s Fault. Chassis %s Slot %s Port %s."
		--#ARGUMENTS { 3, 0, 1, 2 }
		--#SEVERITY CRITICAL
	::= 101

tscPmPortRestored TRAP-TYPE
	ENTERPRISE  portmon
	VARIABLES   { 
		tscPmIndex,
		tscPmChassis,
		tscPmSlot,
		tscPmPos,
		tscPmStatus,
		tscPmName,
		tscPmTime
		}
	DESCRIPTION
		"The status of a port returned to normal.

		This trap is sent after a port status check
		determined that the port is functioning again."

		--#SUMMARY "Port %s Restored. Chassis %s Slot %s Port %s."
		--#ARGUMENTS { 3, 0, 1, 2 }
		--#SEVERITY INFORMATIONAL
	::= 102

tscPmPortUnknown TRAP-TYPE
	ENTERPRISE  portmon
	VARIABLES   { 
		tscPmChassis,
		tscPmSlot,
		tscPmPos,
		tscPmIndex,
		tscPmStatus,
		tscPmName,
		tscPmTime
		}
	DESCRIPTION
		"The status of a port is now unknown.

		This trap is sent after a port status check
		determined that the port has entered an unknown state."

		--#SUMMARY "Port %s Unknown. Chassis %s Slot %s Port %s."
		--#ARGUMENTS { 3, 0, 1, 2 }
		--#SEVERITY INFORMATIONAL
	::= 103

tscPmPortDeleted TRAP-TYPE
	ENTERPRISE  portmon
	VARIABLES   { 
		tscPmIndex,
		tscPmChassis,
		tscPmSlot,
		tscPmPos,
		tscRemoteName
		}
	DESCRIPTION
		"A port has been deleted from portdb.

		This trap is sent after a port status check
		determined that the port no longer exists."

		--#SUMMARY "Port %s Deleted. Chassis %s Slot %s Port %s."
		--#ARGUMENTS { 0, 1, 2, 3 }
		--#SEVERITY INFORMATIONAL
	::= 104

----------------------------------------------
----------------------------------------------
--
-- ATM non IPed interface traps
--
----------------------------------------------
----------------------------------------------
--
-- Variables used by traps
--

tscAtmmonSourceNode OBJECT-TYPE
	SYNTAX  DisplayString
	ACCESS  read-only
	STATUS  optional
	DESCRIPTION
		"The hostname of the interface being reported."
	::= { atmmon 1 }

tscAtmmonIfIndex OBJECT-TYPE
	SYNTAX  INTEGER
	ACCESS  read-only
	STATUS  optional
	DESCRIPTION
		"The relevant ifIndex."
	::= { atmmon 2 }

tscAtmmonifName OBJECT-TYPE
	SYNTAX  DisplayString
	ACCESS  read-only
	STATUS  optional
	DESCRIPTION
		"The name of the interface being reported down."
	::= { atmmon 3 }

tscAtmIfDown TRAP-TYPE
	ENTERPRISE  atmmon
	VARIABLES   { 
		tscAtmmonIfIndex,
		tscAtmmonSourceNode,
		tscAtmmonifName
		}
	DESCRIPTION
		"Interface is not reachable.

		This trap is sent after atmmon determines
		that an interface is no longer reachable.

		The bound variables contain the address of the device."
		--#SUMMARY "Interface %s (%s) down"
		--#ARGUMENTS { 1, 0 }
		--#SEVERITY CRITICAL
		--#STATE NONOPERATIONAL
		--#SLOTMAP origin $V2
		--#SLOTMAP hostname $V2
	::= 101

tscAtmIfUp TRAP-TYPE
	ENTERPRISE  atmmon
	VARIABLES   { 
		tscAtmmonIfIndex,
		tscAtmmonSourceNode,
		tscAtmmonifName
		}
	DESCRIPTION
		"Interface is reachable.

		This trap is sent after atmmon determines
		that an interface is reachable.

		The bound variables contain the address of the device."
		--#SUMMARY "Interface %s (%s) up"
		--#ARGUMENTS { 1, 0 }
		--#SEVERITY INFORMATIONAL
		--#SLOTMAP origin $V2
		--#SLOTMAP hostname $V2
	::= 102

tscAtmIfUnknown TRAP-TYPE
	ENTERPRISE  atmmon
	VARIABLES   { 
		tscAtmmonIfIndex,
		tscAtmmonSourceNode,
		tscAtmmonifName
		}
	DESCRIPTION
		"Interface is not reachable.

		This trap is sent after atmmon determines
		that an interface is no longer reachable.

		The bound variables contain the address of the device."
		--#SUMMARY "Interface %s (%s) unknown"
		--#ARGUMENTS { 1, 0 }
		--#SEVERITY CRITICAL
		--#STATE NONOPERATIONAL
		--#SLOTMAP origin $V2
		--#SLOTMAP hostname $V2
	::= 103


----------------------------------------------
----------------------------------------------
--
-- SyslogTrap
--
----------------------------------------------
----------------------------------------------

--
-- Variables used by traps
--

tscSltLogMessage OBJECT-TYPE
	SYNTAX  DisplayString
	ACCESS  read-only
	STATUS  optional
	DESCRIPTION
		"The message from log file suitable for logging.
		Format is: 
			month day time host facility[pid]: message"
	::= { syslogtrap 1 }

tscSltFacility OBJECT-TYPE
	SYNTAX  DisplayString
	ACCESS  read-only
	STATUS  optional
	DESCRIPTION
		"The facility from log message, e.g. snmpd, kernel."
	::= { syslogtrap 2 }

tscSltPid OBJECT-TYPE
	SYNTAX  INTEGER
	ACCESS  read-only
	STATUS  optional
	DESCRIPTION
		"The process id of the facility or 0."
	::= { syslogtrap 3 }

tscSltHostname OBJECT-TYPE
	SYNTAX  DisplayString
	ACCESS  read-only
	STATUS  optional
	DESCRIPTION
		"The hostname of the device reporting the message."
	::= { syslogtrap 4 }

tscSltMessage OBJECT-TYPE
	SYNTAX  DisplayString
	ACCESS  read-only
	STATUS  optional
	DESCRIPTION
		"The message from log message (stripped of time
		stamp, facility, and hostname"
	::= { syslogtrap 5 }

--
-- Trap Definitions
--

tscSltTrap TRAP-TYPE
	ENTERPRISE  syslogtrap
	VARIABLES   { 
		tscSltLogMessage,
		tscSltFacility,
		tscSltPid,
		tscSltHostname,
		tscSltMessage
		}
	DESCRIPTION
		"Reporting a syslog event."
		--#SUMMARY "%s"
		--#ARGUMENTS { 0 }
		--#SEVERITY CRITICAL
		--#SLOTMAP origin $A
		--#SLOTMAP facility $V2
		--#SLOTMAP pid $V3
		--#SLOTMAP message  $V5
	::= 1

----------------------------------------------
----------------------------------------------
--
-- xmon
--
----------------------------------------------
----------------------------------------------

--
-- Variables used by traps
--

--
-- Trap Definitions
--

-- At this time, xmon traps are dynamically created within user configuration files that
-- generate traps for thresholds and exceptions.

-- As a rule of thumb, this is how the xmon traps are organized:
--
-- User Defined (No overlap from Tavve use)	   1 -  999
-- Fault Exceptions				1000 - 1999
-- Configuration Exceptions			2000 - 2999
-- Accounting Exceptions			3000 - 3999
-- Performance Exceptions			4000 - 4999
-- Security Exceptions				5000 - 5999
-- Network Resource Thresholds			6000 - 6999
-- System Resource Thresholds			7000 - 7999
-- Application Resource Thresholds		8000 - 8999
-- Environmental Thresholds			9000 - 9999

-- End of file

END
