-- extracted from draft-ietf-eos-snmpxproto-mib-03.txt
-- at Fri Aug 30 06:10:05 2002

   SNMP-EXTENDED-PROTOCOL-MIB DEFINITIONS ::= BEGIN

   IMPORTS
      MODULE-IDENTITY, OBJECT-TYPE,
      Unsigned32, mib-2                   FROM SNMPv2-SMI
      IANASnmpProtocol                    FROM IANA-SNMP-PROTOCOL-TC
      MODULE-COMPLIANCE, OBJECT-GROUP     FROM SNMPv2-CONF;

     snmpXProtoMIB MODULE-IDENTITY
         LAST-UPDATED "200202200000Z"
         ORGANIZATION "IETF Evolution of SNMP Working Group"
         CONTACT-INFO
                 "   Sharon Chisholm
                     Nortel Networks
                     PO Box 3511 Station C
                     Ottawa, Ont.  K1Y 4H7
                     Canada
                     schishol@nortelnetworks.com"
         DESCRIPTION
                 "The MIB module describes the SNMP protocol
                 operations supported by this SNMP entity."
         REVISION    "200202200000Z"
         DESCRIPTION
             "Initial version, published as RFC XXXX."

         ::= { mib-2 1 }



   snmpXProtoObjects OBJECT IDENTIFIER ::= { snmpXProtoMIB 1 }

   snmpXProtoConformance OBJECT IDENTIFIER ::= { snmpXProtoMIB 3 }

   snmpXProtoCompliances OBJECT IDENTIFIER
                     ::= { snmpXProtoConformance 1 }

   snmpXProtoSystem OBJECT-TYPE
      SYNTAX     IANASnmpProtocol
      MAX-ACCESS read-only
      STATUS     current
      DESCRIPTION
          "The standard SNMP protocol operations supported
          by this SNMP entity on all objects with appropriate
          access permissions. For example, SNMP sets may be
          included in this list, even if the MAX-ACCESS of
          some objects is read-only."
      ::= { snmpXProtoObjects 1 }

   -- Extra Protocol Support per SubTree

     snmpXProtoSubTreeTable OBJECT-TYPE
        SYNTAX      SEQUENCE OF SnmpXProtoSubTreeEntry
        MAX-ACCESS  not-accessible
        STATUS      current
        DESCRIPTION "A table of additional SNMP protocol operations
        supported on objects in the specific subTrees."
        ::= { snmpXProtoObjects 2 }

     snmpXProtoSubTreeEntry OBJECT-TYPE
        SYNTAX      SnmpXProtoSubTreeEntry
        MAX-ACCESS  not-accessible
        STATUS      current
        DESCRIPTION "A MIB subtree that supports additional
                     protocol operations above that specified
                     in snmpXProtoSystem."
        INDEX       { snmpXProtoSubTreeIndex }
        ::= { snmpXProtoSubTreeTable 1 }

     SnmpXProtoSubTreeEntry ::= SEQUENCE {
        snmpXProtoSubTreeIndex            Unsigned32,
        snmpXProtoSubTreeBranch           OBJECT IDENTIFIER,
        snmpXProtoSubTreeFeature          IANASnmpProtocol
        }

     snmpXProtoSubTreeIndex OBJECT-TYPE
        SYNTAX      Unsigned32(1..4294967295)
        MAX-ACCESS  not-accessible
        STATUS      current
        DESCRIPTION "An arbitrary index into this table."
        ::= { snmpXProtoSubTreeEntry 1 }

     snmpXProtoSubTreeBranch OBJECT-TYPE
        SYNTAX      OBJECT IDENTIFIER
        MAX-ACCESS  read-only
        STATUS      current
        DESCRIPTION
           "The OID that identifies this MIB SubTree."
        ::= { snmpXProtoSubTreeEntry 2 }


     snmpXProtoSubTreeFeature OBJECT-TYPE
        SYNTAX     IANASnmpProtocol
        MAX-ACCESS read-only
        STATUS     current
        DESCRIPTION
            "The standard SNMP protocol operations supported
            by this subTree above and beyond protocol
            support as indicated by snmpXProtoSystem."
        ::= { snmpXProtoSubTreeEntry 3 }

   snmpXProtoCompliance MODULE-COMPLIANCE
         STATUS  current
         DESCRIPTION
             "The compliance statement for systems supporting
             the snmpXProto MIB."
         MODULE -- this module
             MANDATORY-GROUPS {
              snmpXProtoGroup
             }
      ::= { snmpXProtoCompliances 1 }

   snmpXProtoGroups OBJECT IDENTIFIER ::= { snmpXProtoConformance 2 }	

   snmpXProtoGroup OBJECT-GROUP
      OBJECTS {
              snmpXProtoSystem
         }
       STATUS   current
       DESCRIPTION
                  "Standard snmpXProto group."
       ::= { snmpXProtoGroups 1}

   snmpXProtoSubTreeGroup OBJECT-GROUP
      OBJECTS {
             snmpXProtoSubTreeFeature,
             snmpXProtoSubTreeBranch
         }
       STATUS   current
       DESCRIPTION
                  "SubTree specific snmpXProto group."
       ::= { snmpXProtoGroups 2}


   END

-- 
--   Copyright (C) The Internet Society (2002). All Rights Reserved.
-- 
--   This document and translations of it may be copied and furnished to
--   others, and derivative works that comment on or otherwise explain it
--   or assist in its implementation may be prepared, copied, published
--   and distributed, in whole or in part, without restriction of any kind,
--   provided that the above copyright notice and this paragraph are
--   included on all such copies and derivative works.  However, this
--   document itself may not be modified in any way, such as by removing
--   the copyright notice or references to the Internet Society or other
--   Internet organizations, except as needed for the  purpose of
--   developing Internet standards in which case the procedures for
--   copyrights defined in the Internet Standards process must be followed,
--   or as required to translate it into languages other than English.
-- 
--   The limited permissions granted above are perpetual and will not be
--   revoked by the Internet Society or its successors or assigns.
-- 
--   This document and the information contained herein is provided on an
--   "AS IS" basis and THE INTERNET SOCIETY AND THE INTERNET ENGINEERING
--   TASK FORCE DISCLAIMS ALL WARRANTIES, EXPRESS OR IMPLIED, INCLUDING BUT
--   NOT LIMITED TO ANY WARRANTY THAT THE USE OF THE INFORMATION HEREIN
--   WILL NOT INFRINGE ANY RIGHTS OR ANY IMPLIED WARRANTIES OF
--   MERCHANTABILITY OR FITNESS FOR A PARTICULAR PURPOSE.
