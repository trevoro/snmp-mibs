WEBMGMTEXT-MIB 

   --FORCE-INCLUDE <mib.h>
   --FORCE-INCLUDE <snmpdefs.h>
   --FORCE-INCLUDE <snmpstat.h>
   --FORCE-INCLUDE "mibproto.h"
 
	DEFINITIONS ::= BEGIN

	IMPORTS
		MODULE-IDENTITY, OBJECT-TYPE, IpAddress
			FROM SNMPv2-SMI
		webMgmtExt
			FROM APENT-MIB;

--WEBMGMTEXT MIB

    apWebMgmtExtMib MODULE-IDENTITY
	   LAST-UPDATED "9710092000Z" -- Thu October 9 20:00:00 EST 1997
	   ORGANIZATION "ArrowPoint Communications Inc."
	   CONTACT-INFO
	   "                      
	   Postal:               ArrowPoint Communications Inc.
				                 50 Nagog Park
				                 Acton, Massachusetts 01720
	   Tel:                   +1 978-206-3000  option 1
	   E-Mail:                support@arrowpoint.com"
       DESCRIPTION
	  "The MIB module used to describe the ArrowPoint Communications
	  web management subsystem"
      ::= { webMgmtExt 1}


apWebMgmtStatus OBJECT-TYPE
	SYNTAX          INTEGER {
							enable(1),
							disable(2)
							}
	MAX-ACCESS      read-write
	STATUS          current
	DESCRIPTION     "The status of web management for this system."
	DEFVAL { disable }
	::= {webMgmtExt 2}

apWebMgmtAccess OBJECT-TYPE
	SYNTAX          INTEGER {
							any(1),
							limited(2)
							}
	MAX-ACCESS      read-write
	STATUS          current
	DESCRIPTION     
		"The type of access to this system.  Any indicates any IP address, limited means that
		 only specific IP addresses may have access."
	DEFVAL { limited }
	::= {webMgmtExt 3}

apWebMgmtIpAddr1 OBJECT-TYPE
	SYNTAX          IpAddress
	MAX-ACCESS      read-write
	STATUS          current
	DESCRIPTION     "The IpAddr of a client allowed access to web management."
	::= {webMgmtExt 4}

apWebMgmtIpAddr2 OBJECT-TYPE
	SYNTAX          IpAddress
	MAX-ACCESS      read-write
	STATUS          current
	DESCRIPTION     "The IpAddr of a client allowed access to web management."
	::= {webMgmtExt 5}

apWebMgmtIpAddr3 OBJECT-TYPE
	SYNTAX          IpAddress
	MAX-ACCESS      read-write
	STATUS          current
	DESCRIPTION     "The IpAddr of a client allowed access to web management."
	::= {webMgmtExt 6}

apWebMgmtIpAddr4 OBJECT-TYPE
	SYNTAX          IpAddress
	MAX-ACCESS      read-write
	STATUS          current
	DESCRIPTION     "The IpAddr of a client allowed access to web management."
	::= {webMgmtExt 7}

apWebMgmtIpAddr5 OBJECT-TYPE
	SYNTAX          IpAddress
	MAX-ACCESS      read-write
	STATUS          current
	DESCRIPTION     "The IpAddr of a client allowed access to web management."
	::= {webMgmtExt 8}

END
