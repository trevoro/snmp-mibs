-- *****************************************************************
-- tiaranet-chassis.mib:  Tiara Networks System MIB file
--
-- April,1st 1998, Shyla
--
--
-- Copyright (c) 1999-2000 by Tiara Networks, Inc.
-- All rights reserved.
-- 
-- *****************************************************************
--
TIARA-NETWORKS-CHASSIS-MIB DEFINITIONS ::= BEGIN

IMPORTS
        MODULE-IDENTITY, OBJECT-TYPE         FROM SNMPv2-SMI
        DisplayString                        FROM SNMPv2-TC
        tiaraMgmt                            FROM TIARA-NETWORKS-SMI;

tiaraChassisMib MODULE-IDENTITY 
        LAST-UPDATED "0001270000Z"
        ORGANIZATION "Tiara Networks, Inc."
        CONTACT-INFO
                "       Tiara Networks
                        Customer Support

                        525 Race Street, Suite 100,
                        San Jose, CA 95126
                        USA

                        Tel: +1 408-216-4700
                        Fax: +1 408-216-4701

                        E-mail: support@tiaranetworks.com"

        DESCRIPTION
                "Listing and brief description of Tiara Networks product model numbers."
        REVISION      "0001270000Z"
        DESCRIPTION
                "Initial version of this MIB module."
        ::= { tiaraMgmt 2 }

--
-- chassisObjects group
--

-- Brief description of Tiara product model numbers -
--
--              Tiara 1200 - 4 T1s, AC, Fans.
--              Tiara 1400 - 8 T1s, AC, Fans.
--              Tiara 1450 - 8 T1s, 1 HSSI, AC, Fans.
--              Tiara 6100 - 8 T1s, AC/DC, Fans & Filters
--              Tiara 6200 - 16 T1s, AC/DC, Fans & Filters
--              Tiara 6300 - 1 CT3, AC/DC, Fans & Filters
--              Tiara 7011 - 1 CT3, 1 HSSI, AC/DC, Fans & Filters.
--              Tiara 7030 - 1 CT3, 1 DS3, AC/DC, Fans & Filters.
--

chassisType OBJECT-TYPE
        SYNTAX          DisplayString (SIZE (0..32)) 
        MAX-ACCESS      read-only
        STATUS          current
        DESCRIPTION     "The chassis type."
        ::= { tiaraChassisMib 1 }

chassisSerialNumber OBJECT-TYPE
        SYNTAX          DisplayString (SIZE (0..30))
        MAX-ACCESS      read-only
        STATUS          current
        DESCRIPTION     "The serial number of the chassis."
        ::= { tiaraChassisMib 2 }

END
