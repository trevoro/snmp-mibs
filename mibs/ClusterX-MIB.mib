--******************************************************************************
--
-- (c) 1998, 1999 VERITAS Software, Corp.  All rights reserved.
--
--  ClusterX SNMP Management Information Base
--
--  The information in this document is subject to change without notice.
--
--  The VERITAS enterprise number is:  1302
--
--  The ASN.1 object identifier prefix to the VERITAS enterprise is:
--  1.3.6.1.4.1.1302
--
--******************************************************************************
--  Summary of ClusterX Management Information Base
--******************************************************************************
--
--  VERITAS  (1.3.6.1.4.1.1302)
--
--    ClusterX Group (1.3.6.1.4.1.1302.3.7)
--
--      clxMibStats Group                   (ClusterX.1)
--        clxMibStatsMajRev                   (ClusterX.1.1)
--        clxMibStatsMinRev                   (ClusterX.1.2)
--        clxMibStatsVendorName               (ClusterX.1.3)
--
--      clxTrapData Group                   (ClusterX.2)
--        clxTrapDataString01                 (ClusterX.2.1)
--        clxTrapDataNodeName                 (ClusterX.2.2)
--        clxTrapDataClusterName              (ClusterX.2.3)
--        clxTrapDataResourceName             (ClusterX.2.4)
--        clxTrapDataResourceType             (ClusterX.2.5)
--        clxTrapDataSeverityValue            (ClusterX.2.6)
--        clxTrapDataNetwork                  (ClusterX.2.7)
--        clxTrapEventDate                    (ClusterX.2.8)
--        clxTrapEventTime                    (ClusterX.2.9)
--        clxTrapEventSource                  (ClusterX.2.10)
--        clxTrapEventCategory                (ClusterX.2.11)
--        clxTrapEventID                      (ClusterX.2.12)
--        clxTrapEventUser                    (ClusterX.2.13)
--        clxTrapEventComputer                (ClusterX.2.14)
--        clxTrapDataNetworkName              (ClusterX.2.15)
--        clxTrapDataWLBSNodeName             (ClusterX.2.16)
--        clxTrapDataWLBSClusterName          (ClusterX.2.17)
--        clxTrapDataWLBSHostID               (ClusterX.2.18)
--        clxTrapDataPortNumber               (ClusterX.2.19)
--        clxTrapDataApplicationName          (ClusterX.2.20)
--        clxTrapDataApplicationFailureReason (ClusterX.2.21)
--        clxTrapDataApplicationFailureAction (ClusterX.2.22)
--        clxTrapDataApplicationOnLineAction  (ClusterX.2.23)
--
--      clxUptimeStats Group                (ClusterX.3)
--
--      clxAvailabilityStats Group          (ClusterX.4)
--
--******************************************************************************

ClusterX-MIB DEFINITIONS ::= BEGIN

  IMPORTS
    enterprises    FROM RFC1155-SMI
    DisplayString  FROM RFC1213-MIB
    OBJECT-TYPE    FROM RFC-1212
    TRAP-TYPE      FROM RFC-1215;

  veritassoftware          OBJECT IDENTIFIER ::= { enterprises 1302 }
  veritasproducts          OBJECT IDENTIFIER ::= { veritassoftware 3 }

    clusterX               OBJECT IDENTIFIER ::= { veritasproducts 7 }
      clxMibStats          OBJECT IDENTIFIER ::= { clusterX 1 }
      clxTrapData          OBJECT IDENTIFIER ::= { clusterX 2 }
--      clxUptimeStats       OBJECT IDENTIFIER ::= { clusterX 3 }
--      clxAvailabilityStats OBJECT IDENTIFIER ::= { clusterX 4 }

--******************************************************************************
--  clxMibStats Information
--******************************************************************************

clxMibStatsMajRev OBJECT-TYPE
  SYNTAX  INTEGER (1..65535)
  ACCESS  read-only
  STATUS  mandatory
  DESCRIPTION
    "The major revision level of the ClusterX SNMP extension agent MIB."
  ::= { clxMibStats 1 }

clxMibStatsMinRev OBJECT-TYPE
  SYNTAX  INTEGER (1..65535)
  ACCESS  read-only
  STATUS  mandatory
  DESCRIPTION
    "The minor revision level of the ClusterX SNMP extension agent MIB."
  ::= { clxMibStats 2 }

clxMibStatsVendorName OBJECT-TYPE
  SYNTAX  DisplayString
  ACCESS  read-only
  STATUS  mandatory
  DESCRIPTION
    "The name of the vendor supplying the ClusterX SNMP extension agent MIB."
  ::= { clxMibStats 3 }

--******************************************************************************
--  clxTrapData Information
--******************************************************************************

clxTrapDataString01 OBJECT-TYPE
  SYNTAX  DisplayString
  ACCESS  not-accessible
  STATUS  mandatory
  DESCRIPTION
    "Custom string 1 (Varbind #1) for ClusterX trap."
  ::= { clxTrapData 1 }

clxTrapDataNodeName OBJECT-TYPE
  SYNTAX  DisplayString
  ACCESS  not-accessible
  STATUS  mandatory
  DESCRIPTION
    "Name of the MSCS Node."
  ::= { clxTrapData  2 }

clxTrapDataClusterName OBJECT-TYPE
  SYNTAX  DisplayString
  ACCESS  not-accessible
  STATUS  mandatory
  DESCRIPTION
    "Name of the MSCS Cluster."
  ::= { clxTrapData   3 }

clxTrapDataResourceName OBJECT-TYPE
  SYNTAX  DisplayString
  ACCESS  not-accessible
  STATUS  mandatory
  DESCRIPTION
    "Name of the MSCS Resource."
  ::= { clxTrapData 4 }

clxTrapDataResourceType OBJECT-TYPE
  SYNTAX  DisplayString
  ACCESS  not-accessible
  STATUS  mandatory
  DESCRIPTION
    "Type of the MSCS Resource."
  ::= { clxTrapData 5 }

clxTrapDataSeverityValue OBJECT-TYPE
  SYNTAX INTEGER
  {
     info(0),                -- Information
     warning(1),             -- Warning
     error(2)                -- Error
  }
  ACCESS    read-only
  STATUS    mandatory
  DESCRIPTION
     "The severity value type."
  ::= {clxTrapData 6 }

clxTrapDataNetwork OBJECT-TYPE
  SYNTAX  DisplayString
  ACCESS  not-accessible
  STATUS  mandatory
  DESCRIPTION
    "Network Info."
  ::= {clxTrapData 7 }

clxTrapEventDate OBJECT-TYPE
  SYNTAX  DisplayString
  ACCESS  not-accessible
  STATUS  mandatory
  DESCRIPTION
    "Date of the Event created in NT event log."
  ::= { clxTrapData 8 }


clxTrapEventTime OBJECT-TYPE
  SYNTAX  DisplayString
  ACCESS  not-accessible
  STATUS  mandatory
  DESCRIPTION
    "Time of the Event created in NT event log."
  ::= { clxTrapData 9 }


clxTrapEventSource OBJECT-TYPE
  SYNTAX  DisplayString
  ACCESS  not-accessible
  STATUS  mandatory
  DESCRIPTION
    "Source of the Event created in NT event log."
  ::= { clxTrapData 10 }

clxTrapEventCategory OBJECT-TYPE
  SYNTAX  DisplayString
  ACCESS  not-accessible
  STATUS  mandatory
  DESCRIPTION
    "Category of the Event created in NT event log."
  ::= { clxTrapData 11 }

clxTrapEventID OBJECT-TYPE
  SYNTAX  DisplayString
  ACCESS  not-accessible
  STATUS  mandatory
  DESCRIPTION
    "ID of the Event created in NT event log."
  ::= { clxTrapData 12 }

clxTrapEventUser OBJECT-TYPE
  SYNTAX  DisplayString
  ACCESS  not-accessible
  STATUS  mandatory
  DESCRIPTION
    "User which created the event in NT event log."
  ::= { clxTrapData 13 }

clxTrapEventComputer OBJECT-TYPE
  SYNTAX  DisplayString
  ACCESS  not-accessible
  STATUS  mandatory
  DESCRIPTION
    "Computer which created Event in NT event log."
  ::= { clxTrapData 14 }

clxTrapDataNetworkName OBJECT-TYPE
  SYNTAX  DisplayString
  ACCESS  not-accessible
  STATUS  mandatory
  DESCRIPTION
    "Network Name."
  ::= { clxTrapData 15 }

clxTrapDataWLBSNodeName OBJECT-TYPE
  SYNTAX  DisplayString
  ACCESS  not-accessible
  STATUS  mandatory
  DESCRIPTION
    "Name of the WLBS Node."
  ::= { clxTrapData 16 }

clxTrapDataWLBSClusterName OBJECT-TYPE
  SYNTAX  DisplayString
  ACCESS  not-accessible
  STATUS  mandatory
  DESCRIPTION
    "Name of the WLBS Cluster."
  ::= { clxTrapData 17 }

clxTrapDataWLBSHostID OBJECT-TYPE
  SYNTAX  DisplayString
  ACCESS  not-accessible
  STATUS  mandatory
  DESCRIPTION
    "Host ID of WLBS node."
  ::= { clxTrapData 18 }

clxTrapDataPortNumber OBJECT-TYPE
  SYNTAX  DisplayString
  ACCESS  not-accessible
  STATUS  mandatory
  DESCRIPTION
    "TCP or UDP port number."
  ::= { clxTrapData 19 }

clxTrapDataApplicationName OBJECT-TYPE
  SYNTAX  DisplayString
  ACCESS  not-accessible
  STATUS  mandatory
  DESCRIPTION
    "Name of application."
  ::= { clxTrapData 20 }

clxTrapDataApplicationFailureReason OBJECT-TYPE
  SYNTAX  DisplayString
  ACCESS  not-accessible
  STATUS  mandatory
  DESCRIPTION
    "Reason application is classified as failed."
  ::= { clxTrapData 21 }

clxTrapDataApplicationFailureAction OBJECT-TYPE
  SYNTAX  DisplayString
  ACCESS  not-accessible
  STATUS  mandatory
  DESCRIPTION
    "Action taken after application is classified as failed."
  ::= { clxTrapData 22 }

clxTrapDataApplicationOnLineAction OBJECT-TYPE
  SYNTAX  DisplayString
  ACCESS  not-accessible
  STATUS  mandatory
  DESCRIPTION
    "Action taken after application is classified as on-line."
  ::= { clxTrapData 23 }

--******************************************************************************
--  clxUptimeStats Information
--******************************************************************************

--******************************************************************************
--  clxAvailabilityStats Information
--******************************************************************************

--******************************************************************************
--  General Traps
--******************************************************************************

clusterXTrapStr TRAP-TYPE
  ENTERPRISE   clusterX
  VARIABLES    { clxTrapDataString01 }
  DESCRIPTION
    "Generic SNMP trap generated by ClusterX applications and services.
     Varbind #1: Custom string"
  ::= 1

--******************************************************************************
--  ClusterX/MSCS Traps
--
--  Numbers Used: 2 - 9
--******************************************************************************

clusterXTrapNodeFail TRAP-TYPE
  ENTERPRISE   clusterX
  VARIABLES    { clxTrapDataClusterName, clxTrapDataNodeName }
  DESCRIPTION
    "This trap is sent when ClusterX detects the failure of a node in an MSCS cluster.
     Varbind #1: Cluster Name
     Varbind #2: Node Name"
  --#SEVERITY MINOR
  ::= 2

clusterXTrapClusterFail TRAP-TYPE
  ENTERPRISE   clusterX
  VARIABLES    { clxTrapDataClusterName }
  DESCRIPTION
    "This trap is sent when ClusterX detects the failure of an MSCS cluster.
     Varbind #1: Cluster Name"
  --#SEVERITY CRITICAL
  ::= 3

clusterXTrapResourceFail TRAP-TYPE
  ENTERPRISE   clusterX
  VARIABLES    { clxTrapDataClusterName, clxTrapDataNodeName, clxTrapDataResourceName }
  DESCRIPTION
    "This trap is sent when ClusterX detects the failure of a resource on an MSCS cluster.
     Varbind #1: Cluster Name
     Varbind #2: Node Name
     Varbind #3: Resource Name"
  --#SEVERITY INFORMATIONAL
  ::= 4

clusterXTrapNodeJoins TRAP-TYPE
  ENTERPRISE   clusterX
  VARIABLES    { clxTrapDataClusterName, clxTrapDataNodeName }
  DESCRIPTION
    "This trap is sent when ClusterX detects that a node has joined or rejoined an MSCS cluster.
     Varbind #1: Cluster Name
     Varbind #2: Node Name"
  --#SEVERITY INFORMATIONAL
  ::= 5

clusterXTrapNetworkFail TRAP-TYPE
  ENTERPRISE   clusterX
  VARIABLES    { clxTrapDataString01, clxTrapDataNetworkName }
  DESCRIPTION
    "This trap is sent when ClusterX detects the failure of the private or public cluster interconnects on an MSCS 
     cluster.
     Varbind #1: Custom string, containing information about the network failure
     Varbind #2: Network Name"
  --#SEVERITY MAJOR
  ::= 6

clusterXTrapNormalClusterServiceLog TRAP-TYPE
  ENTERPRISE   clusterX
  VARIABLES    { clxTrapEventDate, clxTrapEventTime, clxTrapEventSource, clxTrapEventCategory, clxTrapEventID, clxTrapEventUser, clxTrapEventComputer }
  DESCRIPTION
    "This trap is generated when ClusterX detects that MSCS has written an informational entry in the Windows NT 
     Event Log on a managed cluster.
     Varbind #1: Event Creation Date
     Varbind #2: Event Creation Time
     Varbind #3: Event Source
     Varbind #4: Event Category
     Varbind #5: Event ID
     Varbind #6: Event Creation User
     Varbind #7: Event Creation Computer"
  --#SEVERITY INFORMATIONAL
  ::= 7

clusterXTrapWarningClusterServiceLog TRAP-TYPE
  ENTERPRISE   clusterX
  VARIABLES    { clxTrapEventDate, clxTrapEventTime, clxTrapEventSource, clxTrapEventCategory, clxTrapEventID, clxTrapEventUser, clxTrapEventComputer }
  DESCRIPTION
    "This trap is generated when ClusterX detects that MSCS has written a warning entry in the Windows NT 
     Event Log on a managed cluster.
     Varbind #1: Event Creation Date
     Varbind #2: Event Creation Time
     Varbind #3: Event Source
     Varbind #4: Event Category
     Varbind #5: Event ID
     Varbind #6: Event Creation User
     Varbind #7: Event Creation Computer"
  --#SEVERITY WARNING
  ::= 8

clusterXTrapCriticalClusterServiceLog TRAP-TYPE
  ENTERPRISE   clusterX
  VARIABLES    { clxTrapEventDate, clxTrapEventTime, clxTrapEventSource, clxTrapEventCategory, clxTrapEventID, clxTrapEventUser, clxTrapEventComputer }
  DESCRIPTION
    "This trap is generated when ClusterX detects that MSCS has written an error entry in the Windows NT 
     Event Log on a managed cluster.
     Varbind #1: Event Creation Date
     Varbind #2: Event Creation Time
     Varbind #3: Event Source
     Varbind #4: Event Category
     Varbind #5: Event ID
     Varbind #6: Event Creation User
     Varbind #7: Event Creation Computer"
  --#SEVERITY CRITICAL
  ::= 9

--******************************************************************************
--  ClusterX/WLBS Traps
--
--  Numbers Used: 10 - 24
--******************************************************************************

clusterXWLBSTrapApplicationFail TRAP-TYPE
  ENTERPRISE   clusterX
  VARIABLES    { clxTrapDataWLBSClusterName, clxTrapDataWLBSNodeName, clxTrapDataApplicationName, clxTrapDataApplicationFailureReason, clxTrapDataApplicationFailureAction }
  DESCRIPTION
    "This trap is sent when ClusterX detects the failure of an
     application on a monitored node.
     Varbind #1: Cluster Name
     Varbind #2: Node Name
     Varbind #3: Application Name
     Varbind #4: Application Failure Reason
     Varbind #5: Application Failure Action"
  --#SEVERITY CRITICAL
  ::= 10

clusterXWLBSTrapEventLogNormal TRAP-TYPE
  ENTERPRISE   clusterX
  VARIABLES    { clxTrapEventDate, clxTrapEventTime, clxTrapEventSource, clxTrapEventCategory, clxTrapEventID, clxTrapEventUser, clxTrapEventComputer }
  DESCRIPTION
    "This trap is generated when ClusterX detects that WLBS has written an
     informational entry in the Windows NT Event Log on a managed cluster.
     Varbind #1: Event Creation Date
     Varbind #2: Event Creation Time
     Varbind #3: Event Source
     Varbind #4: Event Category
     Varbind #5: Event ID
     Varbind #6: Event Creation User
     Varbind #7: Event Creation Computer"
  --#SEVERITY INFORMATIONAL
  ::= 11

clusterXWLBSTrapEventLogWarning TRAP-TYPE
  ENTERPRISE   clusterX
  VARIABLES    { clxTrapEventDate, clxTrapEventTime, clxTrapEventSource, clxTrapEventCategory, clxTrapEventID, clxTrapEventUser, clxTrapEventComputer }
  DESCRIPTION
    "This trap is generated when ClusterX detects that WLBS has written a
     warning entry in the Windows NT Event Log on a managed cluster.
     Varbind #1: Event Creation Date
     Varbind #2: Event Creation Time
     Varbind #3: Event Source
     Varbind #4: Event Category
     Varbind #5: Event ID
     Varbind #6: Event Creation User
     Varbind #7: Event Creation Computer"
  --#SEVERITY WARNING
  ::= 12

clusterXWLBSTrapEventLogCritical TRAP-TYPE
  ENTERPRISE   clusterX
  VARIABLES    { clxTrapEventDate, clxTrapEventTime, clxTrapEventSource, clxTrapEventCategory, clxTrapEventID, clxTrapEventUser, clxTrapEventComputer }
  DESCRIPTION
    "This trap is generated when ClusterX detects that WLBS has written an
     error entry in the Windows NT Event Log on a managed cluster.
     Varbind #1: Event Creation Date
     Varbind #2: Event Creation Time
     Varbind #3: Event Source
     Varbind #4: Event Category
     Varbind #5: Event ID
     Varbind #6: Event Creation User
     Varbind #7: Event Creation Computer"
  --#SEVERITY CRITICAL
  ::= 13

clusterXWLBSTrapSuspended TRAP-TYPE
  ENTERPRISE   clusterX
  VARIABLES    { clxTrapDataWLBSClusterName, clxTrapDataWLBSNodeName }
  DESCRIPTION
    "This trap is sent when ClusterX detects that WLBS cluster
     operation control has been suspended.
     Varbind #1: Cluster Name
     Varbind #2: Node Name"
  --#SEVERITY WARNING
  ::= 14

clusterXWLBSTrapResumed TRAP-TYPE
  ENTERPRISE   clusterX
  VARIABLES    { clxTrapDataWLBSClusterName, clxTrapDataWLBSNodeName }
  DESCRIPTION
    "This trap is sent when ClusterX detects that WLBS cluster
     operation control has been resumed.
     Varbind #1: Cluster Name
     Varbind #2: Node Name"
  --#SEVERITY INFORMATIONAL
  ::= 15

clusterXWLBSTrapStarted TRAP-TYPE
  ENTERPRISE   clusterX
  VARIABLES    { clxTrapDataWLBSClusterName, clxTrapDataWLBSNodeName }
  DESCRIPTION
    "This trap is sent when ClusterX detects that WLBS cluster
     operations have started.
     Varbind #1: Cluster Name
     Varbind #2: Node Name"
  --#SEVERITY INFORMATIONAL
  ::= 16

clusterXWLBSTrapStopped TRAP-TYPE
  ENTERPRISE   clusterX
  VARIABLES    { clxTrapDataWLBSClusterName, clxTrapDataWLBSNodeName }
  DESCRIPTION
    "This trap is sent when ClusterX detects that WLBS cluster
     operations have stopped.
     Varbind #1: Cluster Name
     Varbind #2: Node Name"
  --#SEVERITY WARNING
  ::= 17

clusterXWLBSTrapDrainStopped TRAP-TYPE
  ENTERPRISE   clusterX
  VARIABLES    { clxTrapDataWLBSClusterName, clxTrapDataWLBSNodeName }
  DESCRIPTION
    "This trap is sent when ClusterX detects that WLBS cluster
     operations have started draining; once drained, cluster
     operations will stop.
     Varbind #1: Cluster Name
     Varbind #2: Node Name"
  --#SEVERITY WARNING
  ::= 18

clusterXWLBSTrapConverged TRAP-TYPE
  ENTERPRISE   clusterX
  VARIABLES    { clxTrapDataWLBSClusterName, clxTrapDataWLBSNodeName }
  DESCRIPTION
    "This trap is sent when ClusterX detects that a node in
     a WLBS cluster has converged.
     Varbind #1: Cluster Name
     Varbind #2: Node Name"
  --#SEVERITY INFORMATIONAL
  ::= 19

clusterXWLBSTrapEnabled TRAP-TYPE
  ENTERPRISE   clusterX
  VARIABLES    { clxTrapDataWLBSClusterName, clxTrapDataWLBSNodeName, clxTrapDataPortNumber }
  DESCRIPTION
    "This trap is sent when ClusterX detects that WLBS traffic
     handling for the rule containing the specified port number
     has been enabled.
     Varbind #1: Cluster Name
     Varbind #2: Node Name
     Varbind #3: Port Number or 'ALL'"
  --#SEVERITY INFORMATIONAL
  ::= 20

clusterXWLBSTrapDisabled TRAP-TYPE
  ENTERPRISE   clusterX
  VARIABLES    { clxTrapDataWLBSClusterName, clxTrapDataWLBSNodeName, clxTrapDataPortNumber }
  DESCRIPTION
    "This trap is sent when ClusterX detects that WLBS traffic
     handling for the rule containing the specified port number
     has been disabled for ALL traffic.
     Varbind #1: Cluster Name
     Varbind #2: Node Name
     Varbind #3: Port Number or 'ALL'"
  --#SEVERITY WARNING
  ::= 21

clusterXWLBSTrapDrained TRAP-TYPE
  ENTERPRISE   clusterX
  VARIABLES    { clxTrapDataWLBSClusterName, clxTrapDataWLBSNodeName, clxTrapDataPortNumber }
  DESCRIPTION
    "This trap is sent when ClusterX detects that WLBS traffic
     handling for the rule containing the specified port number
     has been disabled for NEW traffic.
     Varbind #1: Cluster Name
     Varbind #2: Node Name
     Varbind #3: Port Number or 'ALL'"
  --#SEVERITY WARNING
  ::= 22

clusterXWLBSTrapApplicationOnLine TRAP-TYPE
  ENTERPRISE   clusterX
  VARIABLES    { clxTrapDataWLBSClusterName, clxTrapDataWLBSNodeName, clxTrapDataApplicationName, clxTrapDataApplicationOnLineAction }
  DESCRIPTION
    "This trap is sent when ClusterX detects that an application
     has come on line on a monitored node.
     Varbind #1: Cluster Name
     Varbind #2: Node Name
     Varbind #3: Application Name
     Varbind #4: Action Taken"
  --#SEVERITY INFORMATIONAL
  ::= 23

clusterXWLBSTrapReloaded TRAP-TYPE
  ENTERPRISE   clusterX
  VARIABLES    { clxTrapDataWLBSClusterName, clxTrapDataWLBSNodeName }
  DESCRIPTION
    "This trap is sent when ClusterX detects that WLBS cluster
     parameters have been reloaded from the registry.
     Varbind #1: Cluster Name
     Varbind #2: Node Name"
  --#SEVERITY WARNING
  ::= 24

END
