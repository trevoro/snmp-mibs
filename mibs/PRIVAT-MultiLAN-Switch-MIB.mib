-- *************************************************************************
-- *                                                                       *
-- *                                                                       *
-- *                       Richard Hirschmann GmbH & Co.                   *
-- *                                                                       *
-- *                              P.O. Box 1649                            *
-- *                            D-72606 Nuertingen                         *
-- *                                                                       *
-- *                          Stuttgarter Str. 45-51                       *
-- *                         D-72654 Neckartenzlingen                      *
-- *                                                                       *
-- *                                 Germany                               *
-- *                                                                       *
-- *                                                                       *
-- *                    MultiLAN Switch MIB Version 1.10                   *
-- *                                                                       *
-- *             Dies ist die SNMP Private MIB fuer den Hirschmann         *
-- *             MultiLAN Switch. Sollten Sie weitere Fragen haben         *
-- *             rufen Sie uns bitte an:                                   *
-- *                                                                       *
-- *                             07127/14-1538                             *
-- *                                                                       *
-- *             This is the SNMP private MIB for the Hirschmann           *
-- *             MultiLAN Switch. If you have any further questions        *
-- *             concerning this MIB feel free to call us:                 *
-- *                                                                       *
-- *                          ???~1538                            *
-- *                                                                       *
-- *             Date:              22.11.1991                             *
-- *             Last Change:       02.08.1995                             *
-- *                                                                       *
-- *************************************************************************
--
-- *************************************************************************
-- *                                                                       *
-- *             C O N F I D E N T I A L   D O C U M E N T                 *
-- *                                                                       *
-- *     Copyright (C) 1993 by Richard Hirschmann GmbH & Co, Germany       *
-- *     For internal use only                                             *
-- *     Do not specify or claim conformance to this document              *
-- *                                                                       *
-- *************************************************************************
--
-- *************************************************************************
-- History:
-- Who     When      What
-- -------------------------------------------------------------------------
-- Hei     02.03.94  Changed Syntax of hirmaBasPortState to DisplayString
--                   according to the hint from A. Schwegmann and after
--                   confirmation by J. Magiera
--
-- Hei     03.03.94  hirmaFilterMode enumerators changed from enabled,
--                   disabled, enabled-inverted to forward, disable,  discard
--                   according PM378.
--
-- Hei     28.03.94  Rework of all DESCRIPTIONs
--
-- Hei     23.06.94  Description of hirmaLoadSaveConIPAddr changed according
--                   the new behaviour of that object class starting with K12.
--                   New enumerator save (3) added to hirmaLoadSaveConAction.
--                   Description adjusted.
--
-- Hei     04.07.94  Naming of hirmaBasPortEthernetSwitching changed to
--                   hirmaBasPortShortDelay according PM 436
--
-- Hei     06.07.94  Enumeration of hirmaMibhCommAccess changed
--
-- Hei     09.09.94  Text aligned to 80 Chars per line
--
-- Gn      19.07.95  hirmaFilterMode
--                   hirmaFilterType
--                     changed
--                   hirmaBasGroupName
--                     new
--                   hirmaBasBridgeMessage
--                     changed from INTEGER to OCTET STRING
--                   hirmaLuiUserName
--                   hirmaLuiUserPasswd
--                   hirmaLuiCommunity
--                     changed from OCTET STRING to DisplayString
--
-- Gn      02.08.95  Description of hirmaBasGroupName changed
--
--
--

PRIVAT-MultiLAN-Switch-MIB   DEFINITIONS ::= BEGIN

IMPORTS
		DisplayString FROM SNMPv2-TC
	IpAddress, TimeTicks, OBJECT-TYPE FROM RFC1155-SMI
	TRAP-TYPE FROM RFC-1215;



MacAddress         ::= OCTET STRING (SIZE (6))

-- IpAddress       ::= OCTET STRING (SIZE (4))

-- DisplayString   ::= OCTET STRING


private               OBJECT IDENTIFIER ::=
                      { iso(1) org(3) dod(6) internet(1) 4 }



enterprises              OBJECT IDENTIFIER ::= { private 1 }
hirschmann               OBJECT IDENTIFIER ::= { enterprises 248 }


multiLANSwitch           OBJECT IDENTIFIER ::= { hirschmann 2 }

bridge1                  OBJECT IDENTIFIER ::= { multiLANSwitch 1 }

bridgemgmt               OBJECT IDENTIFIER ::= { bridge1 1 }
hirmaMibhHandler         OBJECT IDENTIFIER ::= { bridge1 2 }
hirmaUserInterface       OBJECT IDENTIFIER ::= { bridge1 3 }


hirmaBasCapability       OBJECT IDENTIFIER ::= { bridgemgmt 1 }
hirmaSelfTestCapability  OBJECT IDENTIFIER ::= { bridgemgmt 2 }
hirmaFilterCapability    OBJECT IDENTIFIER ::= { bridgemgmt 3 }
hirmaAddrBTCapability    OBJECT IDENTIFIER ::= { bridgemgmt 4 }
hirmaLoadCapability      OBJECT IDENTIFIER ::= { bridgemgmt 5 }


hirmaFlashUpdate         OBJECT IDENTIFIER ::= { hirmaLoadCapability 1}
hirmaLoadSaveConfig      OBJECT IDENTIFIER ::= { hirmaLoadCapability 2}



--      *******************************************
--                HIRMA BASIC BRIDGE TABLE
--      *******************************************
--
--


hirmaBasBridgeTable      OBJECT IDENTIFIER ::= { hirmaBasCapability 1}

hirmaBasBridgeGroupCapacity  OBJECT-TYPE
                SYNTAX       INTEGER
                ACCESS       read-only
                STATUS       mandatory
                DESCRIPTION  "The number of slots
                              of the MultiLAN Switch."
                              ::=  { hirmaBasBridgeTable 1 }

hirmaBasBridgeGroupMap       OBJECT-TYPE
                SYNTAX       INTEGER
                ACCESS       read-only
                STATUS       mandatory
                DESCRIPTION  "This Bitfield represents the current
                              Interface card configuration. The
                              least significant bit indicates the
                              left slot with the number 1.

                              Each interface card (group) of the
                              MultiLAN Switch is represented by a
                              single bit. The value of a bit=1
                              indicates that the group is present."
                ::=  { hirmaBasBridgeTable 2 }


hirmaBasBridgeSoftVersion    OBJECT-TYPE
                SYNTAX       DisplayString
                ACCESS       read-only
                STATUS       mandatory
                DESCRIPTION  "A string that contains information about
                              the software release currently in use"
                ::=  { hirmaBasBridgeTable 3 }

hirmaBasBridgeHardVersion    OBJECT-TYPE
                SYNTAX       DisplayString
                ACCESS       read-only
                STATUS       mandatory
                DESCRIPTION  "A string that contains information about the
                              underlying hardware"
                ::=  { hirmaBasBridgeTable 4 }

hirmaBasBridgeMibVersion     OBJECT-TYPE
                SYNTAX       DisplayString
                ACCESS       read-only
                STATUS       mandatory
                DESCRIPTION  "A string that contains information about
                              the current private MIB release"
                ::=  { hirmaBasBridgeTable 5 }

hirmaBasBridgeSpanningTreeVersion    OBJECT-TYPE
                SYNTAX       DisplayString
                ACCESS       read-only
                STATUS       mandatory
                DESCRIPTION  "A string that contains information about
                              the current Spanning Tree Version."
                ::=  { hirmaBasBridgeTable 6 }

hirmaBasBridgeSwitches       OBJECT-TYPE
                SYNTAX       INTEGER
                ACCESS       read-only
                STATUS       mandatory
                DESCRIPTION  "State of the DIP-switches on
                              the  memoryboard (EBGM).

                              The DIP-switches are defined as follows:

                              switch |         on          |        off
                              -------------------------------------------------
                                 1   | service             | normal
                                 2   | service             | normal
                                 3   | relay on            | relay off
                                 4   | LANswitch           | 802.3 Bridge
                                 5   | service             | normal
                                 6   | Spanning Tree on    | Spanning Tree off
                                 7   | Filtering on        | Filtering off
                                 8   | Learning on         | Learning off"
                        ::=  { hirmaBasBridgeTable 7 }

hirmaBasBridgePwrSplyState   OBJECT-TYPE
                SYNTAX       INTEGER
                                  {
                                    ok                       (1),
                                    error5V1                 (2),
                                    error5V2                 (3),
                                    error5V1and5V2           (4),
                                    error5V3                 (5),
                                    error5V1and5V3           (6),
                                    error5V2and5v3           (7),
                                    error5v1and5v2and5v3     (8)
                                  }
                ACCESS       read-only
                STATUS       mandatory
                DESCRIPTION  "Used to indicate the state of the
 power supplies.

                              5V1 corresponds to the first
                              power supply on the left side, etc."
                ::=  { hirmaBasBridgeTable 8 }

hirmaBasBridgeFanState       OBJECT-TYPE
                SYNTAX       INTEGER
                                {
                                  ok         (1),
                                  nofunction (2)
                                }
                ACCESS       read-only
                STATUS       mandatory
                DESCRIPTION  "Used to indicate the fan state. If
                              one of the two fans rotating speed is under
                              value, hirmaBasBridgeFanState will change to
                              nofunction (2)."
                ::=  { hirmaBasBridgeTable 9 }

hirmaBasBridgePwrAlarm     OBJECT-TYPE
                SYNTAX       INTEGER
                                  {
                                    enabled   (1),
                                    disabled  (2)
                                  }
                ACCESS       read-write
                STATUS       mandatory
                DESCRIPTION  "If enabled (1), the health-trap will be
                              sent in case of a power supply failure."
                ::=  { hirmaBasBridgeTable 10 }

hirmaBasBridgeHealthAlarm    OBJECT-TYPE
                SYNTAX       INTEGER
                                  {
                                    enabled   (1),
                                    disabled  (2)
                                  }
                ACCESS       read-write
                STATUS       mandatory
                DESCRIPTION  "If enabled (1), the health-trap will
                              be sent in case of any kind of failure.

                              Sending of a health-trap in case of a power
                              supply can not be disabled by this
                              attribute (use hirmaBasBridgePwrAlarms
                              instead)."
                ::=  { hirmaBasBridgeTable 11 }

hirmaBasBridgeSpanningTree    OBJECT-TYPE
                SYNTAX        INTEGER
                                   {
                                     enabled      (1),
                                     disabled     (2)
                                   }
                ACCESS        read-write
                STATUS        mandatory
                DESCRIPTION   "Used to indicate and set the state of the
                               spanning tree mode.

                               Note: Setting this variable to enabled (1),
                                     enables also the learning and the
                                     filtering mode.

                                     Setting this variable to
                                     disabled (2), disables only the
                                     spanning tree mode."
                ::=  { hirmaBasBridgeTable 12 }

hirmaBasBridgeHealthState    OBJECT-TYPE
                SYNTAX       INTEGER
                                  {
                              other                  (1), -- undefined or
                                                          -- unknown
                              ok                     (2), -- no known failure
                              generalFailure         (3), -- failure,
                                                          -- unspecifed type
                              multiLANSwitchFailure  (4)  -- MultiLAN Switch
                                                          -- related failure
                                  }
                ACCESS       read-only
                STATUS       mandatory
                DESCRIPTION  "The BridgeHealthState indicates the
                              operational state of the MultiLAN Switch.
                              The BridgeHealthData and BridgeHealthText
                              may be consulted for more specific
                              information about this state."
                ::=  { hirmaBasBridgeTable 13 }

hirmaBasBridgeHealthText     OBJECT-TYPE
                SYNTAX       DisplayString (SIZE (0..255))
                ACCESS       read-only
                STATUS       mandatory
                DESCRIPTION  "The BridgeHealthText provides information
                              relevant to the operational state of the
                              MultiLAN Switch."
                ::=  { hirmaBasBridgeTable 14 }

hirmaBasBridgeHealthData     OBJECT-TYPE
                SYNTAX       OCTET STRING (SIZE (0..255))
                ACCESS       read-only
                STATUS       mandatory
                DESCRIPTION  "The BridgeHealthData is a block of data
                              octets that provides information relevant
                              to the operational state of the
                              MultiLAN Switch."
                ::=  { hirmaBasBridgeTable 15 }

hirmaBasBridgeCounterReset    OBJECT-TYPE
                SYNTAX        INTEGER
                                  {
                                  reset     (1),
                                  no-reset  (2)
                                  }
                ACCESS        read-write
                STATUS        mandatory
                DESCRIPTION   "Resets all non port related counters
                               of the MultiLAN Switch.

                               Note: Setting this variable to noReset (2)
                                     has no effect. The agent will always
                                     return the value noReset (2) in
                                     response to a GetRequest."
                ::=  { hirmaBasBridgeTable 16 }


--      ********************************************
--                    BRIDGE EVENT TABLE
--      ********************************************
--
--


hirmaBasBridgeEventTable     OBJECT-TYPE
                SYNTAX       SEQUENCE OF HirmaBasBridgeEventEntry
                ACCESS       not-accessible
                STATUS       mandatory
                ::=  { hirmaBasCapability 2 }

hirmaBasBridgeEventEntry     OBJECT-TYPE
                SYNTAX       HirmaBasBridgeEventEntry
                ACCESS       not-accessible
                STATUS       mandatory
                INDEX        { hirmaBasBridgeMessageID }
                ::=  { hirmaBasBridgeEventTable 1 }


     HirmaBasBridgeEventEntry ::= SEQUENCE {
                hirmaBasBridgeMessageID      INTEGER,
                hirmaBasBridgeMessageIfIndex INTEGER,
                hirmaBasBridgeMessage        INTEGER,
                hirmaBasBridgeMessageTime    TimeTicks
                }

hirmaBasBridgeMessageID      OBJECT-TYPE
                SYNTAX       INTEGER
                ACCESS       read-only
                STATUS       mandatory
                DESCRIPTION  "Used to uniquely identify messages
                              within this table.

                              Note: This table is as a ring buffer,
                                    a new entry in the table may
                                    overwrite the oldest message in
                                    the table."
                ::=  { hirmaBasBridgeEventEntry 1 }

hirmaBasBridgeMessageIfIndex OBJECT-TYPE
                SYNTAX       INTEGER
                ACCESS       read-only
                STATUS       mandatory
                DESCRIPTION  "Used to uniquely identify the interface
                              where the event has appeared.

"
                ::=  { hirmaBasBridgeEventEntry 2  }

hirmaBasBridgeMessage        OBJECT-TYPE
                SYNTAX       OCTET STRING
                ACCESS       read-only
                STATUS       mandatory
                DESCRIPTION  "This object shows the message code according
                              to the following table.

                              1) error message

                                Code  |Display|           Description
                              ***********************************************
                              0x45:0f |   O   | buffer overflow
                              0x45:91 |   O   | buffer overflow recovered
                              0x45:b3 |   S   | no carrier sense response
                              0x48:f6 |   V   | redundant power supply error
                              0x01:4f |  A-a  | shut-down TFTP transmission
                              0x81:a2 |  A-b  | TFTP transmission error
                              0x01:64 |  A-t  | TFTP transmission time out
                              0x01:65 |  A-u  | no TFTP server attached
                                      |  C-g  | TCP communication problemes
                                      |  C-n  | all TCP-devices are busy
                                      |  C-r  | TCP rexmit timeout probleme
                              0x05:a5 |  E-e  | inaccessible transmission
                              0x05:88 |  E-h  | wrong LAN-controller state
                              0x05:ac |  E-l  | late collision detection
                              0x05:ad |  E-m  | too many collisions
                              0x05:b6 |  E-u  | internal transmission error
                              0x05:b8 |  E-x  | shut-down transmission
                              0x06:a1 |  F-a  | address table overflow
                              0x07:ce |  F-b  | inaccessible address table
                              0x06:a6 |  F-f  | type field table overflow
                              0x06:ad |  F-m  | rejected management packet (rx)
                              0x06:af |  F-o  | filter table overflow
                              0x06:b3 |  F-s  | filter table overflow
                              0x08:d7 |  H-w  | watchdog time out
                              0x09:89 |  I-i  | missing IP-address
                              0x09:8e |  I-n  | no response with RARP
                                      |  O-b  | TCP buffer overflow
                                      |  O-f  | no TCP connection
                                      |  O-k  | TCP transmission error
                                      |  O-n  | disabled TCP device
                                      |  S-c  | wrong INI-file

                              2) fatal error messages

                                Code  |Display|           Errorcode
                              ***********************************************
                              0x85:84 |  E-d  | LAN-controller test failed
                              0x85:87 |  E-g  | LAN-controller disabled
                              0x85:94 |  E-t  | LAN-controller error
                              0x88:8a |  H-j  | wrong master or malfunction
                              0x88:8d |  H-m  | no attached master
                              0x88:90 |  H-p  | processor test failed
                              0x8d:87 |  M-g  | global memory test failed
                              0x8d:8c |  M-l  | local memory test failed
                              0x8d:92 |  M-r  | ROM checksum test failed"
                ::=  { hirmaBasBridgeEventEntry 3 }

hirmaBasBridgeMessageTime    OBJECT-TYPE
                SYNTAX       TimeTicks
                ACCESS       read-only
                STATUS       mandatory
                DESCRIPTION  "The value of sysUpTime when the message
                              has occured. The time unit is tens of
                              milliseconds."
                ::=  { hirmaBasBridgeEventEntry 4 }



--      *******************************************
--                HIRMA BASIC GROUP TABLE
--      *******************************************
--
--


hirmaBasGroupTable           OBJECT-TYPE
                SYNTAX       SEQUENCE OF HirmaBasGroupEntry
                ACCESS       not-accessible
                STATUS       mandatory
                ::=  { hirmaBasCapability 3 }

hirmaBasGroupEntry           OBJECT-TYPE
                SYNTAX       HirmaBasGroupEntry
                ACCESS       not-accessible
                STATUS       mandatory
                INDEX        { hirmaBasGroupID }
                ::=  { hirmaBasGroupTable 1 }

     HirmaBasGroupEntry ::= SEQUENCE {
                hirmaBasGroupID             INTEGER,
                hirmaBasGroupNumOfPorts     INTEGER,
                hirmaBasGroupPortMap        DisplayString,
                hirmaBasGroupName           DisplayString
                }

hirmaBasGroupID              OBJECT-TYPE
                SYNTAX       INTEGER
                ACCESS       read-only
                STATUS       mandatory
                DESCRIPTION  "Used to uniquely identify an interface
                              card within the MultiLAN Switch."
                ::=  { hirmaBasGroupEntry 1 }

hirmaBasGroupNumOfPorts      OBJECT-TYPE
                SYNTAX       INTEGER
                ACCESS       read-only
                STATUS       mandatory
                DESCRIPTION  "Number of ports of the associated
                              interface card."
                ::=  { hirmaBasGroupEntry 2 }

hirmaBasGroupPortMap         OBJECT-TYPE
                SYNTAX       DisplayString
                ACCESS       read-only
                STATUS       mandatory
                DESCRIPTION  "Used to uniquely map interface numbers
                              and interface card numbers. Both,
                              interfaces and interface cards are numbered
                              within a range of 1 to the maximum number
                              of interface cards, where the interface
                              card list may contain holes in case that
                              an interface card is not present.

                              E.g. this value may contain '6', which
                              indicates that this port of this
                              interface card is currently handled as
                              interface number 6.

                              In case of multiple interfaces (ports)
                              per interface card, the numbers are
                              separated with a comma (e.g. '5,6')."
                ::=  { hirmaBasGroupEntry 3 }

hirmaBasGroupName             OBJECT-TYPE
                SYNTAX        DisplayString
                ACCESS        read-only
                STATUS        mandatory
                DESCRIPTION   "Name of the interface cards.
                              E.g : EBAUI, EBTP ..."
                ::=  { hirmaBasGroupEntry 4 }

--      *******************************************
--                 HIRMA BASIC PORT TABLE
--      *******************************************
--
--


hirmaBasPortTable            OBJECT-TYPE
                SYNTAX       SEQUENCE OF HirmaBasPortEntry
                ACCESS       not-accessible
                STATUS       mandatory
                ::=  { hirmaBasCapability 4 }

hirmaBasPortEntry            OBJECT-TYPE
                SYNTAX       HirmaBasPortEntry
                ACCESS       not-accessible
                STATUS       mandatory
                INDEX        { hirmaBasPortID }
                ::=  { hirmaBasPortTable 1 }

     HirmaBasPortEntry ::= SEQUENCE {

                hirmaBasPortID              INTEGER,
                hirmaBasPortGroupID         INTEGER,
                hirmaBasPortLanType         INTEGER,
                hirmaBasPortType            INTEGER,
                hirmaBasPortShortDelay      INTEGER,
                hirmaBasPortLearning        INTEGER,
                hirmaBasPortFiltering       INTEGER,
                hirmaBasPortRelay           INTEGER,
                hirmaBasPortMode            INTEGER,
                hirmaBasPortCounterReset    INTEGER,
                hirmaBasPortState           DisplayString
                }

hirmaBasPortID               OBJECT-TYPE
                SYNTAX       INTEGER
                ACCESS       read-only
                STATUS       mandatory
                DESCRIPTION  "Used to uniquely identify an interface
                              (port) within the MultiLAN Switch.

                              Note: The interfaces (ports) are numbered
                                    in ascending order from the left
                                    side to the right side, within a
                                    range of 1 to n."
                ::=  { hirmaBasPortEntry 1 }

hirmaBasPortGroupID          OBJECT-TYPE
                SYNTAX       INTEGER
                ACCESS       read-only
                STATUS       mandatory
                DESCRIPTION  "Used to identify the associated
                              interface card."
                ::= { hirmaBasPortEntry 2 }

hirmaBasPortLanType          OBJECT-TYPE
                SYNTAX       INTEGER
                                  {
                                    ethernet   (1),
                                    fddi       (2)
                                  }
                ACCESS       read-only
                STATUS       mandatory
                DESCRIPTION  "Used to identify different
                              LAN types."
                ::=  { hirmaBasPortEntry 3 }

hirmaBasPortType              OBJECT-TYPE
                SYNTAX        INTEGER
                                   {
                                     aui                    (1),
                                     optical-asynch-850     (2),
                                     optical-asynch-1300-16 (3),
                                     optical-asynch-1300-40 (4),
                                     unshielded-TP-10BaseT  (5)
                                   }
                ACCESS        read-only
                STATUS        mandatory
                DESCRIPTION   "Used to identify the physical media type of the
                               interface card "
                ::=  { hirmaBasPortEntry 4 }

hirmaBasPortShortDelay    OBJECT-TYPE
                SYNTAX        INTEGER
                                   {
                                     ieee802-3        (1),
                                     ethernet-switch  (2)
                                   }
                ACCESS        read-write
                STATUS        mandatory
                DESCRIPTION   "Used to change the operation mode
                               between ethernet switching and 802.3 CSMA/CD."
                ::=  { hirmaBasPortEntry 5 }

hirmaBasPortLearning          OBJECT-TYPE
                SYNTAX        INTEGER
                                   {
                                     enabled      (1),
                                     disabled     (2)
                                   }
                ACCESS        read-write
                STATUS        mandatory
                DESCRIPTION   "Used to indicate whether the learning
                               mode of this port is enabled or disabled.

                               Note: The learning mode may only be
                                     disabled (2) if the spanning
                                     tree mode is disabled."
                ::=  { hirmaBasPortEntry 6 }

hirmaBasPortFiltering         OBJECT-TYPE
                SYNTAX        INTEGER
                                   {
                                     enabled      (1),
                                     disabled     (2)
                                   }
                ACCESS        read-write
                STATUS        mandatory
                DESCRIPTION   "Used to indicate whether the filtering
                               mode of this port is enabled or disabled.

                               Note: The filtering mode may only be
                                     disabled (2) if the spanning tree
                                     mode is disabled."
                ::=  { hirmaBasPortEntry 7 }

hirmaBasPortRelay             OBJECT-TYPE
                SYNTAX        INTEGER
                                   {
                                     enabled      (1),
                                     disabled     (2)
                                   }
                ACCESS        read-write
                STATUS        mandatory
                DESCRIPTION   "If enabled (1), all
                               packets will be forwarded. Otherwise
                               only packets with known addresses
                               will be forwarded."
                ::=  { hirmaBasPortEntry 8 }

hirmaBasPortMode            OBJECT-TYPE
                SYNTAX       INTEGER
                                  {
                                  half-duplex  (1), -- HDX
                                  full-duplex  (2)  -- FDX
                                  }
                ACCESS       read-only
                STATUS       mandatory
                DESCRIPTION  "Indicates the transmission mode of the
                              interface card. This mode can be adjusted by
                              a jumper on the interface card "
                ::=  { hirmaBasPortEntry 9 }

hirmaBasPortCounterReset      OBJECT-TYPE
                SYNTAX        INTEGER
                                  {
                                  reset     (1),
                                  no-reset  (2)
                                  }
                ACCESS        read-write
                STATUS        mandatory
                DESCRIPTION   "Resets all port related counters.

                               Note: Setting this variable to no reset (2)
                                     has no effect. The agent will always
                                     return the value no-reset (2) in
                                     response to a GetRequest."
                ::=  { hirmaBasPortEntry 10 }

hirmaBasPortState      OBJECT-TYPE
                SYNTAX        DisplayString
                ACCESS        read-only
                STATUS        mandatory
                DESCRIPTION   "Indicates the operational state of
                               the port such as -normal-, -carrier sense-,
                               -jabber-, -idle-, etc."
                ::=  { hirmaBasPortEntry 11 }


--      ************************************************
--              HIRMA MultiLAN Switch SELFTEST TABLE
--      ************************************************
--
--


hirmaSelfTestBridgeReset      OBJECT-TYPE
                SYNTAX        INTEGER
                                   {
                                   reset    (1),
                                   no-reset (2)
                                   }
                ACCESS        read-write
                STATUS        mandatory
                DESCRIPTION   "Setting this value to reset (1),
                               forces the MultiLAN Switch to reset
                               according to the type in
                               hirmaSelfTestBridgeResetType."
                ::=  { hirmaSelfTestCapability 1 }

hirmaSelfTestBridgeResetType  OBJECT-TYPE
                SYNTAX        INTEGER
                                  {
                                  warm-start   (1),
                                  cold-start   (2)
                                  }
                ACCESS        read-write
                STATUS        mandatory
                DESCRIPTION   "Type of resetwhich will be executed
                               if hirmaSelfTestBridgeReset will be set
                               to reset."
                ::=  { hirmaSelfTestCapability 2 }

hirmaSelfTestBridgeSetDefaults OBJECT-TYPE
                SYNTAX        INTEGER
                                  {
                                  reset        (1),
                                  no-reset     (2)
                                  }
                ACCESS        read-write
                STATUS        mandatory
                DESCRIPTION   "Resets all parameters to the default
                               value. Just like after a cold-start."
                ::=  { hirmaSelfTestCapability 3 }


--      ******************************************
--             HIRMA SELFTEST GROUP TABLE
--      ******************************************
--
--


hirmaSelfTestGroupTable      OBJECT-TYPE
                SYNTAX       SEQUENCE OF HirmaSelfTestGroupEntry
                ACCESS       not-accessible
                STATUS       mandatory
                ::=  { hirmaSelfTestCapability 4 }

hirmaSelfTestGroupEntry      OBJECT-TYPE
                SYNTAX       HirmaSelfTestGroupEntry
                ACCESS       not-accessible
                STATUS       mandatory
                INDEX        { hirmaSelfTestGroupID }
                ::=  { hirmaSelfTestGroupTable 1 }

     HirmaSelfTestGroupEntry ::= SEQUENCE {
                hirmaSelfTestGroupID              INTEGER,
                hirmaSelfTestGroupDisplayTest     INTEGER,
                hirmaSelfTestGroupSQETest         INTEGER
                }

hirmaSelfTestGroupID         OBJECT-TYPE
                SYNTAX       INTEGER
                ACCESS       read-only
                STATUS       mandatory
                DESCRIPTION  "Used to uniquely identify a interface
                              card."
                ::=  { hirmaSelfTestGroupEntry 1 }

hirmaSelfTestGroupDisplayTest OBJECT-TYPE
                SYNTAX        INTEGER
                                  {
                                  test     (1),
                                  no-test  (2)
                                  }
                ACCESS        read-write
                STATUS        mandatory
                DESCRIPTION   "Starts the internal display test."
                ::=  { hirmaSelfTestGroupEntry 2 }

hirmaSelfTestGroupSQETest    OBJECT-TYPE
                SYNTAX       INTEGER
                                 {
                                 enabled-ok    (1),  -- read-write
                                 disabled      (2),  -- read-write
                                 not-ok        (3)   -- read-only
                                 }
                ACCESS       read-write
                STATUS       mandatory
                DESCRIPTION  "Reading this value will offer the state
                              of the SQE test. SQE test may be enabled
                              by setting this object to enabled (1).

                              Detecting a SQE test problem will change
                              the value to not-ok (3)."
                ::=  { hirmaSelfTestGroupEntry 3 }



--      *******************************************
--            HIRMA EXTENDED FILTER INFORMATION
--      *******************************************
--
--


hirmaFilterMaxNumOfFilters   OBJECT-TYPE
                SYNTAX       INTEGER
                ACCESS       read-only
                STATUS       mandatory
                DESCRIPTION  "Number of filters in the following table."
                ::=  { hirmaFilterCapability 1 }

hirmaFilterTable             OBJECT-TYPE
                SYNTAX       SEQUENCE OF HirmaFilterTableEntry
                ACCESS       not-accessible
                STATUS       mandatory
                ::=  { hirmaFilterCapability 2 }

hirmaFilterTableEntry        OBJECT-TYPE
                SYNTAX       HirmaFilterTableEntry
                ACCESS       not-accessible
                STATUS       mandatory
                INDEX        { hirmaFilterID }
                ::=  { hirmaFilterTable 1 }

     HirmaFilterTableEntry ::= SEQUENCE {
                hirmaFilterID                   INTEGER,
                hirmaFilterMode                 INTEGER,
                hirmaFilterDest                 DisplayString,
                hirmaFilterSrc                  DisplayString,
                hirmaFilterType                 DisplayString,
                hirmaFilterPortIn               DisplayString,
                hirmaFilterPortOut              DisplayString
                }


hirmaFilterID                OBJECT-TYPE
                SYNTAX       INTEGER
                ACCESS       read-only
                STATUS       mandatory
                DESCRIPTION  "Used to uniquely identify an extended
                              filter. The filter ID ranges between 1
                              and hirmaFilterMaxNumOfFilters.

                              Caution: Throughput rate will decrease
                                       the more extended filters are
                                       used."
                ::=  { hirmaFilterTableEntry 1 }


hirmaFilterMode              OBJECT-TYPE
                SYNTAX       INTEGER
                                 {
                                 forward            (1),
                                 disable            (2),
                                 discard            (3),
                                 alone              (4),
                                 channel            (5),
                                 delete             (6)
                                 }
                ACCESS       read-write
                STATUS       mandatory
                DESCRIPTION  "Setting this variable to forward (1), will
                              forward all packets that match on a single
                              filter.

                              Setting this variable to discard (3),
                              will discard all packets that match on a
                              single filter.

                              Setting this variable to disable (2), will
                              only forward or discard packets according to
                              the learning tables.

                              Setting this variable to alone (4), the packets
                              are filtered with the private filter (forward)
                              and than filtered with the normaly filter.

                              Setting this variable to channel (5), between
                              the ports hirmaFilterPortIn and
                              hirmaFilterPortOut exists a channel.

                              Setting this variable to delete (6), the filter
                              entry will be deleted from the filter structure.


                              Note: One single filter is defined as a set
                                    of hirmaFilterDest, hirmaFilterSrc,
                                    hirmaFilterType and hirmaFilterPortIn,
                                    where each entry may also be
                                    left unused.

                                    Forward on match will forward all
                                    packets to the specified output port(s).

                                    Discard on match will discard all
                                    packets regardless to any specified
                                    output port(s)."
                ::=  { hirmaFilterTableEntry 2 }

hirmaFilterDest              OBJECT-TYPE
                SYNTAX       DisplayString
                ACCESS       read-write
                STATUS       mandatory
                DESCRIPTION  "This display string identifies the
                              MAC address(es) for a single or a set
                              of destination adress filters.

                              For example;
                              00:80:63:01:02:03-00:80:63:04:05:06
                              defines a set of MAC addresses
                              as a destination address filter.
                              00:80:63:01:02:03 defines particularly
                              one MAC destination address filter.

                              Set an empty string to delete the
                              previously defined address.

                              Note: The maximum range runs from
                                    XX:XX:XX:00:00:00 to XX:XX:XX:FF:FF:FF.
                                    Setting of larger ranges will be ignored."
                ::=  { hirmaFilterTableEntry 3 }

hirmaFilterSrc               OBJECT-TYPE
                SYNTAX       DisplayString
                ACCESS       read-write
                STATUS       mandatory
                DESCRIPTION  "This display string identifies the
                              MAC address(es) for a single or a set
                              of source address filters.

                              For example;
                              00:80:63:01:02:03-00:80:63:04:05:06
                              defines a set of MAC addresses
                              as a source address filter.
                              00:80:63:01:02:03 defines particularly
                              one MAC source adress filter.

                              Set an empty string to delete the previously
                              defined address.

                              Note: The maximum range runs from
                                    XX:XX:XX:00:00:00 to XX:XX:XX:FF:FF:FF.
                                    Setting of larger ranges will be ignored."
                ::=  { hirmaFilterTableEntry 4 }

hirmaFilterType              OBJECT-TYPE
                SYNTAX       DisplayString
                ACCESS       read-write
                STATUS       mandatory
                DESCRIPTION  "This display string represents a single
                              or a set of protocol types .

                              For example;
                              8001-8006
                              defines a set of protocol types filter
                              8063 defines particularly
                              one protocol types filter

                              Set an empty string to delete the previously
                              defined type.

                              Note: The maximum range runs from
                                    XX00 to XXFF.
                                    Setting of larger ranges will be ignored.

                              Example of protocols:

                              type 2 bytes  |   protocols
                              ******************************************
                                  809B      |   AppleTalk
                                  6007      |   DEC LAVC, SCA
                                  0800      |   DoD IP
                                  0803      |   ECMA Internet
                                  00FE      |   ISO DIS 8473 (LSAP)
                                  0003      |   LLC (Group) Sublayer Mgmt.
                                  814C      |   SNMP
                              --------------------------------------------
                                  6000-6009 |   10  DEC protocols

                              Set an empty string to delete the previously
                              defined type.

                              Note: The maximum range runs from XXX0 to XXXF.
                                    Setting of larger ranges will be ignored."
                ::=  { hirmaFilterTableEntry 5 }


hirmaFilterPortIn            OBJECT-TYPE
                SYNTAX       DisplayString
                ACCESS       read-write
                STATUS       mandatory
                DESCRIPTION  "Input ports, separated by commas.
                              For example;
                              1,2,5,6 means, that only packets received on
                              these 4 ports match this filter.

                              Set an empty string to delete the previously
                              defined ports."
                ::=  { hirmaFilterTableEntry 6 }

hirmaFilterPortOut           OBJECT-TYPE
                SYNTAX       DisplayString
                ACCESS       read-write
                STATUS       mandatory
                DESCRIPTION  "Output ports, separated by commas.

                              For example;
                              1,2,5,6 means, that matching packets will be
                              forwarded to these 4 ports.

                              Set an empty string to delete the previously
                              defined ports"
                ::=  { hirmaFilterTableEntry 7 }


--      *******************************************
--             HIRMA BLOCK TRANSFER CAPABILITY
--      *******************************************
--
-- These objects are designed to allow network management systems to
-- retrieve a complete block of source addresses.
--

hirmaAddrBTAddr              OBJECT-TYPE
                SYNTAX       MacAddress
                ACCESS       read-write
                STATUS       mandatory
                DESCRIPTION  "All following addresses excluding this
                              address will be listed. In general the
                              last address of the previous block is
                              used as the starting address of the next
                              block.

                              The address 00:00:00:00:00:00 is the start
                              address to get the first block."
                ::= { hirmaAddrBTCapability 1 }

hirmaAddrBTBlock             OBJECT-TYPE
                SYNTAX       OCTET STRING
                ACCESS       read-only
                STATUS       mandatory
                DESCRIPTION  "Offers a block of address information.
                              This list of the address entries is not
                              lexicographically ordered.

                              Byte (n*10)  m |     State
                              ****************************************
                              Byte m=0        | reserved
                              Byte m=1        |
                                  Bit 0..2; 4 | reserved
                                  Bit 3       | MultiLAN Switch MAC address
                                  Bit 5       | static, entered by mgmt
                                  Bit 6       | aged out
                                  Bit 7       | valid
                              Byte m=2        | interface card, where the
                                              | address appeared.
                              Byte m=3        | reserved
                              Byte m=4..m=9   | MAC address

                              Where n is the number of address
                              entries. So, each address block is
                              aligned to n*10 Bytes."
                ::= { hirmaAddrBTCapability 2 }


--      *******************************************
--                  HIRMA FLASH UPDATE
--      *******************************************
--
--


hirmaFlashUpdateIPAddr       OBJECT-TYPE
                SYNTAX       IpAddress
                ACCESS       read-write
                STATUS       mandatory
                DESCRIPTION  "The IP-address of the update-server."
                ::=  { hirmaFlashUpdate 1 }

hirmaFlashUpdateName         OBJECT-TYPE
                SYNTAX       DisplayString
                ACCESS       read-write
                STATUS       mandatory
                DESCRIPTION  "This string contains the full pathname
                              and name of the update file."
                ::=  { hirmaFlashUpdate 2 }

hirmaFlashUpdateAction       OBJECT-TYPE
                SYNTAX       INTEGER
                                  {
                                    program       (1),
                                    normal-mode   (2)
                                  }
                ACCESS       read-write
                STATUS       mandatory
                DESCRIPTION  "Setting this variable to program will
                              force the MultiLAN Switch to run a software
                              update defined by the update file in
                              hirmaFlashUpdateName and the update
                              server defined in hirmaFlashUpdateIPAddr.

                              Note: Setting this variable to normal
                                    mode (2) has no effect. The
                                    agent will always return normal mode (2)
                                    in response to a GetRequest."
                ::=  { hirmaFlashUpdate 3 }


--      *******************************************
--             HIRMA LOAD SAVE CONFIGURATION
--      *******************************************
--
--

hirmaLoadSaveConIPAddr       OBJECT-TYPE
                SYNTAX       IpAddress
                ACCESS       read-write
                STATUS       mandatory
                DESCRIPTION  "Tree different values are possible:
                              1: 0.0.0.0 will cause the MultiLAN Switch
                                 to set all read/write attributes to a
                                 default value in case of warm/cold start.
                              2: Setting this value to the IP address of
                                 the MultiLAN Switch will cause the Switch
                                 in case of a warm/cold start to load the
                                 configuration from the flash eprom which
                                 has been previously saved into the flash
                                 eprom by issueing a Set request to
                                 hirmaLoadSaveConAction.0 = 3.
                              3: The address of an existing tftp server, where
                                 to read a configuration file from in case
                                 of a Set request hirmaLoadSaveConAction.0 = 1
                                 or a warm/cold start."
                ::=  { hirmaLoadSaveConfig 1 }

hirmaLoadSaveConName         OBJECT-TYPE
                SYNTAX       DisplayString
                ACCESS       read-write
                STATUS       mandatory
                DESCRIPTION  "This string contains the full pathname
                              and name of the configuration file."
                ::=  { hirmaLoadSaveConfig 2 }

hirmaLoadSaveConAction       OBJECT-TYPE
                SYNTAX       INTEGER
                                  {
                                    load         (1),
                                    normal-mode  (2),
                                    save         (3)
                                  }
                ACCESS       read-write
                STATUS       mandatory
                DESCRIPTION  "Setting this attribute to 1 (load) will cause
                              the Switch to read a configuration file from
                              a tftp server in case that an existing tftp
                              server is given by hirmaLoadSaveConIPAddr.
                              See the description of hirmaLoadSaveConIPAdd for
                              more details.
                              3 (save) will cause the Switch to save all
                              read/write attributes in the flash eprom.
                              Setting this variable to normal mode (2) has no
                              effect.
                              The agent will always return the value
                              normal-mode (2) in response to a GetRequest."
                ::=  { hirmaLoadSaveConfig 3 }


--      ******************************************
--           HIRMA MIB HANDLER COMMUNITY TABLE
--      ******************************************


hirmaMibhCommTable           OBJECT-TYPE
                SYNTAX       SEQUENCE OF HirmaMibhCommEntry
                ACCESS       not-accessible
                STATUS       mandatory
                ::= { hirmaMibhHandler 1 }

hirmaMibhCommEntry           OBJECT-TYPE
                SYNTAX       HirmaMibhCommEntry
                ACCESS       not-accessible
                STATUS       mandatory
                INDEX        { hirmaMibhCommIndex }
                ::= { hirmaMibhCommTable 1 }


     HirmaMibhCommEntry ::= SEQUENCE {
                hirmaMibhCommIndex     INTEGER,
                hirmaMibhCommCommunity DisplayString,
                hirmaMibhCommAccess    INTEGER
                }

hirmaMibhCommIndex           OBJECT-TYPE
                SYNTAX       INTEGER
                ACCESS       read-only
                STATUS       mandatory
                DESCRIPTION  "Used to uniquely identify an object in the table."
                ::= { hirmaMibhCommEntry 1 }

hirmaMibhCommCommunity       OBJECT-TYPE
                SYNTAX       DisplayString
                ACCESS       read-write
                STATUS       mandatory
                DESCRIPTION  "Community string which the access rights
                              are assigned to. New communities may be
                              defined by setting community string to
                              any non-empty string. Use an empty string
                              to delete table entries."
                ::= { hirmaMibhCommEntry 2 }

hirmaMibhCommAccess          OBJECT-TYPE
                SYNTAX       INTEGER
                                 {
                                   not-accesible  (1),
                                   read-only      (2),
                                   read-write     (3)
                                 }
                ACCESS       read-write
                STATUS       mandatory
                DESCRIPTION  "Access rights of the community.

                              Warning: If you set the access rights
                                       of all non-trap communities
                                       to read-only you will not be
                                       able to write any MIB variable.
                                       If you set the access rights of
                                       all communities that contain this
                                       MIB attribute to read-only, you
                                       will not be able to modify any
                                       access rights later."
                ::= { hirmaMibhCommEntry 3 }


--      ******************************************
--          HIRMA MIB HANDLER HOST ACCESS TABLE
--      ******************************************
--
--


hirmaMibhAccessTable         OBJECT-TYPE
                SYNTAX       SEQUENCE OF HirmaMibhAccessEntry
                ACCESS       not-accessible
                STATUS       mandatory
                ::= { hirmaMibhHandler 2 }

hirmaMibhAccessEntry         OBJECT-TYPE
                SYNTAX       HirmaMibhAccessEntry
                ACCESS       not-accessible
                STATUS       mandatory
                INDEX        { hirmaMibhAccessCommIndex,
                               hirmaMibhAccessIPAddr,
                               hirmaMibhAccessPort }
                ::= { hirmaMibhAccessTable 1 }


     HirmaMibhAccessEntry ::= SEQUENCE {
                hirmaMibhAccessCommIndex   INTEGER,
                hirmaMibhAccessIPAddr      IpAddress,
                hirmaMibhAccessPort        INTEGER,
                hirmaMibhAccessCommunity   DisplayString,
                hirmaMibhAccessAccess      INTEGER,
                hirmaMibhAccessState       INTEGER
                }

hirmaMibhAccessCommIndex     OBJECT-TYPE
                SYNTAX       INTEGER
                ACCESS       read-only
                STATUS       mandatory
                DESCRIPTION  "Index variable, must reference a
                              valid entry in hirmaMibhCommTable."
                ::= { hirmaMibhAccessEntry 1 }

hirmaMibhAccessIPAddr        OBJECT-TYPE
                SYNTAX       IpAddress
                ACCESS       read-only
                STATUS       mandatory
                DESCRIPTION  "Entity's IP address. For example
                              0.0.0.0 means any IP address."
                ::= { hirmaMibhAccessEntry 2 }

hirmaMibhAccessPort          OBJECT-TYPE
                SYNTAX       INTEGER
                ACCESS       read-only
                STATUS       mandatory
                DESCRIPTION  "Entity's UDP port."
                ::= { hirmaMibhAccessEntry 3 }

hirmaMibhAccessCommunity     OBJECT-TYPE
                SYNTAX       DisplayString
                ACCESS       read-only
                STATUS       mandatory
                DESCRIPTION  "Community string referenced by
                              hirmaMibhAccessCommIndex. This
                              variable is supplied for convenience
                              only."
                ::= { hirmaMibhAccessEntry 4 }

hirmaMibhAccessAccess        OBJECT-TYPE
                SYNTAX       INTEGER
                                 {
                                   read-only  (1),
                                   read-write (3)
                                 }
                ACCESS       read-write
                STATUS       mandatory
                DESCRIPTION  "Access rights assigned to this entity.
                              As an extension to the SNMP standard,
                              it is possible to reduce the access rights
                              granted by a given SNMP community profile
                              for any host, but it is not possible to
                              extend access rights beyond those specified
                              by mibhCommAccess.

                              Note: On creation, this value defaults to
                                    the corresponding hirmaMibhCommAccess
                                    instance. Don't write to this attribute
                                    if full conformance to the standard is
                                    desired."
                ::= { hirmaMibhAccessEntry 5 }

hirmaMibhAccessState         OBJECT-TYPE
                SYNTAX       INTEGER
                                  {
                                    enabled  (1),
                                    disabled (2),
                                    deleted  (3)
                                  }
                ACCESS       read-write
                STATUS       mandatory
                DESCRIPTION  "Setting a non-existent instance to
                              enabled (1), will create a new instance
                              in this table.

                              Note: An entry may be temporarily
                                    suspended by setting state to
                                    disabled (2). To permanently
                                    remove an entry from the database,
                                    set state to deleted (3)."
                ::= { hirmaMibhAccessEntry 6 }


--      ******************************************
--            HIRMA MIB HANDLER TRAP TABLE
--      ******************************************
--
--


hirmaMibhTrapTable           OBJECT-TYPE
                SYNTAX       SEQUENCE OF HirmaMibhTrapEntry
                ACCESS       not-accessible
                STATUS       mandatory
                ::= { hirmaMibhHandler 3 }

hirmaMibhTrapEntry           OBJECT-TYPE
                SYNTAX       HirmaMibhTrapEntry
                ACCESS       not-accessible
                STATUS       mandatory
                INDEX        { hirmaMibhTrapCommIndex,
                               hirmaMibhTrapIPAddr,
                               hirmaMibhTrapPort }
                ::= { hirmaMibhTrapTable 1 }

     HirmaMibhTrapEntry ::= SEQUENCE {
                hirmaMibhTrapCommIndex   INTEGER,
                hirmaMibhTrapIPAddr      IpAddress,
                hirmaMibhTrapPort        INTEGER,
                hirmaMibhTrapCommunity   DisplayString,
                hirmaMibhTrapState       INTEGER
                }

hirmaMibhTrapCommIndex       OBJECT-TYPE
                SYNTAX       INTEGER
                ACCESS       read-only
                STATUS       mandatory
                DESCRIPTION  "Index variable, must reference a
                              valid entry in hirmaMibhCommTable."
                ::= { hirmaMibhTrapEntry 1 }

hirmaMibhTrapIPAddr          OBJECT-TYPE
                SYNTAX       IpAddress
                ACCESS       read-only
                STATUS       mandatory
                DESCRIPTION  "Destination IP address."
                ::= { hirmaMibhTrapEntry 2 }

hirmaMibhTrapPort            OBJECT-TYPE
                SYNTAX       INTEGER
                ACCESS       read-only
                STATUS       mandatory
                DESCRIPTION  "Destination UDP port. This must be set
                              to 162 by default because the management
                              system will listen to this UDP port
                              for traps."
                ::= { hirmaMibhTrapEntry 3 }

hirmaMibhTrapCommunity       OBJECT-TYPE
                SYNTAX       DisplayString
                ACCESS       read-only
                STATUS       mandatory
                DESCRIPTION  "Community string referenced by
                              hirmaMibhTrapCommIndex. This
                              variable is supplied for convenience
                              only."
                ::= { hirmaMibhTrapEntry 4 }

hirmaMibhTrapState           OBJECT-TYPE
                SYNTAX       INTEGER
                                  {
                                    enabled  (1),
                                    disabled (2),
                                    deleted  (3)
                                  }
                ACCESS       read-write
                STATUS       mandatory
                DESCRIPTION  "Setting a non-existent instance to
                              enabled (1), will create a new trap
                              entry in this table.

                              Note: An entry may be temporarily
                                    suspended by setting state to
                                    disabled (2). To permanently
                                    remove an entry from the database,
                                    set state to deleted (3)."
                ::= { hirmaMibhTrapEntry 5 }


--      ******************************************
--              HIRMA USER SYSTEM TABLE
--      ******************************************
--
--

hirmaLuiSystemTable          OBJECT IDENTIFIER
                ::= { hirmaUserInterface 1 }

hirmaLuiLocalIPAddr          OBJECT-TYPE
                SYNTAX       IpAddress
                ACCESS       read-write
                STATUS       mandatory
                DESCRIPTION  "IP address of MultiLAN Switch."
                ::= { hirmaLuiSystemTable 1 }

hirmaLuiGatewayIPAddr        OBJECT-TYPE
                SYNTAX       IpAddress
                ACCESS       read-write
                STATUS       mandatory
                DESCRIPTION  "IP address of a gateway (router)
                              needed to reach a server."
                ::= { hirmaLuiSystemTable 2 }

hirmaLuiNetMask              OBJECT-TYPE
                SYNTAX       IpAddress
                ACCESS       read-write
                STATUS       mandatory
                DESCRIPTION  "Subnetmask of the subnet."
                ::= { hirmaLuiSystemTable 3 }

hirmaLuiUserTable            OBJECT-TYPE
                SYNTAX       SEQUENCE OF HirmaLuiUserEntry
                ACCESS       not-accessible
                STATUS       mandatory
                ::= { hirmaUserInterface 2 }


hirmaLuiUserEntry             OBJECT-TYPE
                SYNTAX       HirmaLuiUserEntry
                ACCESS       not-accessible
                STATUS       mandatory
                INDEX        { hirmaLuiUserID }
                ::= { hirmaLuiUserTable 1 }


    HirmaLuiUserEntry ::= SEQUENCE {
                hirmaLuiUserID         INTEGER,
                hirmaLuiUserName       OCTET STRING,
                hirmaLuiUserPasswd     OCTET STRING,
                hirmaLuiUserCommunity  OCTET STRING
                }

hirmaLuiUserID               OBJECT-TYPE
                SYNTAX       INTEGER
                ACCESS       read-only
                STATUS       mandatory
                DESCRIPTION  "Table index variable"
                ::= { hirmaLuiUserEntry 1 }

hirmaLuiUserName             OBJECT-TYPE
                SYNTAX       DisplayString
                ACCESS       read-write
                STATUS       mandatory
                DESCRIPTION  "Userspecific Identification"
                ::= { hirmaLuiUserEntry 2 }

hirmaLuiUserPasswd           OBJECT-TYPE
                SYNTAX       DisplayString
                ACCESS       read-write
                STATUS       mandatory
                DESCRIPTION  "password of a specific user"
                ::= { hirmaLuiUserEntry 3 }

hirmaLuiUserCommunity        OBJECT-TYPE
                SYNTAX       DisplayString
                ACCESS       read-write
                STATUS       mandatory
                DESCRIPTION  "access-rights of the user"
                ::= { hirmaLuiUserEntry 4}




-- **************************************************************************
-- *                                                                        *
-- * MultiLAN Switch TRAPS                                            *
-- *                                                                        *
-- **************************************************************************


bridgeHealth                 TRAP-TYPE
                ENTERPRISE   bridge1
                VARIABLES    { hirmaBasBridgeHealthState }
                DESCRIPTION  " The hirmaBridgeHealth trap information
                               relates to the operational state of the
                               MultiLAN Switch. This trap is sent only
                               when the health state of the
                               MultiLAN Switch changes.

                               The hirmaBridgeHealth trap must contain
                               the hirmaBasBridgeHealthState variable.
                               The MultiLANSwitch optionally includes
                               hirmaBasBridgeHealthText and
                               hirmaBasBridgeHealthData in the
                               varBind list. See  hirmaBasHubHealthState,
                               hirmaBasHubHealthText and
                               hirmaBasHubHealthData objects for
                               descriptions of the information that are sent."
                ::= 1





END
