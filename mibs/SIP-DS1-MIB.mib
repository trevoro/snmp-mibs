-- 
-- SIP-DS1-MIB module definition  
--
-- The definitions in this module specify an initial version of 
-- SIP mib.
-- 
--

SIP-DS1-MIB DEFINITIONS ::= BEGIN
IMPORTS
    enterprises, Counter
        FROM RFC1155-SMI
    OBJECT-TYPE
        FROM RFC-1212
    DisplayString
        FROM RFC1213-MIB
    MODULE-IDENTITY, ObjectName, Integer32, Counter32, snmpModules
        FROM SNMPv2-SMI
    TruthValue, DisplayString, TestAndIncr, TimeStamp, RowStatus
        FROM SNMPv2-TC;

	lucent		    OBJECT IDENTIFIER  ::=  {  enterprises  1751  }
	products	    OBJECT IDENTIFIER  ::=  {  lucent  1  }
	softSwitch      OBJECT IDENTIFIER  ::=  {  products 1198  }
	sipDeviceServer OBJECT IDENTIFIER  ::=  {  softSwitch 5 }

	sipDS1  MODULE-IDENTITY    
        LAST-UPDATED "240701"
        ORGANIZATION "Lucent Technologies"    
        CONTACT-INFO 
                ""    
        DESCRIPTION
                "The MIB module for entities implementing the xxxx
                protocol."  

::=  {  sipDeviceServer 1 }


	-- mib groups
	-- the sipSystem group - contains information about this deviceServer

	sipSystem	OBJECT IDENTIFIER  ::=  {  sipDS1 1 }	
	

	-- attrib definitions

	dsInfo OBJECT-TYPE
	    SYNTAX  DisplayString (SIZE (1..256))
	    MAX-ACCESS  read-only
	    STATUS  current
	    DESCRIPTION
		"Device Server information. This value should 
		include the full name and version identification 
		and/or manufacturer information. It is mandatory 
		that this contains only printable ASCII characters" 

	    ::= { sipSystem 1 }


	dsProtocolInfo OBJECT-TYPE
	    SYNTAX  DisplayString (SIZE (1..256))
	    MAX-ACCESS  read-only
	    STATUS  current
	    DESCRIPTION
		"Device Server H323/SIP stack information. This 
		value should include the full name and version 
		identification and/or manufacturer information of 
		the H323/SIP Stack used in the device server implementation.
		It is mandatory that this contains only printable ASCII 
		characters"

	    ::= { sipSystem 2 }

	logLevel OBJECT-TYPE
	    SYNTAX  INTEGER ( 1..3 )
	    MAX-ACCESS  read-write
	    STATUS  current
	    DESCRIPTION
		"Device Server Log Level. A minimum logging level is
		always set for the device servers, which logs errors 
		and warnings. If still more verbosity is required, that 
		can be done by setting this parameter to a required level.
		1. Error
		2. Warning
		3. Info"

	    ::= { sipSystem 3 }

	succeededCalls OBJECT-TYPE
	    SYNTAX  INTEGER ( 0..65535 )
	    MAX-ACCESS  read-only
	    STATUS  current
	    DESCRIPTION
		"Total number of calls successfully made since the last 
		uptime of this device server."

	    ::= { sipSystem 4 }

	activeCalls OBJECT-TYPE
	    SYNTAX  INTEGER ( 0..65535 )
	    MAX-ACCESS  read-only
	    STATUS  current
	    DESCRIPTION
		"Number of calls which are still progressing at this time
		 by this device server"

	    ::= { sipSystem 5 }

	failedCalls OBJECT-TYPE
	    SYNTAX  INTEGER ( 0..65535 )
	    MAX-ACCESS  read-only
	    STATUS  current
	    DESCRIPTION
		"Total Number of calls failed since the last uptime of 
		this device server"

	    ::= { sipSystem 6 }

	reloadConfig OBJECT-TYPE
	    SYNTAX  INTEGER ( 0..1 )
	    MAX-ACCESS  read-write
	    STATUS  current
	    DESCRIPTION
		"This is to tell the device server to load it's 
		configuration again. This is done when some configuration 
		parameters need to be updated in the system "

	    ::= { sipSystem 7 }

	resetLog OBJECT-TYPE
	    SYNTAX  INTEGER ( 0..1 )
	    MAX-ACCESS  read-write
	    STATUS  current
	    DESCRIPTION
		"To discard previous log and to start logging afresh 
		resetLog would be used "

	    ::= { sipSystem 8 }

END
