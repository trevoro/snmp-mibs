CXISDN-MIB DEFINITIONS ::= BEGIN


IMPORTS
   Counter     FROM RFC1155-SMI
   OBJECT-TYPE FROM RFC-1212
   TRAP-TYPE      FROM RFC-1215
   DisplayString     FROM RFC1213-MIB
   cxISDN,SapIndex,Alias   FROM CXProduct-SMI;


isdnSoftwareVersion OBJECT-TYPE
   SYNTAX   DisplayString
   ACCESS   read-only
        STATUS  mandatory
   DESCRIPTION
"Identifies the main version and revision numbers (separated by a period) 
of the ISDN software layer.

Default Value: none"
   ::= { cxISDN 1 }


isdnTraps OBJECT-TYPE
   SYNTAX   INTEGER {
            disabled (1),
            enabled  (2)
            }
   ACCESS   read-write
   STATUS   mandatory
   DESCRIPTION
"Indicates whether this software layer produces the 
isdnCCSapStatusIndication and isdnL3SapStatusIndication traps.

Options:
disabled(1): software layer does not produce CC and L3 status 
indication traps

enabled (1): software layer produces CC and L3 status indication traps

Default Value: disabled

Configuration Changed: administrative "
   DEFVAL { disabled }
   ::= { cxISDN  2 }



--  Lower Service Access Point Configuration Table

--  The table describing:
-- parameters required to configure a lower service access point
-- controls available to manipulate a lower service access point
-- status available for monitoring the current state of the lower service 
-- access point statistics available for monitoring any lower service access 
-- point

--  The Lower Service Access Points here is considered as a the lower access 
--  point of Digital Subscriber Line (DSL) of this module.  In fact, this 
--  lower access point support two SAPs (0 and 16).  This Lower Service 
--  Access Points is used to communicate with one LAPD channel.  So, every 
--  ISDN Basic Rate Interface line (BRI) will be handled by one of these
--  Lower Service Access Point.

--  The default values for all the timers object are the one defined in the 
--  Q.931 CCITT recommendation.


isdnL3SapTable OBJECT-TYPE
   SYNTAX   SEQUENCE OF IsdnL3SapEntry
   ACCESS   not-accessible
   STATUS   mandatory
   DESCRIPTION
"A table containing configuration, controls, status and statistics 
information about each ISDN layer lower service access point."
   ::= { cxISDN 20 }


   isdnL3SapEntry OBJECT-TYPE
      SYNTAX   IsdnL3SapEntry
      ACCESS   not-accessible
      STATUS   mandatory
      DESCRIPTION
"The parameters for a specific lower service access point."
      INDEX { isdnL3SapNumber }
      ::= { isdnL3SapTable 1 }


   IsdnL3SapEntry ::=
      SEQUENCE {
-- Parameters
         isdnL3SapNumber         SapIndex,
         isdnL3SapRowStatus      INTEGER,
         isdnL3SapAlias          Alias,
         isdnL3SapCompanionAlias    Alias,
         isdnL3SapUserNetType    INTEGER,
         isdnL3SapT303Timer         INTEGER,
         isdnL3SapT304Timer         INTEGER,
         isdnL3SapT305Timer         INTEGER,
         isdnL3SapT308Timer         INTEGER,
         isdnL3SapT310Timer         INTEGER,
         isdnL3SapT313Timer         INTEGER,
         isdnL3SapT318Timer         INTEGER,
         isdnL3SapT319Timer         INTEGER,
         isdnL3SapDefTimerCfg    INTEGER,

-- Control
-- Status
         isdnL3SapStatusEvent       INTEGER,
         isdnL3SapDslType        INTEGER,
         isdnL3SapBRIType        INTEGER
-- Statistics        
         }


   isdnL3SapNumber OBJECT-TYPE
      SYNTAX   SapIndex
      ACCESS   read-only
      STATUS   mandatory
      DESCRIPTION
"Indicates the row containing objects for configuring (or monitoring) a 
SAP that is associated with another SAP in the LAPD software layers.

Note: The SAP number has to be the same than the Digital Subscriber Line 
number used in the BCM software layer.

Range of Values: 1-6

Default Value: none"
      ::= { isdnL3SapEntry 1 }


   
   isdnL3SapRowStatus OBJECT-TYPE
      SYNTAX   INTEGER {
               invalid     (1),
               valid    (2)
               }
      ACCESS   read-write
      STATUS   mandatory
      DESCRIPTION
"Determines whether this SAP is to be removed from service (i.e. 
invalidated) within the ISDN software layer.

Options:
invalid (1): row is flagged; after next reset values will be 
disabled and row will be deleted from table

valid (2): values are enabled

Default Value: none

Configuration Changed: administrative "
      ::= { isdnL3SapEntry 2 }


isdnL3SapAlias OBJECT-TYPE
      SYNTAX   Alias
      ACCESS   read-write
      STATUS   mandatory
      DESCRIPTION
"Determines the textual name identifying this lower SAP.

Range of Values: 0-16 alphanumeric characters beginning with a non-numeric 
character

Default Value: none

Configuration Changed: administrative "
      ::= { isdnL3SapEntry 3 }


   isdnL3SapCompanionAlias OBJECT-TYPE
      SYNTAX   Alias
      ACCESS   read-write
      STATUS   mandatory
      DESCRIPTION
"Determines the textual name identifying this SAPs companion SAP in the 
LAPD software layer.

Range of Values: 0-16 alphanumeric characters beginning with a non-numeric 
character

Default Value: none

Configuration Changed: administrative "
      ::= { isdnL3SapEntry 4 }


   isdnL3SapUserNetType OBJECT-TYPE
      SYNTAX   INTEGER {
               user     (1),
               network  (2)
               }
      ACCESS   read-write
      STATUS   mandatory
      DESCRIPTION
"Determines the Basic Rate Interface emulation for this SAP.

Options:
user (1): BRI type is User

network (2): BRI type is Network (for future use)

Default Value: user

Configuration Changed: administrative "
      DEFVAL { user }
      ::= { isdnL3SapEntry 10 }


   isdnL3SapT303Timer OBJECT-TYPE
      SYNTAX   INTEGER (0..255)
      ACCESS   read-write
      STATUS   mandatory
      DESCRIPTION
"Determines the interval in seconds that the ISDN software layer will wait 
for an Alerting, Connect, Setup Acknowledge, Call Proceeding, or Release 
Complete message after sending a Setup message.

Range of Values: 0-255

Default Value: 4

Configuration Changed: administrative "
      DEFVAL { 4 }
      ::= { isdnL3SapEntry 11 }


isdnL3SapT304Timer OBJECT-TYPE
      SYNTAX   INTEGER (0..255)
      ACCESS   read-write
      STATUS   mandatory
      DESCRIPTION
"Determines the interval in seconds that the ISDN software layer will wait 
for a Call Proceeding, Alerting, Connect, or Disconnect message after 
sending an Information message.

Range of Values: 0-255

Default Value: 15

Configuration Changed: administrative "
      DEFVAL { 15 }
      ::= { isdnL3SapEntry 12 }


isdnL3SapT305Timer OBJECT-TYPE
      SYNTAX   INTEGER (0..255)
      ACCESS   read-write
      STATUS   mandatory
      DESCRIPTION
"Determines the interval in seconds that the ISDN software layer will wait 
for a Release or Disconnect message after sending a Disconnect message.

Range of Values: 0-255

Default Value: 30

Configuration Changed: administrative "
      DEFVAL { 30 }
      ::= { isdnL3SapEntry 13 }


isdnL3SapT308Timer OBJECT-TYPE
      SYNTAX   INTEGER (0..255)
      ACCESS   read-write
      STATUS   mandatory
      DESCRIPTION
"Determines the interval in seconds that the ISDN software layer will wait 
for a Release or Release Complete message after sending a Release message.

Range of Values: 0-255

Default Value: 4

Configuration Changed: administrative "
      DEFVAL { 4 }
      ::= { isdnL3SapEntry 14 }


isdnL3SapT310Timer OBJECT-TYPE
      SYNTAX   INTEGER (0..255)
      ACCESS   read-write
      STATUS   mandatory
      DESCRIPTION
"Determines the interval in seconds that the ISDN software layer will wait 
for an Alerting, Connect, Disconnect or Progress message after receiving a 
Call Proceeding message.

Range of Values: 0-255

Default Value: 10

Configuration Changed: administrative "
      DEFVAL { 10 }
      ::= { isdnL3SapEntry 15 }


isdnL3SapT313Timer OBJECT-TYPE
      SYNTAX   INTEGER (0..255)
      ACCESS   read-write
      STATUS   mandatory
      DESCRIPTION
"Determines the interval in seconds that the ISDN software layer will wait 
for a Connect Acknowledge message after sending a Connect message.

Range of Values: 0-255

Default Value: 4

Configuration Changed: administrative "
      DEFVAL { 4 }
      ::= { isdnL3SapEntry 16 }


isdnL3SapT318Timer OBJECT-TYPE
      SYNTAX   INTEGER (0..255)
      ACCESS   read-write
      STATUS   mandatory
      DESCRIPTION
"Determines the interval in seconds that the ISDN software layer will wait 
for a Resume Acknowledge or Resume Reject message after sending a Resume 
message.

Range of Values: 0-255

Default Value: 4

Configuration Changed: administrative "
      DEFVAL { 4 }
      ::= { isdnL3SapEntry 17}

isdnL3SapT319Timer OBJECT-TYPE
      SYNTAX   INTEGER (0..255)
      ACCESS   read-write
      STATUS   mandatory
      DESCRIPTION
"Determines the interval in seconds that the ISDN software layer will wait 
for a Suspend Acknowledge or Suspend Reject message after sending a 
Suspend message.

Range of Values: 0-255

Default Value: 4

Configuration Changed: administrative "
      DEFVAL { 4 }
      ::= { isdnL3SapEntry 18 }


isdnL3SapDefTimerCfg OBJECT-TYPE
      SYNTAX   INTEGER {
               noDefCfg    (1),
               defCfg      (2)
               }
      ACCESS   read-write
      STATUS   mandatory
      DESCRIPTION
"Determines whether isdnL3SapT303Timer, isdnL3SapT304Timer, 
isdnL3SapT305Timer, isdnL3SapT308Timer, isdnL3SapT310Timer, 
isdnL3SapT313Timer, isdnL3SapT318Timer and isdnL3SapT319Timer will revert 
immediately to their default values if the value of this object has 
previously permitted these values to be changed from their defaults.

Options:
noDefCfg (1): timer values can be or have been modified

DefCfg (2): timer value will maintain or return to their defaults

Default Value: DefCfg

Configuration Changed: administrative "
      DEFVAL { defCfg }
      ::= { isdnL3SapEntry 19 }


isdnL3SapStatusEvent OBJECT-TYPE
   SYNTAX   INTEGER {
            noEvent        (1),
            badCfgVersion     (2),
            badDslID       (3),
            dslInUse       (4),
            dslNotInUse       (5),
            noNLCB         (6),
            nlcbInitErr       (7),
            badSwitchType     (8),
            nlcbPoolErr       (9)
            }
   ACCESS   read-only
   STATUS   mandatory
   DESCRIPTION
"Indicates a status generated by the isdnL3SapStatusIndication trap.

Note: This value will always read noEvent unless isdnTraps has been 
enabled and an event has been trapped.

Options:
noEvent (1): no trapped event

badCfgVersion (2): configuration template not current

badDslID (3): wrong Digital Subscriber Line

dslInUse (4): Digital Subscriber Line in use

dslNotInUse (5): Digital Subscriber Line not available

noNLCB (6): network layer control block not available

nlcbInitErr (7): network layer control block initialization error

badSwitchType (8): incorrect switch-type configuration

nlcbPoolErr (9) no more network layer control blocks          Default 
Value: noEvent"
   ::= { isdnL3SapEntry  40 }


isdnL3SapDslType OBJECT-TYPE
   SYNTAX   INTEGER {
               none  (1),
               bri   (2),
               pri   (3)
            }
   ACCESS   read-only
   STATUS   mandatory
   DESCRIPTION
"Indicates the type of physical interface for this SAP.

Options:
none (1): SAP has no interface

bri (2) SAP uses a Basic Rate Interface

pri (3) SAP uses a Primary Rate Interface

Default Value: none"
   ::= { isdnL3SapEntry 41 }


isdnL3SapBRIType OBJECT-TYPE
      SYNTAX   INTEGER {
               none  (1),
               u  (2),
               s-t   (3)
               }
      ACCESS   read-only
      STATUS   mandatory
      DESCRIPTION
"Indicates the BRI type for this SAP.

Options:
none (1): SAP has no BRI interface

u (2): BRI type is U

s-t (3): BRI type is S/T

Default Value: none"
      DEFVAL { none }
      ::= { isdnL3SapEntry 42 }


--  Upper Service Access Point Configuration Table

--  The table describing:
-- parameters required to modify parameters at a upper service access point
-- controls available to manipulate a upper service access point
-- status available for monitoring the current state of the upper service 
-- access point
-- statistics available for monitoring any upper service access point


isdnCCSapTable OBJECT-TYPE
   SYNTAX   SEQUENCE OF IsdnCCSapEntry
   ACCESS   not-accessible
   STATUS   mandatory
   DESCRIPTION
"A table containing configuration information about each upper service 
access point."
   ::= { cxISDN 21 }


   isdnCCSapEntry OBJECT-TYPE
      SYNTAX   IsdnCCSapEntry
      ACCESS   not-accessible
      STATUS   mandatory
      DESCRIPTION
"The parameters for a specific upper service access point."
      INDEX { isdnCCSapNumber }
      ::= { isdnCCSapTable 1 }


   IsdnCCSapEntry ::=
      SEQUENCE {
-- Parameters
         isdnCCSapNumber         SapIndex,
         isdnCCSapRowStatus         INTEGER,
         isdnCCSapAlias       Alias,
         isdnCCSapSwitchType        INTEGER,
         isdnCCSapInitTerminal         INTEGER,
         isdnCCSapDNRouting         INTEGER,
         isdnCCSapBearerRouting     INTEGER,
         isdnCCSapBearerType        INTEGER,
         isdnCCSapDirectoryNumber      DisplayString,
         isdnCCSapSPID        DisplayString,
         isdnCCSapSubAddress        DisplayString,
         isdnCCSapT415Timer         INTEGER,
-- Control
-- Status
         isdnCCSapStatusEvent       INTEGER,
         isdnCCSapInUse       INTEGER,
         isdnCCSapActiveCalls       Counter
-- Statistics
         }


   isdnCCSapNumber OBJECT-TYPE
      SYNTAX   SapIndex
      ACCESS   read-only
      STATUS   mandatory
      DESCRIPTION
"Indicates the row containing objects for configuring (or monitoring) a 
SAP that is associated with the corresponding SAP in the BCM software 
layer.

Note: The SAP number has to be the same than the Digital Subscriber Line 
number used in the BCM software layer.

Range of Values: 1-6

Default Value: none"
      ::= { isdnCCSapEntry 1 }


   isdnCCSapRowStatus OBJECT-TYPE
      SYNTAX   INTEGER {
               invalid     (1),
               valid    (2)
               }
      ACCESS   read-write
      STATUS   mandatory
      DESCRIPTION
"Determines whether this SAP is to be removed from service (i.e. 
invalidated) within the ISDN software layer.

Options:
invalid (1): row is flagged; after next reset values will be 
disabled and row will be deleted from table

valid (2): values are enabled

Default Value: none

Configuration Changed: administrative "
      ::= { isdnCCSapEntry 2 }


   isdnCCSapAlias OBJECT-TYPE
      SYNTAX   Alias
      ACCESS   read-write
      STATUS   mandatory
      DESCRIPTION
"Determines the textual name identifying this upper SAP.

Range of Values:0-16 alphanumeric characters beginning with a non-numeric 
character

Default Value: none

Configuration Changed: administrative "
      ::= { isdnCCSapEntry 3 }


   isdnCCSapSwitchType OBJECT-TYPE
      SYNTAX   INTEGER {
               unspecified    (1),
               bri-1TR6    (2),  -- Germany / 1TR6
               bri-5ESS    (3),  -- U.S.A     /  At&T 5ESS
               bri-CCITT      (4),  -- CCITT Q.931
               bri-DMS100     (5),  -- U.S.A / Norther Telecom 
               bri-KDD     (6),  -- Japan / KDD
               bri-NET3    (7),  -- Europe / Net3
               bri-NI1     (8),  -- U.S.A / National ISDN 1
               bri-NI2     (9),  -- U.S.A / National ISDN 2
               bri-NTT     (10), -- Japan / NTT
               bri-TS013      (11), -- Australia / TS013
               bri-VN      (12)  -- France / VN
               }
      ACCESS   read-write
      STATUS   mandatory
      DESCRIPTION
"Determines the type of protocol supported by the switch providing the CX 
900 with ISDN access.

Options:
unspecified (1): unspecified

bri-1TR6 (2): Germany / 1TR6

bri-5ESS (3): U.S.A / At&T 5ESS

bri-CCITT (4): CCITT Q.931

bri-DMS100 (5): U.S.A / Norther Telecom

bri-KDD (6): Japan / KDD

bri-NET3 (7): Europe / Net3

bri-NI1 (8): U.S.A / National ISDN 1

bri-NI2 (9): U.S.A / National ISDN 2

bri-NTT (10): Japan / NTT

bri-TS013 (11): Australia / TS013

bri-VN (12): France / VN

Default Value: bri-NI1

Configuration Changed: administrative "
                DEFVAL { bri-NI1 }
      ::= { isdnCCSapEntry 10 }


   isdnCCSapInitTerminal OBJECT-TYPE
      SYNTAX   INTEGER {
               nit   (1),  -- Non-Initializing Terminal
               fit   (2)   -- Fully Initializing Terminal
               }
      ACCESS   read-write
      STATUS   mandatory
      DESCRIPTION
"Determines the initializing characteristics of the ISDN software layer of 
the CX 900.

Options:
nit (1): non-initializing terminal

fit (2) fully-initializing terminal (North American

Note: FIT requires terminal registration.

Default Value: nit

Configuration Changed: administrative "
      DEFVAL { nit }
      ::= { isdnCCSapEntry 11}


   isdnCCSapDNRouting OBJECT-TYPE
      SYNTAX   INTEGER {
               no (1),
               yes   (2)
               }
      ACCESS   read-write
      STATUS   mandatory
      DESCRIPTION
"Determines whether incoming calls will be checked against End-Point ID 
(EPID).

Options:
no (1): incoming call not checked against EPID

yes (2): incoming call checked against EPID

Note: Incoming call not containing EPID will be checked against Directory 
Number (DN).

Default Value: no

Configuration Changed: administrative "
      DEFVAL { no }
      ::= { isdnCCSapEntry 12 }


   isdnCCSapBearerRouting OBJECT-TYPE
      SYNTAX   INTEGER {
               no (1),
               yes   (2)
               }
      ACCESS   read-write
      STATUS   mandatory
      DESCRIPTION
"Determines whether incoming calls will be checked against the bearer-type 
specified in isdnCCSapBearerType

Options:
no (1): incoming call not checked against bearer-type

yes (2): incoming call checked against bearer-type

Default Value: no

Configuration Changed: administrative "
      DEFVAL { no }
      ::= { isdnCCSapEntry 13 }


   isdnCCSapBearerType OBJECT-TYPE
      SYNTAX   INTEGER {
               voice-call        (1),
               circuit-sw-data-call    (2),
               packet-sw-data-call     (3)
               }
      ACCESS   read-write
      STATUS   mandatory
                DESCRIPTION
"Determines the bearer-type that will be checked if isdnCCSapBearerType is 
set to yes.

Options:
voice call (1): call is voice

circuit-sw-data-call (2): call is circuit- switched data

packet-sw-data-call (3): call is packet- switched data

Default Value: circuit-sw-data-call

Configuration Changed: administrative "
      DEFVAL { circuit-sw-data-call }
      ::= { isdnCCSapEntry 14 }


   isdnCCSapDirectoryNumber OBJECT-TYPE
      SYNTAX   DisplayString
      ACCESS   read-write
      STATUS   mandatory
      DESCRIPTION
"Determines the address or calling number assigned to the subcriber 
interface of the CX900.

Range of Values: 0-16 numeric characters (namely, 0123456789*#)

Default Value: none

Configuration Changed: administrative "
      DEFVAL { "" }
      ::= { isdnCCSapEntry 15 }

         
   isdnCCSapSPID OBJECT-TYPE
      SYNTAX   DisplayString
      ACCESS   read-write
      STATUS   mandatory
      DESCRIPTION
"Determines the Service Profile Identifier (SPID) for the subscriber 
interface of the CX900. This object is meaningful only in North America. 
SPIDs are required for DMS-100 and NI-1 switches but optional for 5ESS 
switches.

Range of Values: 0-20

Default Value: none

Configuration Changed: administrative "
      DEFVAL { "" }
      ::= { isdnCCSapEntry 16 }


   isdnCCSapSubAddress OBJECT-TYPE
      SYNTAX   DisplayString
      ACCESS   read-write
      STATUS   mandatory
      DESCRIPTION
"Determines the subaddress (DSS1) that can be used with object 
isdnCCSapDirectoryNumber to specify an end-point user to be reached.

Range of Values: 0-20

Default Value: none

Configuration Changed: administrative "
      DEFVAL { "" }
      ::= { isdnCCSapEntry 17 }


   isdnCCSapT415Timer   OBJECT-TYPE
      SYNTAX      INTEGER (0..255)
      ACCESS      read-write
      STATUS      mandatory
      DESCRIPTION
"Determines the interval in seconds that the ISDN software layer will wait 
for completion of terminal initialization. If the Information and SPID 
messages fail during this interval, they will be permitted only one 
retransmission.

Range of Values: 0-255

Default Value: 20

Configuration Changed: administrative "
      DEFVAL { 20 }
      ::= { isdnCCSapEntry 18 }


isdnCCSapStatusEvent OBJECT-TYPE
   SYNTAX   INTEGER {
            noEvent        (1),
            badCfgVersion     (2),
            badDslID       (3),
            badCes         (4),
            badSwitchType     (5),
            cbPollErr         (6),
            dslInUseErr       (7),
            dslNotCfgErr         (8),
            dslNotInUse       (9),
            noHostCB       (10),
            noT415         (11)
            }
   ACCESS   read-only
   STATUS   mandatory
   DESCRIPTION

"Indicates a status generated by the isdnCCSapStatusIndication trap.

Note: This value will always read noEvent unless isdnTraps has been 
enabled and an event has been trapped.

Options:
noEvent (1): no trapped event

badCfgVersion (2): configuration template not current

badDslID (3): wrong Digital Subscriber Line

badCes (4): bad connection end-point

badSwitchType (5): incorrect switch-type configuration

cbPollErr (6): call control block error

dslInUseErr (7): Digital Subscriber Line in use

dslNotCfgErr (8): Digital Subscriber Line not configured

dslNotInUse (9): Digital Subscriber Line not available

noHostCB (10): no host control block

noT415 (11): no T415 timer

Default Value: noEvent"
   ::= { isdnCCSapEntry 40 }


   isdnCCSapInUse OBJECT-TYPE
      SYNTAX   INTEGER {   no (1),
                  yes   (2)
                    }
      ACCESS   read-only
      STATUS   mandatory
      DESCRIPTION
"Indicates whether this upper SAP has been properly initialized and is now 
in use.

Options:
no (1): SAP has not been initialized

yes (2): SAP is in use

Default Value: none"
      ::= { isdnCCSapEntry 41 }


   isdnCCSapActiveCalls OBJECT-TYPE
      SYNTAX   Counter
      ACCESS   read-only
      STATUS   mandatory
      DESCRIPTION
"Indicates the current number of active calls at this SAP.

Range of Values: 0-2

Default Value: none"
      ::= { isdnCCSapEntry 42 }

-- Debug Table

-- This table is used to get log files of different structure of the code to 
-- be debugged.
-- The table are the following:
--    L3:   NLCBs (Network Link Control Block structure)
--    CC:   CCDsl  (Call Control Dsl context structure)
--    CC:   HCB (Host Control Block structure)
--    CC:   CCB (Call Control Block structures)
-- "L3" being the "layer 3", and "CC" being the "Call Control" layer.


isdnDebugTable OBJECT-TYPE
   SYNTAX   SEQUENCE OF IsdnDebugEntry
   ACCESS   not-accessible
   STATUS   mandatory
   DESCRIPTION
"A table containing control to access debugging information."
   ::= { cxISDN 22 }


   isdnDebugEntry OBJECT-TYPE
      SYNTAX   IsdnDebugEntry
      ACCESS   not-accessible
      STATUS   mandatory
      DESCRIPTION
"The parameters for a specific structure debugging information."
      INDEX { isdnDebugNumber }
      ::= { isdnDebugTable 1 }


   IsdnDebugEntry ::=
      SEQUENCE {
         isdnDebugNumber            SapIndex,
         isdnDebugCCB            INTEGER,
         isdnDebugHCB            INTEGER,
         isdnDebugCCDsl          INTEGER,
         isdnDebugNLCB           INTEGER
         }


   isdnDebugNumber OBJECT-TYPE
      SYNTAX   SapIndex
      ACCESS   read-only
      STATUS   mandatory
      DESCRIPTION
"Indicates the row containing objects for creating diagnostic files for 
this upper SAP.

Range of Values: 1-6

Default Value: none"
      ::= { isdnDebugEntry 1 }


   isdnDebugCCB  OBJECT-TYPE
      SYNTAX   INTEGER
      ACCESS   write-only
      STATUS   mandatory
      DESCRIPTION
"Creates a file that includes the following Call Control Block 
information:

- DSL = #XX
- CCB = #XX
- State = 0xXXXX
- CallType = 0xXXXX
- B-Chan = 0xXXXX
- Call-ID = 0xXXXX
- CallRef = 0xXXXX
- Ces = 0xXX
- Sapi = 0xXX
- MakePrivateMsg = 0xXX
- H cbIndex = 0xXXXX
- CallRefLen = 0xXXXX
- Cause = 0xXXXX
- Host-Specifier = 0xXXXX
- Host-ID = 0xXXXX
- SendClearConf = 0xXX
- Diagnostics = 0xXX
- CollectAddress = 0xXX
- Service = 0xXXXX"
      ::= { isdnDebugEntry 10 }

   isdnDebugHCB  OBJECT-TYPE
      SYNTAX   INTEGER
      ACCESS   write-only
      STATUS   mandatory
      DESCRIPTION
"Creates a file that includes the following Host Control Block 
information:

- DSL = #XX
- HCB = #XX
- Directory = XXXXXXXXXXXXXXXXXXXX
- SPID =  XXXXXXXXXXXXXXXXXXXX

epid(0)

- epsf = 0xXX
- usid = 0xXXXX
- tid = 0xXXXX

epid[1]

- epsf = 0xXX
- usid = 0xXXXX
- tid = 0xXXXX

- Busy[0] = 0xXX,
- Busy[1] = 0xXX
- Terminal-state = 0xXX
- Timer-T415 = 0xXXXX
- Bearer-Routing = 0xXX
- Host-ID   = 0xXXXX
- Ces = 0xXX
- Initializing-Terminal = 0xXX"
      ::= { isdnDebugEntry 11 }



   isdnDebugCCDsl OBJECT-TYPE
      SYNTAX   INTEGER
      ACCESS   write-only
      STATUS   mandatory
      DESCRIPTION
"Creates a file that includes the following Call Control DSL information:

- DSL = #XX
- InUse = 0xXXXX
- ActiveCCBs = 0xXXXX
- Cause-Location = XXXXXX
- Cd-Numb-Plan = XXXXXX
- Cd-Numb-Type = XXXXXX
- Cd-Sub-Type = XXXXXX
- Cr-Numb-Plan = XXXXXX
- Cr-Numb-Type = XXXXXX
- Cr-Prest-Ind = XXXXXX
- Cr-Scrn-Ind = XXXXXX
- Cr-Sub-Type = XXXXXX
- Facility-Code = XXXXXX
- HL-Coding-Std = XXXXXX
- HL-Interpret = XXXXXX
- HL-Presentat = XXXXXX
- HL-Teleservice = XXXXXX
- L2-Prot = XXXXXX
- L3-Prot = XXXXXX
- Sig-Val = XXXXXX
- Status = XXXXXX
- Transmit-Attr = XXXXXX
- Xfer-Cap = XXXXXX
- Xfer-Mode = XXXXXX
- Xfer-Prot = XXXXXX
- Xfer-Rate = XXXXXX
- Prog-Coding = XXXXXX
- Prog-Loc = XXXXX
- Prog-desc = XXXXXX
- Ind-Val = XXXXXX"
      ::= { isdnDebugEntry 12 }


   isdnDebugNLCB  OBJECT-TYPE
      SYNTAX   INTEGER
      ACCESS   write-only
      STATUS   mandatory
      DESCRIPTION
"Creates a file that includes the following Network Link Control Block 
information:

- DSL = #XX
- NLCB = #XX
- DslID = 0xXXXX
- Ces = 0xXX
- CallID = 0xXXXX
- ChanID = 0xXXXX
- CallReflen = 0xXX
- CallRef = 0xXXXX
- State = 0xXXXX
- Event = 0xXXXX
- Timer-T304 = 0xXXXX
- Timer-T310 = 0xXXXX
- T303-First = 0xXX
- T308-First = 0xXX
- T313-First = 0xXX
- UserOriginated = 0xXX
- Internal = 0xXX
- Cause = 0xXX
- PreviousCause = 0xXX"
      ::= { isdnDebugEntry 13 }

-- Traps

isdnL3SapStatusIndication  TRAP-TYPE
   ENTERPRISE cxISDN
   VARIABLES      {  isdnL3SapNumber,
               isdnL3SapStatusEvent
            }
   DESCRIPTION
"Indicates that an event specified in isdnL3SapStatusEvent has occurred."
::= 1




isdnCCSapStatusIndication  TRAP-TYPE
   ENTERPRISE cxISDN
   VARIABLES      {  isdnCCSapNumber,
               isdnCCSapStatusEvent
            }
   DESCRIPTION
"Indicates that an event specified in isdnCCSapStatusEvent has occurred."
::= 2

      
END
