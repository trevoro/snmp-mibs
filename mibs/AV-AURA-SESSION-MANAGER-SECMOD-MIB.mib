-- Avaya Aura Session Manager MIB
-- Copyright (c) 2008-2009 by Avaya Inc. All rights reserved. 
-- MIB version 1.0.0 
-- Avaya Compas ID: NA

AV-AURA-SESSION-MANAGER-SECMOD-MIB DEFINITIONS ::= BEGIN

-- Add your MIB specific imports in the below import section.
IMPORTS 
MODULE-IDENTITY, OBJECT-TYPE, NOTIFICATION-TYPE, enterprises
    FROM SNMPv2-SMI
InetAddressIPv6
    FROM INET-ADDRESS-MIB
MODULE-COMPLIANCE, OBJECT-GROUP
    FROM SNMPv2-CONF
SnmpAdminString
    FROM SNMP-FRAMEWORK-MIB
DateAndTime
    FROM SNMPv2-TC;

        
--
-- The following are defined in Avaya Aura Session Manager-MIB
--
avaya              OBJECT IDENTIFIER ::= { enterprises 6889 }
products           OBJECT IDENTIFIER ::= { avaya 1 }
mibs               OBJECT IDENTIFIER ::= { avaya 2 }

avAuraSessMgrProd OBJECT IDENTIFIER ::= { products 36 }
avAuraSessMgrMibs MODULE-IDENTITY
       LAST-UPDATED "201301211353Z" -- 21 January 2013
       ORGANIZATION "Avaya, Inc."
       CONTACT-INFO "Avaya Customer Services

                     Postal: Avaya, Inc.
                             211 Mount Airy Rd
                             Basking Ridge. NJ 07920
                             USA
                             Tel: +1 908 953 6000
                             WWW: http://www.avaya.com"
       DESCRIPTION "This MIB module is for exposing Avaya Aura Session Manager inventory information via SNMP GET."
       
       REVISION 	"201301211353Z" -- 21 January 2013
       DESCRIPTION "MIB Version 1.0.0 - autobuild. Generated via the MIBTOOL."
             
       
       ::= { mibs 36 }

avAuraSessMgrMibNotifications OBJECT IDENTIFIER ::= { avAuraSessMgrMibs 0 }

avAuraSessMgrMibObjects OBJECT IDENTIFIER ::= { avAuraSessMgrMibs 1 }
avAuraSessMgrMibConformance OBJECT IDENTIFIER ::= { avAuraSessMgrMibs 2 }

-- Avaya Aura Session Manager Notifications (avAuraSessMgrMibNotifications) will be added here
-----------------------------------------------------------------------
-- According to RFC 2578 section 8.5, the next to last sub-identifier
-- in the name of any newly defined notification must have the value
-- zero. This is to achieve compatibility with SNMPv1 traps.
------------------------------------------------------------------------
-------------------NOTIFICATION OBJECTS *********************************START
avSessMgrAASL10900 NOTIFICATION-TYPE
	STATUS current
	DESCRIPTION
	"Certificate load failure(Major)"
	::= { avAuraSessMgrMibNotifications 421 }

avSessMgrAASL10902 NOTIFICATION-TYPE
	STATUS current
	DESCRIPTION
	"Failed binding a listener, the given address is in use or an invalid interface(Major)"
	::= { avAuraSessMgrMibNotifications 423 }

avSessMgrAASL10903 NOTIFICATION-TYPE
	STATUS current
	DESCRIPTION
	"The connection limit has been exceeded for remote IP using transport(Warning)"
	::= { avAuraSessMgrMibNotifications 425 }

avSessMgrAPLM10300 NOTIFICATION-TYPE
	STATUS current
	DESCRIPTION
	"Failure pinholing Network firewall(Major)"
	::= { avAuraSessMgrMibNotifications 431 }

avSessMgrAPLM10302 NOTIFICATION-TYPE
	STATUS current
	DESCRIPTION
	"Failure configuring network parameters(Major)"
	::= { avAuraSessMgrMibNotifications 433 }

avSessMgrAPLM10304 NOTIFICATION-TYPE
	STATUS current
	DESCRIPTION
	"Security Module Interface is down(Major)"
	::= { avAuraSessMgrMibNotifications 435 }

avSessMgrAFWL16002 NOTIFICATION-TYPE
	STATUS current
	DESCRIPTION
	"SIP firewall deep inspection configuration update failed, retaining existing configuration(Minor)"
	::= { avAuraSessMgrMibNotifications 441 }

avSessMgrAFWL16003 NOTIFICATION-TYPE
	STATUS current
	DESCRIPTION
	"SIP firewall configuration failed schema validation(Minor)"
	::= { avAuraSessMgrMibNotifications 443 }

avSessMgrAFWL16501 NOTIFICATION-TYPE
	STATUS current
	DESCRIPTION
	"SIP firewall action matched rule(Warning)"
	::= { avAuraSessMgrMibNotifications 445 }

avSessMgrAFWL17503 NOTIFICATION-TYPE
	STATUS current
	DESCRIPTION
	"SIP firewall blacklist configuration update failed, retaining existing configuration(Minor)"
	::= { avAuraSessMgrMibNotifications 447 }

avSessMgrAFWL17504 NOTIFICATION-TYPE
	STATUS current
	DESCRIPTION
	"SIP firewall whitelist configuration update failed, retaining existing configuration(Minor)"
	::= { avAuraSessMgrMibNotifications 449 }

avSessMgrAFWL16504 NOTIFICATION-TYPE
	STATUS current
	DESCRIPTION
	"SIP firewall loop detection(Minor)"
	::= { avAuraSessMgrMibNotifications 4411 }

avSessMgrAWTC10405 NOTIFICATION-TYPE
	STATUS current
	DESCRIPTION
	"Identity certificate is about to expire(Warning)"
	::= { avAuraSessMgrMibNotifications 451 }

avSessMgrAWTC10406 NOTIFICATION-TYPE
	STATUS current
	DESCRIPTION
	"Identity certificate has expired(Critical)"
	::= { avAuraSessMgrMibNotifications 453 }

avSessMgrANFW11001 NOTIFICATION-TYPE
	STATUS current
	DESCRIPTION
	"Network firewall stopped(Warning)"
	::= { avAuraSessMgrMibNotifications 461 }

avSessMgrANFW11002 NOTIFICATION-TYPE
	STATUS current
	DESCRIPTION
	"SM100 Network Firewall critical event(Warning)"
	::= { avAuraSessMgrMibNotifications 463 }

-------------------NOTIFICATION OBJECTS*******************************************END
END
