--			Ascend mibimagroup MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBIMAGROUP-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibimaGroupConfig  OBJECT IDENTIFIER ::= { configuration 23}

	-- The mibimaGroupConfig table
	--
	-- This table contains parameters for the mibimaGroupConfig profile
	--

    mibimaGroupConfigTable	OBJECT-TYPE
	SYNTAX		SEQUENCE OF MibimaGroupConfigEntry
	ACCESS		not-accessible
	STATUS		mandatory
	DESCRIPTION	"A list of mibimaGroupConfig profile entries."
	::= { mibimaGroupConfig 1 }

    mibimaGroupConfigEntry	OBJECT-TYPE
	SYNTAX		MibimaGroupConfigEntry
	ACCESS		not-accessible
	STATUS		mandatory
	DESCRIPTION	"A mibimaGroupConfig entry containing objects that
			 maps to the parameters of mibimaGroupConfig profile."
	INDEX		{ imaGroupConfig-Name }
	::= { mibimaGroupConfigTable 1 }

    MibimaGroupConfigEntry ::=
	SEQUENCE {
	    imaGroupConfig-Name
		DisplayString,
	    imaGroupConfig-Active
		INTEGER,
	    imaGroupConfig-NailedGroup
		INTEGER,
	    imaGroupConfig-GroupSymmetryMode
		INTEGER,
	    imaGroupConfig-Version
		INTEGER,
	    imaGroupConfig-DoVersionFallback
		INTEGER,
	    imaGroupConfig-IgnoreLineup
		INTEGER,
	    imaGroupConfig-Lasr
		INTEGER,
	    imaGroupConfig-NeTxClkMode
		INTEGER,
	    imaGroupConfig-TxMinNumLinks
		INTEGER,
	    imaGroupConfig-RxMinNumLinks
		INTEGER,
	    imaGroupConfig-ImaId
		INTEGER,
	    imaGroupConfig-FrameLength
		INTEGER,
	    imaGroupConfig-DiffDelayMax
		INTEGER,
	    imaGroupConfig-CheckFarEndImaId
		INTEGER,
	    imaGroupConfig-ExpectedFarEndImaId
		INTEGER,
	    imaGroupConfig-FarEndCheckFrameLength
		INTEGER,
	    imaGroupConfig-ExpectedFarEndFrameLength
		INTEGER,
	    imaGroupConfig-AtmIfDelay
		INTEGER,
	    imaGroupConfig-TppTestLink
		INTEGER,
	    imaGroupConfig-TppTestPattern
		INTEGER,
	    imaGroupConfig-TppState
		INTEGER,
	    imaGroupConfig-VpSwitchingVpi
		INTEGER,
	    imaGroupConfig-Action-o
		INTEGER
	}

    imaGroupConfig-Name	OBJECT-TYPE
	SYNTAX	DisplayString
	ACCESS	read-only
	STATUS	mandatory
	DESCRIPTION	"Name of IMA Group Config profile."
	::= { mibimaGroupConfigEntry 1 }

    imaGroupConfig-Active	OBJECT-TYPE
	SYNTAX	INTEGER {
		    no (1),
		    yes (2)
		}
	ACCESS	read-write
	STATUS	mandatory
	DESCRIPTION	"TRUE if the line is enabled, otherwise FALSE."
	::= { mibimaGroupConfigEntry 2 }

    imaGroupConfig-NailedGroup	OBJECT-TYPE
	SYNTAX	INTEGER
	ACCESS	read-write
	STATUS	mandatory
	DESCRIPTION	"The nailed group to which this IMA group belongs to"
	::= { mibimaGroupConfigEntry 3 }

    imaGroupConfig-GroupSymmetryMode	OBJECT-TYPE
	SYNTAX	INTEGER {
		    symmetricOperation (2),
		    asymmetricOperation (3),
		    configurationAsymmetric (4)
		}
	ACCESS	read-write
	STATUS	mandatory
	DESCRIPTION	"Symmetry mode of group to which this link belongs to"
	::= { mibimaGroupConfigEntry 4 }

    imaGroupConfig-Version	OBJECT-TYPE
	SYNTAX	INTEGER {
		    v10 (2),
		    v11 (4)
		}
	ACCESS	read-write
	STATUS	mandatory
	DESCRIPTION	"IMA spec version"
	::= { mibimaGroupConfigEntry 5 }

    imaGroupConfig-DoVersionFallback	OBJECT-TYPE
	SYNTAX	INTEGER {
		    no (1),
		    yes (2)
		}
	ACCESS	read-write
	STATUS	mandatory
	DESCRIPTION	"Automatically fall back to v 1.0 if FE is detected to be v 1.0, otherwise move to configAborted state"
	::= { mibimaGroupConfigEntry 6 }

    imaGroupConfig-IgnoreLineup	OBJECT-TYPE
	SYNTAX	INTEGER {
		    systemDefined (1),
		    no (2),
		    yes (3)
		}
	ACCESS	read-write
	STATUS	mandatory
	DESCRIPTION	"Ignore line up value for this IMA Group."
	::= { mibimaGroupConfigEntry 24 }

    imaGroupConfig-Lasr	OBJECT-TYPE
	SYNTAX	INTEGER {
		    no (1),
		    yes (2)
		}
	ACCESS	read-write
	STATUS	mandatory
	DESCRIPTION	"enable/disable LASR (Link addition and slow recovery) procedures"
	::= { mibimaGroupConfigEntry 7 }

    imaGroupConfig-NeTxClkMode	OBJECT-TYPE
	SYNTAX	INTEGER {
		    ctc (2),
		    itc (3)
		}
	ACCESS	read-write
	STATUS	mandatory
	DESCRIPTION	"Group Clocking mode"
	::= { mibimaGroupConfigEntry 8 }

    imaGroupConfig-TxMinNumLinks	OBJECT-TYPE
	SYNTAX	INTEGER
	ACCESS	read-write
	STATUS	mandatory
	DESCRIPTION	"Minimum Number of Tx Links to be active for group to remain in operational state"
	::= { mibimaGroupConfigEntry 9 }

    imaGroupConfig-RxMinNumLinks	OBJECT-TYPE
	SYNTAX	INTEGER
	ACCESS	read-write
	STATUS	mandatory
	DESCRIPTION	"Minimum Number of Rx Links to be active for group to remain in operational state"
	::= { mibimaGroupConfigEntry 10 }

    imaGroupConfig-ImaId	OBJECT-TYPE
	SYNTAX	INTEGER
	ACCESS	read-write
	STATUS	mandatory
	DESCRIPTION	"IMA ID of the group"
	::= { mibimaGroupConfigEntry 11 }

    imaGroupConfig-FrameLength	OBJECT-TYPE
	SYNTAX	INTEGER {
		    n-32 (33),
		    n-64 (65),
		    n-128 (129),
		    n-256 (257)
		}
	ACCESS	read-write
	STATUS	mandatory
	DESCRIPTION	"Frame length for the group (M)"
	::= { mibimaGroupConfigEntry 12 }

    imaGroupConfig-DiffDelayMax	OBJECT-TYPE
	SYNTAX	INTEGER
	ACCESS	read-write
	STATUS	mandatory
	DESCRIPTION	"Maximum differential delay of group in msec"
	::= { mibimaGroupConfigEntry 13 }

    imaGroupConfig-CheckFarEndImaId	OBJECT-TYPE
	SYNTAX	INTEGER {
		    no (1),
		    yes (2)
		}
	ACCESS	read-write
	STATUS	mandatory
	DESCRIPTION	"check/compare the expected-far-end-ima-id with the far-end IMA ID during group start up"
	::= { mibimaGroupConfigEntry 14 }

    imaGroupConfig-ExpectedFarEndImaId	OBJECT-TYPE
	SYNTAX	INTEGER
	ACCESS	read-write
	STATUS	mandatory
	DESCRIPTION	"if check-far-end-ima-id set to yes, then the far-end IMA ID is compared against this number during group startup, GSM moves to ConfigAborted if it does not match"
	::= { mibimaGroupConfigEntry 15 }

    imaGroupConfig-FarEndCheckFrameLength	OBJECT-TYPE
	SYNTAX	INTEGER {
		    no (1),
		    yes (2)
		}
	ACCESS	read-write
	STATUS	mandatory
	DESCRIPTION	"check/compare the Expected frame length with the far-end frame length during group start up"
	::= { mibimaGroupConfigEntry 16 }

    imaGroupConfig-ExpectedFarEndFrameLength	OBJECT-TYPE
	SYNTAX	INTEGER {
		    n-32 (33),
		    n-64 (65),
		    n-128 (129),
		    n-256 (257)
		}
	ACCESS	read-write
	STATUS	mandatory
	DESCRIPTION	"If far-end-check-frame-length is set to yes, then the far-end frame length is compared against this number during group startup, GSM moves to ConfigAborted, if it does not match."
	::= { mibimaGroupConfigEntry 17 }

    imaGroupConfig-AtmIfDelay	OBJECT-TYPE
	SYNTAX	INTEGER
	ACCESS	read-write
	STATUS	mandatory
	DESCRIPTION	"minimum time (in seconds) between the subsequent ATM layer (ie IDCR changes) indications"
	::= { mibimaGroupConfigEntry 18 }

    imaGroupConfig-TppTestLink	OBJECT-TYPE
	SYNTAX	INTEGER
	ACCESS	read-write
	STATUS	mandatory
	DESCRIPTION	"Designate a link index as the test link for use in the Test Pattern Procedure."
	::= { mibimaGroupConfigEntry 19 }

    imaGroupConfig-TppTestPattern	OBJECT-TYPE
	SYNTAX	INTEGER
	ACCESS	read-write
	STATUS	mandatory
	DESCRIPTION	"The test pattern transmitted in the ICP cell (octet 17) on the link during the IMA Test Pattern Procedure."
	::= { mibimaGroupConfigEntry 20 }

    imaGroupConfig-TppState	OBJECT-TYPE
	SYNTAX	INTEGER {
		    disabled (2),
		    operating (3)
		}
	ACCESS	read-write
	STATUS	mandatory
	DESCRIPTION	"Enable or disable the Test Pattern Procedure."
	::= { mibimaGroupConfigEntry 21 }

    imaGroupConfig-VpSwitchingVpi	OBJECT-TYPE
	SYNTAX	INTEGER
	ACCESS	read-write
	STATUS	mandatory
	DESCRIPTION	"The Vpi to be used for the VP switching. Rest of the valid VPIs in valid vpi-vci-range will be used for the VC switching. Changes in this range will take effect immediately. THE USER SHOULD BE VERY CAREFUL WHILE CHANGING THIS VALUE BECAUSE ALL CONNECTIONS ON THE LIM WHERE THIS PORT BELONGS WILL BE DROPPED IN ORDER TO MAKE THIS NEW VALUE EFFECTIVE IMMEDIATELY."
	::= { mibimaGroupConfigEntry 22 }

    imaGroupConfig-Action-o	OBJECT-TYPE
	SYNTAX	INTEGER {
		    noAction (1),
		    createProfile (2),
		    deleteProfile (3)
		}
	ACCESS	read-write
	STATUS	mandatory
	DESCRIPTION	""
	::= { mibimaGroupConfigEntry 23 }

END
