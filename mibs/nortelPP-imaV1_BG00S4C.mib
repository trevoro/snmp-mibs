Nortel-Magellan-Passport-ImaMIB
DEFINITIONS ::= BEGIN



IMPORTS

      OBJECT-TYPE
   FROM RFC-1212

      passportMIBs
   FROM Nortel-Magellan-Passport-UsefulDefinitionsMIB

      Counter32,
      DisplayString,
      StorageType,
      RowStatus,
      PassportCounter64,
      Gauge32,
      Integer32,
      Unsigned32
   FROM Nortel-Magellan-Passport-StandardTextualConventionsMIB

      AsciiString,
      Hex,
      NonReplicated,
      Link
   FROM Nortel-Magellan-Passport-TextualConventionsMIB

      lpIndex,
      lp
   FROM Nortel-Magellan-Passport-LogicalProcessorMIB;




-- LAST-UPDATED   "9808030000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     Ima Enterprise MIB."

imaMIB OBJECT IDENTIFIER ::= { passportMIBs 115 }










-- Lp/n InverseMultiplexerAtm/n
-- This component is used to define an inverse multiplexing for ATM 
-- (IMA) group. IMA provides a data rate greater than DS1/E1 in 
-- increments of DS1/E1.

lpIma OBJECT IDENTIFIER ::= { lp 22 }



lpImaRowStatusTable OBJECT-TYPE
   SYNTAX     SEQUENCE OF LpImaRowStatusEntry
   ACCESS     not-accessible
   STATUS     mandatory
   DESCRIPTION
     "This entry controls the addition and deletion of 
      lpIma components."
::= { lpIma 1 }

lpImaRowStatusEntry OBJECT-TYPE
   SYNTAX     LpImaRowStatusEntry
   ACCESS     not-accessible
   STATUS     mandatory
   DESCRIPTION
     "A single entry in the table represents a single 
      lpIma component."
   INDEX {
      lpIndex,
      lpImaIndex }
::= { lpImaRowStatusTable 1 }

LpImaRowStatusEntry ::= SEQUENCE {
   lpImaRowStatus
      RowStatus,
   lpImaComponentName
      DisplayString,
   lpImaStorageType
      StorageType,
   lpImaIndex
      Integer32 }

lpImaRowStatus OBJECT-TYPE
   SYNTAX     RowStatus 
   ACCESS     read-write
   STATUS     mandatory
   DESCRIPTION
     "This variable is used as the basis for SNMP naming of
      lpIma components.
      These components can be added and deleted."
::= { lpImaRowStatusEntry 1 }

lpImaComponentName OBJECT-TYPE
   SYNTAX     DisplayString 
   ACCESS     read-only
   STATUS     mandatory
   DESCRIPTION
     "This variable provides the component's string name for
      use with the ASCII Console Interface"
::= { lpImaRowStatusEntry 2 }

lpImaStorageType OBJECT-TYPE
   SYNTAX     StorageType 
   ACCESS     read-only
   STATUS     mandatory
   DESCRIPTION
     "This variable represents the storage type value for the
      lpIma tables."
::= { lpImaRowStatusEntry 4 }

lpImaIndex OBJECT-TYPE
   SYNTAX     Integer32 (0..7)
   ACCESS     not-accessible
   STATUS     mandatory
   DESCRIPTION
     "This variable represents the index for the lpIma tables."
::= { lpImaRowStatusEntry 10 }

lpImaProvTable OBJECT-TYPE
   SYNTAX     SEQUENCE OF LpImaProvEntry
   ACCESS     not-accessible
   STATUS     mandatory
   DESCRIPTION
     "This group contains the provisionable attributes for the Ima 
      component."
::= { lpIma 10 }

lpImaProvEntry OBJECT-TYPE
   SYNTAX     LpImaProvEntry
   ACCESS     not-accessible
   STATUS     mandatory
   DESCRIPTION
     "An entry in the lpImaProvTable."
   INDEX {
      lpIndex,
      lpImaIndex }
::= { lpImaProvTable 1 }

LpImaProvEntry ::= SEQUENCE {
   lpImaLinkSelectionCriterion
      INTEGER,
   lpImaMaxDiffDelay
      Unsigned32,
   lpImaLinkRetryTimeout
      Unsigned32,
   lpImaApplicationFramerName
      Link,
   lpImaTransmitClockMode
      INTEGER,
   lpImaProtocol
      INTEGER }

lpImaLinkSelectionCriterion OBJECT-TYPE
   SYNTAX     INTEGER  {
                 leastDelay(0),
                 maxBandwidth(1) }
   ACCESS     read-write
   STATUS     mandatory
   DESCRIPTION
     "This attribute specifies the method to be used by the IMA group 
      when selecting links to be activated. This comes into effect only 
      when the configured links do not respect the maximum differential 
      delay (otherwise all links are accepted).
      If leastDelay is chosen, first the link having the smallest delay is 
      selected as the reference link. The IMA group will then include all 
      links which respect the maximum differential delay relative to the 
      reference link.
      If maxBandwidth is chosen, the IMA group will select the 
      maximum possible number of links, with each selected link 
      respecting the maximum differential delay relative to every other 
      selected link. When more than one possibility exists, the 
      combination which offers the least delay will be selected."
   DEFVAL     { maxBandwidth }
::= { lpImaProvEntry 1 }

lpImaMaxDiffDelay OBJECT-TYPE
   SYNTAX     Unsigned32 (1..100)
   ACCESS     read-write
   STATUS     mandatory
   DESCRIPTION
     "This attribute specifies the maximum differential delay (in 
      milliseconds) between links acceptable in the IMA group. If a link 
      violates that maximum differential delay, it will not be active in the 
      IMA group and an alarm will be generated."
   DEFVAL     { 25 }
::= { lpImaProvEntry 2 }

lpImaLinkRetryTimeout OBJECT-TYPE
   SYNTAX     Unsigned32 (0..1000)
   ACCESS     read-write
   STATUS     mandatory
   DESCRIPTION
     "This attribute specifies the amount of time (in seconds) before 
      reactivation of a link is attempted after it recovers from a failure 
      condition."
   DEFVAL     { 10 }
::= { lpImaProvEntry 3 }

lpImaApplicationFramerName OBJECT-TYPE
   SYNTAX     Link 
   ACCESS     read-write
   STATUS     mandatory
   DESCRIPTION
     "This attribute defines the link to the AtmIf component using the Ima. 
      An example is AtmIf/31."
::= { lpImaProvEntry 4 }

lpImaTransmitClockMode OBJECT-TYPE
   SYNTAX     INTEGER  {
                 itc(0),
                 ctc(1) }
   ACCESS     read-write
   STATUS     mandatory
   DESCRIPTION
     "This attribute specifies the transmit clocking mode.
      If itc (Independent Transmit Clock) is chosen, the physical ports 
      used by the IMA group may have different clocking sources.
      If ctc (Common Transmit Clock) is chosen, it is recommended that 
      the physical ports used by the IMA group have the same clocking 
      source. However, if the physical ports have different clocking 
      sources, the operator should ensure that all the clocking sources 
      have the same rate."
   DEFVAL     { itc }
::= { lpImaProvEntry 5 }

lpImaProtocol OBJECT-TYPE
   SYNTAX     INTEGER  {
                 atmForum10(0),
                 proprietary(1) }
   ACCESS     read-write
   STATUS     mandatory
   DESCRIPTION
     "This attribute specifies what protocol the component should run.
      If atmForum10 is chosen, the ATM Forum's IMA protocol (version 
      1.0) will be used and signalled in outgoing IMA Control Protocol 
      (ICP) cells. This protocol is specified in version 1.1 of the ATM 
      Forum IMA specification. The IMA group will come up only if the 
      far end IMA also uses the ATM Forum's IMA protocol.
      If proprietary is chosen, Nortel's proprietary IMA protocol will be 
      used. The IMA group will come up only if the far end IMA also 
      uses Nortel's proprietary IMA protocol. This IMA group will not 
      inter-operate with IMA implementations from other vendors. 
      Feature ima must be provisioned on the LP for this protocol to be 
      used."
   DEFVAL     { atmForum10 }
::= { lpImaProvEntry 6 }

lpImaOperTable OBJECT-TYPE
   SYNTAX     SEQUENCE OF LpImaOperEntry
   ACCESS     not-accessible
   STATUS     mandatory
   DESCRIPTION
     "This group contains the operational attributes for the Ima 
      component."
::= { lpIma 11 }

lpImaOperEntry OBJECT-TYPE
   SYNTAX     LpImaOperEntry
   ACCESS     not-accessible
   STATUS     mandatory
   DESCRIPTION
     "An entry in the lpImaOperTable."
   INDEX {
      lpIndex,
      lpImaIndex }
::= { lpImaOperTable 1 }

LpImaOperEntry ::= SEQUENCE {
   lpImaFailureCause
      INTEGER,
   lpImaRemoteDefect
      INTEGER,
   lpImaRemoteLidsConfig
      OCTET STRING,
   lpImaRemoteLidsActive
      OCTET STRING,
   lpImaCellCapacity
      Unsigned32,
   lpImaRemoteGid
      Unsigned32,
   lpImaClockingModeMismatch
      INTEGER }

lpImaFailureCause OBJECT-TYPE
   SYNTAX     INTEGER  {
                 noFailure(0),
                 noGoodLinksInStartup(1),
                 badGidInStartup(2),
                 badLidInStartup(3),
                 unsupportedFrameLengthInStartup(4),
                 timeoutInStartup(5),
                 noGoodLinks(6),
                 remoteFailure(7),
                 unsupportedSymmetryInStartup(8) }
   ACCESS     read-only
   STATUS     mandatory
   DESCRIPTION
     "This attribute indicates the cause of the current local end failure 
      experienced by the IMA group. The failure may have occurred 
      during a start-up procedure or during normal operation. Possible 
      values are:
      noFailure: no local end failure.
      noGoodLinksInStartup: no good links were available during IMA 
      start-up.
      badGidInStartup: during start-up, different group identifiers (GIDs) 
      were received on the links.
      badLidInStartup: during start-up, duplicate link identifiers (LIDs) 
      were received on the links.
      unsupportedFrameLengthInStartup: during start-up, an 
      unsupported frame length was received.
      timeoutInStartup: a time-out has occurred during start-up.
      noGoodLinks: no good links are available in the IMA group.
      remoteFailure: the far end is down.
      unsupportedSymmetryInStartup: the symmetry proposed by the far 
      end is not supported on the near-end. This value will occur when 
      the IMA group is running the ATM Forum protocol and the far end 
      is proposing a group symmetry other than 'symmetric configuration 
      and operation'."
::= { lpImaOperEntry 1 }

lpImaRemoteDefect OBJECT-TYPE
   SYNTAX     INTEGER  {
                 noDefect(0),
                 noGoodLinksInStartup(1),
                 badGidInStartup(2),
                 badLidInStartup(3),
                 unsupportedFrameLengthInStartup(4),
                 timeoutInStartup(5),
                 noGoodLinks(6),
                 locked(7),
                 unsupportedSymmetryInStartup(8),
                 otherAbortStartup(9),
                 insufficientLinks(10),
                 blocked(11) }
   ACCESS     read-only
   STATUS     mandatory
   DESCRIPTION
     "This attribute indicates the cause of the current far end defect 
      experienced by the IMA group.
      For the ATM Forum IMA protocol, possible values are:
      noDefect: no defect.
      unsupportedFrameLengthInStartup: during the far end's start-up, 
      an unsupported frame length was received.
      unsupportedSymmetryInStartup: during the far end's start-up, an 
      unsupported symmetry configuration was received.
      otherAbortStartup: the far end has aborted its start-up for another 
      reason. This could be because different Gids were received on the 
      links or if duplicate link identifiers (LIDs) were received.
      insufficientLinks: the far end does not have sufficient links active. 
      This value will be displayed if the far end IMA group is locked.
      blocked: the far end IMA group is blocked.
      
      For the proprietary IMA protocol, possible values are:
      noDefect: no defect.
      noGoodLinksInStartup: no good links were available during the far 
      end's start-up.
      badGidInStartup: during the far end's start-up, different GIDs were 
      received on the links.
      badLidInStartup: during the far end's start-up, duplicate link 
      identifiers (LIDs) were received on the links.
      unsupportedFrameLengthInStartup: during the far end's start-up, 
      an unsupported frame length was received.
      timeoutInStartup: a time out has occurred during the far end's start-
      up.
      noGoodLinks: no good links are available in the far end IMA 
      group.
      locked: the far end IMA group is locked."
::= { lpImaOperEntry 2 }

lpImaRemoteLidsConfig OBJECT-TYPE
   SYNTAX     OCTET STRING (SIZE (4))
   ACCESS     read-only
   STATUS     mandatory
   DESCRIPTION
     "This attribute indicates all the links which have been configured in 
      the remote IMA group. For example, if links 1, 3 and 5 have been 
      configured in the remote IMA group, this attribute would contain 1 
      3 5.

      Description of bits:
      n0(0)
      n1(1)
      n2(2)
      n3(3)
      n4(4)
      n5(5)
      n6(6)
      n7(7)
      n8(8)
      n9(9)
      n10(10)
      n11(11)
      n12(12)
      n13(13)
      n14(14)
      n15(15)
      n16(16)
      n17(17)
      n18(18)
      n19(19)
      n20(20)
      n21(21)
      n22(22)
      n23(23)
      n24(24)
      n25(25)
      n26(26)
      n27(27)
      n28(28)
      n29(29)
      n30(30)
      n31(31)"
::= { lpImaOperEntry 3 }

lpImaRemoteLidsActive OBJECT-TYPE
   SYNTAX     OCTET STRING (SIZE (4))
   ACCESS     read-only
   STATUS     mandatory
   DESCRIPTION
     "This attribute indicates all the links which are active in the remote 
      IMA group. For example, if links 1 and 5 are active in the remote 
      IMA, this attribute would contain 1 5.

      Description of bits:
      n0(0)
      n1(1)
      n2(2)
      n3(3)
      n4(4)
      n5(5)
      n6(6)
      n7(7)
      n8(8)
      n9(9)
      n10(10)
      n11(11)
      n12(12)
      n13(13)
      n14(14)
      n15(15)
      n16(16)
      n17(17)
      n18(18)
      n19(19)
      n20(20)
      n21(21)
      n22(22)
      n23(23)
      n24(24)
      n25(25)
      n26(26)
      n27(27)
      n28(28)
      n29(29)
      n30(30)
      n31(31)"
::= { lpImaOperEntry 4 }

lpImaCellCapacity OBJECT-TYPE
   SYNTAX     Unsigned32 (0..4294967295)
   ACCESS     read-only
   STATUS     mandatory
   DESCRIPTION
     "This attribute indicates the total cell capacity (in cells per second) 
      which is provided to the ATM layer. This cell capacity takes into 
      account the physical and IMA level overheads."
::= { lpImaOperEntry 5 }

lpImaRemoteGid OBJECT-TYPE
   SYNTAX     Unsigned32 (0..255)
   ACCESS     read-only
   STATUS     mandatory
   DESCRIPTION
     "This attribute indicates the IMA group identifier (GID) used by the 
      remote IMA. A value of 0 will be displayed if the group is not 
      receiving IMA Control Protocol (ICP) cells.
      This attribute will always have a value of 0 if the protocol for the 
      IMA group is proprietary."
::= { lpImaOperEntry 6 }

lpImaClockingModeMismatch OBJECT-TYPE
   SYNTAX     INTEGER  {
                 no(0),
                 yes(1) }
   ACCESS     read-only
   STATUS     mandatory
   DESCRIPTION
     "This attribute indicates whether or not both ends of the IMA group 
      are using the same transmit clocking mode (itc/ctc). Its value will be 
      yes if both ends are not using the same transmit clocking mode. A 
      clocking mode mismatch does not prevent an IMA group from 
      coming up and can be corrected by using the same clocking mode at 
      both ends.
      This attribute will always have a value of no if the protocol for the 
      IMA group is proprietary."
::= { lpImaOperEntry 7 }

lpImaStatsTable OBJECT-TYPE
   SYNTAX     SEQUENCE OF LpImaStatsEntry
   ACCESS     not-accessible
   STATUS     mandatory
   DESCRIPTION
     "This group contains the statistics data for the Ima component."
::= { lpIma 12 }

lpImaStatsEntry OBJECT-TYPE
   SYNTAX     LpImaStatsEntry
   ACCESS     not-accessible
   STATUS     mandatory
   DESCRIPTION
     "An entry in the lpImaStatsTable."
   INDEX {
      lpIndex,
      lpImaIndex }
::= { lpImaStatsTable 1 }

LpImaStatsEntry ::= SEQUENCE {
   lpImaRunningTime
      Unsigned32,
   lpImaUnavailSecs
      Unsigned32,
   lpImaFailures
      Unsigned32,
   lpImaReceiveCellUtilization
      Gauge32,
   lpImaTransmitCellUtilization
      Gauge32 }

lpImaRunningTime OBJECT-TYPE
   SYNTAX     Unsigned32 (0..4294967295)
   ACCESS     read-only
   STATUS     mandatory
   DESCRIPTION
     "This attribute indicates the length of time (in seconds) for which the 
      Ima component has been in the unlocked state or has been used for 
      operational testing."
::= { lpImaStatsEntry 1 }

lpImaUnavailSecs OBJECT-TYPE
   SYNTAX     Unsigned32 (0..4294967295)
   ACCESS     read-only
   STATUS     mandatory
   DESCRIPTION
     "This attribute indicates the number of one second intervals during 
      which the Ima component has been unlocked and out of service."
::= { lpImaStatsEntry 2 }

lpImaFailures OBJECT-TYPE
   SYNTAX     Unsigned32 (0..4294967295)
   ACCESS     read-only
   STATUS     mandatory
   DESCRIPTION
     "This attribute indicates the number of complete failures, during 
      start-up or normal operation, that the Ima component has 
      experienced since being added. It must be noted that a service 
      degradation, such as 1 of the 3 links in an IMA group being down, 
      is not counted as a failure. If an Ima component is in a failure loop 
      and does not come up, this count will only increase by 1."
::= { lpImaStatsEntry 3 }

lpImaReceiveCellUtilization OBJECT-TYPE
   SYNTAX     Gauge32 (0..100)
   ACCESS     read-only
   STATUS     mandatory
   DESCRIPTION
     "This attribute indicates the ratio of the number of valid, assigned 
      user cells received on the IMA group to the IMA cell capacity 
      (based on the number of active links). The utilization is calculated 
      over a one minute period.
      This attribute will always have a value of 0 if the protocol for the 
      IMA group is proprietary."
::= { lpImaStatsEntry 4 }

lpImaTransmitCellUtilization OBJECT-TYPE
   SYNTAX     Gauge32 (0..100)
   ACCESS     read-only
   STATUS     mandatory
   DESCRIPTION
     "This attribute indicates the ratio of the number of user cells 
      transmitted on the IMA group to the IMA cell capacity (based on 
      the number of active links). The utilization is calculated over a one 
      minute period.
      This attribute will always have a value of 0 if the protocol for the 
      IMA group is proprietary."
::= { lpImaStatsEntry 5 }

lpImaCidDataTable OBJECT-TYPE
   SYNTAX     SEQUENCE OF LpImaCidDataEntry
   ACCESS     not-accessible
   STATUS     mandatory
   DESCRIPTION
     "This group contains the attribute for a component's Customer 
      Identifier (CID). Refer to the attribute description for a detailed 
      explanation of CIDs."
::= { lpIma 13 }

lpImaCidDataEntry OBJECT-TYPE
   SYNTAX     LpImaCidDataEntry
   ACCESS     not-accessible
   STATUS     mandatory
   DESCRIPTION
     "An entry in the lpImaCidDataTable."
   INDEX {
      lpIndex,
      lpImaIndex }
::= { lpImaCidDataTable 1 }

LpImaCidDataEntry ::= SEQUENCE {
   lpImaCustomerIdentifier
      Unsigned32 }

lpImaCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { lpImaCidDataEntry 1 }

lpImaStateTable OBJECT-TYPE
   SYNTAX     SEQUENCE OF LpImaStateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { lpIma 14 }

lpImaStateEntry OBJECT-TYPE
   SYNTAX     LpImaStateEntry
   ACCESS     not-accessible
   STATUS     mandatory
   DESCRIPTION
     "An entry in the lpImaStateTable."
   INDEX {
      lpIndex,
      lpImaIndex }
::= { lpImaStateTable 1 }

LpImaStateEntry ::= SEQUENCE {
   lpImaAdminState
      INTEGER,
   lpImaOperationalState
      INTEGER,
   lpImaUsageState
      INTEGER,
   lpImaAvailabilityStatus
      OCTET STRING,
   lpImaProceduralStatus
      OCTET STRING,
   lpImaControlStatus
      OCTET STRING,
   lpImaAlarmStatus
      OCTET STRING,
   lpImaStandbyStatus
      INTEGER,
   lpImaUnknownStatus
      INTEGER }

lpImaAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { lpImaStateEntry 1 }

lpImaOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { lpImaStateEntry 2 }

lpImaUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { lpImaStateEntry 3 }

lpImaAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { lpImaStateEntry 4 }

lpImaProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { lpImaStateEntry 5 }

lpImaControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { lpImaStateEntry 6 }

lpImaAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { lpImaStateEntry 7 }

lpImaStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { lpImaStateEntry 8 }

lpImaUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { lpImaStateEntry 9 }


-- 
-- The Test component is configured to control a hardware facility test 
-- on a physical (V35, X21, DS1, E1, DS3, E3 etc.) or a logical port.

lpImaTest OBJECT IDENTIFIER ::= { lpIma 2 }



lpImaTestRowStatusTable OBJECT-TYPE
   SYNTAX     SEQUENCE OF LpImaTestRowStatusEntry
   ACCESS     not-accessible
   STATUS     mandatory
   DESCRIPTION
     "This entry controls the addition and deletion of 
      lpImaTest components."
::= { lpImaTest 1 }

lpImaTestRowStatusEntry OBJECT-TYPE
   SYNTAX     LpImaTestRowStatusEntry
   ACCESS     not-accessible
   STATUS     mandatory
   DESCRIPTION
     "A single entry in the table represents a single 
      lpImaTest component."
   INDEX {
      lpIndex,
      lpImaIndex,
      lpImaTestIndex }
::= { lpImaTestRowStatusTable 1 }

LpImaTestRowStatusEntry ::= SEQUENCE {
   lpImaTestRowStatus
      RowStatus,
   lpImaTestComponentName
      DisplayString,
   lpImaTestStorageType
      StorageType,
   lpImaTestIndex
      NonReplicated }

lpImaTestRowStatus OBJECT-TYPE
   SYNTAX     RowStatus 
   ACCESS     read-only
   STATUS     mandatory
   DESCRIPTION
     "This variable is used as the basis for SNMP naming of
      lpImaTest components.
      These components cannot be added nor deleted."
::= { lpImaTestRowStatusEntry 1 }

lpImaTestComponentName OBJECT-TYPE
   SYNTAX     DisplayString 
   ACCESS     read-only
   STATUS     mandatory
   DESCRIPTION
     "This variable provides the component's string name for
      use with the ASCII Console Interface"
::= { lpImaTestRowStatusEntry 2 }

lpImaTestStorageType OBJECT-TYPE
   SYNTAX     StorageType 
   ACCESS     read-only
   STATUS     mandatory
   DESCRIPTION
     "This variable represents the storage type value for the
      lpImaTest tables."
::= { lpImaTestRowStatusEntry 4 }

lpImaTestIndex OBJECT-TYPE
   SYNTAX     NonReplicated 
   ACCESS     not-accessible
   STATUS     mandatory
   DESCRIPTION
     "This variable represents the index for the lpImaTest tables."
::= { lpImaTestRowStatusEntry 10 }

lpImaTestStateTable OBJECT-TYPE
   SYNTAX     SEQUENCE OF LpImaTestStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { lpImaTest 10 }

lpImaTestStateEntry OBJECT-TYPE
   SYNTAX     LpImaTestStateEntry
   ACCESS     not-accessible
   STATUS     mandatory
   DESCRIPTION
     "An entry in the lpImaTestStateTable."
   INDEX {
      lpIndex,
      lpImaIndex,
      lpImaTestIndex }
::= { lpImaTestStateTable 1 }

LpImaTestStateEntry ::= SEQUENCE {
   lpImaTestAdminState
      INTEGER,
   lpImaTestOperationalState
      INTEGER,
   lpImaTestUsageState
      INTEGER }

lpImaTestAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { lpImaTestStateEntry 1 }

lpImaTestOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { lpImaTestStateEntry 2 }

lpImaTestUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { lpImaTestStateEntry 3 }

lpImaTestSetupTable OBJECT-TYPE
   SYNTAX     SEQUENCE OF LpImaTestSetupEntry
   ACCESS     not-accessible
   STATUS     mandatory
   DESCRIPTION
     "This group contains all of the operational data for a Test 
      component."
::= { lpImaTest 11 }

lpImaTestSetupEntry OBJECT-TYPE
   SYNTAX     LpImaTestSetupEntry
   ACCESS     not-accessible
   STATUS     mandatory
   DESCRIPTION
     "An entry in the lpImaTestSetupTable."
   INDEX {
      lpIndex,
      lpImaIndex,
      lpImaTestIndex }
::= { lpImaTestSetupTable 1 }

LpImaTestSetupEntry ::= SEQUENCE {
   lpImaTestPurpose
      AsciiString,
   lpImaTestType
      INTEGER,
   lpImaTestFrmSize
      Unsigned32,
   lpImaTestFrmPatternType
      INTEGER,
   lpImaTestCustomizedPattern
      Hex,
   lpImaTestDataStartDelay
      Unsigned32,
   lpImaTestDisplayInterval
      Unsigned32,
   lpImaTestDuration
      Unsigned32 }

lpImaTestPurpose OBJECT-TYPE
   SYNTAX     AsciiString (SIZE (0..40))
   ACCESS     read-write
   STATUS     mandatory
   DESCRIPTION
     "This attribute records the purpose of the test so that the test results 
      can be associated and properly analyzed."
::= { lpImaTestSetupEntry 1 }

lpImaTestType OBJECT-TYPE
   SYNTAX     INTEGER  {
                 card(0),
                 manual(1),
                 localLoop(2),
                 remoteLoop(3),
                 externalLoop(4),
                 payloadLoop(5),
                 remoteLoopThisTrib(6),
                 v54RemoteLoop(7),
                 pn127RemoteLoop(8) }
   ACCESS     read-write
   STATUS     mandatory
   DESCRIPTION
     "This attribute is the type of test to be run. The available test types 
      include the following:
      card test sets up an internal loop on the board and runs a bit error 
      rate test.
      manual test assumes the line is looped back externally and a bit 
      error rate test is performed.
      localLoop test loops back the local modem and performs a bit error 
      rate test.
      remoteLoop test loops back the remote modem (or CSU) and 
      performs a bit error rate test.
      externalLoop test loops back the line to the far end.
      payloadLoop test only loops back the payload data received from 
      the incoming line.
      remoteLoopThisTrib loops this particular tributary back at the far 
      end, using services provided by the parent.
      v54RemoteLoop initiates a V.54 Remote Loopback test.
      pn127RemoteLoop initiates a PN127 Remote Loopback test.
      Note that not all test types are not supported by all function 
      processors."
   DEFVAL     { card }
::= { lpImaTestSetupEntry 2 }

lpImaTestFrmSize OBJECT-TYPE
   SYNTAX     Unsigned32 (4..4096)
   ACCESS     read-write
   STATUS     mandatory
   DESCRIPTION
     "This attribute defines the size of the test data frames in number of 
      bytes."
   DEFVAL     { 1024 }
::= { lpImaTestSetupEntry 3 }

lpImaTestFrmPatternType OBJECT-TYPE
   SYNTAX     INTEGER  {
                 ccitt32kBitPattern(0),
                 ccitt8MBitPattern(1),
                 customizedPattern(2) }
   ACCESS     read-write
   STATUS     mandatory
   DESCRIPTION
     "This attribute defines the type of data pattern generation to use. The 
      following lists the available pattern types:
      ccitt32kBitPattern is a pseudo-random sequence of 32 kbit.
      ccitt8MBitPattern is a pseudo-random sequence of 8Mbit.
      customizedPattern is the pattern defined in the customizedPattern 
      attribute."
   DEFVAL     { ccitt32kBitPattern }
::= { lpImaTestSetupEntry 4 }

lpImaTestCustomizedPattern OBJECT-TYPE
   SYNTAX     Hex (0..4294967295)
   ACCESS     read-write
   STATUS     mandatory
   DESCRIPTION
     "This attribute allows a customized 32 bit pattern to be defined for 
      use in the test data frames. This attribute is used when the attribute 
      frmPatternType is set to CustomizedPattern. Note that a 55 hex 
      pattern is an alternating 1 and 0 pattern."
   DEFVAL     { 1431655765 }
::= { lpImaTestSetupEntry 5 }

lpImaTestDataStartDelay OBJECT-TYPE
   SYNTAX     Unsigned32 (0..1814400)
   ACCESS     read-write
   STATUS     mandatory
   DESCRIPTION
     "This attribute specifies the time delay (in seconds) between when 
      the test expects the loop to have been set up, to when the test data 
      actually starts to be transmitted. This attribute is to accommodate 
      some non-standard equipment that requires extra time for setting up 
      a requested loop.
      This attribute is ignored when the test type is set to externalLoop."
   DEFVAL     { 0 }
::= { lpImaTestSetupEntry 6 }

lpImaTestDisplayInterval OBJECT-TYPE
   SYNTAX     Unsigned32 (0..30240)
   ACCESS     read-write
   STATUS     mandatory
   DESCRIPTION
     "This attribute defines the interval (in minutes) between which 
      interim test results are to be displayed. Results are displayed at the 
      operator console at which the test was started. When the test type is 
      set to externalLoop, this attribute is ignored. There will be no 
      display of results if displayInterval is set to 0. This attribute can be 
      changed anytime."
   DEFVAL     { 5 }
::= { lpImaTestSetupEntry 7 }

lpImaTestDuration OBJECT-TYPE
   SYNTAX     Unsigned32 (1..30240)
   ACCESS     read-write
   STATUS     mandatory
   DESCRIPTION
     "This attribute is the duration (in minutes) that test data will be 
      transmitted. In the case of an externalLoop, this is the time that the 
      loop is in effect. Note that dataStartDelay does not apply to the 
      externalLoop."
   DEFVAL     { 1 }
::= { lpImaTestSetupEntry 8 }

lpImaTestResultsTable OBJECT-TYPE
   SYNTAX     SEQUENCE OF LpImaTestResultsEntry
   ACCESS     not-accessible
   STATUS     mandatory
   DESCRIPTION
     "This group contains all the statistics related attributes of the Test 
      component."
::= { lpImaTest 12 }

lpImaTestResultsEntry OBJECT-TYPE
   SYNTAX     LpImaTestResultsEntry
   ACCESS     not-accessible
   STATUS     mandatory
   DESCRIPTION
     "An entry in the lpImaTestResultsTable."
   INDEX {
      lpIndex,
      lpImaIndex,
      lpImaTestIndex }
::= { lpImaTestResultsTable 1 }

LpImaTestResultsEntry ::= SEQUENCE {
   lpImaTestElapsedTime
      Counter32,
   lpImaTestTimeRemaining
      Unsigned32,
   lpImaTestCauseOfTermination
      INTEGER,
   lpImaTestBitsTx
      PassportCounter64,
   lpImaTestBytesTx
      PassportCounter64,
   lpImaTestFrmTx
      PassportCounter64,
   lpImaTestBitsRx
      PassportCounter64,
   lpImaTestBytesRx
      PassportCounter64,
   lpImaTestFrmRx
      PassportCounter64,
   lpImaTestErroredFrmRx
      PassportCounter64,
   lpImaTestBitErrorRate
      AsciiString }

lpImaTestElapsedTime OBJECT-TYPE
   SYNTAX     Counter32 
   ACCESS     read-only
   STATUS     mandatory
   DESCRIPTION
     "This attribute is the number of minutes elapsed since the test started 
      for an externalLoop test. For a data test, this is the time since test 
      data was first transmitted."
::= { lpImaTestResultsEntry 1 }

lpImaTestTimeRemaining OBJECT-TYPE
   SYNTAX     Unsigned32 (0..4294967295)
   ACCESS     read-only
   STATUS     mandatory
   DESCRIPTION
     "This attribute is the number of minutes remaining before the test is 
      to be stopped according to the duration attribute."
   DEFVAL     { 0 }
::= { lpImaTestResultsEntry 2 }

lpImaTestCauseOfTermination OBJECT-TYPE
   SYNTAX     INTEGER  {
                 testTimeExpired(0),
                 stoppedByOperator(1),
                 unknown(2),
                 neverStarted(3),
                 testRunning(4),
                 hardwareReconfigured(5) }
   ACCESS     read-only
   STATUS     mandatory
   DESCRIPTION
     "This attribute records the reason the test is terminated."
   DEFVAL     { neverStarted }
::= { lpImaTestResultsEntry 3 }

lpImaTestBitsTx OBJECT-TYPE
   SYNTAX     PassportCounter64 
   ACCESS     read-only
   STATUS     mandatory
   DESCRIPTION
     "This attribute is the total number of bits sent during the test period. 
      As long as the line speed of the hardware interface is less than 
      70 Mbit/s, this counter is not expected to reach the maximum value."
::= { lpImaTestResultsEntry 4 }

lpImaTestBytesTx OBJECT-TYPE
   SYNTAX     PassportCounter64 
   ACCESS     read-only
   STATUS     mandatory
   DESCRIPTION
     "This attribute is the total number of bytes sent during the test 
      period. This counter is not expected to reach its maximum value."
::= { lpImaTestResultsEntry 5 }

lpImaTestFrmTx OBJECT-TYPE
   SYNTAX     PassportCounter64 
   ACCESS     read-only
   STATUS     mandatory
   DESCRIPTION
     "This attribute is the total number of frames sent during the test 
      period. This counter is not expected to reach its maximum value."
::= { lpImaTestResultsEntry 6 }

lpImaTestBitsRx OBJECT-TYPE
   SYNTAX     PassportCounter64 
   ACCESS     read-only
   STATUS     mandatory
   DESCRIPTION
     "This attribute is the total number of bits received during the test 
      period. This counter is not expected to reach its maximum value. 
      The counter will wrap around to 0 if it does reach the maximum 
      value."
::= { lpImaTestResultsEntry 7 }

lpImaTestBytesRx OBJECT-TYPE
   SYNTAX     PassportCounter64 
   ACCESS     read-only
   STATUS     mandatory
   DESCRIPTION
     "This attribute is the total number of bytes received during the test 
      period. This counter is not expected to reach its maximum value. 
      The counter will wrap around to 0 if it does reach its maximum 
      value."
::= { lpImaTestResultsEntry 8 }

lpImaTestFrmRx OBJECT-TYPE
   SYNTAX     PassportCounter64 
   ACCESS     read-only
   STATUS     mandatory
   DESCRIPTION
     "This attribute is the total number of frames received during the test 
      period. This counter is not expected to reach its maximum value. 
      The counter will wrap around to 0 if it does reach its maximum 
      value."
::= { lpImaTestResultsEntry 9 }

lpImaTestErroredFrmRx OBJECT-TYPE
   SYNTAX     PassportCounter64 
   ACCESS     read-only
   STATUS     mandatory
   DESCRIPTION
     "This attribute counts the errored frames received during the test 
      period. This counter is not expected to reach its maximum value. 
      The counter wraps to 0 if it exceeds its maximum value. 
      
      This attribute is not displayed for ATM cards because the physical 
      layer drops all errored frames at the controller interface."
::= { lpImaTestResultsEntry 10 }

lpImaTestBitErrorRate OBJECT-TYPE
   SYNTAX     AsciiString (SIZE (5))
   ACCESS     read-only
   STATUS     mandatory
   DESCRIPTION
     "This attribute indicates the calculated bit error rate on the link. Test 
      data are generated and sent in frames of a preset size (frameSize). 
      The Test component tries to estimate the number of bit errors in any 
      errored frame which is identifiable. The statistics are updated 
      accordingly. A lost frame (possibly due to an error on the flag 
      sequence) is not used for the bit error rate calculation. The result is 
      presented in the form of xEsyy, where x is the mantissa; and syy is 
      the exponent, for example 0E+00, 2E-09.
      Note that the bitErrorRate is an estimate only. For more reliable test 
      results, the test should be done over a long period. Multiple tests 
      would also improve the confidence level of the test results.
      
      This attribute is not displayed for ATM cards because the physical 
      layer drops all errored frames at the controller interface."
::= { lpImaTestResultsEntry 11 }


-- Lp/n Ima/n Link/n
-- This component is used to define a DS1/E1 link belonging to an 
-- IMA group. The instance number of the Link subcomponent 
-- corresponds to the link identifier (LID) used by the link in IMA 
-- Control Protocol (ICP) cells.

lpImaLk OBJECT IDENTIFIER ::= { lpIma 3 }



lpImaLkRowStatusTable OBJECT-TYPE
   SYNTAX     SEQUENCE OF LpImaLkRowStatusEntry
   ACCESS     not-accessible
   STATUS     mandatory
   DESCRIPTION
     "This entry controls the addition and deletion of 
      lpImaLk components."
::= { lpImaLk 1 }

lpImaLkRowStatusEntry OBJECT-TYPE
   SYNTAX     LpImaLkRowStatusEntry
   ACCESS     not-accessible
   STATUS     mandatory
   DESCRIPTION
     "A single entry in the table represents a single 
      lpImaLk component."
   INDEX {
      lpIndex,
      lpImaIndex,
      lpImaLkIndex }
::= { lpImaLkRowStatusTable 1 }

LpImaLkRowStatusEntry ::= SEQUENCE {
   lpImaLkRowStatus
      RowStatus,
   lpImaLkComponentName
      DisplayString,
   lpImaLkStorageType
      StorageType,
   lpImaLkIndex
      Integer32 }

lpImaLkRowStatus OBJECT-TYPE
   SYNTAX     RowStatus 
   ACCESS     read-write
   STATUS     mandatory
   DESCRIPTION
     "This variable is used as the basis for SNMP naming of
      lpImaLk components.
      These components can be added and deleted."
::= { lpImaLkRowStatusEntry 1 }

lpImaLkComponentName OBJECT-TYPE
   SYNTAX     DisplayString 
   ACCESS     read-only
   STATUS     mandatory
   DESCRIPTION
     "This variable provides the component's string name for
      use with the ASCII Console Interface"
::= { lpImaLkRowStatusEntry 2 }

lpImaLkStorageType OBJECT-TYPE
   SYNTAX     StorageType 
   ACCESS     read-only
   STATUS     mandatory
   DESCRIPTION
     "This variable represents the storage type value for the
      lpImaLk tables."
::= { lpImaLkRowStatusEntry 4 }

lpImaLkIndex OBJECT-TYPE
   SYNTAX     Integer32 (0..31)
   ACCESS     not-accessible
   STATUS     mandatory
   DESCRIPTION
     "This variable represents the index for the lpImaLk tables."
::= { lpImaLkRowStatusEntry 10 }

lpImaLkProvTable OBJECT-TYPE
   SYNTAX     SEQUENCE OF LpImaLkProvEntry
   ACCESS     not-accessible
   STATUS     mandatory
   DESCRIPTION
     "This group contains the provisionable attributes for the Link 
      subcomponent."
::= { lpImaLk 10 }

lpImaLkProvEntry OBJECT-TYPE
   SYNTAX     LpImaLkProvEntry
   ACCESS     not-accessible
   STATUS     mandatory
   DESCRIPTION
     "An entry in the lpImaLkProvTable."
   INDEX {
      lpIndex,
      lpImaIndex,
      lpImaLkIndex }
::= { lpImaLkProvTable 1 }

LpImaLkProvEntry ::= SEQUENCE {
   lpImaLkInterfaceName
      Link }

lpImaLkInterfaceName OBJECT-TYPE
   SYNTAX     Link 
   ACCESS     read-write
   STATUS     mandatory
   DESCRIPTION
     "This attribute associates the Link subcomponent with a specific 
      interface on a function processor, for example Lp/5 E1/3 Chan/0.
      If IMA groups and independent links coexist on a card running 
      IMA and per-Vc queueing is enabled, plan the selection of DS1/E1 
      ports to be used by the IMA group carefully."
::= { lpImaLkProvEntry 1 }

lpImaLkOperTable OBJECT-TYPE
   SYNTAX     SEQUENCE OF LpImaLkOperEntry
   ACCESS     not-accessible
   STATUS     mandatory
   DESCRIPTION
     "This group contains the operational attributes for the Link 
      subcomponent."
::= { lpImaLk 11 }

lpImaLkOperEntry OBJECT-TYPE
   SYNTAX     LpImaLkOperEntry
   ACCESS     not-accessible
   STATUS     mandatory
   DESCRIPTION
     "An entry in the lpImaLkOperTable."
   INDEX {
      lpIndex,
      lpImaIndex,
      lpImaLkIndex }
::= { lpImaLkOperTable 1 }

LpImaLkOperEntry ::= SEQUENCE {
   lpImaLkFailureCause
      INTEGER,
   lpImaLkRemoteDefect
      INTEGER,
   lpImaLkRemoteLid
      Unsigned32,
   lpImaLkRelativeDelay
      Unsigned32,
   lpImaLkLastOifCause
      INTEGER }

lpImaLkFailureCause OBJECT-TYPE
   SYNTAX     INTEGER  {
                 noFailure(0),
                 interfaceDown(1),
                 lif(2),
                 lods(3),
                 protocolError(4),
                 remoteFailure(5),
                 misconnected(6),
                 unsupportedFrameLength(7),
                 unsupportedSymmetry(8),
                 noIcp(9) }
   ACCESS     read-only
   STATUS     mandatory
   DESCRIPTION
     "This attribute indicates the failure cause on this link. Possible values 
      are:
      noFailure: there is no failure on this link.
      interfaceDown: the physical port used by the link is down.
      lif: the link is in loss of IMA frame (LIF) state.
      lods: the link is in loss of delay synchronization (LODS) state; that 
      is, it has exhibited a differential delay which is greater than the 
      maximum differential delay tolerated by the IMA group. It must be 
      noted that hysteresis is used for the LODS condition.
      protocolError: the link is down because of a time-out or because 
      bad values are being received in IMA Control Protocol (ICP) cells.
      remoteFailure: the far end link is down.
      misconnected: the link is down because the IMA group has 
      declared, after using its transmit test pattern procedure, that this link 
      is not properly connected. This value can occur only if the protocol 
      for the IMA group is atmForum10.
      unsupportedFrameLength: the link is down because it is receiving 
      from the far end a frame length which is not supported by the local 
      IMA group. This value can occur only if the protocol for the IMA 
      group is atmForum10.
      unsupportedSymmetry: the link is down because it is receiving 
      from the far end a group symmetry which is not supported by the 
      local IMA group. This value can occur only if the protocol for the 
      IMA group is atmForum10.
      noIcp: the link is down because it is not receiving IMA Control 
      Protocol (ICP) cells. This value can occur only if the protocol for 
      the IMA group is atmForum10."
::= { lpImaLkOperEntry 1 }

lpImaLkRemoteDefect OBJECT-TYPE
   SYNTAX     INTEGER  {
                 noDefect(0),
                 physicalLayerDefect(1),
                 lif(2),
                 lods(3),
                 interfaceDown(4) }
   ACCESS     read-only
   STATUS     mandatory
   DESCRIPTION
     "This attribute indicates the IMA remote defect indicator (RDI) 
      currently being received on this link. Possible values are:
      noDefect: no defect.
      physicalLayerDefect: the interface used by the remote link has a 
      physical layer defect. This value can occur only if the protocol for 
      the IMA group is atmForum10.
      interfaceDown: the physical interface used by the remote link is 
      down.This value can occur only if the protocol for the IMA group is 
      proprietary.
      lif: the remote link has a loss of IMA frame (LIF) defect.
      lods: the remote link has a loss of delay synchronization (LODS) 
      defect; that is, it has exhibited a differential delay which is greater 
      than the maximum differential delay tolerated by the IMA group."
::= { lpImaLkOperEntry 2 }

lpImaLkRemoteLid OBJECT-TYPE
   SYNTAX     Unsigned32 (0..31)
   ACCESS     read-only
   STATUS     mandatory
   DESCRIPTION
     "This attribute indicates the link identifier (LID) used by the remote 
      IMA group on the physical link. A value of 0 will be displayed if 
      the link is not receiving IMA Control Protocol (ICP) cells or if the 
      physical layer is down."
::= { lpImaLkOperEntry 3 }

lpImaLkRelativeDelay OBJECT-TYPE
   SYNTAX     Unsigned32 (0..4294967295)
   ACCESS     read-only
   STATUS     mandatory
   DESCRIPTION
     "This attribute indicates the latest measured differential delay 
      (rounded up in milliseconds) between this link and the link, in the 
      same IMA group, having the least delay. A value of 4294967295 
      indicates that the relative delay could not be measured. This can be 
      due to physical layer problems or to no IMA Control Protocol (ICP) 
      cells being received on the link."
::= { lpImaLkOperEntry 4 }

lpImaLkLastOifCause OBJECT-TYPE
   SYNTAX     INTEGER  {
                 noOif(0),
                 badFrameLength(1),
                 badGid(2),
                 badLid(3),
                 badOffset(4),
                 badSequenceNumber(5),
                 stuffError(6),
                 missingIcp(7),
                 unexpectedIcp(8),
                 erroredIcp(9),
                 noCells(10),
                 idleCell(11) }
   ACCESS     read-only
   STATUS     mandatory
   DESCRIPTION
     "This attribute indicates the cause of the last out of IMA frame (OIF) 
      anomaly on the link. It will always have a value of noOif if the 
      protocol for the IMA group is proprietary. 
      Possible values are:
      noOif: no OIF was detected.
      badFrameLength: an IMA Control Protocol (ICP) cell with an 
      unexpected frame length was received.
      badGid: an ICP cell with an unexpected group identifier (GID) was 
      received.
      badLid: an ICP cell with an unexpected link identifier (LID) was 
      received.
      badOffset: an ICP cell with an unexpected cell offset was received.
      badSequenceNumber: an ICP cell with an unexpected frame 
      sequence number was received.
      stuffError: an illegal stuffing sequence was received.
      missingIcp: an expected ICP cell was not received.
      unexpectedIcp: an unexpected ICP cell was received.
      erroredIcp: two consecutive errored ICP cells were received.
      noCells: no cells are being received on the link.
      idleCell: an idle cell was received on the link."
::= { lpImaLkOperEntry 5 }

lpImaLkStatsTable OBJECT-TYPE
   SYNTAX     SEQUENCE OF LpImaLkStatsEntry
   ACCESS     not-accessible
   STATUS     mandatory
   DESCRIPTION
     "This group contains the statistics data for the Link subcomponent."
::= { lpImaLk 12 }

lpImaLkStatsEntry OBJECT-TYPE
   SYNTAX     LpImaLkStatsEntry
   ACCESS     not-accessible
   STATUS     mandatory
   DESCRIPTION
     "An entry in the lpImaLkStatsTable."
   INDEX {
      lpIndex,
      lpImaIndex,
      lpImaLkIndex }
::= { lpImaLkStatsTable 1 }

LpImaLkStatsEntry ::= SEQUENCE {
   lpImaLkRunningTime
      Unsigned32,
   lpImaLkUnavailSecs
      Unsigned32,
   lpImaLkFailures
      Unsigned32,
   lpImaLkUnusableSec
      Counter32,
   lpImaLkSevErroredSec
      Counter32,
   lpImaLkFarEndUnusableSec
      Counter32,
   lpImaLkFarEndSevErroredSec
      Counter32,
   lpImaLkFarEndUnavailSec
      Counter32,
   lpImaLkIcpViolations
      Counter32,
   lpImaLkTxStuffEvents
      Counter32,
   lpImaLkRxStuffEvents
      Counter32,
   lpImaLkIdleCellSec
      Counter32 }

lpImaLkRunningTime OBJECT-TYPE
   SYNTAX     Unsigned32 (0..4294967295)
   ACCESS     read-only
   STATUS     mandatory
   DESCRIPTION
     "This attribute counts the length of time (in seconds) for which the 
      Link component has been running."
::= { lpImaLkStatsEntry 1 }

lpImaLkUnavailSecs OBJECT-TYPE
   SYNTAX     Unsigned32 (0..4294967295)
   ACCESS     read-only
   STATUS     mandatory
   DESCRIPTION
     "For an IMA group whose protocol is atmForum10, this attribute 
      counts the number of unavailable seconds. Unavailability begins at 
      the start of 10 contiguous severely errored seconds (SES) and ends 
      at the start of 10 contiguous seconds with no SES.
      For an IMA group whose protocol is proprietary, this attribute 
      counts the number of one second intervals during which the Link 
      component has been out of service."
::= { lpImaLkStatsEntry 2 }

lpImaLkFailures OBJECT-TYPE
   SYNTAX     Unsigned32 (0..4294967295)
   ACCESS     read-only
   STATUS     mandatory
   DESCRIPTION
     "This attribute counts the number of failures, during link addition or 
      normal operation, that the link has experienced."
::= { lpImaLkStatsEntry 3 }

lpImaLkUnusableSec OBJECT-TYPE
   SYNTAX     Counter32 
   ACCESS     read-only
   STATUS     mandatory
   DESCRIPTION
     "This attribute counts the number of one second intervals during 
      which the near end has been in an unusable state.
      This attribute will always have a value of 0 if the protocol for the 
      IMA group is proprietary."
::= { lpImaLkStatsEntry 4 }

lpImaLkSevErroredSec OBJECT-TYPE
   SYNTAX     Counter32 
   ACCESS     read-only
   STATUS     mandatory
   DESCRIPTION
     "This attribute counts the number of one second intervals in which at 
      least 30 percent of the IMA Control Protocol (ICP) cells were 
      counted as ICP violations or at least one link defect (physical layer, 
      LIF and LODS defects) was detected. This attribute will not 
      increment during UAS (Unavailable Second) conditions.
      This attribute will always have a value of 0 if the protocol for the 
      IMA group is proprietary."
::= { lpImaLkStatsEntry 5 }

lpImaLkFarEndUnusableSec OBJECT-TYPE
   SYNTAX     Counter32 
   ACCESS     read-only
   STATUS     mandatory
   DESCRIPTION
     "This attribute counts the number of one second intervals during 
      which the 'Tx/Rx Unusable' condition has been received from the 
      far end.
      This attribute will always have a value of 0 if the protocol for the 
      IMA group is proprietary."
::= { lpImaLkStatsEntry 6 }

lpImaLkFarEndSevErroredSec OBJECT-TYPE
   SYNTAX     Counter32 
   ACCESS     read-only
   STATUS     mandatory
   DESCRIPTION
     "This attribute counts the number of one second intervals containing 
      one or more RDI defects. This attribute will not increment during 
      FEUAS (Far-End Unavailable Second) conditions.
      This attribute will always have a value of 0 if the protocol for the 
      IMA group is proprietary."
::= { lpImaLkStatsEntry 7 }

lpImaLkFarEndUnavailSec OBJECT-TYPE
   SYNTAX     Counter32 
   ACCESS     read-only
   STATUS     mandatory
   DESCRIPTION
     "This attribute counts the number of unavailable seconds at the far 
      end. Unavailability begins at the start of 10 contiguous severely 
      errored seconds (SES) at the far end and ends at the start of 10 
      contiguous seconds at the far end with no SES.
      This attribute will always have a value of 0 if the protocol for the 
      IMA group is proprietary."
::= { lpImaLkStatsEntry 8 }

lpImaLkIcpViolations OBJECT-TYPE
   SYNTAX     Counter32 
   ACCESS     read-only
   STATUS     mandatory
   DESCRIPTION
     "This attribute counts the number of errored, invalid or missing IMA 
      Control Protocol (ICP) cells during non-SES (Severely Errored 
      Second) and non-UAS (Unavailable Seconds) conditions.
      This attribute will always have a value of 0 if the protocol for the 
      IMA group is proprietary."
::= { lpImaLkStatsEntry 9 }

lpImaLkTxStuffEvents OBJECT-TYPE
   SYNTAX     Counter32 
   ACCESS     read-only
   STATUS     mandatory
   DESCRIPTION
     "This attribute counts the number of Stuff events transmitted during 
      non-SES (Severely Errored Second) and non-UAS (Unavailable 
      Seconds) conditions.
      This attribute will always have a value of 0 if the protocol for the 
      IMA group is proprietary."
::= { lpImaLkStatsEntry 10 }

lpImaLkRxStuffEvents OBJECT-TYPE
   SYNTAX     Counter32 
   ACCESS     read-only
   STATUS     mandatory
   DESCRIPTION
     "This attribute counts the number of Stuff events received during 
      non-SES (Severely Errored Second) and non-UAS (Unavailable 
      Seconds) conditions.
      This attribute will always have a value of 0 if the protocol for the 
      IMA group is proprietary."
::= { lpImaLkStatsEntry 11 }

lpImaLkIdleCellSec OBJECT-TYPE
   SYNTAX     Counter32 
   ACCESS     read-only
   STATUS     mandatory
   DESCRIPTION
     "This attributes counts the number of one second intervals during 
      which one or more idle cells was received. The reception of idle 
      cells is an abnormal condition which could be caused by the remote 
      IMA using the Common Transmit Clock mode with ports whose 
      clock sources are not synchronized.
      This attribute will always have a value of 0 if the protocol for the 
      IMA group is proprietary."
::= { lpImaLkStatsEntry 12 }

lpImaLkStateTable OBJECT-TYPE
   SYNTAX     SEQUENCE OF LpImaLkStateEntry
   ACCESS     not-accessible
   STATUS     mandatory
   DESCRIPTION
     "This group contains the three OSI State attributes and the six OSI 
      Status attributes. The descriptions generically indicate what each 
      attribute implies about the component. Note that not all the values 
      and state combinations described here are supported by every 
      component which uses this group. For component-specific 
      information and the valid state combinations, refer to NTP 241-
      7001-150, Passport Operations and Maintenance Guide."
::= { lpImaLk 13 }

lpImaLkStateEntry OBJECT-TYPE
   SYNTAX     LpImaLkStateEntry
   ACCESS     not-accessible
   STATUS     mandatory
   DESCRIPTION
     "An entry in the lpImaLkStateTable."
   INDEX {
      lpIndex,
      lpImaIndex,
      lpImaLkIndex }
::= { lpImaLkStateTable 1 }

LpImaLkStateEntry ::= SEQUENCE {
   lpImaLkAdminState
      INTEGER,
   lpImaLkOperationalState
      INTEGER,
   lpImaLkUsageState
      INTEGER,
   lpImaLkAvailabilityStatus
      OCTET STRING,
   lpImaLkProceduralStatus
      OCTET STRING,
   lpImaLkControlStatus
      OCTET STRING,
   lpImaLkAlarmStatus
      OCTET STRING,
   lpImaLkStandbyStatus
      INTEGER,
   lpImaLkUnknownStatus
      INTEGER }

lpImaLkAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { lpImaLkStateEntry 1 }

lpImaLkOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { lpImaLkStateEntry 2 }

lpImaLkUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { lpImaLkStateEntry 3 }

lpImaLkAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below are present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. However, the resource remains available for service. The 
      operationalState is enabled.
      
      The value notInstalled indicates the resource is not present. The 
      operationalState is disabled.
      
      The value logFull is not used.

      Description of bits:
      inTest(0)
      failed(1)
      powerOff(2)
      offLine(3)
      offDuty(4)
      dependency(5)
      degraded(6)
      notInstalled(7)
      logFull(8)"
::= { lpImaLkStateEntry 4 }

lpImaLkProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below are present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { lpImaLkStateEntry 5 }

lpImaLkControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below are present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { lpImaLkStateEntry 6 }

lpImaLkAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below are present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { lpImaLkStateEntry 7 }

lpImaLkStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below are present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { lpImaLkStateEntry 8 }

lpImaLkUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { lpImaLkStateEntry 9 }




-- 
-- Version and Compliance statements
-- 



-- Object-Group Statement:
-- A list of all current accessible leaf objects.

-- OBJECTS { lpImaLkUsageState,
--           lpImaProtocol,
--           lpImaStorageType,
--           lpImaTestDataStartDelay,
--           lpImaLinkRetryTimeout,
--           lpImaRunningTime,
--           lpImaLkLastOifCause,
--           lpImaReceiveCellUtilization,
--           lpImaTransmitCellUtilization,
--           lpImaRemoteLidsConfig,
--           lpImaLkRelativeDelay,
--           lpImaLkRemoteDefect,
--           lpImaTestErroredFrmRx,
--           lpImaTestBytesRx,
--           lpImaLkAdminState,
--           lpImaTestDisplayInterval,
--           lpImaRemoteGid,
--           lpImaTestFrmPatternType,
--           lpImaAdminState,
--           lpImaTestFrmRx,
--           lpImaRemoteLidsActive,
--           lpImaLkOperationalState,
--           lpImaLkRowStatus,
--           lpImaApplicationFramerName,
--           lpImaRemoteDefect,
--           lpImaRowStatus,
--           lpImaLkRxStuffEvents,
--           lpImaTestDuration,
--           lpImaProceduralStatus,
--           lpImaCustomerIdentifier,
--           lpImaLkIdleCellSec,
--           lpImaLkStandbyStatus,
--           lpImaLkSevErroredSec,
--           lpImaTestPurpose,
--           lpImaTransmitClockMode,
--           lpImaLkStorageType,
--           lpImaUsageState,
--           lpImaTestRowStatus,
--           lpImaFailureCause,
--           lpImaLkFailureCause,
--           lpImaComponentName,
--           lpImaTestBitsTx,
--           lpImaLinkSelectionCriterion,
--           lpImaMaxDiffDelay,
--           lpImaTestOperationalState,
--           lpImaLkFarEndUnavailSec,
--           lpImaTestStorageType,
--           lpImaLkUnknownStatus,
--           lpImaTestCauseOfTermination,
--           lpImaOperationalState,
--           lpImaTestTimeRemaining,
--           lpImaCellCapacity,
--           lpImaLkAvailabilityStatus,
--           lpImaLkFailures,
--           lpImaTestType,
--           lpImaLkRunningTime,
--           lpImaLkAlarmStatus,
--           lpImaLkIcpViolations,
--           lpImaTestFrmSize,
--           lpImaClockingModeMismatch,
--           lpImaTestAdminState,
--           lpImaLkRemoteLid,
--           lpImaUnavailSecs,
--           lpImaAlarmStatus,
--           lpImaTestElapsedTime,
--           lpImaLkUnusableSec,
--           lpImaTestBitsRx,
--           lpImaTestBitErrorRate,
--           lpImaLkComponentName,
--           lpImaLkControlStatus,
--           lpImaControlStatus,
--           lpImaFailures,
--           lpImaAvailabilityStatus,
--           lpImaTestComponentName,
--           lpImaTestBytesTx,
--           lpImaLkInterfaceName,
--           lpImaLkUnavailSecs,
--           lpImaLkProceduralStatus,
--           lpImaTestFrmTx,
--           lpImaTestUsageState,
--           lpImaLkFarEndUnusableSec,
--           lpImaTestCustomizedPattern,
--           lpImaUnknownStatus,
--           lpImaStandbyStatus,
--           lpImaLkTxStuffEvents,
--           lpImaLkFarEndSevErroredSec }
-- STATUS  mandatory
-- DESCRIPTION
--   "A list of all current accessible leaf objects."

imaGroup OBJECT IDENTIFIER ::= { imaMIB 1 }
imaGroupBE OBJECT IDENTIFIER ::= { imaGroup 5 }
imaGroupBE00 OBJECT IDENTIFIER ::= { imaGroupBE 1 }
imaGroupBE00A OBJECT IDENTIFIER ::= { imaGroupBE00 2 }



-- Agent-Capabilities Statement:

-- PRODUCT-RELEASE "Passport Release 7.0 Ima."
-- STATUS          mandatory
-- DESCRIPTION     "Ima MIB: MIB Version BE00A,
--                  Software Version BG00S4C."
-- SUPPORTS        Nortel-Magellan-Passport-ImaMIB
--    INCLUDES     { imaGroupBE00A }

imaCapabilities OBJECT IDENTIFIER ::= { imaMIB 3 }
imaCapabilitiesBE OBJECT IDENTIFIER ::= { imaCapabilities 5 }
imaCapabilitiesBE00 OBJECT IDENTIFIER ::= { imaCapabilitiesBE 1 }
imaCapabilitiesBE00A OBJECT IDENTIFIER ::= { imaCapabilitiesBE00 2 }





END
