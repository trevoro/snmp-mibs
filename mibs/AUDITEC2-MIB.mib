AUDITEC2-MIB DEFINITIONS ::= BEGIN


   --
   -- 
   -- Mib Of NEWTEST SOFTWARE
   -- 


  IMPORTS
      NOTIFICATION-TYPE, OBJECT-TYPE, MODULE-IDENTITY, Counter32, Counter64, Integer32
              FROM SNMPv2-SMI 
        IpAddress, TimeTicks, Counter
        FROM RFC1155-SMI
        TRAP-TYPE
                FROM RFC-1215
        DisplayString, sysName
                FROM RFC1213-MIB;


   -- base path of private auditec mib branch


   internet     OBJECT IDENTIFIER ::= { iso org(3) dod(6) 1 }
   private      OBJECT IDENTIFIER ::= { internet 4 }
   enterprises  OBJECT IDENTIFIER ::= { private 1 }


   auditec MODULE-IDENTITY
                LAST-UPDATED    "200112111000Z"
                ORGANIZATION    "auditec Corp."
                CONTACT-INFO
                        "   Auditec
                            Support
                            e-mail : support@auditec-newtest.com
                            www : www.auditec-newtest.com"
                DESCRIPTION
                        "auditec is the managment OBJECT IDENTIFIER..."
                REVISION        "200111231000Z"
                DESCRIPTION
                        "Update for MG Soft compiler"
                REVISION        "200112111000Z"
                DESCRIPTION
                        "Revision for Newtest V7"
                ::= { enterprises 1774 }


   -- the probe_2 group


   probe        OBJECT IDENTIFIER ::= { auditec 1 }
   action       OBJECT IDENTIFIER ::= { auditec 2 }
   alarm        OBJECT IDENTIFIER ::= { auditec 3 }
   group        OBJECT IDENTIFIER ::= { auditec 4 }



   -- the probe group


   prbIpAddr OBJECT-TYPE
              SYNTAX  DisplayString (SIZE (1..16))
              ACCESS  read-only
              STATUS  mandatory
              DESCRIPTION "Probe Ip Address"
             ::= { probe 1 }


   prbState OBJECT-TYPE
              SYNTAX  INTEGER 
                  {
                      alive(0),  -- A group running
                      waiting(1),   -- No group running 
                      suspended(3) -- The active group is suspended
              }
              ACCESS  read-only
              STATUS  mandatory
              DESCRIPTION "Current state of the probe due to user's last action"
              ::= { probe 2 }
              
   prbBasePath OBJECT-TYPE
              SYNTAX  DisplayString (SIZE (1..80))
              ACCESS  read-only
              STATUS  mandatory
              DESCRIPTION "Base directory of the probe"
              ::= { probe 3 }


   prbGrpList OBJECT-TYPE
              SYNTAX  DisplayString (SIZE (1..512))
              ACCESS  read-only
              STATUS  mandatory
              DESCRIPTION "Set of NEWTEST groups available on the probe"
              ::= { probe 4 }


   prbServerConnection OBJECT-TYPE
              SYNTAX  INTEGER
              {
                    notConfigured(1), -- Connection to server not configured
                    disconnected(2),  -- Disconnected from server
                    connected(3)           -- Connected to server 
              }
              ACCESS  read-only
              STATUS  mandatory
              DESCRIPTION "Connection with Newtest Server"
              ::= { probe 5 }


   prbDiffGMT OBJECT-TYPE
              SYNTAX  INTEGER
              ACCESS  read-only
              STATUS  mandatory
              DESCRIPTION "GMT time - local time on this probe"
              ::= { probe 6 }


   prbNewtestMemory OBJECT-TYPE
              SYNTAX  INTEGER
              ACCESS  read-only
              STATUS  mandatory
              DESCRIPTION "Memory size of the Newtest process"
              ::= { probe 7 }


   prbGrpStartTime OBJECT-TYPE
              SYNTAX  TimeTicks 
              ACCESS  read-only
              STATUS  mandatory
              DESCRIPTION "Group start time written as the number of seconds since 1980, january the 1st or 0 if no group active"
              ::= { probe 8 }


   prbLastHeartBeat OBJECT-TYPE
              SYNTAX  TimeTicks 
              ACCESS  read-only
              STATUS  mandatory
              DESCRIPTION "Reserved"
              ::= { probe 9 }
              
   -- the action group
      
   actType OBJECT-TYPE
              SYNTAX  INTEGER 
                  {
                        suspend(230),       -- suspend the probe activity
                        resume(231),        -- resume the probe activity        
                        reboot(232),        -- reboot the probe
                        changeGroup(234),   -- change the default group
                        ackAlm(238),        -- acquire the alarms on the probe
                        runSce(239),        -- run a scenario
                        suspendSce(240),    -- interrupt the scheduling of a scenario
                        resumeSce(241),     -- resume the scheduling of a scenario 
                        stopGroup(242),     -- stop the current group
                        startGroup(243)     -- start a group
              }
              ACCESS  read-write
              STATUS  mandatory
              DESCRIPTION "Code of the command sent to the probe"
              ::= { action 1 }


   actParam OBJECT-TYPE
              SYNTAX  DisplayString (SIZE (0..80))
              ACCESS  read-write
              STATUS  mandatory
              DESCRIPTION "Parameter of the command sent to the probe"
             ::= { action 2 }


   -- the alarm group
      
   almSce OBJECT-TYPE
              SYNTAX  DisplayString (SIZE (1..65))
              ACCESS  read-only
              STATUS  mandatory
              DESCRIPTION "Name of the scenario which sent the alarm"
              ::= { alarm 1 }


   almMsg OBJECT-TYPE
              SYNTAX  DisplayString (SIZE (1..129))
              ACCESS  read-only
              STATUS  mandatory
              DESCRIPTION "Alarm message"
              ::= { alarm 2 }


   almCode OBJECT-TYPE
              SYNTAX  DisplayString (SIZE (1..65))
              ACCESS  read-only
              STATUS  mandatory
              DESCRIPTION "Identifier of the alarm"
              ::= { alarm 3 }


   almLevel OBJECT-TYPE
              SYNTAX  INTEGER
              ACCESS  read-only
              STATUS  mandatory
              DESCRIPTION "Level of the alarm"
              ::= { alarm 4 }


   almOrd OBJECT-TYPE
              SYNTAX  DisplayString (SIZE (1..65))
              ACCESS  read-only
              STATUS  mandatory
              DESCRIPTION "Name of the measure which sent the alarm "
              ::= { alarm 5 }


   -- the group group
   
   grpName  OBJECT-TYPE
              SYNTAX  DisplayString (SIZE (1..65))
              ACCESS  read-only
              STATUS  mandatory
              DESCRIPTION "Current NEWTEST group"
              ::= { group 1 }
   


   grpNbQueue OBJECT-TYPE
              SYNTAX  INTEGER (1..65535)
              ACCESS  read-only
              STATUS  mandatory
              DESCRIPTION "Number of NEWTEST queues"
              ::= { group 2 }
   
   grpNextTime OBJECT-TYPE
              SYNTAX  TimeTicks
              ACCESS  read-only
              STATUS  mandatory
              DESCRIPTION "Date of the end of the idle state. The date is written as the number of seconds since 1980, january the 1st."
              ::= { group 3 }


   -- the queue list accessible by index
              
   grpQueueList OBJECT-TYPE
              SYNTAX  SEQUENCE OF Queue
              ACCESS  not-accessible
              STATUS  mandatory
              DESCRIPTION "List of NEWTEST queues"
              ::= { group 4 }
              
   queue OBJECT-TYPE
              SYNTAX  Queue
              ACCESS  not-accessible
              STATUS  mandatory
              DESCRIPTION "Entry of NEWTEST queue list"
              INDEX   { queIndex }              
              ::= { grpQueueList 1 }


   Queue ::= SEQUENCE {
              queIndex           INTEGER,
              queName          DisplayString,
              queType          INTEGER,
              queNbSce         INTEGER
              }


   queIndex OBJECT-TYPE
              SYNTAX  INTEGER
              ACCESS  read-only
              STATUS  mandatory
              DESCRIPTION "Queue index"
              ::= { queue 1 }


   queName OBJECT-TYPE
              SYNTAX  DisplayString (SIZE (1..65))
              ACCESS  read-only
              STATUS  mandatory
              DESCRIPTION "Queue name"
              ::= { queue 2 }
   
   queType OBJECT-TYPE
              SYNTAX  INTEGER 
                  {
                      alarm(2), -- alarm scenario queue
                      user(1)   -- user and service scenario queue                      
              }
              ACCESS  read-only
              STATUS  mandatory
              DESCRIPTION "Queue type"
              ::= { queue 3 }


   queNbSce   OBJECT-TYPE
              SYNTAX  INTEGER
              ACCESS  read-only
              STATUS  mandatory
              DESCRIPTION "Nb of scenarios in the queue"
              ::= { queue 4}


   -- the scenario list accessible by index
                
   grpSceList  OBJECT-TYPE
              SYNTAX  SEQUENCE OF Scenario
              ACCESS  not-accessible
              STATUS  mandatory
              DESCRIPTION "List of scenarios of this group"
              ::= { group 5 }
              
   scenario OBJECT-TYPE
              SYNTAX  Scenario
              ACCESS  not-accessible
              STATUS  mandatory
              DESCRIPTION "Entry of list of scenarios"
              INDEX   { sceQueIndex, sceIndex }
              ::= { grpSceList 1 }


   Scenario ::= SEQUENCE {
              sceIndex         INTEGER,
              sceQueIndex      INTEGER,
              sceName          DisplayString,
              sceType          INTEGER,
              sceUnavailObj    INTEGER,
              sceState         INTEGER,
              sceNbExec        Counter,
              sceNbUnAvailExec Counter,
                  sceStartTime     TimeTicks,
                  sceAccumulationMeasureDuration     Counter,
                  sceAccumulationUnavailDuration     Counter,
              sceNbOrd         INTEGER,
              sceState2        INTEGER
              }


   sceIndex OBJECT-TYPE
              SYNTAX  INTEGER
              ACCESS  read-only
              STATUS  mandatory
              DESCRIPTION "Scenario index"
              ::= { scenario 1 }


   sceQueIndex OBJECT-TYPE
              SYNTAX  INTEGER
              ACCESS  read-only
              STATUS  mandatory
              DESCRIPTION "Queue index"
              ::= { scenario 2 }


   sceName OBJECT-TYPE
              SYNTAX  DisplayString (SIZE (1..65))
              ACCESS  read-only
              STATUS  mandatory
              DESCRIPTION "Scenario name"
              ::= { scenario 3 }
   
   sceType OBJECT-TYPE
              SYNTAX  INTEGER 
                  {
                  user(0),    -- 
                  service(1), --                       
                  alarm(2)    --
                  }
              ACCESS  read-only
              STATUS  mandatory
              DESCRIPTION "Scenario type"
              ::= { scenario 4 }
   
   sceUnavailObj OBJECT-TYPE


              SYNTAX  INTEGER (0..100)
              ACCESS  read-only
              STATUS  mandatory
              DESCRIPTION "Disponibility objective"
              ::= { scenario 5 }


   sceState OBJECT-TYPE
              SYNTAX  INTEGER 
                  {
                  ok(0),          -- 
                  unavailable(1), --                       
                  alarm(2),       --
                  suspended(4)    --
                  }
              ACCESS  read-only
              STATUS  mandatory
              DESCRIPTION "Last scenario state"
              ::= { scenario 6 }


   sceNbExec OBJECT-TYPE
              SYNTAX  Counter
              ACCESS  read-only
              STATUS  mandatory
              DESCRIPTION "Number of scenario executions"
              ::= { scenario 7 }
              
   sceNbUnAvailExec OBJECT-TYPE
              SYNTAX  Counter
              ACCESS  read-only              
              STATUS  mandatory
              DESCRIPTION "Number of unavailable scenario executions"
              ::= { scenario 8 }
   
   sceStartTime OBJECT-TYPE
              SYNTAX  TimeTicks
              ACCESS  read-only
              STATUS  mandatory
              DESCRIPTION "Scenario start time. The time is written as the number of seconds since 1980, january the 1st. 0 if the scenario is not running"
              ::= { scenario 9 }


   sceAccumulationMeasureDuration OBJECT-TYPE
              SYNTAX  Counter
              ACCESS  read-only
              STATUS  mandatory
              DESCRIPTION "Scenario total measure duration"
              ::= { scenario 10 }


   sceAccumulationUnavailDuration OBJECT-TYPE
              SYNTAX  Counter
              ACCESS  read-only
              STATUS  mandatory
              DESCRIPTION "Scenario total unavaibility duration"
              ::= { scenario 11 }


   sceNbOrd   OBJECT-TYPE
              SYNTAX  INTEGER
              ACCESS  read-only
              STATUS  mandatory
              DESCRIPTION "Nb of orders in the scenario"
              ::= { scenario 12 }


   sceState2 OBJECT-TYPE
              SYNTAX  INTEGER 
                  {
                  init(1),       -- At least one execution since group start 
                  outOfRange(2), -- Outside of range (user scenario only)                      
                          suspended(4),  -- The scenario is suspended
                          unavailable(8) -- Last execution unavailable
                  }
              ACCESS  read-only
              STATUS  mandatory
              DESCRIPTION "Last scenario state. State is a combination of values"
              ::= { scenario 13 }
 
   -- the order list accessible by index (response time and numeric orders)
 
   grpOrdList OBJECT-TYPE
              SYNTAX  SEQUENCE OF Order
              ACCESS  not-accessible
              STATUS  mandatory
              DESCRIPTION "List of orders"
              ::= { group 6 }
              
   order OBJECT-TYPE
              SYNTAX  Order
              ACCESS  not-accessible
              STATUS  mandatory
              DESCRIPTION "Entry of list of order"
              INDEX   { ordQueIndex, ordSceIndex, ordIndex }
              ::= { grpOrdList 1 }


   Order ::= SEQUENCE {
              ordIndex             INTEGER,
              ordSceIndex          INTEGER,
              ordQueIndex          INTEGER,
              ordName              DisplayString,
              ordType              INTEGER,
              ordObjNbRef          INTEGER,
              ordRef               INTEGER,
              ordAccumulationNbRef Counter,
              ordCoef              INTEGER,
              ordUnit              DisplayString,
              ordMin               INTEGER,
              ordMax               INTEGER,
              ordAccumulation      Counter,
              ordAverage6          INTEGER,
              ordNbSamples         Counter,
              ordThreashold1       INTEGER,
              ordThreashold2       INTEGER,
              ordThreashold3       INTEGER,
              ordThreashold4       INTEGER,
              ordAccumulationNb1   Counter,
              ordAccumulationNb2   Counter,
              ordAccumulationNb3   Counter,
              ordAccumulationNb4   Counter,
              ordAccumulationNb5   Counter,
              ordNbUnavail                 Counter,
              ordTime              TimeTicks,
              ordValue             INTEGER,
              ordErrCode           DisplayString,
              ordPrev1Time         TimeTicks,
              ordPrev1Value        INTEGER,
              ordPrev1ErrCode      DisplayString,
              ordPrev2Time         TimeTicks,
              ordPrev2Value        INTEGER,
              ordPrev2ErrCode      DisplayString,
              ordPrev3Time         TimeTicks,
              ordPrev3Value        INTEGER,
              ordPrev3ErrCode      DisplayString,
              ordPrev4Time         TimeTicks,
              ordPrev4Value        INTEGER,
              ordPrev4ErrCode      DisplayString,
              ordPrev5Time         TimeTicks,
              ordPrev5Value        INTEGER,
              ordPrev5ErrCode      DisplayString
              }
              
   ordIndex OBJECT-TYPE
              SYNTAX  INTEGER
              ACCESS  read-only
              STATUS  mandatory
              DESCRIPTION "Order index"
              ::= { order 1 }
   
   ordSceIndex OBJECT-TYPE
              SYNTAX  INTEGER
              ACCESS  read-only
              STATUS  mandatory
              DESCRIPTION "Sce index"
              ::= { order 2 }


   ordQueIndex OBJECT-TYPE
              SYNTAX  INTEGER
              ACCESS  read-only
              STATUS  mandatory
              DESCRIPTION "Que Index"
              ::= { order 3 }


   ordName OBJECT-TYPE
              SYNTAX  DisplayString (SIZE (1..65))
              ACCESS  read-only
              STATUS  mandatory
              DESCRIPTION "Order name"
              ::= { order 4 }


   ordType OBJECT-TYPE
              SYNTAX  INTEGER
                  {
                  tps(0), -- 
                  num(2)  --
                  }
              ACCESS  read-only
              STATUS  mandatory
              DESCRIPTION "Order type"
              ::= { order 5 }
   
   ordObjNbRef OBJECT-TYPE
              SYNTAX  INTEGER (0..100)
              ACCESS  read-only
              STATUS  mandatory
              DESCRIPTION "Response time objective: percentage of samples that are lower or equal than the reference value."
              ::= { order 6 }


   ordRef OBJECT-TYPE
              SYNTAX  INTEGER (1..2147483647)
              ACCESS  read-only
              STATUS  mandatory
              DESCRIPTION "Order's value reference"
              ::= { order 7 }


   ordAccumulationNbRef OBJECT-TYPE
              SYNTAX  Counter
              ACCESS  read-only
              STATUS  mandatory
              DESCRIPTION "Number of orders that are lower or equal than the reference value."
              ::= { order 8 }


   ordCoef OBJECT-TYPE
              SYNTAX  INTEGER (1..2147483647)
              ACCESS  read-only
              STATUS  mandatory
              DESCRIPTION "Order scale coefficient"
              ::= { order 9 }
              
   ordUnit OBJECT-TYPE
              SYNTAX  DisplayString (SIZE (1..65))
              ACCESS  read-only
              STATUS  mandatory
              DESCRIPTION "Unit of order value"
              ::= { order 10 }
                           
   ordMin OBJECT-TYPE
              SYNTAX  INTEGER (1..2147483647)
              ACCESS  read-only
              STATUS  mandatory
              DESCRIPTION "Minimum of order sample"
              ::= { order 11 }


   ordMax OBJECT-TYPE
              SYNTAX  INTEGER (1..2147483647)
              ACCESS  read-only
              STATUS  mandatory
              DESCRIPTION "Maximum of order sample"
              ::= { order 12 }


   ordAccumulation OBJECT-TYPE
              SYNTAX  Counter
              ACCESS  read-only
              STATUS  mandatory
              DESCRIPTION "Accumulation of orders' value since the last start"
              ::= { order 13 }


   ordAverage6 OBJECT-TYPE
              SYNTAX  INTEGER (1..2147483647)
              ACCESS  read-only
              STATUS  mandatory
              DESCRIPTION "Average of the 6 last orders' value"
              ::= { order 14 }


   ordNbSamples OBJECT-TYPE
              SYNTAX  Counter
              ACCESS  read-only
              STATUS  mandatory
              DESCRIPTION "Number of response time samples or numerical samples"
              ::= { order 15 }
              
   ordThreashold1 OBJECT-TYPE
              SYNTAX  INTEGER (1..2147483647)
              ACCESS  read-only
              STATUS  mandatory
              DESCRIPTION "Theashold number 1"
              ::= { order 16 }


   ordThreashold2 OBJECT-TYPE
              SYNTAX  INTEGER (1..2147483647)
              ACCESS  read-only
              STATUS  mandatory
              DESCRIPTION "Theashold number 2"
              ::= { order 17 }


   ordThreashold3 OBJECT-TYPE
              SYNTAX  INTEGER (1..2147483647)
              ACCESS  read-only
              STATUS  mandatory
              DESCRIPTION "Theashold number 3"
              ::= { order 18 }


   ordThreashold4 OBJECT-TYPE
              SYNTAX  INTEGER (1..2147483647)
              ACCESS  read-only
              STATUS  mandatory
              DESCRIPTION "Theashold number 4"
              ::= { order 19 }


   ordAccumulationNb1 OBJECT-TYPE
              SYNTAX  Counter
              ACCESS  read-only
              STATUS  mandatory
              DESCRIPTION "Number of order's value that are lower than theashold number 1"
              ::= { order 20 }


   ordAccumulationNb2 OBJECT-TYPE
              SYNTAX  Counter
              ACCESS  read-only
              STATUS  mandatory
              DESCRIPTION "Number of order's value that are upper than theashold number 1 and lower than theashold number 2"
              ::= { order 21 }


   ordAccumulationNb3 OBJECT-TYPE
              SYNTAX  Counter
              ACCESS  read-only
              STATUS  mandatory
              DESCRIPTION "Number of order's value that are upper than theashold number 2 and lower than theashold number 3"
              ::= { order 22 }


   ordAccumulationNb4 OBJECT-TYPE
              SYNTAX  Counter
              ACCESS  read-only
              STATUS  mandatory
              DESCRIPTION "Number of order's value that are upper than theashold number 3 and lower than theashold number 4"
              ::= { order 23 }


   ordAccumulationNb5 OBJECT-TYPE
              SYNTAX  Counter
              ACCESS  read-only
              STATUS  mandatory
              DESCRIPTION "Number of order's value that are upper than 4"
              ::= { order 24 }


   ordNbUnavail OBJECT-TYPE
              SYNTAX  Counter
              ACCESS  read-only
              STATUS  mandatory
              DESCRIPTION "Number of unavailabilities for this order"
              ::= { order 25 }                                  


   ordTime OBJECT-TYPE
              SYNTAX  TimeTicks
              ACCESS  read-only
              STATUS  mandatory
              DESCRIPTION "Date of order execution. The date is written as the number of seconds since 1980, january the 1st"
              ::= { order 26 }                                  


   ordValue OBJECT-TYPE
          SYNTAX  INTEGER (1..2147483647)
              ACCESS  read-only
              STATUS  mandatory
              DESCRIPTION "Result of order execution"
              ::= { order 27 }                                  


   ordErrCode OBJECT-TYPE
              SYNTAX  DisplayString (SIZE (1..65))
              ACCESS  read-only
              STATUS  mandatory
              DESCRIPTION "Error code for order execution"
              ::= { order 28 }                                  


   ordPrev1Time OBJECT-TYPE
              SYNTAX  TimeTicks
              ACCESS  read-only
              STATUS  mandatory
              DESCRIPTION "Date of order execution (for sample = current - 1). The date is written as the number of seconds since 1980, january the 1st"
              ::= { order 29 }                                  


   ordPrev1Value OBJECT-TYPE
          SYNTAX  INTEGER (1..2147483647)
              ACCESS  read-only
              STATUS  mandatory
              DESCRIPTION "Result of order execution (for sample = current -1)"
              ::= { order 30 }                          


   ordPrev1ErrCode OBJECT-TYPE
              SYNTAX  DisplayString (SIZE (1..65))
              ACCESS  read-only
              STATUS  mandatory
              DESCRIPTION "Error code for order execution (for sample = current - 1)"
              ::= { order 31 }                          


   ordPrev2Time OBJECT-TYPE
              SYNTAX  TimeTicks
              ACCESS  read-only
              STATUS  mandatory
              DESCRIPTION "Date of order execution (for sample = current - 2). The date is written as the number of seconds since 1980, january the 1st"
              ::= { order 32 }                                  


   ordPrev2Value OBJECT-TYPE
          SYNTAX  INTEGER (1..2147483647)
              ACCESS  read-only
              STATUS  mandatory
              DESCRIPTION "Result of order execution (for sample = current - 2)"
              ::= { order 33 }                          


   ordPrev2ErrCode OBJECT-TYPE
              SYNTAX  DisplayString (SIZE (1..65))
              ACCESS  read-only
              STATUS  mandatory
              DESCRIPTION "Error code for order execution (for sample = current - 2)"
              ::= { order 34 }                          


   ordPrev3Time OBJECT-TYPE
              SYNTAX  TimeTicks
              ACCESS  read-only
              STATUS  mandatory
              DESCRIPTION "Date of order execution (for sample = current - 3). The date is written as the number of seconds since 1980, january the 1st"
              ::= { order 35 }                                  



   ordPrev3Value OBJECT-TYPE
          SYNTAX  INTEGER (1..2147483647)
              ACCESS  read-only
              STATUS  mandatory
              DESCRIPTION "Result of order execution (for sample = current - 3)"
              ::= { order 36 }                          


   ordPrev3ErrCode OBJECT-TYPE
              SYNTAX  DisplayString (SIZE (1..65))
              ACCESS  read-only
              STATUS  mandatory
              DESCRIPTION "Error code for order execution (for sample = current - 3)"
              ::= { order 37 }                          


   ordPrev4Time OBJECT-TYPE
              SYNTAX  TimeTicks
              ACCESS  read-only
              STATUS  mandatory
              DESCRIPTION "Date of order execution (for sample = current - 4). The date is written as the number of seconds since 1980, january the 1st"
              ::= { order 38 }                                  


   ordPrev4Value OBJECT-TYPE
          SYNTAX  INTEGER (1..2147483647)
              ACCESS  read-only
              STATUS  mandatory
              DESCRIPTION "Result of order execution (for sample = current - 4)"
              ::= { order 39 }                          


   ordPrev4ErrCode OBJECT-TYPE
              SYNTAX  DisplayString (SIZE (1..65))
              ACCESS  read-only
              STATUS  mandatory
              DESCRIPTION "Error code for order execution (for sample = current - 4)"
              ::= { order 40 }                          


   ordPrev5Time OBJECT-TYPE
              SYNTAX  TimeTicks
              ACCESS  read-only
              STATUS  mandatory
              DESCRIPTION "Date of order execution (for sample = current - 5). The date is written as the number of seconds since 1980, january the 1st"
              ::= { order 41 }                                  


   ordPrev5Value OBJECT-TYPE
          SYNTAX  INTEGER (1..2147483647)
              ACCESS  read-only
              STATUS  mandatory
              DESCRIPTION "Result of order execution (for sample = current - 5)"
              ::= { order 42 }                          



   ordPrev5ErrCode OBJECT-TYPE
              SYNTAX  DisplayString (SIZE (1..65))
              ACCESS  read-only
              STATUS  mandatory
              DESCRIPTION "Error code for order execution (for sample = current - 5)"
              ::= { order 43 }                          
 
   -- the order list accessible by index (text orders)
 
   grpOrdTxtList OBJECT-TYPE
              SYNTAX  SEQUENCE OF OrderTxt
              ACCESS  not-accessible
              STATUS  mandatory
              DESCRIPTION "List of text orders"
              ::= { group 7 }
              
   orderTxt OBJECT-TYPE
              SYNTAX  OrderTxt
              ACCESS  not-accessible
              STATUS  mandatory
              DESCRIPTION "Entry of list of text order"
              INDEX   { otxQueIndex, otxSceIndex, otxIndex }
              ::= { grpOrdTxtList 1 }


   OrderTxt ::= SEQUENCE {
              otxIndex             INTEGER,
              otxSceIndex          INTEGER,
              otxQueIndex          INTEGER,
              otxName              DisplayString,
              otxNbSamples         Counter,
              otxNbUnavail                 Counter,
              otxTime              TimeTicks,
              otxValue             DisplayString,
              otxErrCode           DisplayString,
              otxPrev1Time         TimeTicks,
              otxPrev1Value        DisplayString,
              otxPrev1ErrCode      DisplayString,
              otxPrev2Time         TimeTicks,
              otxPrev2Value        DisplayString,
              otxPrev2ErrCode      DisplayString,
              otxPrev3Time         TimeTicks,
              otxPrev3Value        DisplayString,
              otxPrev3ErrCode      DisplayString,
              otxPrev4Time         TimeTicks,
              otxPrev4Value        DisplayString,
              otxPrev4ErrCode      DisplayString,
              otxPrev5Time         TimeTicks,
              otxPrev5Value        DisplayString,
              otxPrev5ErrCode      DisplayString
              }
              
   otxIndex OBJECT-TYPE
              SYNTAX  INTEGER
              ACCESS  read-only
              STATUS  mandatory
              DESCRIPTION "Order index"
              ::= { orderTxt 1 }
   
   otxSceIndex OBJECT-TYPE
              SYNTAX  INTEGER
              ACCESS  read-only
              STATUS  mandatory
              DESCRIPTION "Sce index"
              ::= { orderTxt 2 }


   otxQueIndex OBJECT-TYPE
              SYNTAX  INTEGER
              ACCESS  read-only
              STATUS  mandatory
              DESCRIPTION "Que Index"
              ::= { orderTxt 3 }


   otxName OBJECT-TYPE
              SYNTAX  DisplayString (SIZE (1..65))
              ACCESS  read-only
              STATUS  mandatory
              DESCRIPTION "Order name"
              ::= { orderTxt 4 }


   otxNbSamples OBJECT-TYPE
              SYNTAX  Counter
              ACCESS  read-only
              STATUS  mandatory
              DESCRIPTION "Number of response time samples or numerical samples"
              ::= { orderTxt 5 }


   otxNbUnavail OBJECT-TYPE
              SYNTAX  Counter
              ACCESS  read-only
              STATUS  mandatory
              DESCRIPTION "Number of unavailabilities for this order"
              ::= { orderTxt 6 }                                        


   otxTime OBJECT-TYPE
              SYNTAX  TimeTicks
              ACCESS  read-only
              STATUS  mandatory
              DESCRIPTION "Date of order execution. The date is written as the number of seconds since 1980, january the 1st"
              ::= { orderTxt 7 }                                        


   otxValue OBJECT-TYPE
              SYNTAX  DisplayString (SIZE (1..2048))
              ACCESS  read-only
              STATUS  mandatory
              DESCRIPTION "Result of order execution"
              ::= { orderTxt 8 }                                        


   otxErrCode OBJECT-TYPE
              SYNTAX  DisplayString (SIZE (1..65))
              ACCESS  read-only
              STATUS  mandatory
              DESCRIPTION "Error code for order execution"
              ::= { orderTxt 9 }                                        


   otxPrev1Time OBJECT-TYPE
              SYNTAX  TimeTicks
              ACCESS  read-only
              STATUS  mandatory
              DESCRIPTION "Date of order execution (for sample = current - 1). The date is written as the number of seconds since 1980, january the 1st"
              ::= { orderTxt 10 }                                       


   otxPrev1Value OBJECT-TYPE
              SYNTAX  DisplayString (SIZE (1..2048))
              ACCESS  read-only
              STATUS  mandatory
              DESCRIPTION "Result of order execution (for sample = current -1)"
              ::= { orderTxt 11 }                               


   otxPrev1ErrCode OBJECT-TYPE
              SYNTAX  DisplayString (SIZE (1..65))
              ACCESS  read-only
              STATUS  mandatory
              DESCRIPTION "Error code for order execution (for sample = current - 1)"
              ::= { orderTxt 12 }                               


   otxPrev2Time OBJECT-TYPE
              SYNTAX  TimeTicks
              ACCESS  read-only
              STATUS  mandatory
              DESCRIPTION "Date of order execution (for sample = current - 2). The date is written as the number of seconds since 1980, january the 1st"
              ::= { orderTxt 13 }                                       


   otxPrev2Value OBJECT-TYPE
              SYNTAX  DisplayString (SIZE (1..2048))
              ACCESS  read-only
              STATUS  mandatory
              DESCRIPTION "Result of order execution (for sample = current - 2)"
              ::= { orderTxt 14 }                               


   otxPrev2ErrCode OBJECT-TYPE
              SYNTAX  DisplayString (SIZE (1..65))
              ACCESS  read-only
              STATUS  mandatory
              DESCRIPTION "Error code for order execution (for sample = current - 2)"
              ::= { orderTxt 15 }                               


   otxPrev3Time OBJECT-TYPE
              SYNTAX  TimeTicks
              ACCESS  read-only
              STATUS  mandatory
              DESCRIPTION "Date of order execution (for sample = current - 3). The date is written as the number of seconds since 1980, january the 1st"
              ::= { orderTxt 16 }                                       



   otxPrev3Value OBJECT-TYPE
              SYNTAX  DisplayString (SIZE (1..2048))
              ACCESS  read-only
              STATUS  mandatory
              DESCRIPTION "Result of order execution (for sample = current - 3)"
              ::= { orderTxt 17 }                               


   otxPrev3ErrCode OBJECT-TYPE
              SYNTAX  DisplayString (SIZE (1..65))
              ACCESS  read-only
              STATUS  mandatory
              DESCRIPTION "Error code for order execution (for sample = current - 3)"
              ::= { orderTxt 18 }                               


   otxPrev4Time OBJECT-TYPE
              SYNTAX  TimeTicks
              ACCESS  read-only
              STATUS  mandatory
              DESCRIPTION "Date of order execution (for sample = current - 4). The date is written as the number of seconds since 1980, january the 1st"
              ::= { orderTxt 19 }                                       


   otxPrev4Value OBJECT-TYPE
              SYNTAX  DisplayString (SIZE (1..2048))
              ACCESS  read-only
              STATUS  mandatory
              DESCRIPTION "Result of order execution (for sample = current - 4)"
              ::= { orderTxt 20 }                               


   otxPrev4ErrCode OBJECT-TYPE
              SYNTAX  DisplayString (SIZE (1..65))
              ACCESS  read-only
              STATUS  mandatory
              DESCRIPTION "Error code for order execution (for sample = current - 4)"
              ::= { orderTxt 21 }                               


   otxPrev5Time OBJECT-TYPE
              SYNTAX  TimeTicks
              ACCESS  read-only
              STATUS  mandatory
              DESCRIPTION "Date of order execution (for sample = current - 5). The date is written as the number of seconds since 1980, january the 1st"
              ::= { orderTxt 22 }                                       


   otxPrev5Value OBJECT-TYPE
              SYNTAX  DisplayString (SIZE (1..2048))
              ACCESS  read-only
              STATUS  mandatory
              DESCRIPTION "Result of order execution (for sample = current - 5)"
              ::= { orderTxt 23 }                               



   otxPrev5ErrCode OBJECT-TYPE
              SYNTAX  DisplayString (SIZE (1..65))
              ACCESS  read-only
              STATUS  mandatory
              DESCRIPTION "Error code for order execution (for sample = current - 5)"
              ::= { orderTxt 24 }                               


   -- the queue list accessible by name
              
   grpQueueByNameList OBJECT-TYPE
              SYNTAX  SEQUENCE OF QueueBN
              ACCESS  not-accessible
              STATUS  mandatory
              DESCRIPTION "List of NEWTEST queues accessible by name"
              ::= { group 8 }
              
   queueBN OBJECT-TYPE
              SYNTAX  QueueBN
              ACCESS  not-accessible
              STATUS  mandatory
              DESCRIPTION "Entry of NEWTEST queue list"
              INDEX   { queBNName }              
              ::= { grpQueueByNameList 1 }


   QueueBN ::= SEQUENCE {
              queBNName        DisplayString,
              queBNType        INTEGER,
              queBNNbSce       INTEGER
             }


   queBNName OBJECT-TYPE
              SYNTAX  DisplayString (SIZE (1..65))
              ACCESS  read-only
              STATUS  mandatory
              DESCRIPTION "Queue name"
              ::= { queueBN 1 }
   
   queBNType OBJECT-TYPE
              SYNTAX  INTEGER 
                  {
                      alarm(2), -- alarm scenario queue
                      user(1)   -- user and service scenario queue                      
              }
              ACCESS  read-only
              STATUS  mandatory
              DESCRIPTION "Queue type"
              ::= { queueBN 2 }


   queBNNbSce   OBJECT-TYPE
              SYNTAX  INTEGER
              ACCESS  read-only
              STATUS  mandatory
              DESCRIPTION "Nb of scenarios in the queue"
              ::= { queueBN 3}


   -- the scenario list accessible by names
                
   grpSceByNameList  OBJECT-TYPE
              SYNTAX  SEQUENCE OF ScenarioBN
              ACCESS  not-accessible
              STATUS  mandatory
              DESCRIPTION "List of scenarios accessible by name "
              ::= { group 9 }
              
   scenarioBN OBJECT-TYPE
              SYNTAX  ScenarioBN
              ACCESS  not-accessible
              STATUS  mandatory
              DESCRIPTION "Entry of list of scenarios"
              INDEX   { sceBNQueName, sceBNName }
              ::= { grpSceByNameList 1 }


   ScenarioBN ::= SEQUENCE {
              sceBNName          DisplayString,
              sceBNQueName       DisplayString,
              sceBNType          INTEGER,
              sceBNUnavailObj    INTEGER,
              sceBNState         INTEGER,
              sceBNNbExec        Counter,
              sceBNNbUnAvailExec Counter,
                  sceBNStartTime     TimeTicks,
                  sceBNAccumulationMeasureDuration     Counter,
                  sceBNAccumulationUnavailDuration     Counter,  
              sceBNNbOrd         INTEGER
              }


   sceBNName OBJECT-TYPE
              SYNTAX  DisplayString (SIZE (1..65))
              ACCESS  read-only
              STATUS  mandatory
              DESCRIPTION "Scenario name"
              ::= { scenarioBN 1 }


   sceBNQueName OBJECT-TYPE
              SYNTAX  DisplayString (SIZE (1..65))
              ACCESS  read-only
              STATUS  mandatory
              DESCRIPTION "Queue name"
              ::= { scenarioBN 2 }
   
   sceBNType OBJECT-TYPE
              SYNTAX  INTEGER 
                  {
                  user(0),    -- 
                  service(1), --                       
                  alarm(2)    --
                  }
              ACCESS  read-only
              STATUS  mandatory
              DESCRIPTION "Scenario type"
              ::= { scenarioBN 3 }
   
   sceBNUnavailObj OBJECT-TYPE


              SYNTAX  INTEGER (0..100)
              ACCESS  read-only
              STATUS  mandatory
              DESCRIPTION "Disponibility objective"
              ::= { scenarioBN 4 }


   sceBNState OBJECT-TYPE
              SYNTAX  INTEGER 
                  {
                  init(1),       -- At least one execution since group start 
                  outOfRange(2), -- Outside of range (user scenario only)                      
                      suspended(4),  -- The scenario is suspended
                      unavailable(8) -- Last executuon unavailable
                  }
              ACCESS  read-only
              STATUS  mandatory
              DESCRIPTION "Last scenario state. State is a combination of values"
              ::= { scenarioBN 5 }


   sceBNNbExec OBJECT-TYPE
              SYNTAX  Counter
              ACCESS  read-only
              STATUS  mandatory
              DESCRIPTION "Number of scenario executions"
              ::= { scenarioBN 6 }
              
   sceBNNbUnAvailExec OBJECT-TYPE
              SYNTAX  Counter
              ACCESS  read-only              
              STATUS  mandatory
              DESCRIPTION "Number of unavailable scenario executions"
              ::= { scenarioBN 7 }
   
   sceBNStartTime OBJECT-TYPE
              SYNTAX  TimeTicks
              ACCESS  read-only
              STATUS  mandatory
              DESCRIPTION "Scenario start time. The time is written as the number of seconds since 1980, january the 1st. 0 if the scenario is not running"
              ::= { scenarioBN 8 }


   sceBNAccumulationMeasureDuration OBJECT-TYPE
              SYNTAX  Counter
              ACCESS  read-only
              STATUS  mandatory
              DESCRIPTION "Scenario total measure duration"
              ::= { scenarioBN 9 }


   sceBNAccumulationUnavailDuration OBJECT-TYPE
              SYNTAX  Counter
              ACCESS  read-only
              STATUS  mandatory
              DESCRIPTION "Scenario total unavaibility duration"
              ::= { scenarioBN 10 }


   sceBNNbOrd OBJECT-TYPE
              SYNTAX  INTEGER
              ACCESS  read-only
              STATUS  mandatory
              DESCRIPTION "Nb of orders in the scenario"
              ::= { scenarioBN 11 }


   -- the order list accessible by names (response time and numeric orders)
 
   grpOrdByNameList OBJECT-TYPE
              SYNTAX  SEQUENCE OF OrderBN
              ACCESS  not-accessible
              STATUS  mandatory
              DESCRIPTION "List of orders"
              ::= { group 10 }
              
   orderBN    OBJECT-TYPE
              SYNTAX  OrderBN
              ACCESS  not-accessible
              STATUS  mandatory
              DESCRIPTION "Entry of list of order"
              INDEX   { ordBNQueName, ordBNSceName, ordBNName }
              ::= { grpOrdByNameList 1 }


   OrderBN ::= SEQUENCE {
              ordBNName              DisplayString,
              ordBNSceName           DisplayString,
              ordBNQueName           DisplayString,
              ordBNType              INTEGER,
              ordBNObjNbRef          INTEGER,
              ordBNRef               INTEGER,
              ordBNAccumulationNbRef Counter,
              ordBNCoef              INTEGER,
              ordBNUnit              DisplayString,
              ordBNMin               INTEGER,
              ordBNMax               INTEGER,
              ordBNAccumulation      Counter,
              ordBNAverage6          INTEGER,
              ordBNNbSamples         Counter,
              ordBNThreashold1       INTEGER,
              ordBNThreashold2       INTEGER,
              ordBNThreashold3       INTEGER,
              ordBNThreashold4       INTEGER,
              ordBNAccumulationNb1   Counter,
              ordBNAccumulationNb2   Counter,
              ordBNAccumulationNb3   Counter,
              ordBNAccumulationNb4   Counter,
              ordBNAccumulationNb5   Counter,
              ordBNNbUnavail         Counter,
              ordBNTime              TimeTicks,
              ordBNValue             INTEGER,
              ordBNErrCode           DisplayString,
              ordBNPrev1Time         TimeTicks,
              ordBNPrev1Value        INTEGER,
              ordBNPrev1ErrCode      DisplayString,
              ordBNPrev2Time         TimeTicks,
              ordBNPrev2Value        INTEGER,
              ordBNPrev2ErrCode      DisplayString,
              ordBNPrev3Time         TimeTicks,
              ordBNPrev3Value        INTEGER,
              ordBNPrev3ErrCode      DisplayString,
              ordBNPrev4Time         TimeTicks,
              ordBNPrev4Value        INTEGER,
              ordBNPrev4ErrCode      DisplayString,
              ordBNPrev5Time         TimeTicks,
              ordBNPrev5Value        INTEGER,
              ordBNPrev5ErrCode      DisplayString
              }
              
   ordBNName  OBJECT-TYPE
              SYNTAX  DisplayString (SIZE (1..65))
              ACCESS  read-only
              STATUS  mandatory
              DESCRIPTION "Order name"
              ::= { orderBN 1 }
   
   ordBNSceName OBJECT-TYPE
              SYNTAX  DisplayString (SIZE (1..65))
              ACCESS  read-only
              STATUS  mandatory
              DESCRIPTION "Sce name"
              ::= { orderBN 2 }


   ordBNQueName OBJECT-TYPE
              SYNTAX  DisplayString (SIZE (1..65))
              ACCESS  read-only
              STATUS  mandatory
              DESCRIPTION "Que name"
              ::= { orderBN 3 }


   ordBNType  OBJECT-TYPE
              SYNTAX  INTEGER
                  {
                  tps(0), -- 
                  num(2)  --
                  }
              ACCESS  read-only
              STATUS  mandatory
              DESCRIPTION "Order type"
              ::= { orderBN 4 }
   
   ordBNObjNbRef OBJECT-TYPE
              SYNTAX  INTEGER (0..100)
              ACCESS  read-only
              STATUS  mandatory
              DESCRIPTION "Response time objective: percentage of samples that are lower or equal than the reference value."
              ::= { orderBN 5 }


   ordBNRef OBJECT-TYPE
              SYNTAX  INTEGER (1..2147483647)
              ACCESS  read-only
              STATUS  mandatory
              DESCRIPTION "Order's value reference"
              ::= { orderBN 6 }


   ordBNAccumulationNbRef OBJECT-TYPE
              SYNTAX  Counter
              ACCESS  read-only
              STATUS  mandatory
              DESCRIPTION "Number of orders that are lower or equal than the reference value."
              ::= { orderBN 7 }


   ordBNCoef OBJECT-TYPE
              SYNTAX  INTEGER (1..2147483647)
              ACCESS  read-only
              STATUS  mandatory
              DESCRIPTION "Order scale coefficient"
              ::= { orderBN 8 }
              
   ordBNUnit OBJECT-TYPE
              SYNTAX  DisplayString (SIZE (1..65))
              ACCESS  read-only
              STATUS  mandatory
              DESCRIPTION "Unit of order value"
              ::= { orderBN 9 }
                           
   ordBNMin OBJECT-TYPE
              SYNTAX  INTEGER (1..2147483647)
              ACCESS  read-only
              STATUS  mandatory
              DESCRIPTION "Minimum of order sample"
              ::= { orderBN 10 }


   ordBNMax OBJECT-TYPE
              SYNTAX  INTEGER (1..2147483647)
              ACCESS  read-only
              STATUS  mandatory
              DESCRIPTION "Maximum of order sample"
              ::= { orderBN 11 }


   ordBNAccumulation OBJECT-TYPE
              SYNTAX  Counter
              ACCESS  read-only
              STATUS  mandatory
              DESCRIPTION "Accumulation of orders' value since the last start"
              ::= { orderBN 12 }


   ordBNAverage6 OBJECT-TYPE
              SYNTAX  INTEGER (1..2147483647)
              ACCESS  read-only
              STATUS  mandatory
              DESCRIPTION "Average of the 6 last orderBNs' value"
              ::= { orderBN 13 }


   ordBNNbSamples OBJECT-TYPE
              SYNTAX  Counter
              ACCESS  read-only
              STATUS  mandatory
              DESCRIPTION "Number of response time samples or numerical samples"
              ::= { orderBN 14 }
              
   ordBNThreashold1 OBJECT-TYPE
              SYNTAX  INTEGER (1..2147483647)
              ACCESS  read-only
              STATUS  mandatory
              DESCRIPTION "Theashold number 1"
              ::= { orderBN 15 }


   ordBNThreashold2 OBJECT-TYPE
              SYNTAX  INTEGER (1..2147483647)
              ACCESS  read-only
              STATUS  mandatory
              DESCRIPTION "Theashold number 2"
              ::= { orderBN 16 }


   ordBNThreashold3 OBJECT-TYPE
              SYNTAX  INTEGER (1..2147483647)
              ACCESS  read-only
              STATUS  mandatory
              DESCRIPTION "Theashold number 3"
              ::= { orderBN 17 }


   ordBNThreashold4 OBJECT-TYPE
              SYNTAX  INTEGER (1..2147483647)
              ACCESS  read-only
              STATUS  mandatory
              DESCRIPTION "Theashold number 4"
              ::= { orderBN 18 }


   ordBNAccumulationNb1 OBJECT-TYPE
              SYNTAX  Counter
              ACCESS  read-only
              STATUS  mandatory
              DESCRIPTION "Number of order's value that are lower than theashold number 1"
              ::= { orderBN 19 }


   ordBNAccumulationNb2 OBJECT-TYPE
              SYNTAX  Counter
              ACCESS  read-only
              STATUS  mandatory
              DESCRIPTION "Number of order's value that are upper than theashold number 1 and lower than theashold number 2"
              ::= { orderBN 20 }


   ordBNAccumulationNb3 OBJECT-TYPE
              SYNTAX  Counter
              ACCESS  read-only
              STATUS  mandatory
              DESCRIPTION "Number of order's value that are upper than theashold number 2 and lower than theashold number 3"
              ::= { orderBN 21 }


   ordBNAccumulationNb4 OBJECT-TYPE
              SYNTAX  Counter
              ACCESS  read-only
              STATUS  mandatory
              DESCRIPTION "Number of order's value that are upper than theashold number 3 and lower than theashold number 4"
              ::= { orderBN 22 }


   ordBNAccumulationNb5 OBJECT-TYPE
              SYNTAX  Counter
              ACCESS  read-only
              STATUS  mandatory
              DESCRIPTION "Number of order's value that are upper than 4"
              ::= { orderBN 23 }


   ordBNNbUnavail OBJECT-TYPE
              SYNTAX  Counter
              ACCESS  read-only
              STATUS  mandatory
              DESCRIPTION "Number of unavailabilities for this order"
              ::= { orderBN 24 }                                        


   ordBNTime OBJECT-TYPE
              SYNTAX  TimeTicks
              ACCESS  read-only
              STATUS  mandatory
              DESCRIPTION "Date of order execution. The date is written as the number of seconds since 1980, january the 1st"
              ::= { orderBN 25 }                                        


   ordBNValue OBJECT-TYPE
          SYNTAX  INTEGER (1..2147483647)
              ACCESS  read-only
              STATUS  mandatory
              DESCRIPTION "Result of order execution"
              ::= { orderBN 26 }                                        


   ordBNErrCode OBJECT-TYPE
              SYNTAX  DisplayString (SIZE (1..65))
              ACCESS  read-only
              STATUS  mandatory
              DESCRIPTION "Error code for order execution"
              ::= { orderBN 27 }                                        


   ordBNPrev1Time OBJECT-TYPE
              SYNTAX  TimeTicks
              ACCESS  read-only
              STATUS  mandatory
              DESCRIPTION "Date of order execution (for sample = current - 1). The date is written as the number of seconds since 1980, january the 1st"
              ::= { orderBN 28 }                                        


   ordBNPrev1Value OBJECT-TYPE
          SYNTAX  INTEGER (1..2147483647)
              ACCESS  read-only
              STATUS  mandatory
              DESCRIPTION "Result of order execution (for sample = current -1)"
              ::= { orderBN 29 }                                


   ordBNPrev1ErrCode OBJECT-TYPE
              SYNTAX  DisplayString (SIZE (1..65))
              ACCESS  read-only
              STATUS  mandatory
              DESCRIPTION "Error code for order execution (for sample = current - 1)"
              ::= { orderBN 30 }                                


   ordBNPrev2Time OBJECT-TYPE
              SYNTAX  TimeTicks
              ACCESS  read-only
              STATUS  mandatory
              DESCRIPTION "Date of order execution (for sample = current - 2). The date is written as the number of seconds since 1980, january the 1st"
              ::= { orderBN 31 }                                        


   ordBNPrev2Value OBJECT-TYPE
          SYNTAX  INTEGER (1..2147483647)
              ACCESS  read-only
              STATUS  mandatory
              DESCRIPTION "Result of order execution (for sample = current - 2)"
              ::= { orderBN 32 }                                


   ordBNPrev2ErrCode OBJECT-TYPE
              SYNTAX  DisplayString (SIZE (1..65))
              ACCESS  read-only
              STATUS  mandatory
              DESCRIPTION "Error code for order execution (for sample = current - 2)"
              ::= { orderBN 33 }                                


   ordBNPrev3Time OBJECT-TYPE
              SYNTAX  TimeTicks
              ACCESS  read-only
              STATUS  mandatory
              DESCRIPTION "Date of order execution (for sample = current - 3). The date is written as the number of seconds since 1980, january the 1st"
              ::= { orderBN 34 }                                        



   ordBNPrev3Value OBJECT-TYPE
          SYNTAX  INTEGER (1..2147483647)
              ACCESS  read-only
              STATUS  mandatory
              DESCRIPTION "Result of order execution (for sample = current - 3)"
              ::= { orderBN 35 }                                


   ordBNPrev3ErrCode OBJECT-TYPE
              SYNTAX  DisplayString (SIZE (1..65))
              ACCESS  read-only
              STATUS  mandatory
              DESCRIPTION "Error code for order execution (for sample = current - 3)"
              ::= { orderBN 36 }                                


   ordBNPrev4Time OBJECT-TYPE
              SYNTAX  TimeTicks
              ACCESS  read-only
              STATUS  mandatory
              DESCRIPTION "Date of order execution (for sample = current - 4). The date is written as the number of seconds since 1980, january the 1st"
              ::= { orderBN 37 }                                        


   ordBNPrev4Value OBJECT-TYPE
          SYNTAX  INTEGER (1..2147483647)
              ACCESS  read-only
              STATUS  mandatory
              DESCRIPTION "Result of order execution (for sample = current - 4)"
              ::= { orderBN 38 }                                


   ordBNPrev4ErrCode OBJECT-TYPE
              SYNTAX  DisplayString (SIZE (1..65))
              ACCESS  read-only
              STATUS  mandatory
              DESCRIPTION "Error code for order execution (for sample = current - 4)"
              ::= { orderBN 39 }                                


   ordBNPrev5Time OBJECT-TYPE
              SYNTAX  TimeTicks
              ACCESS  read-only
              STATUS  mandatory
              DESCRIPTION "Date of order execution (for sample = current - 5). The date is written as the number of seconds since 1980, january the 1st"
              ::= { orderBN 40 }                                        


   ordBNPrev5Value OBJECT-TYPE
          SYNTAX  INTEGER (1..2147483647)
              ACCESS  read-only
              STATUS  mandatory
              DESCRIPTION "Result of order execution (for sample = current - 5)"
              ::= { orderBN 41 }                                



   ordBNPrev5ErrCode OBJECT-TYPE
              SYNTAX  DisplayString (SIZE (1..65))
              ACCESS  read-only
              STATUS  mandatory
              DESCRIPTION "Error code for order execution (for sample = current - 5)"
              ::= { orderBN 42 }                                
 
   -- the order list accessible by names (text orders)
 
   grpOrdTxtByNameList OBJECT-TYPE
              SYNTAX  SEQUENCE OF OrderTxtBN
              ACCESS  not-accessible
              STATUS  mandatory
              DESCRIPTION "List of text orders"
              ::= { group 11 }
              
   orderTxtBN OBJECT-TYPE
              SYNTAX  OrderTxtBN
              ACCESS  not-accessible
              STATUS  mandatory
              DESCRIPTION "Entry of list of text order"
              INDEX   { otxBNQueName, otxBNSceName, otxBNName }
              ::= { grpOrdTxtByNameList 1 }


   OrderTxtBN ::= SEQUENCE {
              otxBNName              DisplayString,
              otxBNSceName           DisplayString,
              otxBNQueName           DisplayString,
              otxBNNbSamples         Counter,
              otxBNNbUnavail         Counter,
              otxBNTime              TimeTicks,
              otxBNValue             DisplayString,
              otxBNErrCode           DisplayString,
              otxBNPrev1Time         TimeTicks,
              otxBNPrev1Value        DisplayString,
              otxBNPrev1ErrCode      DisplayString,
              otxBNPrev2Time         TimeTicks,
              otxBNPrev2Value        DisplayString,
              otxBNPrev2ErrCode      DisplayString,
              otxBNPrev3Time         TimeTicks,
              otxBNPrev3Value        DisplayString,
              otxBNPrev3ErrCode      DisplayString,
              otxBNPrev4Time         TimeTicks,
              otxBNPrev4Value        DisplayString,
              otxBNPrev4ErrCode      DisplayString,
              otxBNPrev5Time         TimeTicks,
              otxBNPrev5Value        DisplayString,
              otxBNPrev5ErrCode      DisplayString
              }
              
   otxBNName OBJECT-TYPE
              SYNTAX  DisplayString (SIZE (1..65))
              ACCESS  read-only
              STATUS  mandatory
              DESCRIPTION "Order name"
              ::= { orderTxtBN 1 }
   
   otxBNSceName OBJECT-TYPE
              SYNTAX  DisplayString (SIZE (1..65))
              ACCESS  read-only
              STATUS  mandatory
              DESCRIPTION "Sce name"
              ::= { orderTxtBN 2 }


   otxBNQueName OBJECT-TYPE
              SYNTAX  DisplayString (SIZE (1..65))
              ACCESS  read-only
              STATUS  mandatory
              DESCRIPTION "Que name"
              ::= { orderTxtBN 3 }


   otxBNNbSamples OBJECT-TYPE
              SYNTAX  Counter
              ACCESS  read-only
              STATUS  mandatory
              DESCRIPTION "Number of response time samples or numerical samples"
              ::= { orderTxtBN 4 }


   otxBNNbUnavail OBJECT-TYPE
              SYNTAX  Counter
              ACCESS  read-only
              STATUS  mandatory
              DESCRIPTION "Number of unavailabilities for this order"
              ::= { orderTxtBN 5 }                                      


   otxBNTime OBJECT-TYPE
              SYNTAX  TimeTicks
              ACCESS  read-only
              STATUS  mandatory
              DESCRIPTION "Date of order execution. The date is written as the number of seconds since 1980, january the 1st"
              ::= { orderTxtBN 6 }                                      


   otxBNValue OBJECT-TYPE
              SYNTAX  DisplayString (SIZE (1..2048))
              ACCESS  read-only
              STATUS  mandatory
              DESCRIPTION "Result of order execution"
              ::= { orderTxtBN 7 }                                      


   otxBNErrCode OBJECT-TYPE
              SYNTAX  DisplayString (SIZE (1..65))
              ACCESS  read-only
              STATUS  mandatory
              DESCRIPTION "Error code for order execution"
              ::= { orderTxtBN 8 }                                      


   otxBNPrev1Time OBJECT-TYPE
              SYNTAX  TimeTicks
              ACCESS  read-only
              STATUS  mandatory
              DESCRIPTION "Date of order execution (for sample = current - 1). The date is written as the number of seconds since 1980, january the 1st"
              ::= { orderTxtBN 9 }                                      


   otxBNPrev1Value OBJECT-TYPE
              SYNTAX  DisplayString (SIZE (1..2048))
              ACCESS  read-only
              STATUS  mandatory
              DESCRIPTION "Result of order execution (for sample = current -1)"
              ::= { orderTxtBN 10 }                             


   otxBNPrev1ErrCode OBJECT-TYPE
              SYNTAX  DisplayString (SIZE (1..65))
              ACCESS  read-only
              STATUS  mandatory
              DESCRIPTION "Error code for order execution (for sample = current - 1)"
              ::= { orderTxtBN 11 }                             


   otxBNPrev2Time OBJECT-TYPE
              SYNTAX  TimeTicks
              ACCESS  read-only
              STATUS  mandatory
              DESCRIPTION "Date of order execution (for sample = current - 2). The date is written as the number of seconds since 1980, january the 1st"
              ::= { orderTxtBN 12 }                                     


   otxBNPrev2Value OBJECT-TYPE
              SYNTAX  DisplayString (SIZE (1..2048))
              ACCESS  read-only
              STATUS  mandatory
              DESCRIPTION "Result of order execution (for sample = current - 2)"
              ::= { orderTxtBN 13 }                             


   otxBNPrev2ErrCode OBJECT-TYPE
              SYNTAX  DisplayString (SIZE (1..65))
              ACCESS  read-only
              STATUS  mandatory
              DESCRIPTION "Error code for order execution (for sample = current - 2)"
              ::= { orderTxtBN 14 }                             


   otxBNPrev3Time OBJECT-TYPE
              SYNTAX  TimeTicks
              ACCESS  read-only
              STATUS  mandatory
              DESCRIPTION "Date of order execution (for sample = current - 3). The date is written as the number of seconds since 1980, january the 1st"
              ::= { orderTxtBN 15 }                                     



   otxBNPrev3Value OBJECT-TYPE
              SYNTAX  DisplayString (SIZE (1..2048))
              ACCESS  read-only
              STATUS  mandatory
              DESCRIPTION "Result of order execution (for sample = current - 3)"
              ::= { orderTxtBN 16 }                             


   otxBNPrev3ErrCode OBJECT-TYPE
              SYNTAX  DisplayString (SIZE (1..65))
              ACCESS  read-only
              STATUS  mandatory
              DESCRIPTION "Error code for order execution (for sample = current - 3)"
              ::= { orderTxtBN 17 }                             


   otxBNPrev4Time OBJECT-TYPE
              SYNTAX  TimeTicks
              ACCESS  read-only
              STATUS  mandatory
              DESCRIPTION "Date of order execution (for sample = current - 4). The date is written as the number of seconds since 1980, january the 1st"
              ::= { orderTxtBN 18 }                                     


   otxBNPrev4Value OBJECT-TYPE
              SYNTAX  DisplayString (SIZE (1..2048))
              ACCESS  read-only
              STATUS  mandatory
              DESCRIPTION "Result of order execution (for sample = current - 4)"
              ::= { orderTxtBN 19 }                             


   otxBNPrev4ErrCode OBJECT-TYPE
              SYNTAX  DisplayString (SIZE (1..65))
              ACCESS  read-only
              STATUS  mandatory
              DESCRIPTION "Error code for order execution (for sample = current - 4)"
              ::= { orderTxtBN 20 }                             


   otxBNPrev5Time OBJECT-TYPE
              SYNTAX  TimeTicks
              ACCESS  read-only
              STATUS  mandatory
              DESCRIPTION "Date of order execution (for sample = current - 5). The date is written as the number of seconds since 1980, january the 1st"
              ::= { orderTxtBN 21 }                                     


   otxBNPrev5Value OBJECT-TYPE
              SYNTAX  DisplayString (SIZE (1..2048))
              ACCESS  read-only
              STATUS  mandatory
              DESCRIPTION "Result of order execution (for sample = current - 5)"
              ::= { orderTxtBN 22 }                             



   otxBNPrev5ErrCode OBJECT-TYPE
              SYNTAX  DisplayString (SIZE (1..65))
              ACCESS  read-only
              STATUS  mandatory
              DESCRIPTION "Error code for order execution (for sample = current - 5)"
              ::= { orderTxtBN 23 }                             


   -- Notifications


   probeAlarmEvent NOTIFICATION-TYPE
    OBJECTS  { sysName, almSce, almMsg }
    STATUS current
    DESCRIPTION 
                "Sent by all Newtest versions"
    ::= {auditec 0 1}


   probeAlarmEvent2 NOTIFICATION-TYPE
    OBJECTS  { sysName, almSce, almOrd, almCode,almLevel, almMsg }
    STATUS current
    DESCRIPTION
                "Sent by all Newtest V7 and higher"
    ::= {auditec 0 3}
              
END
