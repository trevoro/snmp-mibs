ACC-PHONE DEFINITIONS ::= BEGIN

    IMPORTS
	 OBJECT-TYPE, IpAddress, TimeTicks, Gauge, Counter FROM RFC1155-SMI
        accTrapLogSeqNum FROM ACC-SYSTEM
	accBRG, DisplayString, RowStatus, IfIndex, SmdsAddress
             FROM ACC-MIB;

-- Phone Group
        accPhoneGroup OBJECT IDENTIFIER ::= { accBRG 50 }
	accPhoneTable OBJECT-TYPE
		SYNTAX SEQUENCE OF AccPhoneTableEntry
		ACCESS not-accessible
		STATUS mandatory
		DESCRIPTION
			"Table containing configuration and operational
			parameters for all PHONE ports."
		::= { accPhoneGroup 1 }
	accPhoneTableEntry OBJECT-TYPE
		SYNTAX AccPhoneTableEntry
		ACCESS not-accessible
		STATUS mandatory
		DESCRIPTION
			"An entry in the PHONE table."
		INDEX { accPhoneIndex }
		::= { accPhoneTable 1 }
	AccPhoneTableEntry ::= SEQUENCE {
		accPhoneIndex 		INTEGER,
		accPhoneDestinationPort	DisplayString,
		accPhoneHookStatus	INTEGER,
		accPhoneRingConfn       INTEGER,
		accPhoneNumber		DisplayString,
		accPhoneNumberStr	DisplayString,
		accPhoneAdminStatus	INTEGER,
		accPhoneAnswerMode	INTEGER,
		accPhoneCallWaitingMode	INTEGER
	}
	accPhoneIndex OBJECT-TYPE
		SYNTAX INTEGER 
		ACCESS read-only
		STATUS mandatory
		DESCRIPTION
			"The instance of the PHONE port to be displayed."
		    ::= { accPhoneTableEntry 1 }
	accPhoneDestinationPort OBJECT-TYPE
		SYNTAX	DisplayString
		ACCESS	read-only
		STATUS	mandatory
		DESCRIPTION
			"The physical port to which this PHONE port is 
			associated with. This value is the value of ifIndex
                        for this physical port."
		::= { accPhoneTableEntry 2 }
	accPhoneHookStatus OBJECT-TYPE
		SYNTAX INTEGER {
			onhook-idle  (1),
			onhook-ringing (2),
			offhook-congested (3),
			offhook-cleared (4),
			offhook-enbloc-ready (5),
			offhook-enbloc-dialing (6),
			offhook-active-normal (7),
			deleted (8),
			offhook-active-twocalls (9),
			offhook-active-callwaiting (10),
			offhook-active-threeparty (11),
			offhook-command-callwaiting (12),
			offhook-command-twocalls (13)
		}
		ACCESS read-only
		STATUS mandatory
		DESCRIPTION
			"The current status of the PHONE ports, indicating
			whether the PHONE is engaged in call activity or not
			Set this object to deleted to remove an entry from
			the phone table."
		    ::= { accPhoneTableEntry 3 }
        accPhoneRingConfn OBJECT-TYPE
                SYNTAX INTEGER {
                        ring-NA (1), -- North America
                        ring-EUR (2) -- Europe
                }
                ACCESS  read-write
                STATUS  mandatory
                DESCRIPTION
                        "The type of ring that needs to be sent to the
                        PHONE port. Current types support North American and
			European switches."
                ::= { accPhoneTableEntry 4 }
         accPhoneNumber OBJECT-TYPE
                SYNTAX DisplayString
                ACCESS read-write
                STATUS mandatory
                DESCRIPTION
                        "The telephone #s associated with this PHONE port."
                ::= { accPhoneTableEntry 5 }
         accPhoneNumberStr OBJECT-TYPE
                SYNTAX DisplayString
                ACCESS read-write
                STATUS mandatory
                DESCRIPTION
                        "The telephone #s associated with this PHONE port.
			 This is used in the custom display tables."
                ::= { accPhoneTableEntry 6 }
         accPhoneAdminStatus OBJECT-TYPE
                SYNTAX INTEGER {
			disabled (1),
			enabled (2)
		}
                ACCESS read-write
                STATUS mandatory
                DESCRIPTION
                        "Admin status of the phone port."
                ::= { accPhoneTableEntry 7 }
         accPhoneAnswerMode OBJECT-TYPE
                SYNTAX INTEGER {
                        disabled (1),
                        enabled (2)
                }
                ACCESS read-write
                STATUS mandatory
                DESCRIPTION
                        "When this is enabled incoming calls are allowed,
                        otherwise if it is disabled then the incoming calls
                        are not allowed."
                DEFVAL { enabled } 
		::= { accPhoneTableEntry 8 }
         accPhoneCallWaitingMode OBJECT-TYPE
                SYNTAX INTEGER {
                        disabled (1),
                        enabled (2)
                }
                ACCESS read-write
                STATUS mandatory
                DESCRIPTION
                        "When this is enabled incoming waiting calls are allowed,
                         otherwise they are rejected."
                DEFVAL { enabled } 
		::= { accPhoneTableEntry 9 }
	accPhoneContainerTable OBJECT-TYPE
		SYNTAX SEQUENCE OF AccPhoneContainerTableEntry
		ACCESS not-accessible
		STATUS mandatory
		DESCRIPTION
			"Table containing operational parameters for all 
			phone port call containers."
		::= { accPhoneGroup 2 }
	accPhoneContainerTableEntry OBJECT-TYPE
		SYNTAX AccPhoneContainerTableEntry
		ACCESS not-accessible
		STATUS mandatory
		DESCRIPTION
			"An entry in the call container table."
		INDEX { accPhoneContainerIndex }
		::= { accPhoneContainerTable 1 }
	AccPhoneContainerTableEntry ::= SEQUENCE {
		accPhoneContainerIndex 		INTEGER,
		accPhoneContainerPhonePort	INTEGER,
		accPhoneContainerStatus		INTEGER,
		accPhoneContainerCallRef	INTEGER,
		accPhoneContainerCallDir	INTEGER
	}
	accPhoneContainerIndex OBJECT-TYPE
		SYNTAX INTEGER 
		ACCESS read-only
		STATUS mandatory
		DESCRIPTION
			"The instance of the call container to be displayed."
		::= { accPhoneContainerTableEntry 1 }
	accPhoneContainerPhonePort OBJECT-TYPE
		SYNTAX INTEGER 
		ACCESS read-only
		STATUS mandatory
		DESCRIPTION
			"The index of the phone port associated with this 
			container."
		::= { accPhoneContainerTableEntry 2 }
	accPhoneContainerStatus OBJECT-TYPE
                SYNTAX INTEGER {
                        empty (1),
                        reserved (2),
			used-invisible (3),
			used-visible (4),
			used-held (5)
                }
		ACCESS read-only
		STATUS mandatory
		DESCRIPTION
			"The status of the call container."
		::= { accPhoneContainerTableEntry 3 }
	accPhoneContainerCallRef OBJECT-TYPE
                SYNTAX INTEGER
		ACCESS read-only
		STATUS mandatory
		DESCRIPTION
			"The ISDN call reference of the call associated with
			this container."
		::= { accPhoneContainerTableEntry 4 }
	accPhoneContainerCallDir OBJECT-TYPE
                SYNTAX INTEGER {
                        incoming (1),
                        outgoing (2),
			none (3)
                }
		ACCESS read-only
		STATUS mandatory
		DESCRIPTION
			"The direction of the call associated with this
			container."
		::= { accPhoneContainerTableEntry 5 }

END
