AIBADGER-MIB   DEFINITIONS ::= BEGIN

IMPORTS 	 
		OBJECT-TYPE, NOTIFICATION-TYPE, MODULE-IDENTITY,
    			Integer32, Opaque, enterprises
        		FROM SNMPv2-SMI

		TEXTUAL-CONVENTION, DisplayString, TruthValue
        		FROM SNMPv2-TC

		MODULE-COMPLIANCE, OBJECT-GROUP
			FROM SNMPv2-CONF
		Counter
			FROM RFC1155-SMI;

	ai-Badger  	MODULE-IDENTITY
		LAST-UPDATED "11022001"
		ORGANIZATION "Applied Innovation Inc."
		CONTACT-INFO "
			Engineering MIB Administrator
			Postal: Applied Innovation Inc.
			5800 Innovation Drive
			Dublin, OH 43016-3271
			Tel: 614-798-2000
			Fax: 614-798-1770
			E-mail: snmp@aiinet.com<mailto:snmp@aiinet.com>
			"
		DESCRIPTION  "A MIB module for AI's AIBadger"					
	::= { enterprises 1438 }


	netManager OBJECT IDENTIFIER ::= { ai-Badger 1 }
	aibadger OBJECT IDENTIFIER ::= { ai-Badger 2 }

	aibadgerInfo OBJECT IDENTIFIER ::= { aibadger 1 }

	aibadgerSAMVer OBJECT-TYPE
		SYNTAX DisplayString (SIZE (0..80))
		MAX-ACCESS read-only
		STATUS mandatory
		DESCRIPTION
			"The aibadgerSAMVer is its hardware and 
			software version for the aibadger and the 
			SAM board."
		::= { aibadgerInfo 1 }
		
        aibadgerMACAddr OBJECT-TYPE
                SYNTAX DisplayString (SIZE (0..17))
                MAX-ACCESS read-only
                STATUS mandatory
                DESCRIPTION
                        "The aibadgerMACAddr is the MAC Address of the
                        SAM board."
                ::= { aibadgerInfo 2 }


	aibadgerStatus OBJECT-TYPE
		SYNTAX DisplayString (SIZE (0..10))
		MAX-ACCESS read-only
		STATUS mandatory
		DESCRIPTION
			"The aibadgerStatus is the status of 
			the aibadger. The possible values are: working,
			failed, disabled."
		::= { aibadgerInfo 3 }

	aibadgerTimeTag OBJECT-TYPE
		SYNTAX DisplayString (SIZE (0..19))
		MAX-ACCESS read-only
		STATUS mandatory
		DESCRIPTION
			"The aibadgerTimeTag is the time stamp 
			when the aibadger status changed."
		::= { aibadgerInfo 4 }

	aibadgerRsp OBJECT-TYPE
		SYNTAX DisplayString (SIZE (0..80))
		MAX-ACCESS read-only
		STATUS mandatory
		DESCRIPTION
			"The aibadgerRsp is the descriptive string 
			for the aibadger status."
		::= { aibadgerInfo 5 }

	aibadgerTrapAck OBJECT-TYPE
    		SYNTAX     DisplayString (SIZE (0..30))
    		MAX-ACCESS read-write
    		STATUS     mandatory
    		DESCRIPTION
        	"The aibadgerTrapAck contains trap ID related information
		 if the trap needs to be acknowledged by the manager." 
    		::= { aibadgerInfo 6 }

	aibadgerTest OBJECT-TYPE
		SYNTAX DisplayString (SIZE (0..10))
		MAX-ACCESS read-write
		STATUS mandatory
		DESCRIPTION
			"The aibadgerTest is for testing the SNMP get 
			and set command for SNMP. Whenever this string 
			is changed it will send a trap to the SNMP manager"
		::= { aibadgerInfo 7 }

		
	deviceTbl OBJECT-TYPE
    		SYNTAX     SEQUENCE OF DeviceTblEntry
    		MAX-ACCESS not-accessible
    		STATUS     mandatory
    		DESCRIPTION
       			"The (conceptual) table listing the network element 
			devices connected to the SAM board"
    		::= { aibadger 2 }

	deviceTblEntry OBJECT-TYPE
    		SYNTAX     DeviceTblEntry
    		MAX-ACCESS not-accessible
    		STATUS     mandatory
    		DESCRIPTION
        	"An entry (conceptual row) in the deviceTbl."
    		INDEX      { devTblIndex }
    		::= { deviceTbl  1 }

	DeviceTblEntry ::=
    		SEQUENCE {
        		devTblIndex
            			INTEGER,
			devName
	    			DisplayString,
			devMacAddr
	    			DisplayString,
			devVersion
	    			DisplayString,
			devBiCnt
	    			INTEGER,
			devAnaCnt
	    			INTEGER,
			devCtrlCnt
				INTEGER,
			devStatus
	    			DisplayString,
			devStatusTimeTag
	    			DisplayString,
			devRspStr
				DisplayString,
			devTrapAck
				DisplayString
    			}

	devTblIndex OBJECT-TYPE
    		SYNTAX     INTEGER (0..65535)
    		MAX-ACCESS not-accessible
    		STATUS     mandatory
    		DESCRIPTION
        	"The auxiliary variable used for identifying instances of
         	the columnar objects in the deviceTbl."
    		::= { deviceTblEntry  1 }

	devName OBJECT-TYPE
    		SYNTAX     DisplayString (SIZE (0..20))
    		MAX-ACCESS read-only
    		STATUS     mandatory
    		DESCRIPTION
        	"The devName is the name of the BAM or other device 
		in the device table."
    		::= { deviceTblEntry  2 }


	devMacAddr OBJECT-TYPE
    		SYNTAX     DisplayString (SIZE (0..20))
    		MAX-ACCESS read-only
    		STATUS     mandatory
    		DESCRIPTION
        	"The devMacAddr is the Mac Address or hardware board 
		related address for the device in the device table."
    		::= { deviceTblEntry  3 }

	devVersion OBJECT-TYPE
    		SYNTAX     DisplayString (SIZE (0..50))
    		MAX-ACCESS read-only
    		STATUS     mandatory
    		DESCRIPTION
        	"The devVersion is the hardware and software version 
		for the device in the device table."
    		::= { deviceTblEntry  4 }


	devBiCnt OBJECT-TYPE
    		SYNTAX     INTEGER (0..65535)
    		MAX-ACCESS read-only
    		STATUS     mandatory
    		DESCRIPTION
        	"The devBiCnt is the number of bistate points for 
		the device in the device table."
    		::= { deviceTblEntry  5 }

	devAnaCnt OBJECT-TYPE
    		SYNTAX     INTEGER (0..65535)
    		MAX-ACCESS read-only
    		STATUS     mandatory
    		DESCRIPTION
        	"The devAnaCnt is the number of analog points for 
		the device in the device table."
    		::= { deviceTblEntry  6 }

	devCtrlCnt OBJECT-TYPE
    		SYNTAX     INTEGER (0..65535)
    		MAX-ACCESS read-only
    		STATUS     mandatory
    		DESCRIPTION
        	"The devCtrlCnt is the number of control points for 
		the device in the device table."
    		::= { deviceTblEntry  7 }

	devStatus OBJECT-TYPE
    		SYNTAX     DisplayString (SIZE (0..10))
    		MAX-ACCESS read-only
    		STATUS     mandatory
    		DESCRIPTION
        	"The devStatus is current Status for the device in 
		the device table. The possiable values are: working,failed,
		disabled."
    		::= { deviceTblEntry  8 }

	devStatusTimeTag OBJECT-TYPE
    		SYNTAX     DisplayString (SIZE (0..19))
    		MAX-ACCESS read-only
    		STATUS     mandatory
    		DESCRIPTION
        	"The devStatusTimeTag is time stamp of the current 
		status for the device in the device table."
    		::= { deviceTblEntry  9 }

	devRspStr OBJECT-TYPE
    		SYNTAX     DisplayString (SIZE (0..80))
    		MAX-ACCESS read-only
    		STATUS     mandatory
    		DESCRIPTION
        	"The devRspStr is more descriptive string for the 
		current status about this device."
    		::= { deviceTblEntry  10 }

	devTrapAck OBJECT-TYPE
    		SYNTAX     DisplayString (SIZE (0..30))
    		MAX-ACCESS read-write
    		STATUS     mandatory
    		DESCRIPTION
        	"The devTrapAck contains trap ID related information if the
		 trap needs to be acknowledged by the manager."  
    		::= { deviceTblEntry  11 }


	bistateTbl OBJECT-TYPE
    		SYNTAX     SEQUENCE OF BistateTblEntry
    		MAX-ACCESS not-accessible
    		STATUS     mandatory
    		DESCRIPTION
       		"The (conceptual) table listing all of the bistate 
		points for all of the devices on the aibadger"
    		::= { aibadger 3 }

	bistateTblEntry OBJECT-TYPE
    		SYNTAX     BistateTblEntry
    		MAX-ACCESS not-accessible
    		STATUS     mandatory
    		DESCRIPTION
        	"An entry (conceptual row) in the deviceTbl."
    		INDEX      { biTblIndex }
    		::= { bistateTbl  1 }

	BistateTblEntry ::=
    		SEQUENCE {
        		biTblIndex
            			INTEGER,
			biAlmID
				DisplayString,
		        biDeviceName
	    			DisplayString,
			biNumber
				INTEGER,
			biName
				DisplayString,
			biStatus
	    			DisplayString,
			biRspStr
	    			DisplayString,
			biStatusTimeTag
	    			DisplayString,
			biTrapAck
				DisplayString,
			biField1
				DisplayString,
			biField2
				DisplayString
    			}

	biTblIndex OBJECT-TYPE
    		SYNTAX     INTEGER (0..65535)
    		MAX-ACCESS not-accessible
    		STATUS     mandatory
    		DESCRIPTION
        	"The auxiliary variable used for identifying instances 
		of the columnar objects in the bistateTbl."
    		::= { bistateTblEntry  1 }

	biAlmID   OBJECT-TYPE
    		SYNTAX     DisplayString (SIZE (0..41))
    		MAX-ACCESS read-only
    		STATUS     mandatory
    		DESCRIPTION
        	"The biAlmID is the unique alarm identifier for the
		 aibadger."
    		::= { bistateTblEntry  2 }


	biDeviceName OBJECT-TYPE
    		SYNTAX     DisplayString (SIZE (0..20))
    		MAX-ACCESS read-only
    		STATUS     mandatory
    		DESCRIPTION
        	"The biDeviceName is the name of the device for this 
		bistate point."
    		::= { bistateTblEntry  3 }

	biNumber   OBJECT-TYPE
    		SYNTAX     INTEGER (0..65535)
    		MAX-ACCESS read-only
    		STATUS     mandatory
    		DESCRIPTION
        	"The biNumber is the physical number for the bistatepoint."
    		::= { bistateTblEntry  4 }

	biName OBJECT-TYPE
    		SYNTAX     DisplayString (SIZE (0..20))
    		MAX-ACCESS read-only
    		STATUS     mandatory
    		DESCRIPTION
        	"The biName is the user assigned name for this bistate point."
    		::= { bistateTblEntry  5 }

	biStatus OBJECT-TYPE
    		SYNTAX     DisplayString (SIZE (0..15))
    		MAX-ACCESS read-only
    		STATUS     mandatory
    		DESCRIPTION
        	"The biStatus is the current status for this bistate point.
		 The possiable values are: critical, major, minor-b, minor-a,
		 normal, informational, not-defined, maintenance."
    		::= { bistateTblEntry  6 }

	biRspStr OBJECT-TYPE
    		SYNTAX     DisplayString (SIZE (0..80))
    		MAX-ACCESS read-only
    		STATUS     mandatory
    		DESCRIPTION
        	"The biRspStr is the descriptive string for this current
		status for this bistate point."
    		::= { bistateTblEntry  7 }

	biStatusTimeTag OBJECT-TYPE
    		SYNTAX     DisplayString (SIZE (0..19))
    		MAX-ACCESS read-only
    		STATUS     mandatory
    		DESCRIPTION
        	"The biStatusTimeTag is the time stamp for the current 
		status when the status changed for this bistate point."
    		::= { bistateTblEntry  8 }


	biTrapAck OBJECT-TYPE
    		SYNTAX     DisplayString (SIZE (0..30))
    		MAX-ACCESS read-write
    		STATUS     mandatory
    		DESCRIPTION
        	"The biTrapAck contains trap IP related information if
		 the trap needs to be acknowledged by the manager." 
    		::= { bistateTblEntry  9 }

	biField1 OBJECT-TYPE
    		SYNTAX     DisplayString (SIZE (0..20))
    		MAX-ACCESS read-only
    		STATUS     mandatory
    		DESCRIPTION
        	"The biField1 holds additional information for each points."
    		::= { bistateTblEntry  10 }

	biField2 OBJECT-TYPE
    		SYNTAX     DisplayString (SIZE (0..20))
    		MAX-ACCESS read-only
    		STATUS     mandatory
    		DESCRIPTION
        	"The biField1 holds additional information for each points."
    		::= { bistateTblEntry  11 }


	analogTbl OBJECT-TYPE
    		SYNTAX     SEQUENCE OF AnalogTblEntry
    		MAX-ACCESS not-accessible
    		STATUS     mandatory
    		DESCRIPTION
       		"The (conceptual) table listing all of the analog 
		alarms for all the devices on the aibadger."
    		::= { aibadger 4 }

	analogTblEntry OBJECT-TYPE
    		SYNTAX     AnalogTblEntry
    		MAX-ACCESS not-accessible
    		STATUS     mandatory
    		DESCRIPTION
        	"An entry (conceptual row) in the analog table."
    		INDEX      { anaTblIndex }
    		::= { analogTbl  1 }

	AnalogTblEntry ::=
    		SEQUENCE {
        		anaTblIndex
            			INTEGER,
			anaAlmID
				DisplayString,
		        anaDeviceName
	    			DisplayString,
			anaNumber
				INTEGER,
			anaName
				DisplayString,
			anaStatus
	    			DisplayString,
			anaRspStr
	    			DisplayString,
			anaStatusTimeTag
	    			DisplayString,
			anaValue
				DisplayString,
			anaThreshold
				DisplayString,
			anaTrapAck
				DisplayString,
			anaField1
				DisplayString,
			anaField2
				DisplayString
    			}

	anaTblIndex OBJECT-TYPE
    		SYNTAX     INTEGER (0..65535)
    		MAX-ACCESS not-accessible
    		STATUS     mandatory
    		DESCRIPTION
        	"The auxiliary variable used for identifying instances 
		of the columnar objects in the analogTbl."
    		::= { analogTblEntry  1 }

	anaAlmID   OBJECT-TYPE
    		SYNTAX     DisplayString (SIZE (0..41))
    		MAX-ACCESS read-only
    		STATUS     mandatory
    		DESCRIPTION
        	"The anaAlmID is the unique alarm identifier for the aibadger."
    		::= { analogTblEntry  2 }


	anaDeviceName OBJECT-TYPE
    		SYNTAX     DisplayString (SIZE (0..20))
    		MAX-ACCESS read-only
    		STATUS     mandatory
    		DESCRIPTION
        	"The anaDeviceName is the name of the device for this 
		analog point."
    		::= { analogTblEntry  3 }

	anaNumber   OBJECT-TYPE
    		SYNTAX     INTEGER (0..65535)
    		MAX-ACCESS read-only
    		STATUS     mandatory
    		DESCRIPTION
        	"The anaNumber is the physical number for the analog point."
    		::= { analogTblEntry  4 }

	anaName OBJECT-TYPE
    		SYNTAX     DisplayString (SIZE (0..20))
    		MAX-ACCESS read-only
    		STATUS     mandatory
    		DESCRIPTION
        	"The anaName is the user assigned name for this analog point."
    		::= { analogTblEntry  5 }

	anaStatus OBJECT-TYPE
    		SYNTAX     DisplayString (SIZE (0..15))
    		MAX-ACCESS read-only
    		STATUS     mandatory
    		DESCRIPTION
        	"The anaStatus is the current status for this analog point.
		 The possiable values are: critical, major, minor-b, minor-a,
		 normal, informational, not-defined, maintenance."
    		::= { analogTblEntry  6 }

	anaRspStr OBJECT-TYPE
    		SYNTAX     DisplayString (SIZE (0..80))
    		MAX-ACCESS read-only
    		STATUS     mandatory
    		DESCRIPTION
        	"The anaRspStr is the descriptive string for this current 
		status for this analog point."
    		::= { analogTblEntry  7 }

	anaStatusTimeTag OBJECT-TYPE
    		SYNTAX     DisplayString (SIZE (0..19))
    		MAX-ACCESS read-only
    		STATUS     mandatory
    		DESCRIPTION
        	"The anaStatusTimeTag is the time stamp for the current 
		status when the status changed for this analog point."
    		::= { analogTblEntry  8 }

	anaValue OBJECT-TYPE
    		SYNTAX     DisplayString (SIZE (0..20))
    		MAX-ACCESS read-only
    		STATUS     mandatory
    		DESCRIPTION
        	"The anaValue is the current value for this analog point."
    		::= { analogTblEntry  9 }


	anaThreshold OBJECT-TYPE
    		SYNTAX     DisplayString (SIZE (0..20))
    		MAX-ACCESS read-only
    		STATUS     mandatory
    		DESCRIPTION
        	"The anaThreshold is the threshold for this analog point 
		indicating the off-normal and normal value range."
    		::= { analogTblEntry  10 }

	anaTrapAck OBJECT-TYPE
    		SYNTAX     DisplayString (SIZE (0..30))
    		MAX-ACCESS read-write
    		STATUS     mandatory
    		DESCRIPTION
        	"The anaTrapAck contains trap ID related information if
		 the trap needs to be acknowledged by the manager ."
    		::= { analogTblEntry  11 }

	anaField1 OBJECT-TYPE
    		SYNTAX     DisplayString (SIZE (0..20))
    		MAX-ACCESS read-only
    		STATUS     mandatory
    		DESCRIPTION
        	"The anaField1 holds additional information for each points."
    		::= { analogTblEntry  12 }

	anaField2 OBJECT-TYPE
    		SYNTAX     DisplayString (SIZE (0..20))
    		MAX-ACCESS read-only
    		STATUS     mandatory
    		DESCRIPTION
        	"The anaField1 holds additional information for each points."
    		::= { analogTblEntry  13 }


	controlTbl OBJECT-TYPE
    		SYNTAX     SEQUENCE OF ControlTblEntry
    		MAX-ACCESS not-accessible
    		STATUS     mandatory
    		DESCRIPTION
       			"The (conceptual) table listing all of the control points for all the devices on the aibadger"
    		::= { aibadger 5 }

	controlTblEntry OBJECT-TYPE
    		SYNTAX     ControlTblEntry
    		MAX-ACCESS not-accessible
    		STATUS     mandatory
    		DESCRIPTION
        	"An entry (conceptual row) in the control points table."
    		INDEX      { ctrlTblIndex }
    		::= { controlTbl  1 }

	ControlTblEntry ::=
    		SEQUENCE {
        		ctrlTblIndex
            			INTEGER,
			ctrlAlmID
				DisplayString,
		        ctrlDeviceName
	    			DisplayString,
			ctrlNumber
				INTEGER,
			ctrlName
				DisplayString,
			ctrlStatus
	    			DisplayString,
			ctrlRspStr
	    			DisplayString,
			ctrlStatusTimeTag
	    			DisplayString,
			ctrlState
				INTEGER,
			ctrlTrapAck
				DisplayString,
			ctrlField1
				DisplayString,
			ctrlField2
				DisplayString
    			}

	ctrlTblIndex OBJECT-TYPE
    		SYNTAX     INTEGER (0..65535)
    		MAX-ACCESS not-accessible
    		STATUS     mandatory
    		DESCRIPTION
        	"The auxiliary variable used for identifying instances of
         	the columnar objects in the ctrlstateTbl."
    		::= { controlTblEntry  1 }

	ctrlAlmID   OBJECT-TYPE
    		SYNTAX     DisplayString (SIZE (0..41))
    		MAX-ACCESS read-only
    		STATUS     mandatory
    		DESCRIPTION
        	"The ctrlAlmID is the unique alarm identifier for the aibadger."
    		::= { controlTblEntry  2 }


	ctrlDeviceName OBJECT-TYPE
    		SYNTAX     DisplayString (SIZE (0..20))
    		MAX-ACCESS read-only
    		STATUS     mandatory
    		DESCRIPTION
        	"The ctrlDeviceName is the name of the device for this control point."
    		::= { controlTblEntry  3 }

	ctrlNumber   OBJECT-TYPE
    		SYNTAX     INTEGER (0..65535)
    		MAX-ACCESS read-only
    		STATUS     mandatory
    		DESCRIPTION
        	"The ctrlNumber is the physical number for the  control point."
    		::= { controlTblEntry  4 }

	ctrlName OBJECT-TYPE
    		SYNTAX     DisplayString (SIZE (0..20))
    		MAX-ACCESS read-only
    		STATUS     mandatory
    		DESCRIPTION
        	"The ctrlName is the user assigned name for this control point."
    		::= { controlTblEntry  5 }

	ctrlStatus OBJECT-TYPE
    		SYNTAX     DisplayString (SIZE (0..15))
    		MAX-ACCESS read-only
    		STATUS     mandatory
    		DESCRIPTION
        	"The ctrlStatus is the current status for this control point.
		 The possiable values are: critical, major, minor-b, minor-a,
		 normal, informational, not-defined, maintenance."
    		::= { controlTblEntry  6 }

	ctrlRspStr OBJECT-TYPE
    		SYNTAX     DisplayString (SIZE (0..80))
    		MAX-ACCESS read-only
    		STATUS     mandatory
    		DESCRIPTION
        	"The ctrlRspStr is the descriptive string of the current 
		status for this bistate point."
    		::= { controlTblEntry  7 }

	ctrlStatusTimeTag OBJECT-TYPE
    		SYNTAX     DisplayString (SIZE (0..19))
    		MAX-ACCESS read-only
    		STATUS     mandatory
    		DESCRIPTION
        	"The ctrlStatusTimeTag is the time stamp for the 
		current status when the status changed for this bistate 
		point."
    		::= { controlTblEntry  8 }


	ctrlState OBJECT-TYPE
    		SYNTAX     INTEGER (1..4)
    		MAX-ACCESS read-write
    		STATUS     mandatory
    		DESCRIPTION
        	"The ctrlState represents the current state of the control 
		point.1--latch off,2--latch on,3--momentary off,4--momentary on."
    		::= { controlTblEntry  9 }

	ctrlTrapAck OBJECT-TYPE
    		SYNTAX     DisplayString (SIZE (0..30))
    		MAX-ACCESS read-write
    		STATUS     mandatory
    		DESCRIPTION
        	"The ctrlTrapAck contains trap ID related information
		 if the trap needs to be acknowledged by the manager." 
    		::= { controlTblEntry  10 }

	ctrlField1 OBJECT-TYPE
    		SYNTAX     DisplayString (SIZE (0..20))
    		MAX-ACCESS read-only
    		STATUS     mandatory
    		DESCRIPTION
        	"The ctrlField1 holds additional information for the point."
    		::= { controlTblEntry  11 }

	ctrlField2 OBJECT-TYPE
    		SYNTAX     DisplayString (SIZE (0..20))
    		MAX-ACCESS read-only
    		STATUS     mandatory
    		DESCRIPTION
        	"The ctrlField1 holds additional information for the point."
    		::= { controlTblEntry  12 }


	snmpManagerTbl OBJECT-TYPE
    		SYNTAX     SEQUENCE OF SnmpManagerTblEntry
    		MAX-ACCESS not-accessible
    		STATUS     mandatory
    		DESCRIPTION
       			"The (conceptual) table listing all of SNMP manager's
			names,IP addresses and community names configured on
			the aibadger"
    		::= { aibadger 6 }

	snmpManagerTblEntry OBJECT-TYPE
    		SYNTAX     SnmpManagerTblEntry
    		MAX-ACCESS not-accessible
    		STATUS     mandatory
    		DESCRIPTION
        	"An entry (conceptual row) in the snmp manager table."
    		INDEX      { name }
    		::= { snmpManagerTbl  1 }

	SnmpManagerTblEntry ::=
    		SEQUENCE {
			snmpTblIndex
				INTEGER,
			name
				DisplayString,
			ipAddr
				DisplayString,
		        community
	    			DisplayString
    			}

	snmpTblIndex OBJECT-TYPE
    		SYNTAX     INTEGER (0..8)
    		MAX-ACCESS not-accessible
    		STATUS     mandatory
    		DESCRIPTION
        	"The auxiliary variable used for identifying instances of
         	the columnar objects in the snmpManagerTbl."
    		::= { snmpManagerTblEntry  1 }

	name OBJECT-TYPE
    		SYNTAX     DisplayString (SIZE (0..20))
    		MAX-ACCESS read-only
    		STATUS     mandatory
    		DESCRIPTION
        	"The name is the name string for the SNMP manager."
    		::= { snmpManagerTblEntry 2 }

	ipAddr OBJECT-TYPE
    		SYNTAX     DisplayString (SIZE (0..15))
    		MAX-ACCESS read-only
    		STATUS     mandatory
    		DESCRIPTION
        	"The ipAddr is the IP address for the SNMP manager."
    		::= { snmpManagerTblEntry 3 }

	community OBJECT-TYPE
    		SYNTAX     DisplayString (SIZE (0..20))
    		MAX-ACCESS read-only
    		STATUS     mandatory
    		DESCRIPTION
        	"The commnity is the community name string for the 
		 SNMP manager."
    		::= { snmpManagerTblEntry 4 }

	snmpSettings OBJECT IDENTIFIER ::= { aibadger 7 }

	trapVer OBJECT-TYPE
    		SYNTAX     DisplayString (SIZE (0..5))
    		MAX-ACCESS read-only
    		STATUS     mandatory
    		DESCRIPTION
        	"The trapVer is the SNMP trap version the aibadger is
		 configured to send. The possiable values are v1, v2."
    		::= { snmpSettings 1 }

	trapControl OBJECT-TYPE
    		SYNTAX     DisplayString (SIZE (0..10))
    		MAX-ACCESS read-only
    		STATUS     mandatory
    		DESCRIPTION
        	"The trapControl indicates the aibadger is configured
		 to enable or disable all traps. The possiable values are 
		 enable or disable."
    		::= { snmpSettings 2 }

	trapSerControl OBJECT-TYPE
    		SYNTAX     DisplayString (SIZE (0..15))
    		MAX-ACCESS read-only
    		STATUS     mandatory
    		DESCRIPTION
        	"The trapSerControl is the severity threshold that triggers
		 a trap if trap control is enabled on the aibadger. The
		 possiable severity values are: critical,major,minor-a,minor-b"
    		::= { snmpSettings 3 }

	ackControl OBJECT-TYPE
    		SYNTAX     DisplayString (SIZE (0..10))
    		MAX-ACCESS read-only
    		STATUS     mandatory
    		DESCRIPTION
        	"The ackControl indicates if the aibadger is configured
		 to expect an acknowlegement from an SNMP manager when it sends
		 a trap. The SNMP manager must support this feature if you 
		 enable ackControl on the aibadger. The possiable values
		 for ackControl are enable or disable."
    		::= { snmpSettings 4 }

	ackSerControl OBJECT-TYPE
    		SYNTAX     DisplayString (SIZE (0..15))
    		MAX-ACCESS read-only
    		STATUS     mandatory
    		DESCRIPTION
        	"The ackSerControl is the trap severity threshold that enables
		 an acknowlegement from a SNMP manager if the ackControl 
		 is enabled on the aibadger. The SNMP manager must support
		 this feature. The possiable severity values are: critical,
		 major,minor-a,minor-b"
    		::= { snmpSettings 5 }

	aibadgerTraps OBJECT IDENTIFIER ::= { aibadger 8 }

	healthTrap OBJECT IDENTIFIER ::= { aibadgerTraps 1 }
	bistateTrap OBJECT IDENTIFIER ::= { aibadgerTraps 2 }
	analogTrap OBJECT IDENTIFIER ::= { aibadgerTraps 3 }
	controlTrap OBJECT IDENTIFIER ::= { aibadgerTraps 4 }
	testTrap OBJECT IDENTIFIER ::= { aibadgerTraps 5 }
	devTrap OBJECT IDENTIFIER ::= { aibadgerTraps 6 }

	healthCheck NOTIFICATION-TYPE
    		OBJECTS { aibadgerStatus, aibadgerRsp,
                	aibadgerSAMVer,aibadgerTimeTag }
		STATUS  current
    		DESCRIPTION
        	"The SNMP trap is generated every 24 hours to indicate 
		that the SAM board is still there."
   		::= { healthTrap 1 }

	maintenaceBistateTrap NOTIFICATION-TYPE
    		OBJECTS { biAlmID,biStatus,biDeviceName,
				biNumber,biName,biRspStr,biStatusTimeTag,
				biField1,biField2}
		STATUS  current
    		DESCRIPTION
        	"The SNMP trap is generated when a bistate point has change 
		of state and it is currently in maintenance state."
    		::= { bistateTrap 1  }

	notDefinedBistateTrap NOTIFICATION-TYPE
    		OBJECTS { biAlmID,biStatus,biDeviceName,
				biNumber,biName,biRspStr,biStatusTimeTag,
				biField1,biField2}
		STATUS  current
    		DESCRIPTION
        	"The SNMP trap is generated when a bistate point has change 
		of state and it is currently in not-defined state."
    		::= { bistateTrap 2  }

	infoBistateTrap NOTIFICATION-TYPE
    		OBJECTS { biAlmID,biStatus,biDeviceName,
				biNumber,biName,biRspStr,biStatusTimeTag,
				biField1,biField2}
		STATUS  current
    		DESCRIPTION
        	"The SNMP trap is generated when a bistate point has change 
		of state and it is currently in informational state."
    		::= { bistateTrap 3  }

	normalBistateTrap NOTIFICATION-TYPE
    		OBJECTS { biAlmID,biStatus,biDeviceName,
				biNumber,biName,biRspStr,biStatusTimeTag,
				biField1,biField2}
		STATUS  current
    		DESCRIPTION
        	"The SNMP trap is generated when a bistate
		point has change of state and it is currently in normal state."
    		::= { bistateTrap 4 }

	minor-aBistateTrap NOTIFICATION-TYPE
    		OBJECTS { biAlmID,biStatus,biDeviceName,
				biNumber,biName,biRspStr,biStatusTimeTag,
				biField1,biField2}
		STATUS  current
    		DESCRIPTION
        	"The SNMP trap is generated when a bistate
		point has change of state and it is currently in minor-a state."
    		::= { bistateTrap 5  }

	minor-bBistateTrap NOTIFICATION-TYPE
    		OBJECTS { biAlmID,biStatus,biDeviceName,
				biNumber,biName,biRspStr,biStatusTimeTag,
				biField1,biField2}
		STATUS  current
    		DESCRIPTION
        	"The SNMP trap is generated when a bistate
		point has change of state and it is currently in minor-b state."
    		::= { bistateTrap 6  }

	majorBistateTrap NOTIFICATION-TYPE
    		OBJECTS { biAlmID,biStatus,biDeviceName,
				biNumber,biName,biRspStr,biStatusTimeTag,
				biField1,biField2}
		STATUS  current
    		DESCRIPTION
        	"The SNMP trap is generated when a bistate
		point has change of state and it is currently in major state."
    		::= { bistateTrap 7  }

	criticalBistateTrap NOTIFICATION-TYPE
    		OBJECTS { biAlmID,biStatus,biDeviceName,
				biNumber,biName,biRspStr,biStatusTimeTag,
				biField1,biField2}
		STATUS  current
    		DESCRIPTION
        	"The SNMP trap is generated when a bistate point has change 
		of state and it is currently in critical state."
    		::= { bistateTrap 8  }

	maintenanceAnalogTrap NOTIFICATION-TYPE
		OBJECTS { anaAlmID,anaStatus,anaDeviceName,
				anaNumber,anaName,anaValue,anaThreshold,
			   anaRspStr,anaStatusTimeTag,anaField1,
				anaField2}
		STATUS   current
		DESCRIPTION
		"The SNMP trap is generated when an analog point
		value crosses its threshold and it is currently in
		maintenance mode."
		::= { analogTrap 1 } 

	notDefinedAnalogTrap NOTIFICATION-TYPE
		OBJECTS { anaAlmID,anaStatus,anaDeviceName,
				anaNumber,anaName,anaValue,anaThreshold,
			   anaRspStr,anaStatusTimeTag,anaField1,
				anaField2}
		STATUS   current
		DESCRIPTION
		"The SNMP trap is generated when an analog point
		value crosses its threshold and it is currently in
		not-defined state."
		::= { analogTrap 2 } 

	infoAnalogTrap NOTIFICATION-TYPE
		OBJECTS { anaAlmID,anaStatus,anaDeviceName,
				anaNumber,anaName,anaValue,anaThreshold,
			   anaRspStr,anaStatusTimeTag,anaField1,
				anaField2}
		STATUS   current
		DESCRIPTION
		"The SNMP trap is generated when an analog point
		value crosses its threshold and it is currently in 
		informational state."
		::= { analogTrap 3 } 

	normalAnalogTrap NOTIFICATION-TYPE
		OBJECTS { anaAlmID,anaStatus,anaDeviceName,
				anaNumber,anaName,anaValue,anaThreshold,
			   anaRspStr,anaStatusTimeTag,anaField1,
				anaField2}
		STATUS   current
		DESCRIPTION
		"The SNMP trap is generated when an analog point
		value crosses its threshold and it is currently in normal
		state."
		::= { analogTrap 4 } 

	minor-aAnalogTrap NOTIFICATION-TYPE
		OBJECTS { anaAlmID,anaStatus,anaDeviceName,
				anaNumber,anaName,anaValue,anaThreshold,
			   anaRspStr,anaStatusTimeTag,anaField1,
				anaField2}
		STATUS   current
		DESCRIPTION
		"The SNMP trap is generated when an analog point
		value crosses its threshold and it is currently in minor-a
		state."
		::= { analogTrap 5 } 

	minor-bAnalogTrap NOTIFICATION-TYPE
		OBJECTS { anaAlmID,anaStatus,anaDeviceName,
				anaNumber,anaName,anaValue,anaThreshold,
			   anaRspStr,anaStatusTimeTag,anaField1,
				anaField2}
		STATUS   current
		DESCRIPTION
		"The SNMP trap is generated when an analog point
		value crosses its threshold and it is currently in minor-b
		state."
		::= { analogTrap 6 } 

	majorAnalogTrap NOTIFICATION-TYPE
		OBJECTS { anaAlmID,anaStatus,anaDeviceName,
				anaNumber,anaName,anaValue,anaThreshold,
			   anaRspStr,anaStatusTimeTag,anaField1,
				anaField2}
		STATUS   current
		DESCRIPTION
		"The SNMP trap is generated when an analog point
		value crosses its threshold and it is currently in major
		state."
		::= { analogTrap 7 } 

	criticalAnalogTrap NOTIFICATION-TYPE
		OBJECTS { anaAlmID,anaStatus,anaDeviceName,
				anaNumber,anaName,anaValue,anaThreshold,
			   anaRspStr,anaStatusTimeTag,anaField1,
				anaField2}
		STATUS   current
		DESCRIPTION
		"The SNMP trap is generated when an analog point
		value crosses its threshold and it is currently in critical
		state."
		::= { analogTrap 8 } 

	maintenanceControlTrap NOTIFICATION-TYPE
    		OBJECTS {ctrlAlmID,ctrlStatus,ctrlDeviceName,
				ctrlNumber,ctrlRspStr,ctrlStatusTimeTag,
				ctrlField1,ctrlField2}
		STATUS  current
    		DESCRIPTION
        	"The SNMP trap is generated when a control point
		has a change of state and it is in maintenance state."
    		::= { controlTrap 1 }

	notDefinedControlTrap NOTIFICATION-TYPE
    		OBJECTS {ctrlAlmID,ctrlStatus,ctrlDeviceName,
				ctrlNumber,ctrlRspStr,ctrlStatusTimeTag,
				ctrlField1,ctrlField2}
		STATUS  current
    		DESCRIPTION
        	"The SNMP trap is generated when a control point
		has a change of state and it is currently in not-defined state."
    		::= { controlTrap 2 }

	infoControlTrap NOTIFICATION-TYPE
    		OBJECTS {ctrlAlmID,ctrlStatus,ctrlDeviceName,
				ctrlNumber,ctrlRspStr,ctrlStatusTimeTag,
				ctrlField1,ctrlField2}
		STATUS  current
    		DESCRIPTION
        	"The SNMP trap is generated when a control point
		has a change of state and it is currently in informational
		state."
    		::= { controlTrap 3 }

	normalControlTrap NOTIFICATION-TYPE
    		OBJECTS {ctrlAlmID,ctrlStatus,ctrlDeviceName,
				ctrlNumber,ctrlRspStr,ctrlStatusTimeTag,
				ctrlField1,ctrlField2}
		STATUS  current
    		DESCRIPTION
        	"The SNMP trap is generated when a control point
		has a change of state and it is currently in normal state."
    		::= { controlTrap 4 }

	minor-aControlTrap NOTIFICATION-TYPE
    		OBJECTS {ctrlAlmID,ctrlStatus,ctrlDeviceName,
				ctrlNumber,ctrlRspStr,ctrlStatusTimeTag,
				ctrlField1,ctrlField2}
		STATUS  current
    		DESCRIPTION
        	"The SNMP trap is generated when a control point
		has a change of state and it is currently in minor-a state."
    		::= { controlTrap 5 }

	minor-bControlTrap NOTIFICATION-TYPE
    		OBJECTS {ctrlAlmID,ctrlStatus,ctrlDeviceName,
				ctrlNumber,ctrlRspStr,ctrlStatusTimeTag,
				ctrlField1,ctrlField2}
		STATUS  current
    		DESCRIPTION
        	"The SNMP trap is generated when a control point
		has a change of state and it is currently in minor-b state."
    		::= { controlTrap 6 }

	majorControlTrap NOTIFICATION-TYPE
    		OBJECTS {ctrlAlmID,ctrlStatus,ctrlDeviceName,
				ctrlNumber,ctrlRspStr,ctrlStatusTimeTag,
				ctrlField1,ctrlField2}
		STATUS  current
    		DESCRIPTION
        	"The SNMP trap is generated when a control point
		has a change of state and it is currently in major state."
    		::= { controlTrap 7 }

	criticalControlTrap NOTIFICATION-TYPE
    		OBJECTS {ctrlAlmID,ctrlStatus,ctrlDeviceName,
				ctrlNumber,ctrlRspStr,ctrlStatusTimeTag,
				ctrlField1,ctrlField2}
		STATUS  current
    		DESCRIPTION
        	"The SNMP trap is generated when a control point
		has a change of state and it is currently in critical state."
    		::= { controlTrap 8 }

	testTraps NOTIFICATION-TYPE
		OBJECTS { aibadgerTest } 
		STATUS  current
		DESCRIPTION
       		"The SNMP trap is generated when the aibadgerTest
		String changes."
   		::= { testTrap 1 }

	normalDeviceResumeTrap NOTIFICATION-TYPE
    		OBJECTS { devName,devStatus,
				devStatusTimeTag ,devRspStr}
		STATUS  current
    		DESCRIPTION
        	"The SNMP trap is generated when the device status changes
		from fail state to resume state."
		::= { devTrap 1 }

	criticalDeviceFailTrap NOTIFICATION-TYPE
    		OBJECTS { devName,devStatus,
				devStatusTimeTag ,devRspStr}
		STATUS  current
    		DESCRIPTION
        	"The SNMP trap is generated when the communication with 
		the device fails."
		::= { devTrap 2 }


END
