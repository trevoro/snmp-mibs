-- Copyright 1995 General DataComm Inc., Inc. All Rights Reserved.
--
-- Reproduction of this document is authorized on condition that the
-- foregoing copyright notice is included. This General DataComm, GDC,
-- SNMP Management Information Base Specification embodies GDCs'
-- confidential and proprietary intellectual property. GDC retains all
-- title and ownership in the Specification, including any revisions.
--
-- It is GDCs intent to encourage the widespread use of this Specification
-- in connection with the management of GDC's products. GDC grants vendors,
-- end-users, and other interested parties a non-exclusive license to use
-- this Specification in connection with the management of GDC's products.
--
-- This Specification is supplied "AS IS," and GDC makes no warranty,
-- either expressed or implied, as to the use operation, condition, or
-- performance of the Specification.

-- Revision History
-- Version   Date	Name		Description
-- 1.00A     01-Sep-94  B. Bergquist	Initial Revision
-- 1.00B     12-Oct-94	J. Tokarski	Added gdcDsuChannelLoopbackConfig
--					   definition
-- 1.00C     16-Nov-94  J. Deptula      Modified GdcDsuChannelDiagEntry
--                                         to match gdcdsx1.mib format
--					Fixed compile bugs
--					Changed syntax of 
--						gdcDsuChannelRTSCTSControl
--						gdcDsuChannelEIAtestLeads
--						gdcDsuChannelInbandLoop
--					Renamed as gdcdsu.mib
--					Added gdcDsuChannelTransmitClockSource
--				              gdcDsuChannelFallbackClockSource
--					      gdcDsuChannelControlModeIdle
--					Redefined location in MIB tree to gdc.dsu
-- 1.00D     16-Jan-95  J. Deptula   	Redefined all Signal Status vars as read-only
-- 					Added some misc SNMPV1 CONFORMANCE statements
-- 1.00E     26-Jan-95  J. Deptula      Removed SNMPV1 CONFORMANCE statements
-- 1.00F     7-Feb-95   J. Deptula      Swapped enum sendProgPattern and send2047Pattern 
--					   in gdcDsuChannelDiagSendCode
--					Added enum rdlReset(5) to gdcDsuChannelLoopbackConfig
--					Added enum to gdcDsuChannelTestDuration
--					Changed a value of gdcDsuChannelTestExceptions from 3 to 4
-- 1.00G     14-Feb-95  J. Deptula	Redefined location in MIB tree to gdc.dsu.T1
-- 					Modified gdcDsuChannelTestStatus to match gdcdsx1.mib
-- 1.00H     30-Mar-95  J. Deptula      Moved location of t1 branch to { dsu 5 }
-- 1.00I     3-Apr-95   J. Deptula      Made gdcDsuChannelTestExceptions and
--					   gdcDsuChannelTestResults read only
--					Changed type of gdcDsuChannelDiagEntry to SCinstance
--					Clarified DESCRIPTION of gdcDsuChannelTestResults
-- 1.00J     6-Apr-95   T.Ecsedy	General Description Corrections
-- 1.00K     28-Jun-95  T. Ecsedy       Description correction for gdcDsuTestExceptions 
-- 1.00L     26-Jul-95  J. Deptula      Added 	send511PatternWithLL(7),	
--						send511PatternWithRDL(8),
--						send2047PatternWithLL(9),
--       					send2047PatternWithRDL(10)
--					enumerations to gdcDsuChannelDiagSendCode
--					Updated DESCRIPTION field for gdcDsuChannelDiagSendCode
GDC-DSU-MGMT-MIB DEFINITIONS ::= BEGIN

IMPORTS	enterprises			FROM RFC1155-SMI
	OBJECT-TYPE			FROM RFC-1212
	DisplayString			FROM RFC1213-MIB
	SCinstance			FROM GDCMACRO-MIB;

gdc 		OBJECT IDENTIFIER ::= { enterprises 498 }
dsu		OBJECT IDENTIFIER ::= { gdc 8 }
t1		OBJECT IDENTIFIER ::= { dsu 5 }

-- This MIB module uses the extended OBJECT-TYPE macro as
-- defined in RFC 1212.

-- The implementation of all groups is mandatory for all products that
-- provide DSU functionality.

-- Note:  All rows in all tables defined within this MIB module are
-- virtual.  They can neither be created or deleted by management
-- operations.

-- The Version Group. This group identifies the version information
-- for the MIB.
--
gdcDsuSystemMIBversion OBJECT-TYPE
    SYNTAX DisplayString (SIZE (5))
    ACCESS read-only
    STATUS mandatory
    DESCRIPTION
    	"Identifies the version of the MIB. The format of the version
    	is x.yzT, where 'x' identifies the major revision number, 'y'
    	identifies the minor revision number, 'z' identifies the
    	typographical revision, and T identifies the test revision.
    	Acceptable values for the individual revision components are
    	as follows:

    		x: 1 - 9
    		y: 0 - 9
    		z: 0 - 9
    		T: A - Z

    	Upon formal release, no designation for the test revision will
    	be present."
    ::= { t1 5 }

-- The GDC DSU Group.  This group contains objects that support the
-- specific management requirements for products that support a GDC
-- DSU functionality.  The group contains tables for DSU DS0 channel
-- allocation management, DSU channel configuration management, DSU
-- channel signal state monitoring, and DSU channel diagnostics.

-- The GDC DSU DS0 Allocation Scheme table

gdcDsuDS0AllocationSchemeTable OBJECT-TYPE
    SYNTAX SEQUENCE OF GdcDsuDS0AllocationSchemeEntry
    ACCESS not-accessible
    STATUS mandatory
    DESCRIPTION 
    	"The GDC DSU DS0 Allocation Scheme table.  Information in
        an entry of this table defines the DS0 allocation scheme 
	(alternate or consecutive) of the represented DSU."
    ::= { t1 1 }

gdcDsuDS0AllocationSchemeEntry OBJECT-TYPE
    SYNTAX GdcDsuDS0AllocationSchemeEntry
    ACCESS not-accessible
    STATUS mandatory
    DESCRIPTION
    	"The GDC DSU DS0 Allocation scheme table entry."
    INDEX { gdcDsuDS0AllocationIndex }
    ::= { gdcDsuDS0AllocationSchemeTable 1 }

GdcDsuDS0AllocationSchemeEntry ::= 
    SEQUENCE {
    	gdcDsuDS0AllocationIndex SCinstance,
        gdcDsuDS0AllocationScheme INTEGER
    }   

gdcDsuDS0AllocationIndex OBJECT-TYPE
    SYNTAX SCinstance
    ACCESS read-only
    STATUS mandatory
    DESCRIPTION
    	"The index value which uniquely identifies the DSU  to
    	which this entry is applicable.  This has the form of a
    	SCinstance which defines the slot, line, drop, and
    	sub-identifier.

	The sub-identifier for this SC instance is the DSU."
    ::= { gdcDsuDS0AllocationSchemeEntry 1 }

gdcDsuDS0AllocationScheme OBJECT-TYPE
    SYNTAX INTEGER {
    	other(1),			-- another allocation scheme
    					-- defined elsewhere
    	consecutive(2),			-- consecutive DS0's
    					-- allocation scheme
    	alternate(3)			-- alternate DS0's allocation scheme
    }
    ACCESS read-write
    STATUS mandatory
    DESCRIPTION
	"Identifies the DSU DS0 allocation scheme. The value of
    	other(1) indicates that an allocation scheme is used
    	which is defined elsewhere. The value consecutive(2) indicates that
    	bundles of DS0s are allocated to channels consecutively from the
	starting DS0. The value of alternate(3) indicates that bundles of DS0s
        are allocated to channels alternatly, or every other DS0 from
        the starting DS0. The unused DS0s are forced to marks.

	The value of other(1) can never be set by management operation.

    	Note that DS0 bundles cannot be split across frames (wrap around
	from the highest numbered DS0 of one frame to DS0 1 of the next
	frame. For example, on a T1 frame using consecutive DS0 allocation,
	a channel configuration of starting DS0 = 20 and number of
	DS0s = 5 is an illegal channel configuration because the DS0 bundle
	wraps from DS0 #24 of 1 frame to DS0 #1 of the next."
    ::= { gdcDsuDS0AllocationSchemeEntry 2 }

-- The GDC DSU Channel Configuration table

gdcDsuChannelConfigTable OBJECT-TYPE
    SYNTAX SEQUENCE OF GdcDsuChannelConfigEntry
    ACCESS not-accessible
    STATUS mandatory
    DESCRIPTION
    	"The GDC DSU Channel Configuration table.  Information in the
    	entries of this table define the configuration of DSU
    	channels.  There are entries in this table for each channel of
    	the associated DSU."
    ::= { t1 2 }

gdcDsuChannelConfigEntry OBJECT-TYPE
    SYNTAX GdcDsuChannelConfigEntry
    ACCESS not-accessible
    STATUS mandatory
    DESCRIPTION
    	"The GDC DSU Channel Configuration table entry."
    INDEX { gdcDsuChannelConfigIndex }
    ::= { gdcDsuChannelConfigTable 1 }

GdcDsuChannelConfigEntry ::= 
    SEQUENCE {
        gdcDsuChannelConfigIndex SCinstance,
        gdcDsuChannelBaseRate INTEGER,
        gdcDsuChannelStartingDS0 INTEGER,
        gdcDsuChannelNumberOfDS0s INTEGER,
        gdcDsuChannelSplitTiming INTEGER,
        gdcDsuChannelChannelType INTEGER,
        gdcDsuChannelTransmitClockInvert INTEGER,
        gdcDsuChannelReceiveClockInvert INTEGER,
        gdcDsuChannelTransmitDataInvert INTEGER,
        gdcDsuChannelReceiveDataInvert INTEGER,
        gdcDsuChannelLocalDCD INTEGER,
        gdcDsuChannelLocalDSR INTEGER,
        gdcDsuChannelReceiveControl INTEGER,
        gdcDsuChannelTransmitControl INTEGER,
        gdcDsuChannelRTSCTScontrol INTEGER,
        gdcDsuChannelEIAtestLeads INTEGER,
        gdcDsuChannelDccMode INTEGER,
        gdcDsuChannelInbandLoop INTEGER,
        gdcDsuChannelInbandLoopCode INTEGER,
        gdcDsuChannelInbandLoopdown INTEGER,
	gdcDsuChannelTransmitClockSource INTEGER,
	gdcDsuChannelFallbackClockSource INTEGER,
	gdcDsuChannelControlModeIdle INTEGER
   }

gdcDsuChannelConfigIndex OBJECT-TYPE
    SYNTAX SCinstance
    ACCESS read-only
    STATUS mandatory
    DESCRIPTION
    	"The index value which uniquely identifies the channel to
    	which this entry is applicable.  This has the form of a
    	SCinstance which defines the slot, line, drop, and
    	sub-identifier.
	
	The sub-indentifier for this SCinstance is the channel."
    ::= { gdcDsuChannelConfigEntry 1 }

gdcDsuChannelBaseRate OBJECT-TYPE
    SYNTAX INTEGER {
    	nx56k(1),			-- N X 56K rate
    	nx64k(2)			-- N X 64K rate
    }
    ACCESS read-write
    STATUS mandatory
    DESCRIPTION
    	"Indicates the DS0 base rate: either 56K or 64K bits per second.
	This is used in conjunction with the number of DS0s to determine
	the bandwidth of the channel.
	
	Note that base rate of 64K defines the DS0 as clear channel in
	which all 8 bits of the DS0 are used. A base rate of 56K defines
	the DS0 as non-clear in which bits 1-7 are used for channel data
	and the 8th bit is either unused and forced to marks or used to
	pass signaling information."
    ::= { gdcDsuChannelConfigEntry 2 }

gdcDsuChannelStartingDS0 OBJECT-TYPE
    SYNTAX INTEGER (0..24)
    ACCESS read-write
    STATUS mandatory
    DESCRIPTION
    	"Indicates the starting DS0 number for the bundle of DS0s used for
	the channel. DS0 bundles are allocated starting at the DS0 defined by 
	this integer.

	When this integer is set to 0, the channel is disabled and no DS0s
	are allocated to the channel. 

    	Note that DS0 bundles cannot be split across frames (wrap around
	from the highest numbered DS0 of one frame to DS0 1 of the next
	frame. For example, on a T1 frame using consecutive DS0 allocation,
	a channel configuration of starting DS0 = 20 and number of
	DS0s = 5 is an illegal channel configuration because the DS0 bundle
	wraps from DS0 #24 of 1 frame to DS0 #1 of the next."
    ::= { gdcDsuChannelConfigEntry 3 }

gdcDsuChannelNumberOfDS0s OBJECT-TYPE
    SYNTAX INTEGER (1..24)
    ACCESS read-write
    STATUS mandatory
    DESCRIPTION
    	"Indicates the number of DS0s for the bundle allocated to the
    	channel. The number of DS0s, in conjunction with the DS0 base
    	rate, also determines the bandwidth of the channel.
  
    	Note that DS0 bundles cannot be split across frames (wrap around
	from the highest numbered DS0 of one frame to DS0 1 of the next
	frame. For example, on a T1 frame using consecutive DS0 allocation,
	a channel configuration of starting DS0 = 20 and number of
	DS0s = 5 is an illegal channel configuration because the DS0 bundle
	wraps from DS0 #24 of 1 frame to DS0 #1 of the next."
   ::= { gdcDsuChannelConfigEntry 4 }
    
gdcDsuChannelSplitTiming OBJECT-TYPE
    SYNTAX INTEGER {
    	disabled(1),			-- split timing disabled
    	enabled(2)			-- split timing enabled
    }
    ACCESS read-write
    STATUS mandatory
    DESCRIPTION
    	"Indicates whether or not to use split timing. The value disabled(1)
	indicates that channel's transmit timing is provided by the DSU.
	The value enabled(2) indicates that the channel's transmit timing
	is provided by the customer business equipment (ext Tx Clk).
 
	Split timing refers to the activation of elastic storage to allow
	the channel interface to receive data using the customer business
	equipment's timing source (ext Tx Clk) and transmit that same data
	to the network using the networks timing source."
    ::= { gdcDsuChannelConfigEntry 5 }

gdcDsuChannelChannelType OBJECT-TYPE
    SYNTAX INTEGER {
    	other(1),			-- another interface defined elsewhere
    	none(2),			-- no channel interface
    	v35(3),				-- V.35 interface
    	eia530(4),			-- 530 EIA interface
    	dra(5)				-- Data Rate Adapter
    }
    ACCESS read-only
    STATUS mandatory
    DESCRIPTION
    	"The channel interface type.  The value other(1) indicates
        the channel interface is a type defined elsewhere. The value
       	none(2) indicates that there is no channel interface for the
	index. The value v35(3) indicates the channel interface is
	standard V.35 and the value eia530(4) indicates the channel
	interface is standard EIA 530.  The value dra(5) indicates the
	channel is is standard RS232 and is using the data rate adapter
	(DRA) to run at subrate speeds (below 56K bits per second)."
    ::= { gdcDsuChannelConfigEntry 6 }
    	
gdcDsuChannelTransmitClockInvert OBJECT-TYPE
    SYNTAX INTEGER {
    	disabled(1),			-- transmit clock invert disabled
    	enabled(2)			-- transmit clock invert enabled
    }
    ACCESS read-write
    STATUS mandatory
    DESCRIPTION
    	"Transmit clock invert.  The value disabled(1) indicates that the
	channel's transmit clock is normal, or not inverted, while the value
	enabled(2) indicates that the channel's transmit clock is inverted."
    ::= { gdcDsuChannelConfigEntry 7 }

gdcDsuChannelReceiveClockInvert OBJECT-TYPE
    SYNTAX INTEGER {
    	disabled(1),			-- receive clock invert disabled
    	enabled(2)			-- receive clock invert enabled
    }
    ACCESS read-write
    STATUS mandatory
    DESCRIPTION
    	"Receive clock invert.  The value disabled(1) indicates that the
	channel's receive clock is normal, or not inverted, while the value
	enabled(2) indicates that the channel's receive clock is inverted."
   ::= { gdcDsuChannelConfigEntry 8 }

gdcDsuChannelTransmitDataInvert OBJECT-TYPE
    SYNTAX INTEGER {
    	disabled(1),			-- transmit data invert disabled
    	enabled(2)			-- transmit clock invert enabled
    }
    ACCESS read-write
    STATUS mandatory
    DESCRIPTION
    	"Invert the transmit data. The value disabled(1) indicates that
	the channel's transmit data is normal, or not inverted, while the
	value enabled(2) indicates that the channel's transmit data is inverted."
    ::= { gdcDsuChannelConfigEntry 9 }

gdcDsuChannelReceiveDataInvert OBJECT-TYPE
    SYNTAX INTEGER {
    	disabled(1),			-- receive data invert disabled
    	enabled(2)			-- receive clock invert enabled
    }
    ACCESS read-write
    STATUS mandatory
    DESCRIPTION
    	"Invert the receive data. The value disabled(1) indicates that
	the channel's receive data is normal, or not inverted, while the
	value enabled(2) indicates that the channel's receive data is inverted."
   ::= { gdcDsuChannelConfigEntry 10 }

gdcDsuChannelLocalDCD OBJECT-TYPE
    SYNTAX INTEGER {
    	followsSignal(1),		-- local DCD follows inband CMI
    	forcedOn(2)			-- local DCD forced on
    }
    ACCESS read-write
    STATUS mandatory
    DESCRIPTION
    	"Controls the operation of Data Carrier Detect (DCD) signal.
    	The value followsSignal(1) indicates that the channel's DCD follows
	the inband control mode idle (CMI). The value forcedOn(2) indicates
	that DCD is forced on."
    ::= { gdcDsuChannelConfigEntry 11 }

gdcDsuChannelLocalDSR OBJECT-TYPE
    SYNTAX INTEGER {
    	followsSignal(1),		-- local DSR follows inband CMI
    	forcedOn(2)			-- local DSR forced on
    }
    ACCESS read-write
    STATUS mandatory
    DESCRIPTION
     	"Controls the operation of the Data Set Ready (DSR) signal.
    	The value followsSignal(1) indicates that the channel's DSR follows
	the inband control mode idle (CMI). The value forcedOn(2) indicates
	that DSR is forced on."
    ::= { gdcDsuChannelConfigEntry 12 }

gdcDsuChannelReceiveControl OBJECT-TYPE
    SYNTAX INTEGER {
    	dcd(1),				-- receive control is DCD
    	dsr(2)				-- receive control is DSR
    }
    ACCESS read-write
    STATUS mandatory
    DESCRIPTION
    	"Identifies which signal is used for receive flow control. The
    	two values are Data Carrier Detect, dcd(1), and Data Set Ready, dsr(2)."
    ::= { gdcDsuChannelConfigEntry 13 }

gdcDsuChannelTransmitControl OBJECT-TYPE
    SYNTAX INTEGER {
    	rts(1),				-- transmit control is RTS
    	dtr(2)				-- transmit control is DTR
    }
    ACCESS read-write
    STATUS mandatory
    DESCRIPTION
    	"Identifies which signal is used for transmit flow control. The
    	two values are Request To Send, rts(1), and Data Terminal Ready, dtr(2)."
    ::= { gdcDsuChannelConfigEntry 14 }

gdcDsuChannelRTSCTScontrol OBJECT-TYPE
    SYNTAX INTEGER {
	other(1),			-- another RTS/CTS control
    	ctsDelay10ms(2),		-- CTS delay 10 ms
    	ctsOn(3),			-- CTS forced on
    	ctsDelayStandard(4)		-- CTS standard delay
    }
    ACCESS read-write
    STATUS mandatory
    DESCRIPTION
    	"Controls the function of the channel's Request To Send (RTS)
	 and Clear To Send signals used for flow control. 

    	The value of ctsOn(2) indicates that CTS is forced on at all
    	times.  The value of ctsDelay10ms(3) indicates that CTS is to
    	respond to RTS after a 10ms delay.  The value of
    	ctsDelayStandard(4) indicates that CTS is to respond to RTS
    	after the standard delay of 40 bits times.

	The value other(1) identifies another RTS/CTS control.  This
	value can never be set by management request.

	For 56Kbps applications using CMI flow control, this object
	must be set for ctsDelayStandard(4)."
    ::= { gdcDsuChannelConfigEntry 15 }

gdcDsuChannelEIAtestLeads OBJECT-TYPE
    SYNTAX INTEGER {
    	disabled(1),			-- EIA test leads disabled
    	enabled(2)			-- EIA test leads enabled
    }
    ACCESS read-write
    STATUS mandatory
    DESCRIPTION
    	"Controls the channel's EIA test leads. The EIA test leads allow
	customer business equipment to initiate diagnostic tests through
	the assertion of the EIA test leads RDL, LL, and ST.

	When this object is enabled(1), then the assertion of these leads
	is recognized and acted upon by the DSU.  When this object is
    	disabled(2), then the assertion of these leads is ignored by the DSU."
    ::= { gdcDsuChannelConfigEntry 16 }

gdcDsuChannelDccMode OBJECT-TYPE
    SYNTAX INTEGER {
    	none(1),
    	normal(2),
    	special(3)
    }
    ACCESS read-write
    STATUS mandatory
    DESCRIPTION
    	"The type of inband Diagnostics Communication Channel (DCC) in use.
	The value none(1) indicates no DCC is being used for the given channel.

    	The value normal(2) indicates the channel's inband DCC is used. For Nx56k
	applications using B8ZS line coding, normal(2) indicates that the DCC
    	embedded in the secondary channel (bit 8) of the channel's DS0 bundle. For
	Nx56k applications using AMI line coding or for Nx65K applications, normal(2) 
	indicates that the DCC is imbedded in the secondary channel (bit 8) of and
	additional DS0 appended to the channel's DS0 bundle.

    	The value special(3) indicates the channel's inband DCC is used. For Nx56k
	applications using B8ZS line coding, special(2) indicates that the DCC is
	imbedded in the secondary channel (bit 8) of and additional DS0 appended to
	the channel's DS0 bundle. For Nx56k applications using AMI line coding,
	normal(2) indicates that the DCC is embedded in the secondary channel (bit 8)
	of the channel's DS0 bundle.

	The value special(3) is not valid for Nx64K applications."
    ::= { gdcDsuChannelConfigEntry 17 }

gdcDsuChannelInbandLoop OBJECT-TYPE
    SYNTAX INTEGER {
    	disable(1),			-- disable detection of in-band
    					-- loop code
    	enabled(2)			-- enable detection of in-band loop code
    }
    ACCESS read-write
    STATUS mandatory
    DESCRIPTION
    	"In-band loopcode enable/disable. The value disabled(1) indicates
	the channel does not enter an RDL loop when an inband RDL code is detected.
	The value enable(2) indicates the channel does enter an RDL loop when
	an inband RDL code is detected."
    ::= { gdcDsuChannelConfigEntry 18 }

gdcDsuChannelInbandLoopCode OBJECT-TYPE
    SYNTAX INTEGER {
    	other(1),			-- another code
    	pn127(2),			-- PN127 random code
    	gdcProprietary(3)		-- GDC proprietary code
    }
    ACCESS read-write
    STATUS mandatory
    DESCRIPTION
    	"In-band RDL code to send and/or receive by the channel. The
	value pn127(2) indicates that the in-band code sent/received is in
	accordance with CCITT V.54 PN-127 scrambled codes. The value of
	gdcProprietary(3) indicates that the in-band code sent/received
	is the GDC defined code.

    	The value other(1) identifies another loopcode defined
    	elsewhere.  This value can never be set by management operation."
    ::= { gdcDsuChannelConfigEntry 19 }

gdcDsuChannelInbandLoopdown OBJECT-TYPE
    SYNTAX INTEGER			-- 0, 1 - 2^31 seconds
    ACCESS read-write
    STATUS mandatory
    DESCRIPTION
    	"The time limit in seconds before terminating a channel's RDL.
    	The value 0 indicates that the loopdown time is disabled and
	the loopback will only terminate by the in-band loopdown code.
	All other values indicate the time in seconds before terminating
	the RDL in the event the loopdown code is never received.

    	Note that certain products may only support discrete time
    	lengths. Setting the value to any unsupported time length
    	results in a badValue error."
    ::= { gdcDsuChannelConfigEntry 20 }

gdcDsuChannelTransmitClockSource OBJECT-TYPE
    SYNTAX INTEGER {
    	disabled(1),			-- Do not use this channels external
					--  clock for network transmit timing
    	enabled(2)			-- Use this channel's external clock 
     					--  for network transmit timing
	}			
    ACCESS read-write
    STATUS mandatory
    DESCRIPTION
    	"This object operates in conjunction with gdcDsx1TransmitClockSource 
	in gdcdsx1.mib. If gdcDsx1TransmitClockSource is channel(4),
	then this object defines whether or not the channel's customer
	business equipment is providing timing with ext Tx Clk to the
	network's transmit interface. 
	
	The value disabled(1) indicates the channel's customer business
	equipment is not providing timing for the transmit network interface.

	The value enabled(1) indicates the channel's customer business 
	equipment is providing timing for the transmit network interface."
    ::= { gdcDsuChannelConfigEntry 21 }

gdcDsuChannelFallbackClockSource OBJECT-TYPE
    SYNTAX INTEGER {
    	other(1),			-- another clock source
    	channel(2)			-- use channel clock 
     }	
    ACCESS read-write
    STATUS mandatory
    DESCRIPTION
    	"This object operates in conjunction with gdcDsx1FallbackClockSource 
	in gdcdsx1.mib. If gdcDsx1FallbackClockSource is channel(4),
	then this object defines whether or not the channel's customer
	business equipment is providing fallback timing with ext Tx Clk to the
	network's transmit interface. 
	
	The value disabled(1) indicates the channel's customer business
	equipment is not providing fallback timing for the transmit
	network interface.

	The value enabled(1) indicates the channel's customer business 
	equipment is providing fallnback timing for the transmit
	network interface."
   ::= { gdcDsuChannelConfigEntry 22 }

gdcDsuChannelControlModeIdle OBJECT-TYPE
    SYNTAX INTEGER {
    	disabled(1),			-- CMI disabled
    	enabled(2)			-- CMI enabled
    }
    ACCESS read-write
    STATUS mandatory
    DESCRIPTION
    	"Control Mode Idle (CMI) enable/disable. When the channel 
	application is Nx56k and RTS/CTS delay is standard, then
	this object defines the the use of CMI to provide flow control.

	The value disabled(1) indicates the channel using CMI to pass
	control flow information.

	The value enabled(w) indicates the channel is using the DDS
	secondary channel CMI format to pass flow control information."
    ::= { gdcDsuChannelConfigEntry 23 }

-- The GDC DSU Channel Signal Status table

gdcDsuChannelSignalStatusTable OBJECT-TYPE
    SYNTAX SEQUENCE OF GdcDsuChannelSignalStatusEntry
    ACCESS not-accessible
    STATUS mandatory
    DESCRIPTION
    	"The GDC DSU Channel Signal Status table. Information in the
    	entries of this table define the status of DSU channel
	interface leads.  There are entries in this table for each
	channel of the associated DSU."
    ::= { t1 3 }

gdcDsuChannelSignalStatusEntry OBJECT-TYPE
    SYNTAX GdcDsuChannelSignalStatusEntry
    ACCESS not-accessible
    STATUS mandatory
    DESCRIPTION
    	"The GDC DSU Channel Signal Status table entry."
    INDEX { gdcDsuChannelSignalStatusIndex } 
    ::= { gdcDsuChannelSignalStatusTable 1 }

GdcDsuChannelSignalStatusEntry ::= 
    SEQUENCE {
        gdcDsuChannelSignalStatusIndex SCinstance,
        gdcDsuChannelCTSstatus INTEGER,
        gdcDsuChannelRTSstatus INTEGER,
        gdcDsuChannelDTRstatus INTEGER,
        gdcDsuChannelDSRstatus INTEGER,
        gdcDsuChannelDCDstatus INTEGER,
        gdcDsuChannelRXCstatus INTEGER,
        gdcDsuChannelTXCstatus INTEGER,
        gdcDsuChannelRXDstatus INTEGER,
        gdcDsuChannelTXDstatus INTEGER
    }

gdcDsuChannelSignalStatusIndex OBJECT-TYPE
    SYNTAX SCinstance
    ACCESS read-only
    STATUS mandatory
    DESCRIPTION
    	"The index value which uniquely identifies the channel to
    	which this entry is applicable.  This has the form of a
    	SCinstance which defines the slot, line, drop, and
    	sub-identifier.
	
	The sub-indentifier for this SCinstance is the channel."
    ::= { gdcDsuChannelSignalStatusEntry 1 }

gdcDsuChannelCTSstatus OBJECT-TYPE
    SYNTAX INTEGER {
    	off(1),				-- CTS is off
    	on(2),				-- CTS is on
    	transitions(3)			-- CTS is transitioning
    }
    ACCESS read-only
    STATUS mandatory
    DESCRIPTION
    	"The state of the channel's Clear To Send (CTS) signal.
	The value transitions(3) indicates that the signal is
	alternating between the states off(1) and on(2)."
    ::= { gdcDsuChannelSignalStatusEntry 2 }

gdcDsuChannelRTSstatus OBJECT-TYPE
    SYNTAX INTEGER {
    	off(1),				-- RTS is off
    	on(2),				-- RTS is on
    	transitions(3)			-- RTS is transitioning
    }
    ACCESS read-only
    STATUS mandatory
    DESCRIPTION
    	"The state of the channel's Request To Send (RTS) signal.
	The value transitions(3) indicates that the signal is
	alternating between the states off(1) and on(2)."
    ::= { gdcDsuChannelSignalStatusEntry 3 }

gdcDsuChannelDTRstatus OBJECT-TYPE
    SYNTAX INTEGER {
    	off(1),				-- DTR is off
    	on(2)				-- DTR is on
    }
    ACCESS read-only
    STATUS mandatory
    DESCRIPTION
    	"The state of the channel's Data Terminal Ready (DTR)
	signal."
    ::= { gdcDsuChannelSignalStatusEntry 4 }

gdcDsuChannelDSRstatus OBJECT-TYPE
    SYNTAX INTEGER {
    	off(1),				-- DSR is off
    	on(2)				-- DSR is on
    }
    ACCESS read-only
    STATUS mandatory
    DESCRIPTION
    	"The state of the channel's Data Set Ready (DSR) signal."
    ::= { gdcDsuChannelSignalStatusEntry 5 }

gdcDsuChannelDCDstatus OBJECT-TYPE
    SYNTAX INTEGER {
    	off(1),				-- DCD is off
    	on(2),				-- DCD is on
    	transitions(3)			-- DCD is transitioning
    }
    ACCESS read-only
    STATUS mandatory
    DESCRIPTION
    	"The state of the channel's Data Carrier Detect (DCD)
	signal. The value transitions(3) indicates that the signal
	is alternating between the states off(1) and on(2)."
    ::= { gdcDsuChannelSignalStatusEntry 6 }

gdcDsuChannelRXCstatus OBJECT-TYPE
    SYNTAX INTEGER {
    	off(1),				-- RXC is off
    	transitions(2)			-- RXC is transitioning
    }
    ACCESS read-only
    STATUS mandatory
    DESCRIPTION
    	"The state of the channel's receive clock (RXC) signal.
	The value transitions(2) indicates that the signal
	is alternating between states off(1) and on(2)."
    ::= { gdcDsuChannelSignalStatusEntry 7 }

gdcDsuChannelTXCstatus OBJECT-TYPE
    SYNTAX INTEGER {
    	off(1),				-- TXC is off
    	transitions(2)			-- TXC is transitioning
    }
    ACCESS read-only
    STATUS mandatory
    DESCRIPTION
    	"The state of the channel's Transmit Clock (TXC) signal.
	The value transitions(2) indicates that the signal is
	alternating between states off(1) and on(2)."
    ::= { gdcDsuChannelSignalStatusEntry 8 }

gdcDsuChannelRXDstatus OBJECT-TYPE
    SYNTAX INTEGER {
    	off(1),				-- RXD is off
    	transitions(2)			-- RXD is transitioning
    }
    ACCESS read-only
    STATUS mandatory
    DESCRIPTION
    	"The state of the channel's Receive Data (RXD) signal.
	The value transitions(2) indicates that the signal is
	alternating between states off(1) and on(2)."
    ::= { gdcDsuChannelSignalStatusEntry 9 }

gdcDsuChannelTXDstatus OBJECT-TYPE
    SYNTAX INTEGER {
    	off(1),				-- TXD is off
    	transitions(2)			-- TXD is transitioning
    }
    ACCESS read-only
    STATUS mandatory
    DESCRIPTION
    	"The state of the channel's Transmit Data (TXD) signal.
	The value transitions(2) indicates that the signal is is
	alternating between states off(1) and on(2)."
    ::= { gdcDsuChannelSignalStatusEntry 10 }

-- The GDC DSU Channel Diagnostics table

gdcDsuChannelDiagTable OBJECT-TYPE
    SYNTAX SEQUENCE OF GdcDsuChannelDiagEntry
    ACCESS not-accessible
    STATUS mandatory
    DESCRIPTION
    	"The GDC DSU Channel Diagnostics table.  The information in
	this table support diagnostic testing, both active
    	testing via patterns, and passive testing via loopback on the
    	DSU channels. There are entries in this table for each
	channel of the associated DSU."
    ::= { t1 4 }

gdcDsuChannelDiagEntry OBJECT-TYPE
    SYNTAX GdcDsuChannelDiagEntry
    ACCESS not-accessible
    STATUS mandatory
    DESCRIPTION
    	"The GDC DSU Channel Diagnostics entry."
    INDEX { gdcDsuChannelDiagIndex }
    ::= { gdcDsuChannelDiagTable 1 }


GdcDsuChannelDiagEntry ::= 
    SEQUENCE {
        gdcDsuChannelDiagIndex SCinstance,
        gdcDsuChannelDiagSendCode INTEGER,
        gdcDsuChannelDiagProgPattern INTEGER,
        gdcDsuChannelLoopbackConfig INTEGER,
        gdcDsuChannelTestDuration INTEGER,
        gdcDsuChannelDiagTimingSource INTEGER,
        gdcDsuChannelTestStatus INTEGER,
        gdcDsuChannelTestExceptions INTEGER,
        gdcDsuChannelTestResults INTEGER
    }

gdcDsuChannelDiagIndex OBJECT-TYPE
    SYNTAX SCinstance
    ACCESS read-only
    STATUS mandatory
    DESCRIPTION
    	"The index value which uniquely identifies the channel to
    	which this entry is applicable.  This has the form of a SC
    	instance which defines the slot, line, drop, and
    	sub-identifier, which in this case is the channel."
    ::= { gdcDsuChannelDiagEntry 1 }

gdcDsuChannelDiagSendCode OBJECT-TYPE
    SYNTAX INTEGER {
	sendNoCode(1),			-- sending normal data
    	sendQRSpattern(2),		-- sending a Quasi-Random
    					--   Signal (QRS) test pattern only
    	send511Pattern(3),		-- sending a 511 bit fixed
    					--   test pattern only
    	send3in24Pattern(4),		-- sending a fixed test
    					--   pattern of 3 bits set in 24 only
    	sendProgPattern(5),		-- sending user programmable
    					--   bit pattern only
    	send2047Pattern(6),		-- sending 2047 bit pattern
					--   only
	send511PatternWithLL(7),	-- sending 511 bit pattern
					--   with local loop
	send511PatternWithRDL(8),	-- sending 511 bit pattern
					--   with remote digital loop
	send2047PatternWithLL(9),	-- sending 2047 bit pattern
					--   with local loop
        send2047PatternWithRDL(10)	-- sending 2047 bit pattern
					--   with remote digital loop
   }
    ACCESS read-write
    STATUS mandatory
    DESCRIPTION
    	"Initiates and terminates  self test pattern generation and detection
	(active diagnostic tests) on the DSU channel. When this object
	is set to other than sendNoCode(1), an active diagnostic test
	is initiated, using the test pattern supplied . When this
	object is set to sendNoCode(1), the active diagnostic test is
	terminated.

    	When read, value sendNoCode(1) indicates there are no active diagnostic
	tests currently running on the channel. The value sendQRSpattern(2)
	indicates that a QRS test is running on the channel. The value
	send511Pattern(3) indicates that a 511 test is running on the channel.
	The value send3in24Pattern(4) indicates that a 3:24 test is running
	on the channel. The value send2047Pattern(5) indicates that a 2047
	test is running on the channel.

	The value sendProgPattern(6) indicates that a user programmable
	pattern test is running on the channel. The value sendProgPattern(6)
	and the object gdcDsuChannelProgPattern work together.
	GdcDsuChannelProgPattern defines the 16 bit user programmable pattern
	for the programmable pattern test.

	The values send511PatternWithLL(7), send511PatternWithRDL(8),
	send2047PatternWithLL(9), send2047PatternWithRDL(10) indicate that 
	the given pattern test is running in conjunction with a local loop (LL)
	or remote digital loop (RDL). gdcDsuChannelLoopbackConfig is updated
        to indicate this as well.  When one of these tests are running, and this
	variable is set to sendNoCode(1), both the pattern and the loopback 
	are terminated.  However, if gdcDsuChannelLoopbackConfig is set to noLoop(1),
	only the loopback portion is terminated.  

	This object, gdcDsuChannelTestResults, and gdcDsuChannelTestStatus
	work together as follows:

	When this object is set to initiate an active diagnostic test,
	gdcDsuTestResults is initialized to 0 and gdcDsuChannelTestStatus
	is initialized to testRunning(1).  When the test is terminated,
	the value of gdcDsuChannelTestStatus reflects testComplete(3).
	gdcDsuChannelTestResults contains the count of bit errors detected
	during the test. "
    ::= { gdcDsuChannelDiagEntry 2 }

gdcDsuChannelDiagProgPattern OBJECT-TYPE
    SYNTAX INTEGER (0..'ffff'h)
    ACCESS read-write
    STATUS mandatory
    DESCRIPTION
    	"The 16 bit user programmable test pattern.  This object works
	with gdcDsuChannelSendCode. When gdcDsuChannelSendCodeis set to
	sendProgPattern(6), this object is used as the 16 bit 
	user programmable test pattern."
    ::= { gdcDsuChannelDiagEntry 3 }

gdcDsuChannelLoopbackConfig OBJECT-TYPE
    SYNTAX INTEGER {
    	noLoop(1),			-- no loop
    	localLoop(2),			-- channel local loop
    	digitalLoop(3),			-- channel digital loop
	rdl(4),				-- remote digital loop
	rdlReset(5),			-- rdl reset
    	otherLoop(6)			-- other loop
    }
    ACCESS read-write
    STATUS mandatory
    DESCRIPTION
    	"The loopback configuration for the DSU channel to be used
	for both active and passive diagnostic tests."
    ::= { gdcDsuChannelDiagEntry 4 }    	 

gdcDsuChannelTestDuration OBJECT-TYPE
    SYNTAX INTEGER	{
	 noLimit(1),
	 testTime1Min(2),
	 testTime2Mins(3),
	 testTime3Mins(4),
	 testTime4Mins(5),
	 testTime5Mins(6),
	 testTime6Mins(7),
	 testTime7Mins(8),
	 testTime8Mins(9),
	 testTime9Mins(10),
	 testTime10Mins(11),
	 testTime15Mins(12),
	 testTime20Mins(13),
	 testTime25Mins(14),
	 testTime30Mins(15),
	 testTime30Secs(16)
		     }	
    ACCESS read-write
    STATUS mandatory
    DESCRIPTION
    	"The length of the diagnostic test, in time. The value 0 signifies
    	that the test should run indefinitely until explicitly
    	terminated." 
    ::= { gdcDsuChannelDiagEntry 5 }

gdcDsuChannelDiagTimingSource OBJECT-TYPE
    SYNTAX INTEGER {
    	currentSource(1),		-- use the current timing source
    	loopTiming(2),			-- loop timing clock source
    	localTiming(3),			-- local timing clock source
    	station(4),			-- station timing source
    	composite(5)			-- composite timing source
    }
    ACCESS read-write
    STATUS mandatory
    DESCRIPTION
    	"The timing source to be used for diagnostic tests.

	For tests that do not disrupt the transmit timing source as
	defined in gdcDsx1TransmitClockSource the value currentSource(1)
	should be used. The remaining timing sources are for use when
	the diagnostic test disrupts the transmit timing source.

	The choice of the diagnostic timing source is dependant upon
	the type of test involved and the network topology."
    ::= { gdcDsuChannelDiagEntry 6 }

gdcDsuChannelTestStatus OBJECT-TYPE
    SYNTAX INTEGER {
	 notInTest(1),			-- a test is not running
	 testInProgress(2),		-- the test is running
	 testCompleted(4),		-- the test is complete
	 testCompletedNotInTest(5)      -- a test has completed,nolonger in test
    }
    ACCESS read-write
    STATUS mandatory
    DESCRIPTION
    	"The current execution status of the diagnostic test. The
    	value testRunning(1) indicates that a diagnostic test is running.
	The value testComplete(2) indicates that no diagnostic test is
	running and that the results are available in gdcDsuChannelTestExceptions
	and gdcDsuChannelTestResults. The value testBeingConfigured(3)
	indicates that no diagnostic test is running and that the
	configuration of a new diagnostic test has been initiated
	and as such the results may be invalid.

    	This object works with the gdcDsuChannelSendCode object.  Whenever a
    	test is initiated by  gdcDsuChannelSendCode, then the value of this
    	object is set to testRunning(1).

    	This object also works with the gdcDsuChannelLoopbackConfig,
    	gdcDsuChannelProgPattern, gdcDsuChannelRemoteLoopback, and
    	gdcDsuChannelTestDuration objects.  Whenever these variables are 
    	set, then the value of this object is set to
    	testBeingConfigured(3)."
    ::= { gdcDsuChannelDiagEntry 7 }

gdcDsuChannelTestExceptions OBJECT-TYPE
    SYNTAX INTEGER (0..6)
    ACCESS read-only
    STATUS mandatory
    DESCRIPTION
    	"Indicates any exceptions that may have occurred that would
	affect the interpretation of the test results provided in
	gdcDsuChannelTestResults.

    	The value of this object is a sum.  This sum initially take
    	the value zero.  Then, for each exception, the value
    	associated with the exception is added to the sum.

    	The exception values are:

    		value	exception
    		    1    A timed test was preempted so the result
    		         cannot be viewed in relation to the test
    		         duration
    		    2    The results overflowed so the result cannot be
    		         viewed as an absolute value
    		    4    The test was performed while synchronization
    		         could not be performed so the result may not
    		         be accurate."
    ::= { gdcDsuChannelDiagEntry 8 }

gdcDsuChannelTestResults OBJECT-TYPE
    SYNTAX INTEGER
    ACCESS read-only
    STATUS mandatory
    DESCRIPTION
    	"The results of the last diagnostic test, in bit errors. This can 
	be the current test running or the last completed test.

    	Note that the interpretation of these results may be affected
    	by the value of gdcDsx1TestExceptions."
    ::= { gdcDsuChannelDiagEntry 9 }

END
