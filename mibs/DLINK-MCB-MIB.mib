-- company.mib:
--

DLINK-MCB-MIB DEFINITIONS ::= BEGIN

IMPORTS
       enterprises , Counter
               FROM RFC1155-SMI 
       OBJECT-TYPE
               FROM RFC-1212
       TRAP-TYPE
		FROM RFC-1215	
       DisplayString
               FROM RFC1213-MIB;


company      OBJECT IDENTIFIER ::= { enterprises 171 }

-- MIB Registration Information


mcbMediaConverterFamily  OBJECT IDENTIFIER ::= { company 41 }
mcbMediaConverterChassis OBJECT IDENTIFIER ::= { mcbMediaConverterFamily 1 }

mcbSNMPMIB          OBJECT IDENTIFIER ::= { mcbMediaConverterChassis 1 }
mcbAdministrator    OBJECT IDENTIFIER ::= { mcbMediaConverterChassis 2 }
mcbMCFrame          OBJECT IDENTIFIER ::= { mcbMediaConverterChassis 3 }
mcbMCSlots          OBJECT IDENTIFIER ::= { mcbMediaConverterChassis 4 }
mcbMCRedundantGroups OBJECT IDENTIFIER ::= { mcbMediaConverterChassis 5 }

-- mcbSNMPTrap	   OBJECT IDENTIFIER ::= { mcbMediaConverterChassis 5 }
-- mcbTraps	   OBJECT IDENTIFIER ::= { mcbSNMPTrap 1 }
-- mcbTrap	   OBJECT IDENTIFIER ::= { mcbSNMPTrap 2 }


--
-- SNMP Agent Relative
--
-- Snmp Capabilities
-- Defined in MIB-II
-- Get Community Name
-- Set Community Name
-- Trap Community Name
-- Trap Host IP Address
-- Cold Start Trap
-- Warm Start Trap
-- Link Up Trap
-- Link Down Trap
-- Authentication Fail Trap

-- Power Fail Trap
-- Fan Fail Trap
-- Media Converter Plugin Trap
-- Media Converter Pullout Trap


mcbSNMPTrapPowerFail  OBJECT-TYPE
    SYNTAX      INTEGER  {
		 enabled(1),
		 disabled(2)
    }
    ACCESS      read-write
    STATUS      mandatory
    DESCRIPTION 
        "Power Fail Trap"
    ::= { mcbSNMPMIB 1 }

mcbSNMPTrapFanFail  OBJECT-TYPE
    SYNTAX      INTEGER  { 
	enabled(1), 
	disabled(2) 
    }
    ACCESS      read-write
    STATUS      mandatory
    DESCRIPTION 
        "Fan Fail Trap"
    ::= { mcbSNMPMIB 2 }

mcbSNMPTrapMCPlugin  OBJECT-TYPE
    SYNTAX      INTEGER  {
	enabled(1),
	disabled(2)
    }
    ACCESS      read-write
    STATUS      mandatory
    DESCRIPTION 
        "Media Converter Plugin Trap"
    ::= { mcbSNMPMIB 3 }

mcbSNMPTrapMCPullout  OBJECT-TYPE
    SYNTAX      INTEGER  {
	enabled(1), 
	disabled(2)
    }
    ACCESS      read-write
    STATUS      mandatory
    DESCRIPTION 
        "Media Converter Pullout Trap"
    ::= { mcbSNMPMIB 4 }

mcbSNMPTrapMCLinkDown  OBJECT-TYPE
    SYNTAX      INTEGER  {
	enabled(1),
	disabled(2)
    }
    ACCESS      read-write
    STATUS      mandatory
    DESCRIPTION 
        "Media Converter Link Down Trap"
    ::= { mcbSNMPMIB 5 }

mcbSNMPTrapMCLinkUp  OBJECT-TYPE
    SYNTAX      INTEGER  {
	enabled(1),
	disabled(2)
    }
    ACCESS      read-write
    STATUS      mandatory
    DESCRIPTION 
        "Media Converter Link Up Trap"
    ::= { mcbSNMPMIB 6 }

mcbSNMPTrapMCLinkBroken  OBJECT-TYPE
    SYNTAX      INTEGER  {
	enabled(1),
	disabled(2)
    }
    ACCESS      read-write
    STATUS      mandatory
    DESCRIPTION 
        "Media Converter Link Broken Trap"
    ::= { mcbSNMPMIB 7 }

mcbSNMPTrapMCActiveSlotChange  OBJECT-TYPE
    SYNTAX      INTEGER  {
	enabled(1),
	disabled(2)
    }
    ACCESS      read-write
    STATUS      mandatory
    DESCRIPTION 
        "A active slot change Trap"
    ::= { mcbSNMPMIB 8 }

mcbSNMPTrapMCActiveSlotLose  OBJECT-TYPE
    SYNTAX      INTEGER  {
	enabled(1),
	disabled(2)
    }
    ACCESS      read-write
    STATUS      mandatory
    DESCRIPTION 
        "A active slot Lose Trap"
    ::= { mcbSNMPMIB 9 }


--
-- MIB 2 Relative
--
-- Defined in MIB-II
-- Out of Band Ethernet Port
-- Mac Address/Speed
-- IP Address/Subnet mask/Default Gateway
-- Administrator
-- System Name/Location




--
-- Enterprise MIB Relative
--
-- Administrator


mcbAdministratorHardwareRev  OBJECT-TYPE
    SYNTAX      DisplayString
    ACCESS      read-only
    STATUS      mandatory
    DESCRIPTION 
        "Hardware Revision"
    ::= { mcbAdministrator 1 }

mcbAdministratorSoftwareRev  OBJECT-TYPE
    SYNTAX      DisplayString
    ACCESS      read-only
    STATUS      mandatory
    DESCRIPTION 
        "Software Revision"
    ::= { mcbAdministrator 2 }

mcbAdministratorBiosRev  OBJECT-TYPE
    SYNTAX      DisplayString
    ACCESS      read-only
    STATUS      mandatory
    DESCRIPTION 
        "Bios Revision"
    ::= { mcbAdministrator 3 }

mcbAdministratorFactoryReset  OBJECT-TYPE
    SYNTAX      INTEGER  { action(1) }
    ACCESS      read-write
    STATUS      mandatory
    DESCRIPTION 
        "Administratoristrator Factory Reset The Whole Chassis"
    ::= { mcbAdministrator 4 }

mcbAdministratorFactoryResetCPU  OBJECT-TYPE
    SYNTAX      INTEGER  { action(1) }
    ACCESS      read-write
    STATUS      mandatory
    DESCRIPTION 
        "Administratoristrator Factory Reset Only CPU"
    ::= { mcbAdministrator 5 }
    
mcbAdministratorSoftwareReboot  OBJECT-TYPE
    SYNTAX      INTEGER  { action(1) }
    ACCESS      read-write
    STATUS      mandatory
    DESCRIPTION 
        "System Software Reboot"
    ::= { mcbAdministrator 6 }

-- Media Converter Frame Relative

mcbFramePowerOneOnStatus  OBJECT-TYPE
    SYNTAX      INTEGER  {
	on(1),
	off(2)
    }
    ACCESS      read-only
    STATUS      mandatory
    DESCRIPTION 
        "Main Power On Status"
    ::= { mcbMCFrame 1 }

mcbFramePowerTwoOnStatus  OBJECT-TYPE
    SYNTAX      INTEGER  {
	on(1),
	off(2)
    }
    ACCESS      read-only
    STATUS      mandatory
    DESCRIPTION 
        "Redundent Power On Status"
    ::= { mcbMCFrame 2 }

mcbFramePowerOneFailStatus  OBJECT-TYPE
    SYNTAX      INTEGER  {
	on(1),
	off(2)
    }
    ACCESS      read-only
    STATUS      mandatory
    DESCRIPTION 
        "Main Power Fail Status"
    ::= { mcbMCFrame 3 }

mcbFramePowerTwoFailStatus  OBJECT-TYPE
    SYNTAX      INTEGER  {
	on(1),
	off(2)
    }
    ACCESS      read-only
    STATUS      mandatory
    DESCRIPTION 
        "Redundent Power Fail Status"
    ::= { mcbMCFrame 4 }

mcbFrameFanOneFailStatus  OBJECT-TYPE
    SYNTAX      INTEGER  {
	on(1),
	off(2)
    }
    ACCESS      read-only
    STATUS      mandatory
    DESCRIPTION 
        "Main Fan Fail Status"
    ::= { mcbMCFrame 5 }

mcbFrameFanTwoFailStatus  OBJECT-TYPE
    SYNTAX      INTEGER  {
	on(1),
	off(2)
    }
    ACCESS      read-only
    STATUS      mandatory
    DESCRIPTION 
        "Redundent Fan Fail Status"
    ::= { mcbMCFrame 6 }

-- Each Media Converter OutBandNetPortice Relative

mcbMCSlotCount  OBJECT-TYPE
    SYNTAX      INTEGER 
    ACCESS      read-only
    STATUS      mandatory
    DESCRIPTION 
        "The Number Of Media Converters. "
    ::= { mcbMCSlots 1 }


mcbMCSlotTable  OBJECT-TYPE
    SYNTAX      SEQUENCE OF McbMCSlotEntry
    ACCESS      not-accessible
    STATUS      mandatory
    DESCRIPTION 
        "Each Media Converter Device Relative Table"
    ::= { mcbMCSlots 2 }

mcbMCSlotEntry  OBJECT-TYPE
    SYNTAX      McbMCSlotEntry
    ACCESS      not-accessible
    STATUS      mandatory
    DESCRIPTION 
        "Each Media Converter Device Relative Entry"
    INDEX       { mcbMCSlotNo }
    ::= { mcbMCSlotTable 1 }

McbMCSlotEntry ::= SEQUENCE {
	mcbMCSlotNo			INTEGER,
	mcbMCSlotExist			INTEGER,
	mcbMCModelName			DisplayString,
	mcbMCMediaOneType		INTEGER,
	mcbMCMediaTwoType		INTEGER,
	mcbMCMediaOneLinkStatus		INTEGER,
	mcbMCMediaOneDupStatus		INTEGER,
	mcbMCMediaOneSpeedStatus	INTEGER,
	mcbMCMediaTwoLinkStatus		INTEGER,
	mcbMCMediaTwoDupStatus		INTEGER,
	mcbMCMediaTwoSpeedStatus	INTEGER,
	mcbMCSlotName			DisplayString,
	mcbMCEnable			INTEGER,
	mcbMCSetLLCF			INTEGER,
	mcbMCEnableMediaOne		INTEGER,
	mcbMCEnableMediaTwo		INTEGER,
	mcbMCSetMediaOneAutoNegotiate	INTEGER,
	mcbMCSetMediaTwoAutoNegotiate	INTEGER,
	mcbMCSetMediaOneSpeed		INTEGER,
	mcbMCSetMediaTwoSpeed		INTEGER,
	mcbMCSetMediaOneDuplex		INTEGER,
	mcbMCSetMediaTwoDuplex		INTEGER,
	mcbMCSetMediaOneFlowControl	INTEGER,
	mcbMCSetMediaTwoFlowControl	INTEGER,
	mcbMCSetMediaOneLLR		INTEGER,
	mcbMCSetMediaTwoLLR		INTEGER,
	mcbMCMediaOneBrokenStatus	INTEGER,
	mcbMCMediaTwoBrokenStatus	INTEGER,
	mcbMCMediaOneTxPacketCount	Counter,
	mcbMCMediaOneRxPacketCount	Counter,
	mcbMCMediaTwoTxPacketCount	Counter,
	mcbMCMediaTwoRxPacketCount	Counter
	}


mcbMCSlotNo  OBJECT-TYPE
    SYNTAX      INTEGER
    ACCESS      read-only
    STATUS      mandatory
    DESCRIPTION 
        "Each Media Converter Device Relative Number On One Base"
    ::= { mcbMCSlotEntry 1 }

mcbMCSlotExist  OBJECT-TYPE
    SYNTAX      INTEGER {
	exist(1),
	nonexist(2),
	unsupported(3)
    }
    ACCESS      read-only
    STATUS      mandatory
    DESCRIPTION 
        "Each Device of Slot Is Exist Or Not"
    ::= { mcbMCSlotEntry 2 }

mcbMCModelName  OBJECT-TYPE
    SYNTAX      DisplayString
    ACCESS      read-only
    STATUS      mandatory
    DESCRIPTION 
        "Each Media Converter Device Relative Model Name"
    ::= { mcbMCSlotEntry 3 }

mcbMCMediaOneType  OBJECT-TYPE
    SYNTAX      INTEGER {
	tp(1),
	fiber(2),
	unsupported(3)
    }
    ACCESS      read-only
    STATUS      mandatory
    DESCRIPTION 
        "Media Type Is TP Or Fiber"
    ::= { mcbMCSlotEntry 4 }

mcbMCMediaTwoType  OBJECT-TYPE
    SYNTAX      INTEGER {
	tp(1),
	fiber(2),
	unsupported(3)
    }
    ACCESS      read-only
    STATUS      mandatory
    DESCRIPTION 
        "Media Type Is TP Or Fiber"
    ::= { mcbMCSlotEntry 5 }

mcbMCMediaOneLinkStatus  OBJECT-TYPE
    SYNTAX      INTEGER  {
	online(1),
	offline(2),
	unsupported(3)
    }
    ACCESS      read-only
    STATUS      mandatory
    DESCRIPTION 
        "Media One Link Status"
    ::= { mcbMCSlotEntry 6 }

mcbMCMediaTwoLinkStatus  OBJECT-TYPE
    SYNTAX      INTEGER  {
	online(1),
	offline(2),
	unsupported(3)
    }
    ACCESS      read-only
    STATUS      mandatory
    DESCRIPTION 
        "Media Two Link Status"
    ::= { mcbMCSlotEntry 7 }

mcbMCMediaOneDupStatus  OBJECT-TYPE
    SYNTAX      INTEGER  {
	half(1),
	full(2),
	unsupported(3)
    }
    ACCESS      read-only
    STATUS      mandatory
    DESCRIPTION 
        "Media One Duplex Status"
    ::= { mcbMCSlotEntry 8 }

mcbMCMediaTwoDupStatus  OBJECT-TYPE
    SYNTAX      INTEGER  {
	half(1),
	full(2),
	unsupported(3)
    }
    ACCESS      read-only
    STATUS      mandatory
    DESCRIPTION 
        "Media Two Duplex Status"
    ::= { mcbMCSlotEntry 9 }

mcbMCMediaOneSpeedStatus  OBJECT-TYPE
    SYNTAX      INTEGER  { 
	speed10M(1),
	speed100M(2),
	speed1000M(3),
	unsupported(4)
    }
    ACCESS      read-only
    STATUS      mandatory
    DESCRIPTION 
        "Media One Speed Status"
    ::= { mcbMCSlotEntry 10 }



mcbMCMediaTwoSpeedStatus  OBJECT-TYPE
    SYNTAX      INTEGER  {
	speed10M(1),
	speed100M(2),
	speed1000M(3),
	unsupported(4)
    }
    ACCESS      read-only
    STATUS      mandatory
    DESCRIPTION 
        "Media Two Speed Status"
    ::= { mcbMCSlotEntry 11 }

mcbMCSlotName  OBJECT-TYPE
    SYNTAX      DisplayString (SIZE (0..7))
    ACCESS      read-write
    STATUS      mandatory
    DESCRIPTION 
        "Each Media Converter Chassis Slot Name"
    ::= { mcbMCSlotEntry 12 }

mcbMCEnable  OBJECT-TYPE
    SYNTAX      INTEGER  {
	enabled(1),
	disabled(2),
	unsupported(3)
    }
    ACCESS      read-write
    STATUS      mandatory
    DESCRIPTION 
        "Enable or Disable the smart Media Converter"
    ::= { mcbMCSlotEntry 13 }

mcbMCSetLLCF  OBJECT-TYPE
    SYNTAX      INTEGER  {
	enabled(1),
	disabled(2),
	unsupported(3)
    }
    ACCESS      read-write
    STATUS      mandatory
    DESCRIPTION 
        "Enable or Disable the LLCF of the smart Media Converter"
    ::= { mcbMCSlotEntry 14 }

mcbMCEnableMediaOne  OBJECT-TYPE
    SYNTAX      INTEGER  {
	enabled(1),
	disabled(2),
	unsupported(3)
    }
    ACCESS      read-write
    STATUS      mandatory
    DESCRIPTION 
        "Enable the media one of the smart Media Converter"
    ::= { mcbMCSlotEntry 15 }

mcbMCEnableMediaTwo  OBJECT-TYPE
    SYNTAX      INTEGER  {
	enabled(1),
	disabled(2),
	unsupported(3)
    }
    ACCESS      read-write
    STATUS      mandatory
    DESCRIPTION 
        "Enable the media two of the smart Media Converter"
    ::= { mcbMCSlotEntry 16 }

mcbMCSetMediaOneAutoNegotiate  OBJECT-TYPE
    SYNTAX      INTEGER  {
	auto-negotiate(1),
	force(2),
	unsupported(3)
    }
    ACCESS      read-write
    STATUS      mandatory
    DESCRIPTION 
        "Set the Auto Negotiation mode or the Force mode of the media one of the smart Media Converter"
    ::= { mcbMCSlotEntry 17 }

mcbMCSetMediaTwoAutoNegotiate  OBJECT-TYPE
    SYNTAX      INTEGER  {
	auto-negotiate(1),
	force(2),
	unsupported(3)
    }
    ACCESS      read-write
    STATUS      mandatory
    DESCRIPTION 
        "Set the Auto Negotiation mode or the Force mode of the media two of the smart Media Converter"
    ::= { mcbMCSlotEntry 18 }

mcbMCSetMediaOneSpeed  OBJECT-TYPE
    SYNTAX      INTEGER  {
	speed10M(1),
	speed100M(2),
	speed1000M(3),
	unsupported(4)
    }
    ACCESS      read-write
    STATUS      mandatory
    DESCRIPTION 
        "Set the speed in Force mode of the media one of the smart Media Converter"
    ::= { mcbMCSlotEntry 19 }

mcbMCSetMediaTwoSpeed  OBJECT-TYPE
    SYNTAX      INTEGER  {
	speed10M(1),
	speed100M(2),
	speed1000M(3),
	unsupported(4)
    }
    ACCESS      read-write
    STATUS      mandatory
    DESCRIPTION 
        "Set the speed in Force mode of the media two of the smart Media Converter"
    ::= { mcbMCSlotEntry 20 }

mcbMCSetMediaOneDuplex  OBJECT-TYPE
    SYNTAX      INTEGER  {
	half(1),
	full(2),
	unsupported(3)
    }
    ACCESS      read-write
    STATUS      mandatory
    DESCRIPTION 
        "Set the duplex in Force mode of the media one of the smart Media Converter"
    ::= { mcbMCSlotEntry 21 }

mcbMCSetMediaTwoDuplex  OBJECT-TYPE
    SYNTAX      INTEGER  {
	half(1),
	full(2),
	unsupported(3)
    }
    ACCESS      read-write
    STATUS      mandatory
    DESCRIPTION 
        "Set the duplex in Force mode of the media two of the smart Media Converter"
    ::= { mcbMCSlotEntry 22 }

mcbMCSetMediaOneFlowControl  OBJECT-TYPE
    SYNTAX      INTEGER  {
	enabled(1),
	disabled(2),
	unsupported(3)
    }
    ACCESS      read-write
    STATUS      mandatory
    DESCRIPTION 
        "Set the flow control in Force mode of the media one of the smart Media Converter"
    ::= { mcbMCSlotEntry 23 }

mcbMCSetMediaTwoFlowControl  OBJECT-TYPE
    SYNTAX      INTEGER  {
	enabled(1),
	disabled(2),
	unsupported(3)
    }
    ACCESS      read-write
    STATUS      mandatory
    DESCRIPTION 
        "Set the flow control in Force mode of the media two of the smart Media Converter"
    ::= { mcbMCSlotEntry 24 }

mcbMCSetMediaOneLLR  OBJECT-TYPE
    SYNTAX      INTEGER  {
	enabled(1),
	disabled(2),
	unsupported(3)
    }
    ACCESS      read-write
    STATUS      mandatory
    DESCRIPTION 
        "Set the LLR of the media one of the smart Media Converter"
    ::= { mcbMCSlotEntry 25 }

mcbMCSetMediaTwoLLR  OBJECT-TYPE
    SYNTAX      INTEGER  {
	enabled(1),
	disabled(2),
	unsupported(3)
    }
    ACCESS      read-write
    STATUS      mandatory
    DESCRIPTION 
        "Set the LLR of the media two of the smart Media Converter"
    ::= { mcbMCSlotEntry 26 }

mcbMCMediaOneBrokenStatus  OBJECT-TYPE
    SYNTAX      INTEGER  {
	unbroken(1),
	broken(2),
	unsupported(3)
    }
    ACCESS      read-only
    STATUS      mandatory
    DESCRIPTION 
        "Media One Broken Status of the smart Media Converter"
    ::= { mcbMCSlotEntry 27 }

mcbMCMediaTwoBrokenStatus  OBJECT-TYPE
    SYNTAX      INTEGER  {
	unbroken(1),
	broken(2),
	unsupported(3)
    }
    ACCESS      read-only
    STATUS      mandatory
    DESCRIPTION 
        "Media Two Broken Status of the smart Media Converter"
    ::= { mcbMCSlotEntry 28 }

mcbMCMediaOneTxPacketCount OBJECT-TYPE
    SYNTAX      Counter
    ACCESS      read-only
    STATUS      mandatory
    DESCRIPTION 
        "Media One transmitting packet count of the smart Media Converter"
    ::= { mcbMCSlotEntry 29 }

mcbMCMediaOneRxPacketCount OBJECT-TYPE
    SYNTAX      Counter
    ACCESS      read-only
    STATUS      mandatory
    DESCRIPTION 
        "Media One receiving packet count of the smart Media Converter"
    ::= { mcbMCSlotEntry 30 }

mcbMCMediaTwoTxPacketCount OBJECT-TYPE
    SYNTAX      Counter
    ACCESS      read-only
    STATUS      mandatory
    DESCRIPTION 
        "Media Two transmitting packet count of the smart Media Converter"
    ::= { mcbMCSlotEntry 31 }

mcbMCMediaTwoRxPacketCount OBJECT-TYPE
    SYNTAX      Counter
    ACCESS      read-only
    STATUS      mandatory
    DESCRIPTION 
        "Media Two receiving packet count of the smart Media Converter"
    ::= { mcbMCSlotEntry 32 }

-- Each Media Converter Redundant Groups Relative

mcbMCRedundantGroupCount  OBJECT-TYPE
    SYNTAX      INTEGER 
    ACCESS      read-only
    STATUS      mandatory
    DESCRIPTION 
        "The Number Of Redundant Groups. "
    ::= { mcbMCRedundantGroups 1 }


mcbMCRedundantGroupTable  OBJECT-TYPE
    SYNTAX      SEQUENCE OF McbMCRedundantGroupEntry
    ACCESS      not-accessible
    STATUS      mandatory
    DESCRIPTION 
        "Each Redundant Group Relative Table"
    ::= { mcbMCRedundantGroups 2 }

mcbMCRedundantGroupEntry  OBJECT-TYPE
    SYNTAX      McbMCRedundantGroupEntry
    ACCESS      not-accessible
    STATUS      mandatory
    DESCRIPTION 
        "Each Redundant Group Relative Entry"
    INDEX       { mcbMCRedundantGroupNo }
    ::= { mcbMCRedundantGroupTable 1 }

McbMCRedundantGroupEntry ::= SEQUENCE {
	mcbMCRedundantGroupNo		INTEGER,
	mcbMCRedundantGroupPrimarySlot	INTEGER,
	mcbMCRedundantGroupSecondarySlot	INTEGER,
	mcbMCRedundantGroupEnable	INTEGER,
	mcbMCRedundantGroupActiveSlot	INTEGER,
	mcbMCRedundantGroupRestart  	INTEGER
	}


mcbMCRedundantGroupNo  OBJECT-TYPE
    SYNTAX      INTEGER
    ACCESS      read-only
    STATUS      mandatory
    DESCRIPTION 
        "Each Redundant Group Relative Number On One Base"
    ::= { mcbMCRedundantGroupEntry 1 }

mcbMCRedundantGroupPrimarySlot  OBJECT-TYPE
    SYNTAX      INTEGER
    ACCESS      read-only
    STATUS      mandatory
    DESCRIPTION 
        "The primary slot member of the Redundant Group"
    ::= { mcbMCRedundantGroupEntry 2 }

mcbMCRedundantGroupSecondarySlot  OBJECT-TYPE
    SYNTAX      INTEGER
    ACCESS      read-only
    STATUS      mandatory
    DESCRIPTION 
        "The secondary slot member of the Redundant Group"
    ::= { mcbMCRedundantGroupEntry 3 }

mcbMCRedundantGroupEnable  OBJECT-TYPE
    SYNTAX      INTEGER  {
	enabled(1),
	disabled(2)
    }
    ACCESS      read-write
    STATUS      mandatory
    DESCRIPTION 
        "Enable or Disable the Redundant Group"
    ::= { mcbMCRedundantGroupEntry 4 }

mcbMCRedundantGroupActiveSlot  OBJECT-TYPE
    SYNTAX      INTEGER
    ACCESS      read-only
    STATUS      mandatory
    DESCRIPTION 
        "The active link slot member of the Redundant Group"
    ::= { mcbMCRedundantGroupEntry 5 }

mcbMCRedundantGroupRestart  OBJECT-TYPE
    SYNTAX      INTEGER  { action(1) }
    ACCESS      read-write
    STATUS      mandatory
    DESCRIPTION 
        "Restart the Redundant Group"
    ::= { mcbMCRedundantGroupEntry 6 }


--
--Convention for Defining Traps 
--

mcbPowerOneFail TRAP-TYPE 
	ENTERPRISE mcbMediaConverterChassis
	DESCRIPTION 
           "A PowerFail trap signifies that the sending protocol entity
            recognizes a failure in one of the communication links 
            represented in the agent's configuration"
        ::= 1

mcbFanOneFail TRAP-TYPE
	ENTERPRISE mcbMediaConverterChassis
        DESCRIPTION
            "A FanFail trap signifies that the sending protocol entity
            recognizes a failure in one of the communication links 
            represented in the agent's configuration"
        ::= 2

mcbPowerTwoFail TRAP-TYPE
	ENTERPRISE mcbMediaConverterChassis
	DESCRIPTION 
           "A PowerFail trap signifies that the sending protocol entity
            recognizes a failure in one of the communication links 
            represented in the agent's configuration"
        ::= 3 

mcbFanTwoFail TRAP-TYPE
	ENTERPRISE mcbMediaConverterChassis
        DESCRIPTION
            "A FanFail trap signifies that the sending protocol entity
            recognizes a failure in one of the communication links 
            represented in the agent's configuration"
        ::= 4

mcbMediaConverterPlugin TRAP-TYPE
	ENTERPRISE mcbMediaConverterChassis
	VARIABLES {  mcbMCSlotNo }
        DESCRIPTION
           "A Media Converter Plugin trap signifies that the sending protocol
            entity checks if the model is pluged in the slot"
        ::= 5

mcbMediaConverterPullout TRAP-TYPE
	ENTERPRISE mcbMediaConverterChassis
	VARIABLES {  mcbMCSlotNo }
        DESCRIPTION
           "A Media Converter Pullout trap signifies that the sending protocol
            entity checks if the model is pull out from the slot"
        ::= 6
 
mcbMCMediaOneLinkDown TRAP-TYPE
	ENTERPRISE mcbMediaConverterChassis
	VARIABLES {  mcbMCSlotNo }
        DESCRIPTION
           "A Media Converter Media One Link Down trap signifies that the 
	    sending protocol entity checks if the media one of the specified
	    media converter in the slot links down"
        ::= 7

mcbMCMediaTwoLinkDown TRAP-TYPE
	ENTERPRISE mcbMediaConverterChassis
	VARIABLES {  mcbMCSlotNo }
        DESCRIPTION
           "A Media Converter Media Two Link Down trap signifies that the 
	    sending protocol entity checks if the media two of the specified
	    media converter in the slot links down"
        ::= 8

mcbMCMediaOneLinkUp TRAP-TYPE
	ENTERPRISE mcbMediaConverterChassis
	VARIABLES {  mcbMCSlotNo }
        DESCRIPTION
           "A Media Converter Media One Link Up trap signifies that the 
	    sending protocol entity checks if the media one of the specified
	    media converter in the slot links up"
        ::= 9

mcbMCMediaTwoLinkUp TRAP-TYPE
	ENTERPRISE mcbMediaConverterChassis
	VARIABLES {  mcbMCSlotNo }
        DESCRIPTION
           "A Media Converter Media Two Link Up trap signifies that the 
	    sending protocol entity checks if the media two of the specified
	    media converter in the slot links up"
        ::= 10

mcbMCMediaOneBroken TRAP-TYPE
	ENTERPRISE mcbMediaConverterChassis
	VARIABLES {  mcbMCSlotNo }
        DESCRIPTION
           "A Media Converter Media One Broken trap signifies that the 
	    sending protocol entity checks if the media one of the specified
	    media converter in the slot was broken"
        ::= 11

mcbMCMediaTwoBroken TRAP-TYPE
	ENTERPRISE mcbMediaConverterChassis
	VARIABLES {  mcbMCSlotNo }
        DESCRIPTION
           "A Media Converter Media Two Broken trap signifies that the 
	    sending protocol entity checks if the media two of the specified
	    media converter in the slot was broken"
        ::= 12

mcbMCActiveSlotChange TRAP-TYPE
	ENTERPRISE mcbMediaConverterChassis
	VARIABLES {  mcbMCRedundantGroupNo }
        DESCRIPTION
           "A Active Slot Change trap signifies that the sending protocol entity checks if the active slot of the redundant group is changed"
        ::= 13

mcbMCActiveSlotLose TRAP-TYPE
	ENTERPRISE mcbMediaConverterChassis
	VARIABLES {  mcbMCRedundantGroupNo }
        DESCRIPTION
           "A Active Slot Lose trap signifies that the sending protocol entity checks if the active slot of the redundant group is lost"
        ::= 14

END
