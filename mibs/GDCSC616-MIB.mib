-- Copyright 1994 General DataComm Ind., Inc. All Rights Reserved.
--
-- Reproduction of this document is authorized on condition that the
-- foregoing copyright notice is included. This General DataComm, GDC,
-- SNMP Management Information Base Specification embodies GDCs'
-- confidential and proprietary intellectual property. GDC retains all
-- title and ownership in the Specification, including any revisions.
--
-- It is GDCs intent to encourage the widespread use of this Specification
-- in connection with the management of GDC's products. GDC grants vendors,
-- end-users, and other interested parties a non-exclusive licence to use
-- this Specification in connection with the management of GDC's products.
--
-- This Specification is supplied "AS IS," and GDC makes no warranty,
-- either expressed or implied, as to the use operation, condition, or
-- performance of the Specification.
--
-- Revision History
--
-- Version   Date       Name            Description
-- 1.00A      14-Dec-94	B. Richards	Initial Revision
-- 1.00B      16-Mar-95 B. Richards     Deleted loop mode of operation
--                                      in config 2
-- 1.00C      19-Apr-95 B. Richards     Added LOOP Performance Interval
--					Maintenance Table FOR SC616,DC610/2
-- 1.00D      26-Apr-95 B. Richards     Changed start of range from 1 to 0
--					bqlNumberofValidIntervals
-- 1.00E      22-Aug-95 M. Cyr          Fixed enums in dtedatarate table
--                                      to be kbps and not bps.  Also
--                                      fixed incorrect comments.
-- 1.00F      01-Sep-95 C. Amorossi	Added Interface Comments.
-- 1.00G      27-Sep-95 E. Moreno-Leon  Added Alarm status command
-- 1.00H      05-Feb-96 E. Moreno-Leon  Added stats to OCTET STRING's and NZ objects
-- 1.00J      07-Apr-98 W. Richards     Added new product GT 128 and NZ tables
--                                        and objects.
--                                      Added bqlDC61xNoResponseAlm and
--                                        bqlDC61xDiagRxErrAlm to DC610 and DC 612



GDCSC616-MIB DEFINITIONS	   ::=	   BEGIN

IMPORTS

	enterprises, Gauge		FROM RFC1155-SMI
	DisplayString                   FROM RFC1213-MIB
	OBJECT-TYPE                     FROM RFC-1212
	SCinstance                      FROM GDCMACRO-MIB;

gdc          OBJECT IDENTIFIER ::= { enterprises 498 }
bql	     OBJECT IDENTIFIER ::= { gdc 10 }


-- This is the GDC MIB for SC616, DC610/NZ, DC612, GT/NZ 128 objects for ISDN 2B1Q.
--
-- This MIB is only usable when the configuration is software controllable.
--
-- See the GDC MIB requirements document to determine how the standard MIB's
-- are supported.
--
--*****************************************************************************
-- 	SCinstance is defined as the addressing/indexing method of accessing
--	table objects in this MIB. The SCinstance represents the SpectraComm
--	shelf Slot, Line, Drop and interface address.
--	Represented as SLDi, (Slot, Line, Drop, interface).
--
--	Slot has values from 1 to 32. 		SpectraComm shelf Slot address.
--	Line has values from 1 to 128. 		Network element Line address.
--	Drop has values from 0 to 31. 		Network element Drop address
--	Interface has values from 0 to 3. 	Network element Loop number.
--
--	Interface is the SC616 loop number. If the interface number is 0 the get
--	or set function is destined for the SC616 network element and does not
--	effect the loop. If the loop number is 1, 2, or 3 the set or get is
--	destined for its associated loop on the SC616.
--
--	The Interfaces are defined as follows:
--		SC616:			DC610:		DC612:		GT 128:
--		Unit	0		Unit	0	Unit	0	Unit	0
--		Loop1	1		Loop1	1	Loop1	1	Loop1	1
--		Loop2	2		DTE	2	DTE1	2	DTE	2
--		Loop3	3				DTE2	3
--
--		
--	In addition to the SLDi a Channel number is used for accessing some
--	tables. The channel number is either 1 or 2. Channel number can be used
-- 	on the SC616, DC610 and DC612 and GT 128 network elements.
--*****************************************************************************



--**************************************************************************
--		GDC SC616, DC610, DC612, GT 128 MIB VERSION NUMBER
--**************************************************************************

bqlMIBVersion	OBJECT-TYPE
	SYNTAX	DisplayString (SIZE (5))
	ACCESS	read-only
	STATUS  mandatory
	DESCRIPTION
		"The version number of the MIB, to allow products to 
		know which MIB is being supported.  The version number
		will be x.yzT where x is a major revision (1-9), y is a minor
		revision(0-9), z is a typo revision (0-9) and T indicates the
		MIB is still a test revision(A-Z).  When a release is complete
		no T should exist."
	::= { bql 1 }


--*****************************************************************************
--                    WHAT ARE YOU TABLE
--*****************************************************************************
--
-- This table contains network element information indexed by SLDi.
--
-- This table uses SCinstance as SLDi where i is always 0.
--
--
bqlWhatAreYouTable OBJECT-TYPE
	SYNTAX	SEQUENCE OF BqlWhatAreYouEntry
	ACCESS  not-accessible
	STATUS  mandatory
	DESCRIPTION
			"The GDC SC616, DC610, DC612, GT 128 What Are You Table."
	::= { bql 2 }

bqlWhatAreYouEntry OBJECT-TYPE
	SYNTAX	BqlWhatAreYouEntry
	ACCESS  not-accessible
	STATUS  mandatory
	DESCRIPTION
			"An entry in the GDC SC616 What Are You table."
	INDEX	{ bqlWhatAreYouIndex }
	::= { bqlWhatAreYouTable 1 }

BqlWhatAreYouEntry ::=
	SEQUENCE  {
		  bqlWhatAreYouIndex		SCinstance,
		  bqlBaseCardType		INTEGER,
		  bqlOptionCard			INTEGER,
		  bqlDTE2CardType		INTEGER,
		  bqlDTE1CardType		INTEGER,
		  bqlCodeRev			DisplayString,
		  bqlAlarmStatus                OCTET STRING
		  }

bqlWhatAreYouIndex OBJECT-TYPE
	SYNTAX  SCinstance
	ACCESS  read-only
	STATUS  mandatory
	DESCRIPTION
	       "This object is the identifier of the SC616 What Are You table."
	::= { bqlWhatAreYouEntry 1 }

bqlBaseCardType OBJECT-TYPE
	SYNTAX	INTEGER {
			dc610(2),
			dc612(4),
			sc616(5),
                        gt128(9),
                        gt128NZ(10)
			}
	ACCESS  read-only
	STATUS  mandatory
	DESCRIPTION
		"This function returns the value the Base Card Type."
	::= { bqlWhatAreYouEntry 2 }

bqlOptionCard OBJECT-TYPE
	SYNTAX  INTEGER {
			notInstalled(1),
			installed(2)
			}
	ACCESS  read-only
	STATUS  mandatory
	DESCRIPTION
		"This indicates whether the option card is installed or not
		 on the DC610 or DC612."
	::= { bqlWhatAreYouEntry 3 }

bqlDTE2CardType	OBJECT-TYPE
	SYNTAX  INTEGER {
			eia530(1),
			x21(2),
			none(7)
			}
	ACCESS  read-only
	STATUS  mandatory
	DESCRIPTION
		"This object is the DTE channel 2 plug-in card type on the
		 DC610 or DC612."
	::= { bqlWhatAreYouEntry 4 }

bqlDTE1CardType	OBJECT-TYPE
	SYNTAX  INTEGER {
			eia530(1),
			x21(2),
                        v35(3),
			none(7)
			}
	ACCESS  read-only
	STATUS  mandatory
	DESCRIPTION
		"This object is the DTE channel 1 plug-in card type on the 
		 DC610 or DC612 or GT 128."
	::= { bqlWhatAreYouEntry 5 }

bqlCodeRev OBJECT-TYPE
	SYNTAX  DisplayString (SIZE (4))
	ACCESS  read-only
	STATUS  mandatory
	DESCRIPTION
		"This function returns the firmware code level.
		 Example A-  ,B-  "
	::= { bqlWhatAreYouEntry 6 }

bqlAlarmStatus OBJECT-TYPE
	SYNTAX	  OCTET STRING (SIZE (1..255))
	ACCESS	  read-only
	STATUS	  mandatory
	DESCRIPTION
		"The current alarms of the unit without the alarm masks."
	::= { bqlWhatAreYouEntry 7 }




--*****************************************************************************
-- 			CONFIGURATION TABLE
--*****************************************************************************
--
-- This table contains the network element's configuration information indexed by
-- SLDi and channel.
--
-- This table uses SCinstance as SLDi where i is Loop 1, 2, or 3 and channel is
-- 1 or 2.
--

bqlConfigTable OBJECT-TYPE
	SYNTAX	SEQUENCE OF BqlConfigEntry
	ACCESS  not-accessible
	STATUS  mandatory
	DESCRIPTION
		"The GDC SC616, DC610, DC612, GT 128 2B1Q configuration table."
	::= { bql 3 }

bqlConfigEntry OBJECT-TYPE
	SYNTAX	BqlConfigEntry
	ACCESS  not-accessible
	STATUS  mandatory
	DESCRIPTION
		"A listing of GDC 2B1Q SC616 options."
	INDEX	{ bqlConfigIndex, bqlConfigChnlIndex }
	::= { bqlConfigTable 1 }

BqlConfigEntry ::=
	SEQUENCE        {
			bqlConfigIndex		SCinstance,
			bqlConfigChnlIndex	INTEGER,
			bqlTestPattern		INTEGER,
			bqlRLTimeout		INTEGER,
			bqlRespRL		INTEGER,
			bqlRLType		INTEGER,
			bqlBilateralRL		INTEGER,
			bqlInbandRTSDCD 	INTEGER,
			bqlRTS 			INTEGER,
			bqlRTSCTSDelay 		INTEGER,
			bqlAntiStream 		INTEGER,
			bqlTXDataElasticBufr 	INTEGER,
			bqlRTSCTSDelayTime 	INTEGER,
			bqlAntiStreamTime 	INTEGER
			}

bqlConfigIndex OBJECT-TYPE
	SYNTAX  SCinstance
	ACCESS  read-only
	STATUS  mandatory
	DESCRIPTION
		"A unique index for the Configuration Table."
	::= { bqlConfigEntry 1 }

bqlConfigChnlIndex OBJECT-TYPE
	SYNTAX  INTEGER {
			channel1(1),
			channel2(2)
			}
	ACCESS  read-only
	STATUS  mandatory
	DESCRIPTION
		"A unique channel index for the Configuration Table."
	::= { bqlConfigEntry 2 }

bqlTestPattern OBJECT-TYPE
	SYNTAX	INTEGER {
			pattern2047(1),
			pattern511(2)
			}
	ACCESS    read-write
	STATUS    mandatory
	DESCRIPTION     "Object to select loop and channel test pattern
			 for SC616, DC610, DC612."
	::= { bqlConfigEntry 3 }

bqlRLTimeout OBJECT-TYPE
	SYNTAX	INTEGER {
			noTimeout(1),
			timeoutAfter10Min(2)
			}
	ACCESS    read-write
	STATUS    mandatory
	DESCRIPTION     "Object to select loop and channel remote loop time out
			 for DC610 and DC612 only."
	::= { bqlConfigEntry 4 }

bqlRespRL OBJECT-TYPE
	SYNTAX	INTEGER {
			enable(1),
			disable(2)
			}
	ACCESS    read-write
	STATUS    mandatory
	DESCRIPTION     "Object to select loop and channel remote loop response
			 for DC610 and DC612 only."
	::= { bqlConfigEntry 5 }

bqlRLType OBJECT-TYPE
	SYNTAX	INTEGER {
			v54(1),
			pn127(2)
			}
	ACCESS    read-write
	STATUS    mandatory
	DESCRIPTION     "Object to select loop and channel remote loop type
			 for DC610 and DC612 only."
	::= { bqlConfigEntry 6 }

bqlBilateralRL OBJECT-TYPE
	SYNTAX	INTEGER {
			enable(1),
			disable(2)
			}
	ACCESS    read-write
	STATUS    mandatory
	DESCRIPTION     "Object to select loop and channel bilateral remote loop
			 for DC610 and DC612 only."
	::= { bqlConfigEntry 7 }

bqlInbandRTSDCD OBJECT-TYPE
	SYNTAX	INTEGER {
			enable(1),
			disable(2)
			}
	ACCESS    read-write
	STATUS    mandatory
	DESCRIPTION     "Object to select loop and channel in-band RTS/DCD
			 for DC610 and DC612 only."
	::= { bqlConfigEntry 8 }

bqlRTS  OBJECT-TYPE
	SYNTAX	INTEGER {
			normal(1),
			force(2)
			}
	ACCESS    read-write
	STATUS    mandatory
	DESCRIPTION     "Object to select loop and channel RTS
			 for DC610 and DC612 only."
	::= { bqlConfigEntry 9 }

bqlRTSCTSDelay OBJECT-TYPE
	SYNTAX	INTEGER {
			noDelay(1),
			delay(2)
			}
	ACCESS    read-write
	STATUS    mandatory
	DESCRIPTION     "Object to select loop and channel RTS/CTS delay
			 for DC610 and DC612 only."
	::= { bqlConfigEntry 10 }

bqlAntiStream OBJECT-TYPE
	SYNTAX	INTEGER {
			noAntistream(1),
			antistream(2)
			}
	ACCESS    read-write
	STATUS    mandatory
	DESCRIPTION     "Object to select loop and channel Anti-streaming
			 for DC610 and DC612 only."
	::= { bqlConfigEntry 11 }

bqlTXDataElasticBufr OBJECT-TYPE
	SYNTAX	INTEGER {
			enable(1),
			disable(2)
			}
	ACCESS    read-write
	STATUS    mandatory
	DESCRIPTION     "Object to select loop and channel transmit data
			 elastic buffer	for DC610 and DC612 only."
	::= { bqlConfigEntry 12 }

bqlRTSCTSDelayTime OBJECT-TYPE
	SYNTAX	INTEGER {
			ms0(1),
			ms5(2),
			ms10(3),
			ms15(4),
			ms20(5),
			ms25(6),
			ms30(7),
			ms35(8),
			ms40(9),
			ms45(10),
			ms50(11),
			ms55(12),
			ms60(13),
			ms65(14),
			ms70(15),
			ms75(16)
			}
	ACCESS    read-write
	STATUS    mandatory
	DESCRIPTION     "Object to select loop and channel RTS to CTS
			 delay time for DC610 and DC612 only."
	::= { bqlConfigEntry 13 }

bqlAntiStreamTime OBJECT-TYPE
	SYNTAX	INTEGER {
			seconds0(1),
			seconds5(2),
			seconds10(3),
			seconds15(4),
			seconds20(5),
			seconds25(6),
			seconds30(7),
			seconds35(8)
			}
	ACCESS    read-write
	STATUS    mandatory
	DESCRIPTION     "Object to select loop and channel anti-streaming
			 time for DC610 and DC612 only."
	::= { bqlConfigEntry 14 }

--******************************************************************************
--	CONFIGURATION 1 TABLE
--******************************************************************************
--
-- This table contains the network element's configuration information indexed by
-- SLDi.
--
-- This table uses SCinstance as SLDi where i is always 0.
--

bqlConfig1Table OBJECT-TYPE
	SYNTAX	SEQUENCE OF BqlConfig1Entry
	ACCESS  not-accessible
	STATUS  mandatory
	DESCRIPTION
		"The GDC SC616, DC610, DC612 2B1Q configuration 1 table."
	::= { bql 4 }

bqlConfig1Entry OBJECT-TYPE
	SYNTAX	BqlConfig1Entry
	ACCESS  not-accessible
	STATUS  mandatory
	DESCRIPTION
		"A listing of GDC 2B1Q SC616 options."
	INDEX	{ bqlConfig1Index }
	::= { bqlConfig1Table 1 }

BqlConfig1Entry ::=
	SEQUENCE        {
			bqlConfig1Index			SCinstance,
			bqlFrontPanel			INTEGER,
			bqlSoftHard			INTEGER,
		 	bqlDteStatus			OCTET STRING
			}

bqlConfig1Index OBJECT-TYPE
	SYNTAX  SCinstance
	ACCESS  read-only
	STATUS  mandatory
	DESCRIPTION
		"A unique index for the Configuration Table."
	::= { bqlConfig1Entry 1 }


bqlFrontPanel OBJECT-TYPE
	SYNTAX  INTEGER {
			enable(1),
			disable(2)
			}
	ACCESS    read-write
	STATUS    mandatory
	DESCRIPTION
			"Object used to enable or disable the units front panel
			 switches."
	::= { bqlConfig1Entry 2 }

bqlSoftHard OBJECT-TYPE
	SYNTAX  INTEGER {
			hardmode(1),
			softmode(2)
			}
	ACCESS    read-only
	STATUS    mandatory
	DESCRIPTION
			"Object used to read how the unit is configured."
	::= { bqlConfig1Entry 3 }

bqlDteStatus	OBJECT-TYPE	
	SYNTAX OCTET STRING (SIZE(2))
	ACCESS    read-only
	STATUS    mandatory
	DESCRIPTION
			"Object used to read the status of the DTE interface."
	::= { bqlConfig1Entry 4 }


--******************************************************************************
--	CONFIGURATION 2 TABLE
--******************************************************************************
--
-- This table contains the network element's configuration information indexed by
-- SLDi.
--
-- This table uses SCinstance as SLDi where i can be 1, 2, or 3.
--

bqlConfig2Table OBJECT-TYPE
	SYNTAX	SEQUENCE OF BqlConfig2Entry
	ACCESS  not-accessible
	STATUS  mandatory
	DESCRIPTION
		"The GDC SC616 2B1Q configuration 2 table."
	::= { bql 5 }

bqlConfig2Entry OBJECT-TYPE
	SYNTAX	BqlConfig2Entry
	ACCESS  not-accessible
	STATUS  mandatory
	DESCRIPTION
		"A listing of GDC 2B1Q SC616 options."
	INDEX	{ bqlConfig2Index }
	::= { bqlConfig2Table 1 }

BqlConfig2Entry ::=
	SEQUENCE   {
		   bqlConfig2Index	SCinstance,
                   bqlMasterTXClkSrc    INTEGER
		   }

bqlConfig2Index OBJECT-TYPE
	SYNTAX  SCinstance
	ACCESS  read-only
	STATUS  mandatory
	DESCRIPTION
		"A unique index for the Configuration Table."
	::= { bqlConfig2Entry 1 }

bqlMasterTXClkSrc OBJECT-TYPE
	SYNTAX  INTEGER {
			xtc1(1),
			xtc2(2)
			}
	ACCESS    read-write
	STATUS    mandatory
	DESCRIPTION
			"Object to option the Loop master transmit clock source. This is
			 for the SC616 only."
        ::= { bqlConfig2Entry 2 }


--*****************************************************************************
--                    DIAGNOSTICS TABLE
--*****************************************************************************
--
-- This table contains the network element's diagnostic test information indexed by
-- SLDi and channel.
--
-- This table uses SCinstance as SLDi where i can be 1, 2, or 3 and channel could 
-- be 1 or 2.

bqlDiagnosticTable OBJECT-TYPE
	SYNTAX	SEQUENCE OF BqlDiagnosticEntry
	ACCESS    not-accessible
	STATUS    mandatory
	DESCRIPTION
			"The GDC SC616 diagnostics table."
	::= { bql 6 }

bqlDiagnosticEntry OBJECT-TYPE
	SYNTAX	  BqlDiagnosticEntry
	ACCESS    not-accessible
	STATUS    mandatory
	DESCRIPTION
			"A listing of GDC SC616 diagnostic tests"
	INDEX	   { bqlDiagnosticIndex, bqlDiagnosticChnlIndex }
	::= { bqlDiagnosticTable 1 }

BqlDiagnosticEntry	::=
	SEQUENCE        {
			bqlDiagnosticIndex	SCinstance,
			bqlDiagnosticChnlIndex	INTEGER,
			bqlDiagnosticTest	INTEGER,
			bqlDiagnosticLength	INTEGER,
			bqlDiagnosticActive 	INTEGER,
			bqlDiagnosticResults	INTEGER
			}

bqlDiagnosticIndex OBJECT-TYPE
	SYNTAX    SCinstance
	ACCESS    read-only
	STATUS    mandatory
	DESCRIPTION
			"A unique index for the Diagnostic Table."
	::= { bqlDiagnosticEntry 1 }

bqlDiagnosticChnlIndex OBJECT-TYPE
	SYNTAX	INTEGER {
			channel1(1),
			channel2(2)
			}
	ACCESS	read-only
	STATUS  mandatory
	DESCRIPTION
		"A unique channel index for the Channel the test will run on."
	::= { bqlDiagnosticEntry 2 }

bqlDiagnosticTest OBJECT-TYPE
	SYNTAX  INTEGER (0..63)
	ACCESS	  read-write
	STATUS    mandatory
	DESCRIPTION
			"This function selects or reads the test.
			 0  = no test currently operating
			 1  = remote loopback test
			 2  = channel loopback test
			 4  = data loopback test 
			 8  = selftest
			 16 = line loopback test
			 32 = terminate test

			 All other values are test combinations such as
			 9 = selftest and remote loopback."

	::= { bqlDiagnosticEntry 3 }

bqlDiagnosticLength OBJECT-TYPE
	SYNTAX	INTEGER (0..127)
	ACCESS    read-write
	STATUS    mandatory
	DESCRIPTION
			"This function selects the test time length. Where 0
			 is test indefinitely and 1 to 127 are seconds."
	::= { bqlDiagnosticEntry 4 }

bqlDiagnosticActive OBJECT-TYPE
	SYNTAX  INTEGER {
			notActive (1),
			active (2)
			}
	ACCESS    read-only
	STATUS    mandatory
	DESCRIPTION
			"This function represents the test condition."
	::= { bqlDiagnosticEntry 5 }

bqlDiagnosticResults OBJECT-TYPE
	SYNTAX  INTEGER (0..16383)
	ACCESS    read-only
	STATUS    mandatory
	DESCRIPTION
			"This function reads the self test results in
			 bit errors."
	::= { bqlDiagnosticEntry 6 }


--********************************************************************************
--	ALARMS SC616 2B1Q - INDIVIDUALLY IDENTIFIED FOR THE CONTROLLER
--********************************************************************************

bqlSC616Alarm  OBJECT IDENTIFIER ::= { bql 7 }

bqlAlarmData OBJECT IDENTIFIER ::= { bqlSC616Alarm 1 }

-- no response alarm (this is a SCM generated alarm)
bqlNoResponseAlm OBJECT IDENTIFIER     			::= { bqlAlarmData 1 }

-- no diagnostic receive error alarm (this is a SCM generated alarm)
bqlDiagRxErrAlm OBJECT IDENTIFIER      			::= { bqlAlarmData 2 }

-- power up alarm
bqlPowerUpAlm OBJECT IDENTIFIER        			::= { bqlAlarmData 3 }

-- LOOP x 2B1Q out of sync alarm
bqlLp2B1QOutofSyncAlm OBJECT IDENTIFIER    		::= { bqlAlarmData 4 }

-- Loop x channel 1 elastic buffer over/underflow alarm
bqlLpChn1ElasBufrOverUnderFlowAlm OBJECT IDENTIFIER	::= { bqlAlarmData 5 }

-- Loop x channel 2 elastic buffer over/underflow alarm
bqlLpChn2ElasBufrOverUnderFlowAlm OBJECT IDENTIFIER	::= { bqlAlarmData 6 }

-- Loop x channel 1 external transmit clock absent alarm
bqlLpChn1ExtTxClkAlm OBJECT IDENTIFIER     		::= { bqlAlarmData 7 }

-- Loop x channel 2 external transmit clock absent alarm
bqlLpChn2ExtTxClkAlm OBJECT IDENTIFIER     		::= { bqlAlarmData 8 }

-- Loop x Sealing Current Non-Continuity
bqlLpSealingCurrentNoContinuityAlm OBJECT IDENTIFIER    ::= { bqlAlarmData 9 }


-- ALARM                             Maskable   Valid interfaces
-- ==============================================================
-- bqlNoResponseAlm                   no         unit            
-- bqlDiagRxErrAlm                    no         unit            
-- bqlPowerUpAlm                      no         unit            
-- bqlLp2B1QOutofSyncAlm              yes        loop 1,2,3            
-- bqlLpChn1ElasBufrOverUnderFlowAlm  yes        loop 1,2,3
-- bqlLpChn2ElasBufrOverUnderFlowAlm  yes        loop 1,2,3 
-- bqlLpChn1ExtTxClkAlm               yes        loop 1,2,3 
-- bqlLpChn2ExtTxClkAlm               yes        loop 1,2,3 
-- bqlLpSealingCurrentNoContinuityAlm yes	 loop 1,2,3


--*****************************************************************************
--                    SC616 LED STATUS
--*****************************************************************************
--
-- This table contains the SC616 front panel LED information indexed by
-- SLDi.
--
-- This table uses SCinstance as SLDi where i is always 0.
--

bqlSC616LEDStatusTable OBJECT-TYPE
	SYNTAX	SEQUENCE OF BqlSC616LEDEntry
	ACCESS  not-accessible
	STATUS  mandatory
	DESCRIPTION
			"The GDC SC616 LED Status Table."
	::= { bql 8 }

bqlSC616LEDEntry OBJECT-TYPE
	SYNTAX	BqlSC616LEDEntry
	ACCESS  not-accessible
	STATUS  mandatory
	DESCRIPTION
			"An entry in the GDC SC616 LED Status table."
	INDEX	{ bqlSC616LEDIndex }
	::= { bqlSC616LEDStatusTable 1 }

BqlSC616LEDEntry ::=
	SEQUENCE  {
		  bqlSC616LEDIndex		SCinstance,
		  bqlSC616LEDStatus		OCTET STRING
		  }

bqlSC616LEDIndex OBJECT-TYPE
	SYNTAX  SCinstance
	ACCESS  read-only
	STATUS  mandatory
	DESCRIPTION
	       "This object is the index of the SC616 LED Status table."
	::= { bqlSC616LEDEntry 1 }

bqlSC616LEDStatus OBJECT-TYPE
	SYNTAX	OCTET STRING (SIZE (3))
	ACCESS  read-only
	STATUS  mandatory
	DESCRIPTION
			"The GDC SC616 front panel LED Status.
			 A value of 1 means on, 0 is off.
			 byte 1 bit 7 (1.7) - not used
			 1.6 - test mode
			 1.5 - alarm on
			 1.4 - loop 1 line loopback
			 1.3 - loop 1 channel 1 send data transitions
			 1.2 - loop 1 channel 1 receive data transitions
			 1.1 - loop 1 channel 2 send data transitions
			 1.0 - loop 1 channel 2 receive data transitions

			 2.7 - not used
			 2.6 - not used
			 2.5 - not used
			 2.4 - loop 2 line loopback
			 2.3 - loop 2 channel 1 send data transitions
			 2.2 - loop 2 channel 1 receive data transitions
			 2.1 - loop 2 channel 2 send data transitions
			 2.0 - loop 2 channel 2 receive data transitions

			 3.7 - not used
			 3.6 - not used
			 3.5 - not used
			 3.4 - loop 3 line loopback
			 3.3 - loop 3 channel 1 send data transitions
			 3.2 - loop 3 channel 1 receive data transitions
			 3.1 - loop 3 channel 2 send data transitions
			 3.0 - loop 3 channel 2 receive data transitions"

			
	::= { bqlSC616LEDEntry 2 }


--********************************************************************************
--	ALARMS DC610 2B1Q - INDIVIDUALLY IDENTIFIED FOR THE CONTROLLER
--********************************************************************************

bqlDC610Alarm  OBJECT IDENTIFIER ::= { bql 9 }

bqlDC610AlarmData OBJECT IDENTIFIER ::= { bqlDC610Alarm 1 }

-- power up alarm
bqlDC610PowerUpAlm OBJECT IDENTIFIER    	::= { bqlDC610AlarmData 1 }

-- channel 1 DTR absent alarm
bqlDC610Chnl1DTRAlm OBJECT IDENTIFIER    	::= { bqlDC610AlarmData 2 }
bqlDC610NoResponseAlm OBJECT IDENTIFIER  ::= { bqlDC610AlarmData 3 }
bqlDC610DiagRxErrAlm OBJECT IDENTIFIER   ::= { bqlDC610AlarmData 4 }



-- ALARM                             Maskable   Valid interfaces
-- ==============================================================
-- bqlDC610PowerUpAlm                no         unit            
-- bqlDC610Chnl1DTRAlm               yes        unit            
-- bqlDC610NoResponseAlm             no         unit
-- bqlDC610DiagRxErrAlm              no         unit


--*****************************************************************************
--                    DC610 LED STATUS
--*****************************************************************************
--
-- This table contains the DC610 front panel LED information indexed by
-- SLDi.
--
-- This table uses SCinstance as SLDi where i is always 0.
--

bqlDC610LEDStatusTable OBJECT-TYPE
	SYNTAX	SEQUENCE OF BqlDC610LEDEntry
	ACCESS  not-accessible
	STATUS  mandatory
	DESCRIPTION
			"The GDC DC610 LED Status Table."
	::= { bql 10 }

bqlDC610LEDEntry OBJECT-TYPE
	SYNTAX	BqlDC610LEDEntry
	ACCESS  not-accessible
	STATUS  mandatory
	DESCRIPTION
			"An entry in the GDC DC610 LED Status table."
	INDEX	{ bqlDC610LEDIndex }
	::= { bqlDC610LEDStatusTable 1 }

BqlDC610LEDEntry ::=
	SEQUENCE  {
		  bqlDC610LEDIndex		SCinstance,
		  bqlDC610LEDStatus		OCTET STRING
		  }

bqlDC610LEDIndex OBJECT-TYPE
	SYNTAX  SCinstance
	ACCESS  read-only
	STATUS  mandatory
	DESCRIPTION
	       "This object is the index of the DC610 LED Status table."
	::= { bqlDC610LEDEntry 1 }

bqlDC610LEDStatus OBJECT-TYPE
	SYNTAX	OCTET STRING (SIZE (1))
	ACCESS  read-only
	STATUS  mandatory
	DESCRIPTION
			"The GDC DC610 front panel LED Status.
			 A value of 1 means on, 0 is off.
			 byte 1 bit 7 (1.7) - not used
			 1.6 - test mode
			 1.5 - sync
			 1.4 - request to send
			 1.3 - clear to send
			 1.2 - carrier on
			 1.1 - send data transitions
			 1.0 - receive data transitions"

			
	::= { bqlDC610LEDEntry 2 }


--********************************************************************************
--	ALARMS DC612 2B1Q - INDIVIDUALLY IDENTIFIED FOR THE CONTROLLER
--********************************************************************************

bqlDC612Alarm  OBJECT IDENTIFIER ::= { bql 11 }

bqlDC612AlarmData OBJECT IDENTIFIER ::= { bqlDC612Alarm 1 }

-- power up alarm
bqlDC612PowerUpAlm OBJECT IDENTIFIER    	::= { bqlDC612AlarmData 1 }

-- channel 1 DTR absent alarm
bqlDC612Chnl1DTRAlm OBJECT IDENTIFIER    	::= { bqlDC612AlarmData 2 }

-- channel 2 DTR absent alarm
bqlDC612Chnl2DTRAlm OBJECT IDENTIFIER    	::= { bqlDC612AlarmData 3 }
bqlDC612NoResponseAlm OBJECT IDENTIFIER  ::= { bqlDC612AlarmData 4 }
bqlDC612DiagRxErrAlm OBJECT IDENTIFIER   ::= { bqlDC612AlarmData 5 }



-- ALARM                             Maskable   Valid interfaces
-- ==============================================================
-- bqlDC612PowerUpAlm                no         unit            
-- bqlDC612Chnl1DTRAlm               yes        unit            
-- bqlDC612Chnl2DTRAlm               yes        unit            
-- bqlDC612NoResponseAlm             no         unit
-- bqlDC612DiagRxErrAlm              no         unit


--*****************************************************************************
--                    DC612 LED STATUS
--*****************************************************************************
--
-- This table contains the DC612 front panel LED information indexed by
-- SLDi.
--
-- This table uses SCinstance as SLDi where i is always 0.
--

bqlDC612LEDStatusTable OBJECT-TYPE
	SYNTAX	SEQUENCE OF BqlDC612LEDEntry
	ACCESS  not-accessible
	STATUS  mandatory
	DESCRIPTION
			"The GDC DC612 LED Status Table."
	::= { bql 12 }

bqlDC612LEDEntry OBJECT-TYPE
	SYNTAX	BqlDC612LEDEntry
	ACCESS  not-accessible
	STATUS  mandatory
	DESCRIPTION
			"An entry in the GDC DC612 LED Status table."
	INDEX	{ bqlDC612LEDIndex }
	::= { bqlDC612LEDStatusTable 1 }

BqlDC612LEDEntry ::=
	SEQUENCE  {
		  bqlDC612LEDIndex		SCinstance,
		  bqlDC612LEDStatus		OCTET STRING
		  }

bqlDC612LEDIndex OBJECT-TYPE
	SYNTAX  SCinstance
	ACCESS  read-only
	STATUS  mandatory
	DESCRIPTION
	       "This object is the index of the DC612 LED Status table."
	::= { bqlDC612LEDEntry 1 }

bqlDC612LEDStatus OBJECT-TYPE
	SYNTAX	OCTET STRING (SIZE (3))
	ACCESS  read-only
	STATUS  mandatory
	DESCRIPTION
			"The GDC DC612 front panel LED Status.
			 A value of 1 means on, 0 is off.
			 byte 1 bit 7 (1.7) - not used
			 1.6 - not used
			 1.5 - not used
			 1.4 - not used
			 1.3 - not used
			 1.2 - not used
			 1.1 - channel 1 selected for front panel pushbutton operation
			 1.0 - channel 2 selected for front panel pushbutton operation

			 2.7 - not used
			 2.6 - channel 1 test mode
			 2.5 - channel 1 sync
			 2.4 - channel 1 request to send
		         2.3 - channel 1 clear to send
			 2.2 - channel 1 carrier on
			 2.1 - channel 1 send data transitions
			 2.0 - channel 1 receive data transitions

			 3.7 - not used
			 3.6 - channel 2 test mode
			 3.5 - channel 2 sync
			 3.4 - channel 2 request to send
		         3.3 - channel 2 clear to send
			 3.2 - channel 2 carrier on
			 3.1 - channel 2 send data transitions
			 3.0 - channel 2 receive data transitionscd"
			
	::= { bqlDC612LEDEntry 2 }


--*****************************************************************************
--		      CONTROL TABLE FOR 2B1Q SC616 DC610 DC612
--*****************************************************************************
--
-- This table contains the SC616, DC610, DC612 control functions indexed by
-- SLDi.
--
-- This table uses SCinstance as SLDi where i is always 0.
--

bqlControlTable OBJECT-TYPE
	SYNTAX	SEQUENCE OF BqlControlEntry
	ACCESS  not-accessible
	STATUS  mandatory
	DESCRIPTION
			"The GDC SC616 Control Table."
	::= { bql 13 }

bqlControlEntry OBJECT-TYPE
	SYNTAX	BqlControlEntry
	ACCESS  not-accessible
	STATUS  mandatory
	DESCRIPTION
			"An entry in the GDC SC616 Control table."
	INDEX	{ bqlControlIndex }
	::= { bqlControlTable 1 }

BqlControlEntry ::=
	SEQUENCE {
		  bqlControlIndex	SCinstance,
		  bqlSoftReset		INTEGER,
		  bqlEraseConfig	INTEGER
		  }

bqlControlIndex OBJECT-TYPE
	SYNTAX  SCinstance
	ACCESS  read-only
	STATUS  mandatory
	DESCRIPTION
	       "This object is the identifier of the SC616 Control table."
	::= { bqlControlEntry 1 }

bqlSoftReset OBJECT-TYPE
	SYNTAX  INTEGER  {
			 normal(1),
			 reset(2)
			 }
        ACCESS  read-write
	STATUS  mandatory
	DESCRIPTION
                "Forces a soft reset on the network element.
                 The reset selection is write only. The normal
                 selection is read only."
	::= { bqlControlEntry 2 }

bqlEraseConfig OBJECT-TYPE
	SYNTAX  INTEGER  {
			 normal(1),
			 erase(2)
			 }
        ACCESS  read-write
	STATUS  mandatory
	DESCRIPTION
		"Forces an erase of the stored configuration in the
                 network element. The erase selection is write only.
                 The normal selection is read only."
	::= { bqlControlEntry 3 }


--*****************************************************************************
--           STATISTICS TABLE - CURRENT 15 MINUTE INTERVAL TABLE
--*****************************************************************************
--
-- The SC616 current table contains various statistics being
-- collected for the current 15 minute interval.
-- It is indexed by SLDi.
--
-- This table uses SCinstance as SLDi where i is Loop 1, 2, or 3.
--

bqlCurrentTable OBJECT-TYPE
             SYNTAX  SEQUENCE OF BqlCurrentEntry
             ACCESS  not-accessible
             STATUS  mandatory
             DESCRIPTION
                "The SC616 Current table."
            ::= { bql 14 }

bqlCurrentEntry OBJECT-TYPE
             SYNTAX  BqlCurrentEntry
             ACCESS  not-accessible
             STATUS  mandatory
             DESCRIPTION
                "An entry in the SC616 Current table."
            INDEX   { bqlCurrentIndex }
            ::= { bqlCurrentTable 1 }

BqlCurrentEntry ::=
         SEQUENCE {
                  bqlCurrentIndex	SCinstance,
                  bqlCurrentESs         Gauge,
                  bqlCurrentBESs	Gauge,
                  bqlCurrentSESs	Gauge,
                  bqlCurrentUASs	Gauge,
		  bqlCurrentStats 	OCTET STRING
         	  }

bqlCurrentIndex OBJECT-TYPE
             SYNTAX  SCinstance
             ACCESS  read-only
             STATUS  mandatory
             DESCRIPTION
                "The index value which uniquely identifies  the
                SC616 DC610 or DC612 interface to which this entry
		is applicable."
            ::= { bqlCurrentEntry 1 }

bqlCurrentESs OBJECT-TYPE
             SYNTAX  Gauge
             ACCESS  read-only
             STATUS  mandatory
             DESCRIPTION
                "The number of Errored Seconds, encountered  by
                an ISDN interface in the current 15 minute interval.
		This is defined as a second with at least one
                CRC error event or one or more out of frames (OOF)."
            ::= { bqlCurrentEntry 2 }

bqlCurrentBESs OBJECT-TYPE
             SYNTAX Gauge
             ACCESS read-only
             STATUS mandatory
             DESCRIPTION
                "The number of Bursty  Errored  Seconds  (BESs)
                encountered  by  an ISDN interface in the current
                15 minute interval.
		This is defined as a second with more than one but
                less than 640 CRC error events."
            ::= {bqlCurrentEntry 3 }

bqlCurrentSESs OBJECT-TYPE
             SYNTAX  Gauge
             ACCESS  read-only
             STATUS  mandatory
             DESCRIPTION
                "The number of Severely Errored Seconds encoun-
                tered  by  an ISDN interface  in the current 15
                minute interval.
		This is defined as a second with 640 or more CRC
		error events or one or more out of frames (OOF)."
            ::= { bqlCurrentEntry 4 }


bqlCurrentUASs OBJECT-TYPE
             SYNTAX  Gauge
             ACCESS  read-only
             STATUS  mandatory
             DESCRIPTION
                "The number of Unavailable Seconds  encountered
                by an ISDN interface in the current 15 minute interval.
		This is a count of one-second intervals during which 
		service is not available."
            ::= { bqlCurrentEntry 5 }

bqlCurrentStats OBJECT-TYPE
             SYNTAX  OCTET STRING (SIZE(12))
             ACCESS  read-only
             STATUS  mandatory
             DESCRIPTION
                "The number of ES, BES, ESE and UAS encountered
                by an ISDN interface in the current 15 minute interval.
		This is a count of one-second intervals during which 
		service is not available."
            ::= { bqlCurrentEntry 6 }

--*****************************************************************************
--           STATISTICS TABLE - 15 MINUTE INTERVAL TABLE
--*****************************************************************************
--
-- The SC616 Interval Table contains various statistics
-- collected by each ISDN Interface over the previous 24 hours of
-- operation.  The past 24 hours are broken into 96 completed
-- 15 minute intervals. This table is indexed by SLDi and IntervalNumber.
--
-- This table uses SCinstance as SLDi where i can be 1, 2, or 3 and IntervalNumber
-- is a number between 1 and 96. Where 1 is the most recently completed 15 minute
-- interval and 96 is the least recently completed 15 minute interval.
--

bqlIntervalTable OBJECT-TYPE
             SYNTAX  SEQUENCE OF BqlIntervalEntry
             ACCESS  not-accessible
             STATUS  mandatory
             DESCRIPTION
                "The SC616 Interval table."
            ::= { bql 15 }

bqlIntervalEntry OBJECT-TYPE
             SYNTAX  BqlIntervalEntry
             ACCESS  not-accessible
             STATUS  mandatory
             DESCRIPTION
                "An entry in the SC616 Interval table."
            INDEX   { bqlIntervalIndex, bqlIntervalNumber }
            ::= { bqlIntervalTable 1 }

BqlIntervalEntry ::=
         SEQUENCE {
                  bqlIntervalIndex	SCinstance,
                  bqlIntervalNumber	INTEGER,
                  bqlIntervalESs	Gauge,
                  bqlIntervalBESs	Gauge,
                  bqlIntervalSESs	Gauge,
                  bqlIntervalUASs	Gauge,
                  bqlIntervalStats	OCTET STRING
	          }

bqlIntervalIndex OBJECT-TYPE
             SYNTAX  SCinstance
             ACCESS  read-only
             STATUS  mandatory
             DESCRIPTION
                "The index value which uniquely identifies  the
                ISDN  interface  to which this entry is applicable."
            ::= { bqlIntervalEntry 1 }

bqlIntervalNumber OBJECT-TYPE
             SYNTAX  INTEGER (1..96)
             ACCESS  read-only
             STATUS  mandatory
             DESCRIPTION
                "A number between 1 and 96, where 1 is the most
                recently completed 15 minute interval and 96 is
                the least recently completed 15 minute  inter-
                val   (assuming   that  all  96  intervals  are
                valid)."
            ::= { bqlIntervalEntry 2 }

bqlIntervalESs OBJECT-TYPE
             SYNTAX  Gauge
             ACCESS  read-only
             STATUS  mandatory
             DESCRIPTION
                "The number of Errored Seconds encountered by a
                DS1  interface in one of the previous 96,
                individual 15 minute, intervals.
		This is defined as a second with at least one
                CRC error event or one or more out of frames (OOF)."
            ::= { bqlIntervalEntry 3 }

bqlIntervalBESs OBJECT-TYPE
             SYNTAX Gauge
             ACCESS read-only
             STATUS mandatory
             DESCRIPTION
                "The number of Bursty  Errored  Seconds  (BESs)
                encountered  by  an ISDN interface in one of the
                previous 96, individual 15 minute, intervals.
		This is defined as a second with more than one but
                less than 640 CRC error events."
            ::= {bqlIntervalEntry 4 }

bqlIntervalSESs OBJECT-TYPE
             SYNTAX  Gauge
             ACCESS  read-only
             STATUS  mandatory
             DESCRIPTION
                "The number of Severely Errored Seconds encoun-
                tered by an ISDN interface in one of the previous
                96, individual 15 minute, intervals.
		This is defined as a second with 640 or more CRC
		error events or one or more out of frames (OOF)."
            ::= { bqlIntervalEntry 5 }

bqlIntervalUASs OBJECT-TYPE
             SYNTAX  Gauge
             ACCESS  read-only
             STATUS  mandatory
             DESCRIPTION
                "The number of Unavailable Seconds  encountered
                by  an ISDN interface in one of the previous 96,
                individual 15 minute, intervals.
		This is a count of one-second intervals during which 
		service is not available."
            ::= { bqlIntervalEntry 6 }

bqlIntervalStats OBJECT-TYPE
             SYNTAX  OCTET STRING (SIZE(12))
             ACCESS  read-only
             STATUS  mandatory
             DESCRIPTION
                "The number of ES, BES, SES, and UAS encountered
                by  an ISDN interface in one of the previous 96,
                individual 15 minute, intervals.
		This is a count of one-second intervals during which 
		service is not available."
            ::= { bqlIntervalEntry 7 }


--*****************************************************************************
--           STATISTICS TABLE - TOTAL OF INTERVALS TABLE
--*****************************************************************************
--
-- The SC616 Total Table contains the cumulative sum of the
-- various statistics for the 24 hour period preceding the
-- current interval. It is indexed by SLDi.
--
-- This table uses SCinstance as SLDi where i is Loop 1, 2, or 3.
--

bqlTotalTable OBJECT-TYPE
             SYNTAX  SEQUENCE OF BqlTotalEntry
             ACCESS  not-accessible
             STATUS  mandatory
             DESCRIPTION
                "The SC616 Total table.  24 hour interval."
            ::= { bql 16 }

bqlTotalEntry OBJECT-TYPE
             SYNTAX  BqlTotalEntry
             ACCESS  not-accessible
             STATUS  mandatory
             DESCRIPTION
                "An entry in the SC616 Total table."
            INDEX   { bqlTotalIndex }
            ::= { bqlTotalTable 1 }

BqlTotalEntry ::=
         SEQUENCE {
                  bqlTotalIndex	SCinstance,
                  bqlTotalESs	Gauge,
                  bqlTotalBESs	Gauge,
             	  bqlTotalSESs	Gauge,
                  bqlTotalUASs	Gauge,
		  bqlTotalStats OCTET STRING
         	  }

bqlTotalIndex OBJECT-TYPE
             SYNTAX  SCinstance
             ACCESS  read-only
             STATUS  mandatory
             DESCRIPTION
                "The index value which uniquely identifies  the
                ISDN interface  to which this entry is applicable."
            ::= { bqlTotalEntry 1 }

bqlTotalESs OBJECT-TYPE
             SYNTAX  Gauge
             ACCESS  read-only
             STATUS  mandatory
             DESCRIPTION
                "The number of Errored Seconds encountered by an
                ISDN interface in the previous 24 hour interval.
		This is defined as a second with at least one
                CRC error event or one or more out of frames (OOF)."
            ::= { bqlTotalEntry 2 }

bqlTotalBESs OBJECT-TYPE
             SYNTAX Gauge
             ACCESS read-only
             STATUS mandatory
             DESCRIPTION
                "The number of Bursty  Errored  Seconds  (BESs)
                encountered  by an ISDN interface in the previous
                24 hour interval.
		This is defined as a second with more than one but
                less than 640 CRC error events."
            ::= { bqlTotalEntry 3 }

bqlTotalSESs OBJECT-TYPE
             SYNTAX  Gauge
             ACCESS  read-only
             STATUS  mandatory
             DESCRIPTION
                "The number of Severely Errored Seconds encoun-
                tered  by  an ISDN interface in the previous 24
                hour interval.
		This is defined as a second with 640 or more CRC
		error events or one or more out of frames (OOF)."
            ::= { bqlTotalEntry 4 }

bqlTotalUASs OBJECT-TYPE
             SYNTAX  Gauge
             ACCESS  read-only
             STATUS  mandatory
             DESCRIPTION
                "The number of Unavailable Seconds  encountered
                by  an ISDN interface in the previous 24 hour interval.
		This is a count of one-second intervals during which 
		service is not available."
            ::= { bqlTotalEntry 5 }

bqlTotalStats OBJECT-TYPE
             SYNTAX  OCTET STRING (SIZE(12))
             ACCESS  read-only
             STATUS  mandatory
             DESCRIPTION
                "The number of ES, BES, SES and UAS encountered
                by  an ISDN interface in the previous 24 hour interval.
		This is a count of one-second intervals during which 
		service is not available."
            ::= { bqlTotalEntry 6 }

--*****************************************************************************
--            DTE RATE TABLE FOR DC610, DC612 
--*****************************************************************************
--
-- This table contains the DC610, DC612 channel mapped and data rate
-- functions indexed by SLDi.
--
-- This table uses SCinstance as SLDi. Where i is always 2 or 3.
--

bqlDTERateTable OBJECT-TYPE
             SYNTAX  SEQUENCE OF BqlDTEEntry
             ACCESS  not-accessible
             STATUS  mandatory
             DESCRIPTION
                "The DC610 DC612 DTE rate table."
            ::= { bql 17 }

bqlDTEEntry OBJECT-TYPE
             SYNTAX  BqlDTEEntry
             ACCESS  not-accessible
             STATUS  mandatory
             DESCRIPTION
                "An entry in the DC610 DC612 table."
            INDEX   { bqlDTEIndex }
            ::= { bqlDTERateTable 1 }

BqlDTEEntry ::=
         SEQUENCE {
                  bqlDTEIndex		SCinstance,
                  bqlDTE2Mapped         INTEGER,
                  bqlDTE2DataRate	INTEGER,
                  bqlDTE1Mapped         INTEGER,
                  bqlDTE1DataRate	INTEGER
         	  }

bqlDTEIndex OBJECT-TYPE
             SYNTAX  SCinstance
             ACCESS  read-only
             STATUS  mandatory
             DESCRIPTION
                "The index value which uniquely identifies  the
                 DC610 DC612 interface  to which this entry is
		 applicable."
            ::= { bqlDTEEntry 1 }

bqlDTE2Mapped OBJECT-TYPE
	SYNTAX  INTEGER  {
			 toChannel2(1),
			 toChannel1(2)
			 }
	ACCESS  read-write
	STATUS  mandatory
	DESCRIPTION
	   "Forces a DC612 to map DTE channel 2 into channel 2 or channel 1."
	::= { bqlDTEEntry 2 }

bqlDTE2DataRate OBJECT-TYPE
	SYNTAX  INTEGER  {
			 kBps2400(1),
			 kBps4800(2),
			 kBps9600(3),
			 kBps19200(4),
			 kBps38400(5),
			 kBps48000(6),
			 kBps56000(7),
			 kBps57600(8),
			 kBps64000(9),
			 kBps128000(10)
			 }
	ACCESS  read-write
	STATUS  mandatory
	DESCRIPTION
	   "Forces a DC612 DTE channel 2 to a K bit per second rate."
	::= { bqlDTEEntry 3 }

bqlDTE1Mapped OBJECT-TYPE
	SYNTAX  INTEGER  {
			 toChannel1(1),
			 toChannel2(2)
			 }
	ACCESS  read-write
	STATUS  mandatory
	DESCRIPTION
	   "Forces a DC610 or DC612 to map DTE channel 1 into channel 1 or channel 2."
	::= { bqlDTEEntry 4 }

bqlDTE1DataRate OBJECT-TYPE
	SYNTAX  INTEGER  {
			 kBps2400(1),
			 kBps4800(2),
			 kBps9600(3),
			 kBps19200(4),
			 kBps38400(5),
			 kBps48000(6),
			 kBps56000(7),
			 kBps57600(8),
			 kBps64000(9),
			 kBps128000(10)
			 }
	ACCESS  read-write
	STATUS  mandatory
	DESCRIPTION
	   "Forces a DC610 or DC612 DTE channel 1 to a K bit per second rate."
	::= { bqlDTEEntry 5 }


--*****************************************************************************
--            LOOP Performance Interval Maintenance Table FOR SC616,DC610, DC612 
--*****************************************************************************
bqlIntervalMaintenanceTable OBJECT-TYPE
     	SYNTAX SEQUENCE OF BqlIntervalMaintenanceEntry
     	ACCESS not-accessible
     	STATUS mandatory
    	DESCRIPTION
     		"The SC616, DC610, DC612 Loop Interval  Maintenance table. "
         ::= { bql 18 }
 	
bqlIntervalMaintenanceEntry OBJECT-TYPE
 	SYNTAX BqlIntervalMaintenanceEntry
     	ACCESS not-accessible
     	STATUS mandatory
     	DESCRIPTION
     		"The SC616, DC610, DC612 Interval Maintenance table entry. "
     	INDEX { bqlIntervalMaintenanceIndex }
     	::= { bqlIntervalMaintenanceTable 1 }
 
BqlIntervalMaintenanceEntry ::= 
     	SEQUENCE {
     	    	 bqlIntervalMaintenanceIndex SCinstance,
         	 bqlResetIntervals           INTEGER,
		 bqlNumberofValidIntervals   INTEGER
     		 }
 
bqlIntervalMaintenanceIndex OBJECT-TYPE
     	SYNTAX SCinstance
     	ACCESS read-only
     	STATUS mandatory
     	DESCRIPTION
     		"The index value which uniquely identifies the interface to
     		which this entry is applicable.  This has the form of a
     		SCinstance which defines the slot, line, drop, and interface,
     		which in this case is a Loop interface."
     	::= { bqlIntervalMaintenanceEntry 1 }  

bqlResetIntervals OBJECT-TYPE
     	SYNTAX INTEGER {
     		       norm(1),
     		       reset(2)	
     		       }
     	ACCESS read-write 
     	STATUS mandatory
        DESCRIPTION " This variable is used to reset Loop performance intervals.
 		      When it is set to reset, the Loop performance tables are
 		      reset to zero."
     	::= { bqlIntervalMaintenanceEntry 2 }

bqlNumberofValidIntervals OBJECT-TYPE
     	SYNTAX INTEGER (0..96)
     	ACCESS read-only 
     	STATUS mandatory
        DESCRIPTION " This variable is used to read the number of intervals collected.
		      Each interval is an increment of 15 minutes."
     	::= { bqlIntervalMaintenanceEntry 3 }


--*****************************************************************************
--                NZ    DC610 NZ LED STATUS
--*****************************************************************************
--
-- This table contains the DC610 front panel LED information indexed by
-- SLDi.
--
-- This table uses SCinstance as SLDi where i is always 0.
--

bqlDC610LEDStatusNZTable OBJECT-TYPE
	SYNTAX	SEQUENCE OF BqlDC610LEDNZEntry
	ACCESS  not-accessible
	STATUS  mandatory
	DESCRIPTION
			"The GDC DC610NZ LED Status Table."
	::= { bql 19 }

bqlDC610LEDNZEntry OBJECT-TYPE
	SYNTAX	BqlDC610LEDNZEntry
	ACCESS  not-accessible
	STATUS  mandatory
	DESCRIPTION
			"An entry in the GDC DC610NZ LED Status table."
	INDEX	{ bqlDC610LEDNZIndex }
	::= { bqlDC610LEDStatusNZTable 1 }

BqlDC610LEDNZEntry ::=
	SEQUENCE  {
		  bqlDC610LEDNZIndex		SCinstance,
		  bqlDC610LEDNZStatus		OCTET STRING
		  }

bqlDC610LEDNZIndex OBJECT-TYPE
	SYNTAX  SCinstance
	ACCESS  read-only
	STATUS  mandatory
	DESCRIPTION
	       "This object is the index of the DC610 LED Status table."
	::= { bqlDC610LEDNZEntry 1 }


bqlDC610LEDNZStatus OBJECT-TYPE
	SYNTAX	OCTET STRING (SIZE (1))
	ACCESS  read-only
	STATUS  mandatory
	DESCRIPTION
			"The GDC DC610NZ front panel LED Status.
			 A value of 1 means on, 0 is off.
			 byte 1 bit 7 (1.7) - not used
			 1.6 - test mode
			 1.5 - 128K (sync )
			 1.4 - request to send
			 1.3 - clear to send
			 1.2 - network available (carrier on)
			 1.1 - send data transitions
			 1.0 - receive data transitions"
			
	::= { bqlDC610LEDNZEntry 2 }

--********************************************************************************
--	ALARMS GT 128  - INDIVIDUALLY IDENTIFIED FOR THE CONTROLLER
--********************************************************************************

bqlGT128Alarm  OBJECT IDENTIFIER         ::= { bql 20 }
bqlGT128AlarmData OBJECT IDENTIFIER      ::= { bqlGT128Alarm 1 }
bqlGT128NoResponseAlm OBJECT IDENTIFIER  ::= { bqlGT128AlarmData 1 }
bqlGT128DiagRxErrAlm OBJECT IDENTIFIER   ::= { bqlGT128AlarmData 2 }
bqlGT128PowerUpAlm OBJECT IDENTIFIER     ::= { bqlGT128AlarmData 3 }
bqlGT128Chnl1DTRAlm OBJECT IDENTIFIER    ::= { bqlGT128AlarmData 4 }

-- ALARM                             Maskable   Valid interfaces
-- ==============================================================
-- bqlGT128NoResponseAlm             no         unit            
-- bqlGT128DiagRxErrAlm              no         unit            
-- bqlGT128PowerUpAlm                no         unit            
-- bqlGT128Chnl1DTRAlm               yes        unit  


--*****************************************************************************
--                    GT 128 LED STATUS
--*****************************************************************************
--
-- This table contains the GT 128 front panel LED information indexed by
-- SLDi.
--
-- This table uses SCinstance as SLDi where i is always 0.
--

bqlGT128LEDStatusTable OBJECT-TYPE
	SYNTAX	SEQUENCE OF BqlGT128LEDEntry
	ACCESS  not-accessible
	STATUS  mandatory
	DESCRIPTION
			"The GDC GT 128 LED Status Table."
	::= { bql 21 }

bqlGT128LEDEntry OBJECT-TYPE
	SYNTAX	BqlGT128LEDEntry
	ACCESS  not-accessible
	STATUS  mandatory
	DESCRIPTION
			"An entry in the GDC GT128 LED Status table."
	INDEX	{ bqlGT128LEDIndex }
	::= { bqlGT128LEDStatusTable 1 }

BqlGT128LEDEntry ::=
	SEQUENCE  {
		  bqlGT128LEDIndex		SCinstance,
		  bqlGT128LEDStatus		OCTET STRING
		  }

bqlGT128LEDIndex OBJECT-TYPE
	SYNTAX  SCinstance
	ACCESS  read-only
	STATUS  mandatory
	DESCRIPTION
	       "This object is the index of the GT 128 LED Status table."
	::= { bqlGT128LEDEntry 1 }

bqlGT128LEDStatus OBJECT-TYPE
	SYNTAX	OCTET STRING (SIZE (2))
	ACCESS  read-only
	STATUS  mandatory
	DESCRIPTION
			"The GDC GT128 front panel LED Status.
			 A value of 1 means on, 0 is off.
			 byte 1 bit 7 (1.7) - not used
			 1.6 - test mode
			 1.5 - sync
			 1.4 - request to send
			 1.3 - clear to send
			 1.2 - carrier on
			 1.1 - send data transitions
			 1.0 - receive data transitions

			 2.6 - fu
			 2.5 - fu
			 2.4 - fu
			 2.3 - fu
			 2.2 - remote loopback ON
			 2.1 - selftest ON
			 2.0 - line loopback ON"
			
	::= { bqlGT128LEDEntry 2 }


--********************************************************************************
--	ALARMS NZ GT 128 NZ  - INDIVIDUALLY IDENTIFIED FOR THE CONTROLLER
--********************************************************************************

bqlGT128NZAlarm  OBJECT IDENTIFIER         ::= { bql 22 }
bqlGT128NZAlarmData OBJECT IDENTIFIER      ::= { bqlGT128NZAlarm 1 }
bqlGT128NZNoResponseAlm OBJECT IDENTIFIER  ::= { bqlGT128NZAlarmData 1 }
bqlGT128NZDiagRxErrAlm OBJECT IDENTIFIER   ::= { bqlGT128NZAlarmData 2 }
bqlGT128NZPowerUpAlm OBJECT IDENTIFIER     ::= { bqlGT128NZAlarmData 3 }
bqlGT128NZChnl1DTRAlm OBJECT IDENTIFIER    ::= { bqlGT128NZAlarmData 4 }

-- ALARM                             Maskable   Valid interfaces
-- ==============================================================
-- bqlGT128NZNoResponseAlm             no         unit            
-- bqlGT128NZDiagRxErrAlm              no         unit            
-- bqlGT128NZPowerUpAlm                no         unit            
-- bqlGT128NZChnl1DTRAlm               yes        unit  

--*****************************************************************************
--                 NZ   GT 128 NZ LED STATUS
--*****************************************************************************
--
-- This table contains the GT 128 NZ front panel LED information indexed by
-- SLDi.
--
-- This table uses SCinstance as SLDi where i is always 0.
--

bqlGT128LEDNZStatusTable OBJECT-TYPE
	SYNTAX	SEQUENCE OF BqlGT128LEDNZEntry
	ACCESS  not-accessible
	STATUS  mandatory
	DESCRIPTION
			"The GDC GT 128 NZ LED Status Table."
	::= { bql 23 }

bqlGT128LEDNZEntry OBJECT-TYPE
	SYNTAX	BqlGT128LEDNZEntry
	ACCESS  not-accessible
	STATUS  mandatory
	DESCRIPTION
			"An entry in the GDC GT128 NZ LED Status table."
	INDEX	{ bqlGT128LEDNZIndex }
	::= { bqlGT128LEDNZStatusTable 1 }

BqlGT128LEDNZEntry ::=
	SEQUENCE  {
		  bqlGT128LEDNZIndex		SCinstance,
		  bqlGT128LEDNZStatus		OCTET STRING
		  }

bqlGT128LEDNZIndex OBJECT-TYPE
	SYNTAX  SCinstance
	ACCESS  read-only
	STATUS  mandatory
	DESCRIPTION
	       "This object is the index of the GT 128 NZ LED Status table."
	::= { bqlGT128LEDNZEntry 1 }

bqlGT128LEDNZStatus OBJECT-TYPE
	SYNTAX	OCTET STRING (SIZE (2))
	ACCESS  read-only
	STATUS  mandatory
	DESCRIPTION
			"The GDC GT128 NZ front panel LED Status.
			 A value of 1 means on, 0 is off.
			 byte 1 bit 7 (1.7) - not used
			 1.6 - test mode
			 1.5 - 128K (sync)
			 1.4 - request to send
			 1.3 - clear to send
			 1.2 - network available (carrier on)
			 1.1 - send data transitions
			 1.0 - receive data transitions

			 2.6 - fu
			 2.5 - fu
			 2.4 - fu
			 2.3 - fu
			 2.2 - remote loopback ON
			 2.1 - selftest ON
			 2.0 - line loopback ON"
			
	::= { bqlGT128LEDNZEntry 2 }

END
