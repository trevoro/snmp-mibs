TERAWAVE-teraIpClassification-MIB DEFINITIONS ::= BEGIN
        -- Created by sml2mib compiler 
        IMPORTS

 IpAddress, enterprises,  OBJECT-TYPE,  Counter,  Gauge,  TimeTicks
        FROM RFC1155-SMI;

terawave OBJECT IDENTIFIER ::=  { enterprises 4513 }

teraIpClassificationGroup OBJECT IDENTIFIER ::=  { terawave 23 }

     -- teraIpClassTable

teraIpClassTable OBJECT-TYPE
     SYNTAX SEQUENCE OF TeraIpClassTableEntryType
     ACCESS not-accessible
     STATUS mandatory
     DESCRIPTION
          " table teraIpClassTable"
     ::= { teraIpClassificationGroup 1 }

teraIpClassTableEntry OBJECT-TYPE
          SYNTAX TeraIpClassTableEntryType
          ACCESS not-accessible
          STATUS mandatory
          DESCRIPTION
               " table entry teraIpClassTableEntry "
          INDEX {                   teraIpClassField }
     ::= { teraIpClassTable 1 }

TeraIpClassTableEntryType ::= SEQUENCE {
          teraIpClassField   
             INTEGER,
          teraIpClassType   
             INTEGER,
          teraIpClassValue   
             INTEGER,
          teraIpClassMinRange   
             INTEGER,
          teraIpClassMaxRange   
             INTEGER,
          teraIpClassIpAddr   
             IpAddress,
          teraIpClassMask   
             IpAddress
}

teraIpClassField OBJECT-TYPE
          SYNTAX INTEGER
          ACCESS read-only
          STATUS mandatory
          DESCRIPTION
               ""
          ::= { teraIpClassTableEntry 1 }

teraIpClassType OBJECT-TYPE
          SYNTAX INTEGER
          ACCESS read-write
          STATUS mandatory
          DESCRIPTION
               ""
          ::= { teraIpClassTableEntry 2 }

teraIpClassValue OBJECT-TYPE
          SYNTAX INTEGER
          ACCESS read-write
          STATUS mandatory
          DESCRIPTION
               ""
          ::= { teraIpClassTableEntry 3 }

teraIpClassMinRange OBJECT-TYPE
          SYNTAX INTEGER
          ACCESS read-write
          STATUS mandatory
          DESCRIPTION
               ""
          ::= { teraIpClassTableEntry 4 }

teraIpClassMaxRange OBJECT-TYPE
          SYNTAX INTEGER
          ACCESS read-write
          STATUS mandatory
          DESCRIPTION
               ""
          ::= { teraIpClassTableEntry 5 }

teraIpClassIpAddr OBJECT-TYPE
          SYNTAX IpAddress
          ACCESS read-write
          STATUS mandatory
          DESCRIPTION
               ""
          ::= { teraIpClassTableEntry 6 }

teraIpClassMask OBJECT-TYPE
          SYNTAX IpAddress
          ACCESS read-write
          STATUS mandatory
          DESCRIPTION
               ""
          ::= { teraIpClassTableEntry 7 }

     -- teraIpClassificationTable

teraIpClassificationTable OBJECT-TYPE
     SYNTAX SEQUENCE OF TeraIpClassificationTableEntryType
     ACCESS not-accessible
     STATUS mandatory
     DESCRIPTION
          " table teraIpClassificationTable"
     ::= { teraIpClassificationGroup 2 }

teraIpClassificationTableEntry OBJECT-TYPE
          SYNTAX TeraIpClassificationTableEntryType
          ACCESS not-accessible
          STATUS mandatory
          DESCRIPTION
               " table entry teraIpClassificationTableEntry "
          INDEX {                   teraClassificationRule,                  teraIpClassField }
     ::= { teraIpClassificationTable 1 }

TeraIpClassificationTableEntryType ::= SEQUENCE {
          teraClassificationRule   
             INTEGER,
          teraIpClassificationField   
             INTEGER
}

teraClassificationRule OBJECT-TYPE
          SYNTAX INTEGER
          ACCESS read-only
          STATUS mandatory
          DESCRIPTION
               ""
          ::= { teraIpClassificationTableEntry 1 }

teraIpClassificationField OBJECT-TYPE
          SYNTAX INTEGER
          ACCESS read-write
          STATUS mandatory
          DESCRIPTION
               ""
          ::= { teraIpClassificationTableEntry 2 }

END
