-- SECTION 1: Top Level Definitions

S5-TOKENRING-COMMON-MIB DEFINITIONS ::= BEGIN


-- 5000 Token Ring Common MIB Release 1.1.7
-- Revision 08/01/96

-- Copyright 1996 Bay Networks, Inc.
-- All rights reserved.
-- This Bay Networks SNMP Management Information Base Specification
-- (Specification) embodies Bay Networks' confidential and
-- proprietary intellectual property. Bay Networks retains all
-- title and ownership in the Specification, including any
-- revisions.

-- This Specification is supplied "AS IS," and Bay Networks makes
-- no warranty, either express or implied, as to the use,
-- operation, condition, or performance of the Specification.


-- Imports

IMPORTS
	Counter, TimeTicks
		FROM RFC1155-SMI
	OBJECT-TYPE
		FROM RFC-1212
	DisplayString
		FROM RFC1213-MIB
	s5TrCfg, s5TrStat
		FROM S5-TOKENRING-MIB
	TimeIntervalSec, SrcIndx
		FROM S5-TCS-MIB
	MacAddress FROM SNMPv2-TC;




-- SECTION 2: Configuration information

-- Port Table

s5TrPortTable OBJECT-TYPE
	SYNTAX	SEQUENCE OF S5TrPortEntry
	ACCESS	not-accessible
	STATUS	mandatory
	DESCRIPTION
		"A table containing information about each
		port on a board. The number of entries
		is determined by the number of manageable
		ports. Those boards that do not have any
		manageable ports do not have
		any entries in this table."
	::= { s5TrCfg 1 }

s5TrPortEntry OBJECT-TYPE
	SYNTAX	S5TrPortEntry
	ACCESS	not-accessible
	STATUS	mandatory
	DESCRIPTION
		"A row in Token Ring port table. Entries
		can not be created or deleted via SNMP."
	INDEX	{ s5TrPortBrdIndx,
		  s5TrPortIndx }
	::= { s5TrPortTable 1 }

S5TrPortEntry ::= SEQUENCE {
	s5TrPortBrdIndx INTEGER,
	s5TrPortIndx INTEGER,
	s5TrPortWrapStatus INTEGER,
	s5TrPortWrapTime TimeIntervalSec,
	s5TrPortInsrtStatus INTEGER,
	s5TrPortPhanStatus INTEGER,
	s5TrPortPhanChngs Counter,
	s5TrPortTrnkAccMthdStrap INTEGER,
	s5TrPortTrnkAccMthd INTEGER,
	s5TrPortClass INTEGER,
	s5TrPortMedia INTEGER,
	s5TrPortConnector INTEGER,
	s5TrPortSoftwareInsertion INTEGER,
        s5TrPortAFD INTEGER
	}

s5TrPortBrdIndx OBJECT-TYPE
	SYNTAX	INTEGER (1..255)
	ACCESS	read-only
	STATUS	mandatory
	DESCRIPTION
		"The index of the board. This corresponds to
		the index of the slot containing the board."
	::= { s5TrPortEntry 1 }

s5TrPortIndx OBJECT-TYPE
	SYNTAX	INTEGER (1..255)
	ACCESS	read-only
	STATUS	mandatory
	DESCRIPTION
		"The index of the port on the board.  Its value
		ranges between 1 and the number of manageable
		ports on the board."
	::= { s5TrPortEntry 2 }

s5TrPortWrapStatus OBJECT-TYPE
	SYNTAX	INTEGER {
		other(1),
		wrap(2),
		connect(3),
		timedWrap(4),
		nmmBeaconWrap(5),
		wrongSpeedWrap(6),
		permBeaconWrap(7),
		hostBecaonWrap (8)
		}
	ACCESS	read-write
	STATUS	mandatory
	DESCRIPTION
		"The wrap status of the port. The following
		values can be written:
		  wrap(2)........wrap the port
		  connect(3).....unwrap the port
		  timedWrap(4)...time wrap port (uses value
		                   from s5TrPortWrapTime)

		The following values reflect the wrap
		status of the port:
		  other(1)............wrap status unknown
		  wrap(2).............port is wrapped
		  connect(3)..........port is not wrapped
		  timedWrap(4)........port is timed wrapped
		                        (see value of
		                        s5TrPortWrapTime)
		  nmmBeaconWrap(5)....beaconing station
		                        automatically removed
		                        by an NMM
		  wrongSpeedWrap(6)...station with wrong speed
		                        automatically removed
		  permBeaconWrap(7)...station permanently removed
		                        by an NMM since it attempted
		                        to deinsert and insert in the
		                        ring at a high rate while it
		                        beacons the ring.
		On GETs with port status of timeWrap(4), if
		the time remaining before the wrap is undone
		is available, it will be reported in object
		s5TrPortWrapTime as a positive value. If not
		available, the value of s5TrPortWrapTime will
		be zero. When changing a port to timedWrap(4),
		the SET request must also contain the value
		for object s5TrPortWrapTime. Only value
		wrap(2) will survive resets of the host card."
	::= { s5TrPortEntry 3 }

s5TrPortWrapTime OBJECT-TYPE
	SYNTAX	TimeIntervalSec
	ACCESS	read-write
	STATUS	mandatory
	DESCRIPTION
		"The length of time to keep the port
		wrapped when a timed wrap is done to the
		board. This object can only be written
		in the same request that sets s5TrPortWrapStatus
		to timedWrap(4). Afterwards, it indicates
		the amount of time left before the timed
		wrap is completed, at which time
		s5TrPortWrapStatus is changed to connect(3).
		This object has the value of zero if the
		port is not timed wrapped, and also if the
		amount of time is not available."
	::= { s5TrPortEntry 4 }

s5TrPortInsrtStatus OBJECT-TYPE
	SYNTAX	INTEGER {
		other(1),
		notInserted(2),
		inserted(3)
		}
	ACCESS	read-only
	STATUS	mandatory
	DESCRIPTION
		"The port insertion status. The values are:
		  other(1).........status unknown
		  notInserted(2)...port is not inserted
		  inserted(3)......port inserted into the ring"
	::= { s5TrPortEntry 5 }

s5TrPortPhanStatus OBJECT-TYPE
	SYNTAX	INTEGER {
		other(1),
		noPhantom(2),
		phantom(3),
		softwarePhantom(4)
		}
	ACCESS	read-only
	STATUS	mandatory
	DESCRIPTION
		"The port phantom status. The values are:
		  other(1).............status unknown
		  noPhantom(2).........no phantom signal
		  phantom(3)...........phantom signal is on
		  softwarePhantom(4)...phantom signal is on by
		                         turning on software
		                         insertion (see
		                         s5TrPortSoftwareInsertion
		                         for more details)

		Note: for RI/RO ports, this signal is
		driven by the 'lowlight' detector. For
		RI/RO ports that have the value of
		none(3) for s5TrPortTrnkAccMthd,
		this value will always be phantom(3)."
	::= { s5TrPortEntry 6 }

s5TrPortPhanChngs OBJECT-TYPE
	SYNTAX	Counter
	ACCESS	read-only
	STATUS	mandatory
	DESCRIPTION
		"A counter of changes of s5TrPortPhanStatus
		from noPhantom(2) to phantom(3)."
	::= { s5TrPortEntry 7 }

s5TrPortTrnkAccMthdStrap OBJECT-TYPE
	SYNTAX	INTEGER {
		notSupported(1),
		synoptics(2),
		none(3)
		}
	ACCESS	read-only
	STATUS	mandatory
	DESCRIPTION
		"The strap (hardware jumper) setting for
		the RI/RO port trunk validation method.
		The values are:
		  notSupported(1)...a fiber port, or
		                      not a RI/RO port
		  synoptics(2)......use SynOptics method
		  none(3)...........no validation done
		The operational method used is indicated
		by the value of s5TrPortTrnkAccMthd."
	::= { s5TrPortEntry 8 }

s5TrPortTrnkAccMthd OBJECT-TYPE
	SYNTAX	INTEGER {
		notSupported(1),
		synoptics(2),
		none(3)
		}
	ACCESS	read-write
	STATUS	mandatory
	DESCRIPTION
		"The operational setting for the
		RI/RO port trunk validation method.
		The following values can be written:
		  synoptics(2)...use SynOptics method
		  none(3)........no validation done

		The following values can be read:
		  notSupported(1)...not a RI/RO port, or
		                      a fiber port
		  synoptics(2)......use SynOptics method
		  none(3)...........do no validation"
	::= { s5TrPortEntry 9 }

s5TrPortClass OBJECT-TYPE
	SYNTAX	INTEGER {
		other(1),
		ri(2),
		ro(3),
		lobe(4),
		internal(5)
		}
	ACCESS	read-only
	STATUS	mandatory
	DESCRIPTION
		"The port class. The values are:
		  other(1)......unknown or some other type
		  ri(2).........Ring In port
		  ro(3).........Ring Out port
		  lobe(4).......Lobe port
		  internal(5)...Internal port which may be
		                  connected to a backplane ring"
	::= { s5TrPortEntry 10 }

s5TrPortMedia OBJECT-TYPE
	SYNTAX	INTEGER {
		other(1),
		synFiber(2),
		stdFiber(3),
		copperActive(4),
		copperPassive(5),
		mac(6),
		specialProc(7)
		}
	ACCESS	read-only
	STATUS	mandatory
	DESCRIPTION
		"The port media type. The values are:
		  other(1)...........unknown or some other type
		  synFiber(2)........SynOptics Fiber
		  stdFiber(3)........Standard Fiber
		  copperActive(4)....Active copper
		  copperPassive(5)...Passive copper
		  mac(6).............Internal MAC
		  specialProc(7).....Internal special processor"
	::= { s5TrPortEntry 11 }

s5TrPortConnector OBJECT-TYPE
	SYNTAX	INTEGER {
		other(1),
		internal(2),
		db9(3),
		rj45(4),
		fiberST(5)
		}
	ACCESS	read-only
	STATUS	mandatory
	DESCRIPTION
		"The port connector type. The values are:
		  other(1)......unknown or some other type
		  internal(2)...no external connector
		  db9(3)........DB9
		  rj45(4).......RJ-45
		  fiberST(5)....fiber ST"
	::= { s5TrPortEntry 12 }

s5TrPortSoftwareInsertion OBJECT-TYPE
	SYNTAX	INTEGER {
		notCapableOfSoftwareInsertion(1),
		capableAndSoftwareInsertionOn(2),
		capableAndSoftwareInsertionOff(3)
		}
	ACCESS	read-write
	STATUS	mandatory
	DESCRIPTION
		"This object reflects the capability for a port
		to connect to the Ring-In (RI) or Ring-Out (RO)
		port of a MAU by software controlled phantom
		insertion.

		The following values can be read:
		  notCapableOfSoftwareInsertion(1)...
		                 The port is incapable of
		                   software insertion and
		                   therefore cannot connect
		                   to the RI or RO port 
		                   of a MAU
		  capableAndSoftwareInsertionOn(2)...
		                 The port is capable of
		                   software insertion,
		                   and software insertion
		                   is on
		  capableAndSoftwareInsertionOff(3)...
		                 The port is capable of
		                   software insertion,
		                   and software insertion
		                   is off

		The following values can be written:
		  capableAndSoftwareInsertionOn(2)...
		                 Turns on the software
		                   insertion (see note)
		  capableAndSoftwareInsertionOff(3)...
		                 Turns off the software
		                   insertion (see note)

		Note:  The values capableAndSoftwareInsertionOn(2)
		       and capableAndSoftwareInsertionOff(3)
		       are only valid for writing if the port
		       has the capability of software insertion."
	::= {s5TrPortEntry 13}

s5TrPortAFD OBJECT-TYPE
        SYNTAX  INTEGER {
                notCapableOfAFDDisable(1),
                capableAndAFDEnabled(2),
                capableAndAFDDisabled(3)
                }
        ACCESS  read-write
        STATUS  mandatory
        DESCRIPTION
                "This object reflects the capability for a port
                to disable AFD, Automatic Frequency Detection.

                The following values can be read:
                  notCapableOfAFDDisable(1)...
                                 The port is incapable of
                                   AFD disable.
                  capableAndAFDEnabled(2)...
                                 The port is capable of
                                   AFD disable and the
                                   current AFD is enabled.
                  capableAndAFDDisabled(3)...
                                 The port is capable of
                                   AFD disable and the
                                   current AFD is disabled.

                The following values can be written:
                  capableAndAFDEnabled(2)...
                                 Enable the AFD.
                  capableAndAFDDisabled(3)...
                                 Disable the AFD.

                Note:  The values capableAndAFDEnabled(2)
                       and capableAndAFDDisabled(3)
                       are only valid for writing if the port
                       has the capability of AFD disable."
        ::= {s5TrPortEntry 14}

-- FPU Table

s5TrFpuTable OBJECT-TYPE
	SYNTAX	SEQUENCE OF S5TrFpuEntry
	ACCESS	not-accessible
	STATUS	mandatory
	DESCRIPTION
		"A table containing information about each
		FPU (Frame Processing Unit) on a board."
	::= { s5TrCfg 2 }

s5TrFpuEntry OBJECT-TYPE
	SYNTAX	S5TrFpuEntry
	ACCESS	not-accessible
	STATUS	mandatory
	DESCRIPTION
		"A row in the Token Ring FPU table. Entries
		can not be created or deleted via SNMP."
	INDEX	{ s5TrFpuBrdIndx,
		  s5TrFpuIndx }
	::= { s5TrFpuTable 1 }

S5TrFpuEntry ::= SEQUENCE {
	s5TrFpuBrdIndx INTEGER,
	s5TrFpuIndx INTEGER,
	s5TrFpuType INTEGER,
	s5TrFpuTypeIndx INTEGER,
	s5TrFpuVer DisplayString,
	s5TrFpuCapabilites INTEGER,
	s5TrFpuRunningMode INTEGER
	}

s5TrFpuBrdIndx OBJECT-TYPE
	SYNTAX	INTEGER (1..255)
	ACCESS	read-only
	STATUS	mandatory
	DESCRIPTION
		"The index of the board. This corresponds to
		the index of the slot containing the board."
	::= { s5TrFpuEntry 1 }

s5TrFpuIndx OBJECT-TYPE
	SYNTAX	INTEGER (1..255)
	ACCESS	read-only
	STATUS	mandatory
	DESCRIPTION
		"The index of the FPU on the board. The
		value ranges between 1 and the number
		of FPUs on the board."
	::= { s5TrFpuEntry 2 }

s5TrFpuType OBJECT-TYPE
	SYNTAX	INTEGER {
		other(1),
		cluster(2),
		port(3),
		roving(4)
		}
	ACCESS	read-only
	STATUS	mandatory
	DESCRIPTION
		"The type of FPU. The values are:
		  other(1).....other or unknown
		  cluster(2)...FPU is associated with
		                 a cluster
		  port(3)......FPU is associated with
		                 a port
		  roving(4)....FPU is a virtual one due
		                 to roving embedded
		                 management FPU.  The
		                 type index s5TrFpuTypeIndx
		                 specifies port number in
		                 this case.

		This describes at what point an FPU
		is connected so that it can collect
		information."
	::= { s5TrFpuEntry 3 }

s5TrFpuTypeIndx OBJECT-TYPE
	SYNTAX	INTEGER (0..255)
	ACCESS	read-only
	STATUS	mandatory
	DESCRIPTION
		"The index of the cluster or port
		that the FPU is associated with. The
		object s5TrFpuType type specifies the
		type."
	::= { s5TrFpuEntry 4 }

s5TrFpuVer OBJECT-TYPE
	SYNTAX	DisplayString (SIZE(0..32))
	ACCESS	read-only
	STATUS	obsolete
	DESCRIPTION
		"The version of the FPU. If not available,
		then the value is a zero length string."
	::= { s5TrFpuEntry 5 }

s5TrFpuCapabilites OBJECT-TYPE
	SYNTAX	INTEGER {
		other(1),
		coreStatistics(2),
		embeddedManagement(3)
		}
	ACCESS	read-only
	STATUS	mandatory
	DESCRIPTION
		"The capabilities of the FPU.

		The values are:
		  other (1)...............Other or unknown
		  coreStatistics(2).......Core statistics FPU
		  embeddedManagement(3)...FPU capable of core
		                            statistics and roving;
		                            both features are
		                            mutually exclusive."
	::= { s5TrFpuEntry 6 }

s5TrFpuRunningMode OBJECT-TYPE
	SYNTAX	INTEGER {
		other(1),
		coreStatistics(2),
		rovingFPU(4),
		securityRoving(5)
		}
	ACCESS	read-write
	STATUS	mandatory
	DESCRIPTION
		"The running mode of the FPU. These values
		are for both read and write with the exception
		of other(1) which is for read only.

		The values are:
		  other(1).......................Other or unknown
		  coreStatistics(2)..............FPU running in core
		                                   statistics mode.
		  roving(4)......................FPU running in roving mode;
		                                   Note: core statistics is
		                                   unavailable in this mode.
		  securityRoving(5)..............FPU running in roving mode
		                                   due to authorized nodes
		                                   security being turned on."
	::= { s5TrFpuEntry 7 }



-- Token Ring Extensions to the Chassis MIB


s5TrAttTable OBJECT-TYPE
	SYNTAX	SEQUENCE OF S5TrAttEntry
	ACCESS	not-accessible
	STATUS	mandatory
	DESCRIPTION
		"A table containing information about each
		Token Ring attachment point on a board. This
		table extends table s5ChasAttTable for Token
		Ring Boards."
	::= { s5TrCfg 3 }

s5TrAttEntry OBJECT-TYPE
	SYNTAX	S5TrAttEntry
	ACCESS	not-accessible
	STATUS	mandatory
	DESCRIPTION
		"A row in Token Ring attachment table. Entries
		can not be created or deleted via SNMP."
	INDEX	{ s5TrAttBrdIndx,
		  s5TrAttIndx }
	::= { s5TrAttTable 1 }

S5TrAttEntry ::= SEQUENCE {
	s5TrAttBrdIndx INTEGER,
	s5TrAttIndx INTEGER,
	s5TrAttDfltSpeed INTEGER,
	s5TrAttCurSpeed INTEGER,
	s5TrAttFault INTEGER
	}

s5TrAttBrdIndx OBJECT-TYPE
	SYNTAX	INTEGER (1..255)
	ACCESS	read-only
	STATUS	mandatory
	DESCRIPTION
		"The index of the board. This corresponds to
		the index of the slot containing the board."
	::= { s5TrAttEntry 1 }

s5TrAttIndx OBJECT-TYPE
	SYNTAX	INTEGER (1..255)
	ACCESS	read-only
	STATUS	mandatory
	DESCRIPTION
		"The index of the attachment point on the board."
	::= { s5TrAttEntry 2 }

s5TrAttDfltSpeed OBJECT-TYPE
	SYNTAX	INTEGER {
		other(1),
		s4Mbit(2),
		s16Mbit(3)
		}
	ACCESS	read-only
	STATUS	mandatory
	DESCRIPTION
		"The default speed setting for the attachment
		point. The values are:
		  other(1).....unknown or other speed
		  s4Mbit(2)....4Mbit
		  s16Mbit(3)...16Mbit"
	::= { s5TrAttEntry 3 }

s5TrAttCurSpeed OBJECT-TYPE
	SYNTAX	INTEGER {
		other(1),
		s4Mbit(2),
		s16Mbit(3)
		}
	ACCESS	read-write
	STATUS	mandatory
	DESCRIPTION
		"The current speed setting for the attachment
		point. The read-only value is:
		  other(1).....unknown or other speed

		The read-write values are:
		  s4Mbit(2)....4Mbit
		  s16Mbit(3)...16Mbit"
	::= { s5TrAttEntry 4 }

s5TrAttFault OBJECT-TYPE
	SYNTAX	INTEGER {
		other(1),
		nofault(2),
		fault(3)
		}
	ACCESS	read-only
	STATUS	mandatory
	DESCRIPTION
		"A fault indicator for the attachment point.
		The values are:
		  other(1).....not connected to a backplane network
		                 or value is unknown
		  nofault(2)...no fault detected
		  fault(3).....fault detected."
	::= { s5TrAttEntry 5 }

s5TrBkDiv OBJECT-TYPE
	SYNTAX	INTEGER {
		other(1),
		split(2),
		join(3)
		}
	ACCESS	read-write
	STATUS	mandatory
	DESCRIPTION
		"Setting of the Token Ring backplane divider.
		The value that can only be read is:
		  other(1)...unknown or other state

		Values that can be read and written are:
		  split(2)...split the backplane
		  join(3)....join the backplane"
	::= { s5TrCfg 4 }



-- Ring Extension Table

s5TrRingExt OBJECT IDENTIFIER ::=  { s5TrCfg 5 }

-- Ring Extension Table Highlight

s5TrRingExtLastChange OBJECT-TYPE
	SYNTAX	TimeTicks
	ACCESS	read-only
	STATUS	mandatory
	DESCRIPTION
		"The value of sysUpTime when the last change
		of any Ring Extension table entry within the 
		chassis was detected."
	::= { s5TrRingExt 1}

s5TrRingExtCurNum OBJECT-TYPE
	SYNTAX	INTEGER (0..65535)
	ACCESS	read-only
	STATUS	mandatory
	DESCRIPTION
		"The current number of entries in the Ring
		Extension Table."
	::= { s5TrRingExt 2 }

-- Ring Extension Table Details

s5TrRingExtTable OBJECT-TYPE
	SYNTAX	SEQUENCE OF S5TrRingExtEntry
	ACCESS	not-accessible
	STATUS	mandatory
	DESCRIPTION
		"A table containing information about each
		RI/RO (Ring In / Ring Out) pair on a board. 
		The number of entries is determined by the 
		number of existing RI/RO pairs. Those boards 
		that do not have any RI/RO do not have any 
		entries in this table."
	::= { s5TrRingExt 3 }

s5TrRingExtEntry OBJECT-TYPE
	SYNTAX	S5TrRingExtEntry
	ACCESS	not-accessible
	STATUS	mandatory
	DESCRIPTION
		"A row in the Ring Extension table.
		Entries can not be created or deleted via
		SNMP."
	INDEX { s5TrRingExtBoardIndx,
		s5TrRingExtExtensionIndx }
	::= { s5TrRingExtTable 1 }

S5TrRingExtEntry ::= SEQUENCE {
	s5TrRingExtBoardIndx 		INTEGER,
	s5TrRingExtExtensionIndx 	INTEGER,
	s5TrRingExtRingNumber 		INTEGER,
	s5TrRingExtRingInUna 		MacAddress,
	s5TrRingExtRingOutUna 		MacAddress,
	s5TrRingExtSecUna 		MacAddress,
	s5TrRingExtRingInPhanStatus 	INTEGER,
	s5TrRingExtRingOutPhanStatus 	INTEGER,
	s5TrRingExtRingInWrapStatus 	INTEGER,
	s5TrRingExtRingOutWrapStatus 	INTEGER,
	s5TrRingExtClusterNumber 	INTEGER,
	s5TrRingExtRingInPortNumber 	INTEGER,
	s5TrRingExtRingOutPortNumber 	INTEGER
	}

s5TrRingExtBoardIndx OBJECT-TYPE
	SYNTAX	INTEGER (1..255)
	ACCESS	read-only
	STATUS	mandatory
	DESCRIPTION
		"The index of the board which has RI/RO.
		This corresponds to the index of the slot 
		containing the board."
	::= { s5TrRingExtEntry 1 }

s5TrRingExtExtensionIndx OBJECT-TYPE
	SYNTAX	INTEGER (1..255)
	ACCESS	read-only
	STATUS	mandatory
	DESCRIPTION
		"The index of the RI/RO extension pair 
		on the board. The value ranges between 1 
		and the number of RI/RO pairs on the board."
	::= { s5TrRingExtEntry 2 }

s5TrRingExtRingNumber OBJECT-TYPE
	SYNTAX	INTEGER (0..4095)
	ACCESS	read-only
	STATUS	mandatory
	DESCRIPTION
		"The logical ring number of the ring
		that RI/RO connects to." 
	::= { s5TrRingExtEntry 3 }

s5TrRingExtRingInUna OBJECT-TYPE
	SYNTAX	MacAddress
	ACCESS	read-only
	STATUS	mandatory
	DESCRIPTION
		"The upstream neighbor address to the 
		Ring In port."
	::= { s5TrRingExtEntry 4 }

s5TrRingExtRingOutUna OBJECT-TYPE
	SYNTAX	MacAddress	
	ACCESS	read-only
	STATUS	mandatory
	DESCRIPTION
		"The upstream neighbor address to the 
		Ring Out port."
	::= { s5TrRingExtEntry 5 }

s5TrRingExtSecUna OBJECT-TYPE
	SYNTAX	MacAddress	
	ACCESS	read-only
	STATUS	mandatory
	DESCRIPTION
		"The (secondary) upstream neighbor 
		address as read by the FPU that is
		located between RI and RO."
	::= { s5TrRingExtEntry 6 }

s5TrRingExtRingInPhanStatus OBJECT-TYPE
	SYNTAX	INTEGER	{
		other(1),
		noPhantom(2),
		phantom(3)
		}
	ACCESS	read-only
	STATUS	mandatory
	DESCRIPTION
		"The phantom status of the Ring In port.  
		The values are:
		  other(1).........status unknown
		  noPhantom(2).....no phantom signal
		  phantom(3).......phantom signal is on."
	::= { s5TrRingExtEntry 7 }

s5TrRingExtRingOutPhanStatus OBJECT-TYPE
	SYNTAX	INTEGER	{
		other(1),
		noPhantom(2),
		phantom(3)
		}
	ACCESS	read-only
	STATUS	mandatory
	DESCRIPTION
		"The phantom status of the Ring Out port.  
		The values are:
		  other(1).........status unknown
		  noPhantom(2).....no phantom signal
		  phantom(3).......phantom signal is on."
	::= { s5TrRingExtEntry 8 }

s5TrRingExtRingInWrapStatus OBJECT-TYPE
	SYNTAX	INTEGER	{
		other(1),
		wrap(2),
		connect(3)
		}
	ACCESS	read-only
	STATUS	mandatory
	DESCRIPTION
		"The wrap status of the Ring-In port.
		The values are:
		  other(1)............wrap status unknown
		  wrap(2).............port is wrapped
		  connect(3)..........port is unwrapped"
	::= { s5TrRingExtEntry 9 }

s5TrRingExtRingOutWrapStatus OBJECT-TYPE
	SYNTAX	INTEGER	{
		other(1),
		wrap(2),
		connect(3)
		}
	ACCESS	read-only
	STATUS	mandatory
	DESCRIPTION
		"The wrap status of the Ring-Out port.
		The values are:
		  other(1)............wrap status unknown
		  wrap(2).............port is wrapped
		  connect(3)..........port is unwrapped"
	::= { s5TrRingExtEntry 10 }

s5TrRingExtClusterNumber OBJECT-TYPE
	SYNTAX	INTEGER (1..255)
	ACCESS	read-only
	STATUS	mandatory
	DESCRIPTION
		"The cluster number where RI/RO pair is 
		located on the board."
	::= { s5TrRingExtEntry 11 }

s5TrRingExtRingInPortNumber OBJECT-TYPE
	SYNTAX	INTEGER (1..255)
	ACCESS	read-only
	STATUS	mandatory
	DESCRIPTION
		"The port number where RI is located on 
		the board."
	::= { s5TrRingExtEntry 12 }

s5TrRingExtRingOutPortNumber OBJECT-TYPE
	SYNTAX	INTEGER (1..255)
	ACCESS	read-only
	STATUS	mandatory
	DESCRIPTION
		"The port number where RO is located on
		the board."
	::= { s5TrRingExtEntry 13 }



-- Encoded Octet Strings for Ring Extension Table

s5TrRingExtEosSize OBJECT-TYPE
	SYNTAX	INTEGER (0..1400)
	ACCESS	read-only
	STATUS	mandatory
	DESCRIPTION
		"The current size of a 'row' in the table
		s5TrRingExtEosTable. This allows applications
		to be able to break apart 'rows' in the table."
	::= { s5TrRingExt 4 }

s5TrRingExtEosTable OBJECT-TYPE
	SYNTAX	SEQUENCE OF S5TrRingExtEosEntry
	ACCESS	not-accessible
	STATUS	mandatory
	DESCRIPTION
		"A table of encoded octet strings of
		entries in table s5TrRingExtTable.
		The number of entries is determined by the
		packing of 'rows' from s5TrRingExtTable."
	::= { s5TrRingExt 5 }

s5TrRingExtEosEntry OBJECT-TYPE
	SYNTAX	S5TrRingExtEosEntry
	ACCESS	not-accessible
	STATUS	mandatory
	DESCRIPTION
		"A row in the table of encoded octet
		strings for table s5TrRingExtTable.
		Instance returned in Response PDU:
		  On GETs: instance specified is the
		           instance returned.
		  On GET-NEXTs: instance returned is the
		                instance of the last record
		                contained in the octet string.
		Entries in the table can not be created
		or deleted via SNMP."
	INDEX { s5TrRingExtBoardIndx,
 		s5TrRingExtExtensionIndx }
	::= { s5TrRingExtEosTable 1 }

S5TrRingExtEosEntry ::= SEQUENCE {
	s5TrRingExtEos OCTET STRING
	}

s5TrRingExtEos OBJECT-TYPE
	SYNTAX	OCTET STRING (SIZE(0..1400))
	ACCESS	read-only
	STATUS	mandatory
	DESCRIPTION
		"An encoded octet string. On reads it contains
		an integral number of 'rows' from table
		s5TrRingExtTable. All 'rows' are the same size
		which is defined by object s5TrRingExtEosSize."
	::= { s5TrRingExtEosEntry 1 }



-- SECTION 3: Statistics


-- Basic Statistics Table

s5TrBStatTable OBJECT-TYPE
	SYNTAX	SEQUENCE OF S5TrBStatEntry
	ACCESS	not-accessible
	STATUS	mandatory
	DESCRIPTION
		"A table containing Token Ring basic
		statistics. The entries in the table
		may come from several different data
		sources including FPUs (Frame Processing
		Units) and MACs on NMMs (Network Management
		Modules). The number of entries is
		determined by the number of sources
		that can provide the information."
	::= { s5TrStat 1 }

s5TrBStatEntry OBJECT-TYPE
	SYNTAX	S5TrBStatEntry
	ACCESS	not-accessible
	STATUS	mandatory
	DESCRIPTION
		"A row in Token Ring basic statistics
		table. Entries can not be created or
		deleted via SNMP."
	INDEX	{ s5TrBStatSrcIndx }
	::= { s5TrBStatTable 1 }

S5TrBStatEntry ::= SEQUENCE {
	s5TrBStatSrcIndx SrcIndx,

	s5TrBStatTtlOctets Counter,
	s5TrBStatMacOctets Counter,
	s5TrBStatLlcOctets Counter,

	s5TrBStatTtlFrms Counter,
	s5TrBStatTtlGoodFrms Counter,
	s5TrBStatTtlBadFrms Counter,

	s5TrBStatMacFrms Counter,
	s5TrBStatLlcFrms Counter,
	s5TrBStatLlcNonUcastFrms Counter,
	s5TrBStatLlcUcastFrms Counter,

	s5TrBStatGoodErrReportFrms Counter,
	s5TrBStatBeaconFrms Counter,
	s5TrBStatRingPurgeFrms Counter,
	s5TrBStatClaimTokenFrms Counter,

	s5TrBStatUna MacAddress
	}

s5TrBStatSrcIndx OBJECT-TYPE
	SYNTAX	SrcIndx
	ACCESS	read-only
	STATUS	mandatory
	DESCRIPTION
		"The index of the entry in the table.
		This index identifies the source of the
		information. Only those sources that provide
		these statistics are in this table."
	::= { s5TrBStatEntry 1 }

s5TrBStatTtlOctets OBJECT-TYPE
	SYNTAX	Counter
	ACCESS	read-only
	STATUS	mandatory
	DESCRIPTION
		"The total number of octets of data in LLC
		frames and MAC frames (including frames with
		errors) measured on the ring (excluding
		framing bits, but including FCS octets)."
	::= { s5TrBStatEntry 2 }

s5TrBStatMacOctets OBJECT-TYPE
	SYNTAX	Counter
	ACCESS	read-only
	STATUS	mandatory
	DESCRIPTION
		"The total number of octets of data in MAC
		frames (including frames with errors) measured
		on the ring (excluding framing bits,
		but including FCS octets)."
	::= { s5TrBStatEntry 3 }

s5TrBStatLlcOctets OBJECT-TYPE
	SYNTAX	Counter
	ACCESS	read-only
	STATUS	mandatory
	DESCRIPTION
		"The total number of octets of data in LLC
		frames (including frames with errors) measured
		on the ring (excluding framing bits,
		but including FCS octets)."
	::= { s5TrBStatEntry 4 }

s5TrBStatTtlFrms OBJECT-TYPE
	SYNTAX	Counter
	ACCESS	read-only
	STATUS	mandatory
	DESCRIPTION
		"The total number of LLC frames and MAC
		frames (including frames with errors)
		detected on the ring."
	::= { s5TrBStatEntry 5 }

s5TrBStatTtlGoodFrms OBJECT-TYPE
	SYNTAX	Counter
	ACCESS	read-only
	STATUS	mandatory
	DESCRIPTION
		"The total number of LLC frames and MAC
		frames (excluding frames with errors)
		detected on the ring."
	::= { s5TrBStatEntry 6 }

s5TrBStatTtlBadFrms OBJECT-TYPE
	SYNTAX	Counter
	ACCESS	read-only
	STATUS	mandatory
	DESCRIPTION
		"The total number of LLC frames and MAC
		frames with errors detected on the ring."
	::= { s5TrBStatEntry 7 }

s5TrBStatMacFrms OBJECT-TYPE
	SYNTAX	Counter
	ACCESS	read-only
	STATUS	mandatory
	DESCRIPTION
		"The total number of MAC frames (including frames
		with errors) detected on the ring."
	::= { s5TrBStatEntry 8 }

s5TrBStatLlcFrms OBJECT-TYPE
	SYNTAX	Counter
	ACCESS	read-only
	STATUS	mandatory
	DESCRIPTION
		"The total number of LLC frames (including
		frames with errors) detected on the ring."
	::= { s5TrBStatEntry 9 }

s5TrBStatLlcNonUcastFrms OBJECT-TYPE
	SYNTAX	Counter
	ACCESS	read-only
	STATUS	mandatory
	DESCRIPTION
		"The total number of LLC frames (including
		frames with errors) detected on the ring
		that were directed to a LLC broadcast address
		(i.e., 0xFFFFFFFFFFFF or 0xC000FFFFFFFF) or
		a local or global multicast or functional
		address (i.e., 0xC000xxxxxxxx)."
	::= { s5TrBStatEntry 10 }

s5TrBStatLlcUcastFrms OBJECT-TYPE
	SYNTAX	Counter
	ACCESS	read-only
	STATUS	mandatory
	DESCRIPTION
		"The total number of LLC frames (including
		frames with errors) detected on the ring
		that were directed to a LLC unicast address."
	::= { s5TrBStatEntry 11 }

s5TrBStatGoodErrReportFrms OBJECT-TYPE
	SYNTAX	Counter
	ACCESS	read-only
	STATUS	mandatory
	DESCRIPTION
		"The total number of Soft error Report frames
		(excluding frames with errors) detected on
		the ring."
	::= { s5TrBStatEntry 12 }

s5TrBStatBeaconFrms OBJECT-TYPE
	SYNTAX	Counter
	ACCESS	read-only
	STATUS	mandatory
	DESCRIPTION
		"The total number of Beacon frames (including
		frames with errors) detected on the ring."
	::= { s5TrBStatEntry 13 }

s5TrBStatRingPurgeFrms OBJECT-TYPE
	SYNTAX	Counter
	ACCESS	read-only
	STATUS	mandatory
	DESCRIPTION
		"The total number of Ring Purge frames (including
		frames with errors) detected on the ring."
	::= { s5TrBStatEntry 14 }

s5TrBStatClaimTokenFrms OBJECT-TYPE
	SYNTAX	Counter
	ACCESS	read-only
	STATUS	mandatory
	DESCRIPTION
		"The total number of Claim Token frames (including
		frames with errors) detected on the ring."
	::= { s5TrBStatEntry 15 }

s5TrBStatUna OBJECT-TYPE
	SYNTAX	MacAddress
	ACCESS	read-only
	STATUS	mandatory
	DESCRIPTION
		"The MAC address of the next active upstream
		neighbor (NAUN) (or upstream neighbor address (UNA))
		of the ring monitoring source. If it is unknown
		or at power reset (for example, no activity on the
		ring), the value is 00:00:00:00:00:00. The old
		value of the NAUN will be held, even if the ring
		becomes inactive (i.e., it will not clear to zero
		after no activity)."
	::= { s5TrBStatEntry 16 }



-- Frame Size Statistics Table


s5TrFStatTable OBJECT-TYPE
	SYNTAX	SEQUENCE OF S5TrFStatEntry
	ACCESS	not-accessible
	STATUS	obsolete
	DESCRIPTION
		"A table containing Token Ring frame
		size distribution statistics. These
		statistics are for LLC frames.
		Counters for frames and octets can
		be found in the basic statistics table.
		The entries in this table may come from
		several different data sources.
		The number of entries is determined
		by the number of sources that can
		provide the information."
	::= { s5TrStat 2 }

s5TrFStatEntry OBJECT-TYPE
	SYNTAX	S5TrFStatEntry
	ACCESS	not-accessible
	STATUS	obsolete
	DESCRIPTION
		"A row in Token Ring frame size
		distribution statistics table.
		Entries can not be created or deleted
		via SNMP."
	INDEX	{ s5TrFStatSrcIndx }
	::= { s5TrFStatTable 1 }

S5TrFStatEntry ::= SEQUENCE {
	s5TrFStatSrcIndx SrcIndx,
	s5TrFStatDropEvents Counter,
	s5TrFStatLlcFrms18to63Octets Counter,
	s5TrFStatLlcFrms64to127Octets Counter,
	s5TrFStatLlcFrms128to255Octets Counter,
	s5TrFStatLlcFrms256to511Octets Counter,
	s5TrFStatLlcFrms512to1023Octets Counter,
	s5TrFStatLlcFrms1024to2047Octets Counter,
	s5TrFStatLlcFrms2048to4095Octets Counter,
	s5TrFStatLlcFrms4096to8191Octets Counter,
	s5TrFStatLlcFrms8192to18000Octets Counter,
	s5TrFStatLlcFrmsGreaterThan18000Octets Counter
	}

s5TrFStatSrcIndx OBJECT-TYPE
	SYNTAX	SrcIndx
	ACCESS	read-only
	STATUS	obsolete
	DESCRIPTION
		"The index of the entry in the table.
		This index identifies the source of the
		information. Only those sources that provide
		these statistics are in this table."
	::= { s5TrFStatEntry 1 }

s5TrFStatDropEvents OBJECT-TYPE
	SYNTAX	Counter
	ACCESS	read-only
	STATUS	obsolete
	DESCRIPTION
		"The total number of events in which frames
		were dropped by the data source due to
		lack of resources.

		Note that this number is not necessarily the
		number of frames dropped; it is just the number
		of times this condition has been detected."
	::= { s5TrFStatEntry 2 }

s5TrFStatLlcFrms18to63Octets OBJECT-TYPE
	SYNTAX	Counter
	ACCESS	read-only
	STATUS	obsolete
	DESCRIPTION
		"The total number of LLC frames (excluding
		frames with errors) measured on the ring
		that were between 18 and 63 octets in
		length inclusive, excluding framing bits
		but including FCS octets."
	::= { s5TrFStatEntry 3 }

s5TrFStatLlcFrms64to127Octets OBJECT-TYPE
	SYNTAX	Counter
	ACCESS	read-only
	STATUS	obsolete
	DESCRIPTION
		"The total number of LLC frames (excluding
		frames with errors) measured on the ring
		that were between 64 and 127 octets in
		length inclusive, excluding framing bits
		but including FCS octets."
	::= { s5TrFStatEntry 4 }

s5TrFStatLlcFrms128to255Octets OBJECT-TYPE
	SYNTAX	Counter
	ACCESS	read-only
	STATUS	obsolete
	DESCRIPTION
		"The total number of LLC frames (excluding
		frames with errors) measured on the ring
		that were between 128 and 255 octets in
		length inclusive, excluding framing bits
		but including FCS octets."
	::= { s5TrFStatEntry 5 }

s5TrFStatLlcFrms256to511Octets OBJECT-TYPE
	SYNTAX	Counter
	ACCESS	read-only
	STATUS	obsolete
	DESCRIPTION
		"The total number of LLC frames (excluding
		frames with errors) measured on the ring
		that were between 256 and 511 octets in
		length inclusive, excluding framing bits
		but including FCS octets."
	::= { s5TrFStatEntry 6 }

s5TrFStatLlcFrms512to1023Octets OBJECT-TYPE
	SYNTAX	Counter
	ACCESS	read-only
	STATUS	obsolete
	DESCRIPTION
		"The total number of LLC frames (excluding
		frames with errors) measured on the ring
		that were between 512 and 1023 octets in
		length inclusive, excluding framing bits
		but including FCS octets."
	::= { s5TrFStatEntry 7 }

s5TrFStatLlcFrms1024to2047Octets OBJECT-TYPE
	SYNTAX	Counter
	ACCESS	read-only
	STATUS	obsolete
	DESCRIPTION
		"The total number of LLC frames (excluding
		frames with errors) measured on the ring
		that were between 1024 and 2047 octets in
		length inclusive, excluding framing bits
		but including FCS octets."
	::= { s5TrFStatEntry 8 }

s5TrFStatLlcFrms2048to4095Octets OBJECT-TYPE
	SYNTAX	Counter
	ACCESS	read-only
	STATUS	obsolete
	DESCRIPTION
		"The total number of LLC frames (excluding
		frames with errors) measured on the ring
		that were between 2048 and 4095 octets in
		length inclusive, excluding framing bits
		but including FCS octets."
	::= { s5TrFStatEntry 9 }

s5TrFStatLlcFrms4096to8191Octets OBJECT-TYPE
	SYNTAX	Counter
	ACCESS	read-only
	STATUS	obsolete
	DESCRIPTION
		"The total number of LLC frames (excluding
		frames with errors) measured on the ring
		that were between 4096 and 8191 octets in
		length inclusive, excluding framing bits
		but including FCS octets."
	::= { s5TrFStatEntry 10 }

s5TrFStatLlcFrms8192to18000Octets OBJECT-TYPE
	SYNTAX	Counter
	ACCESS	read-only
	STATUS	obsolete
	DESCRIPTION
		"The total number of LLC frames (excluding
		frames with errors) measured on the ring
		that were between 8192 and 18000 octets in
		length inclusive, excluding framing bits
		but including FCS octets."
	::= { s5TrFStatEntry 11 }

s5TrFStatLlcFrmsGreaterThan18000Octets OBJECT-TYPE
	SYNTAX	Counter
	ACCESS	read-only
	STATUS	obsolete
	DESCRIPTION
		"The total number of LLC frames (excluding
		frames with errors) measured on the ring
		that were greater than 18000 octets in
		length, excluding framing bits but
		including FCS octets."
	::= { s5TrFStatEntry 12 }



-- Error Statistics Table

s5TrEStatTable OBJECT-TYPE
	SYNTAX	SEQUENCE OF S5TrEStatEntry
	ACCESS	not-accessible
	STATUS	mandatory
	DESCRIPTION
		"A table containing Token Ring error
		statistics. The entries in the table
		may come from several different data
		sources. The number of entries is
		determined by the number of sources
		that can provide the information. (For
		example, this table is valid only on NMMs
		when they have become a Ring Error Monitor
		(REM)."
	::= { s5TrStat 3 }

s5TrEStatEntry OBJECT-TYPE
	SYNTAX	S5TrEStatEntry
	ACCESS	not-accessible
	STATUS	mandatory
	DESCRIPTION
		"A row in Token Ring error statistics table.
		Entries can not be created or deleted via
		SNMP."
	INDEX	{ s5TrEStatSrcIndx }
	::= { s5TrEStatTable 1 }

S5TrEStatEntry ::= SEQUENCE {
	s5TrEStatSrcIndx SrcIndx,
	s5TrEStatDropEvents Counter,
	s5TrEStatLineErrs Counter,
	s5TrEStatInternalErrs Counter,
	s5TrEStatBurstErrs Counter,
	s5TrEStatACErrs Counter,
	s5TrEStatAbortErrs Counter,
	s5TrEStatLostFrameErrs Counter,
	s5TrEStatCongestionErrs Counter,
	s5TrEStatFrameCopiedErrs Counter,
	s5TrEStatFrequencyErrs Counter,
	s5TrEStatTokenErrs Counter,
	s5TrEStatSoftErrFrms Counter
	}

s5TrEStatSrcIndx OBJECT-TYPE
	SYNTAX	SrcIndx
	ACCESS	read-only
	STATUS	mandatory
	DESCRIPTION
		"The index of the entry in the table.
		This index identifies the source of the
		information. Only those sources that provide
		these statistics are in this table."
	::= { s5TrEStatEntry 1 }

s5TrEStatDropEvents OBJECT-TYPE
	SYNTAX	Counter
	ACCESS	read-only
	STATUS	obsolete
	DESCRIPTION
		"Total number of events in which frames
		were dropped by the data source due to
		lack of resources.

		Note that this number is not necessarily the
		number of frames dropped; it is just the number
		of times this condition has been detected."
	::= { s5TrEStatEntry 2 }

s5TrEStatLineErrs OBJECT-TYPE
	SYNTAX	Counter
	ACCESS	read-only
	STATUS	mandatory
	DESCRIPTION
		"Total number of line errors reported by
		all stations in error report frames
		and detected on the ring.
		Section 3.8.1 of IEEE 802.5 specification."
	::= { s5TrEStatEntry 3 }

s5TrEStatInternalErrs OBJECT-TYPE
	SYNTAX	Counter
	ACCESS	read-only
	STATUS	mandatory
	DESCRIPTION
		"Total number of adapter internal errors
		reported by all stations in error report
		frames and detected on the ring.
		Section 3.8.2 of IEEE 802.5 specification."
	::= { s5TrEStatEntry 4 }

s5TrEStatBurstErrs OBJECT-TYPE
	SYNTAX	Counter
	ACCESS	read-only
	STATUS	mandatory
	DESCRIPTION
		"Total number of burst errors reported by
		all stations in error report frames
		and detected on the ring.
		Section 3.8.3 of IEEE 802.5 specification."
	::= { s5TrEStatEntry 5 }

s5TrEStatACErrs OBJECT-TYPE
	SYNTAX	Counter
	ACCESS	read-only
	STATUS	mandatory
	DESCRIPTION
		"Total number of AC (Address Copied) errors
		reported by all stations in error report frames
		and detected on the ring.
		Section 3.8.4 of IEEE 802.5 specification."
	::= { s5TrEStatEntry 6 }

s5TrEStatAbortErrs OBJECT-TYPE
	SYNTAX	Counter
	ACCESS	read-only
	STATUS	mandatory
	DESCRIPTION
		"Total number of abort delimiter transmitted
		errors reported by all stations in error report
		frames and detected on the ring.
		Section 3.8.5 of IEEE 802.5 specification."
	::= { s5TrEStatEntry 7 }

s5TrEStatLostFrameErrs OBJECT-TYPE
	SYNTAX	Counter
	ACCESS	read-only
	STATUS	mandatory
	DESCRIPTION
		"Total number of frames lost errors reported
		by all stations in error report frames
		and detected on the ring.
		Section 3.8.6 of IEEE 802.5 specification."
	::= { s5TrEStatEntry 8 }

s5TrEStatCongestionErrs OBJECT-TYPE
	SYNTAX	Counter
	ACCESS	read-only
	STATUS	mandatory
	DESCRIPTION
		"Total number of receive congestion errors
		reported by all stations in error report
		frames and detected on the ring.
		Section 3.8.7 of IEEE 802.5 specification."
	::= { s5TrEStatEntry 9 }

s5TrEStatFrameCopiedErrs OBJECT-TYPE
	SYNTAX	Counter
	ACCESS	read-only
	STATUS	mandatory
	DESCRIPTION
		"Total number of frame copied errors reported
		by all stations in error report frames
		and detected on the ring.
		Section 3.8.8 of IEEE 802.5 specification."
	::= { s5TrEStatEntry 10 }

s5TrEStatFrequencyErrs OBJECT-TYPE
	SYNTAX	Counter
	ACCESS	read-only
	STATUS	mandatory
	DESCRIPTION
		"Total number of frequency errors reported by
		all stations in error report frames
		and detected on the ring.
		Section 3.8.9 of IEEE 802.5 specification."
	::= { s5TrEStatEntry 11 }

s5TrEStatTokenErrs OBJECT-TYPE
	SYNTAX	Counter
	ACCESS	read-only
	STATUS	mandatory
	DESCRIPTION
		"Total number of token errors reported by
		all stations in error report frames
		and detected on the ring.
		Section 3.8.10 of IEEE 802.5 specification."
	::= { s5TrEStatEntry 12 }

s5TrEStatSoftErrFrms OBJECT-TYPE
	SYNTAX	Counter
	ACCESS	read-only
	STATUS	mandatory
	DESCRIPTION
		"Total number of error report frames detected
		on the ring. (Note: this has the same count
		as object s5TrBStatGoodErrReportFrms.)"
	::= { s5TrEStatEntry 13 }


-- Port Information Table

s5TrPortInfoTable OBJECT-TYPE
	SYNTAX	SEQUENCE OF S5TrPortInfoEntry
	ACCESS	not-accessible
	STATUS	mandatory
	DESCRIPTION
		"A table containing information for each managed 
		token ring connectivity port on a board, excluding 
		ring in, ring out, and those used as cascade expansion.
		The number of entries is determined by
		the number of manageable ports and the number 
		of occupied slots in s5ChasComTable whose 
		s5ChasComType is of a token Ring type and
		 is on the same backplane ring as the NMM interface."
	::= { s5TrCfg 6 }

s5TrPortInfoEntry OBJECT-TYPE
	SYNTAX	S5TrPortInfoEntry
	ACCESS	not-accessible
	STATUS	mandatory
	DESCRIPTION
		"A row in the port information table.
   		  Entries can not be created or
       		   deleted via SNMP."
	INDEX	{ s5TrPortInfoSrcIndx,
		  s5TrPortInfoBrdIndx,
		  s5TrPortInfoPortIndx }
	::= { s5TrPortInfoTable 1 }

S5TrPortInfoEntry ::= SEQUENCE {
	s5TrPortInfoSrcIndx SrcIndx,
	s5TrPortInfoBrdIndx INTEGER,
	s5TrPortInfoPortIndx INTEGER,
	s5TrPortInfoAddr MacAddress,
	s5TrPortInfoLastNaun MacAddress,
	s5TrPortInfoStationStatus INTEGER,
	s5TrPortInfoFirstEnterTime TimeTicks,
	s5TrPortInfoLastEnterTime TimeTicks,
	s5TrPortInfoLastExitTime TimeTicks,
	s5TrPortInfoDupAddrErrs Counter,
	s5TrPortInfoLineErrs Counter,
	s5TrPortInfoInternalErrs Counter,
	s5TrPortInfoBurstErrs Counter,
	s5TrPortInfoACErrs Counter,
	s5TrPortInfoAbortErrs Counter,
	s5TrPortInfoLostFrameErrs Counter,
	s5TrPortInfoCongestionErrs Counter,
	s5TrPortInfoFrameCopiedErrs Counter,
	s5TrPortInfoFrequencyErrs Counter,
	s5TrPortInfoTokenErrs Counter,
	s5TrPortInfoBeaconErrs Counter,
	s5TrPortInfoInsertions Counter
	}

s5TrPortInfoSrcIndx OBJECT-TYPE
	SYNTAX	SrcIndx
	ACCESS	read-only
	STATUS	mandatory
	DESCRIPTION
		"This index identifies the source of the
		information. Only those sources that provide
		these statistics are in this table."
	::= { s5TrPortInfoEntry 1 }

s5TrPortInfoBrdIndx OBJECT-TYPE
	SYNTAX	INTEGER
	ACCESS	read-only
	STATUS	mandatory
	DESCRIPTION
		"The index of the board. This corresponds to 
		the index of the slot containing the board."
	::= { s5TrPortInfoEntry 2 }

s5TrPortInfoPortIndx OBJECT-TYPE
	SYNTAX	INTEGER
	ACCESS	read-only
	STATUS	mandatory
	DESCRIPTION
	       "The index of the port on the board. 
	        Its value ranges between 1 and the 
		number of manageable ports on the board."
	::= { s5TrPortInfoEntry 3 }

s5TrPortInfoAddr OBJECT-TYPE
	SYNTAX	MacAddress
	ACCESS	read-only
	STATUS	mandatory
	DESCRIPTION
		"The MAC address of the station currently/last
		 attached to the port.
		 If no station in the ring can be found 
		 attached to the port, the address should be 0"
	::= { s5TrPortInfoEntry 4 }

s5TrPortInfoLastNaun OBJECT-TYPE
	SYNTAX	MacAddress
	ACCESS	read-only
	STATUS	mandatory
	DESCRIPTION
		"The MAC address of the last known NAUN (Next
		Active Upstream Neighbor) of the station 
		currently/last  attached to the port."
	::= { s5TrPortInfoEntry 5 }

s5TrPortInfoStationStatus OBJECT-TYPE
	SYNTAX	INTEGER {
		active(1),
		notInRingPoll(2),
		inactive(3),
		forcedRemoval(4)
		}
	ACCESS	read-only
	STATUS	mandatory
	DESCRIPTION
		"The insertion status of the station currently/last
		attached to the port. The values are:
		  active(1)..........Actively participating in
		                       ring poll from this port
		  notInRingPoll(2)...Detected on the ring, but
		                       not currently participating
		                       in the ring poll from this port
		  inactive(3)........ No  longer on the ring
				 from this port
		  forcedRemoval(4)... forced off the ring from this port 
				by network management."
		                     
				  
	::= { s5TrPortInfoEntry 6 }

s5TrPortInfoFirstEnterTime OBJECT-TYPE
	SYNTAX	TimeTicks
	ACCESS	read-only
	STATUS	mandatory
	DESCRIPTION
		"The value of sysUpTime when this port first time 
		entered the ring. 
		If the time is unknown, the value shall be zero."
	::= { s5TrPortInfoEntry 7 }

s5TrPortInfoLastEnterTime OBJECT-TYPE
	SYNTAX	TimeTicks
	ACCESS	read-only
	STATUS	mandatory
	DESCRIPTION
		"The value of sysUpTime when this port last time entered 
		the ring.
		 If the time is unknown, the value shall be zero."
	::= { s5TrPortInfoEntry 8 }

s5TrPortInfoLastExitTime OBJECT-TYPE
	SYNTAX	TimeTicks
	ACCESS	read-only
	STATUS	mandatory
	DESCRIPTION
		"The value of sysUpTime when this port last 
		exited the ring. 
		If the time is unknown, the value shall be zero."
	::= { s5TrPortInfoEntry 9 }

s5TrPortInfoDupAddrErrs OBJECT-TYPE
	SYNTAX	Counter
	ACCESS	read-only
	STATUS	mandatory
	DESCRIPTION
		"Total number of duplicate address error 
		detected from this port."
	::= { s5TrPortInfoEntry 10}

s5TrPortInfoLineErrs OBJECT-TYPE
	SYNTAX	Counter
	ACCESS	read-only
	STATUS	mandatory
	DESCRIPTION
		"Total number of line errors detected 
		from this port."
	::= { s5TrPortInfoEntry 11 }

s5TrPortInfoInternalErrs OBJECT-TYPE
	SYNTAX	Counter
	ACCESS	read-only
	STATUS	mandatory
	DESCRIPTION
		"Total number of adapter internal errors
		detected from  this port. "
	::= { s5TrPortInfoEntry 12 }

s5TrPortInfoBurstErrs OBJECT-TYPE
	SYNTAX	Counter
	ACCESS	read-only
	STATUS	mandatory
	DESCRIPTION
		"Total number of burst errors detected 
		from this port. "
	::= { s5TrPortInfoEntry 13 }

s5TrPortInfoACErrs OBJECT-TYPE
	SYNTAX	Counter
	ACCESS	read-only
	STATUS	mandatory
	DESCRIPTION
		"Total number of AC (Address Copied) 
		errors detected from this port. "
	::= { s5TrPortInfoEntry 14 }

s5TrPortInfoAbortErrs OBJECT-TYPE
	SYNTAX	Counter
	ACCESS	read-only
	STATUS	mandatory
	DESCRIPTION
		"Total number of abort delimiter 
		transmitted errors detected from this port."
	::= { s5TrPortInfoEntry 15 }

s5TrPortInfoLostFrameErrs OBJECT-TYPE
	SYNTAX	Counter
	ACCESS	read-only
	STATUS	mandatory
	DESCRIPTION
		"Total number of lost frame errors detected
		from this port. "
	::= { s5TrPortInfoEntry 16 }

s5TrPortInfoCongestionErrs OBJECT-TYPE
	SYNTAX	Counter
	ACCESS	read-only
	STATUS	mandatory
	DESCRIPTION
		"Total number of receive congestion errors
		detected from this port ."
	::= { s5TrPortInfoEntry 17 }

s5TrPortInfoFrameCopiedErrs OBJECT-TYPE
	SYNTAX	Counter
	ACCESS	read-only
	STATUS	mandatory
	DESCRIPTION
		"Total number of frame copied errors detected
		from this port."
	::= { s5TrPortInfoEntry 18 }

s5TrPortInfoFrequencyErrs OBJECT-TYPE
	SYNTAX	Counter
	ACCESS	read-only
	STATUS	mandatory
	DESCRIPTION
		"Total number of frequency errors detected
		from this port."
	::= { s5TrPortInfoEntry 19 }

s5TrPortInfoTokenErrs OBJECT-TYPE
	SYNTAX	Counter
	ACCESS	read-only
	STATUS	mandatory
	DESCRIPTION
		"Total number of token errors detected
		from this port."
	::= { s5TrPortInfoEntry 20 }

s5TrPortInfoBeaconErrs OBJECT-TYPE
	SYNTAX	Counter
	ACCESS	read-only
	STATUS	mandatory
	DESCRIPTION
		"Total number of beacon frames detected 
		from this port."
	::= { s5TrPortInfoEntry 21 }

s5TrPortInfoInsertions OBJECT-TYPE
	SYNTAX	Counter
	ACCESS	read-only
	STATUS	mandatory
	DESCRIPTION
		"Total number of times that the port
		was detected inserting into the ring."
	::= { s5TrPortInfoEntry 22 }


-- Port FPU Statistics table

s5TrPortFpuStatsTable OBJECT-TYPE
	SYNTAX	SEQUENCE OF S5TrPortFpuStatsEntry
	ACCESS	not-accessible
	STATUS	mandatory
	DESCRIPTION
		"A table containing FPU statistics 
		information for each managed token ring
		connectivity port on a board. "
	::= { s5TrCfg 7 }

s5TrPortFpuStatsEntry OBJECT-TYPE
	SYNTAX	S5TrPortFpuStatsEntry
	ACCESS	not-accessible
	STATUS	mandatory
	DESCRIPTION
		"A row in the Port FPU statistics table.
		Entries can not be created or deleted via SNMP. "
	INDEX	{ s5TrPortFpuStatsBrdIndx,
		  s5TrPortFpuStatsPortIndx }
	::= { s5TrPortFpuStatsTable 1 }

S5TrPortFpuStatsEntry ::= SEQUENCE {
	s5TrPortFpuStatsBrdIndx INTEGER,
	s5TrPortFpuStatsPortIndx INTEGER,
	s5TrPortFpuStatsAddr MacAddress,
	s5TrPortFpuStatsTxOctets Counter,
	s5TrPortFpuStatsTxPkts  Counter,
	s5TrPortFpuStatsRxOctets Counter,
	s5TrPortFpuStatsRxPkts Counter
	}


s5TrPortFpuStatsBrdIndx OBJECT-TYPE
	SYNTAX	INTEGER (1..255)
	ACCESS	read-only
	STATUS	mandatory
	DESCRIPTION
		"The index of the board. This corresponds to
		the index of the slot containing the board."
	::= { s5TrPortFpuStatsEntry 1 }

s5TrPortFpuStatsPortIndx OBJECT-TYPE
	SYNTAX	INTEGER (1..255)
	ACCESS	read-only
	STATUS	mandatory
	DESCRIPTION
		"The index of the port on the board. The
		value ranges between 1 and the number
		of manageable ports on the board."
	::= { s5TrPortFpuStatsEntry 2 }


s5TrPortFpuStatsAddr OBJECT-TYPE
	SYNTAX	MacAddress
	ACCESS	read-only
	STATUS	mandatory
	DESCRIPTION
		"The MAC address of the station currently/last 
		 attached to the port.
		For ring in, ring out and cascade expansion ports, 
		this MAC address is the UNA (Upstream Neighbor
		Address) as seen by the port.
		If no station has ever been connected to this port, 
		the address should be zero."
	::= { s5TrPortFpuStatsEntry 3 }


s5TrPortFpuStatsTxOctets OBJECT-TYPE
	SYNTAX	Counter
	ACCESS	read-only
	STATUS	mandatory
	DESCRIPTION
		"Total number of octets transmitted at this port.
		 If no station is connected to the port, 
		 the counter should return the last collected value."
	::= { s5TrPortFpuStatsEntry 4 }

s5TrPortFpuStatsTxPkts OBJECT-TYPE
	SYNTAX	Counter
	ACCESS	read-only
	STATUS	mandatory
	DESCRIPTION
		"Total number of packets transmitted at this port.
		 If no station is connected to the port, 
		 the counter should return the last collected value."
	::= { s5TrPortFpuStatsEntry 5 }

s5TrPortFpuStatsRxOctets OBJECT-TYPE
	SYNTAX	Counter
	ACCESS	read-only
	STATUS	mandatory
	DESCRIPTION
		"Total number of octets received at this port.
		 If no station is connected to the port, 
		 the counter should return the last collected value."
	::= { s5TrPortFpuStatsEntry 6 }

s5TrPortFpuStatsRxPkts OBJECT-TYPE
	SYNTAX	Counter
	ACCESS	read-only
	STATUS	mandatory
	DESCRIPTION
		"The number of packets receive at this port.
		 If no station is connected to the port, 
		 the counter should return the last collected value."
	::= { s5TrPortFpuStatsEntry 7 }

END
