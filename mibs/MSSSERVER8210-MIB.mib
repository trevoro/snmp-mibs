MSSSERVER8210-MIB DEFINITIONS ::= BEGIN

IMPORTS
   OBJECT-TYPE
         FROM RFC-1212
   proElsSubSysEventMsg
         FROM PROTEON-MIB
   enterprises
         FROM RFC1155-SMI
   TRAP-TYPE
         FROM RFC-1215;

--  MSSSERVER8210-MIB MODULE-IDENTITY
--            LAST-UPDATED "9711101200Z"
--            ORGANIZATION "IBM Corporation"
--            CONTACT-INFO
--            " Florian K Kandefer
--               Postal:  IBM Corporation
--                        800 Park Offices Drive
--                        Research Triangle Park, NC 27709
--                        US
--               Tel:     +1 919 254 0685
--               Fax:     +1 919 254 0391
--               E-mail:  kandefer@vnet.ibm.com     "
--            DESCRIPTION
--             " MSS Server 8210 Enterprise MIB
--
--               This MIB defines the enterprise specific management objects
--               for the IBM 8210 Nways Multiprotocol Switched Services Server
--               (MSS server stand-alone).
--
--               This MIB is defined in the SNMP version 1 SMI format.
--
--               MIB Version:
--
--                1)  This is the first version of this MIB
--                2)  Add PCI definition for FDDI and notPresent
--                    Added PCMCIA definition for notPresent
--                3)  Added PCMCIA definition for FLASH card
--             "

-- ===============
-- | Definitions |
-- ===============

--  PC adapter indicates a PCMCIA adapter.

-- =============
-- | Reminders |
-- =============

-- o The DisplayString data type is ASCII characters
-- o An implementation that conforms to this MIB shall implement all
--   variables for each mandatory group.
-- o If an Optional Group is implemented, all variables of that group
--   must be implemented.

-- ========
-- | OID's|
-- ========

ibm            OBJECT IDENTIFIER ::= { enterprises 2 }

ibmProd        OBJECT IDENTIFIER ::= { ibm 6 }

nwaysMSS       OBJECT IDENTIFIER ::= { ibmProd 118 }

mssServer8210  OBJECT IDENTIFIER ::= { nwaysMSS 2 }

-- ===============================
-- | Groups in MSSSERVER8210-MIB |
-- ===============================

mss8210Prod         OBJECT IDENTIFIER ::= { mssServer8210 1 }

mss8210PCAdapter    OBJECT IDENTIFIER ::= { mssServer8210 2 }

mss8210PCIAdapter   OBJECT IDENTIFIER ::= { mssServer8210 3 }


-- =====================
-- || The mss8210Prod ||
-- =====================
-- The mss8210Prod group is MANDATORY for all implementations of the
-- MSSSERVER8210-MIB. All implementations that claim conformance to this
-- MIB shall implement this group.

mss8210ResetFlag  OBJECT-TYPE
   SYNTAX  INTEGER {
           noreset (1),
           reboot  (2)}
   ACCESS  read-write
   STATUS  mandatory
   DESCRIPTION
        "The flag that controls the reset process in this stand-alone.
        This variable shall assume a value of noreset(1) in
        the absence of a request for a reset from the management
        application. This variable shall assume a value of reboot(2) if
        the management application requests that this stand-alone execute
        a complete hardware reboot which reloads the code load from
        storage."
   DEFVAL { noreset }
   ::= {mss8210Prod 1}

mss8210DRAMinstalled  OBJECT-TYPE
   SYNTAX  INTEGER
   ACCESS  read-only
   STATUS  mandatory
   DESCRIPTION
        "The total amount of dynamic RAM installed on this stand-alone.
        The amount is in units of megabytes."
   ::= {mss8210Prod 2}

mss8210NotifyStatus  OBJECT-TYPE
   SYNTAX  INTEGER {
           enabled  (1),
           disabled (2)}
   ACCESS  read-write
   STATUS  mandatory
   DESCRIPTION
        "The status of the trap reporting service in this stand-alone. This
        variable shall assume a value of enabled(1) if this stand-alone is
        permitted to send traps. This variable shall assume a value of
        disabled(2) if this stand-alone is prohibited from sending traps."
   DEFVAL { enabled }
   ::= {mss8210Prod 3}

mss8210TempThresholdStatus  OBJECT-TYPE
   SYNTAX  INTEGER {
           normal   (1),
           warning  (2),
           shutdown (3)}
   ACCESS  read-only
   STATUS  mandatory
   DESCRIPTION
        "The status of the temperature in this stand-alone. This variable
        shall assume a value of normal(1) if the temperature is within
        proper operating range for this stand-alone. This variable shall
        assume a value of warning(2) if the temperature becomes elevated
        but this stand-alone can still operate. This variable shall assume
        a value of shutdown(3) if the temperature is beyond the operating
        limits of this stand-alone."
   ::= {mss8210Prod 4}


-- ================================
-- || The mss8210PCAdapter group ||
-- ================================
-- The mss8210PCAdapter group is MANDATORY for all implementations of the
-- MSSSERVER8210-MIB. All implementations that claim conformance to this
-- MIB shall implement this group.

mss8210PCAdapNumSlot  OBJECT-TYPE
   SYNTAX  INTEGER
   ACCESS  read-only
   STATUS  mandatory
   DESCRIPTION
        "The number of PC adapter slots available for this stand-alone."
   ::= {mss8210PCAdapter 1}

mss8210PCAdapTable  OBJECT-TYPE
   SYNTAX  SEQUENCE OF Mss8210PCAdapEntry
   ACCESS  not-accessible
   STATUS  mandatory
   DESCRIPTION
        "A table of PC adapters entries. The number of entries is
        given by the value of mss8210PCAdapNumSlot."
   ::= {mss8210PCAdapter 2}

mss8210PCAdapEntry   OBJECT-TYPE
   SYNTAX  Mss8210PCAdapEntry
   ACCESS  not-accessible
   STATUS  mandatory
   DESCRIPTION
        "A PC adapter entry containing objects to describe the
        operational aspects of the PC adapter on this stand-alone."
   INDEX  {mss8210PCAdapSlotNum}
   ::= {mss8210PCAdapTable 1}

Mss8210PCAdapEntry  ::=
   SEQUENCE {
        mss8210PCAdapSlotNum
           INTEGER,
        mss8210PCAdapType
           INTEGER
   }

mss8210PCAdapSlotNum   OBJECT-TYPE
   SYNTAX  INTEGER
   ACCESS  read-only
   STATUS  mandatory
   DESCRIPTION
        "The relative slot location at which the adapter is attached to
        this stand-alone.  The slots are numbered from 1 to 2 (left to right)
        when facing this stand-alone. This variable serves as the index
        for the mss8210PCAdapTable."
   ::= {mss8210PCAdapEntry 1}

mss8210PCAdapType  OBJECT-TYPE
   SYNTAX  INTEGER {
           unknown     (1),
           harddrive   (2),
           modem       (3),
           notPresent  (4),
           flashcard    (5)}
   ACCESS  read-only
   STATUS  mandatory
   DESCRIPTION
        "The type of PC adapter that is inserted into this slot.
        The variable shall assume a value of unknown(1) if the adapter
        in the slot is not supported by this stand-alone. The variable
        shall assume a value of harddrive(2) if the slot contains a PC disk
        drive. The variable shall assume a value of modem(3) if the
        slot contains a PC data/fax/voice modem. The variable shall
        assume a value of flashcard(5) if the slot contains a PC flash card.
        This variable shall assume a value of notPresent(4), when a
        PC card is not plugged into the corrisponding slot.
        "
   ::= {mss8210PCAdapEntry 2}

-- =================================
-- || The mss8210PCIAdapter group ||
-- =================================
-- The mss8210PCIAdapter group is MANDATORY for all implementations of the
-- MSSSERVER8210-MIB. All implementations that claim conformance to this MIB
-- shall implement this group.

mss8210PCIAdapNumSlot  OBJECT-TYPE
   SYNTAX  INTEGER
   ACCESS  read-only
   STATUS  mandatory
   DESCRIPTION
        "The number of PCI adapter slots available for this stand-alone."
   ::= {mss8210PCIAdapter 1}

mss8210PCIAdapTable  OBJECT-TYPE
   SYNTAX  SEQUENCE OF Mss8210PCIAdapEntry
   ACCESS  not-accessible
   STATUS  mandatory
   DESCRIPTION
        "A table of PCI adapters entries. The number of entries is
        given by the value of mss8210PCIAdapNumSlot."
   ::= {mss8210PCIAdapter 2}

mss8210PCIAdapEntry  OBJECT-TYPE
   SYNTAX  Mss8210PCIAdapEntry
   ACCESS  not-accessible
   STATUS  mandatory
   DESCRIPTION
        "A PCI adapter entry containing objects to describe the
        operational aspects of the PCI adapter on this stand-alone."
   INDEX  {mss8210PCIAdapSlotNum}
   ::= {mss8210PCIAdapTable 1}

Mss8210PCIAdapEntry  ::=
   SEQUENCE {
        mss8210PCIAdapSlotNum
           INTEGER,
        mss8210PCIAdapType
           INTEGER,
        mss8210PCIAdapConfigType
           INTEGER,
        mss8210PCIAdapOperStatus
           INTEGER,
        mss8210PCIAdapDiagStatus
           INTEGER,
        mss8210PCIAdapNetworkStatus
           INTEGER,
        mss8210PCIAdapFaultStatus
           INTEGER
   }

mss8210PCIAdapSlotNum  OBJECT-TYPE
   SYNTAX  INTEGER
   ACCESS  read-only
   STATUS  mandatory
   DESCRIPTION
        "The relative slot location at which the adapter is attached to
        this stand-alone.  Slots are numbered from 1 to 2 (top to
        bottom) when facing this stand-alone. This variable serves as the
        index for the mss8210PCIAdapTable."
   ::= {mss8210PCIAdapEntry 1}

mss8210PCIAdapType  OBJECT-TYPE
   SYNTAX  INTEGER {
           unknown    (1),
           atm        (2),
           fddi       (3),
           notPresent (4)}
   ACCESS  read-only
   STATUS  mandatory
   DESCRIPTION
        "The type of PCI adapter that is inserted into this slot.
        This variable shall assume a value of unknown(1) if the
        mss8210PCIAdapConfigType is not-configured(1) or if the
        mss8210PCIAdapConfigType is atm(2) and the mss8210PCIAdapOperStatus
        has a value of unknown(1), not-configured(2), not-present(3),
        unavailable(4), does-not_apply(5) or miss-configured(10).
        The variable shall assume a value of atm(2) if the
        mss8210PCIAdapConfigType has a value of atm(2) and the
        mss8210PCIAdapOperStatus has a value of enabled-pending(6),
        enabled(7), disabled-pending(8) or disabled(9).
        The variable shall assume a value of fddi(3) if the
        mss8210PCIAdapConfigType has a value of fddi(3) and the
        mss8210PCIAdapOperStatus has a value of enabled-pending(6),
        enabled(7), disabled-pending(8) or disabled(9).
        This variable shall assue a value of notPresent(4), when a
        PCI card is not plugged into the corrisponding slot.
        "
   ::= {mss8210PCIAdapEntry 2}

mss8210PCIAdapConfigType  OBJECT-TYPE
   SYNTAX  INTEGER {
           not-configured (1),
           atm            (2),
           fddi           (3)}
   ACCESS  read-only
   STATUS  mandatory
   DESCRIPTION
        "The router configuration type for this slot. The configuration
        type originates from the configuration tool used for this
        stand-alone. The variable shall assume a value of
        not-configured(1) if no configuration exist for this slot. The
        variable shall assume a value of atm(2) if the slot is
        configured for an ATM adapter. The variable shall assume a value
        of fddi(3) if the slot is configured for an FDDI adapter."
   ::= {mss8210PCIAdapEntry 3}

mss8210PCIAdapOperStatus  OBJECT-TYPE
   SYNTAX  INTEGER {
           unknown         (1),
           not-configured  (2),
           not-present     (3),
           unavailable     (4),
           does-not-apply  (5),
           enable-pending  (6),
           enabled         (7),
           disable-pending (8),
           disabled        (9),
           miss-configured (10)}
   ACCESS  read-only
   STATUS  mandatory
   DESCRIPTION
        "The operational status of this PCI adapter on this stand-alone.
        The variable shall assume a value of unknown(1) if the adapter
        inserted in the slot can not be recognized. The variable shall
        assume a value of not-configured(2) if the adapter inserted in
        the slot is recognized but no router configuration exists. The
        variable shall assume a value of not-present(3) if the adapter
        is not inserted in the slot but the router configuration exists.
        The variable shall assume a value of unavailable(4) if adapter
        inserted in the slot can not be used nor made ready to be used;
        for example, a hardware error. The variable shall assume a value
        of does-not-apply(5) if this adapter does not contain an
        operational state. The variable shall assume a value of
        enable-pending(6) if commands have been issued to enable the
        adapter but have not been completed. The variable shall assume
        a value of enabled(7) if commands have been successfully issued
        to enable the adapter. The variable shall assume a value of
        disable-pending(8) if commands have been issued to disable the
        adapter but have not been completed. The variable shall assume
        a value of disabled(9) if commands have been successfully issued
        to disable the adapter. The variable shall assume a value of
        miss-configured(10) if the adapter is inserted in the slot
        but the router configuration is of a different type."
   ::= {mss8210PCIAdapEntry 4}

mss8210PCIAdapDiagStatus  OBJECT-TYPE
   SYNTAX  INTEGER {
           auto         (1),
           inactive     (2),
           idle         (3),
           active       (4)}
   ACCESS  read-only
   STATUS  mandatory
   DESCRIPTION
        "The diagnostic status of this PCI adapter on this stand-alone.
        The variable shall assume a value of auto(1) if commands have
        been issued by the system to determine the status of the
        adapter; for example, at initialization. The variable shall
        assume a value of inactive(2) if the adapter is not currently
        running any diagnostics. The variable shall assume a value
        of idle(3) if the adapter is in the disabled operational state
        ready to run the diagnostics. The variable shall assume a value
        of active(4) if commands have been issued by the user to
        run the diagnostics."
   ::= {mss8210PCIAdapEntry 5}

mss8210PCIAdapNetworkStatus  OBJECT-TYPE
   SYNTAX  INTEGER {
           unknown         (1),
           up              (2),
           down            (3),
           testing         (4),
           does-not-apply  (5)}
   ACCESS  read-only
   STATUS  mandatory
   DESCRIPTION
        "The network status of this PCI adapter on this stand-alone.
        The variable shall assume a value of up(1) if the adapter
        is connected to the network. The variable shall assume a value
        of down(3) if the adapter can not verify a network connection.
        The variable shall assume a value of testing(4) if the
        adapter is running tests for the network connection. The
        variable shall assume a value of unknown(1) if network status
        can not be determined. The variable shall assume a value of
        does-not-apply(5) if the adapter does not contain a network
        state."
   ::= {mss8210PCIAdapEntry 6}

mss8210PCIAdapFaultStatus  OBJECT-TYPE
   SYNTAX  INTEGER {
           unknown         (1),
           no-fault        (2),
           isolated        (3),
           non-isolated    (4)}
   ACCESS  read-only
   STATUS  mandatory
   DESCRIPTION
        "The fault status of this PCI adapter on this stand-alone.
        The variable shall assume a value of no-fault(2)
        if no fault that is associated with this adapter has been
        detected. The variable shall assume a value of isolated(3) if this
        fault that can be isolated on the adapter itself. The variable
        shall assume a value of non-isolated(4) if the fault
        can not isolated on the adapter or in the network.
        The variable shall assume a value of unknown(1) if the
        fault status has not been determined; for example, at
        initialization."
   ::= {mss8210PCIAdapEntry 7}

-- ======================
-- || Trap Definitions ||
-- ======================

mssServer8210ELSTrapV2 TRAP-TYPE
   ENTERPRISE   mssServer8210
   VARIABLES    { proElsSubSysEventMsg }
   DESCRIPTION
       "The trap announces that an Event Logging System (ELS) event
       occurred. The variable proElsSubSysEventMsg provides a textual
       description of the event. The variable is in one of two
       formats. If ELS timestamping is enabled, the format is
       hr:min:sec subsys_name.event_num: message_text. An example
       would be 09:32:56 IP.008: no rte 9.7.1.8 -> 9.7.4.3 dsc.
       If ELS timestamping is disabled, the format is
       subsys_name.event_num: message_text. An example would be
       IP.008: no rte 9.7.1.8 -> 9.7.4.3 dsc."
   ::= 2

mss8210PCAdapTypeChg TRAP-TYPE
   ENTERPRISE   mssServer8210
   VARIABLES    { mss8210PCAdapType }
   DESCRIPTION
        "The trap announces a change in the type of PC card. It shall be
        sent if the value of the mss8210PCAdapType changes and
        mss8210NotifyStatus has a value of enabled(1)."
   ::= 3

mss8210TempThresholdChg TRAP-TYPE
   ENTERPRISE   mssServer8210
   VARIABLES    { mss8210TempThresholdStatus }
   DESCRIPTION
        "The trap announces a change in the temperature of the stand-alone.
        It shall be sent if the value of the mss8210TempThreshold changes
        and mss8210NotifyStatus has a value of enabled(1)."
   ::= 4

mss8210PCIAdapStatusChg TRAP-TYPE
   ENTERPRISE   mssServer8210
   VARIABLES    { mss8210PCIAdapConfigType,
                  mss8210PCIAdapOperStatus,
                  mss8210PCIAdapDiagStatus,
                  mss8210PCIAdapNetworkStatus,
                  mss8210PCIAdapFaultStatus}
   DESCRIPTION
        "The trap announces a change in the status of the PCI adapter.
        It shall be sent if the value of either mss8210PCIAdapConfigType,
        mss8210PCIAdapOperStatus, mss8210PCIAdapDiagStatus,
        mss8210PCIAdapNetworkStatus or mss8210PCIAdapFaultStatus changes
        and mss8210NotifyStatus has a value of enabled(1)."
   ::= 5

END
