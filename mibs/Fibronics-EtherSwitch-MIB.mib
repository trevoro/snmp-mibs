Fibronics-EtherSwitch-MIB DEFINITIONS ::= BEGIN

-- Title:         Fibronics' MIB  
-- MIB Module :   Private MIB for  XM516
-- Version    :   V1.0
-- Date       :   Jan 1, 1995
-- By         :   Gadi K.
-- Contact    :   Edna Ganon
-- Email:     :   edna@fibronics.co.il 
-- 
-- Description:   Fibronics EtherSwitch MIB   
-- Copyright (c) 1994 Fibronics International
-- Copyright 1994 Kalpana.  All rights reserved.


IMPORTS
	TimeTicks, IpAddress, Counter, enterprises
			FROM RFC1155-SMI
	OBJECT-TYPE
			FROM RFC-1212
	DisplayString
			FROM RFC1213-MIB;

-- Ethernet station MAC address

MacAddr ::= OCTET STRING (SIZE(6))

fibronics  OBJECT IDENTIFIER    ::= { enterprises 22}      


-- System Object ID defintions for Fibronics EtherSwitches

products            OBJECT IDENTIFIER ::= { fibronics 100 }
eth-switch          OBJECT IDENTIFIER ::= { products 9 }
xm516-card          OBJECT IDENTIFIER ::= { eth-switch 3}
xm517-card          OBJECT IDENTIFIER ::= { eth-switch 4}
xm518-card          OBJECT IDENTIFIER ::= { eth-switch 5}
xm519-card          OBJECT IDENTIFIER ::= { eth-switch 6}
xm5110-card         OBJECT IDENTIFIER ::= { eth-switch 7}
xm5111-card         OBJECT IDENTIFIER ::= { eth-switch 8}
xm5112-card         OBJECT IDENTIFIER ::= { eth-switch 9}
xm5113-card         OBJECT IDENTIFIER ::= { eth-switch 10}
xm5114-card         OBJECT IDENTIFIER ::= { eth-switch 11}
xm5115-card         OBJECT IDENTIFIER ::= { eth-switch 12}

-- Managed Object defintions for Fibronics EtherSwitch

mibs                OBJECT IDENTIFIER ::= { fibronics    101 }
mibsbridges         OBJECT IDENTIFIER ::= { mibs 9 }
mibbridges-specific OBJECT IDENTIFIER ::= { mibsbridges 1 }
mibeth2eth          OBJECT IDENTIFIER ::= { mibbridges-specific 2}
mib-eps             OBJECT IDENTIFIER ::= { mibeth2eth 1  }

-- Managed Objects

fibEsObjects          OBJECT IDENTIFIER ::= { mib-eps 1 }

-- Managed Groups

fibEsMain	OBJECT IDENTIFIER ::= { fibEsObjects 1 }

-- Configuration objects
fibEsConfig	OBJECT IDENTIFIER ::= { fibEsMain 1 }

-- System Module objects
fibEsSys	OBJECT IDENTIFIER ::= { fibEsMain 2 }

-- Port level objects
fibEsPort	OBJECT IDENTIFIER ::= { fibEsObjects 2 }



-- Configuration group

fibEsFwVer OBJECT-TYPE
	SYNTAX	DisplayString
	ACCESS	read-only
	STATUS	mandatory
	DESCRIPTION
		"The firmware version in the form major.minor."
	::= { fibEsConfig 1 }

fibEsHwVer OBJECT-TYPE
	SYNTAX	DisplayString
	ACCESS	read-only
	STATUS	mandatory
	DESCRIPTION
		"The hardware version in the form major.minor."
	::= { fibEsConfig 2 }

fibEsIpAddr OBJECT-TYPE
	SYNTAX	IpAddress
	ACCESS	read-write
	STATUS	mandatory
	DESCRIPTION
		"The administrative value of the IP address.  The
		current operational IP address can be obtained by
		the ipAdEntAddr entry in the ipAddrTable.

		This parameter will take effect only after a reset
		(fibEsReset) is issued or a power cycle."
	::= { fibEsConfig 3 }

fibEsNetMask OBJECT-TYPE
	SYNTAX	IpAddress
	ACCESS	read-write
	STATUS	mandatory
	DESCRIPTION
		"The administrative value of the subnet mask.  The
		current operational subnet mask can be obtained by
		the ipAdEntNetMask entry in the ipAddrTable.

		This parameter will take effect only after a reset
		(fibEsReset) is issued or a power cycle."
	::= { fibEsConfig 4 }

fibEsDefaultGateway OBJECT-TYPE
	SYNTAX	IpAddress
	ACCESS	read-write
	STATUS	mandatory
	DESCRIPTION
		"The administrative value of the default gateway
		(router) IP address.  The current operational
		default gateway's IP address can be obtained from
		the ipRouteTable.

		This parameter will take effect only after a reset
		(fibEsReset) is issued or a power cycle."
	::= { fibEsConfig 5 }

fibEsTrapRcvrMaxEnt OBJECT-TYPE
	SYNTAX	INTEGER
	ACCESS	read-only
	STATUS	mandatory
	DESCRIPTION
		"The maximum number of rows in the trap receiver
		table."
	::= { fibEsConfig 6 }

fibEsTrapRcvrCurEnt OBJECT-TYPE
	SYNTAX	INTEGER
	ACCESS	read-only
	STATUS	mandatory
	DESCRIPTION
		"The current number of rows in the trap receiver
		table."
	::= { fibEsConfig 7 }

fibEsTrapRcvrNext OBJECT-TYPE
	SYNTAX	INTEGER (0..655535)
	ACCESS	read-only
	STATUS	mandatory
	DESCRIPTION
		"The index of the next available row to be created
		in the trap receiver table.  A value of zero means
		that the table is full and no more rows can be
		added."
	::= { fibEsConfig 8 }

fibEsTrapRcvrTable OBJECT-TYPE
	SYNTAX	SEQUENCE OF FibEsTrapRcvrEntry
	ACCESS	not-accessible
	STATUS	mandatory
	DESCRIPTION
		"A table of managers to which to send traps.
		Entries in the table are saved across resets and
		power cycles."
	::= { fibEsConfig 9 }

fibEsTrapRcvrEntry OBJECT-TYPE
	SYNTAX	FibEsTrapRcvrEntry
	ACCESS	not-accessible
	STATUS	mandatory
	DESCRIPTION
		"Definition of rows in the trap receiver table.
		The column fibEsTrapRcvrStatus is used to create
		and delete rows in the table.  Creation requires
		a SET PDU with objects fibEsTrapRcvrStatus,
		fibEsTrapRcvrIpAddress, and fibEsTrapRcvrComm."
	INDEX	{ fibEsTrapRcvrIndex }
	::= { fibEsTrapRcvrTable 1 }

FibEsTrapRcvrEntry ::= SEQUENCE {
	fibEsTrapRcvrIndex	INTEGER,
	fibEsTrapRcvrStatus	INTEGER,
	fibEsTrapRcvrIpAddress	IpAddress,
	fibEsTrapRcvrComm	DisplayString
	}

fibEsTrapRcvrIndex OBJECT-TYPE
	SYNTAX	INTEGER (1..65535)
	ACCESS	read-only
	STATUS	mandatory
	DESCRIPTION
		"The index of the row in the table."
	::= { fibEsTrapRcvrEntry 1 }

fibEsTrapRcvrStatus OBJECT-TYPE
	SYNTAX	INTEGER {
		other(1),	-- none of the following
		valid(2),	-- a valid address
		invalid(3),	-- an invalid address
		create(4)	-- create row
		}
	ACCESS	read-write
	STATUS	mandatory
	DESCRIPTION
		"Setting this object to the value invalid(3)
		deletes the row from the table.  The value
		invalid(3) should never be returned on a GET.  The
		value of create(4) on a SET causes a new row to be
		created if the row does not already exist.  If it
		does, then a 'badValue'error should be returned.
		The value returned on GETs should be valid(2) or
		other(1), which is used to indicate any other
		condition."
	::= { fibEsTrapRcvrEntry 2 }

fibEsTrapRcvrIpAddress OBJECT-TYPE
	SYNTAX	IpAddress
	ACCESS	read-write
	STATUS	mandatory
	DESCRIPTION
		"IP address for an SNMP manager that is to receive
		the trap."
	::= { fibEsTrapRcvrEntry 3 }

fibEsTrapRcvrComm OBJECT-TYPE
	SYNTAX	DisplayString
	ACCESS	read-write
	STATUS	mandatory
	DESCRIPTION
		"Community string to use."
	::= { fibEsTrapRcvrEntry 4 }


-- System Group

fibEsNumPorts OBJECT-TYPE
	SYNTAX	INTEGER
	ACCESS	read-only
	STATUS	mandatory
	DESCRIPTION
		"The maximum number of ports on the switch."
	::= { fibEsSys 1 }

fibEsNumStations OBJECT-TYPE
	SYNTAX	INTEGER
	ACCESS	read-only
	STATUS	mandatory
	DESCRIPTION
		"Aggregate number of currently active stations
		(nodes) on all ports on the switch.  This is the
		value from the system module."
	::= { fibEsSys 2 }

fibEsMostStations OBJECT-TYPE
	SYNTAX	INTEGER
	ACCESS	read-only
	STATUS	mandatory
	DESCRIPTION
		"Highest aggregate number of stations ever active
		on all ports at one time, since the last reset or
		power cycle.  This is the value as seen by the
		system module."
	::= { fibEsSys 3 }

fibEsMaxStations OBJECT-TYPE
	SYNTAX	INTEGER
	ACCESS	read-only
	STATUS	mandatory
	DESCRIPTION
		"Highest aggregate number of stations which the
		switch can support simultaneously.  (This is the
		maximum number that the system module can
		support.)"
	::= { fibEsSys 4 }

fibEsReset OBJECT-TYPE
	SYNTAX	INTEGER {
		other(1),	-- none of the following
		running(2),	-- switch is running
		softReset(3),	-- do soft reset of switch
		hardReset(4)	-- do hard reset of switch
		}
	ACCESS	read-write
	STATUS	mandatory
	DESCRIPTION
		"This object is used to reset the switch.  Writing
		softReset(3) causes the switch to reset the
		hardware, run quick diagnostics, clear all
		counters, start switching, issue a warmstart trap,
		and then be able to respond to SNMP requests.
		Writing hardReset(4) causes the switch to run
		power up diagnostics and then execute a soft
		reset.	Note:  all address tables are cleared in
		both cases.  The administrative parameters from
		nonvolatile memory are used to initialize the
		operational parameters.  The value returned on GETs 
		should be running(2) or other(1), which is used to
		indicate any other condition."
	::= { fibEsSys 5 }

fibEsNumResets OBJECT-TYPE
	SYNTAX	Counter
	ACCESS	read-only
	STATUS	mandatory
	DESCRIPTION
		"Number of soft resets the switch has executed
		since the last hard reset or power cycle.  Soft
		resets are defined as writing softReset(3) to
		fibEsReset, pressing the front panel reset button,
		executing a soft reset from the console, or resets
		induced by the switch firmware."
	::= { fibEsSys 6 }

fibEsAddrAgingTime OBJECT-TYPE
	SYNTAX	INTEGER (0..9999)
	ACCESS	read-write
	STATUS	mandatory
	DESCRIPTION
		"Number of minutes of inactivity before an address
		entity is aged out.  A value of zero means no
		aging.	Note:  if an address shows up on another
		port, the original port to address assignment is
		automatically deleted.  The value is saved across
		resets and power cycles."
	::= { fibEsSys 7 }

fibEsSysStaTable OBJECT-TYPE
	SYNTAX	SEQUENCE OF FibEsSysStaEntry
	ACCESS	not-accessible
	STATUS	mandatory
	DESCRIPTION
		"A table of station addresses from all ports known
		to the system module."
	::= { fibEsSys 9 }

fibEsSysStaEntry OBJECT-TYPE
	SYNTAX	FibEsSysStaEntry
	ACCESS	not-accessible
	STATUS	mandatory
	DESCRIPTION
		"Definition of the rows in the system module
		station address table.	Rows can not be created or
		deleted via SNMP requests."
	INDEX	{ fibEsSysStaMacAddr }
	::= { fibEsSysStaTable 1 }

FibEsSysStaEntry ::= SEQUENCE {
	fibEsSysStaMacAddr	MacAddr,
	fibEsSysStaPort 	INTEGER,
	fibEsSysStaTraffic	OCTET STRING
	}

fibEsSysStaMacAddr OBJECT-TYPE
	SYNTAX	MacAddr
	ACCESS	read-only
	STATUS	mandatory
	DESCRIPTION
		"The Station's MAC address."
	::= { fibEsSysStaEntry 1 }

fibEsSysStaPort OBJECT-TYPE
	SYNTAX	INTEGER
	ACCESS	read-only
	STATUS	mandatory
	DESCRIPTION
		"The source port for the Station."
	::= { fibEsSysStaEntry 2 }

fibEsSysStaTraffic OBJECT-TYPE
	SYNTAX	OCTET STRING
	ACCESS	read-only
	STATUS	mandatory
	DESCRIPTION
		"A bit string that identifies with value of one of
		the ports that this station has generated traffic
		to or from.  The bits are numbered starting at zero,
		with bit zero being the high order bit in the first
		byte, bit seven being the low order bit in the first
		byte, bit eight being the high order bit in the second
		byte, etc.  Ports correspond with bits (i.e., port 1 is
		bit 1, etc.).	The size of this in octets is the number
		of ports (i.e., fibEsNumPorts), divided by 8, plus
		one."
	::= { fibEsSysStaEntry 3 }

-- Port level objects

-- Fibronics EtherSwitch Port table

fibEsPortTable OBJECT-TYPE
	SYNTAX	SEQUENCE OF FibEsPortEntry
	ACCESS	not-accessible
	STATUS	mandatory
	DESCRIPTION
		"A table of information about each port.  The
		number of rows is given by fibEsNumPorts."
	::= { fibEsPort 1 }

fibEsPortEntry OBJECT-TYPE
	SYNTAX	FibEsPortEntry
	ACCESS	not-accessible
	STATUS	mandatory
	DESCRIPTION
		"Definition of rows in the port table.  The number
		of rows is determined by the hardware and is
		specified by the value of fibEsNumPorts.  Rows can
		not be created or deleted via SNMP requests."
	INDEX { fibEsPortIndex }
	::= { fibEsPortTable 1 }

FibEsPortEntry ::= SEQUENCE {
	fibEsPortIndex		INTEGER,
	fibEsPortOprStatus	INTEGER,
	fibEsPortDuplex 	INTEGER,
	fibEsPortRcvLocalFrames Counter,
	fibEsPortForwardedFrames Counter,
	fibEsPortMostStations	Counter,
	fibEsPortMaxStations	Counter,
	fibEsPortSWHandledFrames Counter,
	fibEsPortLocalStations	Counter,
	fibEsPortRemoteStations Counter,
	fibEsPortUnknownStaFrames Counter,
	fibEsPortResetStats	INTEGER,
	fibEsPortResetTimer	TimeTicks,
	fibEsPortResetAddrs	INTEGER,
	fibEsPortRcvBcasts	Counter,
	fibEsPortSwitchedFrames  Counter
	}

fibEsPortIndex OBJECT-TYPE
	SYNTAX	INTEGER (1..65535)
	ACCESS	read-only
	STATUS	mandatory
	DESCRIPTION
		"A unique value for each port entry.  The value
		corresponds the port number."
	::= { fibEsPortEntry 1 }

fibEsPortOprStatus OBJECT-TYPE
	SYNTAX	INTEGER {
		enabled(1),	-- port enabled
		disabled(2)	-- port disabled
		}
	ACCESS	read-write
	STATUS	mandatory
	DESCRIPTION
		"The operational status of the port.  Setting to
		enabled(1) enables the port.  Setting to
		disabled(2) disables the port.  The value is saved across
		resets and power cycles."
	::= { fibEsPortEntry 2 }

fibEsPortDuplex OBJECT-TYPE
	SYNTAX	INTEGER {
		fullDuplex(1),
		halfDuplex(2)
		}
	ACCESS	read-only
	STATUS	mandatory
	DESCRIPTION
		"Indicates whether the port is jumper configured
		for full or half duplex operation.  Note:
		internal connected ports are always
		halfDuplex(2)."
	::= { fibEsPortEntry 3 }

fibEsPortRcvLocalFrames OBJECT-TYPE
	SYNTAX	Counter
	ACCESS	read-only
	STATUS	mandatory
	DESCRIPTION
		"Number of frames received where the destination
		is on this port."
	::= { fibEsPortEntry 4 }

fibEsPortForwardedFrames OBJECT-TYPE
	SYNTAX	Counter
	ACCESS	read-only
	STATUS	mandatory
	DESCRIPTION
		"Number of frames received on this port and
		 forwarded to another port or the system module 
                 for processing."
	::= { fibEsPortEntry 5 }

fibEsPortMostStations OBJECT-TYPE
	SYNTAX	Counter
	ACCESS	read-only
	STATUS	mandatory
	DESCRIPTION
		"Highest number of stations ever active at any
		time since the last reset of the switch as seen by
		this port."
	::= { fibEsPortEntry 6 }

fibEsPortMaxStations OBJECT-TYPE
	SYNTAX	Counter
	ACCESS	read-only
	STATUS	mandatory
	DESCRIPTION
		"Maximum number of stations which the port can
		support simultaneously."
	::= { fibEsPortEntry 7 }

fibEsPortSWHandledFrames OBJECT-TYPE
	SYNTAX	Counter
	ACCESS	read-only
	STATUS	mandatory
	DESCRIPTION
		"Number of Frames received on this port and
		delivered to the system module for processing."
	::= { fibEsPortEntry 8 }

fibEsPortLocalStations OBJECT-TYPE
	SYNTAX	Counter
	ACCESS	read-only
	STATUS	mandatory
	DESCRIPTION
		"Number of stations on this port's address table
                 which belong to the segment attached to this port."
	::= { fibEsPortEntry 9 }

fibEsPortRemoteStations OBJECT-TYPE
	SYNTAX	Counter
	ACCESS	read-only
	STATUS	mandatory
	DESCRIPTION
		"Number of stations on this port's address table
                 which belong to segments attached to other ports."
	::= { fibEsPortEntry 10 }

fibEsPortUnknownStaFrames OBJECT-TYPE
	SYNTAX	Counter
	ACCESS	read-only
	STATUS	mandatory
	DESCRIPTION
		"Number of unicast frames received on this port
		and forwarded to the system module for processing
		because the source or destination station address 
		is not in the port's forwarding table."
	::= { fibEsPortEntry 11 }

fibEsPortResetStats OBJECT-TYPE
	SYNTAX	INTEGER {
		other(1),	-- none of the following
		running(2),	-- port is functioning
		reset(3)	-- reset port counters
		}
	ACCESS	read-write
	STATUS	mandatory
	DESCRIPTION
		"Setting this object to reset(3) causes all
		traffic counters for this port to be set to zero.
		Also the value of fibEsPortResetTimer is set to
		zero."
	::= { fibEsPortEntry 12 }

fibEsPortResetTimer OBJECT-TYPE
	SYNTAX	TimeTicks
	ACCESS	read-only
	STATUS	mandatory
	DESCRIPTION
		"Time (in 100th second ticks) since the port
		counters were reset."
	::= { fibEsPortEntry 13 }


fibEsPortResetAddrs OBJECT-TYPE
	SYNTAX	INTEGER {
		other(1),	-- none of the following
		running(2),	-- port is functioning
		reset(3)	-- clear address table &
		}		--  reset port counters
	ACCESS	read-write
	STATUS	mandatory
	DESCRIPTION
		"Setting this object to reset(3) clears all
		address table entries for this port as well as
		setting all port traffic counters to zero and
		setting fibEsPortResetTimer to zero."
	::= { fibEsPortEntry 14 }

fibEsPortRcvBcasts OBJECT-TYPE
	SYNTAX	Counter
	ACCESS	read-only
	STATUS	mandatory
	DESCRIPTION
		"Number of Broadcast Frames received on this port
		without errors."
	::= { fibEsPortEntry 15 }

fibEsPortSwitchedFrames OBJECT-TYPE
	SYNTAX	Counter
	ACCESS	read-only
	STATUS	mandatory
	DESCRIPTION
		"Number of frames switched on this port"
	::= { fibEsPortEntry 16 }

END
