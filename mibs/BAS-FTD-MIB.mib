BAS-FTD-MIB DEFINITIONS ::= BEGIN

IMPORTS
	MODULE-IDENTITY, 
	OBJECT-TYPE, 
	Counter32 
	        FROM SNMPv2-SMI
	basFtd 
		FROM BAS-MIB;

          
basFtdMib MODULE-IDENTITY
	LAST-UPDATED "9810071415Z"
	ORGANIZATION "Broadband Access Systems"
	CONTACT-INFO
		" Tech Support
		  Broadband Access Systems
		  4 Technology Drive
		  Westborough, MA  01581
		  U.S.A.
		  
		  508-366-8833
		  support@basystems.com"
	DESCRIPTION
		"This MIB module defines the configuration and 
		 status MIB objects for a Broadband Access System 
		 FTD objects."
	::= { basFtd 1 }


basFtdObjects	       	OBJECT IDENTIFIER ::= { basFtdMib 1 }

 basFtdHeartBeatTimer OBJECT-TYPE
	SYNTAX      INTEGER ( 1..10 )
	MAX-ACCESS  read-create
	STATUS      current
	DESCRIPTION
		"Timer value in seconds for the FTD heartbeat."
	DEFVAL { 1 }

	::= { basFtdObjects 1 }

 basFtdTableEligibilityCounter OBJECT-TYPE
	SYNTAX   Counter32
	MAX-ACCESS  read-only
	STATUS      current
	DESCRIPTION
		"Count of the FTD heartbeat timeouts since receiving a table request, i.e. an eligibility cycle."

	::= {  basFtdObjects 2  }

basFtdTableEligibilityCounterThreshold OBJECT-TYPE
	SYNTAX      INTEGER ( 1..100 )
	MAX-ACCESS  read-create
	STATUS      current
	DESCRIPTION
		"Counter threshold (table eligibility counter) defining a time window used to accumulate table requests and stagger their distribution."
	DEFVAL { 5 }

	::= { basFtdObjects 3  }

 basFtdIdleCounter OBJECT-TYPE
	SYNTAX   Counter32
	MAX-ACCESS  read-only
	STATUS      current
	DESCRIPTION
		"Count of the FTD heartbeat timeouts in an idle state."

	::= {  basFtdObjects 4  }

basFtdIdleCounterThreshold OBJECT-TYPE
	SYNTAX      INTEGER ( 1..100 )
	MAX-ACCESS  read-create
	STATUS      current
	DESCRIPTION
		"Counter threshold (idle counter) defining a time
	window ( in heartbeat units ) used to stagger the transmission
	of revision packets."
	DEFVAL { 5 }

	::= { basFtdObjects 5  }

basFtdTableRequestCounter OBJECT-TYPE
	SYNTAX   Counter32
	MAX-ACCESS  read-only
	STATUS      current
	DESCRIPTION
		"Count of FTD table requests during an eligibility cycle."

	::= { basFtdObjects 6 }

basFtdPendingCallbackCounter OBJECT-TYPE
	SYNTAX   Counter32
	MAX-ACCESS  read-only
	STATUS      current
	DESCRIPTION
		"Count of the FTD heartbeat timeouts accumulated while a callback is pending, i.e. a pending cycle."

	::= { basFtdObjects 7 }

basFtdPendingCallbackThreshold OBJECT-TYPE
	SYNTAX      INTEGER ( 1..100 )
	MAX-ACCESS  read-create
	STATUS      current
	DESCRIPTION
		"Counter threshold (pending callback counter) defining a maximum time window to wait for a callback."
	DEFVAL { 10 }

	::= { basFtdObjects 8 }

basFtdBootState OBJECT-TYPE
	SYNTAX      INTEGER { 
			      null (1),
			      cold (2),
			      warm (3) 
		        }

	MAX-ACCESS  read-create
	STATUS      current
	DESCRIPTION
		"FTD objects boot state"

	::= { basFtdObjects 9 }

basFtdPurgeConfiguration OBJECT-TYPE
	SYNTAX      INTEGER { 
			      immediate (1),
			      delayed (2)
			   }
	MAX-ACCESS  read-create
	STATUS      current
	DESCRIPTION
		"Configuration for when to purge the forwarding table: immediately or delayed (after a new table has been received)."
	DEFVAL { 1 }

	::= { basFtdObjects 10 }

--   stats: all RO

basFtdUpdateRequests OBJECT-TYPE
	SYNTAX      Counter32
	MAX-ACCESS  read-only
	STATUS      current
	DESCRIPTION
		"Count of the total number of update requests."

	::= { basFtdObjects 11 }

basFtdUpdatepackets OBJECT-TYPE
	SYNTAX      Counter32
	MAX-ACCESS  read-only
	STATUS      current
	DESCRIPTION
		"Count of the total number of update packets."

	::= { basFtdObjects 12 }

basFtdTableRequests OBJECT-TYPE
	SYNTAX      Counter32
	MAX-ACCESS  read-only
	STATUS      current
	DESCRIPTION
		"Count of the total number of table requests."

	::= { basFtdObjects 13 }

basFtdTablePackets OBJECT-TYPE
	SYNTAX      Counter32
	MAX-ACCESS  read-only
	STATUS      current
	DESCRIPTION
		"Count of the total number of table packets."

	::= { basFtdObjects 14 }

basFtdAllocatedPackets OBJECT-TYPE
	SYNTAX      Counter32
	MAX-ACCESS  read-only
	STATUS      current
	DESCRIPTION
		"Count of the total number of allocated packets."

	::= { basFtdObjects 15 }

basFtdSentPackets OBJECT-TYPE
	SYNTAX      Counter32
	MAX-ACCESS  read-only
	STATUS      current
	DESCRIPTION
		"Count of the total number of packets sent."

	::= { basFtdObjects 16 }

basFtdFreedPackets OBJECT-TYPE
	SYNTAX      Counter32
	MAX-ACCESS  read-only
	STATUS      current
	DESCRIPTION
		"Count of the total number of packets freed."

	::= { basFtdObjects 17 }

   
-- Forwarder
-- 
-- stats: all RO
basFtdSpuriousUpdatePackets OBJECT-TYPE
	SYNTAX      Counter32
	MAX-ACCESS  read-only
	STATUS      current
	DESCRIPTION
		"Count of the total number of spurious update packets."

	::= { basFtdObjects 18 }

basFtdSpuriousTablePackets OBJECT-TYPE
	SYNTAX      Counter32
	MAX-ACCESS  read-only
	STATUS      current
	DESCRIPTION
		"Count of the total number of spurious table packets."

	::= { basFtdObjects 19 }

basFtdIgnoredUpdatePackets OBJECT-TYPE
	SYNTAX      Counter32
	MAX-ACCESS  read-only
	STATUS      current
	DESCRIPTION
		"Count of the total number of ignored update packets."

	::= { basFtdObjects 20 }

basFtdIgnoredTablePackets OBJECT-TYPE
	SYNTAX      Counter32
	MAX-ACCESS  read-only
	STATUS      current
	DESCRIPTION
		"Count of the total number of ignored table packets."

	::= { basFtdObjects 21 }

basFtdInstalledUpdatePackets OBJECT-TYPE
	SYNTAX      Counter32
	MAX-ACCESS  read-only
	STATUS      current
	DESCRIPTION
		"Count of the total number of installed update packets."

	::= { basFtdObjects 22 }

basFtdInstalledTablePackets OBJECT-TYPE
	SYNTAX      Counter32
	MAX-ACCESS  read-only
	STATUS      current
	DESCRIPTION
		"Count of the total number of installed table packets."

	::= { basFtdObjects 23 }

basFtdStoredTablePackets OBJECT-TYPE
	SYNTAX      Counter32
	MAX-ACCESS  read-only
	STATUS      current
	DESCRIPTION
		"Count of the total number of stored table packets."

	::= { basFtdObjects 24 }

-- Common

basFtdRevisionPackets OBJECT-TYPE
	SYNTAX      Counter32
	MAX-ACCESS  read-only
	STATUS      current
	DESCRIPTION
		"Count of the total number of sent(rs) or received
	(fwd) revision packets."

	::= { basFtdObjects 25 }

basFtdFailureCode OBJECT-TYPE
	SYNTAX      INTEGER {
			      finite-state-machine (1),
			      dequeue (2),
			      null-table-fia (3),
			      nonnull-update-pkt (4),
			      nonnull-table-pkt (5),
			      pending-threshold (6),
			      uninitialized-storage (7),

			      external (100),
			      rbp-registration (101),
			      unknown-pkt (102),
			      rbp-send (103),
			      rbp-callback (104),
			      packet-allocation (105),
			      packet-corruption (106),
			      rte-error-bad-prefix (107),
			      rte-error-bad-version (108),
			      add-route-failure (109)
	              }
	MAX-ACCESS  read-only
	STATUS      current
	DESCRIPTION
		"Log of the most recent failure code."

	::= { basFtdObjects 26 }

basFtdRevision OBJECT-TYPE
	SYNTAX      INTEGER
	MAX-ACCESS  read-create
	STATUS      current
	DESCRIPTION
		"FTD update revision (write only for testing)."

	::= { basFtdObjects 27 }

basFtdPresentFsmState OBJECT-TYPE
	SYNTAX      INTEGER
	MAX-ACCESS  read-only
	STATUS      current
	DESCRIPTION
		"Current FTD finite state maching state."

	::= { basFtdObjects 28 }

-- stats: all RO

basFtdFsmRestarts OBJECT-TYPE
	SYNTAX      Counter32
	MAX-ACCESS  read-only
	STATUS      current
	DESCRIPTION
		"Count of the total number of FTD object restarts since a cold boot."

	::= { basFtdObjects 29 }


END
