Nortel-Magellan-Passport-GsmIwfMIB
DEFINITIONS ::= BEGIN



IMPORTS

      OBJECT-TYPE
   FROM RFC-1212

      IpAddress
   FROM RFC1155-SMI

      components,
      passportMIBs
   FROM Nortel-Magellan-Passport-UsefulDefinitionsMIB

      Counter32,
      RowPointer,
      DisplayString,
      StorageType,
      RowStatus,
      Gauge32,
      Integer32,
      Unsigned32
   FROM Nortel-Magellan-Passport-StandardTextualConventionsMIB

      AsciiString,
      NonReplicated,
      Link,
      FixedPoint2
   FROM Nortel-Magellan-Passport-TextualConventionsMIB;




-- LAST-UPDATED   "9905250000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     GsmIwf Enterprise MIB."

gsmIwfMIB OBJECT IDENTIFIER ::= { passportMIBs 129 }










-- GsmCs/<trunkGrp>
-- The GsmIwfCallServer component represents an instance of a call 
-- manager for Global System for Mobile communications (GSM) 
-- InterWorking Function (IWF) calls on this node. The 
-- GsmIwfCallServer provides a mechanism to segregate call 
-- resources (GsmIwfBearerChannels) and maintenance activities for 
-- the GsmIwfBearerChannels associated with that GsmIwfCallServer. 
-- The instance value trunkGrp is an external identifier for the trunk 
-- group configured at the Mobile Services-switching Center (MSC) 
-- connected to this node and associated with this GsmIwfCallServer 
-- instance.
-- 
-- This component is specific to the gsmIwfCallServer feature of the 
-- wirelessIwf application. Refer to NTP 411-5221-520 "GPP 
-- Interworking Function Data Guide" for details on its usage.

gsmCs OBJECT IDENTIFIER ::= { components 127 }



gsmCsRowStatusTable OBJECT-TYPE
   SYNTAX     SEQUENCE OF GsmCsRowStatusEntry
   ACCESS     not-accessible
   STATUS     mandatory
   DESCRIPTION
     "This entry controls the addition and deletion of 
      gsmCs components."
::= { gsmCs 1 }

gsmCsRowStatusEntry OBJECT-TYPE
   SYNTAX     GsmCsRowStatusEntry
   ACCESS     not-accessible
   STATUS     mandatory
   DESCRIPTION
     "A single entry in the table represents a single 
      gsmCs component."
   INDEX {
      gsmCsTrunkGrpIndex }
::= { gsmCsRowStatusTable 1 }

GsmCsRowStatusEntry ::= SEQUENCE {
   gsmCsRowStatus
      RowStatus,
   gsmCsComponentName
      DisplayString,
   gsmCsStorageType
      StorageType,
   gsmCsTrunkGrpIndex
      Integer32 }

gsmCsRowStatus OBJECT-TYPE
   SYNTAX     RowStatus 
   ACCESS     read-write
   STATUS     mandatory
   DESCRIPTION
     "This variable is used as the basis for SNMP naming of
      gsmCs components.
      These components can be added and deleted."
::= { gsmCsRowStatusEntry 1 }

gsmCsComponentName OBJECT-TYPE
   SYNTAX     DisplayString 
   ACCESS     read-only
   STATUS     mandatory
   DESCRIPTION
     "This variable provides the component's string name for
      use with the ASCII Console Interface"
::= { gsmCsRowStatusEntry 2 }

gsmCsStorageType OBJECT-TYPE
   SYNTAX     StorageType 
   ACCESS     read-only
   STATUS     mandatory
   DESCRIPTION
     "This variable represents the storage type value for the
      gsmCs tables."
::= { gsmCsRowStatusEntry 4 }

gsmCsTrunkGrpIndex OBJECT-TYPE
   SYNTAX     Integer32 (1..8191)
   ACCESS     not-accessible
   STATUS     mandatory
   DESCRIPTION
     "This variable represents the index for the gsmCs tables."
::= { gsmCsRowStatusEntry 10 }

gsmCsProvTable OBJECT-TYPE
   SYNTAX     SEQUENCE OF GsmCsProvEntry
   ACCESS     not-accessible
   STATUS     mandatory
   DESCRIPTION
     "This group contains general provisioning data for the 
      GsmIwfCallServer that does not fit within other provisioning 
      groups."
::= { gsmCs 100 }

gsmCsProvEntry OBJECT-TYPE
   SYNTAX     GsmCsProvEntry
   ACCESS     not-accessible
   STATUS     mandatory
   DESCRIPTION
     "An entry in the gsmCsProvTable."
   INDEX {
      gsmCsTrunkGrpIndex }
::= { gsmCsProvTable 1 }

GsmCsProvEntry ::= SEQUENCE {
   gsmCsCommentText
      AsciiString,
   gsmCsMscIpAddress
      IpAddress,
   gsmCsVirtualRouterName
      RowPointer,
   gsmCsVoiceLaw
      INTEGER }

gsmCsCommentText OBJECT-TYPE
   SYNTAX     AsciiString (SIZE (0..40))
   ACCESS     read-write
   STATUS     mandatory
   DESCRIPTION
     "Use of this attribute is at the discretion of the system administrator. 
      Typically, this attribute specifies the name of the trunk group at the 
      Mobile Services-switching Center (MSC) configured for this 
      GsmIwfCallServer plus any other commentary information."
   DEFVAL     { ''H }  -- ""
::= { gsmCsProvEntry 1 }

gsmCsMscIpAddress OBJECT-TYPE
   SYNTAX     IpAddress 
   ACCESS     read-write
   STATUS     mandatory
   DESCRIPTION
     "This attribute specifies the Internetwork Protocol (IP) Address of 
      the Mobile Services-switching Center (MSC) Control Module (CM) 
      that is permitted to set up GSM InterWorking Function (IWF) calls 
      using this GsmIwfCallServer. This address must be specified in 
      order for this GsmIwfCallServer to provide service. If call setups 
      are attempted from an MSC which does not have this address, those 
      calls are rejected. 
      The callsRequested statistic of this GsmIwfCallServer is 
      incremented, but the callsSetup statistic of this GsmIwfCallServer is 
      not, when call setup attempts are rejected. Also, at the MSC, 
      appropriate call failure logs are generated."
   DEFVAL     { '00000000'H }  -- "0.0.0.0"
::= { gsmCsProvEntry 2 }

gsmCsVirtualRouterName OBJECT-TYPE
   SYNTAX     RowPointer 
   ACCESS     read-write
   STATUS     mandatory
   DESCRIPTION
     "This attribute specifies the VirtualRouter that this 
      GsmIwfCallServer uses to transmit signaling messages to and 
      receive signaling messages from the Mobile Services-switching 
      Center (MSC) that utilizes this GsmIwfCallServer."
::= { gsmCsProvEntry 4 }

gsmCsVoiceLaw OBJECT-TYPE
   SYNTAX     INTEGER  {
                 aLaw(0),
                 muLaw(1) }
   ACCESS     read-write
   STATUS     mandatory
   DESCRIPTION
     "This attribute specifies the voice law to be established for the IWF 
      to Public Switched Telephone Network (PSTN) modem link for 
      calls established by this GsmIwfCallServer. Valid values are:
      aLaw, a protocol for encoding voice-band audio, Pulse Code 
      Modulation (PCM).
      muLaw, a protocol for encoding voice-band audio, PCM. 
      
      Note that this value must match the voice law used at the Mobile 
      Services-switching Center (MSC) connected to this 
      GsmIwfCallServer."
   DEFVAL     { aLaw }
::= { gsmCsProvEntry 5 }

gsmCsCidDataTable OBJECT-TYPE
   SYNTAX     SEQUENCE OF GsmCsCidDataEntry
   ACCESS     not-accessible
   STATUS     mandatory
   DESCRIPTION
     "This group contains the attribute for a component's Customer 
      Identifier (CID). Refer to the attribute description for a detailed 
      explanation of CIDs."
::= { gsmCs 103 }

gsmCsCidDataEntry OBJECT-TYPE
   SYNTAX     GsmCsCidDataEntry
   ACCESS     not-accessible
   STATUS     mandatory
   DESCRIPTION
     "An entry in the gsmCsCidDataTable."
   INDEX {
      gsmCsTrunkGrpIndex }
::= { gsmCsCidDataTable 1 }

GsmCsCidDataEntry ::= SEQUENCE {
   gsmCsCustomerIdentifier
      Unsigned32 }

gsmCsCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { gsmCsCidDataEntry 1 }

gsmCsStateTable OBJECT-TYPE
   SYNTAX     SEQUENCE OF GsmCsStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { gsmCs 104 }

gsmCsStateEntry OBJECT-TYPE
   SYNTAX     GsmCsStateEntry
   ACCESS     not-accessible
   STATUS     mandatory
   DESCRIPTION
     "An entry in the gsmCsStateTable."
   INDEX {
      gsmCsTrunkGrpIndex }
::= { gsmCsStateTable 1 }

GsmCsStateEntry ::= SEQUENCE {
   gsmCsAdminState
      INTEGER,
   gsmCsOperationalState
      INTEGER,
   gsmCsUsageState
      INTEGER }

gsmCsAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { gsmCsStateEntry 1 }

gsmCsOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { gsmCsStateEntry 2 }

gsmCsUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { gsmCsStateEntry 3 }

gsmCsStatsTable OBJECT-TYPE
   SYNTAX     SEQUENCE OF GsmCsStatsEntry
   ACCESS     not-accessible
   STATUS     mandatory
   DESCRIPTION
     "This group contains operational attributes that measure the 
      performance of this particular GsmIwfCallServer."
::= { gsmCs 121 }

gsmCsStatsEntry OBJECT-TYPE
   SYNTAX     GsmCsStatsEntry
   ACCESS     not-accessible
   STATUS     mandatory
   DESCRIPTION
     "An entry in the gsmCsStatsTable."
   INDEX {
      gsmCsTrunkGrpIndex }
::= { gsmCsStatsTable 1 }

GsmCsStatsEntry ::= SEQUENCE {
   gsmCsCurrentCalls
      Gauge32,
   gsmCsCallsRequested
      Counter32,
   gsmCsCallsSetup
      Counter32,
   gsmCsCallsActivated
      Counter32,
   gsmCsCallsReleasedNormal
      Counter32,
   gsmCsCallsReleasedAbnormal
      Counter32,
   gsmCsChannelConfigChanges
      Counter32,
   gsmCsChannelModeModifyRequests
      Counter32,
   gsmCsStatusMessagesRx
      Counter32,
   gsmCsErroredMipFrames
      Counter32 }

gsmCsCurrentCalls OBJECT-TYPE
   SYNTAX     Gauge32 (0..2047)
   ACCESS     read-only
   STATUS     mandatory
   DESCRIPTION
     "This attribute indicates the number of active calls currently serviced 
      by this particular GsmIwfCallServer."
   DEFVAL     { 0 }
::= { gsmCsStatsEntry 1 }

gsmCsCallsRequested OBJECT-TYPE
   SYNTAX     Counter32 
   ACCESS     read-only
   STATUS     mandatory
   DESCRIPTION
     "This attribute counts the number of IWF call setup requests received 
      at this particular GsmIwfCallServer from the Mobile Services-
      switching Center (MSC). The counter wraps when it exceeds the 
      maximum value."
::= { gsmCsStatsEntry 2 }

gsmCsCallsSetup OBJECT-TYPE
   SYNTAX     Counter32 
   ACCESS     read-only
   STATUS     mandatory
   DESCRIPTION
     "This attribute counts the number of IWF calls successfully setup by 
      this particular GsmIwfCallServer. A call is considered setup when 
      the IWF-Setup-Request message is received, indicating a request 
      for a data communications service, and the IWF has successfully 
      allocated the necessary resources to fulfill the request. The counter 
      wraps when it exceeds the maximum value."
::= { gsmCsStatsEntry 3 }

gsmCsCallsActivated OBJECT-TYPE
   SYNTAX     Counter32 
   ACCESS     read-only
   STATUS     mandatory
   DESCRIPTION
     "This attribute counts the number of IWF calls successfully activated 
      by this particular GsmIwfCallServer. A call is considered activated 
      when the IWF receives an IWF-Activate-Request, indicating that 
      the call parties are connected and that data communications must 
      begin. The counter wraps when it exceeds the maximum value."
::= { gsmCsStatsEntry 4 }

gsmCsCallsReleasedNormal OBJECT-TYPE
   SYNTAX     Counter32 
   ACCESS     read-only
   STATUS     mandatory
   DESCRIPTION
     "This attribute counts the number of IWF calls that have completed 
      successfully on this particular GsmIwfCallServer. The counter 
      wraps when it exceeds the maximum value."
::= { gsmCsStatsEntry 5 }

gsmCsCallsReleasedAbnormal OBJECT-TYPE
   SYNTAX     Counter32 
   ACCESS     read-only
   STATUS     mandatory
   DESCRIPTION
     "This attribute counts the number of IWF calls that have been 
      released due to error conditions at this particular GsmIwfCallServer 
      or one if its GsmIwfBearerChannels. The counter wraps when it 
      exceeds the maximum value."
::= { gsmCsStatsEntry 6 }

gsmCsChannelConfigChanges OBJECT-TYPE
   SYNTAX     Counter32 
   ACCESS     read-only
   STATUS     mandatory
   DESCRIPTION
     "This attribute counts the number of channel configuration requests 
      from the Mobile-services Switching Center (MSC) that have been 
      received at this GsmIwfCallServer and have resulted in successful 
      responses. The counter wraps when it exceeds the maximum value."
::= { gsmCsStatsEntry 7 }

gsmCsChannelModeModifyRequests OBJECT-TYPE
   SYNTAX     Counter32 
   ACCESS     read-only
   STATUS     mandatory
   DESCRIPTION
     "This attribute counts the number of channel mode modify requests 
      that have been generated by fax calls serviced by this particular 
      GsmIwfCallServer. The counter wraps when it exceeds the 
      maximum value."
::= { gsmCsStatsEntry 8 }

gsmCsStatusMessagesRx OBJECT-TYPE
   SYNTAX     Counter32 
   ACCESS     read-only
   STATUS     mandatory
   DESCRIPTION
     "This attribute counts the number of status messages received from 
      the Mobile Services-switching Center (MSC). The counter wraps 
      when it exceeds the maximum value."
::= { gsmCsStatsEntry 9 }

gsmCsErroredMipFrames OBJECT-TYPE
   SYNTAX     Counter32 
   ACCESS     read-only
   STATUS     mandatory
   DESCRIPTION
     "This attribute counts the number of MSC/IWF Interface Protocol 
      (MIP) messages received from the Mobile Services-switching 
      Center (MSC) that were in error. The counter wraps when it 
      exceeds the maximum value."
::= { gsmCsStatsEntry 10 }


-- GsmCs/<trunkGrp> Modem/<modem-type> 
-- This component represents a group of modem instances, indexed by 
-- modem type, that enable support of the various modem protocols on 
-- the GSM IWF. Valid modem types are:
-- 
-- v17, 14400 bit/s fax modem type.
-- v21, 300 bit/s data modem type.
-- v22, 600 or 1200 bit/s data modem type.
-- v22bis, 1200 or 2400 bit/s data modem type.
-- v23, 75(rx)/1200(tx) bit/s data modem type.
-- v27ter, 2400 or 4800 7200 bit/s fax modem type.
-- v29, 4800, 7200, or 9600 bit/s fax modem type.
-- v32, 4800 or 9600 bit/s data modem type.
-- v32bis, 14400 bit/s data modem type.
-- 
-- Many Modem attributes are dependent on the modem type. When a 
-- GsmIwfCallServer is added, a Modem instance is added 
-- automatically for each supported instance value. The attributes are 
-- set to default values, dependent on the modem type of the 
-- component instance.

gsmCsModem OBJECT IDENTIFIER ::= { gsmCs 2 }



gsmCsModemRowStatusTable OBJECT-TYPE
   SYNTAX     SEQUENCE OF GsmCsModemRowStatusEntry
   ACCESS     not-accessible
   STATUS     mandatory
   DESCRIPTION
     "This entry controls the addition and deletion of 
      gsmCsModem components."
::= { gsmCsModem 1 }

gsmCsModemRowStatusEntry OBJECT-TYPE
   SYNTAX     GsmCsModemRowStatusEntry
   ACCESS     not-accessible
   STATUS     mandatory
   DESCRIPTION
     "A single entry in the table represents a single 
      gsmCsModem component."
   INDEX {
      gsmCsTrunkGrpIndex,
      gsmCsModemIndex }
::= { gsmCsModemRowStatusTable 1 }

GsmCsModemRowStatusEntry ::= SEQUENCE {
   gsmCsModemRowStatus
      RowStatus,
   gsmCsModemComponentName
      DisplayString,
   gsmCsModemStorageType
      StorageType,
   gsmCsModemIndex
      INTEGER }

gsmCsModemRowStatus OBJECT-TYPE
   SYNTAX     RowStatus 
   ACCESS     read-only
   STATUS     mandatory
   DESCRIPTION
     "This variable is used as the basis for SNMP naming of
      gsmCsModem components.
      These components cannot be added nor deleted."
::= { gsmCsModemRowStatusEntry 1 }

gsmCsModemComponentName OBJECT-TYPE
   SYNTAX     DisplayString 
   ACCESS     read-only
   STATUS     mandatory
   DESCRIPTION
     "This variable provides the component's string name for
      use with the ASCII Console Interface"
::= { gsmCsModemRowStatusEntry 2 }

gsmCsModemStorageType OBJECT-TYPE
   SYNTAX     StorageType 
   ACCESS     read-only
   STATUS     mandatory
   DESCRIPTION
     "This variable represents the storage type value for the
      gsmCsModem tables."
::= { gsmCsModemRowStatusEntry 4 }

gsmCsModemIndex OBJECT-TYPE
   SYNTAX     INTEGER  {
                 v17(0),
                 v21(1),
                 v22(2),
                 v22bis(3),
                 v23(4),
                 v27ter(6),
                 v29(7),
                 v32(8),
                 v32bis(9) }
   ACCESS     not-accessible
   STATUS     mandatory
   DESCRIPTION
     "This variable represents the index for the gsmCsModem tables."
::= { gsmCsModemRowStatusEntry 10 }


-- GsmCs/<trunkGrp> RadioLinkProtocol/<radio-channel-type>
-- This component represents a group of Radio Link Protocol (RLP) 
-- instances, indexed by radio channel type. Valid radio channel types 
-- are:
-- 
-- half6kRate, Half rate channel at 6 kbit/s. 
-- full6kRate, Full rate channel at 6 kbit/s.
-- full12kRate, Full rate channel at 12 kbit/s.
-- full14k5Rate, Full rate channel at 14.5 kbit/s.
-- 
-- Many RLP attributes are dependent on the frame rate and frame 
-- size, that is dictated by the radio channel type. When a 
-- GsmIwfCallServer is added, a RadioLinkProtocol instance is added 
-- automatically for each possible instance value. The attributes are set 
-- to default values, dependent on the radio channel type of the 
-- component instance.

gsmCsRlp OBJECT IDENTIFIER ::= { gsmCs 3 }



gsmCsRlpRowStatusTable OBJECT-TYPE
   SYNTAX     SEQUENCE OF GsmCsRlpRowStatusEntry
   ACCESS     not-accessible
   STATUS     mandatory
   DESCRIPTION
     "This entry controls the addition and deletion of 
      gsmCsRlp components."
::= { gsmCsRlp 1 }

gsmCsRlpRowStatusEntry OBJECT-TYPE
   SYNTAX     GsmCsRlpRowStatusEntry
   ACCESS     not-accessible
   STATUS     mandatory
   DESCRIPTION
     "A single entry in the table represents a single 
      gsmCsRlp component."
   INDEX {
      gsmCsTrunkGrpIndex,
      gsmCsRlpIndex }
::= { gsmCsRlpRowStatusTable 1 }

GsmCsRlpRowStatusEntry ::= SEQUENCE {
   gsmCsRlpRowStatus
      RowStatus,
   gsmCsRlpComponentName
      DisplayString,
   gsmCsRlpStorageType
      StorageType,
   gsmCsRlpIndex
      INTEGER }

gsmCsRlpRowStatus OBJECT-TYPE
   SYNTAX     RowStatus 
   ACCESS     read-only
   STATUS     mandatory
   DESCRIPTION
     "This variable is used as the basis for SNMP naming of
      gsmCsRlp components.
      These components cannot be added nor deleted."
::= { gsmCsRlpRowStatusEntry 1 }

gsmCsRlpComponentName OBJECT-TYPE
   SYNTAX     DisplayString 
   ACCESS     read-only
   STATUS     mandatory
   DESCRIPTION
     "This variable provides the component's string name for
      use with the ASCII Console Interface"
::= { gsmCsRlpRowStatusEntry 2 }

gsmCsRlpStorageType OBJECT-TYPE
   SYNTAX     StorageType 
   ACCESS     read-only
   STATUS     mandatory
   DESCRIPTION
     "This variable represents the storage type value for the
      gsmCsRlp tables."
::= { gsmCsRlpRowStatusEntry 4 }

gsmCsRlpIndex OBJECT-TYPE
   SYNTAX     INTEGER  {
                 half6kRate(0),
                 full6kRate(1),
                 full12kRate(2),
                 full14k5Rate(3) }
   ACCESS     not-accessible
   STATUS     mandatory
   DESCRIPTION
     "This variable represents the index for the gsmCsRlp tables."
::= { gsmCsRlpRowStatusEntry 10 }

gsmCsRlpProvTable OBJECT-TYPE
   SYNTAX     SEQUENCE OF GsmCsRlpProvEntry
   ACCESS     not-accessible
   STATUS     mandatory
   DESCRIPTION
     "This group contains provisionable attributes for the Radio Link 
      Protocol (RLP) parameters used for the call set up by this particular 
      GsmIwfCallServer. Changes to these attributes do not effect existing 
      calls."
::= { gsmCsRlp 10 }

gsmCsRlpProvEntry OBJECT-TYPE
   SYNTAX     GsmCsRlpProvEntry
   ACCESS     not-accessible
   STATUS     mandatory
   DESCRIPTION
     "An entry in the gsmCsRlpProvTable."
   INDEX {
      gsmCsTrunkGrpIndex,
      gsmCsRlpIndex }
::= { gsmCsRlpProvTable 1 }

GsmCsRlpProvEntry ::= SEQUENCE {
   gsmCsRlpHighestVersion
      Unsigned32,
   gsmCsRlpIwfToMsWindowSize
      Unsigned32,
   gsmCsRlpMsToIwfWindowSize
      Unsigned32,
   gsmCsRlpT1AckTimer
      Unsigned32,
   gsmCsRlpT2AckDelayTimer
      Unsigned32,
   gsmCsRlpN2RetransmitCount
      Unsigned32 }

gsmCsRlpHighestVersion OBJECT-TYPE
   SYNTAX     Unsigned32 (0..1)
   ACCESS     read-write
   STATUS     mandatory
   DESCRIPTION
     "This attribute specifies the highest version of the Radio Link 
      Protocol (RLP) protocol supported on this GsmIwfCallServer. Valid 
      values are:
      0, Single-link basic version.
      1, Single-link extended version (for example, extended by data 
      compression).
      During the Exchange Information (XID) negotiation at the start of 
      the call, both RLP entities (mobile station and IWF) can agree to 
      use a particular RLP version. The IWF attempts to negotiate the 
      value specified by this attribute.
      Note that if V.42bis data compression is be established between the 
      mobile station and IWF, both entities must agree to use version 1 
      (or higher). 
      The default value for highestVersion is 1 to enable support for 
      V.42bis data compression. The negotiated value can be viewed in 
      the component GsmIwfRlpOp attribute highestVersion.
      Changes to this attribute do not effect existing calls."
   DEFVAL     { 1 }
::= { gsmCsRlpProvEntry 1 }

gsmCsRlpIwfToMsWindowSize OBJECT-TYPE
   SYNTAX     Unsigned32 (0..61)
   ACCESS     read-write
   STATUS     mandatory
   DESCRIPTION
     "This attribute specifies the maximum number of sequentially 
      numbered Information (I) frames that may be outstanding (that is, 
      unacknowledged) at any given time from the IWF to the mobile 
      station. GSM specification 4.22 defines the range as 0 to 61. 
      During the Exchange Information (XID) negotiation, both Radio 
      Link Protocol (RLP) entities (mobile station and IWF) can agree to 
      use a specific window size. The IWF attempts to negotiate to the 
      value specified by this attribute. 
      The negotiated value can be viewed in the component 
      GsmIwfRlpOp attribute iwfToMsWindowSize.
      Changes to this attribute do not effect existing calls."
   DEFVAL     { 61 }
::= { gsmCsRlpProvEntry 2 }

gsmCsRlpMsToIwfWindowSize OBJECT-TYPE
   SYNTAX     Unsigned32 (0..61)
   ACCESS     read-write
   STATUS     mandatory
   DESCRIPTION
     "This attribute specifies the maximum number of sequentially 
      numbered Information (I) frames that may be outstanding (that is, 
      unacknowledged) at any given time from the mobile station to IWF.
      GSM specification 4.22 defines the range as 0-61. 
      During the Exchange Information (XID) negotiation, both Radio 
      Link Protocol (RLP) entities (mobile station and IWF) can agree to 
      use a specific window size. The IWF attempts to negotiate to the 
      value specified by this attribute.
      The negotiated value can be viewed in the component 
      GsmIwfRlpOp attribute msToIwfWindowSize. Changes to this 
      attribute do not effect existing calls."
   DEFVAL     { 61 }
::= { gsmCsRlpProvEntry 3 }

gsmCsRlpT1AckTimer OBJECT-TYPE
   SYNTAX     Unsigned32 (380..1020)
   ACCESS     read-write
   STATUS     mandatory
   DESCRIPTION
     "This attribute specifies the time in milliseconds within which an 
      acknowledgment of a sent frame must be received. Once this timer 
      expires, the transmitting Radio Link Protocol (RLP) entity shall 
      assume that the frame was lost.
      During the Exchange Information (XID) negotiation, both RLP 
      entities (mobile station and IWF) can agree to use specific value for 
      this timer (T1). The IWF attempts to negotiate to the value specified 
      by this attribute. 
      The default value for t1AckTimer is 520 msec for the full14k5Rate 
      instance of this component, 480 msec for full12kRate, 540 msec for 
      full6kRate, and 780 msec for half6kRate. The negotiated value can 
      be viewed in the component GsmIwfRlpOp attribute t1AckTimer.
      Changes to this attribute do not effect existing calls."
::= { gsmCsRlpProvEntry 4 }

gsmCsRlpT2AckDelayTimer OBJECT-TYPE
   SYNTAX     Unsigned32 (10..79)
   ACCESS     read-write
   STATUS     mandatory
   DESCRIPTION
     "This attribute specifies the maximum time in milliseconds the 
      receiving Radio Link Protocol (RLP) entity shall wait before 
      sending an acknowledgment for a received information frame.
      During the Exchange Information (XID) negotiation, both RLP 
      entities (mobile station and IWF) can agree to use specific value for 
      this timer (T2). The IWF attempts to negotiate to the value specified 
      by this attribute. 
      The negotiated value can be viewed in the component 
      GsmIwfRlpOp attribute t2AckDelayTimer.
      Changes to this attribute do not effect existing calls."
   DEFVAL     { 50 }
::= { gsmCsRlpProvEntry 5 }

gsmCsRlpN2RetransmitCount OBJECT-TYPE
   SYNTAX     Unsigned32 (1..255)
   ACCESS     read-write
   STATUS     mandatory
   DESCRIPTION
     "This attribute specifies the maximum number of times a Radio Link 
      Protocol (RLP) entity shall retransmit an individual frame following 
      the expiry of timer T1.
      
      During the Exchange Information (XID) negotiation, both RLP 
      entities (mobile station and InterWorking Function (IWF)) can 
      agree to use specific value for N2 (Retransmit Count). The IWF 
      attempts to negotiate to the value specified by this attribute.
      The negotiated value can be viewed in the component 
      GsmIwfRlpOp attribute n2RetransmitCount.
      Changes to this attribute do not effect existing calls."
   DEFVAL     { 6 }
::= { gsmCsRlpProvEntry 6 }


-- GsmCs/<trunkGrp> Fax
-- This component represents a group of fax provisioning attributes. 
-- These attributes specify various default settings for aspects of the 
-- fax protocol, which may be used for a GSM IWF call.

gsmCsFax OBJECT IDENTIFIER ::= { gsmCs 4 }



gsmCsFaxRowStatusTable OBJECT-TYPE
   SYNTAX     SEQUENCE OF GsmCsFaxRowStatusEntry
   ACCESS     not-accessible
   STATUS     mandatory
   DESCRIPTION
     "This entry controls the addition and deletion of 
      gsmCsFax components."
::= { gsmCsFax 1 }

gsmCsFaxRowStatusEntry OBJECT-TYPE
   SYNTAX     GsmCsFaxRowStatusEntry
   ACCESS     not-accessible
   STATUS     mandatory
   DESCRIPTION
     "A single entry in the table represents a single 
      gsmCsFax component."
   INDEX {
      gsmCsTrunkGrpIndex,
      gsmCsFaxIndex }
::= { gsmCsFaxRowStatusTable 1 }

GsmCsFaxRowStatusEntry ::= SEQUENCE {
   gsmCsFaxRowStatus
      RowStatus,
   gsmCsFaxComponentName
      DisplayString,
   gsmCsFaxStorageType
      StorageType,
   gsmCsFaxIndex
      NonReplicated }

gsmCsFaxRowStatus OBJECT-TYPE
   SYNTAX     RowStatus 
   ACCESS     read-only
   STATUS     mandatory
   DESCRIPTION
     "This variable is used as the basis for SNMP naming of
      gsmCsFax components.
      These components cannot be added nor deleted."
::= { gsmCsFaxRowStatusEntry 1 }

gsmCsFaxComponentName OBJECT-TYPE
   SYNTAX     DisplayString 
   ACCESS     read-only
   STATUS     mandatory
   DESCRIPTION
     "This variable provides the component's string name for
      use with the ASCII Console Interface"
::= { gsmCsFaxRowStatusEntry 2 }

gsmCsFaxStorageType OBJECT-TYPE
   SYNTAX     StorageType 
   ACCESS     read-only
   STATUS     mandatory
   DESCRIPTION
     "This variable represents the storage type value for the
      gsmCsFax tables."
::= { gsmCsFaxRowStatusEntry 4 }

gsmCsFaxIndex OBJECT-TYPE
   SYNTAX     NonReplicated 
   ACCESS     not-accessible
   STATUS     mandatory
   DESCRIPTION
     "This variable represents the index for the gsmCsFax tables."
::= { gsmCsFaxRowStatusEntry 10 }

gsmCsFaxProvTable OBJECT-TYPE
   SYNTAX     SEQUENCE OF GsmCsFaxProvEntry
   ACCESS     not-accessible
   STATUS     mandatory
   DESCRIPTION
     "This group contains the provisionable attributes for the fascimile 
      protocol (T.30 and GSM 03.45) for this particular 
      GsmIwfCallServer. Changes to these attributes do not effect existing 
      calls."
::= { gsmCsFax 10 }

gsmCsFaxProvEntry OBJECT-TYPE
   SYNTAX     GsmCsFaxProvEntry
   ACCESS     not-accessible
   STATUS     mandatory
   DESCRIPTION
     "An entry in the gsmCsFaxProvTable."
   INDEX {
      gsmCsTrunkGrpIndex,
      gsmCsFaxIndex }
::= { gsmCsFaxProvTable 1 }

GsmCsFaxProvEntry ::= SEQUENCE {
   gsmCsFaxT1CalledToneTimer
      FixedPoint2 }

gsmCsFaxT1CalledToneTimer OBJECT-TYPE
   SYNTAX     FixedPoint2 (150..300)
   ACCESS     read-write
   STATUS     mandatory
   DESCRIPTION
     "This attribute specifies the delay to generate a Called (CED) tone at 
      the IWF after the called station is connected to the line for mobile 
      terminated calls. Changes to this attribute do not effect existing 
      calls."
   DEFVAL     { 180 }
::= { gsmCsFaxProvEntry 1 }


-- GsmCs/<trunkGrp> V42
-- This component represents a group of ITU-T V.42 error correcting 
-- data link protocol provisioning attributes. These attributes specify 
-- various default settings for aspects of the V.42 protocol, that may be 
-- used for a GSM IWF call for the IWF to Public Switched Telephone 
-- Network (PSTN) modem link.

gsmCsV42 OBJECT IDENTIFIER ::= { gsmCs 5 }



gsmCsV42RowStatusTable OBJECT-TYPE
   SYNTAX     SEQUENCE OF GsmCsV42RowStatusEntry
   ACCESS     not-accessible
   STATUS     mandatory
   DESCRIPTION
     "This entry controls the addition and deletion of 
      gsmCsV42 components."
::= { gsmCsV42 1 }

gsmCsV42RowStatusEntry OBJECT-TYPE
   SYNTAX     GsmCsV42RowStatusEntry
   ACCESS     not-accessible
   STATUS     mandatory
   DESCRIPTION
     "A single entry in the table represents a single 
      gsmCsV42 component."
   INDEX {
      gsmCsTrunkGrpIndex,
      gsmCsV42Index }
::= { gsmCsV42RowStatusTable 1 }

GsmCsV42RowStatusEntry ::= SEQUENCE {
   gsmCsV42RowStatus
      RowStatus,
   gsmCsV42ComponentName
      DisplayString,
   gsmCsV42StorageType
      StorageType,
   gsmCsV42Index
      NonReplicated }

gsmCsV42RowStatus OBJECT-TYPE
   SYNTAX     RowStatus 
   ACCESS     read-only
   STATUS     mandatory
   DESCRIPTION
     "This variable is used as the basis for SNMP naming of
      gsmCsV42 components.
      These components cannot be added nor deleted."
::= { gsmCsV42RowStatusEntry 1 }

gsmCsV42ComponentName OBJECT-TYPE
   SYNTAX     DisplayString 
   ACCESS     read-only
   STATUS     mandatory
   DESCRIPTION
     "This variable provides the component's string name for
      use with the ASCII Console Interface"
::= { gsmCsV42RowStatusEntry 2 }

gsmCsV42StorageType OBJECT-TYPE
   SYNTAX     StorageType 
   ACCESS     read-only
   STATUS     mandatory
   DESCRIPTION
     "This variable represents the storage type value for the
      gsmCsV42 tables."
::= { gsmCsV42RowStatusEntry 4 }

gsmCsV42Index OBJECT-TYPE
   SYNTAX     NonReplicated 
   ACCESS     not-accessible
   STATUS     mandatory
   DESCRIPTION
     "This variable represents the index for the gsmCsV42 tables."
::= { gsmCsV42RowStatusEntry 10 }

gsmCsV42ProvTable OBJECT-TYPE
   SYNTAX     SEQUENCE OF GsmCsV42ProvEntry
   ACCESS     not-accessible
   STATUS     mandatory
   DESCRIPTION
     "This group contains the provisionable attributes for the V.42 
      protocol for this particular GsmIwfCallServer. Changes to these 
      attributes do not effect existing calls."
::= { gsmCsV42 10 }

gsmCsV42ProvEntry OBJECT-TYPE
   SYNTAX     GsmCsV42ProvEntry
   ACCESS     not-accessible
   STATUS     mandatory
   DESCRIPTION
     "An entry in the gsmCsV42ProvTable."
   INDEX {
      gsmCsTrunkGrpIndex,
      gsmCsV42Index }
::= { gsmCsV42ProvTable 1 }

GsmCsV42ProvEntry ::= SEQUENCE {
   gsmCsV42T400DetectTimer
      FixedPoint2,
   gsmCsV42T401AckTimer
      FixedPoint2,
   gsmCsV42T402AckDelayTimer
      FixedPoint2,
   gsmCsV42T403IdleProbeTimer
      Unsigned32,
   gsmCsV42TxN401FrameSize
      Unsigned32,
   gsmCsV42RxN401FrameSize
      Unsigned32,
   gsmCsV42TxKwindowSize
      Unsigned32,
   gsmCsV42RxKwindowSize
      Unsigned32,
   gsmCsV42N400RetransLimit
      Unsigned32 }

gsmCsV42T400DetectTimer OBJECT-TYPE
   SYNTAX     FixedPoint2 (75..254)
   ACCESS     read-write
   STATUS     mandatory
   DESCRIPTION
     "This attribute specifies the maximum amount of time that the IWF 
      waits for an Originator Detection Pattern (ODP) or Answerer 
      Detection Pattern (ADP). ODP/ADP is a series of special bit 
      patterns used during the call setup procedures.
      If the IWF is the Originator of the call, it starts sending ODP 
      patterns and waits for an ADP for the duration of T400 milliseconds 
      from the answerer at call setup time. 
      If the IWF is the Answerer of the call, it waits for an ODP for T400 
      seconds from the originator and if it receives during that time it 
      sends an ADP pattern to the originator at the call setup time. Since 
      both sides operate with different values of T400 timer, a higher 
      value increases the chance of a successful call setup.
      Changes to this attribute do not effect existing calls."
   DEFVAL     { 200 }
::= { gsmCsV42ProvEntry 1 }

gsmCsV42T401AckTimer OBJECT-TYPE
   SYNTAX     FixedPoint2 (50..900)
   ACCESS     read-write
   STATUS     mandatory
   DESCRIPTION
     "This attribute specifies the maximum amount of time that the IWF 
      waits for an acknowledgment before retransmitting a frame. Since 
      information about the T401 timer is not carried in the Exchange 
      Identification (XID) negotiations at call setup time, both sides 
      operate with different timer values. The value for T401 depends on 
      many factors, such as propagation delay or frame processing time. 
      A frame is retransmitted up to N400 times if the timer T401 expires 
      before an acknowledgment for a frame is actually received. The 
      performance of the data link layer can be impacted by the value of 
      this timer as retransmissions of frames occur on expiry of timer 
      T401. 
      Changes to this attribute do not effect existing calls."
   DEFVAL     { 400 }
::= { gsmCsV42ProvEntry 2 }

gsmCsV42T402AckDelayTimer OBJECT-TYPE
   SYNTAX     FixedPoint2 (25..450)
   ACCESS     read-write
   STATUS     mandatory
   DESCRIPTION
     "This attribute specifies the maximum amount of time that the IWF 
      may wait following the receipt of any frame requiring a reply before 
      it initiates transmission of an appropriate reply in order to ensure 
      that the reply frame is received by the remote error-correcting entity 
      prior to expiration of the T401 timer of the remote error-correcting 
      entity. Since information about the T402 timer is not carried in the 
      Exchange Identification (XID) negotiations at call setup, both sides 
      operate with different timer values. If this timer expires, then the 
      reply that would have been returned prior to its expiration is not 
      sent. The performance of the data link layer can be impacted by the 
      value of this timer as retransmissions of frames occur on expiry of 
      timer T401. For better performance, a value of t402AckDelayTimer 
      (T402) equal to half the value of t401AckTimer (T401) is 
      recommended.
      Changes to this attribute do not effect existing calls."
   DEFVAL     { 200 }
::= { gsmCsV42ProvEntry 3 }

gsmCsV42T403IdleProbeTimer OBJECT-TYPE
   SYNTAX     Unsigned32 (30..90)
   ACCESS     read-write
   STATUS     mandatory
   DESCRIPTION
     "This attribute specifies the maximum amount of time that the IWF 
      allows to elapse without frames being exchanged. The link is 
      permitted to remain idle with no frames being exchanged on the 
      data link. Upon expiry of this timer, the IWF polls its peer for 
      status. Since information about the T403 timer is not carried in the 
      Exchange Identification (XID) negotiations at call setup time, both 
      sides operate with different timer values. 
      Changes to this attribute do not effect existing calls."
   DEFVAL     { 60 }
::= { gsmCsV42ProvEntry 4 }

gsmCsV42TxN401FrameSize OBJECT-TYPE
   SYNTAX     Unsigned32 (1..255)
   ACCESS     read-write
   STATUS     mandatory
   DESCRIPTION
     "This attribute specifies the maximum number of octets that can be 
      carried in the information field of an Information (I) frame, 
      Exchange Identification (XID) frame, and a Unnumbered 
      Information (UI) frame from the IWF to the remote entity. The 
      default value is 128 octets, and no XID negotiations required for 
      txN401FrameSize. If the value for txN401FrameSize value is set to 
      other than 128 octets, then XID frames are exchanged to negotiate a 
      value. The value provided for txN401FrameSize sets up the bounds 
      during XID negotiations. The IWF performs XID negotiations with 
      this value as a minimum or maximum value. If a value greater than 
      128 is specified, then the IWF negotiates or attempts to negotiate a 
      value between the 128 (as a minimum) and the given value (as a 
      maximum). If a value less than 128 is specified, then the IWF 
      attempts to negotiate a value between the given value (as a 
      minimum) and 128 (as a maximum). Any value can be specified as 
      long as it is within the provisionable limits. However, a value equal 
      to or close to 128 is recommended.
      The negotiated value can be viewed in the component 
      GsmIwfV42Op attribute txN401FrameSize. Changes to this attribute 
      do not effect existing calls."
   DEFVAL     { 128 }
::= { gsmCsV42ProvEntry 5 }

gsmCsV42RxN401FrameSize OBJECT-TYPE
   SYNTAX     Unsigned32 (1..255)
   ACCESS     read-write
   STATUS     mandatory
   DESCRIPTION
     "This attribute specifies the maximum number of octets that can be 
      carried in the information field of an Information (I) frame, 
      Exchange Identification (XID) frame, and a Unnumbered 
      Information (UI) frame from the remote entity to the IWF. The 
      default value is 128 octets, and no XID negotiations are required for 
      rxN401FrameSize. If the value set for rxN401FrameSize is other 
      than 128, XID frames are exchanged to negotiate a value. The value 
      provided for rxN401FrameSize sets up the bounds during XID 
      negotiations. The IWF performs XID negotiations with this value as 
      a minimum or maximum value. If a value greater than 128 is 
      specified, then the IWF attempts to negotiate for a value between 
      128 (as a minimum) and the given value (as a maximum). If a value 
      less than 128 value is specified, then the IWF attempts to negotiate 
      for a value between the given value (as a minimum) and 128 (as a 
      maximum). Any value can be specified as long as it is within the 
      provisionable limits. However, a value equal to or close to the 
      default is recommended.
      The negotiated value can be viewed in the component 
      GsmIwfV42Op attribute rxN401FrameSize. Changes to this attribute 
      do not effect existing calls."
   DEFVAL     { 128 }
::= { gsmCsV42ProvEntry 6 }

gsmCsV42TxKwindowSize OBJECT-TYPE
   SYNTAX     Unsigned32 (1..255)
   ACCESS     read-write
   STATUS     mandatory
   DESCRIPTION
     "This attribute specifies the maximum number of outstanding 
      unacknowledged sequenced Information (I) frames from the IWF to 
      the remote entity. The default value is 15 frames, and if this value is 
      used then no Exchange Identification (XID) negotiations are 
      required for txKwindowSize. If the value set for txKwindowSize is 
      other than 15, then XID frames are exchanged to negotiate a value. 
      The value provided for txKwindowSize sets up the bounds during 
      XID negotiations. The IWF performs XID negotiations with this 
      value as a minimum or maximum value. If a value greater than 15 is 
      specified, then the IWF attempts to negotiate a value between 15 (as 
      a minimum) and the given value (as a maximum). If a value less 
      than 15 is specified, then the IWF attempts to negotiate for a value 
      between the given value (as a minimum) and 15 (as a maximum). 
      Any value can be specified as long at it is within the provisionable 
      limits. However, a value equal to or close to the default is 
      recommended.
      The negotiated value can be viewed in the component 
      GsmIwfV42Op attribute txKwindowSize. Changes to this attribute do 
      not effect existing calls."
   DEFVAL     { 15 }
::= { gsmCsV42ProvEntry 7 }

gsmCsV42RxKwindowSize OBJECT-TYPE
   SYNTAX     Unsigned32 (1..255)
   ACCESS     read-write
   STATUS     mandatory
   DESCRIPTION
     "This attribute specifies the maximum number of outstanding 
      unacknowledged sequenced Information (I) frames from the remote 
      entity to the IWF. The default value is 15 frames, and if this value is 
      used then no Exchange Identification (XID) negotiations are 
      required for rxKwindowSize. If the value set for rxKwindowSize is 
      other than 15, then XID frames are exchanged to negotiate a value. 
      The value provided for rxKwindowSize sets up the bounds during 
      XID negotiations. The IWF performs XID negotiations with this 
      value as a minimum or maximum value. If a value greater than 15 is 
      specified, then the IWF attempts to negotiate a value between 15 (as 
      a minimum) and the given value (as a maximum). If a value less 
      than 15 is specified, then the IWF attempts to negotiate for a value 
      between the given value (as a minimum) and 15 (as a maximum). 
      Any value can be specified as long as it is within the provisionable 
      limits. However, a value equal to or close to the default is 
      recommended.
      The negotiated value can be viewed in the component 
      GsmIwfV42Op attribute rxKwindowSize. Changes to this attribute 
      do not effect existing calls."
   DEFVAL     { 15 }
::= { gsmCsV42ProvEntry 8 }

gsmCsV42N400RetransLimit OBJECT-TYPE
   SYNTAX     Unsigned32 (0..255)
   ACCESS     read-write
   STATUS     mandatory
   DESCRIPTION
     "This attribute specifies the maximum number of times the IWF 
      retransmits a frame upon expiry of t401AckTimer before 
      appropriate recovery action is taken. Information about N400 
      (Retransmission Limit) is not carried in the Exchange Identification 
      (XID) negotiation at call setup time so both sides operate with 
      different N400 values. 
      Changes to this attribute do not effect existing calls."
   DEFVAL     { 10 }
::= { gsmCsV42ProvEntry 9 }


-- GsmCs/<trunkGrp> V42bis
-- This component represents a group of ITU-T V.42bis data 
-- compression protocol provisioning attributes. These attributes 
-- specify various default settings for aspects of the V.42bis protocol, 
-- which may be used in a GSM IWF call on the mobile station to 
-- IWF link and/or the IWF to Public Switched Telephone Network 
-- (PSTN) modem link.

gsmCsV42bis OBJECT IDENTIFIER ::= { gsmCs 6 }



gsmCsV42bisRowStatusTable OBJECT-TYPE
   SYNTAX     SEQUENCE OF GsmCsV42bisRowStatusEntry
   ACCESS     not-accessible
   STATUS     mandatory
   DESCRIPTION
     "This entry controls the addition and deletion of 
      gsmCsV42bis components."
::= { gsmCsV42bis 1 }

gsmCsV42bisRowStatusEntry OBJECT-TYPE
   SYNTAX     GsmCsV42bisRowStatusEntry
   ACCESS     not-accessible
   STATUS     mandatory
   DESCRIPTION
     "A single entry in the table represents a single 
      gsmCsV42bis component."
   INDEX {
      gsmCsTrunkGrpIndex,
      gsmCsV42bisIndex }
::= { gsmCsV42bisRowStatusTable 1 }

GsmCsV42bisRowStatusEntry ::= SEQUENCE {
   gsmCsV42bisRowStatus
      RowStatus,
   gsmCsV42bisComponentName
      DisplayString,
   gsmCsV42bisStorageType
      StorageType,
   gsmCsV42bisIndex
      NonReplicated }

gsmCsV42bisRowStatus OBJECT-TYPE
   SYNTAX     RowStatus 
   ACCESS     read-only
   STATUS     mandatory
   DESCRIPTION
     "This variable is used as the basis for SNMP naming of
      gsmCsV42bis components.
      These components cannot be added nor deleted."
::= { gsmCsV42bisRowStatusEntry 1 }

gsmCsV42bisComponentName OBJECT-TYPE
   SYNTAX     DisplayString 
   ACCESS     read-only
   STATUS     mandatory
   DESCRIPTION
     "This variable provides the component's string name for
      use with the ASCII Console Interface"
::= { gsmCsV42bisRowStatusEntry 2 }

gsmCsV42bisStorageType OBJECT-TYPE
   SYNTAX     StorageType 
   ACCESS     read-only
   STATUS     mandatory
   DESCRIPTION
     "This variable represents the storage type value for the
      gsmCsV42bis tables."
::= { gsmCsV42bisRowStatusEntry 4 }

gsmCsV42bisIndex OBJECT-TYPE
   SYNTAX     NonReplicated 
   ACCESS     not-accessible
   STATUS     mandatory
   DESCRIPTION
     "This variable represents the index for the gsmCsV42bis tables."
::= { gsmCsV42bisRowStatusEntry 10 }

gsmCsV42bisProvTable OBJECT-TYPE
   SYNTAX     SEQUENCE OF GsmCsV42bisProvEntry
   ACCESS     not-accessible
   STATUS     mandatory
   DESCRIPTION
     "This group contains the provisionable attributes for the V.42bis data 
      compression protocol parameters used for the calls set up by this 
      particular GsmIwfCallServer. Changes to these attributes do not 
      effect existing calls."
::= { gsmCsV42bis 10 }

gsmCsV42bisProvEntry OBJECT-TYPE
   SYNTAX     GsmCsV42bisProvEntry
   ACCESS     not-accessible
   STATUS     mandatory
   DESCRIPTION
     "An entry in the gsmCsV42bisProvTable."
   INDEX {
      gsmCsTrunkGrpIndex,
      gsmCsV42bisIndex }
::= { gsmCsV42bisProvTable 1 }

GsmCsV42bisProvEntry ::= SEQUENCE {
   gsmCsV42bisCompressionDirection
      INTEGER,
   gsmCsV42bisMaximumCodewords
      Unsigned32,
   gsmCsV42bisMaximumStringSize
      Unsigned32,
   gsmCsV42bisActionOnError
      INTEGER }

gsmCsV42bisCompressionDirection OBJECT-TYPE
   SYNTAX     INTEGER  {
                 none(0),
                 encode(1),
                 decode(2),
                 both(3) }
   ACCESS     read-write
   STATUS     mandatory
   DESCRIPTION
     "This attribute specifies the V.42bis data compression direction to be 
      supported. The value for compression direction is negotiated at link 
      setup by the data link protocol by way of the Exchange 
      Identification (XID) negotiation of parameter P0 (compression 
      direction).
      During XID negotiation of parameter P0, both sides (IWF and 
      mobile or IWF and Public Switched Telephone Network (PSTN)) 
      agree on the compression direction.
      Valid values are:
      none, No compression is present.
      encode, The data sent by the IWF to the other entity is compressed.
      decode, The data received by the IWF from the other entity is 
      compressed.
      both, The data sent and received by the IWF is compressed.
      The negotiated value can be viewed in the component 
      GsmIwfV42bisOp attribute compressionDirection. Changes to this 
      attribute do not effect existing calls."
   DEFVAL     { both }
::= { gsmCsV42bisProvEntry 1 }

gsmCsV42bisMaximumCodewords OBJECT-TYPE
   SYNTAX     Unsigned32 (512 | 1024 | 2048 | 4096)
   ACCESS     read-write
   STATUS     mandatory
   DESCRIPTION
     "This attribute specifies the maximum number of V.42bis codewords 
      the IWF supports. A codeword is a binary number that represents a 
      string of characters in compressed form. V.42bis keeps a dictionary 
      of codewords for each compression direction. During Exchange 
      Identification (XID) negotiation of parameter P1 (number of 
      codewords), both sides (IWF and mobile or IWF and Public 
      Switched Telephone Network (PSTN)) agree on the total number of 
      codewords in the dictionaries. Changes to this attribute impact the 
      compression ratio for the encoder (component GsmV42BisOp 
      attribute compRatioEncoder). Changes also impact the amount of 
      memory used (more memory is used when increasing the attribute). 
      The gain in performance obtained from the selection of a larger 
      dictionary may be offset by the larger codeword size needed, and 
      for certain types of data, better performance may be obtained by 
      using a smaller dictionary. 
      The negotiated value can be viewed in the component 
      GsmIwfV42bisOp attribute maximumCodewords . Changes to this 
      attribute do not effect existing calls."
   DEFVAL     { 2048 }
::= { gsmCsV42bisProvEntry 2 }

gsmCsV42bisMaximumStringSize OBJECT-TYPE
   SYNTAX     Unsigned32 (6..250)
   ACCESS     read-write
   STATUS     mandatory
   DESCRIPTION
     "This attribute specifies the maximum number of characters allowed 
      in a string represented by a codeword that the IWF supports. Each 
      codeword in a V.42bis dictionary represents a string of characters. 
      During Exchange Identification (XID) negotiation of parameter P2 
      (maximum string size), both sides (IWF and mobile or IWF and 
      Public Switched Telephone Network (PSTN)) agree on the 
      maximum string length to be used in the dictionaries. Changes to 
      this attribute impact the compression ratio for the encoder 
      (component GsmIwfV42bisOp attribute compRatioEncoder). 
      The negotiated value can be viewed in the component 
      GsmIwfV42bisOp attribute maximumStringSize. Changes to this 
      attribute do not effect existing calls."
   DEFVAL     { 20 }
::= { gsmCsV42bisProvEntry 3 }

gsmCsV42bisActionOnError OBJECT-TYPE
   SYNTAX     INTEGER  {
                 resetLink(0),
                 takeDownCall(1) }
   ACCESS     read-write
   STATUS     mandatory
   DESCRIPTION
     "This attribute specifies whether or not V.42bis takes down the call 
      or resets the link when any of the following errors occur: 
      1.Receipt of STEPUP (step up codeword size) codeword when it 
      would cause C2 (current code word size) to exceed N1 (maximum 
      code word size).
      2. Receipt of a codeword, at any time, equal to C1 (next empty 
      dictionary entry).
      3. Receipt of a codeword representing an empty dictionary entry.
      4. Receipt of a reserved command code.
      5. Receipt of any other error.
      If the value is resetLink, the error corrected connection and V.42bis 
      dictionaries are reset. Some data is lost but the call continues. If the 
      value is takeDownCall, the call is taken down.
      Changes to this attribute do not effect existing calls."
   DEFVAL     { resetLink }
::= { gsmCsV42bisProvEntry 4 }


-- GsmCs/<trunkGrp> LogicalProcessor/n
-- The LogicalProcessor component represents a logical processor 
-- that may be linked to this GsmIwfCallServer. A 
-- GsmIwfBearerChannel is indirectly linked to this LogicalProcessor 
-- by way of the Framer component. This component must be added 
-- to the GsmIwfCallServer (and the change activated) prior to adding 
-- the GsmIwfBearerChannels.

gsmCsLp OBJECT IDENTIFIER ::= { gsmCs 7 }



gsmCsLpRowStatusTable OBJECT-TYPE
   SYNTAX     SEQUENCE OF GsmCsLpRowStatusEntry
   ACCESS     not-accessible
   STATUS     mandatory
   DESCRIPTION
     "This entry controls the addition and deletion of 
      gsmCsLp components."
::= { gsmCsLp 1 }

gsmCsLpRowStatusEntry OBJECT-TYPE
   SYNTAX     GsmCsLpRowStatusEntry
   ACCESS     not-accessible
   STATUS     mandatory
   DESCRIPTION
     "A single entry in the table represents a single 
      gsmCsLp component."
   INDEX {
      gsmCsTrunkGrpIndex,
      gsmCsLpIndex }
::= { gsmCsLpRowStatusTable 1 }

GsmCsLpRowStatusEntry ::= SEQUENCE {
   gsmCsLpRowStatus
      RowStatus,
   gsmCsLpComponentName
      DisplayString,
   gsmCsLpStorageType
      StorageType,
   gsmCsLpIndex
      Integer32 }

gsmCsLpRowStatus OBJECT-TYPE
   SYNTAX     RowStatus 
   ACCESS     read-write
   STATUS     mandatory
   DESCRIPTION
     "This variable is used as the basis for SNMP naming of
      gsmCsLp components.
      These components can be added and deleted."
::= { gsmCsLpRowStatusEntry 1 }

gsmCsLpComponentName OBJECT-TYPE
   SYNTAX     DisplayString 
   ACCESS     read-only
   STATUS     mandatory
   DESCRIPTION
     "This variable provides the component's string name for
      use with the ASCII Console Interface"
::= { gsmCsLpRowStatusEntry 2 }

gsmCsLpStorageType OBJECT-TYPE
   SYNTAX     StorageType 
   ACCESS     read-only
   STATUS     mandatory
   DESCRIPTION
     "This variable represents the storage type value for the
      gsmCsLp tables."
::= { gsmCsLpRowStatusEntry 4 }

gsmCsLpIndex OBJECT-TYPE
   SYNTAX     Integer32 (0..15)
   ACCESS     not-accessible
   STATUS     mandatory
   DESCRIPTION
     "This variable represents the index for the gsmCsLp tables."
::= { gsmCsLpRowStatusEntry 10 }

gsmCsLpOperTable OBJECT-TYPE
   SYNTAX     SEQUENCE OF GsmCsLpOperEntry
   ACCESS     not-accessible
   STATUS     mandatory
   DESCRIPTION
     "This group contains operational attributes pertaining to information 
      about GsmIwfBearerChannels and logical processors associated 
      with a GsmIwfCallServer from a high-level view."
::= { gsmCsLp 10 }

gsmCsLpOperEntry OBJECT-TYPE
   SYNTAX     GsmCsLpOperEntry
   ACCESS     not-accessible
   STATUS     mandatory
   DESCRIPTION
     "An entry in the gsmCsLpOperTable."
   INDEX {
      gsmCsTrunkGrpIndex,
      gsmCsLpIndex }
::= { gsmCsLpOperTable 1 }

GsmCsLpOperEntry ::= SEQUENCE {
   gsmCsLpConfiguredBearerChannels
      Unsigned32,
   gsmCsLpActiveCalls
      Gauge32,
   gsmCsLpAssignedCapacity
      Unsigned32,
   gsmCsLpModemsSupported
      INTEGER }

gsmCsLpConfiguredBearerChannels OBJECT-TYPE
   SYNTAX     Unsigned32 (0..124)
   ACCESS     read-only
   STATUS     mandatory
   DESCRIPTION
     "This attribute indicates the number of GsmIwfBearerChannel 
      components provisioned for the Logical Processor represented by 
      this component."
::= { gsmCsLpOperEntry 1 }

gsmCsLpActiveCalls OBJECT-TYPE
   SYNTAX     Gauge32 (0..124)
   ACCESS     read-only
   STATUS     mandatory
   DESCRIPTION
     "This attribute indicates the number of GsmIwfBearerChannel 
      components currently active on this LogicalProcessor."
::= { gsmCsLpOperEntry 2 }

gsmCsLpAssignedCapacity OBJECT-TYPE
   SYNTAX     Unsigned32 (0..100)
   ACCESS     read-only
   STATUS     mandatory
   DESCRIPTION
     "This attribute indicates what percentage (0 to 100%) of a given 
      LogicalProcessor has been reserved for the data calls which are 
      currently active. When the assignedCapacity reaches 100%, no new 
      calls are established on the given LogicalProcessor. During the life 
      of a call, the compute requirements will vary. The compute capacity 
      required for a given call type depends on the type of call established 
      including such factors as connection type, data compression, user 
      rate, error correction, flow control; therefore, at call establishment 
      the compute capacity is added to the assignedCapacity for a 
      LogicalProcessor. When the call is released, it's compute capacity 
      is subtracted from the assigned capacity for the Lp.The 
      GsmIwfCallServer uses this information to balance the distribution 
      of data calls across the logical processors."
::= { gsmCsLpOperEntry 3 }

gsmCsLpModemsSupported OBJECT-TYPE
   SYNTAX     INTEGER  {
                 yes(0),
                 no(1) }
   ACCESS     read-only
   STATUS     mandatory
   DESCRIPTION
     "This attribute indicates if modems are supported with this 
      LogicalProcessor."
::= { gsmCsLpOperEntry 4 }


-- GsmBc/<trunkGrp>,<cic>
-- This component represents an individual bearer channel resource 
-- for a given GsmIwfCallServer. Depending on the call type 
-- requested, the GsmIwfCallServer links one or more 
-- GsmIwfBearerChannels in a single GSM InterWorking Function 
-- (IWF) call. Each GsmIwfBearerChannel is linked to a channel on a 
-- DS1 or E1 port on a logical processor (one GsmIwfBearerChannel 
-- per channel). 
-- The instance value trunkGrp is the external identifier for the trunk 
-- group configured at the Mobile Services-switching Center (MSC) 
-- connected to this node and associated with this 
-- GsmIwfBearerChannel instance. 
-- The instance value cic is the external identifier for the trunk group 
-- member. It is referred to as the circuit identifier code (cic) and is the 
-- same index used when configuring the channel at the Mobile 
-- Services-switching Center (MSC).
-- 
-- This component is specific to the gsmIwfBearerChannel feature of 
-- the wirelessIwf application. Refer to NTP 411-5221-520 "GPP 
-- Interworking Function Data Guide" for details on its usage.

gsmBc OBJECT IDENTIFIER ::= { components 128 }



gsmBcRowStatusTable OBJECT-TYPE
   SYNTAX     SEQUENCE OF GsmBcRowStatusEntry
   ACCESS     not-accessible
   STATUS     mandatory
   DESCRIPTION
     "This entry controls the addition and deletion of 
      gsmBc components."
::= { gsmBc 1 }

gsmBcRowStatusEntry OBJECT-TYPE
   SYNTAX     GsmBcRowStatusEntry
   ACCESS     not-accessible
   STATUS     mandatory
   DESCRIPTION
     "A single entry in the table represents a single 
      gsmBc component."
   INDEX {
      gsmBcTrunkGrpIndex,
      gsmBcCicIndex }
::= { gsmBcRowStatusTable 1 }

GsmBcRowStatusEntry ::= SEQUENCE {
   gsmBcRowStatus
      RowStatus,
   gsmBcComponentName
      DisplayString,
   gsmBcStorageType
      StorageType,
   gsmBcTrunkGrpIndex
      Integer32,
   gsmBcCicIndex
      Integer32 }

gsmBcRowStatus OBJECT-TYPE
   SYNTAX     RowStatus 
   ACCESS     read-write
   STATUS     mandatory
   DESCRIPTION
     "This variable is used as the basis for SNMP naming of
      gsmBc components.
      These components can be added and deleted."
::= { gsmBcRowStatusEntry 1 }

gsmBcComponentName OBJECT-TYPE
   SYNTAX     DisplayString 
   ACCESS     read-only
   STATUS     mandatory
   DESCRIPTION
     "This variable provides the component's string name for
      use with the ASCII Console Interface"
::= { gsmBcRowStatusEntry 2 }

gsmBcStorageType OBJECT-TYPE
   SYNTAX     StorageType 
   ACCESS     read-only
   STATUS     mandatory
   DESCRIPTION
     "This variable represents the storage type value for the
      gsmBc tables."
::= { gsmBcRowStatusEntry 4 }

gsmBcTrunkGrpIndex OBJECT-TYPE
   SYNTAX     Integer32 (1..8191)
   ACCESS     not-accessible
   STATUS     mandatory
   DESCRIPTION
     "This variable represents an index for the gsmBc tables."
::= { gsmBcRowStatusEntry 10 }

gsmBcCicIndex OBJECT-TYPE
   SYNTAX     Integer32 (1..2047)
   ACCESS     not-accessible
   STATUS     mandatory
   DESCRIPTION
     "This variable represents an index for the gsmBc tables."
::= { gsmBcRowStatusEntry 11 }

gsmBcOperTable OBJECT-TYPE
   SYNTAX     SEQUENCE OF GsmBcOperEntry
   ACCESS     not-accessible
   STATUS     mandatory
   DESCRIPTION
     "This group contains operational attributes concerning the operation 
      of this particular GsmIwfBearerChannel for the current or most 
      recent call."
::= { gsmBc 101 }

gsmBcOperEntry OBJECT-TYPE
   SYNTAX     GsmBcOperEntry
   ACCESS     not-accessible
   STATUS     mandatory
   DESCRIPTION
     "An entry in the gsmBcOperTable."
   INDEX {
      gsmBcTrunkGrpIndex,
      gsmBcCicIndex }
::= { gsmBcOperTable 1 }

GsmBcOperEntry ::= SEQUENCE {
   gsmBcMipState
      INTEGER,
   gsmBcMaxUserDataRate
      INTEGER,
   gsmBcConnectionType
      INTEGER,
   gsmBcDataBits
      INTEGER,
   gsmBcStopBits
      INTEGER,
   gsmBcParity
      INTEGER,
   gsmBcFlowControl
      INTEGER,
   gsmBcCallType
      INTEGER,
   gsmBcLastResponseCode
      INTEGER,
   gsmBcMateBearerChannel
      RowPointer }

gsmBcMipState OBJECT-TYPE
   SYNTAX     INTEGER  {
                 idle(0),
                 pendingSetup(1),
                 setup(2),
                 pendingActivation(3),
                 activated(4),
                 holdDisconnect(5),
                 suspended(6) }
   ACCESS     read-only
   STATUS     mandatory
   DESCRIPTION
     "This attribute indicates the current state of the MSC/IWF Interface 
      Protocol (MIP) for an IWF element. Valid values are:
      idle, Startup state of IWF element.
      pendingSetup, Pending initial state of IWF element.
      setup, Initial state of IWF element.
      pendingActivation, Synchronization has been requested, but the 
      IWF element is not yet in the Synchronization state.
      activated, Synchronization state.
      holdDisconnect, Flush buffer state, during call clearing the MSC is 
      responsible for holding the network connection towards the 
      disconnected party while the IWF completes the data transmission 
      (flushing any buffered data towards the disconnected party; any 
      buffered data towards the disconnecting party is discarded.)
      currentlySuspended, The call is temporarily switched to speech 
      phase during a dual services call."
   DEFVAL     { idle }
::= { gsmBcOperEntry 1 }

gsmBcMaxUserDataRate OBJECT-TYPE
   SYNTAX     INTEGER  {
                 n300(0),
                 n600(1),
                 n1200(2),
                 n120075(3),
                 n2400(4),
                 n4800(5),
                 n7200(6),
                 n9600(7),
                 n12000(8),
                 n14400(9),
                 n16800(10),
                 n19200(11),
                 n21600(12),
                 n24000(13),
                 n26400(14),
                 n28800(15),
                 n31200(16),
                 n32000(17),
                 n33600(18),
                 n38400(19),
                 n43200(20),
                 n48000(21),
                 n56000(22),
                 n57600(23),
                 n64000(24),
                 none(25) }
   ACCESS     read-only
   STATUS     mandatory
   DESCRIPTION
     "This attribute indicates the user rate which is in affect between the 
      IWF and the fixed network. A user rate of 1200_75 is 75 bit/s in the 
      receive direction 1200 bit/s in the transmit direction."
   DEFVAL     { none }
::= { gsmBcOperEntry 2 }

gsmBcConnectionType OBJECT-TYPE
   SYNTAX     INTEGER  {
                 synchronous(0),
                 asynchronous(1) }
   ACCESS     read-only
   STATUS     mandatory
   DESCRIPTION
     "This attribute indicates the connection types between the terminal 
      equipment or terminal adaptor and mobile and between the IWF 
      and the network. Valid connection types are: 
      asynchronous, Transmission of data which does not require 
      clocking of the data signal. 
      synchronous, Transmission of data which requires clocking of the 
      data signal."
::= { gsmBcOperEntry 3 }

gsmBcDataBits OBJECT-TYPE
   SYNTAX     INTEGER  {
                 n7(0),
                 n8(1),
                 notApplicable(99) }
   ACCESS     read-only
   STATUS     mandatory
   DESCRIPTION
     "This attribute indicates the number of data bits encoded between 
      start and stop bits in an asynchronous data call connection data 
      stream. This attribute is set to notApplicable for a synchronous data 
      call."
   DEFVAL     { notApplicable }
::= { gsmBcOperEntry 4 }

gsmBcStopBits OBJECT-TYPE
   SYNTAX     INTEGER  {
                 n1(0),
                 n2(1),
                 notApplicable(99) }
   ACCESS     read-only
   STATUS     mandatory
   DESCRIPTION
     "This attribute indicates the number of stop bits (a mark (binary 1) 
      placed at the end of each data byte) inserted between the data bits in 
      an asynchronous data call connection data stream, this marks the 
      end of the character. This attribute is set to notApplicable for a 
      synchronous data call."
   DEFVAL     { notApplicable }
::= { gsmBcOperEntry 5 }

gsmBcParity OBJECT-TYPE
   SYNTAX     INTEGER  {
                 none(0),
                 odd(1),
                 even(2),
                 forced0(3),
                 forced1(4),
                 notApplicable(99) }
   ACCESS     read-only
   STATUS     mandatory
   DESCRIPTION
     "This attribute indicates the type of parity for the data bits in an 
      asynchronous data call connection data stream. Parity is a redundant 
      bit that is added to each data byte to aid in error detection. If odd 
      parity is used, all data bytes have an odd number of 1s, and if even 
      parity is used, all data bytes have an even number of 1s. Also parity 
      may be forced to 0, forced to 1, or may not be used at all (required 
      for sending 8-bit data). This attribute will be set to notApplicable 
      for a synchronouse data call. Valid values are:
      none, No parity.
      odd, Odd parity.
      even, Even parity.
      forced0, Parity forced to 0.
      forced1, Parity forced to 1.
      notApplicable, Parity not applicable."
   DEFVAL     { none }
::= { gsmBcOperEntry 6 }

gsmBcFlowControl OBJECT-TYPE
   SYNTAX     INTEGER  {
                 noFlowControlActive(0),
                 inband(1),
                 v110FlowCntrl(2),
                 errorCntrl(3) }
   ACCESS     read-only
   STATUS     mandatory
   DESCRIPTION
     "This attribute indicates the current flow control status of this 
      GsmIwfBearerChannel for an asynchronous call. For a synchronous 
      data call this attribute will be set to noFlowControlActive. Valid 
      values are:
      noFlowControlActive, There is no flow control active over the air 
      interface and network interfaces. The applications at the end points 
      handle flow control. 
      inband, Embedded characters in the data stream indicate flow 
      control. 
      v110FlowCtnrl, Utilization of V.110 flow control. 
      errorCntrl, Flow control is handle by datalink protocols."
   DEFVAL     { noFlowControlActive }
::= { gsmBcOperEntry 7 }

gsmBcCallType OBJECT-TYPE
   SYNTAX     INTEGER  {
                 faxG3(0),
                 cda31khz(1),
                 cdaUdi(2),
                 cdsUdi(3),
                 cds31khz(4) }
   ACCESS     read-only
   STATUS     mandatory
   DESCRIPTION
     "This attribute indicates the current call type. Valid values are:
      faxG3, group 3 fax calls
      cda31khz, asynchronous 3.1kHz modem
      cdaUdi, asynchronous unrestricted digital data call
      cdsUdi, synchronous unrestricted digital data call
      cds31khz, synchronous 3.1kHz modem"
::= { gsmBcOperEntry 8 }

gsmBcLastResponseCode OBJECT-TYPE
   SYNTAX     INTEGER  {
                 requestDone(0),
                 systemError(1),
                 applicationError(2),
                 noResources(3),
                 msgSizeMismatch(4),
                 protocolViolation(5),
                 requestNotSupported(6),
                 requestDenied(7),
                 invalidMessage(8),
                 bufferNotFlushed(9),
                 notApplicable(99) }
   ACCESS     read-only
   STATUS     mandatory
   DESCRIPTION
     "This attribute indicates the MSC/IWF Interface Protocol (MIP) 
      response code returned for the last call which was active on this 
      particular GsmIwfBearerChannel. Valid values are:
      requestDone, the call was terminated normally.
      systemError, the call was terminated due to a base system problem.
      applicationError, the call was terminated due to an application 
      level problem.
      noResources, the call was terminated due to a lack of available 
      resources.
      msgSizeMismatch, Message length does not match length defined 
      by the MSC/IWF Interface Protocol for the particular message type.
      protocolViolation, Failed to perform the request because the coding 
      of the request message was invalid; message was not understood.
      requestNotSupported, Message was understood but not supported 
      by the IWF or MSC.
      requestDenied, Message was understood and supported by the IWF 
      or MSC but the request is denied. 
      invalidMessage, Message received is invalid for the current state of 
      the IWF's state machine or the MSC data call state machine. The 
      message is ignored.
      bufferNotFlushed, Message from the Iwf to the MSC indicating 
      that the buffers are not flushed as requested by the MSC.
      notApplicable, this attribute is not applicable for this call. This is 
      the default value for this attribute."
   DEFVAL     { notApplicable }
::= { gsmBcOperEntry 9 }

gsmBcMateBearerChannel OBJECT-TYPE
   SYNTAX     RowPointer 
   ACCESS     read-only
   STATUS     mandatory
   DESCRIPTION
     "This attribute contains the name of the mate GsmIwfBearerChannel 
      that this GsmIwfBearerChannel is involved with in the currently 
      active call."
::= { gsmBcOperEntry 10 }

gsmBcCidDataTable OBJECT-TYPE
   SYNTAX     SEQUENCE OF GsmBcCidDataEntry
   ACCESS     not-accessible
   STATUS     mandatory
   DESCRIPTION
     "This group contains the attribute for a component's Customer 
      Identifier (CID). Refer to the attribute description for a detailed 
      explanation of CIDs."
::= { gsmBc 104 }

gsmBcCidDataEntry OBJECT-TYPE
   SYNTAX     GsmBcCidDataEntry
   ACCESS     not-accessible
   STATUS     mandatory
   DESCRIPTION
     "An entry in the gsmBcCidDataTable."
   INDEX {
      gsmBcTrunkGrpIndex,
      gsmBcCicIndex }
::= { gsmBcCidDataTable 1 }

GsmBcCidDataEntry ::= SEQUENCE {
   gsmBcCustomerIdentifier
      Unsigned32 }

gsmBcCustomerIdentifier OBJECT-TYPE
   SYNTAX     Unsigned32 (0 | 1..8191)
   ACCESS     read-write
   STATUS     mandatory
   DESCRIPTION
     "This attribute holds the Customer Identifier (CID).
      
      Every component has a CID. If a component has a cid attribute, the 
      component's CID is the provisioned value of that attribute; 
      otherwise the component inherits the CID of its parent. The top-
      level component has a CID of 0.
      
      Every operator session also has a CID, which is the CID 
      provisioned for the operator's user ID. An operator will see only the 
      stream data for components having a matching CID. Also, the 
      operator will be allowed to issue commands for only those 
      components which have a matching CID.
      
      An operator CID of 0 is used to identify the Network Manager 
      (referred to as 'NetMan' in DPN). This CID matches the CID of 
      any component. Values 1 to 8191 inclusive (equivalent to 'basic 
      CIDs' in DPN) may be assigned to specific customers."
   DEFVAL     { 0 }
::= { gsmBcCidDataEntry 1 }

gsmBcStateTable OBJECT-TYPE
   SYNTAX     SEQUENCE OF GsmBcStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { gsmBc 105 }

gsmBcStateEntry OBJECT-TYPE
   SYNTAX     GsmBcStateEntry
   ACCESS     not-accessible
   STATUS     mandatory
   DESCRIPTION
     "An entry in the gsmBcStateTable."
   INDEX {
      gsmBcTrunkGrpIndex,
      gsmBcCicIndex }
::= { gsmBcStateTable 1 }

GsmBcStateEntry ::= SEQUENCE {
   gsmBcAdminState
      INTEGER,
   gsmBcOperationalState
      INTEGER,
   gsmBcUsageState
      INTEGER }

gsmBcAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { gsmBcStateEntry 1 }

gsmBcOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { gsmBcStateEntry 2 }

gsmBcUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { gsmBcStateEntry 3 }


-- GsmBc/<trunkGrp>,<cic> Framer
-- The Framer component controls link layer framing for application 
-- components sending and receiving data on a link interface. The 
-- Framer component also associates an application component with a 
-- specific hardware link interface. The Framer component provides 
-- provisionable attributes related to datapath aspects of the hardware 
-- interface rather than interface specific attributes which are 
-- associated with hardware components. The Framer component also 
-- provides a provisionable attribute which binds the application 
-- component to a specific hardware component.

gsmBcFramer OBJECT IDENTIFIER ::= { gsmBc 2 }



gsmBcFramerRowStatusTable OBJECT-TYPE
   SYNTAX     SEQUENCE OF GsmBcFramerRowStatusEntry
   ACCESS     not-accessible
   STATUS     mandatory
   DESCRIPTION
     "This entry controls the addition and deletion of 
      gsmBcFramer components."
::= { gsmBcFramer 1 }

gsmBcFramerRowStatusEntry OBJECT-TYPE
   SYNTAX     GsmBcFramerRowStatusEntry
   ACCESS     not-accessible
   STATUS     mandatory
   DESCRIPTION
     "A single entry in the table represents a single 
      gsmBcFramer component."
   INDEX {
      gsmBcTrunkGrpIndex,
      gsmBcCicIndex,
      gsmBcFramerIndex }
::= { gsmBcFramerRowStatusTable 1 }

GsmBcFramerRowStatusEntry ::= SEQUENCE {
   gsmBcFramerRowStatus
      RowStatus,
   gsmBcFramerComponentName
      DisplayString,
   gsmBcFramerStorageType
      StorageType,
   gsmBcFramerIndex
      NonReplicated }

gsmBcFramerRowStatus OBJECT-TYPE
   SYNTAX     RowStatus 
   ACCESS     read-only
   STATUS     mandatory
   DESCRIPTION
     "This variable is used as the basis for SNMP naming of
      gsmBcFramer components.
      These components cannot be added nor deleted."
::= { gsmBcFramerRowStatusEntry 1 }

gsmBcFramerComponentName OBJECT-TYPE
   SYNTAX     DisplayString 
   ACCESS     read-only
   STATUS     mandatory
   DESCRIPTION
     "This variable provides the component's string name for
      use with the ASCII Console Interface"
::= { gsmBcFramerRowStatusEntry 2 }

gsmBcFramerStorageType OBJECT-TYPE
   SYNTAX     StorageType 
   ACCESS     read-only
   STATUS     mandatory
   DESCRIPTION
     "This variable represents the storage type value for the
      gsmBcFramer tables."
::= { gsmBcFramerRowStatusEntry 4 }

gsmBcFramerIndex OBJECT-TYPE
   SYNTAX     NonReplicated 
   ACCESS     not-accessible
   STATUS     mandatory
   DESCRIPTION
     "This variable represents the index for the gsmBcFramer tables."
::= { gsmBcFramerRowStatusEntry 10 }

gsmBcFramerProvTable OBJECT-TYPE
   SYNTAX     SEQUENCE OF GsmBcFramerProvEntry
   ACCESS     not-accessible
   STATUS     mandatory
   DESCRIPTION
     "This group contains the base provisioning data for the Framer 
      component. Application or hardware interface specific provisioning 
      data is contained in other provisionable Framer groups."
::= { gsmBcFramer 10 }

gsmBcFramerProvEntry OBJECT-TYPE
   SYNTAX     GsmBcFramerProvEntry
   ACCESS     not-accessible
   STATUS     mandatory
   DESCRIPTION
     "An entry in the gsmBcFramerProvTable."
   INDEX {
      gsmBcTrunkGrpIndex,
      gsmBcCicIndex,
      gsmBcFramerIndex }
::= { gsmBcFramerProvTable 1 }

GsmBcFramerProvEntry ::= SEQUENCE {
   gsmBcFramerInterfaceName
      Link }

gsmBcFramerInterfaceName OBJECT-TYPE
   SYNTAX     Link 
   ACCESS     read-write
   STATUS     mandatory
   DESCRIPTION
     "This attribute contains a hardware component name.
      
      The attribute associates the application with a specific link. This 
      defines the module processor on which Framer's parent component 
      (as well as Framer itself) will run."
::= { gsmBcFramerProvEntry 1 }

gsmBcFramerStatsTable OBJECT-TYPE
   SYNTAX     SEQUENCE OF GsmBcFramerStatsEntry
   ACCESS     not-accessible
   STATUS     mandatory
   DESCRIPTION
     "This group contains the operational statistics data for a Framer 
      component."
::= { gsmBcFramer 11 }

gsmBcFramerStatsEntry OBJECT-TYPE
   SYNTAX     GsmBcFramerStatsEntry
   ACCESS     not-accessible
   STATUS     mandatory
   DESCRIPTION
     "An entry in the gsmBcFramerStatsTable."
   INDEX {
      gsmBcTrunkGrpIndex,
      gsmBcCicIndex,
      gsmBcFramerIndex }
::= { gsmBcFramerStatsTable 1 }

GsmBcFramerStatsEntry ::= SEQUENCE {
   gsmBcFramerFrmToIf
      Counter32,
   gsmBcFramerFrmFromIf
      Counter32,
   gsmBcFramerOctetFromIf
      Counter32,
   gsmBcFramerCrcErrors
      Counter32,
   gsmBcFramerLrcErrors
      Counter32,
   gsmBcFramerNonOctetErrors
      Counter32,
   gsmBcFramerOverruns
      Counter32,
   gsmBcFramerUnderruns
      Counter32 }

gsmBcFramerFrmToIf OBJECT-TYPE
   SYNTAX     Counter32 
   ACCESS     read-only
   STATUS     mandatory
   DESCRIPTION
     "This attribute counts the number of frames transmitted to the link 
      interface by Framer. The counter wraps when it exceeds the 
      maximum value."
::= { gsmBcFramerStatsEntry 1 }

gsmBcFramerFrmFromIf OBJECT-TYPE
   SYNTAX     Counter32 
   ACCESS     read-only
   STATUS     mandatory
   DESCRIPTION
     "This attribute counts the number of frames received from the link 
      interface by Framer. The counter wraps when it exceeds the 
      maximum value."
::= { gsmBcFramerStatsEntry 2 }

gsmBcFramerOctetFromIf OBJECT-TYPE
   SYNTAX     Counter32 
   ACCESS     read-only
   STATUS     mandatory
   DESCRIPTION
     "This attribute counts the number of bytes received from the link 
      interface by Framer. The counter wraps when it exceeds the 
      maximum value."
::= { gsmBcFramerStatsEntry 3 }

gsmBcFramerCrcErrors OBJECT-TYPE
   SYNTAX     Counter32 
   ACCESS     read-only
   STATUS     mandatory
   DESCRIPTION
     "This attribute coutns the the total number of frames with CRC 
      errors, occurring in the receive direction from the link. The counter 
      wraps when it exceeds the maximum value."
::= { gsmBcFramerStatsEntry 5 }

gsmBcFramerLrcErrors OBJECT-TYPE
   SYNTAX     Counter32 
   ACCESS     read-only
   STATUS     mandatory
   DESCRIPTION
     "This attribute counts the total number of frames with LRC errors, 
      occurring in the Tx link prior to transmission onto the link. The 
      counter wraps when it exceeds the maximum value."
::= { gsmBcFramerStatsEntry 6 }

gsmBcFramerNonOctetErrors OBJECT-TYPE
   SYNTAX     Counter32 
   ACCESS     read-only
   STATUS     mandatory
   DESCRIPTION
     "This attribute counts the total number of frames that were non octet 
      aligned. The counter wraps when it exceeds the maximum value."
::= { gsmBcFramerStatsEntry 7 }

gsmBcFramerOverruns OBJECT-TYPE
   SYNTAX     Counter32 
   ACCESS     read-only
   STATUS     mandatory
   DESCRIPTION
     "This attribute counts the total number of frames received from the 
      link for which overruns occurred. The counter wraps when it 
      exceeds the maximum value."
::= { gsmBcFramerStatsEntry 8 }

gsmBcFramerUnderruns OBJECT-TYPE
   SYNTAX     Counter32 
   ACCESS     read-only
   STATUS     mandatory
   DESCRIPTION
     "This attributecounts the total number of frames transmitted to the 
      link for which underruns occurred. The counter wraps when it 
      exceeds the maximum value."
::= { gsmBcFramerStatsEntry 9 }

gsmBcFramerLinkTable OBJECT-TYPE
   SYNTAX     SEQUENCE OF GsmBcFramerLinkEntry
   ACCESS     not-accessible
   STATUS     mandatory
   DESCRIPTION
     "This group contains provisionable attributes for the GsmIwfFramer 
      which controls link layer framing for application components 
      sending and receiving data on a link interface for this particular 
      GsmIwfBearerChannel."
::= { gsmBcFramer 12 }

gsmBcFramerLinkEntry OBJECT-TYPE
   SYNTAX     GsmBcFramerLinkEntry
   ACCESS     not-accessible
   STATUS     mandatory
   DESCRIPTION
     "An entry in the gsmBcFramerLinkTable."
   INDEX {
      gsmBcTrunkGrpIndex,
      gsmBcCicIndex,
      gsmBcFramerIndex }
::= { gsmBcFramerLinkTable 1 }

GsmBcFramerLinkEntry ::= SEQUENCE {
   gsmBcFramerFramingType
      INTEGER }

gsmBcFramerFramingType OBJECT-TYPE
   SYNTAX     INTEGER  {
                 btdsFraming(2),
                 gsmFraming(8) }
   ACCESS     read-write
   STATUS     mandatory
   DESCRIPTION
     "This attribute indicates the type of framing for the link layer data 
      received and transmitted on this channel. Valid values are:
      BtdsFraming, bit transparent framing required for the 
      GsmIwfBearerChannel components on MVP cards.
      GsmFraming, GSM framing for the GsmIwfBearerChannel 
      components on DS1C/E1C cards."
   DEFVAL     { gsmFraming }
::= { gsmBcFramerLinkEntry 1 }

gsmBcFramerStateTable OBJECT-TYPE
   SYNTAX     SEQUENCE OF GsmBcFramerStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { gsmBcFramer 13 }

gsmBcFramerStateEntry OBJECT-TYPE
   SYNTAX     GsmBcFramerStateEntry
   ACCESS     not-accessible
   STATUS     mandatory
   DESCRIPTION
     "An entry in the gsmBcFramerStateTable."
   INDEX {
      gsmBcTrunkGrpIndex,
      gsmBcCicIndex,
      gsmBcFramerIndex }
::= { gsmBcFramerStateTable 1 }

GsmBcFramerStateEntry ::= SEQUENCE {
   gsmBcFramerAdminState
      INTEGER,
   gsmBcFramerOperationalState
      INTEGER,
   gsmBcFramerUsageState
      INTEGER }

gsmBcFramerAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { gsmBcFramerStateEntry 1 }

gsmBcFramerOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { gsmBcFramerStateEntry 2 }

gsmBcFramerUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { gsmBcFramerStateEntry 3 }


-- GsmBc/<trunkGrp>,<cic> Layer1
-- This component represents the group of measurements for the GSM 
-- Layer 1 protocol established for a GSM IWF call (on the mobile 
-- station to IWF link) on this particular GsmIwfBearerChannel. 
-- Note that this component is present only if the current (or most 
-- recent call) involved this protocol.

gsmBcLayer1 OBJECT IDENTIFIER ::= { gsmBc 3 }



gsmBcLayer1RowStatusTable OBJECT-TYPE
   SYNTAX     SEQUENCE OF GsmBcLayer1RowStatusEntry
   ACCESS     not-accessible
   STATUS     mandatory
   DESCRIPTION
     "This entry controls the addition and deletion of 
      gsmBcLayer1 components."
::= { gsmBcLayer1 1 }

gsmBcLayer1RowStatusEntry OBJECT-TYPE
   SYNTAX     GsmBcLayer1RowStatusEntry
   ACCESS     not-accessible
   STATUS     mandatory
   DESCRIPTION
     "A single entry in the table represents a single 
      gsmBcLayer1 component."
   INDEX {
      gsmBcTrunkGrpIndex,
      gsmBcCicIndex,
      gsmBcLayer1Index }
::= { gsmBcLayer1RowStatusTable 1 }

GsmBcLayer1RowStatusEntry ::= SEQUENCE {
   gsmBcLayer1RowStatus
      RowStatus,
   gsmBcLayer1ComponentName
      DisplayString,
   gsmBcLayer1StorageType
      StorageType,
   gsmBcLayer1Index
      NonReplicated }

gsmBcLayer1RowStatus OBJECT-TYPE
   SYNTAX     RowStatus 
   ACCESS     read-only
   STATUS     mandatory
   DESCRIPTION
     "This variable is used as the basis for SNMP naming of
      gsmBcLayer1 components.
      These components cannot be added nor deleted."
::= { gsmBcLayer1RowStatusEntry 1 }

gsmBcLayer1ComponentName OBJECT-TYPE
   SYNTAX     DisplayString 
   ACCESS     read-only
   STATUS     mandatory
   DESCRIPTION
     "This variable provides the component's string name for
      use with the ASCII Console Interface"
::= { gsmBcLayer1RowStatusEntry 2 }

gsmBcLayer1StorageType OBJECT-TYPE
   SYNTAX     StorageType 
   ACCESS     read-only
   STATUS     mandatory
   DESCRIPTION
     "This variable represents the storage type value for the
      gsmBcLayer1 tables."
::= { gsmBcLayer1RowStatusEntry 4 }

gsmBcLayer1Index OBJECT-TYPE
   SYNTAX     NonReplicated 
   ACCESS     not-accessible
   STATUS     mandatory
   DESCRIPTION
     "This variable represents the index for the gsmBcLayer1 tables."
::= { gsmBcLayer1RowStatusEntry 10 }

gsmBcLayer1OperTable OBJECT-TYPE
   SYNTAX     SEQUENCE OF GsmBcLayer1OperEntry
   ACCESS     not-accessible
   STATUS     mandatory
   DESCRIPTION
     "This group contains physical layer operational attributes concerning 
      the operation of this particular GsmIwfBearerChannel."
::= { gsmBcLayer1 10 }

gsmBcLayer1OperEntry OBJECT-TYPE
   SYNTAX     GsmBcLayer1OperEntry
   ACCESS     not-accessible
   STATUS     mandatory
   DESCRIPTION
     "An entry in the gsmBcLayer1OperTable."
   INDEX {
      gsmBcTrunkGrpIndex,
      gsmBcCicIndex,
      gsmBcLayer1Index }
::= { gsmBcLayer1OperTable 1 }

GsmBcLayer1OperEntry ::= SEQUENCE {
   gsmBcLayer1ActiveMode
      INTEGER,
   gsmBcLayer1Connection
      INTEGER,
   gsmBcLayer1DataRate
      Unsigned32,
   gsmBcLayer1IntermediateRate
      Unsigned32 }

gsmBcLayer1ActiveMode OBJECT-TYPE
   SYNTAX     INTEGER  {
                 v110(0),
                 aTrau(1) }
   ACCESS     read-only
   STATUS     mandatory
   DESCRIPTION
     "This attribute indicates the active physical layer protocol between 
      the mobile and the IWF. Valid values are:
      v110, GSM V.110 rate adaptation scheme for interworking V-series 
      connections to an Integrated Services Digital Network (ISDN).
      aTrau, GSM A-Transcoder/Rate Adaptor (A-TRAU)."
::= { gsmBcLayer1OperEntry 1 }

gsmBcLayer1Connection OBJECT-TYPE
   SYNTAX     INTEGER  {
                 transparent(0),
                 nonTransparent(1) }
   ACCESS     read-only
   STATUS     mandatory
   DESCRIPTION
     "This attribute indicates the connection between the mobile and the 
      IWF. Valid values are:
      transparent, Constant throughput, constant transit delay, and 
      variable error rate (does not use Radio Link Protocol).
      nonTransparent, Improved error rate with variable transit delay and 
      variable throughput (uses Radio Link Protocol)."
::= { gsmBcLayer1OperEntry 2 }

gsmBcLayer1DataRate OBJECT-TYPE
   SYNTAX     Unsigned32 (0..64000)
   ACCESS     read-only
   STATUS     mandatory
   DESCRIPTION
     "This attribute indicates the layer 1 user data rate for the currently 
      active call for this GsmIwfBearerChannel. This is the data rate 
      between the mobile and IWF."
::= { gsmBcLayer1OperEntry 3 }

gsmBcLayer1IntermediateRate OBJECT-TYPE
   SYNTAX     Unsigned32 (8 | 16)
   ACCESS     read-only
   STATUS     mandatory
   DESCRIPTION
     "This attribute indicates the intermediate rate used in the physical 
      layer rate adaptation process. This field is valid between the mobile 
      and the IWF. For user data rates of 300 bit/s - 4800 bit/s the 
      intermediate rate is 8 kbit/s. For user data rates 9600 bit/s and above 
      the intermediate rate is 16 kbit/s."
::= { gsmBcLayer1OperEntry 10 }

gsmBcLayer1StatsTable OBJECT-TYPE
   SYNTAX     SEQUENCE OF GsmBcLayer1StatsEntry
   ACCESS     not-accessible
   STATUS     mandatory
   DESCRIPTION
     "This group contains physical layer statistics concerning the 
      operation of this particular GsmIwfBearerChannel."
::= { gsmBcLayer1 11 }

gsmBcLayer1StatsEntry OBJECT-TYPE
   SYNTAX     GsmBcLayer1StatsEntry
   ACCESS     not-accessible
   STATUS     mandatory
   DESCRIPTION
     "An entry in the gsmBcLayer1StatsTable."
   INDEX {
      gsmBcTrunkGrpIndex,
      gsmBcCicIndex,
      gsmBcLayer1Index }
::= { gsmBcLayer1StatsTable 1 }

GsmBcLayer1StatsEntry ::= SEQUENCE {
   gsmBcLayer1FramesTx
      Counter32,
   gsmBcLayer1FramesRx
      Counter32,
   gsmBcLayer1BytesTx
      Counter32,
   gsmBcLayer1BytesRx
      Counter32,
   gsmBcLayer1UnderRunsTx
      Counter32,
   gsmBcLayer1OverRunsRx
      Counter32,
   gsmBcLayer1NonOctetErrorsRx
      Counter32,
   gsmBcLayer1LargeFrameErrorsRx
      Counter32,
   gsmBcLayer1FramesDiscarded
      Counter32,
   gsmBcLayer1LrcErrorsTx
      Counter32 }

gsmBcLayer1FramesTx OBJECT-TYPE
   SYNTAX     Counter32 
   ACCESS     read-only
   STATUS     mandatory
   DESCRIPTION
     "This attribute counts the number of frames transmitted on the link. 
      The counter wraps when it exceeds the maximum value."
::= { gsmBcLayer1StatsEntry 1 }

gsmBcLayer1FramesRx OBJECT-TYPE
   SYNTAX     Counter32 
   ACCESS     read-only
   STATUS     mandatory
   DESCRIPTION
     "This attribute counts the number of frames received on the link. 
      Discarded frames are not included in this count. The counter wraps 
      when it exceeds the maximum value."
::= { gsmBcLayer1StatsEntry 2 }

gsmBcLayer1BytesTx OBJECT-TYPE
   SYNTAX     Counter32 
   ACCESS     read-only
   STATUS     mandatory
   DESCRIPTION
     "This attribute counts number of bytes transmitted on the link. The 
      counter wraps when it exceeds the maximum value."
::= { gsmBcLayer1StatsEntry 3 }

gsmBcLayer1BytesRx OBJECT-TYPE
   SYNTAX     Counter32 
   ACCESS     read-only
   STATUS     mandatory
   DESCRIPTION
     "This attribute counts the number of bytes received on the link. Bytes 
      from discarded frames are not included in this count. The counter 
      wraps when it exceeds the maximum value."
::= { gsmBcLayer1StatsEntry 4 }

gsmBcLayer1UnderRunsTx OBJECT-TYPE
   SYNTAX     Counter32 
   ACCESS     read-only
   STATUS     mandatory
   DESCRIPTION
     "This attribute counts number of underruns, on a per-call basis, in the 
      transmit direction reported by the hardware on the mobile-side.. 
      These frames are not counted towards the number of frames 
      transmitted (framesTx). The counter wraps when it exceeds the 
      maximum value."
::= { gsmBcLayer1StatsEntry 5 }

gsmBcLayer1OverRunsRx OBJECT-TYPE
   SYNTAX     Counter32 
   ACCESS     read-only
   STATUS     mandatory
   DESCRIPTION
     "This attribute counts number of overruns, on a per-call basis, in the 
      receive direction reported by the hardware on the mobile-side. 
      These frames are discarded. These frames are not counted towards 
      the number of frames received (framesRx). The counter wraps when 
      it exceeds the maximum value."
::= { gsmBcLayer1StatsEntry 6 }

gsmBcLayer1NonOctetErrorsRx OBJECT-TYPE
   SYNTAX     Counter32 
   ACCESS     read-only
   STATUS     mandatory
   DESCRIPTION
     "This attribute counts the number of non-octet synchronous frame 
      errors, on a per-call basis, received on the link reported by the 
      hardware. This is when a frame whose bit content was not divisible 
      by eight was detected. These frames are discarded. These frames 
      are not counted towards the number of frames received (framesRx). 
      The counter wraps when it exceeds the maximum value."
::= { gsmBcLayer1StatsEntry 7 }

gsmBcLayer1LargeFrameErrorsRx OBJECT-TYPE
   SYNTAX     Counter32 
   ACCESS     read-only
   STATUS     mandatory
   DESCRIPTION
     "This attribute counts the number of frames, on a per-call basis, 
      received on the link that exceeded internal buffer limits reported by 
      the hardware. A large number of these errors could indicate a bad 
      physical medium. These frames are discarded. These frames are not 
      counted towards the number of frames received (framesRx). The 
      counter wraps when it exceeds the maximum value."
::= { gsmBcLayer1StatsEntry 8 }

gsmBcLayer1FramesDiscarded OBJECT-TYPE
   SYNTAX     Counter32 
   ACCESS     read-only
   STATUS     mandatory
   DESCRIPTION
     "This attribute counts the number of frames discarded, on a per-call 
      basis, in the receive direction by software due to frame errors. The 
      counter wraps when it exceeds the maximum value."
::= { gsmBcLayer1StatsEntry 9 }

gsmBcLayer1LrcErrorsTx OBJECT-TYPE
   SYNTAX     Counter32 
   ACCESS     read-only
   STATUS     mandatory
   DESCRIPTION
     "This attribute counts the number of corrupted frames, on a per-call 
      basis, due to memory inconsistencies found by Longitude 
      Redundancy Check (LRC) checks at the IWF. These frames are not 
      counted towards the number of frames transmitted (framesTx). The 
      counter wraps when it exceeds the maximum value."
::= { gsmBcLayer1StatsEntry 10 }


-- GsmBc/<trunkGrp>,<cic> Modem
-- This component represents the group of measurements for the 
-- modem protocol established for a GSM IWF call (on the IWF to 
-- Public Switched Telephone Network (PSTN) modem link) on this 
-- particular GsmIwfBearerChannel. 
-- Note that this component is present only if the current (or most 
-- recent call) involved this protocol.

gsmBcModem OBJECT IDENTIFIER ::= { gsmBc 4 }



gsmBcModemRowStatusTable OBJECT-TYPE
   SYNTAX     SEQUENCE OF GsmBcModemRowStatusEntry
   ACCESS     not-accessible
   STATUS     mandatory
   DESCRIPTION
     "This entry controls the addition and deletion of 
      gsmBcModem components."
::= { gsmBcModem 1 }

gsmBcModemRowStatusEntry OBJECT-TYPE
   SYNTAX     GsmBcModemRowStatusEntry
   ACCESS     not-accessible
   STATUS     mandatory
   DESCRIPTION
     "A single entry in the table represents a single 
      gsmBcModem component."
   INDEX {
      gsmBcTrunkGrpIndex,
      gsmBcCicIndex,
      gsmBcModemIndex }
::= { gsmBcModemRowStatusTable 1 }

GsmBcModemRowStatusEntry ::= SEQUENCE {
   gsmBcModemRowStatus
      RowStatus,
   gsmBcModemComponentName
      DisplayString,
   gsmBcModemStorageType
      StorageType,
   gsmBcModemIndex
      NonReplicated }

gsmBcModemRowStatus OBJECT-TYPE
   SYNTAX     RowStatus 
   ACCESS     read-only
   STATUS     mandatory
   DESCRIPTION
     "This variable is used as the basis for SNMP naming of
      gsmBcModem components.
      These components cannot be added nor deleted."
::= { gsmBcModemRowStatusEntry 1 }

gsmBcModemComponentName OBJECT-TYPE
   SYNTAX     DisplayString 
   ACCESS     read-only
   STATUS     mandatory
   DESCRIPTION
     "This variable provides the component's string name for
      use with the ASCII Console Interface"
::= { gsmBcModemRowStatusEntry 2 }

gsmBcModemStorageType OBJECT-TYPE
   SYNTAX     StorageType 
   ACCESS     read-only
   STATUS     mandatory
   DESCRIPTION
     "This variable represents the storage type value for the
      gsmBcModem tables."
::= { gsmBcModemRowStatusEntry 4 }

gsmBcModemIndex OBJECT-TYPE
   SYNTAX     NonReplicated 
   ACCESS     not-accessible
   STATUS     mandatory
   DESCRIPTION
     "This variable represents the index for the gsmBcModem tables."
::= { gsmBcModemRowStatusEntry 10 }

gsmBcModemOperTable OBJECT-TYPE
   SYNTAX     SEQUENCE OF GsmBcModemOperEntry
   ACCESS     not-accessible
   STATUS     mandatory
   DESCRIPTION
     "This group contains operational attributes that measure performance 
      of the modem component for this particular GsmIwfBearerChannel."
::= { gsmBcModem 10 }

gsmBcModemOperEntry OBJECT-TYPE
   SYNTAX     GsmBcModemOperEntry
   ACCESS     not-accessible
   STATUS     mandatory
   DESCRIPTION
     "An entry in the gsmBcModemOperTable."
   INDEX {
      gsmBcTrunkGrpIndex,
      gsmBcCicIndex,
      gsmBcModemIndex }
::= { gsmBcModemOperTable 1 }

GsmBcModemOperEntry ::= SEQUENCE {
   gsmBcModemRate
      INTEGER,
   gsmBcModemAlgorithmInUse
      OCTET STRING,
   gsmBcModemProtocolState
      INTEGER,
   gsmBcModemReceiverTransmitter
      INTEGER,
   gsmBcModemTraining
      INTEGER,
   gsmBcModemToUpperFlowControlActive
      INTEGER,
   gsmBcModemToDspFlowControlActive
      INTEGER,
   gsmBcModemAsyncMode
      INTEGER,
   gsmBcModemAutoHdlcMode
      INTEGER,
   gsmBcModemOutbandFlowControl
      INTEGER,
   gsmBcModemOutbandBreak
      INTEGER,
   gsmBcModemAutobaud
      INTEGER }

gsmBcModemRate OBJECT-TYPE
   SYNTAX     INTEGER  {
                 n300(0),
                 n600(1),
                 n1200(2),
                 n120075(3),
                 n2400(4),
                 n4800(5),
                 n7200(6),
                 n9600(7),
                 n12000(8),
                 n14400(9),
                 n16800(10),
                 n19200(11),
                 n21600(12),
                 n24000(13),
                 n26400(14),
                 n28800(15),
                 n31200(16),
                 n32000(17),
                 n33600(18),
                 n38400(19),
                 n43200(20),
                 n48000(21),
                 n56000(22),
                 n57600(23),
                 n64000(24) }
   ACCESS     read-only
   STATUS     mandatory
   DESCRIPTION
     "This attribute indicates the transmission rate of the current modem 
      in use. A rate of 1200_75 is 75 bit/s in the transmit direction and 
      1200 bit/s in the receive direction. All other rates are the same in 
      both the transmit and receive directions."
::= { gsmBcModemOperEntry 2 }

gsmBcModemAlgorithmInUse OBJECT-TYPE
   SYNTAX     OCTET STRING (SIZE (2))
   ACCESS     read-only
   STATUS     mandatory
   DESCRIPTION
     "This attribute indicates the current modem algorithm(s) active for 
      the channel. Valid values are:
      v17, V.17 is active.V.17 is an ITU-T 14400bit/s modem standard. 
      v27ter, V.27ter is active. V.27ter is an ITU-T 7200bit/s modem 
      standard.
      v29, V.29 is active. V.29 an ITU-T 9600bit/s modem standard. 
      v21, V.21 active. V.21 is an ITU-4 300bit/s modem standard. 
      v22bis, V.22 or V.22bis active. V.22 ia an ITU-T modem standard 
      that operates at 1200bit/s and 600 baud. V.22bis is an ITU-T 
      modem standard that operates at 2400bit/s and 600 baud. 
      v23, V.23 active. V.23 is an ITU-T modem standard that operates at 
      a speed of 1200bit/s. 
      v26ter, V.26ter active. V.26ter is an ITU-T modem standard that 
      operates at a speed of 2400bit/s. 
      v32bis, V.32 or V.32bis active. V.32 is an ITU-T modem standard 
      that operates at 9600bit/s and 2400 baud. V.32bis is an ITU-T 
      modem standard that operates at a speed of 14.4kbit/s. 
      v34, V.34 active. V.34 is an ITU-T modem standard that operates at 
      a speed of up to 28.8kbit/s.

      Description of bits:
      notused0(0)
      v17(1)
      v29(2)
      v27ter(3)
      v21(4)
      v22bis(5)
      v23(6)
      v26ter(7)
      v32bis(8)
      v34(9)"
::= { gsmBcModemOperEntry 3 }

gsmBcModemProtocolState OBJECT-TYPE
   SYNTAX     INTEGER  {
                 idle(0),
                 training(1),
                 connected(2) }
   ACCESS     read-only
   STATUS     mandatory
   DESCRIPTION
     "This attribute indicates the active protocol state of the modem in 
      use.Valid values are:
      idle, Modem is in an inactive state and has no current connection 
      established.
      training, Modem is attempting to establish a connection with the far 
      end modem via handshaking.
      connected, Modem has establish a connection with the far end 
      modem."
::= { gsmBcModemOperEntry 4 }

gsmBcModemReceiverTransmitter OBJECT-TYPE
   SYNTAX     INTEGER  {
                 notApplicable(0),
                 rxOnTxOff(1),
                 rxOffTxOn(2),
                 rxTxOn(3) }
   ACCESS     read-only
   STATUS     mandatory
   DESCRIPTION
     "This attribute indicates whether the fax data modem is in receive or 
      transmit mode. If this is not a fax data modem call, then the value is 
      set to notApplicable. Valid values are:
      notApplicable, Not an applicable field. 
      rxOnTxOff, Receiver is on, transmitter is off.
      rxOffTxOn, Receiver is off, transmitter is on.
      rxTxOn, Reciever is on, transmitter is on."
   DEFVAL     { notApplicable }
::= { gsmBcModemOperEntry 5 }

gsmBcModemTraining OBJECT-TYPE
   SYNTAX     INTEGER  {
                 short(0),
                 long(1),
                 notApplicable(99) }
   ACCESS     read-only
   STATUS     mandatory
   DESCRIPTION
     "This attribute indicates the training procedure used by the V.17 
      modems. ITU-T defines two training procedures. A longer training 
      procedure used at call setup, and a short training procedure is used 
      during the fax call when switching from the V.21 modem to the 
      V.17 modem. A value of notApplicable indicates that the attribute is 
      not applicable for the modem."
   DEFVAL     { notApplicable }
::= { gsmBcModemOperEntry 6 }

gsmBcModemToUpperFlowControlActive OBJECT-TYPE
   SYNTAX     INTEGER  {
                 on(0),
                 off(1) }
   ACCESS     read-only
   STATUS     mandatory
   DESCRIPTION
     "This attribute indicates whether flow control was requested and an 
      indication was sent to an upper layer protocol."
::= { gsmBcModemOperEntry 8 }

gsmBcModemToDspFlowControlActive OBJECT-TYPE
   SYNTAX     INTEGER  {
                 on(0),
                 off(1) }
   ACCESS     read-only
   STATUS     mandatory
   DESCRIPTION
     "This attribute indicates whether an upper layer protocol requested 
      flow control and an indication was sent to the Digital Signal 
      Processor."
::= { gsmBcModemOperEntry 9 }

gsmBcModemAsyncMode OBJECT-TYPE
   SYNTAX     INTEGER  {
                 on(0),
                 off(1) }
   ACCESS     read-only
   STATUS     mandatory
   DESCRIPTION
     "This attribute indicates whether conversion between synchronous 
      and asynchronous data format (specifacally, the stripping or 
      insertion of start and stop bits) is being performed. The value will 
      be on unless the V.42 layer is active or it is a fax call."
::= { gsmBcModemOperEntry 10 }

gsmBcModemAutoHdlcMode OBJECT-TYPE
   SYNTAX     INTEGER  {
                 on(0),
                 off(1) }
   ACCESS     read-only
   STATUS     mandatory
   DESCRIPTION
     "This attribute indicates whether High-Level Data Link Control 
      (HDLC) functions are being performed by the modem to support 
      HDLC applications (V.42 for example)."
::= { gsmBcModemOperEntry 11 }

gsmBcModemOutbandFlowControl OBJECT-TYPE
   SYNTAX     INTEGER  {
                 on(0),
                 off(1) }
   ACCESS     read-only
   STATUS     mandatory
   DESCRIPTION
     "This attribute indicates whether inband or outband flow control 
      conversions are being performed. The modem performs either 
      inband or outband flow control unless V.42 layer is active, it is a fax 
      call, or no flow control was specified by the MSC."
::= { gsmBcModemOperEntry 12 }

gsmBcModemOutbandBreak OBJECT-TYPE
   SYNTAX     INTEGER  {
                 on(0),
                 off(1) }
   ACCESS     read-only
   STATUS     mandatory
   DESCRIPTION
     "This attribute indicates whether inband or outband break control 
      conversions are being performed. This is when the modem detects a 
      break condition as defined by ITU-T X.28 and reports it. When a 
      break condition is discovered all subsequent incoming data is 
      discarded until a start bit is received."
::= { gsmBcModemOperEntry 13 }

gsmBcModemAutobaud OBJECT-TYPE
   SYNTAX     INTEGER  {
                 on(0),
                 off(1) }
   ACCESS     read-only
   STATUS     mandatory
   DESCRIPTION
     "This attribute indicates whether autobaud is active. 
      The modem is instructed at call setup time by the MSC on:
      What is the initial modem data rate value and 
      Whether a modem is allowed to perform autobauding (on) or not 
      (off). With Autobauding on, the modem is allowed to connect using 
      a valid modem data rate less than or equal to the initial rate 
      specified to the modem by the MSC. If a modem can not perform 
      autobauding and the carrier can not be established at the initial data 
      rate, the modem is disabled."
::= { gsmBcModemOperEntry 14 }

gsmBcModemStatsTable OBJECT-TYPE
   SYNTAX     SEQUENCE OF GsmBcModemStatsEntry
   ACCESS     not-accessible
   STATUS     mandatory
   DESCRIPTION
     "This group contains operational attributes that measure performance 
      of the modem component for this particular GsmIwfBearerChannel."
::= { gsmBcModem 11 }

gsmBcModemStatsEntry OBJECT-TYPE
   SYNTAX     GsmBcModemStatsEntry
   ACCESS     not-accessible
   STATUS     mandatory
   DESCRIPTION
     "An entry in the gsmBcModemStatsTable."
   INDEX {
      gsmBcTrunkGrpIndex,
      gsmBcCicIndex,
      gsmBcModemIndex }
::= { gsmBcModemStatsTable 1 }

GsmBcModemStatsEntry ::= SEQUENCE {
   gsmBcModemBytesTx
      Counter32,
   gsmBcModemBytesRx
      Counter32,
   gsmBcModemFramingErrors
      Counter32 }

gsmBcModemBytesTx OBJECT-TYPE
   SYNTAX     Counter32 
   ACCESS     read-only
   STATUS     mandatory
   DESCRIPTION
     "This attribute counts the number of payload bytes transmitted. The 
      counter wraps when it exceeds the maximum value."
::= { gsmBcModemStatsEntry 1 }

gsmBcModemBytesRx OBJECT-TYPE
   SYNTAX     Counter32 
   ACCESS     read-only
   STATUS     mandatory
   DESCRIPTION
     "This attribute counts the number of payload bytes received. The 
      counter wraps when it exceeds the maximum value."
::= { gsmBcModemStatsEntry 2 }

gsmBcModemFramingErrors OBJECT-TYPE
   SYNTAX     Counter32 
   ACCESS     read-only
   STATUS     mandatory
   DESCRIPTION
     "This attribute counts the number of framing errors detected by the 
      hardware. This is the absence of a stop bit after a start bit and eight 
      bits of data. All incoming data is discarded until the next start bit is 
      received. The counter wraps when it exceeds the maximum value."
::= { gsmBcModemStatsEntry 6 }


-- GsmBc/<trunkGrp>,<cic> V110
-- This component represents the group of measurements for the ITU-
-- T V.110 rate adaptation protocol established for a GSM IWF call 
-- (on the IWF to Integrated Services Digital Network (ISDN) 
-- terminal adapter link) on this particular GsmIwfBearerChannel. 
-- Note that this component is present only if the current (or most 
-- recent call) involved this protocol.

gsmBcV110 OBJECT IDENTIFIER ::= { gsmBc 5 }



gsmBcV110RowStatusTable OBJECT-TYPE
   SYNTAX     SEQUENCE OF GsmBcV110RowStatusEntry
   ACCESS     not-accessible
   STATUS     mandatory
   DESCRIPTION
     "This entry controls the addition and deletion of 
      gsmBcV110 components."
::= { gsmBcV110 1 }

gsmBcV110RowStatusEntry OBJECT-TYPE
   SYNTAX     GsmBcV110RowStatusEntry
   ACCESS     not-accessible
   STATUS     mandatory
   DESCRIPTION
     "A single entry in the table represents a single 
      gsmBcV110 component."
   INDEX {
      gsmBcTrunkGrpIndex,
      gsmBcCicIndex,
      gsmBcV110Index }
::= { gsmBcV110RowStatusTable 1 }

GsmBcV110RowStatusEntry ::= SEQUENCE {
   gsmBcV110RowStatus
      RowStatus,
   gsmBcV110ComponentName
      DisplayString,
   gsmBcV110StorageType
      StorageType,
   gsmBcV110Index
      NonReplicated }

gsmBcV110RowStatus OBJECT-TYPE
   SYNTAX     RowStatus 
   ACCESS     read-only
   STATUS     mandatory
   DESCRIPTION
     "This variable is used as the basis for SNMP naming of
      gsmBcV110 components.
      These components cannot be added nor deleted."
::= { gsmBcV110RowStatusEntry 1 }

gsmBcV110ComponentName OBJECT-TYPE
   SYNTAX     DisplayString 
   ACCESS     read-only
   STATUS     mandatory
   DESCRIPTION
     "This variable provides the component's string name for
      use with the ASCII Console Interface"
::= { gsmBcV110RowStatusEntry 2 }

gsmBcV110StorageType OBJECT-TYPE
   SYNTAX     StorageType 
   ACCESS     read-only
   STATUS     mandatory
   DESCRIPTION
     "This variable represents the storage type value for the
      gsmBcV110 tables."
::= { gsmBcV110RowStatusEntry 4 }

gsmBcV110Index OBJECT-TYPE
   SYNTAX     NonReplicated 
   ACCESS     not-accessible
   STATUS     mandatory
   DESCRIPTION
     "This variable represents the index for the gsmBcV110 tables."
::= { gsmBcV110RowStatusEntry 10 }

gsmBcV110OperTable OBJECT-TYPE
   SYNTAX     SEQUENCE OF GsmBcV110OperEntry
   ACCESS     not-accessible
   STATUS     mandatory
   DESCRIPTION
     "This group contains operational attributes that measure the 
      performance of V110."
::= { gsmBcV110 10 }

gsmBcV110OperEntry OBJECT-TYPE
   SYNTAX     GsmBcV110OperEntry
   ACCESS     not-accessible
   STATUS     mandatory
   DESCRIPTION
     "An entry in the gsmBcV110OperTable."
   INDEX {
      gsmBcTrunkGrpIndex,
      gsmBcCicIndex,
      gsmBcV110Index }
::= { gsmBcV110OperTable 1 }

GsmBcV110OperEntry ::= SEQUENCE {
   gsmBcV110DataRate
      Unsigned32,
   gsmBcV110IntermediateRate
      INTEGER }

gsmBcV110DataRate OBJECT-TYPE
   SYNTAX     Unsigned32 (0..65000)
   ACCESS     read-only
   STATUS     mandatory
   DESCRIPTION
     "This attribute contains the layer 1 user data rate for the currently 
      active call for this GsmIwfBearerChannel. This is the data rate 
      between the IWF and the fixed network."
::= { gsmBcV110OperEntry 2 }

gsmBcV110IntermediateRate OBJECT-TYPE
   SYNTAX     INTEGER  {
                 n8KbitS(0),
                 n16KbitS(1),
                 n32KbitS(2),
                 notApplicable(3) }
   ACCESS     read-only
   STATUS     mandatory
   DESCRIPTION
     "This attribute indicates the intermediate rate used in the physical 
      layer rate adaptation process. This field is valid between the 
      network and the IWF. For user data rates of 300 bit/s to 4800 bit/s 
      the intermediate rate is 8 kbit/s. For a user data rate of 9600 bit/s the 
      intermediate rate is 16 kbit/s. For user data rates of 1200 bit/s to 
      19200 bit/s the intermediate rate is 32 kbit/s. Data rates above this 
      have no intermediate rate."
::= { gsmBcV110OperEntry 9 }

gsmBcV110StatsTable OBJECT-TYPE
   SYNTAX     SEQUENCE OF GsmBcV110StatsEntry
   ACCESS     not-accessible
   STATUS     mandatory
   DESCRIPTION
     "This group contains statistical attributes which measure the 
      performance of V110."
::= { gsmBcV110 11 }

gsmBcV110StatsEntry OBJECT-TYPE
   SYNTAX     GsmBcV110StatsEntry
   ACCESS     not-accessible
   STATUS     mandatory
   DESCRIPTION
     "An entry in the gsmBcV110StatsTable."
   INDEX {
      gsmBcTrunkGrpIndex,
      gsmBcCicIndex,
      gsmBcV110Index }
::= { gsmBcV110StatsTable 1 }

GsmBcV110StatsEntry ::= SEQUENCE {
   gsmBcV110FramesTx
      Counter32,
   gsmBcV110FramesRx
      Counter32,
   gsmBcV110BytesTx
      Counter32,
   gsmBcV110BytesRx
      Counter32,
   gsmBcV110UnderRunsTx
      Counter32,
   gsmBcV110OverRunsRx
      Counter32,
   gsmBcV110NonOctetErrorsRx
      Counter32,
   gsmBcV110LargeFrameErrorsRx
      Counter32,
   gsmBcV110FramesDiscarded
      Counter32,
   gsmBcV110LrcErrorsTx
      Counter32 }

gsmBcV110FramesTx OBJECT-TYPE
   SYNTAX     Counter32 
   ACCESS     read-only
   STATUS     mandatory
   DESCRIPTION
     "This attribute counts the number of frames transmitted on the link. 
      The counter wraps when it exceeds the maximum value."
::= { gsmBcV110StatsEntry 1 }

gsmBcV110FramesRx OBJECT-TYPE
   SYNTAX     Counter32 
   ACCESS     read-only
   STATUS     mandatory
   DESCRIPTION
     "This attribute counts the number of frames received on the link. 
      Discarded frames are not included in this count. The counter wraps 
      when it exceeds the maximum value."
::= { gsmBcV110StatsEntry 2 }

gsmBcV110BytesTx OBJECT-TYPE
   SYNTAX     Counter32 
   ACCESS     read-only
   STATUS     mandatory
   DESCRIPTION
     "This attribute counts the number of bytes transmitted on the link. 
      The counter wraps when it exceeds the maximum value."
::= { gsmBcV110StatsEntry 3 }

gsmBcV110BytesRx OBJECT-TYPE
   SYNTAX     Counter32 
   ACCESS     read-only
   STATUS     mandatory
   DESCRIPTION
     "This attribute counts the number of bytes received on the link. Bytes 
      from discarded frames are not included in this count. The counter 
      wraps when it exceeds the maximum value."
::= { gsmBcV110StatsEntry 4 }

gsmBcV110UnderRunsTx OBJECT-TYPE
   SYNTAX     Counter32 
   ACCESS     read-only
   STATUS     mandatory
   DESCRIPTION
     "This attribute counts the number of underruns, on a per-call basis, in 
      the transmit direction reported by the hardware on the network side. 
      These frames are not counted towards the number of frames 
      transmitted (framesTx). The counter wraps when it exceeds the 
      maximum value."
::= { gsmBcV110StatsEntry 5 }

gsmBcV110OverRunsRx OBJECT-TYPE
   SYNTAX     Counter32 
   ACCESS     read-only
   STATUS     mandatory
   DESCRIPTION
     "This attribute counts the number of overruns, on a per-call basis, in 
      the receive direction reported by the hardware on the network side. 
      These frames are discarded. These frames are not counted towards 
      the number of frames received (framesRx). The counter wraps when 
      it exceeds the maximum value."
::= { gsmBcV110StatsEntry 6 }

gsmBcV110NonOctetErrorsRx OBJECT-TYPE
   SYNTAX     Counter32 
   ACCESS     read-only
   STATUS     mandatory
   DESCRIPTION
     "This attribute counts the number of non-octet synchronous frame 
      errors, on a per-call basis, received on the link reported by the 
      hardware. These frames are discarded. These frames are not 
      counted towards the number of frames received (framesRx). The 
      counter wraps when it exceeds the maximum value."
::= { gsmBcV110StatsEntry 7 }

gsmBcV110LargeFrameErrorsRx OBJECT-TYPE
   SYNTAX     Counter32 
   ACCESS     read-only
   STATUS     mandatory
   DESCRIPTION
     "This attribute counts the number of frames received on the link that 
      exceeded internal buffer limits reported by the hardware, on a per-
      call basis. These frames are discarded. These frames are not 
      counted towards the number of frames received (framesRx). The 
      counter wraps when it exceeds the maximum value."
::= { gsmBcV110StatsEntry 8 }

gsmBcV110FramesDiscarded OBJECT-TYPE
   SYNTAX     Counter32 
   ACCESS     read-only
   STATUS     mandatory
   DESCRIPTION
     "This attribute counts the number of frames discarded, on a per-call 
      basis, in the receive direction by software due to frame errors. The 
      counter wraps when it exceeds the maximum value."
::= { gsmBcV110StatsEntry 9 }

gsmBcV110LrcErrorsTx OBJECT-TYPE
   SYNTAX     Counter32 
   ACCESS     read-only
   STATUS     mandatory
   DESCRIPTION
     "This attribute counts the number of corrupted frames, on a per-call 
      basis, due to memory inconsistencies found by Longitude 
      Redundancy Check (LRC) checks at the IWF. The counter wraps 
      when it exceeds the maximum value."
::= { gsmBcV110StatsEntry 10 }


-- GsmBc/<trunkGrp>,<cic> Fax
-- This component represents the group of measurements for the fax 
-- protocol established for a GSM IWF call (on the mobile station to 
-- IWF link or the IWF to Public Switched Telephone Network 
-- (PSTN) fax modem/machine link) on this particular 
-- GsmIwfBearerChannel.
-- Note that this component is present only if the current (or most 
-- recent call) involved this protocol. 

gsmBcFax OBJECT IDENTIFIER ::= { gsmBc 6 }



gsmBcFaxRowStatusTable OBJECT-TYPE
   SYNTAX     SEQUENCE OF GsmBcFaxRowStatusEntry
   ACCESS     not-accessible
   STATUS     mandatory
   DESCRIPTION
     "This entry controls the addition and deletion of 
      gsmBcFax components."
::= { gsmBcFax 1 }

gsmBcFaxRowStatusEntry OBJECT-TYPE
   SYNTAX     GsmBcFaxRowStatusEntry
   ACCESS     not-accessible
   STATUS     mandatory
   DESCRIPTION
     "A single entry in the table represents a single 
      gsmBcFax component."
   INDEX {
      gsmBcTrunkGrpIndex,
      gsmBcCicIndex,
      gsmBcFaxIndex }
::= { gsmBcFaxRowStatusTable 1 }

GsmBcFaxRowStatusEntry ::= SEQUENCE {
   gsmBcFaxRowStatus
      RowStatus,
   gsmBcFaxComponentName
      DisplayString,
   gsmBcFaxStorageType
      StorageType,
   gsmBcFaxIndex
      NonReplicated }

gsmBcFaxRowStatus OBJECT-TYPE
   SYNTAX     RowStatus 
   ACCESS     read-only
   STATUS     mandatory
   DESCRIPTION
     "This variable is used as the basis for SNMP naming of
      gsmBcFax components.
      These components cannot be added nor deleted."
::= { gsmBcFaxRowStatusEntry 1 }

gsmBcFaxComponentName OBJECT-TYPE
   SYNTAX     DisplayString 
   ACCESS     read-only
   STATUS     mandatory
   DESCRIPTION
     "This variable provides the component's string name for
      use with the ASCII Console Interface"
::= { gsmBcFaxRowStatusEntry 2 }

gsmBcFaxStorageType OBJECT-TYPE
   SYNTAX     StorageType 
   ACCESS     read-only
   STATUS     mandatory
   DESCRIPTION
     "This variable represents the storage type value for the
      gsmBcFax tables."
::= { gsmBcFaxRowStatusEntry 4 }

gsmBcFaxIndex OBJECT-TYPE
   SYNTAX     NonReplicated 
   ACCESS     not-accessible
   STATUS     mandatory
   DESCRIPTION
     "This variable represents the index for the gsmBcFax tables."
::= { gsmBcFaxRowStatusEntry 10 }

gsmBcFaxOperTable OBJECT-TYPE
   SYNTAX     SEQUENCE OF GsmBcFaxOperEntry
   ACCESS     not-accessible
   STATUS     mandatory
   DESCRIPTION
     "This group contains operational attributes which measure the 
      performance of the fax protocol."
::= { gsmBcFax 10 }

gsmBcFaxOperEntry OBJECT-TYPE
   SYNTAX     GsmBcFaxOperEntry
   ACCESS     not-accessible
   STATUS     mandatory
   DESCRIPTION
     "An entry in the gsmBcFaxOperTable."
   INDEX {
      gsmBcTrunkGrpIndex,
      gsmBcCicIndex,
      gsmBcFaxIndex }
::= { gsmBcFaxOperTable 1 }

GsmBcFaxOperEntry ::= SEQUENCE {
   gsmBcFaxActiveMode
      INTEGER,
   gsmBcFaxProtocolState
      INTEGER,
   gsmBcFaxMessageRate
      Unsigned32 }

gsmBcFaxActiveMode OBJECT-TYPE
   SYNTAX     INTEGER  {
                 normal(0),
                 ecm(1) }
   ACCESS     read-only
   STATUS     mandatory
   DESCRIPTION
     "This attribute indicates the mode of the fax T.30 protocol, 
      determined during Exchange Identification (XID) negotiations. The 
      following modes are supported:
      normal, normal T.30 protocol, Error Correction Mode (ECM) not 
      used
      ecm, Error Correction Mode used. Fax error correction is done 
      using a half-duplex page selective repeat technique."
   DEFVAL     { normal }
::= { gsmBcFaxOperEntry 1 }

gsmBcFaxProtocolState OBJECT-TYPE
   SYNTAX     INTEGER  {
                 setup(0),
                 idle(1),
                 bcsRx(2),
                 bcsTx(3),
                 msgRx(4),
                 msgTx(5) }
   ACCESS     read-only
   STATUS     mandatory
   DESCRIPTION
     "This attribute indicates the protocol state of the fax adaptor. The 
      values are:
      setup, call setup state
      idle, idle state only transmitting Synchronize (SYNC) frames
      bcsRx, receiving Binary Coded Signal (BCS) packet from modem
      bcsTx, transmitting BCS packet to modem
      msgRx, receiving fax message from modem
      msgTx, transmitting fax message to modem"
   DEFVAL     { idle }
::= { gsmBcFaxOperEntry 2 }

gsmBcFaxMessageRate OBJECT-TYPE
   SYNTAX     Unsigned32 (0..65000)
   ACCESS     read-only
   STATUS     mandatory
   DESCRIPTION
     "This attribute indicates the fax message rate used for sending fax 
      documents."
::= { gsmBcFaxOperEntry 3 }

gsmBcFaxStatsTable OBJECT-TYPE
   SYNTAX     SEQUENCE OF GsmBcFaxStatsEntry
   ACCESS     not-accessible
   STATUS     mandatory
   DESCRIPTION
     "This group contains statistical attributes which measure the 
      performance of the fax protocol."
::= { gsmBcFax 11 }

gsmBcFaxStatsEntry OBJECT-TYPE
   SYNTAX     GsmBcFaxStatsEntry
   ACCESS     not-accessible
   STATUS     mandatory
   DESCRIPTION
     "An entry in the gsmBcFaxStatsTable."
   INDEX {
      gsmBcTrunkGrpIndex,
      gsmBcCicIndex,
      gsmBcFaxIndex }
::= { gsmBcFaxStatsTable 1 }

GsmBcFaxStatsEntry ::= SEQUENCE {
   gsmBcFaxMessageFramesRx
      Counter32,
   gsmBcFaxMessageFramesTx
      Counter32,
   gsmBcFaxBcsFramesRx
      Counter32,
   gsmBcFaxBcsFramesTx
      Counter32,
   gsmBcFaxPagesRxFromMobile
      Counter32,
   gsmBcFaxPagesTxToMobile
      Counter32,
   gsmBcFaxChannelModeModify
      Counter32,
   gsmBcFaxBcsFrameErrors
      Counter32 }

gsmBcFaxMessageFramesRx OBJECT-TYPE
   SYNTAX     Counter32 
   ACCESS     read-only
   STATUS     mandatory
   DESCRIPTION
     "This attribute counts the number of fax message frames received 
      from the mobile. One fax message frame is an eight byte DATA 
      frame defined in GSM 3.45. The counter wraps when it exceeds the 
      maximum value."
::= { gsmBcFaxStatsEntry 1 }

gsmBcFaxMessageFramesTx OBJECT-TYPE
   SYNTAX     Counter32 
   ACCESS     read-only
   STATUS     mandatory
   DESCRIPTION
     "This attribute counts the number of fax message frames transmitted 
      to the mobile. One fax message frame is an eight byte DATA frame 
      defined in GSM 3.45. The counter wraps when it exceeds the 
      maximum value."
::= { gsmBcFaxStatsEntry 2 }

gsmBcFaxBcsFramesRx OBJECT-TYPE
   SYNTAX     Counter32 
   ACCESS     read-only
   STATUS     mandatory
   DESCRIPTION
     "This attribute counts the number of fax Binary Coded Signal (BCS) 
      frames received from the mobile. A fax BCS frame is an 8-byte 
      STATUS frame, which carries T.30 BCS data as defined in GSM 
      3.45. The counter wraps when it exceeds the maximum value."
::= { gsmBcFaxStatsEntry 3 }

gsmBcFaxBcsFramesTx OBJECT-TYPE
   SYNTAX     Counter32 
   ACCESS     read-only
   STATUS     mandatory
   DESCRIPTION
     "This attribute counts the number of fax Binary Coded Signal (BCS) 
      frames transmitted to the mobile. A fax BCS frame is an 8-byte 
      STATUS frame, which carries T.30 BCS data as defined in GSM 
      3.45. The counter wraps when it exceeds the maximum value."
::= { gsmBcFaxStatsEntry 4 }

gsmBcFaxPagesRxFromMobile OBJECT-TYPE
   SYNTAX     Counter32 
   ACCESS     read-only
   STATUS     mandatory
   DESCRIPTION
     "This attribute counts the number of fax pages received from the 
      mobile. The counter wraps when it exceeds the maximum value."
::= { gsmBcFaxStatsEntry 5 }

gsmBcFaxPagesTxToMobile OBJECT-TYPE
   SYNTAX     Counter32 
   ACCESS     read-only
   STATUS     mandatory
   DESCRIPTION
     "The attribute counts the number of fax pages transmitted to the 
      mobile. The counter wraps when it exceeds the maximum value."
::= { gsmBcFaxStatsEntry 6 }

gsmBcFaxChannelModeModify OBJECT-TYPE
   SYNTAX     Counter32 
   ACCESS     read-only
   STATUS     mandatory
   DESCRIPTION
     "This attribute counts the number of Channel Mode Modify (CMM) 
      requests initiated by the IWF. 
      For transparent fax calls, the transmission speed is determined by 
      the two fax machines at call setup. The speed may change during 
      the transmission to satisfy the T.30 protocol. The CMM request is 
      used by the GSM IWF to request that the T.30 requested speed 
      change can be propagated throughout the network. The counter 
      wraps when it exceeds the maximum value."
::= { gsmBcFaxStatsEntry 7 }

gsmBcFaxBcsFrameErrors OBJECT-TYPE
   SYNTAX     Counter32 
   ACCESS     read-only
   STATUS     mandatory
   DESCRIPTION
     "This attribute counts the number of fax Binary Coded Signal (BCS) 
      frames in error. This attribute indicates the count of corrupted fax 
      BCS frames over the GSM radio channel. The counter wraps when 
      it exceeds the maximum value."
::= { gsmBcFaxStatsEntry 8 }


-- GsmBc<trunkGrp>,<cic> RadioLinkProtocol/<rlp-type>
-- This component represents the group of measurements for the 
-- Radio Link Protocol (RLP) established for a GSM IWF call (on the 
-- mobile station to IWF link) on this particular 
-- GsmIwfBearerChannel. 
-- Note that this component is present only if the current (or most 
-- recent call) involved this protocol.

gsmBcRlp OBJECT IDENTIFIER ::= { gsmBc 7 }



gsmBcRlpRowStatusTable OBJECT-TYPE
   SYNTAX     SEQUENCE OF GsmBcRlpRowStatusEntry
   ACCESS     not-accessible
   STATUS     mandatory
   DESCRIPTION
     "This entry controls the addition and deletion of 
      gsmBcRlp components."
::= { gsmBcRlp 1 }

gsmBcRlpRowStatusEntry OBJECT-TYPE
   SYNTAX     GsmBcRlpRowStatusEntry
   ACCESS     not-accessible
   STATUS     mandatory
   DESCRIPTION
     "A single entry in the table represents a single 
      gsmBcRlp component."
   INDEX {
      gsmBcTrunkGrpIndex,
      gsmBcCicIndex,
      gsmBcRlpIndex }
::= { gsmBcRlpRowStatusTable 1 }

GsmBcRlpRowStatusEntry ::= SEQUENCE {
   gsmBcRlpRowStatus
      RowStatus,
   gsmBcRlpComponentName
      DisplayString,
   gsmBcRlpStorageType
      StorageType,
   gsmBcRlpIndex
      NonReplicated }

gsmBcRlpRowStatus OBJECT-TYPE
   SYNTAX     RowStatus 
   ACCESS     read-only
   STATUS     mandatory
   DESCRIPTION
     "This variable is used as the basis for SNMP naming of
      gsmBcRlp components.
      These components cannot be added nor deleted."
::= { gsmBcRlpRowStatusEntry 1 }

gsmBcRlpComponentName OBJECT-TYPE
   SYNTAX     DisplayString 
   ACCESS     read-only
   STATUS     mandatory
   DESCRIPTION
     "This variable provides the component's string name for
      use with the ASCII Console Interface"
::= { gsmBcRlpRowStatusEntry 2 }

gsmBcRlpStorageType OBJECT-TYPE
   SYNTAX     StorageType 
   ACCESS     read-only
   STATUS     mandatory
   DESCRIPTION
     "This variable represents the storage type value for the
      gsmBcRlp tables."
::= { gsmBcRlpRowStatusEntry 4 }

gsmBcRlpIndex OBJECT-TYPE
   SYNTAX     NonReplicated 
   ACCESS     not-accessible
   STATUS     mandatory
   DESCRIPTION
     "This variable represents the index for the gsmBcRlp tables."
::= { gsmBcRlpRowStatusEntry 10 }

gsmBcRlpOperTable OBJECT-TYPE
   SYNTAX     SEQUENCE OF GsmBcRlpOperEntry
   ACCESS     not-accessible
   STATUS     mandatory
   DESCRIPTION
     "This group contains operational attributes that measure performance 
      of the GsmIwfBearerChannel."
::= { gsmBcRlp 10 }

gsmBcRlpOperEntry OBJECT-TYPE
   SYNTAX     GsmBcRlpOperEntry
   ACCESS     not-accessible
   STATUS     mandatory
   DESCRIPTION
     "An entry in the gsmBcRlpOperTable."
   INDEX {
      gsmBcTrunkGrpIndex,
      gsmBcCicIndex,
      gsmBcRlpIndex }
::= { gsmBcRlpOperTable 1 }

GsmBcRlpOperEntry ::= SEQUENCE {
   gsmBcRlpProtocolState
      INTEGER,
   gsmBcRlpFrameSize
      Unsigned32,
   gsmBcRlpHighestVersion
      Unsigned32,
   gsmBcRlpIwfToMsWindowSize
      Unsigned32,
   gsmBcRlpMsToIwfWindowSize
      Unsigned32,
   gsmBcRlpT1AckTimer
      Unsigned32,
   gsmBcRlpT2AckDelayTimer
      Unsigned32,
   gsmBcRlpN2RetransmitCount
      Unsigned32 }

gsmBcRlpProtocolState OBJECT-TYPE
   SYNTAX     INTEGER  {
                 detached(0),
                 disconnected(1),
                 connPending(2),
                 discPending(3),
                 connectEstablished(4),
                 synchronized(5) }
   ACCESS     read-only
   STATUS     mandatory
   DESCRIPTION
     "This attribute indicates the last Radio Link Protocol (RLP) state 
      before call take down. The following are the states:
      detached, Initial State. The call has not even started. 
      disconnected, Asynchronous Disconnected Mode (ADM). 
      connPending, In ADM, but sent Set Asynchronous Balanced Mode 
      (SABM) and waiting for a response.
      discPending, Sent Disconnect (DISC), waiting for a response.
      connectEstablished, In Asynchronous Balanced Mode (ABM), 
      Information frames can be exchanged.
      synchronized, Synchronization state entered after a change of 
      channel coding. Handles REMAP procedure."
   DEFVAL     { detached }
::= { gsmBcRlpOperEntry 1 }

gsmBcRlpFrameSize OBJECT-TYPE
   SYNTAX     Unsigned32 (0..65000)
   ACCESS     read-only
   STATUS     mandatory
   DESCRIPTION
     "This attribute indicates the current Radio Link Protocol (RLP) 
      frame size transmitted. The size of the frame depends on the radio 
      channel type. The frames can be 240 bits long for 12 kbit/s and 6 
      kbit/s or 576 bits long for 14.5 kbit/s."
::= { gsmBcRlpOperEntry 2 }

gsmBcRlpHighestVersion OBJECT-TYPE
   SYNTAX     Unsigned32 (0..1)
   ACCESS     read-only
   STATUS     mandatory
   DESCRIPTION
     "This attribute indicates the current highest version of the Radio Link 
      Protocol (RLP) protocol negotiated by the Radio Link Protocol 
      (RLP), during Exchange Information (XID). Valid values are:
      0, Single-link basic version.
      1, Single-link extended version (for example, extended by data 
      compression).
      The value used for XID negotiations can be provisioned by 
      component GsmIwfRadioLinkProtocol attribute highestVersion."
::= { gsmBcRlpOperEntry 3 }

gsmBcRlpIwfToMsWindowSize OBJECT-TYPE
   SYNTAX     Unsigned32 (0..61)
   ACCESS     read-only
   STATUS     mandatory
   DESCRIPTION
     "This attribute indicates the current IWF to mobile window size 
      negotiated by the Radio Link Protocol (RLP) during Exchange 
      Information (XID). The window size is the maximum number of 
      sequentially numbered Information (I) frames that may be 
      unacknowledged at any given time. GSM specification 4.22 defines 
      the range as 0 to 61. The value used for XID negotiations can be 
      provisioned by component GsmIwfRadioLinkProtocol attribute 
      iwftoMsWindowSize."
::= { gsmBcRlpOperEntry 4 }

gsmBcRlpMsToIwfWindowSize OBJECT-TYPE
   SYNTAX     Unsigned32 (0..61)
   ACCESS     read-only
   STATUS     mandatory
   DESCRIPTION
     "This attribute indicates the current mobile to IWF window size 
      negotiated by the Radio Link Protocol (RLP), during Exchange 
      Information (XID). The window size is the maximum number of 
      sequentially numbered Information (I) frames that may be 
      unacknowledged at any given time. GSM specification 4.22 defines 
      the range as 0 to 61. The value used for XID negotiations can be 
      provisioned by component GsmIwfRadioLinkProtocol attribute 
      msToIwfWindowSize."
::= { gsmBcRlpOperEntry 5 }

gsmBcRlpT1AckTimer OBJECT-TYPE
   SYNTAX     Unsigned32 (380..1020)
   ACCESS     read-only
   STATUS     mandatory
   DESCRIPTION
     "This attribute indicates the current T1 timer negotiated by the Radio 
      Link Protocol (RLP), during Exchange Information (XID). This is 
      the period in milliseconds within which an acknowledgment of a 
      sent frame must be received. Once this timer expires, the 
      transmitting RLP entity shall assume that the frame was lost. The 
      value used for XID negotiations can be provisioned by component 
      GsmIwfRadioLinkProtocol attribute t1AckTimer."
::= { gsmBcRlpOperEntry 6 }

gsmBcRlpT2AckDelayTimer OBJECT-TYPE
   SYNTAX     Unsigned32 (10..70)
   ACCESS     read-only
   STATUS     mandatory
   DESCRIPTION
     "This attribute indicates the current T2 timer negotiated by the Radio 
      Link Protocol (RLP), during Exchange Information (XID). This is 
      the maximum period in milliseconds the receiving RLP entity shall 
      wait before sending an acknowledgment for a received in sequenced 
      frame. The value used for XID negotiations can be provisioned by 
      component GsmIwfRadioLinkProtocol attribute t2AckDelayTimer."
::= { gsmBcRlpOperEntry 7 }

gsmBcRlpN2RetransmitCount OBJECT-TYPE
   SYNTAX     Unsigned32 (0..255)
   ACCESS     read-write
   STATUS     mandatory
   DESCRIPTION
     "This attribute indicates the current value of N2 negotiated by the 
      Radio Link Protocol (RLP), during Exchange Information (XID). 
      This is the maximum number of times a RLP entity shall retransmit 
      an individual frame following the expiry of timer T1. The value 
      used for XID negotiations can be provisioned by component 
      GsmIwfRadioLinkProtocol attribute n2RetransmitCount."
::= { gsmBcRlpOperEntry 8 }

gsmBcRlpStatsTable OBJECT-TYPE
   SYNTAX     SEQUENCE OF GsmBcRlpStatsEntry
   ACCESS     not-accessible
   STATUS     mandatory
   DESCRIPTION
     "This group contains operational attributes that measure performance 
      of the GsmIwfBearerChannel."
::= { gsmBcRlp 11 }

gsmBcRlpStatsEntry OBJECT-TYPE
   SYNTAX     GsmBcRlpStatsEntry
   ACCESS     not-accessible
   STATUS     mandatory
   DESCRIPTION
     "An entry in the gsmBcRlpStatsTable."
   INDEX {
      gsmBcTrunkGrpIndex,
      gsmBcCicIndex,
      gsmBcRlpIndex }
::= { gsmBcRlpStatsTable 1 }

GsmBcRlpStatsEntry ::= SEQUENCE {
   gsmBcRlpIFramesTx
      Counter32,
   gsmBcRlpIFramesRx
      Counter32,
   gsmBcRlpFramesRetransmitted
      Counter32,
   gsmBcRlpT1AckTimeouts
      Counter32,
   gsmBcRlpInvalidFrames
      Counter32,
   gsmBcRlpCrcErrorsRx
      Counter32,
   gsmBcRlpOutOfSequenceFrames
      Counter32,
   gsmBcRlpRemoteBusyIndications
      Counter32,
   gsmBcRlpLocalBusyIndications
      Counter32,
   gsmBcRlpIFramesTxDiscarded
      Counter32,
   gsmBcRlpResetsRx
      Counter32 }

gsmBcRlpIFramesTx OBJECT-TYPE
   SYNTAX     Counter32 
   ACCESS     read-only
   STATUS     mandatory
   DESCRIPTION
     "This attribute counts the number of valid Information frames 
      transmitted. This count does not include the Information frames 
      discarded. The counter wraps when it exceeds the maximum value."
::= { gsmBcRlpStatsEntry 1 }

gsmBcRlpIFramesRx OBJECT-TYPE
   SYNTAX     Counter32 
   ACCESS     read-only
   STATUS     mandatory
   DESCRIPTION
     "This attributes counts the number of valid Information (I) frames 
      received. The counter wraps when it exceeds the maximum value."
::= { gsmBcRlpStatsEntry 2 }

gsmBcRlpFramesRetransmitted OBJECT-TYPE
   SYNTAX     Counter32 
   ACCESS     read-only
   STATUS     mandatory
   DESCRIPTION
     "This attribute counts the total number of frames retransmitted. 
      Frames that are not acknowledged within the T1 timer are 
      retransmitted. The counter wraps when it exceeds the maximum 
      value."
::= { gsmBcRlpStatsEntry 3 }

gsmBcRlpT1AckTimeouts OBJECT-TYPE
   SYNTAX     Counter32 
   ACCESS     read-only
   STATUS     mandatory
   DESCRIPTION
     "This attribute counts the total number of T1 timer time-outs. 
      Retransmission of all unacknowledged frames is started after T1 
      timer expiry. The counter wraps when it exceeds the maximum 
      value."
::= { gsmBcRlpStatsEntry 4 }

gsmBcRlpInvalidFrames OBJECT-TYPE
   SYNTAX     Counter32 
   ACCESS     read-only
   STATUS     mandatory
   DESCRIPTION
     "This attribute counts the number of invalid frames received. These 
      invalid frames are frames received from the mobile which contain 
      errors in the header information. This count does not include the 
      number of frames with Cyclic Redundancy Check (CRC) errors or 
      out-of-sequence Frame Errors. The counter wraps when it exceeds 
      the maximum value."
::= { gsmBcRlpStatsEntry 5 }

gsmBcRlpCrcErrorsRx OBJECT-TYPE
   SYNTAX     Counter32 
   ACCESS     read-only
   STATUS     mandatory
   DESCRIPTION
     "This attribute counts the number of frames with Cyclic Redundancy 
      Check (CRC) errors received by the IWF Radio Link Protocol 
      (RLP) entity. CRC is a type of block check character that is very 
      effective in detecting communications errors. CRCs are commonly 
      16 or 32 bits long (though, in GSM non-transparent services, a 24-
      bit CRC is used). The counter wraps when it exceeds the maximum 
      value."
::= { gsmBcRlpStatsEntry 6 }

gsmBcRlpOutOfSequenceFrames OBJECT-TYPE
   SYNTAX     Counter32 
   ACCESS     read-only
   STATUS     mandatory
   DESCRIPTION
     "This attribute counts the number of out-of-sequence Information 
      frames received by the IWF Radio Link Protocol (RLP) entity. The 
      counter wraps when it exceeds the maximum value."
::= { gsmBcRlpStatsEntry 7 }

gsmBcRlpRemoteBusyIndications OBJECT-TYPE
   SYNTAX     Counter32 
   ACCESS     read-only
   STATUS     mandatory
   DESCRIPTION
     "This attribute counts the number of times the mobile Radio Link 
      Protocol (RLP) entity is busy (that is, it is in Asynchronous 
      Balanced Mode (ABM) and is not ready to receive Information 
      frames). The RLP entity is considered to be not ready to receive 
      information frames if the mobile sends a flow control indication 
      RNR (Receive Not Ready). A Receive Ready is sent to the RLP 
      entity when the mobile is ready to receive data. The counter wraps 
      when it exceeds the maximum value."
::= { gsmBcRlpStatsEntry 8 }

gsmBcRlpLocalBusyIndications OBJECT-TYPE
   SYNTAX     Counter32 
   ACCESS     read-only
   STATUS     mandatory
   DESCRIPTION
     "This attribute counts the number of times the IWF RLP entity is 
      busy (that is it is in Asynchronous Balanced Mode (ABM) and is 
      not ready to receive Information frames). When the network side 
      introduces flow control towards the mobile and a Receive Not 
      Ready (RNR) is sent to the mobile to stop the mobile from sending 
      any more data frames. A Receive Ready (RR) is sent to the mobile 
      when the RLP entity is ready to receive data. The counter wraps 
      when it exceeds the maximum value."
::= { gsmBcRlpStatsEntry 9 }

gsmBcRlpIFramesTxDiscarded OBJECT-TYPE
   SYNTAX     Counter32 
   ACCESS     read-only
   STATUS     mandatory
   DESCRIPTION
     "This attribute counts the number of frames discarded by the IWF. 
      Untransmitted and unacknowledged frames are discarded when a 
      Set Asynchronous Balanced Mode (SABM) or Disconnect (DISC) 
      is received or sent in Asynchronous Balanced Mode (ABM) mode. 
      The counter wraps when it exceeds the maximum value."
::= { gsmBcRlpStatsEntry 10 }

gsmBcRlpResetsRx OBJECT-TYPE
   SYNTAX     Counter32 
   ACCESS     read-only
   STATUS     mandatory
   DESCRIPTION
     "This attribute counts the number of resets sent by the mobile. Loss 
      of information may occur when a reset is issued. A reset is issued 
      by the mobile on failure of checkpoint recovery. That is if the 
      mobile does not receive acknowledgment for its information frame, 
      it does checkpoint recovery (it sends a supervisory frame requesting 
      the status of the other entity. If the responding entity fails to respond 
      to N2 of this checkpoint frame a reset is initiated by the originating 
      entity. A reset can also be issued by the mobile during handover 
      where a loss of connection or synchronization occurs. The counter 
      wraps when it exceeds the maximum value."
::= { gsmBcRlpStatsEntry 11 }


-- GsmBc/<trunkGrp>,<cic> V42
-- This component represents the group of measurements for the ITU-
-- T V.42 error correcting protocol established for a GSM IWF call 
-- (on the IWF to Public Switched Telephone Network (PSTN) 
-- modem link) on this particular GsmIwfBearerChannel. 
-- Note that this component is present only if the current (or most 
-- recent call) involved this protocol.

gsmBcV42 OBJECT IDENTIFIER ::= { gsmBc 8 }



gsmBcV42RowStatusTable OBJECT-TYPE
   SYNTAX     SEQUENCE OF GsmBcV42RowStatusEntry
   ACCESS     not-accessible
   STATUS     mandatory
   DESCRIPTION
     "This entry controls the addition and deletion of 
      gsmBcV42 components."
::= { gsmBcV42 1 }

gsmBcV42RowStatusEntry OBJECT-TYPE
   SYNTAX     GsmBcV42RowStatusEntry
   ACCESS     not-accessible
   STATUS     mandatory
   DESCRIPTION
     "A single entry in the table represents a single 
      gsmBcV42 component."
   INDEX {
      gsmBcTrunkGrpIndex,
      gsmBcCicIndex,
      gsmBcV42Index }
::= { gsmBcV42RowStatusTable 1 }

GsmBcV42RowStatusEntry ::= SEQUENCE {
   gsmBcV42RowStatus
      RowStatus,
   gsmBcV42ComponentName
      DisplayString,
   gsmBcV42StorageType
      StorageType,
   gsmBcV42Index
      NonReplicated }

gsmBcV42RowStatus OBJECT-TYPE
   SYNTAX     RowStatus 
   ACCESS     read-only
   STATUS     mandatory
   DESCRIPTION
     "This variable is used as the basis for SNMP naming of
      gsmBcV42 components.
      These components cannot be added nor deleted."
::= { gsmBcV42RowStatusEntry 1 }

gsmBcV42ComponentName OBJECT-TYPE
   SYNTAX     DisplayString 
   ACCESS     read-only
   STATUS     mandatory
   DESCRIPTION
     "This variable provides the component's string name for
      use with the ASCII Console Interface"
::= { gsmBcV42RowStatusEntry 2 }

gsmBcV42StorageType OBJECT-TYPE
   SYNTAX     StorageType 
   ACCESS     read-only
   STATUS     mandatory
   DESCRIPTION
     "This variable represents the storage type value for the
      gsmBcV42 tables."
::= { gsmBcV42RowStatusEntry 4 }

gsmBcV42Index OBJECT-TYPE
   SYNTAX     NonReplicated 
   ACCESS     not-accessible
   STATUS     mandatory
   DESCRIPTION
     "This variable represents the index for the gsmBcV42 tables."
::= { gsmBcV42RowStatusEntry 10 }

gsmBcV42OperTable OBJECT-TYPE
   SYNTAX     SEQUENCE OF GsmBcV42OperEntry
   ACCESS     not-accessible
   STATUS     mandatory
   DESCRIPTION
     "This group contains operational attributes which measure V.42 error 
      detection and correction performance."
::= { gsmBcV42 10 }

gsmBcV42OperEntry OBJECT-TYPE
   SYNTAX     GsmBcV42OperEntry
   ACCESS     not-accessible
   STATUS     mandatory
   DESCRIPTION
     "An entry in the gsmBcV42OperTable."
   INDEX {
      gsmBcTrunkGrpIndex,
      gsmBcCicIndex,
      gsmBcV42Index }
::= { gsmBcV42OperTable 1 }

GsmBcV42OperEntry ::= SEQUENCE {
   gsmBcV42ProtocolState
      INTEGER,
   gsmBcV42TxN401FrameSize
      Unsigned32,
   gsmBcV42RxN401FrameSize
      Unsigned32,
   gsmBcV42TxKwindowSize
      Unsigned32,
   gsmBcV42RxKwindowSize
      Unsigned32 }

gsmBcV42ProtocolState OBJECT-TYPE
   SYNTAX     INTEGER  {
                 notActive(0),
                 disconnected(1),
                 linksetup(2),
                 frameReject(3),
                 disconnectRequest(4),
                 informationTransfer(5),
                 waitingAck(6) }
   ACCESS     read-only
   STATUS     mandatory
   DESCRIPTION
     "This attribute indicates the state of V.42. Valid states are:
      
      notActive, The V.42 link connection with the Public Switched 
      Telephoned Network) PSTN modem is not established. None of the 
      V.42 functions including the error detection, error correction, and 
      flow control is provided to the data call. This is the initial state of 
      V.42.
      disconnected, This means that the V42 link is disconnected.
      linksetup, The V.42 operation enters this state from the 
      disconnected state after the V.42 sends to the PSTN modem a Set 
      Asynchronous Balanced Mode Extended (SABME) frame in an 
      attempt to establish the error control connection with the PSTN 
      modem.
      frameReject, The V.42 operation enters into this state after it 
      identifies an invalid frame sent by the peer and it sends back a frame 
      reject (FRMR) frame to the peer.
      disconnectRequest, The V.42 operation enters into this state after it 
      sends to the peer a disconnect (DISC) frame with the attempt to 
      disconnect the V.42 error control link.
      informationTransfer, The V.42 enters into this state after it receives 
      a UA (unnumbered acknowledgment) frame which the peer sent 
      upon receipt of the SAMBE frame from IWF V.42. Once in this 
      state, the V.42 can exchange data and supervisory information with 
      its peer.
      waitingAck, The V.42 enters this state after it sends polling enquiry 
      to its peer. The V.42 sends the polling enquiry when it receives a 
      reject frame (REJ) from its peer or either its acknowledgment timer 
      or inactivity timer timed out on the information frames sent out."
   DEFVAL     { notActive }
::= { gsmBcV42OperEntry 1 }

gsmBcV42TxN401FrameSize OBJECT-TYPE
   SYNTAX     Unsigned32 (0..65355)
   ACCESS     read-only
   STATUS     mandatory
   DESCRIPTION
     "This attribute indicates the current value of parameter N401 for 
      V.42 which is negotiated during Exchange Information (XID). This 
      is the maximum number of octets that can be carried in the 
      information field of an information frame that the IWF V.42 
      transmits to the Public Switched Telephone Network (PSTN) 
      modem. The IWF V.42 puts this or even smaller size of data into the 
      outgoing information frame. The value used for XID negotiations 
      can be provisioned by component GsmIwfV42 attribute 
      txN401FrameSize."
::= { gsmBcV42OperEntry 2 }

gsmBcV42RxN401FrameSize OBJECT-TYPE
   SYNTAX     Unsigned32 (1..255)
   ACCESS     read-only
   STATUS     mandatory
   DESCRIPTION
     "This attribute indicates the current value of N401, that is negotiated 
      during Exchange Identification (XID). This is the maximum number 
      of octets that can be carried in the information field of an 
      information frame received from the Public Switched Telephone 
      Network (PSTN) modem. An incoming information frame carrying 
      data octets more than this size shall be rejected by the IWF V.42. 
      The value used for XID negotiations can be provisioned by 
      component GsmIwfV42 attribute rxN401FrameSize."
::= { gsmBcV42OperEntry 3 }

gsmBcV42TxKwindowSize OBJECT-TYPE
   SYNTAX     Unsigned32 (0..127)
   ACCESS     read-only
   STATUS     mandatory
   DESCRIPTION
     "This attribute indicates the current value of k, that is negotiated 
      during Exchange Identification (XID). This is the size of flow 
      control sliding window used for the information frames that the 
      V.42 transmits to the Public Switched Telephone Network (PSTN) 
      modem. This size governs the maximum number of information 
      frames that the IWF V.42 error-correcting entity can have 
      outstanding (that is, unacknowledged). The value used for XID 
      negotiations can be provisioned by component GsmIwfV42 attribute 
      txKwindowSize."
::= { gsmBcV42OperEntry 4 }

gsmBcV42RxKwindowSize OBJECT-TYPE
   SYNTAX     Unsigned32 (1..127)
   ACCESS     read-only
   STATUS     mandatory
   DESCRIPTION
     "This attribute indicates the current value of k that is negotiated 
      during Exchange Identification (XID). This is the size of flow 
      control sliding window used for information frames transmitted 
      from the Public Switched Telephone Network (PSTN) modem. This 
      size governs the maximum number of information frames that the 
      peer of the IWF V.42 error-correcting entity can have outstanding 
      (that is, unacknowledged). The value used for XID negotiations can 
      be provisioned by component GsmIwfV42 attribute rxKwindowSize."
::= { gsmBcV42OperEntry 5 }

gsmBcV42StatsTable OBJECT-TYPE
   SYNTAX     SEQUENCE OF GsmBcV42StatsEntry
   ACCESS     not-accessible
   STATUS     mandatory
   DESCRIPTION
     "This group contains statistical attributes that measure the V.42 error 
      detection and correction performance."
::= { gsmBcV42 11 }

gsmBcV42StatsEntry OBJECT-TYPE
   SYNTAX     GsmBcV42StatsEntry
   ACCESS     not-accessible
   STATUS     mandatory
   DESCRIPTION
     "An entry in the gsmBcV42StatsTable."
   INDEX {
      gsmBcTrunkGrpIndex,
      gsmBcCicIndex,
      gsmBcV42Index }
::= { gsmBcV42StatsTable 1 }

GsmBcV42StatsEntry ::= SEQUENCE {
   gsmBcV42IBytesRx
      Counter32,
   gsmBcV42IBytesTx
      Counter32,
   gsmBcV42IFramesRx
      Counter32,
   gsmBcV42IFramesTx
      Counter32,
   gsmBcV42FramesRetransmitted
      Counter32,
   gsmBcV42T1AckTimeouts
      Counter32,
   gsmBcV42RemoteBusyIndications
      Counter32,
   gsmBcV42LocalBusyIndications
      Counter32,
   gsmBcV42BadFramesRx
      Counter32,
   gsmBcV42CrcErrorsRx
      Counter32 }

gsmBcV42IBytesRx OBJECT-TYPE
   SYNTAX     Counter32 
   ACCESS     read-only
   STATUS     mandatory
   DESCRIPTION
     "This attribute counts the total number of bytes that the V.42 actually 
      received from the Public Switched Telephone Network (PSTN) 
      modem in a data call. The counter wraps when it exceeds the 
      maximum value."
::= { gsmBcV42StatsEntry 1 }

gsmBcV42IBytesTx OBJECT-TYPE
   SYNTAX     Counter32 
   ACCESS     read-only
   STATUS     mandatory
   DESCRIPTION
     "This attribute counts the total number of bytes that the V.42 
      transmitted to the Public Switched Telephone Network (PSTN) 
      modem in a data call. The counter wraps when it exceeds the 
      maximum value."
::= { gsmBcV42StatsEntry 2 }

gsmBcV42IFramesRx OBJECT-TYPE
   SYNTAX     Counter32 
   ACCESS     read-only
   STATUS     mandatory
   DESCRIPTION
     "This attribute counts the total number of Information (I) frames that 
      the V.42 received from the Public Switched Telephone Network 
      (PSTN) modem in a data call. The counter wraps when it exceeds 
      the maximum value."
::= { gsmBcV42StatsEntry 3 }

gsmBcV42IFramesTx OBJECT-TYPE
   SYNTAX     Counter32 
   ACCESS     read-only
   STATUS     mandatory
   DESCRIPTION
     "This attribute counts the total number of information frames that the 
      V.42 transmitted to the Public Switched Telephone Network 
      (PSTN) modem in a data call. The counter wraps when it exceeds 
      the maximum value."
::= { gsmBcV42StatsEntry 4 }

gsmBcV42FramesRetransmitted OBJECT-TYPE
   SYNTAX     Counter32 
   ACCESS     read-only
   STATUS     mandatory
   DESCRIPTION
     "This attribute counts the total number of frames retransmitted by the 
      IWF V.42 entity in a data call. The V.42 retransmits the same frame 
      when the associated T401 acknowledgment timer time-outs or when 
      a Reject (REJ) supervisory frame has been received from the Public 
      Switched Telephone Network (PSTN) modem. The counter wraps 
      when it exceeds the maximum value."
::= { gsmBcV42StatsEntry 5 }

gsmBcV42T1AckTimeouts OBJECT-TYPE
   SYNTAX     Counter32 
   ACCESS     read-only
   STATUS     mandatory
   DESCRIPTION
     "This attribute counts the total number of times that the T401 timer 
      has timed out within a data call. If this timer times-out frequently, 
      the operator may need to adjust the provisional parameter T401 
      acknowledgment timer to a larger time amount, since every time 
      that V.42 sends out a frame it sets the T401 timer to wait for the 
      peer's acknowledgment of the frame. When the timer times-out and 
      no acknowledgment has been received, the V.42 sends the same 
      frame to its peer. The counter wraps when it exceeds the maximum 
      value."
::= { gsmBcV42StatsEntry 6 }

gsmBcV42RemoteBusyIndications OBJECT-TYPE
   SYNTAX     Counter32 
   ACCESS     read-only
   STATUS     mandatory
   DESCRIPTION
     "This attribute counts the total number of times the Public Switched 
      Telephone Network (PSTN) modem enters a busy state (the IWF 
      has received a Receive Not Ready message) and asks the IWF V.42 
      not to send Information (I) frames to it until it is ready to receive 
      information frames again (indicated by receipt of a Receive Ready 
      message or a data message). The counter wraps when it exceeds the 
      maximum value."
::= { gsmBcV42StatsEntry 7 }

gsmBcV42LocalBusyIndications OBJECT-TYPE
   SYNTAX     Counter32 
   ACCESS     read-only
   STATUS     mandatory
   DESCRIPTION
     "This attribute counts the total number of times the IWF V.42 enters 
      in a busy condition and asks the peer to stop sending information 
      frames until it has cleared up from the busy condition. The V.42 
      enters busy condition when its data buffer is about to be overflowed 
      by the incoming Information (I) frames. The counter wraps when it 
      exceeds the maximum value."
::= { gsmBcV42StatsEntry 8 }

gsmBcV42BadFramesRx OBJECT-TYPE
   SYNTAX     Counter32 
   ACCESS     read-only
   STATUS     mandatory
   DESCRIPTION
     "This attribute counts the total number of bad frames the IWF V.42 
      has received from the Public Switched Telephone Network (PSTN) 
      remote modem within the data call. In this instance, 'bad frames' 
      refer to the V.42 protocol error frames other than the check 
      sequence error frames. The counter wraps when it exceeds the 
      maximum value."
::= { gsmBcV42StatsEntry 9 }

gsmBcV42CrcErrorsRx OBJECT-TYPE
   SYNTAX     Counter32 
   ACCESS     read-only
   STATUS     mandatory
   DESCRIPTION
     "This attribute counts the total number of frames received from the 
      remote Public Switched Telephone Network (PSTN) modem that 
      contain incorrect frame check sequence. A high value signifies the 
      condition of the physical medium is poor. The counter wraps when 
      it exceeds the maximum value."
::= { gsmBcV42StatsEntry 10 }


-- GsmBc<trunkGrp>,<cic> V42bis
-- This component represents the group of measurements for the ITU-
-- T V.42bis data compression protocol established for a GSM IWF 
-- call (on the mobile station to the IWF link or the IWF to Public 
-- Switched Telephone Network (PSTN) fax modem link) on this 
-- particular GsmIwfBearerChannel.
-- Note that this component is present only if the current (or most 
-- recent call) involved this protocol. 

gsmBcV42bis OBJECT IDENTIFIER ::= { gsmBc 9 }



gsmBcV42bisRowStatusTable OBJECT-TYPE
   SYNTAX     SEQUENCE OF GsmBcV42bisRowStatusEntry
   ACCESS     not-accessible
   STATUS     mandatory
   DESCRIPTION
     "This entry controls the addition and deletion of 
      gsmBcV42bis components."
::= { gsmBcV42bis 1 }

gsmBcV42bisRowStatusEntry OBJECT-TYPE
   SYNTAX     GsmBcV42bisRowStatusEntry
   ACCESS     not-accessible
   STATUS     mandatory
   DESCRIPTION
     "A single entry in the table represents a single 
      gsmBcV42bis component."
   INDEX {
      gsmBcTrunkGrpIndex,
      gsmBcCicIndex,
      gsmBcV42bisIndex }
::= { gsmBcV42bisRowStatusTable 1 }

GsmBcV42bisRowStatusEntry ::= SEQUENCE {
   gsmBcV42bisRowStatus
      RowStatus,
   gsmBcV42bisComponentName
      DisplayString,
   gsmBcV42bisStorageType
      StorageType,
   gsmBcV42bisIndex
      NonReplicated }

gsmBcV42bisRowStatus OBJECT-TYPE
   SYNTAX     RowStatus 
   ACCESS     read-only
   STATUS     mandatory
   DESCRIPTION
     "This variable is used as the basis for SNMP naming of
      gsmBcV42bis components.
      These components cannot be added nor deleted."
::= { gsmBcV42bisRowStatusEntry 1 }

gsmBcV42bisComponentName OBJECT-TYPE
   SYNTAX     DisplayString 
   ACCESS     read-only
   STATUS     mandatory
   DESCRIPTION
     "This variable provides the component's string name for
      use with the ASCII Console Interface"
::= { gsmBcV42bisRowStatusEntry 2 }

gsmBcV42bisStorageType OBJECT-TYPE
   SYNTAX     StorageType 
   ACCESS     read-only
   STATUS     mandatory
   DESCRIPTION
     "This variable represents the storage type value for the
      gsmBcV42bis tables."
::= { gsmBcV42bisRowStatusEntry 4 }

gsmBcV42bisIndex OBJECT-TYPE
   SYNTAX     NonReplicated 
   ACCESS     not-accessible
   STATUS     mandatory
   DESCRIPTION
     "This variable represents the index for the gsmBcV42bis tables."
::= { gsmBcV42bisRowStatusEntry 10 }

gsmBcV42bisOperTable OBJECT-TYPE
   SYNTAX     SEQUENCE OF GsmBcV42bisOperEntry
   ACCESS     not-accessible
   STATUS     mandatory
   DESCRIPTION
     "This group contains operational attributes that measure the 
      performance of V.42bis."
::= { gsmBcV42bis 10 }

gsmBcV42bisOperEntry OBJECT-TYPE
   SYNTAX     GsmBcV42bisOperEntry
   ACCESS     not-accessible
   STATUS     mandatory
   DESCRIPTION
     "An entry in the gsmBcV42bisOperTable."
   INDEX {
      gsmBcTrunkGrpIndex,
      gsmBcCicIndex,
      gsmBcV42bisIndex }
::= { gsmBcV42bisOperTable 1 }

GsmBcV42bisOperEntry ::= SEQUENCE {
   gsmBcV42bisProtocolModeEncoder
      INTEGER,
   gsmBcV42bisProtocolModeDecoder
      INTEGER,
   gsmBcV42bisCompressionDirection
      INTEGER,
   gsmBcV42bisMaximumCodewords
      Unsigned32,
   gsmBcV42bisMaximumStringSize
      Unsigned32,
   gsmBcV42bisLastDecodeError
      INTEGER,
   gsmBcV42bisCompRatioEncoder
      FixedPoint2,
   gsmBcV42bisCompRatioDecoder
      FixedPoint2 }

gsmBcV42bisProtocolModeEncoder OBJECT-TYPE
   SYNTAX     INTEGER  {
                 transparent(0),
                 compressed(1) }
   ACCESS     read-only
   STATUS     mandatory
   DESCRIPTION
     "This attribute indicates the current mode of the V.42bis encoder. 
      This mode can be either:
      transparent - A mode of operation in which compression has been 
      selected but data is being transmitted in uncompressed form. 
      Transparent mode command sequences may be inserted into the 
      data stream. 
      compressed - A mode of operation in which data is transmitted in 
      codewords.
      The encoder switches between the two modes depending on 
      whether the data coming from the Date Terminal Equipment (DTE) 
      is suitable for compression. The data comression function 
      periodically determines the compressibility of the data based on a 
      comparison of the number of bits required to represent a segment of 
      the data stream before and after compression."
::= { gsmBcV42bisOperEntry 1 }

gsmBcV42bisProtocolModeDecoder OBJECT-TYPE
   SYNTAX     INTEGER  {
                 transparent(0),
                 compressed(1) }
   ACCESS     read-only
   STATUS     mandatory
   DESCRIPTION
     "This attribute indicates the current mode of the V.42bis decoder. 
      This mode can be either: 
      transparent - A mode of operation in which compression has been 
      selected but data is being transmitted in uncompressed form. 
      Transparent mode command sequences may be inserted into the 
      data stream.
      compressed - A mode of operation in which data is transmitted in 
      codewords.
      The encoder (at the mobile or Public Switched Telephone Network) 
      switches between the two modes depending on whether the data 
      coming from the Date Terminal Equipment (DTE) is suitable for 
      compression. The data comression function periodically determines 
      the compressibility of the data based on a comparison of the number 
      of bits required to represent a segment of the data stream before and 
      after compression."
::= { gsmBcV42bisOperEntry 2 }

gsmBcV42bisCompressionDirection OBJECT-TYPE
   SYNTAX     INTEGER  {
                 none(0),
                 encode(1),
                 decode(2),
                 both(3) }
   ACCESS     read-only
   STATUS     mandatory
   DESCRIPTION
     "This attribute indicates the direction in which V.42bis is active, 
      negotiated at link setup by the data link protocol through Exchange 
      Identification (XID) negotiation of parameter P0 (compression 
      direction). The value used for XID negotiations can be provisioned 
      by component GsmIwfV42bisProv attribute compressionDirection. 
      Valid values are:
      none, No compression is present.
      encode, The data sent by the IWF to the other entity is compressed.
      decode, The data received by the IWF from the other entity is 
      compressed.
      both, The data sent and received by the IWF is compressed."
::= { gsmBcV42bisOperEntry 3 }

gsmBcV42bisMaximumCodewords OBJECT-TYPE
   SYNTAX     Unsigned32 (0..4096)
   ACCESS     read-only
   STATUS     mandatory
   DESCRIPTION
     "This attribute indicates the maximum number of codewords in the 
      dictionary negotiated at link setup by the data link protocol by way 
      of the Exchange Identification (XID) negotiation of parameter P1 
      (number of codewords). The value used for XID negotiations can be 
      provisioned by component GsmIwfV42bisProv attribute 
      maximumCodewords."
::= { gsmBcV42bisOperEntry 4 }

gsmBcV42bisMaximumStringSize OBJECT-TYPE
   SYNTAX     Unsigned32 (6..250)
   ACCESS     read-only
   STATUS     mandatory
   DESCRIPTION
     "This attribute indicates the maximum number of characters allowed 
      in a string represented by a codeword negotiated at link setup by the 
      data link protocol by way of the Exchange Identification (XID) 
      negotiation of parameter P2 (maximum string size). The value used 
      for XID negotiations can be provisioned by component 
      GsmIwfV42bisProv attribute maximumStringSize."
::= { gsmBcV42bisOperEntry 5 }

gsmBcV42bisLastDecodeError OBJECT-TYPE
   SYNTAX     INTEGER  {
                 none(0),
                 badStepup(1),
                 codewordEqC1(2),
                 emptyCodeword(3),
                 reservedCommand(4),
                 generalError(5) }
   ACCESS     read-only
   STATUS     mandatory
   DESCRIPTION
     "This attribute indicates last error found by the decoder. Error values 
      are:
      none, No errors found.
      badStepup, Receipt of STEPUP (step up codeword size) codeword 
      when it would cause C2 (current code word size) to exceed N1 
      (maximum code word size).
      codewordEqC1, Receipt of a codeword, at any time, equal to C1 
      (next empty dictionary entry).
      emptyCodeword, Receipt of a codeword representing an empty 
      dictionary entry. 
      reservedCommand, Receipt of a reserved command code.
      generalError, Receipt of any other error.
      The action taken by V.42bis on detecting an error is provisioned by 
      component GsmIwfV42bis attribute actionOnError."
   DEFVAL     { none }
::= { gsmBcV42bisOperEntry 6 }

gsmBcV42bisCompRatioEncoder OBJECT-TYPE
   SYNTAX     FixedPoint2 (0..30000)
   ACCESS     read-only
   STATUS     mandatory
   DESCRIPTION
     "This attribute indicates the number of uncompressed bytes divided 
      by the number of compressed bytes. A value greater than one means 
      that the data is being compressed. This is the compression ratio 
      achieved by the V.42bis encoder running on the Passport. This 
      attribute is relevant for both protocol modes transparent and 
      compressed as the encoder switches between the two modes."
::= { gsmBcV42bisOperEntry 7 }

gsmBcV42bisCompRatioDecoder OBJECT-TYPE
   SYNTAX     FixedPoint2 (0..30000)
   ACCESS     read-only
   STATUS     mandatory
   DESCRIPTION
     "This attribute indicates the number of uncompressed bytes divided 
      by the number of compressed bytes. A value greater than one means 
      that the data is being compressed. This is the compression ratio 
      achieved by the V.42bis encoder at the mobile or Public Switched 
      Telephone Network (PSTN). This attribute is relevant for both 
      protocol modes transparent and compressed as the encoder switches 
      between the two modes."
::= { gsmBcV42bisOperEntry 8 }

gsmBcV42bisStatsTable OBJECT-TYPE
   SYNTAX     SEQUENCE OF GsmBcV42bisStatsEntry
   ACCESS     not-accessible
   STATUS     mandatory
   DESCRIPTION
     "This group contains operational attributes that measure the 
      performance of V.42bis."
::= { gsmBcV42bis 11 }

gsmBcV42bisStatsEntry OBJECT-TYPE
   SYNTAX     GsmBcV42bisStatsEntry
   ACCESS     not-accessible
   STATUS     mandatory
   DESCRIPTION
     "An entry in the gsmBcV42bisStatsTable."
   INDEX {
      gsmBcTrunkGrpIndex,
      gsmBcCicIndex,
      gsmBcV42bisIndex }
::= { gsmBcV42bisStatsTable 1 }

GsmBcV42bisStatsEntry ::= SEQUENCE {
   gsmBcV42bisModeChangesEncode
      Counter32,
   gsmBcV42bisModeChangesDecode
      Counter32,
   gsmBcV42bisResetsEncode
      Counter32,
   gsmBcV42bisResetsDecode
      Counter32,
   gsmBcV42bisReInitializations
      Counter32,
   gsmBcV42bisErrorsInDecode
      Counter32 }

gsmBcV42bisModeChangesEncode OBJECT-TYPE
   SYNTAX     Counter32 
   ACCESS     read-only
   STATUS     mandatory
   DESCRIPTION
     "This attribute counts the number of mode changes (from transparent 
      to compressed or from compressed to transparent) by the encoder. 
      The counter wraps when it exceeds the maximum value."
::= { gsmBcV42bisStatsEntry 1 }

gsmBcV42bisModeChangesDecode OBJECT-TYPE
   SYNTAX     Counter32 
   ACCESS     read-only
   STATUS     mandatory
   DESCRIPTION
     "This attribute counts the number of mode changes (from transparent 
      to compressed or from compressed to transparent) by the decoder. 
      The mode changes are determined by the encoder at the mobile or 
      the Public Switched Telephone Network (PSTN). The counter 
      wraps when it exceeds the maximum value."
::= { gsmBcV42bisStatsEntry 2 }

gsmBcV42bisResetsEncode OBJECT-TYPE
   SYNTAX     Counter32 
   ACCESS     read-only
   STATUS     mandatory
   DESCRIPTION
     "This attribute counts the number of resets sent by the encoder. A 
      reset is a command code sent by the encoder to force dictionary 
      reinitialization. The counter wraps when it exceeds the maximum 
      value."
::= { gsmBcV42bisStatsEntry 3 }

gsmBcV42bisResetsDecode OBJECT-TYPE
   SYNTAX     Counter32 
   ACCESS     read-only
   STATUS     mandatory
   DESCRIPTION
     "This attribute counts the number of resets received by the decoder. 
      A reset is a command code sent by the encoder to force dictionary 
      reinitialization. The resets of the decoder are determined by the 
      encoder at the mobile or Public Switched Telephone Network 
      (PSTN). The counter wraps when it exceeds the maximum value."
::= { gsmBcV42bisStatsEntry 4 }

gsmBcV42bisReInitializations OBJECT-TYPE
   SYNTAX     Counter32 
   ACCESS     read-only
   STATUS     mandatory
   DESCRIPTION
     "This attribute counts the number of times V.42bis is reinitialized 
      because of a destructive break (a destructive break is a break that 
      causes data to be discarded) occurring on the error-corrected 
      connection initiatated by either the mobile or Public Switched 
      Telephone Network (PSTN). The counter wraps when it exceeds the 
      maximum value."
::= { gsmBcV42bisStatsEntry 5 }

gsmBcV42bisErrorsInDecode OBJECT-TYPE
   SYNTAX     Counter32 
   ACCESS     read-only
   STATUS     mandatory
   DESCRIPTION
     "This attribute counts the number of errors found by the decoder. 
      The errors could be any of the following:
      1.Receipt of STEPUP (step up codeword size) codeword when it 
      would cause C2 (current code word size) to exceed N1 (maximum 
      code word size).
      2. Receipt of a codeword, at any time, equal to C1 (next empty 
      dictionary entry).
      3. Receipt of a codeword representing an empty dictionary entry.
      4. Receipt of a reserved command code.
      5. Receipt of any other error.
      The counter wraps when it exceeds the maximum value.
      The action taken by V.42bis on detecting any of these errors is 
      provisioned by component GsmIwfV42bis attribute actionOnError."
::= { gsmBcV42bisStatsEntry 6 }


-- GsmBc/<trunkGrp>,<cic> Layer2RelayCop
-- This component represents the group of measurements for the GSM 
-- Layer 2 Relay Character Oriented Protocol (L2RCOP) established 
-- for a GSM IWF call (on the mobile station to the IWF link) on this 
-- particular GsmIwfBearerChannel. 
-- Note that this component is present only if the current (or most 
-- recent call) involved this protocol.

gsmBcL2RCop OBJECT IDENTIFIER ::= { gsmBc 10 }



gsmBcL2RCopRowStatusTable OBJECT-TYPE
   SYNTAX     SEQUENCE OF GsmBcL2RCopRowStatusEntry
   ACCESS     not-accessible
   STATUS     mandatory
   DESCRIPTION
     "This entry controls the addition and deletion of 
      gsmBcL2RCop components."
::= { gsmBcL2RCop 1 }

gsmBcL2RCopRowStatusEntry OBJECT-TYPE
   SYNTAX     GsmBcL2RCopRowStatusEntry
   ACCESS     not-accessible
   STATUS     mandatory
   DESCRIPTION
     "A single entry in the table represents a single 
      gsmBcL2RCop component."
   INDEX {
      gsmBcTrunkGrpIndex,
      gsmBcCicIndex,
      gsmBcL2RCopIndex }
::= { gsmBcL2RCopRowStatusTable 1 }

GsmBcL2RCopRowStatusEntry ::= SEQUENCE {
   gsmBcL2RCopRowStatus
      RowStatus,
   gsmBcL2RCopComponentName
      DisplayString,
   gsmBcL2RCopStorageType
      StorageType,
   gsmBcL2RCopIndex
      NonReplicated }

gsmBcL2RCopRowStatus OBJECT-TYPE
   SYNTAX     RowStatus 
   ACCESS     read-only
   STATUS     mandatory
   DESCRIPTION
     "This variable is used as the basis for SNMP naming of
      gsmBcL2RCop components.
      These components cannot be added nor deleted."
::= { gsmBcL2RCopRowStatusEntry 1 }

gsmBcL2RCopComponentName OBJECT-TYPE
   SYNTAX     DisplayString 
   ACCESS     read-only
   STATUS     mandatory
   DESCRIPTION
     "This variable provides the component's string name for
      use with the ASCII Console Interface"
::= { gsmBcL2RCopRowStatusEntry 2 }

gsmBcL2RCopStorageType OBJECT-TYPE
   SYNTAX     StorageType 
   ACCESS     read-only
   STATUS     mandatory
   DESCRIPTION
     "This variable represents the storage type value for the
      gsmBcL2RCop tables."
::= { gsmBcL2RCopRowStatusEntry 4 }

gsmBcL2RCopIndex OBJECT-TYPE
   SYNTAX     NonReplicated 
   ACCESS     not-accessible
   STATUS     mandatory
   DESCRIPTION
     "This variable represents the index for the gsmBcL2RCop tables."
::= { gsmBcL2RCopRowStatusEntry 10 }

gsmBcL2RCopOperTable OBJECT-TYPE
   SYNTAX     SEQUENCE OF GsmBcL2RCopOperEntry
   ACCESS     not-accessible
   STATUS     mandatory
   DESCRIPTION
     "This group contains operational attributes that measure the 
      performance of L2RCop."
::= { gsmBcL2RCop 10 }

gsmBcL2RCopOperEntry OBJECT-TYPE
   SYNTAX     GsmBcL2RCopOperEntry
   ACCESS     not-accessible
   STATUS     mandatory
   DESCRIPTION
     "An entry in the gsmBcL2RCopOperTable."
   INDEX {
      gsmBcTrunkGrpIndex,
      gsmBcCicIndex,
      gsmBcL2RCopIndex }
::= { gsmBcL2RCopOperTable 1 }

GsmBcL2RCopOperEntry ::= SEQUENCE {
   gsmBcL2RCopFlowControlStateTx
      INTEGER,
   gsmBcL2RCopFlowControlStateRx
      INTEGER }

gsmBcL2RCopFlowControlStateTx OBJECT-TYPE
   SYNTAX     INTEGER  {
                 active(0),
                 inactive(1) }
   ACCESS     read-only
   STATUS     mandatory
   DESCRIPTION
     "This attribute indicates whether flow control is active in the transmit 
      direction (towards the network side) for Layer2 Relay."
   DEFVAL     { inactive }
::= { gsmBcL2RCopOperEntry 1 }

gsmBcL2RCopFlowControlStateRx OBJECT-TYPE
   SYNTAX     INTEGER  {
                 active(0),
                 inactive(1) }
   ACCESS     read-only
   STATUS     mandatory
   DESCRIPTION
     "This attribute indicates whether flow control is active in the receive 
      direction (towards the mobile) for Layer2 Relay."
   DEFVAL     { inactive }
::= { gsmBcL2RCopOperEntry 2 }

gsmBcL2RCopStatsTable OBJECT-TYPE
   SYNTAX     SEQUENCE OF GsmBcL2RCopStatsEntry
   ACCESS     not-accessible
   STATUS     mandatory
   DESCRIPTION
     "This group contains operational attributes that measure the 
      performance of L2RCop."
::= { gsmBcL2RCop 11 }

gsmBcL2RCopStatsEntry OBJECT-TYPE
   SYNTAX     GsmBcL2RCopStatsEntry
   ACCESS     not-accessible
   STATUS     mandatory
   DESCRIPTION
     "An entry in the gsmBcL2RCopStatsTable."
   INDEX {
      gsmBcTrunkGrpIndex,
      gsmBcCicIndex,
      gsmBcL2RCopIndex }
::= { gsmBcL2RCopStatsTable 1 }

GsmBcL2RCopStatsEntry ::= SEQUENCE {
   gsmBcL2RCopBytesTx
      Counter32,
   gsmBcL2RCopBytesRx
      Counter32,
   gsmBcL2RCopBreakCountRx
      Counter32,
   gsmBcL2RCopBreakCountTx
      Counter32 }

gsmBcL2RCopBytesTx OBJECT-TYPE
   SYNTAX     Counter32 
   ACCESS     read-only
   STATUS     mandatory
   DESCRIPTION
     "This attribute counts the number of data bytes relayed by Layer2 
      Relay in the transmit direction (towards the network). The counter 
      wraps when it exceeds the maximum value."
::= { gsmBcL2RCopStatsEntry 1 }

gsmBcL2RCopBytesRx OBJECT-TYPE
   SYNTAX     Counter32 
   ACCESS     read-only
   STATUS     mandatory
   DESCRIPTION
     "This attribute counts the number of data bytes relayed by Layer2 
      Relay in the receive direction (towards the mobile). The counter 
      wraps when it exceeds the maximum value."
::= { gsmBcL2RCopStatsEntry 2 }

gsmBcL2RCopBreakCountRx OBJECT-TYPE
   SYNTAX     Counter32 
   ACCESS     read-only
   STATUS     mandatory
   DESCRIPTION
     "This attribute counts the number of breaks received from the 
      mobile. A break received from the mobile results in the V.42bis 
      function being reset and the break condition forwarded to the 
      network. The counter wraps when it exceeds the maximum value."
::= { gsmBcL2RCopStatsEntry 3 }

gsmBcL2RCopBreakCountTx OBJECT-TYPE
   SYNTAX     Counter32 
   ACCESS     read-only
   STATUS     mandatory
   DESCRIPTION
     "This attribute counts the number of breaks transmitted to the mobile 
      (a break was received from the network). A break received from the 
      network results in the V.42bis function being reset and the break 
      condition forwarded to the mobile. The counter wraps when it 
      exceeds the maximum value."
::= { gsmBcL2RCopStatsEntry 4 }


-- GsmBc/<trunkGrp>,<cic> UpperRelay
-- This component represents the group of measurements for the 
-- Upper Relay function established for a GSM IWF call (internally 
-- between the two GsmIwfBearerChannels involved in a call) from 
-- this particular GsmIwfBearerChannel perspective.
-- Note that this component is present only if the current (or most 
-- recent call) involved this protocol. 

gsmBcUpperRelay OBJECT IDENTIFIER ::= { gsmBc 11 }



gsmBcUpperRelayRowStatusTable OBJECT-TYPE
   SYNTAX     SEQUENCE OF GsmBcUpperRelayRowStatusEntry
   ACCESS     not-accessible
   STATUS     mandatory
   DESCRIPTION
     "This entry controls the addition and deletion of 
      gsmBcUpperRelay components."
::= { gsmBcUpperRelay 1 }

gsmBcUpperRelayRowStatusEntry OBJECT-TYPE
   SYNTAX     GsmBcUpperRelayRowStatusEntry
   ACCESS     not-accessible
   STATUS     mandatory
   DESCRIPTION
     "A single entry in the table represents a single 
      gsmBcUpperRelay component."
   INDEX {
      gsmBcTrunkGrpIndex,
      gsmBcCicIndex,
      gsmBcUpperRelayIndex }
::= { gsmBcUpperRelayRowStatusTable 1 }

GsmBcUpperRelayRowStatusEntry ::= SEQUENCE {
   gsmBcUpperRelayRowStatus
      RowStatus,
   gsmBcUpperRelayComponentName
      DisplayString,
   gsmBcUpperRelayStorageType
      StorageType,
   gsmBcUpperRelayIndex
      NonReplicated }

gsmBcUpperRelayRowStatus OBJECT-TYPE
   SYNTAX     RowStatus 
   ACCESS     read-only
   STATUS     mandatory
   DESCRIPTION
     "This variable is used as the basis for SNMP naming of
      gsmBcUpperRelay components.
      These components cannot be added nor deleted."
::= { gsmBcUpperRelayRowStatusEntry 1 }

gsmBcUpperRelayComponentName OBJECT-TYPE
   SYNTAX     DisplayString 
   ACCESS     read-only
   STATUS     mandatory
   DESCRIPTION
     "This variable provides the component's string name for
      use with the ASCII Console Interface"
::= { gsmBcUpperRelayRowStatusEntry 2 }

gsmBcUpperRelayStorageType OBJECT-TYPE
   SYNTAX     StorageType 
   ACCESS     read-only
   STATUS     mandatory
   DESCRIPTION
     "This variable represents the storage type value for the
      gsmBcUpperRelay tables."
::= { gsmBcUpperRelayRowStatusEntry 4 }

gsmBcUpperRelayIndex OBJECT-TYPE
   SYNTAX     NonReplicated 
   ACCESS     not-accessible
   STATUS     mandatory
   DESCRIPTION
     "This variable represents the index for the gsmBcUpperRelay tables."
::= { gsmBcUpperRelayRowStatusEntry 10 }

gsmBcUpperRelayOperTable OBJECT-TYPE
   SYNTAX     SEQUENCE OF GsmBcUpperRelayOperEntry
   ACCESS     not-accessible
   STATUS     mandatory
   DESCRIPTION
     "This group contains operational attributes that measure the 
      performance of the UpperRelay."
::= { gsmBcUpperRelay 10 }

gsmBcUpperRelayOperEntry OBJECT-TYPE
   SYNTAX     GsmBcUpperRelayOperEntry
   ACCESS     not-accessible
   STATUS     mandatory
   DESCRIPTION
     "An entry in the gsmBcUpperRelayOperTable."
   INDEX {
      gsmBcTrunkGrpIndex,
      gsmBcCicIndex,
      gsmBcUpperRelayIndex }
::= { gsmBcUpperRelayOperTable 1 }

GsmBcUpperRelayOperEntry ::= SEQUENCE {
   gsmBcUpperRelayBufferSize
      Unsigned32,
   gsmBcUpperRelayFlowControlStateTx
      INTEGER,
   gsmBcUpperRelayFlowControlStateRx
      INTEGER }

gsmBcUpperRelayBufferSize OBJECT-TYPE
   SYNTAX     Unsigned32 (0..65535)
   ACCESS     read-only
   STATUS     mandatory
   DESCRIPTION
     "This attribute indicates the size of the transmit and receive flow 
      control buffers."
::= { gsmBcUpperRelayOperEntry 1 }

gsmBcUpperRelayFlowControlStateTx OBJECT-TYPE
   SYNTAX     INTEGER  {
                 active(0),
                 inactive(1) }
   ACCESS     read-only
   STATUS     mandatory
   DESCRIPTION
     "This attribute indicates whether the transmit flow control is active or 
      not."
   DEFVAL     { inactive }
::= { gsmBcUpperRelayOperEntry 2 }

gsmBcUpperRelayFlowControlStateRx OBJECT-TYPE
   SYNTAX     INTEGER  {
                 active(0),
                 inactive(1) }
   ACCESS     read-only
   STATUS     mandatory
   DESCRIPTION
     "This attribute indicates whether the receive flow control is active or 
      not."
   DEFVAL     { inactive }
::= { gsmBcUpperRelayOperEntry 3 }

gsmBcUpperRelayStatsTable OBJECT-TYPE
   SYNTAX     SEQUENCE OF GsmBcUpperRelayStatsEntry
   ACCESS     not-accessible
   STATUS     mandatory
   DESCRIPTION
     "This group contains operational attributes that measure the 
      performance of the UpperRelay."
::= { gsmBcUpperRelay 11 }

gsmBcUpperRelayStatsEntry OBJECT-TYPE
   SYNTAX     GsmBcUpperRelayStatsEntry
   ACCESS     not-accessible
   STATUS     mandatory
   DESCRIPTION
     "An entry in the gsmBcUpperRelayStatsTable."
   INDEX {
      gsmBcTrunkGrpIndex,
      gsmBcCicIndex,
      gsmBcUpperRelayIndex }
::= { gsmBcUpperRelayStatsTable 1 }

GsmBcUpperRelayStatsEntry ::= SEQUENCE {
   gsmBcUpperRelayFramesTx
      Counter32,
   gsmBcUpperRelayFramesRx
      Counter32,
   gsmBcUpperRelayUnacknowledgedFrames
      Gauge32 }

gsmBcUpperRelayFramesTx OBJECT-TYPE
   SYNTAX     Counter32 
   ACCESS     read-only
   STATUS     mandatory
   DESCRIPTION
     "This attribute counts the number of frames that are sent in the 
      transmit direction. The counter wraps when it exceeds the 
      maximum value."
::= { gsmBcUpperRelayStatsEntry 1 }

gsmBcUpperRelayFramesRx OBJECT-TYPE
   SYNTAX     Counter32 
   ACCESS     read-only
   STATUS     mandatory
   DESCRIPTION
     "This attribute counts the number of frames that are sent in the 
      receive direction. The counter wraps when it exceeds the maximum 
      value."
::= { gsmBcUpperRelayStatsEntry 2 }

gsmBcUpperRelayUnacknowledgedFrames OBJECT-TYPE
   SYNTAX     Gauge32 (0..4294967295)
   ACCESS     read-only
   STATUS     mandatory
   DESCRIPTION
     "This attribute indicates the number of current frames sent that have 
      not been acknowledged."
::= { gsmBcUpperRelayStatsEntry 3 }




-- 
-- Version and Compliance statements
-- 



-- Object-Group Statement:
-- A list of all current accessible leaf objects.

-- OBJECTS { gsmBcCallType,
--           gsmBcV110LrcErrorsTx,
--           gsmBcV110FramesDiscarded,
--           gsmBcV42bisLastDecodeError,
--           gsmBcRlpIFramesTx,
--           gsmCsCommentText,
--           gsmCsV42bisActionOnError,
--           gsmBcFramerOctetFromIf,
--           gsmBcModemOutbandBreak,
--           gsmBcModemStorageType,
--           gsmBcStopBits,
--           gsmCsRlpN2RetransmitCount,
--           gsmBcLayer1LargeFrameErrorsRx,
--           gsmBcFaxRowStatus,
--           gsmCsErroredMipFrames,
--           gsmCsV42N400RetransLimit,
--           gsmBcRlpFramesRetransmitted,
--           gsmBcV110ComponentName,
--           gsmBcFramerOverruns,
--           gsmBcV42bisModeChangesEncode,
--           gsmCsCustomerIdentifier,
--           gsmBcFaxComponentName,
--           gsmBcRlpIFramesRx,
--           gsmCsV42RowStatus,
--           gsmBcFaxMessageFramesTx,
--           gsmBcL2RCopFlowControlStateTx,
--           gsmBcLayer1ActiveMode,
--           gsmBcComponentName,
--           gsmCsChannelConfigChanges,
--           gsmCsStorageType,
--           gsmBcV42bisCompressionDirection,
--           gsmBcRlpRemoteBusyIndications,
--           gsmBcUpperRelayUnacknowledgedFrames,
--           gsmBcRlpProtocolState,
--           gsmBcRlpIFramesTxDiscarded,
--           gsmBcV42StorageType,
--           gsmBcModemBytesRx,
--           gsmBcModemAlgorithmInUse,
--           gsmBcFaxMessageFramesRx,
--           gsmCsRlpHighestVersion,
--           gsmBcL2RCopFlowControlStateRx,
--           gsmCsAdminState,
--           gsmBcUpperRelayFlowControlStateTx,
--           gsmBcUsageState,
--           gsmBcFaxStorageType,
--           gsmCsV42T401AckTimer,
--           gsmCsFaxComponentName,
--           gsmBcFramerFrmToIf,
--           gsmBcMateBearerChannel,
--           gsmBcUpperRelayFramesTx,
--           gsmBcV42bisMaximumCodewords,
--           gsmBcV110OverRunsRx,
--           gsmBcModemProtocolState,
--           gsmBcV42IFramesTx,
--           gsmBcFramerStorageType,
--           gsmBcV42bisResetsEncode,
--           gsmBcUpperRelayFlowControlStateRx,
--           gsmBcFramerCrcErrors,
--           gsmCsModemComponentName,
--           gsmBcV110RowStatus,
--           gsmCsLpAssignedCapacity,
--           gsmBcV42bisComponentName,
--           gsmBcRlpT2AckDelayTimer,
--           gsmBcV42IBytesTx,
--           gsmBcUpperRelayComponentName,
--           gsmBcV42RxN401FrameSize,
--           gsmBcFramerAdminState,
--           gsmCsRlpStorageType,
--           gsmCsRlpIwfToMsWindowSize,
--           gsmBcV42FramesRetransmitted,
--           gsmBcLayer1FramesDiscarded,
--           gsmCsRlpT1AckTimer,
--           gsmCsRlpRowStatus,
--           gsmBcLayer1DataRate,
--           gsmBcV42IFramesRx,
--           gsmCsStatusMessagesRx,
--           gsmBcRowStatus,
--           gsmBcFramerUsageState,
--           gsmBcFaxBcsFramesRx,
--           gsmBcFramerNonOctetErrors,
--           gsmBcModemTraining,
--           gsmBcLayer1ComponentName,
--           gsmBcL2RCopBreakCountTx,
--           gsmCsCallsSetup,
--           gsmBcV42IBytesRx,
--           gsmBcV42RemoteBusyIndications,
--           gsmBcV42bisMaximumStringSize,
--           gsmBcV42ProtocolState,
--           gsmCsCurrentCalls,
--           gsmBcRlpComponentName,
--           gsmBcModemComponentName,
--           gsmCsModemStorageType,
--           gsmBcOperationalState,
--           gsmBcL2RCopRowStatus,
--           gsmBcModemToDspFlowControlActive,
--           gsmCsFaxRowStatus,
--           gsmCsFaxT1CalledToneTimer,
--           gsmCsModemRowStatus,
--           gsmBcL2RCopBreakCountRx,
--           gsmBcLastResponseCode,
--           gsmCsLpStorageType,
--           gsmBcV42bisModeChangesDecode,
--           gsmBcUpperRelayBufferSize,
--           gsmCsComponentName,
--           gsmBcRlpOutOfSequenceFrames,
--           gsmBcModemOutbandFlowControl,
--           gsmBcV42bisReInitializations,
--           gsmBcV42TxN401FrameSize,
--           gsmBcV42bisRowStatus,
--           gsmCsV42T403IdleProbeTimer,
--           gsmBcV110LargeFrameErrorsRx,
--           gsmBcRlpRowStatus,
--           gsmBcRlpFrameSize,
--           gsmBcV110NonOctetErrorsRx,
--           gsmCsV42bisCompressionDirection,
--           gsmBcV110FramesTx,
--           gsmBcFaxPagesRxFromMobile,
--           gsmBcLayer1OverRunsRx,
--           gsmBcFaxBcsFrameErrors,
--           gsmBcV42TxKwindowSize,
--           gsmCsVoiceLaw,
--           gsmBcV42ComponentName,
--           gsmBcLayer1IntermediateRate,
--           gsmBcLayer1LrcErrorsTx,
--           gsmCsV42StorageType,
--           gsmBcUpperRelayRowStatus,
--           gsmCsMscIpAddress,
--           gsmBcV42bisProtocolModeEncoder,
--           gsmCsV42T402AckDelayTimer,
--           gsmBcV110BytesTx,
--           gsmBcLayer1RowStatus,
--           gsmCsV42T400DetectTimer,
--           gsmBcV42bisCompRatioDecoder,
--           gsmCsRlpMsToIwfWindowSize,
--           gsmBcUpperRelayStorageType,
--           gsmBcV110FramesRx,
--           gsmCsV42bisRowStatus,
--           gsmBcV42RxKwindowSize,
--           gsmBcModemRowStatus,
--           gsmCsV42bisMaximumCodewords,
--           gsmBcModemAutobaud,
--           gsmBcFramerComponentName,
--           gsmBcV42bisResetsDecode,
--           gsmBcV110BytesRx,
--           gsmBcModemRate,
--           gsmBcFramerUnderruns,
--           gsmBcRlpCrcErrorsRx,
--           gsmCsCallsRequested,
--           gsmBcV42T1AckTimeouts,
--           gsmBcV42BadFramesRx,
--           gsmCsLpConfiguredBearerChannels,
--           gsmBcL2RCopBytesTx,
--           gsmCsV42bisComponentName,
--           gsmCsRlpT2AckDelayTimer,
--           gsmCsV42bisStorageType,
--           gsmCsRlpComponentName,
--           gsmBcMipState,
--           gsmBcDataBits,
--           gsmBcRlpN2RetransmitCount,
--           gsmBcFaxChannelModeModify,
--           gsmBcFlowControl,
--           gsmCsCallsActivated,
--           gsmCsRowStatus,
--           gsmBcFaxProtocolState,
--           gsmBcRlpT1AckTimeouts,
--           gsmCsLpComponentName,
--           gsmBcModemAsyncMode,
--           gsmBcV110UnderRunsTx,
--           gsmBcV110StorageType,
--           gsmBcRlpIwfToMsWindowSize,
--           gsmCsCallsReleasedNormal,
--           gsmCsChannelModeModifyRequests,
--           gsmBcV42RowStatus,
--           gsmCsUsageState,
--           gsmBcRlpLocalBusyIndications,
--           gsmBcModemToUpperFlowControlActive,
--           gsmCsV42bisMaximumStringSize,
--           gsmBcFramerFrmFromIf,
--           gsmBcFaxBcsFramesTx,
--           gsmBcMaxUserDataRate,
--           gsmBcL2RCopBytesRx,
--           gsmBcV42bisErrorsInDecode,
--           gsmBcStorageType,
--           gsmBcModemAutoHdlcMode,
--           gsmCsOperationalState,
--           gsmBcLayer1NonOctetErrorsRx,
--           gsmBcLayer1FramesTx,
--           gsmBcUpperRelayFramesRx,
--           gsmBcFaxPagesTxToMobile,
--           gsmBcRlpHighestVersion,
--           gsmBcAdminState,
--           gsmBcFramerRowStatus,
--           gsmBcLayer1Connection,
--           gsmBcLayer1BytesTx,
--           gsmBcV42bisCompRatioEncoder,
--           gsmBcCustomerIdentifier,
--           gsmCsVirtualRouterName,
--           gsmBcL2RCopStorageType,
--           gsmBcV110DataRate,
--           gsmBcRlpInvalidFrames,
--           gsmCsV42TxN401FrameSize,
--           gsmCsFaxStorageType,
--           gsmCsCallsReleasedAbnormal,
--           gsmBcLayer1FramesRx,
--           gsmBcV42CrcErrorsRx,
--           gsmBcFaxActiveMode,
--           gsmBcModemBytesTx,
--           gsmBcFramerInterfaceName,
--           gsmBcFramerFramingType,
--           gsmCsV42TxKwindowSize,
--           gsmBcFramerOperationalState,
--           gsmCsV42ComponentName,
--           gsmBcFaxMessageRate,
--           gsmBcLayer1BytesRx,
--           gsmCsLpRowStatus,
--           gsmBcRlpResetsRx,
--           gsmBcModemFramingErrors,
--           gsmCsLpModemsSupported,
--           gsmBcV42bisProtocolModeDecoder,
--           gsmBcV42bisStorageType,
--           gsmBcFramerLrcErrors,
--           gsmCsV42RxN401FrameSize,
--           gsmBcRlpStorageType,
--           gsmBcRlpMsToIwfWindowSize,
--           gsmBcParity,
--           gsmBcRlpT1AckTimer,
--           gsmBcL2RCopComponentName,
--           gsmCsV42RxKwindowSize,
--           gsmBcV42LocalBusyIndications,
--           gsmBcModemReceiverTransmitter,
--           gsmCsLpActiveCalls,
--           gsmBcConnectionType,
--           gsmBcLayer1UnderRunsTx,
--           gsmBcLayer1StorageType,
--           gsmBcV110IntermediateRate }
-- STATUS  mandatory
-- DESCRIPTION
--   "A list of all current accessible leaf objects."

gsmIwfGroup OBJECT IDENTIFIER ::= { gsmIwfMIB 1 }
gsmIwfGroupBE OBJECT IDENTIFIER ::= { gsmIwfGroup 5 }
gsmIwfGroupBE01 OBJECT IDENTIFIER ::= { gsmIwfGroupBE 2 }
gsmIwfGroupBE01A OBJECT IDENTIFIER ::= { gsmIwfGroupBE01 2 }



-- Agent-Capabilities Statement:

-- PRODUCT-RELEASE "Passport Release 7.0 GsmIwf."
-- STATUS          mandatory
-- DESCRIPTION     "GsmIwf MIB: MIB Version BE01A,
--                  Software Version BG00S4C."
-- SUPPORTS        Nortel-Magellan-Passport-GsmIwfMIB
--    INCLUDES     { gsmIwfGroupBE01A }

gsmIwfCapabilities OBJECT IDENTIFIER ::= { gsmIwfMIB 3 }
gsmIwfCapabilitiesBE OBJECT IDENTIFIER ::= { gsmIwfCapabilities 5 }
gsmIwfCapabilitiesBE01 OBJECT IDENTIFIER ::= { gsmIwfCapabilitiesBE 2 }
gsmIwfCapabilitiesBE01A OBJECT IDENTIFIER ::= { gsmIwfCapabilitiesBE01 2 }





END
