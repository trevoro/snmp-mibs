-- ZyXEL Communications Corporation
-- Private Enterprise MIB definition 
  
-- This file describes the ZyXEL Communications Corporation Enterprise MIB.
-- It contains ZyXEL products OIDs, and common managed objects.

-- $Log: ZYXEL-IPSG-MIB.mib $ 
-- Revision 1.3  2012/09/19 07:37:47  Kevin 
-- if it's leaf node, revise the vender name from zyxel to zy 
-- Revision 1.2  2012/07/05 06:23:05  Kevin 
-- 1. upgrade from SNMP to SNMPv2  
-- 2. clean warning 
-- Revision 1.1  2012/05/30 07:49:38  Kevin 
-- Initial revision 

ZYXEL-IPSG-MIB DEFINITIONS ::= BEGIN

    IMPORTS
	enterprises		FROM RFC1155-SMI                                
	
	OBJECT-TYPE
		FROM SNMPv2-SMI			-- RFC2578	
	RowStatus, DateAndTime, TruthValue, StorageType, MacAddress
		FROM SNMPv2-TC			-- RFC2579
	DisplayString                                          
	  	FROM RFC1213-MIB
	EnabledStatus
		FROM  P-BRIDGE-MIB
	PortList
		FROM  Q-BRIDGE-MIB
	dot1dBasePort
       	FROM BRIDGE-MIB
	InterfaceIndexOrZero			-- RFC2863
		FROM IF-MIB
	SnmpAdminString
		FROM SNMP-FRAMEWORK-MIB		-- RFC2571
	InetAddressType, InetAddress
		FROM INET-ADDRESS-MIB		-- RFC2851
	OperationResponseStatus
		FROM DISMAN-PING-MIB
    Counter, TimeTicks
        FROM RFC1155-SMI
    BridgeId, Timeout
        FROM BRIDGE-MIB  
    dot1agCfmMdIndex 
		FROM IEEE8021-CFM-MIB
	dot1agCfmMaIndex
		FROM IEEE8021-CFM-MIB	
	dot1agCfmMepIdentifier
		FROM IEEE8021-CFM-MIB   	
    IpAddress
        FROM SNMPv2-SMI
    ifIndex
    	FROM IF-MIB					-- RFC2863
    NOTIFICATION-TYPE
        FROM SNMPv2-SMI
    sysObjectID 
        FROM RFC1213-MIB 
	ospfIfIpAddress, ospfAddressLessIf, ospfAreaId, ospfNbrIpAddr, ospfNbrAddressLessIndex,
	ospfLsdbAreaId, ospfLsdbType, ospfLsdbLsid, ospfLsdbRouterId, ospfVirtIfAreaId, ospfVirtIfNeighbor
		FROM OSPF-MIB
	esMgmt			
		FROM ZYXEL-ES-SMI;

	zyxelIpsg MODULE-IDENTITY
		LAST-UPDATED	"201207010000Z"    
		ORGANIZATION "Enterprise Solution ZyXEL"     
		CONTACT-INFO
			""	   
		DESCRIPTION
			"The subtree for IP Source Guard (IPSG)"
		::= { esMgmt 33 }
	
	zyxelArpFreezeSetup 	OBJECT IDENTIFIER ::= { zyxelIpsg 1 }	
	zyxelIpsgStatus 		OBJECT IDENTIFIER ::= { zyxelIpsg 2 }	
	zyxelStaticBindingSetup OBJECT IDENTIFIER ::= { zyxelIpsg 3 }	
---------------------------------------------------
--
--  33.zyxelIpsg
--
---------------------------------------------------	

--		zyxelArpFreezeSetup  
        
        zyArpFreeze OBJECT-TYPE
        SYNTAX  INTEGER
        MAX-ACCESS  read-write
        STATUS  current
        DESCRIPTION
		"Add all learned ARP table entries to static binding table. 
		 It's meaningless while reading this entry."
        ::= { zyxelArpFreezeSetup 1 }
 
        zyArpFreezePorts OBJECT-TYPE
        SYNTAX  PortList
        MAX-ACCESS  read-write
        STATUS  current
        DESCRIPTION
		"Add learned ARP table entries to static binding table by ports. 
		 It's meaningless while reading this entry."
        ::= { zyxelArpFreezeSetup 2 }

        zyArpFreezeVlan OBJECT-TYPE
        SYNTAX  INTEGER
        MAX-ACCESS  read-write
        STATUS  current
        DESCRIPTION
		"Add learned ARP table entries to static binding table by VLAN. 
		 It's meaningless while reading this entry."
        ::= { zyxelArpFreezeSetup 3 }


--		zyxelIpsgStatus 
        
	    zyxelIpsgInfoTable  OBJECT-TYPE
	    SYNTAX	SEQUENCE OF ZyxelIpsgInfoEntry 
	    MAX-ACCESS  not-accessible
	    STATUS  current
	    DESCRIPTION
		"The table contains IGMP information."
	    ::= { zyxelIpsgStatus 1 }	

		zyxelIpsgInfoEntry  OBJECT-TYPE
        SYNTAX	ZyxelIpsgInfoEntry 
        MAX-ACCESS	not-accessible
        STATUS	current
        DESCRIPTION    	
        "An entry contains IGMP information. "
        INDEX          	{ zyIpsgInfoMacAddress, zyIpsgInfoVid }
        ::= { zyxelIpsgInfoTable 1 }

        ZyxelIpsgInfoEntry ::=
           SEQUENCE {
            zyIpsgInfoMacAddress	MacAddress,
        	zyIpsgInfoVid			INTEGER,
        	zyIpsgInfoIpAddress		IpAddress,
        	zyIpsgInfoLeaseTime		INTEGER,
        	zyIpsgInfoType			INTEGER,
        	zyIpsgInfoPort			INTEGER
        }

        zyIpsgInfoMacAddress OBJECT-TYPE
        SYNTAX  MacAddress
        MAX-ACCESS  not-accessible
        STATUS  current
        DESCRIPTION
		"The source MAC address in the binding."
        ::= { zyxelIpsgInfoEntry 1 }

        zyIpsgInfoVid OBJECT-TYPE
        SYNTAX  INTEGER (1.. 4094)
        MAX-ACCESS  not-accessible
        STATUS  current
        DESCRIPTION
		"The source VLAN ID in the binding."
        ::= { zyxelIpsgInfoEntry 2 }

        zyIpsgInfoIpAddress OBJECT-TYPE
        SYNTAX  IpAddress
        MAX-ACCESS  read-only
        STATUS  current
        DESCRIPTION
		"The IP address assigned to the MAC address in the binding."
        ::= { zyxelIpsgInfoEntry 3 }

        zyIpsgInfoLeaseTime OBJECT-TYPE
        SYNTAX  INTEGER
        MAX-ACCESS  read-only
        STATUS  current
        DESCRIPTION
		"This entry displays how much time (seconds) the binding is valid. 
		 This entry displays value 0 if the binding is always valid (for example, a static binding)."
        ::= { zyxelIpsgInfoEntry 4 }

        zyIpsgInfoType OBJECT-TYPE
        SYNTAX  INTEGER { 
        	static(1), 
        	dhcp(2) 
        }
        MAX-ACCESS  read-only
        STATUS  current
        DESCRIPTION
		"This entry displays how the switch learned the binding.
		 static: This binding was learned from information provided manually by an administrator.
		 dhcp: This binding was learned by snooping DHCP packets."
        ::= { zyxelIpsgInfoEntry 5 }

        zyIpsgInfoPort OBJECT-TYPE
        SYNTAX  INTEGER 
        MAX-ACCESS  read-only
        STATUS  current
        DESCRIPTION
		"The port number in the binding. The value 0 means any port."
        ::= { zyxelIpsgInfoEntry 6 }
 
 --  	zyxelStaticBindingSetup      		                       
        
        zyStaticBindingMaxNumberOfRules OBJECT-TYPE
        SYNTAX  INTEGER
        MAX-ACCESS  read-only
        STATUS  current
        DESCRIPTION
		"The maximum number of static binding rules that can be created."
        ::= { zyxelStaticBindingSetup 1 }

--     zyxelStaticBindingTable
        zyxelStaticBindingTable  OBJECT-TYPE
	    SYNTAX	SEQUENCE OF ZyxelStaticBindingEntry 
	    MAX-ACCESS  not-accessible
	    STATUS  current
	    DESCRIPTION
		"The table contains static binding configuration. "
	    ::= { zyxelStaticBindingSetup 2 }	

		zyxelStaticBindingEntry  OBJECT-TYPE
        SYNTAX	ZyxelStaticBindingEntry 
        MAX-ACCESS	not-accessible
        STATUS	current
        DESCRIPTION    	
        "An entry contains static binding configuration."
        INDEX          	{ zyStaticBindingMacAddress, zyStaticBindingVid }
        ::= { zyxelStaticBindingTable 1 }

        ZyxelStaticBindingEntry ::=
           SEQUENCE {
            zyStaticBindingMacAddress	MacAddress,
        	zyStaticBindingVid			INTEGER,
        	zyStaticBindingIpAddress	IpAddress,
        	zyStaticBindingPort			INTEGER,
        	zyStaticBindingRowStatus	RowStatus
           }

        zyStaticBindingMacAddress OBJECT-TYPE
        SYNTAX  MacAddress
        MAX-ACCESS  not-accessible
        STATUS  current
        DESCRIPTION
		"The source MAC address in the binding."
        ::= { zyxelStaticBindingEntry 1 }

        zyStaticBindingVid OBJECT-TYPE
        SYNTAX  INTEGER (1..4094)
        MAX-ACCESS  not-accessible
        STATUS  current
        DESCRIPTION
		"The IP address assigned to the MAC address in the binding."
        ::= { zyxelStaticBindingEntry 2 }

        zyStaticBindingIpAddress OBJECT-TYPE
        SYNTAX  IpAddress
        MAX-ACCESS  read-write
        STATUS  current
        DESCRIPTION
		"Enter the source VLAN ID in the binding."
        ::= { zyxelStaticBindingEntry 3 }

        zyStaticBindingPort OBJECT-TYPE
        SYNTAX  INTEGER 
        MAX-ACCESS  read-write
        STATUS  current
        DESCRIPTION
		"Enter the port number in the binding. The value 0 means any port."
        ::= { zyxelStaticBindingEntry 4 }

        zyStaticBindingRowStatus OBJECT-TYPE
        SYNTAX  RowStatus
        MAX-ACCESS  read-create
        STATUS  current
        DESCRIPTION
		"This object allows static binding entries to be created and deleted from static binding table."
        ::= { zyxelStaticBindingEntry 5 } 
                                      
     
  
END
