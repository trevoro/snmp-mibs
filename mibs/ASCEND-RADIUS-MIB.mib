--			Ascend RADIUS MIB
--
--			Ascend Communications, Inc
--			1275 Harbor Bay Pkwy
--			Alameda, CA 94502
--			+1 510 769 6001
--			info@ascend.com
--
--		Copyright (c) 1993-1997 Ascend Communications, Inc.
--		All rights reserved.
--
-- $Id: radius.mib,v 29.2.174.1 1999/11/03 01:23:18 sbhattac Exp $
--
-- 11 Mar 97:	  Initial release
-- 13 Jul 98: aq  Add radiusNewNASPortIDFormat to radiusGroup

ASCEND-RADIUS-MIB DEFINITIONS ::= BEGIN

    IMPORTS
	radiusGroup
	    FROM ASCEND-MIB
	IpAddress
	    FROM RFC1155-SMI
	OBJECT-TYPE
	    FROM RFC-1212;

	--
	-- Ascend RADIUS Group
	--
	-- This group contains statistics for RADIUS requests.
	--

    radiusNumAuthServers OBJECT-TYPE
	SYNTAX		INTEGER
	ACCESS		read-only
	STATUS		mandatory
	DESCRIPTION	"The maximum number of RADIUS authentication
			 servers supported by the system."
	::= { radiusGroup 1 }

    radiusNumAcctServers OBJECT-TYPE
	SYNTAX		INTEGER
	ACCESS		read-only
	STATUS		mandatory
	DESCRIPTION	"The maximum number of RADIUS accounting
			 servers supported by the system."
	::= { radiusGroup 2 }
 
    radiusAuthStatsTable	OBJECT-TYPE
	SYNTAX		SEQUENCE OF RadiusAuthStatsEntry
	ACCESS		not-accessible
	STATUS		mandatory
	DESCRIPTION	"A list of entries for RADIUS authentication
			 statistics."
	::= { radiusGroup 3 }

    radiusAuthStatsEntry	OBJECT-TYPE
	SYNTAX		RadiusAuthStatsEntry
	ACCESS		not-accessible
	STATUS		mandatory
	DESCRIPTION	"An entry containing object variables to describe
			 a session."
	INDEX		{ radAuthServerIndex }
	::= { radiusAuthStatsTable 1 }

    RadiusAuthStatsEntry ::=
	SEQUENCE {
	    radAuthServerIndex
		INTEGER,
	    radAuthLoginRqstSent
		INTEGER,
	    radAuthOtherRqstSent
		INTEGER,
	    radAuthRqstTimedOut
		INTEGER,
	    radAuthOtherRqstTimedOut
		INTEGER,
	    radAuthRspRcvd
		INTEGER,
	    radAuthOtherRspRcvd
		INTEGER,
	    radAuthUnexpRspRcvd
		INTEGER,
	    radAuthBadRspRcvd
		INTEGER,
	    radAuthAckRspRcvd
		INTEGER,
	    radAuthHostIPAddress
		IpAddress,
	    radAuthCurrentServerFlag
		INTEGER
	}

    radAuthServerIndex	OBJECT-TYPE
	SYNTAX		INTEGER
	ACCESS		read-only
	STATUS		mandatory
	DESCRIPTION	"The index number for this session status entry. Its
			 value ranges from 1 to 'radiusNumAuthServers'.
			 and identifies which server entry is associated
			 with."
	::= { radiusAuthStatsEntry 1 }

    radAuthLoginRqstSent OBJECT-TYPE
	SYNTAX		INTEGER
	ACCESS		read-only
	STATUS		mandatory
	DESCRIPTION	"Total number of authentication requests sent.
			 These requests are strictly for authentication
			 purposes.  The sum of this value and
			 'radAuthOtherRqstSent' represents the total
			 number of requests sent (excluding RADIUS
			 accounting requests)."
	::= { radiusAuthStatsEntry 2 }

    radAuthOtherRqstSent	OBJECT-TYPE
	SYNTAX		INTEGER
	ACCESS		read-only
	STATUS		mandatory
	DESCRIPTION	"Total number of requests sent that are NOT
			 related to authentication or accounting. These
			 include requests for routes, filters, banners, etc."
	::= { radiusAuthStatsEntry 3 }

    radAuthRqstTimedOut	OBJECT-TYPE
	SYNTAX		INTEGER
	ACCESS		read-only
	STATUS		mandatory
	DESCRIPTION	"Total number of authentication requests which
			 timed out. Value should be less than or equal
			 to 'radAuthLoginRqstSent'."
	::= { radiusAuthStatsEntry 4 }

    radAuthOtherRqstTimedOut	OBJECT-TYPE
	SYNTAX		INTEGER
	ACCESS		read-only
	STATUS		mandatory
	DESCRIPTION	"Total number of requests excluding authentication
			 and accounting which timed out. Value should be
			 less than or equal to 'radAuthOtherRqstSent'."
	::= { radiusAuthStatsEntry 5 }

    radAuthRspRcvd	OBJECT-TYPE
	SYNTAX		INTEGER
	ACCESS		read-only
	STATUS		mandatory
	DESCRIPTION	"Total number of responses to authentication
			 requests received. Response could be a NAK
			 or an ACK. Value should match radAuthLoginRqstSent.
			 The sum of this value and 'radAuthOtherRspRcvd',
			 'radAuthUnexpRspRcvd', and 'radAuthBadRspRcvd'
			 represents the total number of responses
			 received (excluding those related to RADIUS
			 accounting)."
	::= { radiusAuthStatsEntry 6 }

    radAuthOtherRspRcvd	OBJECT-TYPE
	SYNTAX		INTEGER
	ACCESS		read-only
	STATUS		mandatory
	DESCRIPTION	"Total number of responses to requests that
			 were NOT related to authentication or accounting.
			 Response could be a NAK or an ACK. Value should
			 be less than or equal to radAuthOtherRqstSent."
	::= { radiusAuthStatsEntry 7 }

    radAuthUnexpRspRcvd  OBJECT-TYPE
	SYNTAX		INTEGER
	ACCESS		read-only
	STATUS		mandatory
	DESCRIPTION	"Total number of responses received that
			 did not match an outstanding request.
			 A positive value may indicate configured
			 timeout is insufficient. Total excludes
			 accounting responses."
	::= { radiusAuthStatsEntry 8 }

    radAuthBadRspRcvd	OBJECT-TYPE
	SYNTAX		INTEGER
	ACCESS		read-only
	STATUS		mandatory
	DESCRIPTION	"Total number of authentication responses
			 received that were rejected due to:
			    (1) authentication NAKed.
			    (2) invalid authenticator field.
			    (3) invalid packet format.
			    (4) invalid code field.
			    (5) unrecognized attribute.
			 A positive value may indicate mismatch in
			 the shared secrets."
	::= { radiusAuthStatsEntry 9 }

    radAuthAckRspRcvd	OBJECT-TYPE
	SYNTAX		INTEGER
	ACCESS		read-only
	STATUS		mandatory
	DESCRIPTION	"Total number of authentication requests
			 which were ACKed or authenticated
			 successfully. Value is less than or
			 equal to 'radAuthLoginRqstSent'."
	::= { radiusAuthStatsEntry 10 }

    radAuthHostIPAddress OBJECT-TYPE
	SYNTAX		 IpAddress
	ACCESS		 read-only
	STATUS		 mandatory
	DESCRIPTION	 "The IP address of the Authentication server. The 
			  value 0.0.0.0 is returned if entry is invalid."
	::= { radiusAuthStatsEntry 11 }

    radAuthCurrentServerFlag OBJECT-TYPE
	SYNTAX		     INTEGER {
			         standby(1),
			         current(2)
			     }
	ACCESS		     read-write
	STATUS		     mandatory
	DESCRIPTION	     "Value indicates whether this entry is the current
			      authentication server or not. Writing a value
			      will cause the current server to be reset."
	::= { radiusAuthStatsEntry 12 }

    radiusAcctStatsTable	OBJECT-TYPE
	SYNTAX		SEQUENCE OF RadiusAcctStatsEntry
	ACCESS		not-accessible
	STATUS		mandatory
	DESCRIPTION	"A list of entries for RADIUS accounting
			 statistics."
	::= { radiusGroup 4 }

    radiusAcctStatsEntry	OBJECT-TYPE
	SYNTAX		RadiusAcctStatsEntry
	ACCESS		not-accessible
	STATUS		mandatory
	DESCRIPTION	"An entry containing object variables to describe
			 a session."
	INDEX		{ radAcctServerIndex }
	::= { radiusAcctStatsTable 1 }

    RadiusAcctStatsEntry ::=
	SEQUENCE {
	    radAcctServerIndex
		INTEGER,
	    radAcctRqstSent
		INTEGER,
	    radAcctRqstTimedOut
		INTEGER,
	    radAcctRspRcvd
		INTEGER,
	    radAcctUnexpRspRcvd
		INTEGER,
	    radAcctHostIPAddress
		IpAddress,
	    radAcctCurrentServerFlag
		INTEGER
	}

    radAcctServerIndex	OBJECT-TYPE
	SYNTAX		INTEGER
	ACCESS		read-only
	STATUS		mandatory
	DESCRIPTION	"The index number for this session status entry. Its
			 value ranges from 1 to 'radiusNumAcctServers'.
			 and identifies which server entry is associated
			 with."
	::= { radiusAcctStatsEntry 1 }

    radAcctRqstSent	OBJECT-TYPE
	SYNTAX		INTEGER
	ACCESS		read-only
	STATUS		mandatory
	DESCRIPTION	"Total number of accounting requests sent."
	::= { radiusAcctStatsEntry 2 }

    radAcctRqstTimedOut	OBJECT-TYPE
	SYNTAX		INTEGER
	ACCESS		read-only
	STATUS		mandatory
	DESCRIPTION	"Total number of accounting requests which
			 timed out."
	::= { radiusAcctStatsEntry 3 }

    radAcctRspRcvd	OBJECT-TYPE
	SYNTAX		INTEGER
	ACCESS		read-only
	STATUS		mandatory
	DESCRIPTION	"Total number of responses to accounting
			 requests received."
	::= { radiusAcctStatsEntry 4 }

    radAcctUnexpRspRcvd	OBJECT-TYPE
	SYNTAX		INTEGER
	ACCESS		read-only
	STATUS		mandatory
	DESCRIPTION	"Total number of accounting responses received
			 that did not match an outstanding request.
			 A positive value may indicate configured
			 timeout is insufficient."
	::= { radiusAcctStatsEntry 5 }

    radAcctHostIPAddress OBJECT-TYPE
	SYNTAX		 IpAddress
	ACCESS		 read-only
	STATUS		 mandatory
	DESCRIPTION	 "The IP address of the Accounting server. The 
			  value 0.0.0.0 is returned if entry is invalid."
	::= { radiusAcctStatsEntry 6 }

    radAcctCurrentServerFlag OBJECT-TYPE
	SYNTAX		     INTEGER {
			         inactive(1),
			         active(2)
			     }
	ACCESS		     read-write
	STATUS		     mandatory
	DESCRIPTION	     "Value indicates whether this entry is the current
			      active accounting server or not. Writing a value
			      will cause the current server to be reset."
	::= { radiusAcctStatsEntry 7 }

    radiusNewNASPortIDFormat OBJECT-TYPE
        SYNTAX          INTEGER {
                        true(1),
                        false(2)
        }
        ACCESS          read-write
        STATUS          mandatory
        DESCRIPTION
           "TRUE if new NAS port ID format is used, FALSE if old NAS Port
            ID is used. On the TNT product family the new NAS port ID format
            is used by default. The old format cannot be used for multi-shelf
            systems or if any line cards are in a slot greater than the
            twelfth position."
        ::= { radiusGroup 5 }

END
