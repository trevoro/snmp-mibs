HIPATH-WIRELESS-PRODUCTS-MIB DEFINITIONS ::= BEGIN
 
		IMPORTS
				enterprises FROM RFC1155-SMI
			hiPathWirelessProducts, hiPathWirelessModules			
				FROM HIPATH-WIRELESS-SMI			
			MODULE-IDENTITY			
				FROM SNMPv2-SMI;
	
	
		-- 1.3.6.1.4.1.4329.15.5.1
		hiPathWirelessProductsMIB MODULE-IDENTITY 
			LAST-UPDATED "200811191021Z"		-- November 19, 2008 at 10:21
			ORGANIZATION 
				"Chantry Networks Inc."
			CONTACT-INFO 
				"Behrouz Sultan
				Chantry Networks, Inc.
				
				1900 Minnesota Court, Suite 125
				Mississauga ON, L5N 3C9
				
				Email: behrouz.sultan@siemens.com
				Phone 1-905-288-3537
				Fax   1-905-567-0099"
			DESCRIPTION 
				"This module defines object identifiers assigned to all 
				High Path Wireless hardware devices."
			REVISION "200811191021Z"		-- November 19, 2008 at 10:21 GMT
			DESCRIPTION 
				"Added OID for new HiPath Controllers (CRBT-8110, CRBT-8210 and C5110)."
			REVISION "200708071357Z"		-- August 07, 2007 at 13:57 GMT
			DESCRIPTION 
				"Added product OID for new Access Point."
			REVISION "200609111803Z"		-- September 11, 2006 at 18:03 GMT
			DESCRIPTION 
				"Added OID for C2000 platform."
			REVISION "200507211450Z"		-- July 21, 2005 at 14:50 GMT
			DESCRIPTION 
				"Initial revision."
			::= { hiPathWirelessModules 1 }

		
	
--
-- Node definitions
--
	
		-- 1.3.6.1.4.1.4329.15.1.1
		control OBJECT IDENTIFIER ::= { hiPathWirelessProducts 1 }

		
-- High Path Wireless Controller C10
		-- 1.3.6.1.4.1.4329.15.1.1.1
		c10 OBJECT IDENTIFIER ::= { control 1 }

		
-- High Path Wireless Controller C100
		-- 1.3.6.1.4.1.4329.15.1.1.2
		c100 OBJECT IDENTIFIER ::= { control 2 }

		
-- High Path Wireless Controller C1000
		-- 1.3.6.1.4.1.4329.15.1.1.3
		c1000 OBJECT IDENTIFIER ::= { control 3 }

		
-- High Path Wireless Controller Manager
		-- 1.3.6.1.4.1.4329.15.1.1.4
		hiPathWirelessManager OBJECT IDENTIFIER ::= { control 4 }

		
-- High Path Wireless Controller C2000
		-- 1.3.6.1.4.1.4329.15.1.1.5
		c2000 OBJECT IDENTIFIER ::= { control 5 }


-- High Path Wireless Controller C20
		-- 1.3.6.1.4.1.4329.15.1.1.6
		c20 OBJECT IDENTIFIER ::= { control 6 }
		

-- High Path Wireless Controller C20N
		-- 1.3.6.1.4.1.4329.15.1.1.7
		c20N OBJECT IDENTIFIER ::= { control 7 }

-- High Path Wireless Controller CRBT-8110
		-- 1.3.6.1.4.1.4329.15.1.1.8
		crbt8110 OBJECT IDENTIFIER ::= { control 8 }

-- High Path Wireless Controller CRBT-8210
		-- 1.3.6.1.4.1.4329.15.1.1.9
		crbt8210 OBJECT IDENTIFIER ::= { control 9 }

-- High Path Wireless Controller C5110
		-- 1.3.6.1.4.1.4329.15.1.1.10
		c5110 OBJECT IDENTIFIER ::= { control 10 }





		-- 1.3.6.1.4.1.4329.15.1.2
		access OBJECT IDENTIFIER ::= { hiPathWirelessProducts 2 }

		
-- High Path Wireless Access Point
		-- 1.3.6.1.4.1.4329.15.1.2.2
		ap26xx OBJECT IDENTIFIER ::= { access 2 }


-- High Path Wireless Access Point 2600 series
		-- 1.3.6.1.4.1.4329.15.1.2.3
		ap2600 OBJECT IDENTIFIER ::= { access 3 }

-- High Path Wireless Access Point 2650 series
		-- 1.3.6.1.4.1.4329.15.1.2.4
		ap2650 OBJECT IDENTIFIER ::= { access 4 }

-- High Path Wireless Access Point Scalance 786 series
		-- 1.3.6.1.4.1.4329.15.1.2.5
		apW786 OBJECT IDENTIFIER ::= { access 5 }
		
-- High Path Wireless Access Point Scalance 788
		-- 1.3.6.1.4.1.4329.15.1.2.6
		apW788 OBJECT IDENTIFIER ::= { access 6 }

-- High Path Wireless Access Point 802.11n series 
		-- 1.3.6.1.4.1.4329.15.1.2.7
		ap3610 OBJECT IDENTIFIER ::= { access 7 }
	
	END
