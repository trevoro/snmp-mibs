Nortel-MsCarrier-MscPassport-UnackTrunksMIB
DEFINITIONS ::= BEGIN



IMPORTS

      OBJECT-TYPE
   FROM RFC-1212

      mscPassportMIBs
   FROM Nortel-MsCarrier-MscPassport-UsefulDefinitionsMIB

      Counter32,
      DisplayString,
      StorageType,
      RowStatus,
      Gauge32,
      Unsigned32
   FROM Nortel-MsCarrier-MscPassport-StandardTextualConventionsMIB

      NonReplicated,
      PassportCounter64,
      Link
   FROM Nortel-MsCarrier-MscPassport-TextualConventionsMIB

      mscTrk,
      mscTrkIndex
   FROM Nortel-MsCarrier-MscPassport-TrunksMIB;




-- LAST-UPDATED   "0011300000Z"
-- ORGANIZATION   "Nortel Networks"
-- CONTACT-INFO   "
--         Nortel Carrier Data Network Management
--         
--         Postal:       P.O. Box 3511, Station C 
--                       Ottawa, Ontario 
--                       Canada  K1Y 4H7
--         
--         via the WEB:  http://www.nortelnetworks.com  
--                       select 'Contact Us' from the menu
--          
--         via phone:    1-800-4NORTEL"
-- DESCRIPTION
--    "The module describing the Nortel MsCarrier MscPassport
--     UnackTrunks Enterprise MIB."

unackTrunksMIB OBJECT IDENTIFIER ::= { mscPassportMIBs 22 }










-- Trunk/n Unacknowledged
-- The Unacknowledged component provides a Layer 2 protocol that 
-- adds the minimum of overhead to data on the link. A Framer 
-- subcomponent is automatically added providing the underlying 
-- HDLC framing and associated hardware that the Unacknowledged 
-- component will use.

mscTrkUnAcked OBJECT IDENTIFIER ::= { mscTrk 2 }



mscTrkUnAckedRowStatusTable OBJECT-TYPE
   SYNTAX     SEQUENCE OF MscTrkUnAckedRowStatusEntry
   ACCESS     not-accessible
   STATUS     mandatory
   DESCRIPTION
     "This entry controls the addition and deletion of 
      mscTrkUnAcked components."
::= { mscTrkUnAcked 1 }

mscTrkUnAckedRowStatusEntry OBJECT-TYPE
   SYNTAX     MscTrkUnAckedRowStatusEntry
   ACCESS     not-accessible
   STATUS     mandatory
   DESCRIPTION
     "A single entry in the table represents a single 
      mscTrkUnAcked component."
   INDEX {
      mscTrkIndex,
      mscTrkUnAckedIndex }
::= { mscTrkUnAckedRowStatusTable 1 }

MscTrkUnAckedRowStatusEntry ::= SEQUENCE {
   mscTrkUnAckedRowStatus
      RowStatus,
   mscTrkUnAckedComponentName
      DisplayString,
   mscTrkUnAckedStorageType
      StorageType,
   mscTrkUnAckedIndex
      NonReplicated }

mscTrkUnAckedRowStatus OBJECT-TYPE
   SYNTAX     RowStatus 
   ACCESS     read-write
   STATUS     mandatory
   DESCRIPTION
     "This variable is used as the basis for SNMP naming of
      mscTrkUnAcked components.
      These components can be added and deleted."
::= { mscTrkUnAckedRowStatusEntry 1 }

mscTrkUnAckedComponentName OBJECT-TYPE
   SYNTAX     DisplayString 
   ACCESS     read-only
   STATUS     mandatory
   DESCRIPTION
     "This variable provides the component's string name for
      use with the ASCII Console Interface"
::= { mscTrkUnAckedRowStatusEntry 2 }

mscTrkUnAckedStorageType OBJECT-TYPE
   SYNTAX     StorageType 
   ACCESS     read-only
   STATUS     mandatory
   DESCRIPTION
     "This variable represents the storage type value for the
      mscTrkUnAcked tables."
::= { mscTrkUnAckedRowStatusEntry 4 }

mscTrkUnAckedIndex OBJECT-TYPE
   SYNTAX     NonReplicated 
   ACCESS     not-accessible
   STATUS     mandatory
   DESCRIPTION
     "This variable represents the index for the mscTrkUnAcked tables."
::= { mscTrkUnAckedRowStatusEntry 10 }

mscTrkUnAckedProvTable OBJECT-TYPE
   SYNTAX     SEQUENCE OF MscTrkUnAckedProvEntry
   ACCESS     not-accessible
   STATUS     mandatory
   DESCRIPTION
     "This group of provisionable attributes contains the parameters used 
      by Unacknowledged, Utp, and FrAccess for monitoring link quality."
::= { mscTrkUnAcked 10 }

mscTrkUnAckedProvEntry OBJECT-TYPE
   SYNTAX     MscTrkUnAckedProvEntry
   ACCESS     not-accessible
   STATUS     mandatory
   DESCRIPTION
     "An entry in the mscTrkUnAckedProvTable."
   INDEX {
      mscTrkIndex,
      mscTrkUnAckedIndex }
::= { mscTrkUnAckedProvTable 1 }

MscTrkUnAckedProvEntry ::= SEQUENCE {
   mscTrkUnAckedMaximumErroredInterval
      Unsigned32,
   mscTrkUnAckedReceiveErrorSensitivity
      Unsigned32 }

mscTrkUnAckedMaximumErroredInterval OBJECT-TYPE
   SYNTAX     Unsigned32 (0 | 1..15)
   ACCESS     read-write
   STATUS     mandatory
   DESCRIPTION
     "This attribute specifies the interval time over which the error 
      threshold (as specified by receiveErrorSensitivity) must be 
      continuously exceeded before the Unacknowledged, Utp, or 
      FrAccess component can be degraded. Once the error interval count 
      exceeds the provisioned value, the Unacknowledged, Utp, or 
      FrAccess component issues an alarm indicating that link quality has 
      degraded, and it disables its parent component. The exception to 
      this is a value of zero, the default, which indicates that the 
      mechanism is completely disabled."
   DEFVAL     { 0 }
::= { mscTrkUnAckedProvEntry 1 }

mscTrkUnAckedReceiveErrorSensitivity OBJECT-TYPE
   SYNTAX     Unsigned32 (0 | 1..10)
   ACCESS     read-write
   STATUS     mandatory
   DESCRIPTION
     "This attribute is the allowable error rate beyond which the 
      Unacknowledged, Utp, or FrAccess component can be degraded if it 
      persists for a duration longer than the maximumErrorInterval. The 
      threshold is expressed as a percentage of number of errored frames 
      in the last interval per number of frames received in the last interval. 
      The exception to this is a value of zero, which indicates that the 
      mechanism is completely disabled. The configurable values are:
      0 = the mechanism is completely disabled
      1 = 1/(2**1)
      2 = 1/(2**2)
      3 = 1/(2**3)
      :
      10 = 1/(2**10)"
   DEFVAL     { 3 }
::= { mscTrkUnAckedProvEntry 2 }

mscTrkUnAckedStateTable OBJECT-TYPE
   SYNTAX     SEQUENCE OF MscTrkUnAckedStateEntry
   ACCESS     not-accessible
   STATUS     mandatory
   DESCRIPTION
     "This group contains the three OSI State attributes and the six OSI 
      Status attributes. The descriptions generically indicate what each 
      attribute implies about the component. Note that not all the values 
      and state combinations described here are supported by every 
      component which reuses this group. For component-specific 
      information and the valid state combinations, refer to the 
      appropriate NTP."
::= { mscTrkUnAcked 11 }

mscTrkUnAckedStateEntry OBJECT-TYPE
   SYNTAX     MscTrkUnAckedStateEntry
   ACCESS     not-accessible
   STATUS     mandatory
   DESCRIPTION
     "An entry in the mscTrkUnAckedStateTable."
   INDEX {
      mscTrkIndex,
      mscTrkUnAckedIndex }
::= { mscTrkUnAckedStateTable 1 }

MscTrkUnAckedStateEntry ::= SEQUENCE {
   mscTrkUnAckedAdminState
      INTEGER,
   mscTrkUnAckedOperationalState
      INTEGER,
   mscTrkUnAckedUsageState
      INTEGER,
   mscTrkUnAckedAvailabilityStatus
      OCTET STRING,
   mscTrkUnAckedProceduralStatus
      OCTET STRING,
   mscTrkUnAckedControlStatus
      OCTET STRING,
   mscTrkUnAckedAlarmStatus
      OCTET STRING,
   mscTrkUnAckedStandbyStatus
      INTEGER,
   mscTrkUnAckedUnknownStatus
      INTEGER }

mscTrkUnAckedAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock -force or 
      Lock command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component.
      
      The OSI Status attributes, if supported by the component, may 
      provide more details, qualifying the state of the component."
   DEFVAL     { unlocked }
::= { mscTrkUnAckedStateEntry 1 }

mscTrkUnAckedOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle.
      
      The OSI Status attributes, if supported by the component, may 
      provide more details, qualifying the state of the component."
   DEFVAL     { disabled }
::= { mscTrkUnAckedStateEntry 2 }

mscTrkUnAckedUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time.
      
      The OSI Status attributes, if supported by the component, may 
      provide more details, qualifying the state of the component."
   DEFVAL     { idle }
::= { mscTrkUnAckedStateEntry 3 }

mscTrkUnAckedAvailabilityStatus OBJECT-TYPE
   SYNTAX     OCTET STRING (SIZE (2))
   ACCESS     read-only
   STATUS     mandatory
   DESCRIPTION
     "If supported by the component, this attribute indicates the OSI 
      Availability status of the component. Note that, even though it is 
      defined as a multi-valued set, at most one value is shown to the user.
      
      When no values are in the set, this indicates that either the attribute 
      is not supported or that none of the status conditions described 
      below is present.
      
      The value inTest indicates that the resource is undergoing a test 
      procedure. If adminState is locked or shuttingDown, the normal 
      users are precluded from using the resource and controlStatus is 
      reservedForTest. Tests that do not exclude additional users can be 
      present in any operational or administrative state but the 
      reservedForTest condition should not be present.
      
      The value failed indicates that the component has an internal fault 
      that prevents it from operating. The operationalState is disabled.
      
      The value dependency indicates that the component cannot operate 
      because some other resource on which it depends is unavailable. 
      The operationalState is disabled.
      
      The value powerOff indicates the resource requires power to be 
      applied and it is not powered on. The operationalState is disabled.
      
      The value offLine indicates the resource requires a routine 
      operation (either manual, automatic, or both) to be performed to 
      place it on-line and make it available for use. The operationalState 
      is disabled.
      
      The value offDuty indicates the resource is inactive in accordance 
      with a predetermined time schedule. In the absence of other 
      disabling conditions, the operationalState is enabled or disabled.
      
      The value degraded indicates the service provided by the 
      component is degraded in some way, such as in speed or operating 
      capacity. Usually, the resource remains available for service. The 
      operationalState is almost always enabled. There is one exception 
      where an operationalState of disabled is used in conjunction with 
      degraded for a component which represents a rolled up view of a 
      set of other components.
      
      The value notInstalled indicates the resource is not present. The 
      operationalState is disabled.
      
      The value logFull is not used.
      
      The value migrating indicates that a software migration activation 
      is in progress, making the component unavailable for other 
      activities until the migration is complete.

      Description of bits:
      inTest(0)
      failed(1)
      powerOff(2)
      offLine(3)
      offDuty(4)
      dependency(5)
      degraded(6)
      notInstalled(7)
      logFull(8)
      migrating(9)"
::= { mscTrkUnAckedStateEntry 4 }

mscTrkUnAckedProceduralStatus OBJECT-TYPE
   SYNTAX     OCTET STRING (SIZE (1))
   ACCESS     read-only
   STATUS     mandatory
   DESCRIPTION
     "If supported by the component, this attribute indicates the OSI 
      Procedural status of the component. Note that, even though it is 
      defined as a multi-valued set, at most one value is shown to the user.
      
      When no values are in the set, this indicates that either the attribute 
      is not supported or that none of the status conditions described 
      below is present.
      
      The value initializationRequired indicates (for a resource which 
      doesn't initialize autonomously) that initialization is required before 
      it can perform its normal functions, and this procedure has not been 
      initiated. The operationalState is disabled.
      
      The value notInitialized indicates (for a resource which does 
      initialize autonomously) that initialization is required before it can 
      perform its normal functions, and this procedure has not been 
      initiated. The operationalState may be enabled or disabled.
      
      The value initializing indicates that initialization has been initiated 
      but is not yet complete. The operationalState may be enabled or 
      disabled.
      
      The value reporting indicates the resource has completed some 
      processing operation and is notifying the results. The 
      operationalState is enabled.
      
      The value terminating indicates the component is in a termination 
      phase. If the resource doesn't reinitialize autonomously, 
      operationalState is disabled; otherwise it is enabled or disabled.

      Description of bits:
      initializationRequired(0)
      notInitialized(1)
      initializing(2)
      reporting(3)
      terminating(4)"
::= { mscTrkUnAckedStateEntry 5 }

mscTrkUnAckedControlStatus OBJECT-TYPE
   SYNTAX     OCTET STRING (SIZE (1))
   ACCESS     read-only
   STATUS     mandatory
   DESCRIPTION
     "If supported by the component, this attribute indicates the OSI 
      Control status of the component. Note that, even though it is defined 
      as a multi-valued set, at most one value is shown to the user.
      
      When no values are in the set, this indicates that either the attribute 
      is not supported or that none of the status conditions described 
      below is present.
      
      The value subjectToTest indicates the resource is available but tests 
      may be conducted simultaneously at unpredictable times, which 
      may cause it to exhibit unusual characteristics.
      
      The value partOfServicesLocked indicates that part of the service is 
      restricted from users of a resource. The adminState is unlocked.
      
      The value reservedForTest indicates that the component is 
      administratively unavailable because it is undergoing a test 
      procedure. The adminState is locked.
      
      The value suspended indicates that the service has been 
      administratively suspended.

      Description of bits:
      subjectToTest(0)
      partOfServicesLocked(1)
      reservedForTest(2)
      suspended(3)"
::= { mscTrkUnAckedStateEntry 6 }

mscTrkUnAckedAlarmStatus OBJECT-TYPE
   SYNTAX     OCTET STRING (SIZE (1))
   ACCESS     read-only
   STATUS     mandatory
   DESCRIPTION
     "If supported by the component, this attribute indicates the OSI 
      Alarm status of the component. Note that, even though it is defined 
      as a multi-valued set, at most one value is shown to the user.
      
      When no values are in the set, this indicates that either the attribute 
      is not supported or that none of the status conditions described 
      below is present.
      
      The value underRepair indicates the component is currently being 
      repaired. The operationalState is enabled or disabled.
      
      The value critical indicates one or more critical alarms are 
      outstanding against the component. Other, less severe, alarms may 
      also be outstanding. The operationalState is enabled or disabled.
      
      The value major indicates one or more major alarms are 
      outstanding against the component. Other, less severe, alarms may 
      also be outstanding. The operationalState is enabled or disabled.
      
      The value minor indicates one or more minor alarms are 
      outstanding against the component. Other, less severe, alarms may 
      also be outstanding. The operationalState is enabled or disabled.
      
      The value alarmOutstanding generically indicates that an alarm of 
      some severity is outstanding against the component.

      Description of bits:
      underRepair(0)
      critical(1)
      major(2)
      minor(3)
      alarmOutstanding(4)"
::= { mscTrkUnAckedStateEntry 7 }

mscTrkUnAckedStandbyStatus OBJECT-TYPE
   SYNTAX     INTEGER  {
                 hotStandby(0),
                 coldStandby(1),
                 providingService(2),
                 notSet(15) }
   ACCESS     read-only
   STATUS     mandatory
   DESCRIPTION
     "If supported by the component, this attribute indicates the OSI 
      Standby status of the component.
      
      The value notSet indicates that either the attribute is not supported 
      or that none of the status conditions described below is present. 
      Note that this is a non-standard value, used because the original 
      specification indicated this attribute was set-valued and thus, did not 
      provide a value to indicate that none of the other three are 
      applicable.
      
      The value hotStandby indicates that the resource is not providing 
      service but will be immediately able to take over the role of the 
      resource to be backed up, without initialization activity, and 
      containing the same information as the resource to be backed up.
      
      The value coldStandby indicates the resource is a backup for 
      another resource but will not be immediately able to take over the 
      role of the backed up resource and will require some initialization 
      activity.
      
      The value providingService indicates that this component, as a 
      backup resource, is currently backing up another resource."
   DEFVAL     { notSet }
::= { mscTrkUnAckedStateEntry 8 }

mscTrkUnAckedUnknownStatus OBJECT-TYPE
   SYNTAX     INTEGER  {
                 false(0),
                 true(1) }
   ACCESS     read-only
   STATUS     mandatory
   DESCRIPTION
     "This attribute indicates the OSI Unknown status of the component.
      
      The value false indicates that all of the other OSI State and Status 
      attribute values can be considered accurate.
      
      The value true indicates that the actual state of the component is not 
      known for sure."
   DEFVAL     { false }
::= { mscTrkUnAckedStateEntry 9 }


-- 
-- Trunk/n Unack Framer
-- 
-- The Framer component controls link layer framing for application 
-- components sending and receiving data on a link interface. It is also 
-- through Framer, that an application component is associated with a 
-- specific hardware link interface.
-- 
-- The Framer component provides provisionable attributes related to 
-- datapath aspects of the hardware interface (such as crc and frame 
-- length) rather than interface specific attributes (such as modem 
-- leads and clocking) which are associated with specific hardware 
-- components (such as V35/n or DS1/n). The Framer component also 
-- provides a provisionable attribute which binds the application 
-- component to a specific hardware component.
-- 
-- The Framer component contains operational attributes for link 
-- interface datapath statistics (such as frame counts and aborts).
-- 

mscTrkUnAckedFramer OBJECT IDENTIFIER ::= { mscTrkUnAcked 2 }



mscTrkUnAckedFramerRowStatusTable OBJECT-TYPE
   SYNTAX     SEQUENCE OF MscTrkUnAckedFramerRowStatusEntry
   ACCESS     not-accessible
   STATUS     mandatory
   DESCRIPTION
     "This entry controls the addition and deletion of 
      mscTrkUnAckedFramer components."
::= { mscTrkUnAckedFramer 1 }

mscTrkUnAckedFramerRowStatusEntry OBJECT-TYPE
   SYNTAX     MscTrkUnAckedFramerRowStatusEntry
   ACCESS     not-accessible
   STATUS     mandatory
   DESCRIPTION
     "A single entry in the table represents a single 
      mscTrkUnAckedFramer component."
   INDEX {
      mscTrkIndex,
      mscTrkUnAckedIndex,
      mscTrkUnAckedFramerIndex }
::= { mscTrkUnAckedFramerRowStatusTable 1 }

MscTrkUnAckedFramerRowStatusEntry ::= SEQUENCE {
   mscTrkUnAckedFramerRowStatus
      RowStatus,
   mscTrkUnAckedFramerComponentName
      DisplayString,
   mscTrkUnAckedFramerStorageType
      StorageType,
   mscTrkUnAckedFramerIndex
      NonReplicated }

mscTrkUnAckedFramerRowStatus OBJECT-TYPE
   SYNTAX     RowStatus 
   ACCESS     read-only
   STATUS     mandatory
   DESCRIPTION
     "This variable is used as the basis for SNMP naming of
      mscTrkUnAckedFramer components.
      These components cannot be added nor deleted."
::= { mscTrkUnAckedFramerRowStatusEntry 1 }

mscTrkUnAckedFramerComponentName OBJECT-TYPE
   SYNTAX     DisplayString 
   ACCESS     read-only
   STATUS     mandatory
   DESCRIPTION
     "This variable provides the component's string name for
      use with the ASCII Console Interface"
::= { mscTrkUnAckedFramerRowStatusEntry 2 }

mscTrkUnAckedFramerStorageType OBJECT-TYPE
   SYNTAX     StorageType 
   ACCESS     read-only
   STATUS     mandatory
   DESCRIPTION
     "This variable represents the storage type value for the
      mscTrkUnAckedFramer tables."
::= { mscTrkUnAckedFramerRowStatusEntry 4 }

mscTrkUnAckedFramerIndex OBJECT-TYPE
   SYNTAX     NonReplicated 
   ACCESS     not-accessible
   STATUS     mandatory
   DESCRIPTION
     "This variable represents the index for the mscTrkUnAckedFramer tables."
::= { mscTrkUnAckedFramerRowStatusEntry 10 }

mscTrkUnAckedFramerProvTable OBJECT-TYPE
   SYNTAX     SEQUENCE OF MscTrkUnAckedFramerProvEntry
   ACCESS     not-accessible
   STATUS     mandatory
   DESCRIPTION
     "This group contains the base provisioning data for the Framer 
      component. Application or hardware interface specific provisioning 
      data is contained in other provisionable Framer groups."
::= { mscTrkUnAckedFramer 10 }

mscTrkUnAckedFramerProvEntry OBJECT-TYPE
   SYNTAX     MscTrkUnAckedFramerProvEntry
   ACCESS     not-accessible
   STATUS     mandatory
   DESCRIPTION
     "An entry in the mscTrkUnAckedFramerProvTable."
   INDEX {
      mscTrkIndex,
      mscTrkUnAckedIndex,
      mscTrkUnAckedFramerIndex }
::= { mscTrkUnAckedFramerProvTable 1 }

MscTrkUnAckedFramerProvEntry ::= SEQUENCE {
   mscTrkUnAckedFramerInterfaceName
      Link }

mscTrkUnAckedFramerInterfaceName OBJECT-TYPE
   SYNTAX     Link 
   ACCESS     read-write
   STATUS     mandatory
   DESCRIPTION
     "This attribute contains a hardware component name.
      
      The attribute associates the application with a specific link. This 
      defines the module processor on which Framer's parent component 
      (as well as Framer itself) will run."
::= { mscTrkUnAckedFramerProvEntry 1 }

mscTrkUnAckedFramerLinkTable OBJECT-TYPE
   SYNTAX     SEQUENCE OF MscTrkUnAckedFramerLinkEntry
   ACCESS     not-accessible
   STATUS     mandatory
   DESCRIPTION
     "This group contains attributes defining the framing of data on the 
      link interface."
::= { mscTrkUnAckedFramer 11 }

mscTrkUnAckedFramerLinkEntry OBJECT-TYPE
   SYNTAX     MscTrkUnAckedFramerLinkEntry
   ACCESS     not-accessible
   STATUS     mandatory
   DESCRIPTION
     "An entry in the mscTrkUnAckedFramerLinkTable."
   INDEX {
      mscTrkIndex,
      mscTrkUnAckedIndex,
      mscTrkUnAckedFramerIndex }
::= { mscTrkUnAckedFramerLinkTable 1 }

MscTrkUnAckedFramerLinkEntry ::= SEQUENCE {
   mscTrkUnAckedFramerFramingType
      INTEGER,
   mscTrkUnAckedFramerDataInversion
      INTEGER,
   mscTrkUnAckedFramerFrameCrcType
      INTEGER,
   mscTrkUnAckedFramerFlagsBetweenFrames
      Unsigned32 }

mscTrkUnAckedFramerFramingType OBJECT-TYPE
   SYNTAX     INTEGER  {
                 hdlc(0),
                 interrupting(1) }
   ACCESS     read-write
   STATUS     mandatory
   DESCRIPTION
     "This attribute specifies the type of framing protocol that will be 
      used for frames transmitted to the link interface and received from 
      the link interface. If the value of this attribute is set to the default 
      interrupting, then a Proprietary hdlc protocol is used which allows 
      for voice cells to interrupt transmission of data frames, transmit the 
      voice cell, and then continue transmitting the data frame. If the 
      value of this attribute is set to hdlc, then the standard hdlc procotol 
      is used for the sequential transmission of individual frames."
   DEFVAL     { interrupting }
::= { mscTrkUnAckedFramerLinkEntry 1 }

mscTrkUnAckedFramerDataInversion OBJECT-TYPE
   SYNTAX     INTEGER  {
                 off(0),
                 on(16) }
   ACCESS     read-write
   STATUS     mandatory
   DESCRIPTION
     "This attribute determines whether data bits are to be inverted (1 to 0 
      and 0 to 1) before transmission of frames to the interface. If the 
      value of this attribute is On, the incoming data bits will also be 
      inverted when frames are received from the link before being 
      processed.
      
      This option is typically used in hdlc framing mode when inversion 
      is used to guarantee 1's density.
      
      Note that aborts (in hdlc and interrupting modes) are corrupted 
      when data is inverted."
   DEFVAL     { off }
::= { mscTrkUnAckedFramerLinkEntry 2 }

mscTrkUnAckedFramerFrameCrcType OBJECT-TYPE
   SYNTAX     INTEGER  {
                 crc16(0),
                 crc32(1),
                 noCrc(2) }
   ACCESS     read-write
   STATUS     mandatory
   DESCRIPTION
     "This attribute defines the type of CRC used. 
      
      The CRC value calculated is appended to the end of the frames 
      transmitted to the link. The CRC value is removed from the end of 
      frames received from the link and checked for correctness.
      NoCrc means that CRC is not used."
   DEFVAL     { crc16 }
::= { mscTrkUnAckedFramerLinkEntry 3 }

mscTrkUnAckedFramerFlagsBetweenFrames OBJECT-TYPE
   SYNTAX     Unsigned32 (1..16)
   ACCESS     read-write
   STATUS     mandatory
   DESCRIPTION
     "This attribute defines the number of flags that are inserted between 
      frames sent to the link interface."
   DEFVAL     { 1 }
::= { mscTrkUnAckedFramerLinkEntry 4 }

mscTrkUnAckedFramerStateTable OBJECT-TYPE
   SYNTAX     SEQUENCE OF MscTrkUnAckedFramerStateEntry
   ACCESS     not-accessible
   STATUS     mandatory
   DESCRIPTION
     "This group contains the three OSI State attributes. The descriptions 
      generically indicate what each state attribute implies about the 
      component. Note that not all the values and state combinations 
      described here are supported by every component which reuses this 
      group. For component-specific information and the valid state 
      combinations, refer to the appropriate NTP."
::= { mscTrkUnAckedFramer 12 }

mscTrkUnAckedFramerStateEntry OBJECT-TYPE
   SYNTAX     MscTrkUnAckedFramerStateEntry
   ACCESS     not-accessible
   STATUS     mandatory
   DESCRIPTION
     "An entry in the mscTrkUnAckedFramerStateTable."
   INDEX {
      mscTrkIndex,
      mscTrkUnAckedIndex,
      mscTrkUnAckedFramerIndex }
::= { mscTrkUnAckedFramerStateTable 1 }

MscTrkUnAckedFramerStateEntry ::= SEQUENCE {
   mscTrkUnAckedFramerAdminState
      INTEGER,
   mscTrkUnAckedFramerOperationalState
      INTEGER,
   mscTrkUnAckedFramerUsageState
      INTEGER }

mscTrkUnAckedFramerAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock -force or 
      Lock command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { mscTrkUnAckedFramerStateEntry 1 }

mscTrkUnAckedFramerOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { mscTrkUnAckedFramerStateEntry 2 }

mscTrkUnAckedFramerUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { mscTrkUnAckedFramerStateEntry 3 }

mscTrkUnAckedFramerStatsTable OBJECT-TYPE
   SYNTAX     SEQUENCE OF MscTrkUnAckedFramerStatsEntry
   ACCESS     not-accessible
   STATUS     mandatory
   DESCRIPTION
     "This group contains the operational statistics data for a 
      Unacknowledge Framer component."
::= { mscTrkUnAckedFramer 13 }

mscTrkUnAckedFramerStatsEntry OBJECT-TYPE
   SYNTAX     MscTrkUnAckedFramerStatsEntry
   ACCESS     not-accessible
   STATUS     mandatory
   DESCRIPTION
     "An entry in the mscTrkUnAckedFramerStatsTable."
   INDEX {
      mscTrkIndex,
      mscTrkUnAckedIndex,
      mscTrkUnAckedFramerIndex }
::= { mscTrkUnAckedFramerStatsTable 1 }

MscTrkUnAckedFramerStatsEntry ::= SEQUENCE {
   mscTrkUnAckedFramerFrmToIf
      Counter32,
   mscTrkUnAckedFramerFrmFromIf
      Counter32,
   mscTrkUnAckedFramerOctetFromIf
      Counter32,
   mscTrkUnAckedFramerAborts
      Counter32,
   mscTrkUnAckedFramerCrcErrors
      Counter32,
   mscTrkUnAckedFramerLrcErrors
      Counter32,
   mscTrkUnAckedFramerNonOctetErrors
      Counter32,
   mscTrkUnAckedFramerOverruns
      Counter32,
   mscTrkUnAckedFramerUnderruns
      Counter32,
   mscTrkUnAckedFramerLargeFrmErrors
      Counter32,
   mscTrkUnAckedFramerFrmModeErrors
      Counter32,
   mscTrkUnAckedFramerOutOfSequenceFrm
      Counter32,
   mscTrkUnAckedFramerRepeatedFrm
      Counter32,
   mscTrkUnAckedFramerFrmFromIf64
      PassportCounter64,
   mscTrkUnAckedFramerOctetFromIf64
      PassportCounter64 }

mscTrkUnAckedFramerFrmToIf OBJECT-TYPE
   SYNTAX     Counter32 
   ACCESS     read-only
   STATUS     obsolete
   DESCRIPTION
     "The number of frames transmitted to the link interface by Framer.
      
      Note: This does not include the number of frames transmitted 
      directly to the hardware queue, thus bypassing the Framer 
      component."
::= { mscTrkUnAckedFramerStatsEntry 1 }

mscTrkUnAckedFramerFrmFromIf OBJECT-TYPE
   SYNTAX     Counter32 
   ACCESS     read-only
   STATUS     obsolete
   DESCRIPTION
     "The number of frames received from the link interface by Framer."
::= { mscTrkUnAckedFramerStatsEntry 2 }

mscTrkUnAckedFramerOctetFromIf OBJECT-TYPE
   SYNTAX     Counter32 
   ACCESS     read-only
   STATUS     obsolete
   DESCRIPTION
     "The number of bytes received from the link interface by Framer."
::= { mscTrkUnAckedFramerStatsEntry 3 }

mscTrkUnAckedFramerAborts OBJECT-TYPE
   SYNTAX     Counter32 
   ACCESS     read-only
   STATUS     mandatory
   DESCRIPTION
     "This attribute is the total number of aborts received."
::= { mscTrkUnAckedFramerStatsEntry 4 }

mscTrkUnAckedFramerCrcErrors OBJECT-TYPE
   SYNTAX     Counter32 
   ACCESS     read-only
   STATUS     mandatory
   DESCRIPTION
     "This attribute is the total number of frames with with CRC errors."
::= { mscTrkUnAckedFramerStatsEntry 5 }

mscTrkUnAckedFramerLrcErrors OBJECT-TYPE
   SYNTAX     Counter32 
   ACCESS     read-only
   STATUS     mandatory
   DESCRIPTION
     "This attribute is the total number of frames with LRC errors."
::= { mscTrkUnAckedFramerStatsEntry 6 }

mscTrkUnAckedFramerNonOctetErrors OBJECT-TYPE
   SYNTAX     Counter32 
   ACCESS     read-only
   STATUS     mandatory
   DESCRIPTION
     "This attribute is the total number of frames that were non octet 
      aligned."
::= { mscTrkUnAckedFramerStatsEntry 7 }

mscTrkUnAckedFramerOverruns OBJECT-TYPE
   SYNTAX     Counter32 
   ACCESS     read-only
   STATUS     mandatory
   DESCRIPTION
     "This attribute is the total number of frames received from the link 
      for which overruns occurred."
::= { mscTrkUnAckedFramerStatsEntry 8 }

mscTrkUnAckedFramerUnderruns OBJECT-TYPE
   SYNTAX     Counter32 
   ACCESS     read-only
   STATUS     mandatory
   DESCRIPTION
     "This attribute is the total number of frames transmitted to the link 
      for which underruns occurred."
::= { mscTrkUnAckedFramerStatsEntry 9 }

mscTrkUnAckedFramerLargeFrmErrors OBJECT-TYPE
   SYNTAX     Counter32 
   ACCESS     read-only
   STATUS     mandatory
   DESCRIPTION
     "This attribute is the total number of frames received which were too 
      large. The frame execeeded the maximumFrameLengthLimit 
      provisioned attribute or it contained more than the 255 block 
      hardware limit."
::= { mscTrkUnAckedFramerStatsEntry 10 }

mscTrkUnAckedFramerFrmModeErrors OBJECT-TYPE
   SYNTAX     Counter32 
   ACCESS     read-only
   STATUS     mandatory
   DESCRIPTION
     "This attribute is the total number of frames detected with framing 
      mode errors. A framingModeError is flagged when frames are 
      inconsistent with the specified framingType, that is when 
      interrupting frames are used while running in hdlc mode."
::= { mscTrkUnAckedFramerStatsEntry 11 }

mscTrkUnAckedFramerOutOfSequenceFrm OBJECT-TYPE
   SYNTAX     Counter32 
   ACCESS     read-only
   STATUS     mandatory
   DESCRIPTION
     "This attribute is the total number of out of sequence frames in 
      interrupting mode that have been received from the link."
::= { mscTrkUnAckedFramerStatsEntry 12 }

mscTrkUnAckedFramerRepeatedFrm OBJECT-TYPE
   SYNTAX     Counter32 
   ACCESS     read-only
   STATUS     mandatory
   DESCRIPTION
     "This attribute is the total number of repeated frames (frames with 
      the same sequence number) in interrupting mode that have been 
      received from the link."
::= { mscTrkUnAckedFramerStatsEntry 13 }

mscTrkUnAckedFramerFrmFromIf64 OBJECT-TYPE
   SYNTAX     PassportCounter64 
   ACCESS     read-only
   STATUS     mandatory
   DESCRIPTION
     "The number of frames received from the link interface by Framer."
::= { mscTrkUnAckedFramerStatsEntry 15 }

mscTrkUnAckedFramerOctetFromIf64 OBJECT-TYPE
   SYNTAX     PassportCounter64 
   ACCESS     read-only
   STATUS     mandatory
   DESCRIPTION
     "The number of bytes received from the link interface by Framer."
::= { mscTrkUnAckedFramerStatsEntry 16 }

mscTrkUnAckedFramerUtilTable OBJECT-TYPE
   SYNTAX     SEQUENCE OF MscTrkUnAckedFramerUtilEntry
   ACCESS     not-accessible
   STATUS     mandatory
   DESCRIPTION
     "This group contains the link utilization operational data for a 
      Framer component."
::= { mscTrkUnAckedFramer 14 }

mscTrkUnAckedFramerUtilEntry OBJECT-TYPE
   SYNTAX     MscTrkUnAckedFramerUtilEntry
   ACCESS     not-accessible
   STATUS     mandatory
   DESCRIPTION
     "An entry in the mscTrkUnAckedFramerUtilTable."
   INDEX {
      mscTrkIndex,
      mscTrkUnAckedIndex,
      mscTrkUnAckedFramerIndex }
::= { mscTrkUnAckedFramerUtilTable 1 }

MscTrkUnAckedFramerUtilEntry ::= SEQUENCE {
   mscTrkUnAckedFramerNormPrioLinkUtilToIf
      Gauge32,
   mscTrkUnAckedFramerHighPrioLinkUtilToIf
      Gauge32,
   mscTrkUnAckedFramerNormPrioLinkUtilFromIf
      Gauge32,
   mscTrkUnAckedFramerHighPrioLinkUtilFromIf
      Gauge32 }

mscTrkUnAckedFramerNormPrioLinkUtilToIf OBJECT-TYPE
   SYNTAX     Gauge32 (0..100)
   ACCESS     read-only
   STATUS     mandatory
   DESCRIPTION
     "This attribute is the utilization of the normal and high priority data 
      traffic (interruptable traffic) sent to the link as a percentage of the 
      available bandwidth on the link. Note that this includes traffic with 
      Transfer Priorities (TP) of 0, 6 and 9 and/or Emission Priority of 2 
      and 3. The utilization is the average for the last minute."
   DEFVAL     { 0 }
::= { mscTrkUnAckedFramerUtilEntry 1 }

mscTrkUnAckedFramerHighPrioLinkUtilToIf OBJECT-TYPE
   SYNTAX     Gauge32 (0..100)
   ACCESS     read-only
   STATUS     mandatory
   DESCRIPTION
     "This attribute is the utilization of the interrupting data traffic sent to 
      the link as a percentage of the available bandwidth on the link. Note 
      that this includes traffic with a Transfer Priority (TP) of 11 and/or 
      Emission Priority of 1. The utilization is the average for the last 
      minute."
   DEFVAL     { 0 }
::= { mscTrkUnAckedFramerUtilEntry 2 }

mscTrkUnAckedFramerNormPrioLinkUtilFromIf OBJECT-TYPE
   SYNTAX     Gauge32 (0..100)
   ACCESS     read-only
   STATUS     mandatory
   DESCRIPTION
     "This attribute is the utilization of the normal and high priority data 
      traffic (interruptable traffic) received from the link as a percentage 
      of the available bandwidth on the link. Note that this includes traffic 
      with Transfer Priorities (TP) of 0, 6 and 9 and/or Emission Priority 
      of 2 and 3. The utilization is the average for the last minute."
   DEFVAL     { 0 }
::= { mscTrkUnAckedFramerUtilEntry 3 }

mscTrkUnAckedFramerHighPrioLinkUtilFromIf OBJECT-TYPE
   SYNTAX     Gauge32 (0..100)
   ACCESS     read-only
   STATUS     mandatory
   DESCRIPTION
     "This attribute is the utilization of the interrupting data traffic 
      received from the link as a percentage of the available bandwidth on 
      the link. Note that this includes traffic with a Transfer Priority (TP) 
      of 11 and/or Emission Priority of 1. The utilization is the average 
      for the last minute."
   DEFVAL     { 0 }
::= { mscTrkUnAckedFramerUtilEntry 4 }

mscTrkUnAckedFramerUtilThresholdTable OBJECT-TYPE
   SYNTAX     SEQUENCE OF MscTrkUnAckedFramerUtilThresholdEntry
   ACCESS     not-accessible
   STATUS     mandatory
   DESCRIPTION
     "This group contains all of the provisioning data required to set the 
      link utilization alarm thresholds. All thresholds are percentages 
      which can take on any value in the range of 0% through 100%. The 
      value 100% is used to disable an individual threshold. For values 
      other than 100%, a semantic check ensures that the minor alarm 
      threshold is less than the other thresholds and that the major alarm 
      threshold is less than the critical alarm threshold."
::= { mscTrkUnAckedFramer 15 }

mscTrkUnAckedFramerUtilThresholdEntry OBJECT-TYPE
   SYNTAX     MscTrkUnAckedFramerUtilThresholdEntry
   ACCESS     not-accessible
   STATUS     mandatory
   DESCRIPTION
     "An entry in the mscTrkUnAckedFramerUtilThresholdTable."
   INDEX {
      mscTrkIndex,
      mscTrkUnAckedIndex,
      mscTrkUnAckedFramerIndex }
::= { mscTrkUnAckedFramerUtilThresholdTable 1 }

MscTrkUnAckedFramerUtilThresholdEntry ::= SEQUENCE {
   mscTrkUnAckedFramerMinorLinkUtilAlarmThreshold
      Unsigned32,
   mscTrkUnAckedFramerMajorLinkUtilAlarmThreshold
      Unsigned32,
   mscTrkUnAckedFramerCriticalLinkUtilAlarmThreshold
      Unsigned32,
   mscTrkUnAckedFramerLinkUtilAlarmStatus
      INTEGER }

mscTrkUnAckedFramerMinorLinkUtilAlarmThreshold OBJECT-TYPE
   SYNTAX     Unsigned32 (0..100)
   ACCESS     read-write
   STATUS     mandatory
   DESCRIPTION
     "This attribute provides the threshold value which defines when a 
      minor alarm would be issued, denoting a sustained total average 
      link utilization. The total average link utilization is calculated based 
      on the number of received bytes. The Set alarm is issued after 3 
      minutes of utilization greater than the given threshold. The 
      corresponding Clear alarm is issued after a subsequent 3 minutes of 
      utilization less than or equal to the given threshold.
      The value 100% is used to disable an individual threshold. For 
      values other than 100%, a semantic check ensures that the minor 
      alarm threshold is less than the other thresholds."
   DEFVAL     { 75 }
::= { mscTrkUnAckedFramerUtilThresholdEntry 1 }

mscTrkUnAckedFramerMajorLinkUtilAlarmThreshold OBJECT-TYPE
   SYNTAX     Unsigned32 (0..100)
   ACCESS     read-write
   STATUS     mandatory
   DESCRIPTION
     "This attribute provides the threshold value which defines when a 
      major alarm would be issued, denoting a sustained total average 
      link utilization. The total average link utilization is calculated based 
      on the number of received bytes. The Set alarm is issued after 3 
      minutes of utilization greater than the given threshold. The 
      corresponding Clear alarm is issued after a subsequent 3 minutes of 
      utilization less than or equal to the given threshold.
      The value 100% is used to disable an individual threshold. For 
      values other than 100%, a semantic check ensures that the major 
      alarm threshold is greater than the minor threshold and less than the 
      critical threshold."
   DEFVAL     { 85 }
::= { mscTrkUnAckedFramerUtilThresholdEntry 2 }

mscTrkUnAckedFramerCriticalLinkUtilAlarmThreshold OBJECT-TYPE
   SYNTAX     Unsigned32 (0..100)
   ACCESS     read-write
   STATUS     mandatory
   DESCRIPTION
     "This attribute provides the threshold value which defines when a 
      critical alarm would be issued, denoting a sustained total average 
      link utilization. The total average link utilization is calculated based 
      on the number of received bytes. The Set alarm is issued after 3 
      minutes of utilization greater than the given threshold. The 
      corresponding Clear alarm is issued after a subsequent 3 minutes of 
      utilization less than or equal to the given threshold.
      The value 100% is used to disable an individual threshold. For 
      values other than 100%, a semantic check ensures that the critical 
      alarm threshold is greater than the other thresholds."
   DEFVAL     { 95 }
::= { mscTrkUnAckedFramerUtilThresholdEntry 3 }

mscTrkUnAckedFramerLinkUtilAlarmStatus OBJECT-TYPE
   SYNTAX     INTEGER  {
                 disabled(0),
                 enabled(1) }
   ACCESS     read-write
   STATUS     mandatory
   DESCRIPTION
     "This attribute provides control of the generation of link utilization 
      alarms. If the value is disabled, none of the alarms are generated 
      (this is equivalent to setting all of the thresholds to 100%). If the 
      value is enabled, the individual thresholds are handled."
   DEFVAL     { disabled }
::= { mscTrkUnAckedFramerUtilThresholdEntry 4 }




-- 
-- Version and Compliance statements
-- 



-- Object-Group Statement:
-- A list of all current accessible leaf objects.

-- OBJECTS { mscTrkUnAckedMaximumErroredInterval,
--           mscTrkUnAckedFramerLrcErrors,
--           mscTrkUnAckedFramerMajorLinkUtilAlarmThreshold,
--           mscTrkUnAckedControlStatus,
--           mscTrkUnAckedAdminState,
--           mscTrkUnAckedFramerFrmFromIf64,
--           mscTrkUnAckedFramerRowStatus,
--           mscTrkUnAckedFramerStorageType,
--           mscTrkUnAckedFramerAborts,
--           mscTrkUnAckedRowStatus,
--           mscTrkUnAckedFramerOverruns,
--           mscTrkUnAckedFramerLargeFrmErrors,
--           mscTrkUnAckedFramerCrcErrors,
--           mscTrkUnAckedProceduralStatus,
--           mscTrkUnAckedFramerLinkUtilAlarmStatus,
--           mscTrkUnAckedAvailabilityStatus,
--           mscTrkUnAckedFramerNonOctetErrors,
--           mscTrkUnAckedFramerOctetFromIf64,
--           mscTrkUnAckedFramerCriticalLinkUtilAlarmThreshold,
--           mscTrkUnAckedFramerUsageState,
--           mscTrkUnAckedFramerOutOfSequenceFrm,
--           mscTrkUnAckedFramerNormPrioLinkUtilFromIf,
--           mscTrkUnAckedFramerRepeatedFrm,
--           mscTrkUnAckedAlarmStatus,
--           mscTrkUnAckedUsageState,
--           mscTrkUnAckedFramerUnderruns,
--           mscTrkUnAckedFramerInterfaceName,
--           mscTrkUnAckedUnknownStatus,
--           mscTrkUnAckedStandbyStatus,
--           mscTrkUnAckedFramerComponentName,
--           mscTrkUnAckedFramerFramingType,
--           mscTrkUnAckedComponentName,
--           mscTrkUnAckedFramerFlagsBetweenFrames,
--           mscTrkUnAckedStorageType,
--           mscTrkUnAckedFramerOperationalState,
--           mscTrkUnAckedFramerDataInversion,
--           mscTrkUnAckedFramerHighPrioLinkUtilFromIf,
--           mscTrkUnAckedFramerHighPrioLinkUtilToIf,
--           mscTrkUnAckedOperationalState,
--           mscTrkUnAckedFramerFrmModeErrors,
--           mscTrkUnAckedFramerMinorLinkUtilAlarmThreshold,
--           mscTrkUnAckedFramerNormPrioLinkUtilToIf,
--           mscTrkUnAckedReceiveErrorSensitivity,
--           mscTrkUnAckedFramerFrameCrcType,
--           mscTrkUnAckedFramerAdminState }
-- STATUS  mandatory
-- DESCRIPTION
--   "A list of all current accessible leaf objects."

unackTrunksGroup OBJECT IDENTIFIER ::= { unackTrunksMIB 1 }
unackTrunksGroupCB OBJECT IDENTIFIER ::= { unackTrunksGroup 2 }
unackTrunksGroupCB01 OBJECT IDENTIFIER ::= { unackTrunksGroupCB 2 }
unackTrunksGroupCB01A OBJECT IDENTIFIER ::= { unackTrunksGroupCB01 2 }



-- Agent-Capabilities Statement:

-- PRODUCT-RELEASE "MscPassport Release 2.2 UnackTrunks."
-- STATUS          mandatory
-- DESCRIPTION     "Carrier Passport UnackTrunks MIB: MIB Version CB01A,
--                  Software Version CB02S1B."
-- SUPPORTS        Nortel-MsCarrier-MscPassport-UnackTrunksMIB
--    INCLUDES     { unackTrunksGroupCB01A }

unackTrunksCapabilities OBJECT IDENTIFIER ::= { unackTrunksMIB 3 }
unackTrunksCapabilitiesCB OBJECT IDENTIFIER ::= { unackTrunksCapabilities 2 }
unackTrunksCapabilitiesCB01 OBJECT IDENTIFIER ::= { unackTrunksCapabilitiesCB 2 }
unackTrunksCapabilitiesCB01A OBJECT IDENTIFIER ::= { unackTrunksCapabilitiesCB01 2 }





END
