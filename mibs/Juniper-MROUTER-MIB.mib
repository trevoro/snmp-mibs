-- *****************************************************************************
-- Juniper-MROUTER-MIB
--
-- Juniper Networks Enterprise MIB
--   IP multicast router MIB
--
-- Copyright (c) 2002 Juniper Networks, Inc.
--   All Rights Reserved.
-- *****************************************************************************

Juniper-MROUTER-MIB  DEFINITIONS ::= BEGIN

IMPORTS
    MODULE-IDENTITY, OBJECT-TYPE, Integer32, IpAddress, Unsigned32
        FROM SNMPv2-SMI
    DisplayString, RowStatus
        FROM SNMPv2-TC
    MODULE-COMPLIANCE, OBJECT-GROUP  
        FROM SNMPv2-CONF
    juniMibs
        FROM Juniper-MIBs;

juniMRouterMIB  MODULE-IDENTITY
    LAST-UPDATED "200609021102Z"  -- 02-Sep-06 07:02 PM EDT
    ORGANIZATION "Juniper Networks, Inc."
    CONTACT-INFO
        "       Juniper Networks, Inc.
        Postal: 10 Technology Park Drive
                Westford MA  01886-3146
                USA
        Tel:    +1 978 589 5800
        Email:  mib@Juniper.net"
    DESCRIPTION
        "The IP multicast router MIB for Juniper Networks enterprise."
    -- Revision History
    REVISION    "200609021102Z"  -- 02-Sep-06 07:02 PM EDT  - JUNOSe 8.0
    DESCRIPTION
        "Scalar attribute juniMcastRpfDisable is supported in this MIB module."
    REVISION    "200210282006Z"  -- 28-Oct-02 03:06 PM EST  - JUNOSe 5.0
    DESCRIPTION
        "Initial version of this MIB module."
    ::= { juniMibs 65 }


-- +++++++++++++++++++++++++++++++++++++++++++++++++++++++++++++++++++++++++++++
-- Managed objects
-- +++++++++++++++++++++++++++++++++++++++++++++++++++++++++++++++++++++++++++++
juniMRouterMIBObject     OBJECT IDENTIFIER ::= { juniMRouterMIB 1 }
juniMcastObjects         OBJECT IDENTIFIER ::= { juniMRouterMIBObject 1 }

--
--  The static IP route table for RPF check
--
juniMcastRpfRouteTable  OBJECT-TYPE
    SYNTAX      SEQUENCE OF JuniMcastRpfRouteEntry
    MAX-ACCESS  not-accessible
    STATUS      current
    DESCRIPTION
        "The table listing the static IP routes for the mcast RPF check."
    ::= { juniMcastObjects 1 }

juniMcastRpfRouteEntry  OBJECT-TYPE
    SYNTAX      JuniMcastRpfRouteEntry 
    MAX-ACCESS  not-accessible
    STATUS      current
    DESCRIPTION
        "An entry representing the static IP route for the mcast RPF check."
    INDEX     { juniMcastRouteStaticDest,
                juniMcastRouteStaticMask }
    ::= { juniMcastRpfRouteTable 1 }

JuniMcastRpfRouteEntry ::= SEQUENCE {
    juniMcastRouteStaticDest          IpAddress,
    juniMcastRouteStaticMask          IpAddress,
    juniMcastRouteStaticRtPreference  Integer32,
    juniMcastRouteStaticRpfHop        IpAddress,
    juniMcastRouteStaticTag           Unsigned32,
    juniMcastRouteStaticRowStatus     RowStatus }

juniMcastRouteStaticDest  OBJECT-TYPE
    SYNTAX      IpAddress
    MAX-ACCESS  not-accessible
    STATUS      current
    DESCRIPTION
        "The static group's destination IpAddress."
    ::= { juniMcastRpfRouteEntry 1 }

juniMcastRouteStaticMask  OBJECT-TYPE
    SYNTAX      IpAddress
    MAX-ACCESS  not-accessible
    STATUS      current
    DESCRIPTION
        "The static group's destination IpAddress Mask."
    ::= { juniMcastRpfRouteEntry 2 }

juniMcastRouteStaticRtPreference  OBJECT-TYPE
    SYNTAX      Integer32 (0..255)
    MAX-ACCESS  read-create
    STATUS      current
    DESCRIPTION
        "The administrative distance metric."
    ::= { juniMcastRpfRouteEntry 3 }

juniMcastRouteStaticRpfHop  OBJECT-TYPE
    SYNTAX      IpAddress
    MAX-ACCESS  read-create
    STATUS      current
    DESCRIPTION
        "The next hop IP address."
    ::= { juniMcastRpfRouteEntry 4 }

juniMcastRouteStaticTag  OBJECT-TYPE
    SYNTAX      Unsigned32
    MAX-ACCESS  read-create
    STATUS      current
    DESCRIPTION
        "The tag value to be associated."
    ::= { juniMcastRpfRouteEntry 5 }

juniMcastRouteStaticRowStatus  OBJECT-TYPE
    SYNTAX      RowStatus
    MAX-ACCESS  read-create
    STATUS      current
    DESCRIPTION
        "Controls creation/deletion of entries in this table according to the
        RowStatus textual convention, constrained to support the following
        values only:
            createAndGo
            destroy

        To create an entry in this table, the following entry objects MUST be
        explicitly configured:
            juniMcastRouteStaticRowStatus
            juniMcastRouteStaticDest
            juniMcastRouteStaticMask
            juniMcastRouteStaticRtPreference
            juniMcastRouteStaticRpfHop
            juniMcastRouteStaticTag "
    ::= { juniMcastRpfRouteEntry 6 }

juniMcastRpfDisable OBJECT-TYPE
    SYNTAX      DisplayString (SIZE(0..32)) 
    MAX-ACCESS  read-write
    STATUS      current
    DESCRIPTION
        " Disable RPF check for the Group access list name. Null value for 
          enabling RPF check for the access list. "  
    ::= { juniMcastObjects 2 }

-- +++++++++++++++++++++++++++++++++++++++++++++++++++++++++++++++++++++++++++++
-- Conformance information
-- +++++++++++++++++++++++++++++++++++++++++++++++++++++++++++++++++++++++++++++
juniMcastConformance OBJECT IDENTIFIER ::= { juniMRouterMIB 2 }
juniMcastCompliances OBJECT IDENTIFIER ::= { juniMcastConformance 1 }
juniMcastConfGroups  OBJECT IDENTIFIER ::= { juniMcastConformance 2 }


--
-- compliance statements
--
juniMcastCompliance  MODULE-COMPLIANCE
    STATUS      obsolete
    DESCRIPTION
        "The compliance statement for entities which implement the Juniper
        multicast MIB."
    MODULE   -- this module
        MANDATORY-GROUPS {
            juniMcastRpfRouteConfGroup }
    ::= { juniMcastCompliances 1 }                                 -- JUNOSe 5.0

juniMcastCompliance2  MODULE-COMPLIANCE
    STATUS      current
    DESCRIPTION
        "The compliance statement for entities which implement the Juniper
        multicast MIB."
    MODULE   -- this module
        MANDATORY-GROUPS {
            juniMcastRpfRouteConfGroup,
            juniMcastGlobalConfGroup }
    ::= { juniMcastCompliances 2 }                                 -- JUNOSe 8.0


--
-- units of conformance
--
juniMcastRpfRouteConfGroup  OBJECT-GROUP
    OBJECTS {
        juniMcastRouteStaticRtPreference,
        juniMcastRouteStaticRpfHop,
        juniMcastRouteStaticTag,
        juniMcastRouteStaticRowStatus }
    STATUS      current
    DESCRIPTION
        "A collection of objects providing management of multicast RPF static
        routes of the product."
    ::= { juniMcastConfGroups 1 }

juniMcastGlobalConfGroup   OBJECT-GROUP
    OBJECTS {
        juniMcastRpfDisable }
    STATUS      current
    DESCRIPTION
        "A collection of global scalar objects providing extended information 
        of IP Multicast Route Entry."
    ::= { juniMcastConfGroups 2 }

END
