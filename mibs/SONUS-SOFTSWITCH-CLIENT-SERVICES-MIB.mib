--
-- This SMIv2 module has been generated by smidump 0.2-cvs. Do not edit.
--

SONUS-SOFTSWITCH-CLIENT-SERVICES-MIB DEFINITIONS ::= BEGIN

IMPORTS
    Counter32, Counter64, Integer32, IpAddress, MODULE-IDENTITY, 
    NOTIFICATION-TYPE, OBJECT-TYPE
        FROM SNMPv2-SMI
    DisplayString, RowStatus
        FROM SNMPv2-TC
    sonusEventClass, sonusEventDescription, sonusEventLevel
        FROM SONUS-COMMON-MIB
    sonusServicesMIBs
        FROM SONUS-SMI
    SonusName
        FROM SONUS-TC;

sonusSoftswitchClientServicesMIB MODULE-IDENTITY
    LAST-UPDATED    "200102030000Z"
    ORGANIZATION    
            "Sonus Networks, Inc."
    CONTACT-INFO    
            "   Customer Support    
             Sonus Networks, Inc,
             5 carlisle Road
             Westford, MA 01886
             USA
             
             Tel: 978-692-8999
             Fax: 978-392-9118
             E-mail: cs.snmp@sonusnet.com"
    DESCRIPTION     
            "The MIB Module for Softswitch Client Services Management."
    ::= { sonusServicesMIBs 6 }


sonusSoftswitchClientServicesMIBObjects OBJECT IDENTIFIER
    ::= { sonusSoftswitchClientServicesMIB 1 }

sonusSoftswitch OBJECT IDENTIFIER
    ::= { sonusSoftswitchClientServicesMIBObjects 1 }

sonusPscsConfigObjects OBJECT IDENTIFIER
    ::= { sonusSoftswitch 1 }

sonusPscsReconnectTimeOut OBJECT-TYPE
    SYNTAX          Integer32 (1..3600)
    MAX-ACCESS      read-write
    STATUS          current
    DESCRIPTION     
            "The timer parameter for re-attempting connection to a Softswitch  
             that is in the enabled state in seconds."
    DEFVAL          { 10 }
    ::= { sonusPscsConfigObjects 1 }

sonusPscsSwitchOver OBJECT-TYPE
    SYNTAX          INTEGER { automatic(1), manual(2) }
    MAX-ACCESS      read-write
    STATUS          current
    DESCRIPTION     
            "Automatic means retries to the previously ACTIVE Softswitch after a switch over."
    DEFVAL          { automatic }
    ::= { sonusPscsConfigObjects 2 }

sonusPscsAdmn OBJECT IDENTIFIER
    ::= { sonusSoftswitch 2 }

sonusPscsAdmnNextIndex OBJECT-TYPE
    SYNTAX          Integer32
    MAX-ACCESS      read-only
    STATUS          current
    DESCRIPTION     
            "The next valid index to use when creating a new sonusPscsAdmnEntry"
    ::= { sonusPscsAdmn 1 }

sonusPscsAdmnTable OBJECT-TYPE
    SYNTAX          SEQUENCE OF SonusPscsAdmnEntry
    MAX-ACCESS      not-accessible
    STATUS          current
    DESCRIPTION     
            "Table of Softswitch admin configurations."
    ::= { sonusPscsAdmn 2 }

sonusPscsAdmnEntry OBJECT-TYPE
    SYNTAX          SonusPscsAdmnEntry
    MAX-ACCESS      not-accessible
    STATUS          current
    DESCRIPTION     
            "List of Softswitch configuration parameters."
    INDEX           { sonusPscsPolicyServerIndex }
    ::= { sonusPscsAdmnTable 1 }

SonusPscsAdmnEntry ::=
    SEQUENCE {
        sonusPscsPolicyServerIndex      Integer32,
        sonusPscsPolicyServerName       SonusName,
        sonusPscsPolicyServerIpAddress  IpAddress,
        sonusPscsPolicyServerPortNum    Integer32,
        sonusPscsPolicyServerAdmnState  INTEGER,
        sonusPscsPolicyServerMode       INTEGER,
        sonusPscsPolicyServerAction     INTEGER,
        sonusPscsTransactionTimer       Integer32,
        sonusPscsKeepAliveTimer         Integer32,
        sonusPscsRetryTimer             Integer32,
        sonusPscsRetries                Integer32,
        sonusPscsPolicyServerRowStatus  RowStatus
    }

sonusPscsPolicyServerIndex OBJECT-TYPE
    SYNTAX          Integer32
    MAX-ACCESS      read-only
    STATUS          current
    DESCRIPTION     
            "Identifies the Softswitch entry."
    ::= { sonusPscsAdmnEntry 1 }

sonusPscsPolicyServerName OBJECT-TYPE
    SYNTAX          SonusName
    MAX-ACCESS      read-write
    STATUS          current
    DESCRIPTION     
            "The name of this Softswitch."
    ::= { sonusPscsAdmnEntry 2 }

sonusPscsPolicyServerIpAddress OBJECT-TYPE
    SYNTAX          IpAddress
    MAX-ACCESS      read-write
    STATUS          current
    DESCRIPTION     
            "IP Address of the Softswitch - this is a required parameter."
    DEFVAL          { 0 }
    ::= { sonusPscsAdmnEntry 3 }

sonusPscsPolicyServerPortNum OBJECT-TYPE
    SYNTAX          Integer32 (1..65535)
    MAX-ACCESS      read-write
    STATUS          current
    DESCRIPTION     
            "This is the port number assigned for the Ip address of the Softswitch."
    DEFVAL          { 3055 }
    ::= { sonusPscsAdmnEntry 4 }

sonusPscsPolicyServerAdmnState OBJECT-TYPE
    SYNTAX          INTEGER { disabled(1), enabled(2) }
    MAX-ACCESS      read-write
    STATUS          current
    DESCRIPTION     
            "Admin State (disabled or enabled) of the Softswitch."
    DEFVAL          { disabled }
    ::= { sonusPscsAdmnEntry 5 }

sonusPscsPolicyServerMode OBJECT-TYPE
    SYNTAX          INTEGER { active(1), standby(2), outOfService(3) }
    MAX-ACCESS      read-write
    STATUS          current
    DESCRIPTION     
            "Assignment of the Softswitch to have the active, standby or out of service role.
             This is the only parameter that may be changed when the Softswitch is ENABLED."
    DEFVAL          { outOfService }
    ::= { sonusPscsAdmnEntry 6 }

sonusPscsPolicyServerAction OBJECT-TYPE
    SYNTAX          INTEGER { dryUp(1), force(2) }
    MAX-ACCESS      read-write
    STATUS          current
    DESCRIPTION     
            "Action assignment of this Softswitch to dry up or remove all the pending transactions 
             when the sonusPscsPolicyServerMode is set to out of service."
    DEFVAL          { dryUp }
    ::= { sonusPscsAdmnEntry 7 }

sonusPscsTransactionTimer OBJECT-TYPE
    SYNTAX          Integer32 (50..60000)
    MAX-ACCESS      read-write
    STATUS          current
    DESCRIPTION     
            "The timer parameter for this Softswitch's transaction in milliseconds."
    DEFVAL          { 500 }
    ::= { sonusPscsAdmnEntry 8 }

sonusPscsKeepAliveTimer OBJECT-TYPE
    SYNTAX          Integer32 (1..60)
    MAX-ACCESS      read-write
    STATUS          current
    DESCRIPTION     
            "The timer parameter for this Softswitch's keep alive exchange in seconds."
    DEFVAL          { 15 }
    ::= { sonusPscsAdmnEntry 9 }

sonusPscsRetryTimer OBJECT-TYPE
    SYNTAX          Integer32 (50..60000)
    MAX-ACCESS      read-write
    STATUS          current
    DESCRIPTION     
            "The timer parameter for this Softswitch's retry connections in milliseconds."
    DEFVAL          { 500 }
    ::= { sonusPscsAdmnEntry 10 }

sonusPscsRetries OBJECT-TYPE
    SYNTAX          Integer32 (0..32)
    MAX-ACCESS      read-write
    STATUS          current
    DESCRIPTION     
            "The number of reconnection attempts for this Softswitch."
    DEFVAL          { 3 }
    ::= { sonusPscsAdmnEntry 11 }

sonusPscsPolicyServerRowStatus OBJECT-TYPE
    SYNTAX          RowStatus
    MAX-ACCESS      read-write
    STATUS          current
    DESCRIPTION     
            "This is for SNMP use."
    ::= { sonusPscsAdmnEntry 12 }

sonusPscsStatusTable OBJECT-TYPE
    SYNTAX          SEQUENCE OF SonusPscsStatusEntry
    MAX-ACCESS      not-accessible
    STATUS          current
    DESCRIPTION     
            "Status Table of the Softswitch"
    ::= { sonusSoftswitch 3 }

sonusPscsStatusEntry OBJECT-TYPE
    SYNTAX          SonusPscsStatusEntry
    MAX-ACCESS      not-accessible
    STATUS          current
    DESCRIPTION     
            "List of Softswitch status elements."
    INDEX           { sonusPscsStatusIndex }
    ::= { sonusPscsStatusTable 1 }

SonusPscsStatusEntry ::=
    SEQUENCE {
        sonusPscsStatusIndex            Integer32,
        sonusPscsOperState              INTEGER,
        sonusPscsAverageTransactionTime Integer32,
        sonusPscsServerReconnects       Counter32,
        sonusPscsTransactionCompleted   Counter64,
        sonusPscsTransactionRetryAttempts Counter32,
        sonusPscsTransactionFailedAttempts  Counter32,
        sonusPscsVersion                Integer32
    }

sonusPscsStatusIndex OBJECT-TYPE
    SYNTAX          Integer32
    MAX-ACCESS      read-only
    STATUS          current
    DESCRIPTION     
            "Identifies the Softswitch entry."
    ::= { sonusPscsStatusEntry 1 }

sonusPscsOperState OBJECT-TYPE
    SYNTAX          INTEGER { active(1), standby(2), congested(3), 
                        down(4), dryingup(5) }
    MAX-ACCESS      read-only
    STATUS          current
    DESCRIPTION     
            "Operational state of the Softswitch."
    ::= { sonusPscsStatusEntry 2 }

sonusPscsAverageTransactionTime OBJECT-TYPE
    SYNTAX          Integer32
    MAX-ACCESS      read-only
    STATUS          current
    DESCRIPTION     
            "Records the average time taken in milliseconds for a Softswitch transaction."
    ::= { sonusPscsStatusEntry 3 }

sonusPscsServerReconnects OBJECT-TYPE
    SYNTAX          Counter32
    MAX-ACCESS      read-only
    STATUS          current
    DESCRIPTION     
            "The number of successful reconnections between the gateway and the Softswitch."
    ::= { sonusPscsStatusEntry 4 }

sonusPscsTransactionCompleted OBJECT-TYPE
    SYNTAX          Counter64
    MAX-ACCESS      read-only
    STATUS          current
    DESCRIPTION     
            "The number of successful transactions between the gateway and the Softswitch."
    ::= { sonusPscsStatusEntry 5 }

sonusPscsTransactionRetryAttempts OBJECT-TYPE
    SYNTAX          Counter32
    MAX-ACCESS      read-only
    STATUS          current
    DESCRIPTION     
            "The number of transaction retries between the gateway and the Softswitch."
    ::= { sonusPscsStatusEntry 6 }

sonusPscsTransactionFailedAttempts OBJECT-TYPE
    SYNTAX          Counter32
    MAX-ACCESS      read-only
    STATUS          current
    DESCRIPTION     
            "The number of un-successful transactions between the gateway and the Softswitch."
    ::= { sonusPscsStatusEntry 7 }

sonusPscsVersion OBJECT-TYPE
    SYNTAX          Integer32
    MAX-ACCESS      read-only
    STATUS          current
    DESCRIPTION     
            "The negotiated protocol version between the gateway and the Softswitch."
    ::= { sonusPscsStatusEntry 8 }

sonusSoftswitchClientServicesMIBNotifications OBJECT IDENTIFIER
    ::= { sonusSoftswitchClientServicesMIB 2 }

sonusSoftswitchClientServicesMIBNotificationsPrefix OBJECT IDENTIFIER
    ::= { sonusSoftswitchClientServicesMIBNotifications 0 }

sonusSoftswitchClientServicesMIBNotificationsObjects OBJECT IDENTIFIER
    ::= { sonusSoftswitchClientServicesMIBNotifications 1 }

sonusPscsInServiceReason OBJECT-TYPE
    SYNTAX          INTEGER { configured(1), successfulReConnect(2), 
                        automatic(3) }
    MAX-ACCESS      read-only
    STATUS          current
    DESCRIPTION     
            "The reason why a softswitch is in service."
    ::= { sonusSoftswitchClientServicesMIBNotificationsObjects 1 }

sonusPscsOutOfServiceReason OBJECT-TYPE
    SYNTAX          INTEGER { configured(1), connectionLoss(2), 
                        noConnection(3), nodeNameChange(4), 
                        incompatibleVersion(5) }
    MAX-ACCESS      read-only
    STATUS          current
    DESCRIPTION     
            "The reason why the softswitch is out of service."
    ::= { sonusSoftswitchClientServicesMIBNotificationsObjects 2 }

sonusPscsSwitchoverReason OBJECT-TYPE
    SYNTAX          INTEGER { configured(1), automatic(2), 
                        versionChanged(3) }
    MAX-ACCESS      read-only
    STATUS          current
    DESCRIPTION     
            "The reason why the softswitch has switch to be the active softswitch."
    ::= { sonusSoftswitchClientServicesMIBNotificationsObjects 3 }

sonusPscsRouteFailureReason OBJECT-TYPE
    SYNTAX          INTEGER { routeNotFound(1), noServiceConfigured(2), 
                        databaseError(3) }
    MAX-ACCESS      read-only
    STATUS          current
    DESCRIPTION     
            "The reason why a route look up has failed."
    ::= { sonusSoftswitchClientServicesMIBNotificationsObjects 4 }

sonusPscsCallInfo OBJECT-TYPE
    SYNTAX          DisplayString
    MAX-ACCESS      read-only
    STATUS          current
    DESCRIPTION     
            "Call information content."
    ::= { sonusSoftswitchClientServicesMIBNotificationsObjects 5 }

sonusPscsTranErrorReason OBJECT-TYPE
    SYNTAX          INTEGER { noSoftswitchAvailable(1), 
                        transactionTimeout(2), invalidParameters(3), 
                        receiveError(4), transmitError(5), 
                        encodeApiError(6), decodeApiError(7) }
    MAX-ACCESS      read-only
    STATUS          current
    DESCRIPTION     
            "The reason why a transaction has failed."
    ::= { sonusSoftswitchClientServicesMIBNotificationsObjects 6 }

sonusPscsRejectIndReason OBJECT-TYPE
    SYNTAX          INTEGER { notRegistered(1), unknownGateway(2), 
                        errorAVPContent(3), errorMsgContent(4), 
                        maxClientAccount(5), miscRegFailure(6) }
    MAX-ACCESS      read-only
    STATUS          current
    DESCRIPTION     
            "The reason why a reject ind received."
    ::= { sonusSoftswitchClientServicesMIBNotificationsObjects 7 }

sonusPscsCalledNumber OBJECT-TYPE
    SYNTAX          DisplayString
    MAX-ACCESS      read-only
    STATUS          current
    DESCRIPTION     
            "Destination number."
    ::= { sonusSoftswitchClientServicesMIBNotificationsObjects 8 }

sonusPscsCallingNumber OBJECT-TYPE
    SYNTAX          DisplayString
    MAX-ACCESS      read-only
    STATUS          current
    DESCRIPTION     
            "Originating number."
    ::= { sonusSoftswitchClientServicesMIBNotificationsObjects 9 }

sonusPscsCarrierCode OBJECT-TYPE
    SYNTAX          DisplayString
    MAX-ACCESS      read-only
    STATUS          current
    DESCRIPTION     
            "Carrier code."
    ::= { sonusSoftswitchClientServicesMIBNotificationsObjects 10 }

sonusSscsInServiceNotification NOTIFICATION-TYPE
    OBJECTS         { sonusPscsPolicyServerName, sonusPscsOperState, 
                      sonusPscsInServiceReason, sonusEventDescription, 
                      sonusEventClass, sonusEventLevel }
    STATUS          current
    DESCRIPTION     
            "This trap indicates a softswitch is now in service."
    ::= { sonusSoftswitchClientServicesMIBNotificationsPrefix 1 }

sonusSscsOutOfServiceNotification NOTIFICATION-TYPE
    OBJECTS         { sonusPscsPolicyServerName, 
                      sonusPscsOutOfServiceReason, sonusEventDescription, 
                      sonusEventClass, sonusEventLevel }
    STATUS          current
    DESCRIPTION     
            "This trap indicates a softswitch is now out of service."
    ::= { sonusSoftswitchClientServicesMIBNotificationsPrefix 2 }

sonusSscsSwitchoverNotification NOTIFICATION-TYPE
    OBJECTS         { sonusPscsPolicyServerName, 
                      sonusPscsSwitchoverReason, sonusEventDescription, 
                      sonusEventClass, sonusEventLevel }
    STATUS          current
    DESCRIPTION     
            "This trap indicates a softswitch has switched over."
    ::= { sonusSoftswitchClientServicesMIBNotificationsPrefix 3 }

sonusSscsRouteFailureNotification NOTIFICATION-TYPE
    OBJECTS         { sonusPscsPolicyServerName, 
                      sonusPscsRouteFailureReason, sonusPscsCalledNumber, 
                      sonusPscsCallingNumber, sonusPscsCarrierCode, 
                      sonusEventDescription, sonusEventClass, 
                      sonusEventLevel }
    STATUS          current
    DESCRIPTION     
            "This trap indicates a route look up has failed."
    ::= { sonusSoftswitchClientServicesMIBNotificationsPrefix 4 }

sonusSscsTransErrorNotification NOTIFICATION-TYPE
    OBJECTS         { sonusPscsPolicyServerName, 
                      sonusPscsTranErrorReason, sonusEventDescription, 
                      sonusEventClass, sonusEventLevel }
    STATUS          current
    DESCRIPTION     
            "This trap indicates a softswitch has a trans error."
    ::= { sonusSoftswitchClientServicesMIBNotificationsPrefix 5 }

sonusSscsRejectIndNotification NOTIFICATION-TYPE
    OBJECTS         { sonusPscsPolicyServerName, 
                      sonusPscsRejectIndReason, sonusEventDescription, 
                      sonusEventClass, sonusEventLevel }
    STATUS          current
    DESCRIPTION     
            "This trap indicates a reject indication has been received."
    ::= { sonusSoftswitchClientServicesMIBNotificationsPrefix 6 }

END -- end of module SONUS-SOFTSWITCH-CLIENT-SERVICES-MIB.
