-- *****************************************************************
-- ciscoEntityCapabilities MIB
--
-- AGENT-CAPABILITIES mib for ENTITY-MIB 
--
-- June 2002, Subra Hegde
-- August 2003, Seth Wang
--
-- Copyright(c) 2002-2003, 2006 by Cisco Systems,Inc.
--
-- *****************************************************************

CISCO-ENTITY-CAPABILITY DEFINITIONS ::= BEGIN
IMPORTS
        MODULE-IDENTITY
                FROM SNMPv2-SMI
        AGENT-CAPABILITIES
                FROM SNMPv2-CONF
        ciscoAgentCapability
                FROM CISCO-SMI;   

ciscoEntityCapability MODULE-IDENTITY
        LAST-UPDATED    "200605260000Z"
        ORGANIZATION    "Cisco Systems, Inc."
        CONTACT-INFO
                "       Cisco Systems
                        Customer Service

                Postal: 170 W Tasman Drive
                        San Jose, CA  95134
                        USA

                        Tel: +1 800 553-NETS

                E-mail: cs-snmp@cisco.com
                        cs-lan-switch-snmp@cisco.com"
        DESCRIPTION
                "The Agent Capabilities for ENTITY-MIB."

        REVISION "200605260000Z"
        DESCRIPTION
                "Added ciscoEntityCapabilityACSWV03R000 agent
                 capabilities for Cisco Application Control 
                 Engine (ACE)."
        REVISION        "200603240000Z"
        DESCRIPTION
                "Add VARIATION for the notification 
                 entConfigChange in ciscoEntityCapCatOSV08R0101."
        REVISION "200602080000Z"
        DESCRIPTION
            "Added ciscoEntityCapabilityV20CRS1 Agent 
             capabilities for IOS XR release 2.0 CRS1"
        REVISION "200308120000Z"
        DESCRIPTION
            "Updated the ciscoEntityCapability OID with the one
             assigned by CANA."
        REVISION "200308080000Z"
        DESCRIPTION
            "Added ciscoEntityCapV12R0111bEXCat6K
             ciscoEntityCapV12R0214SXCat6K and
             ciscoEntityCapCatOSV08R0101."
        REVISION "200206120000Z"
        DESCRIPTION
            "Initial version of this MIB module."
        ::= { ciscoAgentCapability 277 }

ciscoEntityCapabilityV2R00 AGENT-CAPABILITIES

PRODUCT-RELEASE "MGX8850 Release 2.00,
                BPX SES Release 1.00"
STATUS          current
DESCRIPTION     "Agent capabilities for ENTITY-MIB."

SUPPORTS ENTITY-MIB
INCLUDES { entityPhysicalGroup,entityPhysical2Group  }

VARIATION    entPhysicalName
DESCRIPTION  "This Object is set to one of the following 
             for entPhysicalClass = module(9)
                 * Slot Number for the Module
                 * Slot Number as seen in rear view of the
                   chassis for the line module(Back cards).
             for entPhysicalClass = chassis(1)
                 * Chassis number(Shelf number)"

VARIATION    entPhysicalMfgName
DESCRIPTION  "This Object is set to PCB Part Number
             800 Level if applicable. It contains
             a zero-length string if 800 level
             is not applicable."

VARIATION    entPhysicalModelName
DESCRIPTION  "This Object is set to PCB Part Number 
             73 Level if applicable. It contains
             a zero-length string if 73 Level is not 
             applicable."

VARIATION    entPhysicalAssetID
ACCESS       not-implemented
DESCRIPTION  "Not supported."

    ::= { ciscoEntityCapability 1 }

ciscoEntityCapV12R0111bEXCat6K AGENT-CAPABILITIES
    PRODUCT-RELEASE     "Cisco IOS 12.1(11b)EX on Catalyst 6000/6500
                         and Cisco 7600 series devices."
    STATUS              current
    DESCRIPTION         "ENTITY-MIB capabilities."

    SUPPORTS            ENTITY-MIB
        INCLUDES        { entityPhysicalGroup, entityLogicalGroup,
                          entityMappingGroup, entityGeneralGroup,
                          entityNotificationsGroup }

        VARIATION       entLPPhysicalIndex
            ACCESS      not-implemented
            DESCRIPTION "Not supported."

        VARIATION       entAliasMappingIdentifier
            ACCESS      not-implemented
            DESCRIPTION "Not supported."

    ::= { ciscoEntityCapability 2 }

ciscoEntityCapV12R0214SXCat6K AGENT-CAPABILITIES
    PRODUCT-RELEASE     "Cisco IOS 12.2(14)SX on Catalyst 6000/6500
                         and Cisco 7600 series devices."
    STATUS              current
    DESCRIPTION         "ENTITY-MIB capabilities."

    SUPPORTS            ENTITY-MIB
        INCLUDES        { entityPhysicalGroup, entityLogicalGroup,
                          entityMappingGroup, entityGeneralGroup,
                          entityNotificationsGroup,
                          entityPhysical2Group, entityLogical2Group }

        VARIATION       entPhysicalSerialNum
            ACCESS      read-only
            DESCRIPTION "Only support read-only access."

        VARIATION       entLPPhysicalIndex
            ACCESS      not-implemented
            DESCRIPTION "Not supported."

    ::= { ciscoEntityCapability 3 }

ciscoEntityCapCatOSV08R0101 AGENT-CAPABILITIES
    PRODUCT-RELEASE     "Cisco CatOS 8.1(1)."
    STATUS              current
    DESCRIPTION         "ENTITY-MIB capabilities."

    SUPPORTS            ENTITY-MIB
        INCLUDES        { entityPhysicalGroup, entityMappingGroup,
                          entityGeneralGroup, entityNotificationsGroup,
                          entityPhysical2Group }

        VARIATION       entPhysicalSerialNum
            ACCESS      read-only
            DESCRIPTION "Only support read-only access."

        VARIATION       entPhysicalAssetID
            ACCESS      not-implemented
            DESCRIPTION "Not supported."

        VARIATION       entLPPhysicalIndex
            ACCESS      not-implemented
            DESCRIPTION "Not supported."

        VARIATION       entConfigChange -- NOTIFICATION-TYPE
--          OBJECTS     { entLastChangeTime }
            DESCRIPTION
                    "This notification has no varbind object 
                     defined in ENTITY-MIB. However the instance 
                     value of entLastChangeTime is appended to 
                     it."

    ::= { ciscoEntityCapability 4 }


ciscoEntityCapabilityV20CRS1 AGENT-CAPABILITIES
    PRODUCT-RELEASE "Cisco IOS XR 2.0 for CRS-1"
    STATUS          current
    DESCRIPTION     "ENTITY-MIB capabilities for 
                     IOS XR release 2.0" 

    SUPPORTS        ENTITY-MIB
        INCLUDES    {               
                     entityLogical2Group,
                     entityPhysical2Group,              
                     entityGeneralGroup,
                     entityPhysicalGroup,
                     entityNotificationsGroup
                    } 

    VARIATION         entLogicalType
        ACCESS        not-implemented
        DESCRIPTION   "This object is not supported in
                       the current MIB Implementation."

    VARIATION         entLogicalTAddress
        ACCESS        not-implemented    
        DESCRIPTION   "This object is not supported in
                       the current MIB Implementation."

    VARIATION         entLogicalTDomain
        ACCESS        not-implemented    
        DESCRIPTION   "This object is not supported in
                       the current MIB Implementation."

    ::= { ciscoEntityCapability 5 }

ciscoEntityCapabilityACSWV03R000 AGENT-CAPABILITIES
    PRODUCT-RELEASE "ACSW (Application Control Software) 3.0"
    STATUS          current
    DESCRIPTION     "ENTITY-MIB capabilities for ACSW 3.0" 
    
    SUPPORTS        ENTITY-MIB
        INCLUDES    { entityPhysicalGroup, entityPhysical2Group } 

    VARIATION         entPhysicalSerialNum
        ACCESS        read-only
        DESCRIPTION   "Create operation not allowed."

    VARIATION         entPhysicalAlias
        ACCESS        not-implemented    
        DESCRIPTION   "This object is not supported in
                       the current MIB Implementation."

    VARIATION         entPhysicalAssetID
        ACCESS        not-implemented    
        DESCRIPTION   "This object is not supported in
                       the current MIB Implementation."

      ::= { ciscoEntityCapability 6}

END
