Nortel-Magellan-Passport-IpMIB
DEFINITIONS ::= BEGIN



IMPORTS

      OBJECT-TYPE
   FROM RFC-1212

      TimeTicks,
      IpAddress
   FROM RFC1155-SMI

      passportMIBs
   FROM Nortel-Magellan-Passport-UsefulDefinitionsMIB

      Counter32,
      PhysAddress,
      Gauge32,
      RowPointer,
      DisplayString,
      StorageType,
      RowStatus,
      AreaID,
      InterfaceIndex,
      RouterID,
      Integer32,
      Unsigned32
   FROM Nortel-Magellan-Passport-StandardTextualConventionsMIB

      AsciiString,
      DashedHexString,
      NonReplicated,
      HexString,
      EnterpriseDateAndTime,
      Link,
      AsciiStringIndex
   FROM Nortel-Magellan-Passport-TextualConventionsMIB

      vrIndex,
      vrPpIndex,
      vrPp,
      vr
   FROM Nortel-Magellan-Passport-VirtualRouterMIB;




-- LAST-UPDATED   "9905250000Z"
-- ORGANIZATION   "Nortel"
-- CONTACT-INFO   "
--         Nortel Magellan Network Management
--         
--         Postal: P.O. Box 5080, Station F 
--                 Ottawa, Ontario 
--                 Canada  K2C 3T1
--         
--         Email:  nm_plm@nt.com"
-- DESCRIPTION
--    "The module describing the Nortel Magellan Passport
--     Ip Enterprise MIB."

ipMIB OBJECT IDENTIFIER ::= { passportMIBs 27 }










-- Vr<string> Pp<string> IpPort
-- The IpPort component contains IP attributes specific to this port.

vrPpIpPort OBJECT IDENTIFIER ::= { vrPp 5 }



vrPpIpPortRowStatusTable OBJECT-TYPE
   SYNTAX     SEQUENCE OF VrPpIpPortRowStatusEntry
   ACCESS     not-accessible
   STATUS     mandatory
   DESCRIPTION
     "This entry controls the addition and deletion of 
      vrPpIpPort components."
::= { vrPpIpPort 1 }

vrPpIpPortRowStatusEntry OBJECT-TYPE
   SYNTAX     VrPpIpPortRowStatusEntry
   ACCESS     not-accessible
   STATUS     mandatory
   DESCRIPTION
     "A single entry in the table represents a single 
      vrPpIpPort component."
   INDEX {
      vrIndex,
      vrPpIndex,
      vrPpIpPortIndex }
::= { vrPpIpPortRowStatusTable 1 }

VrPpIpPortRowStatusEntry ::= SEQUENCE {
   vrPpIpPortRowStatus
      RowStatus,
   vrPpIpPortComponentName
      DisplayString,
   vrPpIpPortStorageType
      StorageType,
   vrPpIpPortIndex
      NonReplicated }

vrPpIpPortRowStatus OBJECT-TYPE
   SYNTAX     RowStatus 
   ACCESS     read-write
   STATUS     mandatory
   DESCRIPTION
     "This variable is used as the basis for SNMP naming of
      vrPpIpPort components.
      These components can be added and deleted."
::= { vrPpIpPortRowStatusEntry 1 }

vrPpIpPortComponentName OBJECT-TYPE
   SYNTAX     DisplayString 
   ACCESS     read-only
   STATUS     mandatory
   DESCRIPTION
     "This variable provides the component's string name for
      use with the ASCII Console Interface"
::= { vrPpIpPortRowStatusEntry 2 }

vrPpIpPortStorageType OBJECT-TYPE
   SYNTAX     StorageType 
   ACCESS     read-only
   STATUS     mandatory
   DESCRIPTION
     "This variable represents the storage type value for the
      vrPpIpPort tables."
::= { vrPpIpPortRowStatusEntry 4 }

vrPpIpPortIndex OBJECT-TYPE
   SYNTAX     NonReplicated 
   ACCESS     not-accessible
   STATUS     mandatory
   DESCRIPTION
     "This variable represents the index for the vrPpIpPort tables."
::= { vrPpIpPortRowStatusEntry 10 }

vrPpIpPortProvTable OBJECT-TYPE
   SYNTAX     SEQUENCE OF VrPpIpPortProvEntry
   ACCESS     not-accessible
   STATUS     mandatory
   DESCRIPTION
     "This group contains provisionable attributes for IP ports."
::= { vrPpIpPort 10 }

vrPpIpPortProvEntry OBJECT-TYPE
   SYNTAX     VrPpIpPortProvEntry
   ACCESS     not-accessible
   STATUS     mandatory
   DESCRIPTION
     "An entry in the vrPpIpPortProvTable."
   INDEX {
      vrIndex,
      vrPpIndex,
      vrPpIpPortIndex }
::= { vrPpIpPortProvTable 1 }

VrPpIpPortProvEntry ::= SEQUENCE {
   vrPpIpPortMaxTxUnit
      Unsigned32,
   vrPpIpPortArpStatus
      INTEGER,
   vrPpIpPortProxyArpStatus
      INTEGER,
   vrPpIpPortArpNoLearn
      INTEGER,
   vrPpIpPortSendRedirect
      INTEGER,
   vrPpIpPortMulticastStatus
      INTEGER,
   vrPpIpPortRelayAddress
      IpAddress,
   vrPpIpPortRelayBroadcast
      INTEGER,
   vrPpIpPortLinkModel
      INTEGER,
   vrPpIpPortLanModel
      INTEGER,
   vrPpIpPortEncap
      INTEGER,
   vrPpIpPortIcmpMaskReply
      INTEGER,
   vrPpIpPortDirectedBroadcast
      INTEGER,
   vrPpIpPortAssignedQos
      Unsigned32,
   vrPpIpPortAllowMcastMacDest
      INTEGER,
   vrPpIpPortCosPolicyAssignment
      Link,
   vrPpIpPortMcastDomain
      Unsigned32,
   vrPpIpPortMcastPolicyAssignment
      Link }

vrPpIpPortMaxTxUnit OBJECT-TYPE
   SYNTAX     Unsigned32 (0..0 | 576..18944)
   ACCESS     read-write
   STATUS     mandatory
   DESCRIPTION
     "This attribute specifies the IP MTU (Maximum Transmission Unit) 
      supported by this IpPort. The specified MTU must be within the valid 
      range for the IpPort media type."
   DEFVAL     { 0 }
::= { vrPpIpPortProvEntry 2 }

vrPpIpPortArpStatus OBJECT-TYPE
   SYNTAX     INTEGER  {
                 enabled(1),
                 disabled(2),
                 auto(3) }
   ACCESS     read-write
   STATUS     mandatory
   DESCRIPTION
     "This attribute specifies whether ARP is enabled or disabled on this 
      IpPort. If auto is specified, an appropriate value will be selected based 
      on the IpPort media type."
   DEFVAL     { auto }
::= { vrPpIpPortProvEntry 3 }

vrPpIpPortProxyArpStatus OBJECT-TYPE
   SYNTAX     INTEGER  {
                 enabled(1),
                 disabled(2) }
   ACCESS     read-write
   STATUS     mandatory
   DESCRIPTION
     "This attribute specifies whether Proxy ARP is enabled or disabled for 
      this IpPort."
   DEFVAL     { disabled }
::= { vrPpIpPortProvEntry 4 }

vrPpIpPortArpNoLearn OBJECT-TYPE
   SYNTAX     INTEGER  {
                 enabled(1),
                 disabled(2) }
   ACCESS     read-write
   STATUS     mandatory
   DESCRIPTION
     "This attribute specifies whether or not dynamic host entries will be 
      installed in the ARP table when ARP packets are received on this 
      IpPort."
   DEFVAL     { disabled }
::= { vrPpIpPortProvEntry 5 }

vrPpIpPortSendRedirect OBJECT-TYPE
   SYNTAX     INTEGER  {
                 enabled(1),
                 disabled(2) }
   ACCESS     read-write
   STATUS     mandatory
   DESCRIPTION
     "This attribute specifies whether or not ICMP host redirects will be sent 
      out this IpPort."
   DEFVAL     { enabled }
::= { vrPpIpPortProvEntry 6 }

vrPpIpPortMulticastStatus OBJECT-TYPE
   SYNTAX     INTEGER  {
                 enabled(1),
                 disabled(2),
                 auto(3) }
   ACCESS     read-write
   STATUS     mandatory
   DESCRIPTION
     "This attribute specifies whether or not IP multicast packets can be sent 
      out this IpPort. If auto is specified, an appropriate value will be selected 
      based on the IpPort media type."
   DEFVAL     { auto }
::= { vrPpIpPortProvEntry 7 }

vrPpIpPortRelayAddress OBJECT-TYPE
   SYNTAX     IpAddress 
   ACCESS     read-write
   STATUS     mandatory
   DESCRIPTION
     "This attribute specifies a relay broadcast address for this IpPort. Each 
      packet, received on this IpPort, meeting the relay broadcast criteria will 
      be forwarded to the specified relay broadcast address. An relay address 
      of all zero's indicates no relay broadcast address."
   DEFVAL     { '00000000'H }  -- "0.0.0.0"
::= { vrPpIpPortProvEntry 8 }

vrPpIpPortRelayBroadcast OBJECT-TYPE
   SYNTAX     INTEGER  {
                 enabled(1),
                 disabled(2),
                 auto(3) }
   ACCESS     read-write
   STATUS     mandatory
   DESCRIPTION
     "This attribute specifies how packets, received on other IpPorts, meeting 
      the relay broadcast criteria, will be forwarded out this IpPort. The three 
      options are described as follows:
      enabled: packets will be forwarded out this IpPort.
      disabled: packets will not be forwarded out this IpPort.
      auto: packets will be forwarded out this IpPort only when the bridge 
      state is forwarding."
   DEFVAL     { disabled }
::= { vrPpIpPortProvEntry 9 }

vrPpIpPortLinkModel OBJECT-TYPE
   SYNTAX     INTEGER  {
                 localAreaNetwork(1),
                 pointToPoint(2),
                 loopback(5) }
   ACCESS     read-write
   STATUS     mandatory
   DESCRIPTION
     "This attribute specifies the link model to use when the media type for 
      this IpPort is PPP (Point to Point Protocol). A value of 
      localAreaNetwork causes IP to treat this IpPort like a LAN. A value of 
      pointToPoint causes IP to treat this IpPort like two directly connected 
      IP hosts. A value of loopback causes IP to treat this IpPort similar to a 
      point-to-point, but the destination and source points are the same 
      providing an always up interface."
   DEFVAL     { localAreaNetwork }
::= { vrPpIpPortProvEntry 10 }

vrPpIpPortLanModel OBJECT-TYPE
   SYNTAX     INTEGER  {
                 localAreaNetwork(1),
                 nonBroadcastMultipleAccess(2) }
   ACCESS     read-write
   STATUS     mandatory
   DESCRIPTION
     "This attribute specifies the lan model to use for this IpPort."
   DEFVAL     { localAreaNetwork }
::= { vrPpIpPortProvEntry 11 }

vrPpIpPortEncap OBJECT-TYPE
   SYNTAX     INTEGER  {
                 ieee8023(1),
                 ethernet(2),
                 auto(3) }
   ACCESS     read-write
   STATUS     mandatory
   DESCRIPTION
     "This attribute specifies the encapsulation type to be used when sending 
      packets out this IpPort. If auto is specified, an appropriate value is 
      selected based on the IpPort media type. The values ieee8023 and 
      ethernet can only be specified if the media type is ethernet. Otherwise, 
      auto must be specified. For ethernet media type, the default 
      encapsulation is ethernet."
   DEFVAL     { auto }
::= { vrPpIpPortProvEntry 12 }

vrPpIpPortIcmpMaskReply OBJECT-TYPE
   SYNTAX     INTEGER  {
                 enabled(1),
                 disabled(2) }
   ACCESS     read-write
   STATUS     mandatory
   DESCRIPTION
     "This attribute specifies whether or not replies will be generated in 
      response to ICMP Address Mask Requests received on this IpPort."
   DEFVAL     { enabled }
::= { vrPpIpPortProvEntry 13 }

vrPpIpPortDirectedBroadcast OBJECT-TYPE
   SYNTAX     INTEGER  {
                 enabled(1),
                 disabled(2) }
   ACCESS     read-write
   STATUS     mandatory
   DESCRIPTION
     "This attribute specifies whether or not directed broadcast to physical 
      broadcast translation is enabled for incoming traffic on this IpPort. The 
      IP router requirement (RFC1812) says this translation should be 
      enabled; however, in some network environments, setting this attribute 
      to disabled may prevent operational problem such as broadcast storms. 
      Note that in some configuration, setting this attribute to disabled may 
      cause Bootp to fail."
   DEFVAL     { enabled }
::= { vrPpIpPortProvEntry 14 }

vrPpIpPortAssignedQos OBJECT-TYPE
   SYNTAX     Unsigned32 (0..3)
   ACCESS     read-write
   STATUS     mandatory
   DESCRIPTION
     "This attribute specifies the initial Class of Service (CoS) given to each 
      packet received on the IpPort. The CoS value n is used to select Vr/
      <string> QosP/n. which determines the QualityofService-Profile to be 
      used when the packet is forwarded.
      
      The intial CoS given to a packet by the assignedQoS attribute may be 
      overriden under certain circumstances (see the description of the Vr 
      Qosp component, the cosPolicyAssignment attribute on the IpPort and Ip 
      components, and the ipCos attribute on any of the frameRelayDte 
      staticDlci, frameRelayDte dynamicDlciDefaults, and atmMpe 
      atmConnection components)."
   DEFVAL     { 0 }
::= { vrPpIpPortProvEntry 15 }

vrPpIpPortAllowMcastMacDest OBJECT-TYPE
   SYNTAX     INTEGER  {
                 enabled(1),
                 disabled(2) }
   ACCESS     read-write
   STATUS     mandatory
   DESCRIPTION
     "This attribute specifies whether a multicast destination MAC address is 
      valid on this IpPort or not. Enabling it is non-standard. It can be used for 
      applications such as transparent server backup. Multicast destination 
      MAC address is only supported on LAN media."
   DEFVAL     { disabled }
::= { vrPpIpPortProvEntry 16 }

vrPpIpPortCosPolicyAssignment OBJECT-TYPE
   SYNTAX     Link 
   ACCESS     read-write
   STATUS     mandatory
   DESCRIPTION
     "This attribute specifies the CosPolicyGroup component this IpPort 
      component is using. Assigning a particular policy group to the IpPort 
      may override the effect of the assignedQos; this depends on the actual 
      policies provisioned under the policy group."
::= { vrPpIpPortProvEntry 17 }

vrPpIpPortMcastDomain OBJECT-TYPE
   SYNTAX     Unsigned32 (0..3)
   ACCESS     read-write
   STATUS     mandatory
   DESCRIPTION
     "This attribute specifies the multicast domain index which all traffic 
      coming in from this IpPort use. The numerical value of this attribute 
      selects Vr/<string> Ip Mcast Domain/n."
   DEFVAL     { 0 }
::= { vrPpIpPortProvEntry 18 }

vrPpIpPortMcastPolicyAssignment OBJECT-TYPE
   SYNTAX     Link 
   ACCESS     read-write
   STATUS     mandatory
   DESCRIPTION
     "This attribute specifies the policyGroup component that this 
      IpPort component is using."
::= { vrPpIpPortProvEntry 19 }

vrPpIpPortSresProvTable OBJECT-TYPE
   SYNTAX     SEQUENCE OF VrPpIpPortSresProvEntry
   ACCESS     not-accessible
   STATUS     mandatory
   DESCRIPTION
     "This group contains the provisioned attributes for 
      SourceRouteEndStation support."
::= { vrPpIpPort 11 }

vrPpIpPortSresProvEntry OBJECT-TYPE
   SYNTAX     VrPpIpPortSresProvEntry
   ACCESS     not-accessible
   STATUS     mandatory
   DESCRIPTION
     "An entry in the vrPpIpPortSresProvTable."
   INDEX {
      vrIndex,
      vrPpIndex,
      vrPpIpPortIndex }
::= { vrPpIpPortSresProvTable 1 }

VrPpIpPortSresProvEntry ::= SEQUENCE {
   vrPpIpPortSourceRouteEndStationSupport
      INTEGER }

vrPpIpPortSourceRouteEndStationSupport OBJECT-TYPE
   SYNTAX     INTEGER  {
                 enable(1),
                 disable(2) }
   ACCESS     read-write
   STATUS     mandatory
   DESCRIPTION
     "This attribute is used to enable or disable support for 
      SourceRouteEndStation (Sres). If set to enable, Sres will be supported 
      on this protocol on this ProtocolPort (Pp). If set to disable, it will not be 
      supported. An Sres component must be provisioned under the 
      VirtualRouter if this attribute is set to enable. If this attribute is set to 
      enable and this Pp has its linkToMedia attribute set, it must be linked to 
      a LanApplication (La) that has its Framer interfaceName linked to a 
      Fddi or TokenRing component."
   DEFVAL     { disable }
::= { vrPpIpPortSresProvEntry 1 }

vrPpIpPortAdminControlTable OBJECT-TYPE
   SYNTAX     SEQUENCE OF VrPpIpPortAdminControlEntry
   ACCESS     not-accessible
   STATUS     mandatory
   DESCRIPTION
     "This group includes the Administrative Control attribute. This 
      attribute defines the current administrative state of this component."
::= { vrPpIpPort 12 }

vrPpIpPortAdminControlEntry OBJECT-TYPE
   SYNTAX     VrPpIpPortAdminControlEntry
   ACCESS     not-accessible
   STATUS     mandatory
   DESCRIPTION
     "An entry in the vrPpIpPortAdminControlTable."
   INDEX {
      vrIndex,
      vrPpIndex,
      vrPpIpPortIndex }
::= { vrPpIpPortAdminControlTable 1 }

VrPpIpPortAdminControlEntry ::= SEQUENCE {
   vrPpIpPortSnmpAdminStatus
      INTEGER }

vrPpIpPortSnmpAdminStatus OBJECT-TYPE
   SYNTAX     INTEGER  {
                 up(1),
                 down(2),
                 testing(3) }
   ACCESS     read-write
   STATUS     mandatory
   DESCRIPTION
     "The desired state of the interface. The up state indicates the 
      interface is operational and packet forwarding is allowed. The down 
      state indicates the interface is not operational and packet forwarding 
      is unavailable. The testing state indicates that no operational 
      packets can be passed."
   DEFVAL     { up }
::= { vrPpIpPortAdminControlEntry 1 }

vrPpIpPortOperTable OBJECT-TYPE
   SYNTAX     SEQUENCE OF VrPpIpPortOperEntry
   ACCESS     not-accessible
   STATUS     mandatory
   DESCRIPTION
     "This group contains operational attributes for an IpPort."
::= { vrPpIpPort 13 }

vrPpIpPortOperEntry OBJECT-TYPE
   SYNTAX     VrPpIpPortOperEntry
   ACCESS     not-accessible
   STATUS     mandatory
   DESCRIPTION
     "An entry in the vrPpIpPortOperTable."
   INDEX {
      vrIndex,
      vrPpIndex,
      vrPpIpPortIndex }
::= { vrPpIpPortOperTable 1 }

VrPpIpPortOperEntry ::= SEQUENCE {
   vrPpIpPortMediaType
      INTEGER,
   vrPpIpPortOperMtu
      Unsigned32,
   vrPpIpPortOperArpStatus
      INTEGER,
   vrPpIpPortOperMulticastStatus
      INTEGER,
   vrPpIpPortOperEncap
      INTEGER,
   vrPpIpPortOperCosPolicyAssignment
      RowPointer }

vrPpIpPortMediaType OBJECT-TYPE
   SYNTAX     INTEGER  {
                 ethernet(1),
                 fddi(2),
                 tokenRing(3),
                 ppp(4),
                 vcpEther(5),
                 vcpToken(6),
                 vns(7),
                 x25(8),
                 frameRelay(9),
                 clusterBridge(10),
                 smds(11),
                 invalid(12),
                 atmMpeVcEncap(13),
                 atmMpeLlcEncap(14),
                 lecEther(15),
                 lecToken(16),
                 tunnel(17),
                 virtual(18) }
   ACCESS     read-only
   STATUS     mandatory
   DESCRIPTION
     "This attribute indicates the media type of this IpPort."
   DEFVAL     { invalid }
::= { vrPpIpPortOperEntry 1 }

vrPpIpPortOperMtu OBJECT-TYPE
   SYNTAX     Unsigned32 (0..0 | 576..18944)
   ACCESS     read-only
   STATUS     mandatory
   DESCRIPTION
     "This attribute indicates the current operational IP MTU for this IpPort. 
      Note that this value may be different than the provisioned maxTxUnit."
   DEFVAL     { 0 }
::= { vrPpIpPortOperEntry 2 }

vrPpIpPortOperArpStatus OBJECT-TYPE
   SYNTAX     INTEGER  {
                 enabled(1),
                 disabled(2) }
   ACCESS     read-only
   STATUS     mandatory
   DESCRIPTION
     "This attribute indicates the current operational ARP status. If the 
      provisioned arpStatus is set to auto, then the IP application 
      automatically determines the operArpStatus based on the IpPort media 
      type."
   DEFVAL     { disabled }
::= { vrPpIpPortOperEntry 3 }

vrPpIpPortOperMulticastStatus OBJECT-TYPE
   SYNTAX     INTEGER  {
                 enabled(1),
                 disabled(2) }
   ACCESS     read-only
   STATUS     mandatory
   DESCRIPTION
     "This attribute indicates the current operational Multicast status. If the 
      provisioned multicastStatus is set to auto, then the IP application 
      automatically determines the operMulticastStatus based on the IpPort 
      media type."
   DEFVAL     { disabled }
::= { vrPpIpPortOperEntry 4 }

vrPpIpPortOperEncap OBJECT-TYPE
   SYNTAX     INTEGER  {
                 ieee8023(1),
                 ethernet(2),
                 notApplicable(3) }
   ACCESS     read-only
   STATUS     mandatory
   DESCRIPTION
     "This attribute indicates the current operational encapsulation type. If the 
      provisioned encap is set to auto, then the IP application automatically 
      determines the operEncap based on the IpPort media type."
   DEFVAL     { notApplicable }
::= { vrPpIpPortOperEntry 5 }

vrPpIpPortOperCosPolicyAssignment OBJECT-TYPE
   SYNTAX     RowPointer 
   ACCESS     read-only
   STATUS     mandatory
   DESCRIPTION
     "This attribute specifies the CosPolicyGroup component this IpPort 
      component is using."
::= { vrPpIpPortOperEntry 433 }

vrPpIpPortRelayBcOperTable OBJECT-TYPE
   SYNTAX     SEQUENCE OF VrPpIpPortRelayBcOperEntry
   ACCESS     not-accessible
   STATUS     mandatory
   DESCRIPTION
     "This group contains operational attributes for an IpPort's RelayBc 
      counters."
::= { vrPpIpPort 14 }

vrPpIpPortRelayBcOperEntry OBJECT-TYPE
   SYNTAX     VrPpIpPortRelayBcOperEntry
   ACCESS     not-accessible
   STATUS     mandatory
   DESCRIPTION
     "An entry in the vrPpIpPortRelayBcOperTable."
   INDEX {
      vrIndex,
      vrPpIndex,
      vrPpIpPortIndex }
::= { vrPpIpPortRelayBcOperTable 1 }

VrPpIpPortRelayBcOperEntry ::= SEQUENCE {
   vrPpIpPortRelayAddressCount
      Counter32,
   vrPpIpPortRelayBcCount
      Counter32 }

vrPpIpPortRelayAddressCount OBJECT-TYPE
   SYNTAX     Counter32 
   ACCESS     read-only
   STATUS     mandatory
   DESCRIPTION
     "This attribute indicates the number of frames received on this IpPort 
      which were forwarded to the provisioned relayAddress for this port. This 
      counter wraps to zero when it reaches it's maximum."
::= { vrPpIpPortRelayBcOperEntry 1 }

vrPpIpPortRelayBcCount OBJECT-TYPE
   SYNTAX     Counter32 
   ACCESS     read-only
   STATUS     mandatory
   DESCRIPTION
     "This attribute indicates the number of frames received on this port which 
      were forwarded to the broadcastAddress on other IpPorts. This counter 
      is incremented once for every frame received on this port regardless of 
      how many other ports it was sent on. This counter wraps to zero when it 
      reaches it's maximum."
::= { vrPpIpPortRelayBcOperEntry 2 }

vrPpIpPortStateTable OBJECT-TYPE
   SYNTAX     SEQUENCE OF VrPpIpPortStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { vrPpIpPort 15 }

vrPpIpPortStateEntry OBJECT-TYPE
   SYNTAX     VrPpIpPortStateEntry
   ACCESS     not-accessible
   STATUS     mandatory
   DESCRIPTION
     "An entry in the vrPpIpPortStateTable."
   INDEX {
      vrIndex,
      vrPpIndex,
      vrPpIpPortIndex }
::= { vrPpIpPortStateTable 1 }

VrPpIpPortStateEntry ::= SEQUENCE {
   vrPpIpPortAdminState
      INTEGER,
   vrPpIpPortOperationalState
      INTEGER,
   vrPpIpPortUsageState
      INTEGER }

vrPpIpPortAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { vrPpIpPortStateEntry 1 }

vrPpIpPortOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { vrPpIpPortStateEntry 2 }

vrPpIpPortUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { vrPpIpPortStateEntry 3 }

vrPpIpPortOperStatusTable OBJECT-TYPE
   SYNTAX     SEQUENCE OF VrPpIpPortOperStatusEntry
   ACCESS     not-accessible
   STATUS     mandatory
   DESCRIPTION
     "This group includes the Operational Status attribute. This attribute 
      defines the current operational state of this component."
::= { vrPpIpPort 16 }

vrPpIpPortOperStatusEntry OBJECT-TYPE
   SYNTAX     VrPpIpPortOperStatusEntry
   ACCESS     not-accessible
   STATUS     mandatory
   DESCRIPTION
     "An entry in the vrPpIpPortOperStatusTable."
   INDEX {
      vrIndex,
      vrPpIndex,
      vrPpIpPortIndex }
::= { vrPpIpPortOperStatusTable 1 }

VrPpIpPortOperStatusEntry ::= SEQUENCE {
   vrPpIpPortSnmpOperStatus
      INTEGER }

vrPpIpPortSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { vrPpIpPortOperStatusEntry 1 }


-- The IpLogicalIf component defines a single IpPort address on a logical 
-- IP network. In general, IpPort's can have multiple IpLogicalIf's. 
-- However, if the media type is PPP (Point to Point Protocol), then only 
-- one IpLogicalIf is allowed for that IpPort.

vrPpIpPortLogicalIf OBJECT IDENTIFIER ::= { vrPpIpPort 2 }



vrPpIpPortLogicalIfRowStatusTable OBJECT-TYPE
   SYNTAX     SEQUENCE OF VrPpIpPortLogicalIfRowStatusEntry
   ACCESS     not-accessible
   STATUS     mandatory
   DESCRIPTION
     "This entry controls the addition and deletion of 
      vrPpIpPortLogicalIf components."
::= { vrPpIpPortLogicalIf 1 }

vrPpIpPortLogicalIfRowStatusEntry OBJECT-TYPE
   SYNTAX     VrPpIpPortLogicalIfRowStatusEntry
   ACCESS     not-accessible
   STATUS     mandatory
   DESCRIPTION
     "A single entry in the table represents a single 
      vrPpIpPortLogicalIf component."
   INDEX {
      vrIndex,
      vrPpIndex,
      vrPpIpPortIndex,
      vrPpIpPortLogicalIfAddressIndex }
::= { vrPpIpPortLogicalIfRowStatusTable 1 }

VrPpIpPortLogicalIfRowStatusEntry ::= SEQUENCE {
   vrPpIpPortLogicalIfRowStatus
      RowStatus,
   vrPpIpPortLogicalIfComponentName
      DisplayString,
   vrPpIpPortLogicalIfStorageType
      StorageType,
   vrPpIpPortLogicalIfAddressIndex
      IpAddress }

vrPpIpPortLogicalIfRowStatus OBJECT-TYPE
   SYNTAX     RowStatus 
   ACCESS     read-write
   STATUS     mandatory
   DESCRIPTION
     "This variable is used as the basis for SNMP naming of
      vrPpIpPortLogicalIf components.
      These components can be added and deleted."
::= { vrPpIpPortLogicalIfRowStatusEntry 1 }

vrPpIpPortLogicalIfComponentName OBJECT-TYPE
   SYNTAX     DisplayString 
   ACCESS     read-only
   STATUS     mandatory
   DESCRIPTION
     "This variable provides the component's string name for
      use with the ASCII Console Interface"
::= { vrPpIpPortLogicalIfRowStatusEntry 2 }

vrPpIpPortLogicalIfStorageType OBJECT-TYPE
   SYNTAX     StorageType 
   ACCESS     read-only
   STATUS     mandatory
   DESCRIPTION
     "This variable represents the storage type value for the
      vrPpIpPortLogicalIf tables."
::= { vrPpIpPortLogicalIfRowStatusEntry 4 }

vrPpIpPortLogicalIfAddressIndex OBJECT-TYPE
   SYNTAX     IpAddress 
   ACCESS     not-accessible
   STATUS     mandatory
   DESCRIPTION
     "This variable represents the index for the vrPpIpPortLogicalIf tables."
::= { vrPpIpPortLogicalIfRowStatusEntry 10 }

vrPpIpPortLogicalIfProvTable OBJECT-TYPE
   SYNTAX     SEQUENCE OF VrPpIpPortLogicalIfProvEntry
   ACCESS     not-accessible
   STATUS     mandatory
   DESCRIPTION
     "This group contains attributes required to define an IpLogicalIf."
::= { vrPpIpPortLogicalIf 10 }

vrPpIpPortLogicalIfProvEntry OBJECT-TYPE
   SYNTAX     VrPpIpPortLogicalIfProvEntry
   ACCESS     not-accessible
   STATUS     mandatory
   DESCRIPTION
     "An entry in the vrPpIpPortLogicalIfProvTable."
   INDEX {
      vrIndex,
      vrPpIndex,
      vrPpIpPortIndex,
      vrPpIpPortLogicalIfAddressIndex }
::= { vrPpIpPortLogicalIfProvTable 1 }

VrPpIpPortLogicalIfProvEntry ::= SEQUENCE {
   vrPpIpPortLogicalIfNetMask
      IpAddress,
   vrPpIpPortLogicalIfBroadcastAddress
      IpAddress,
   vrPpIpPortLogicalIfLinkDestinationAddress
      IpAddress,
   vrPpIpPortLogicalIfLinkToPimSmCandidateRp
      Link,
   vrPpIpPortLogicalIfLinkToPimSmCandidateBsr
      Link }

vrPpIpPortLogicalIfNetMask OBJECT-TYPE
   SYNTAX     IpAddress 
   ACCESS     read-write
   STATUS     mandatory
   DESCRIPTION
     "This attribute specifies the subnet mask for this IpLogicalIf. This 
      attribute must be specified because the IP application will not 
      automatically provide a default value."
   DEFVAL     { '00000000'H }  -- "0.0.0.0"
::= { vrPpIpPortLogicalIfProvEntry 1 }

vrPpIpPortLogicalIfBroadcastAddress OBJECT-TYPE
   SYNTAX     IpAddress 
   ACCESS     read-write
   STATUS     mandatory
   DESCRIPTION
     "This attribute specifies the broadcast address for this IpLogicalIf. This 
      attribute is ignored if the IpPort mediaType is ppp (Point to Point 
      Protocol). If the value is 0.0.0.0, the actual broadcast address will be 
      derived from the IP address of this LogicalIf and the netmask attribute."
   DEFVAL     { '00000000'H }  -- "0.0.0.0"
::= { vrPpIpPortLogicalIfProvEntry 2 }

vrPpIpPortLogicalIfLinkDestinationAddress OBJECT-TYPE
   SYNTAX     IpAddress 
   ACCESS     read-write
   STATUS     mandatory
   DESCRIPTION
     "This attribute specifies the address for the link destination for this 
      IpLogicalIf. This attribute is only required if the IpPort media type is 
      PPP (Point to Point Protocol)."
   DEFVAL     { '00000000'H }  -- "0.0.0.0"
::= { vrPpIpPortLogicalIfProvEntry 3 }

vrPpIpPortLogicalIfLinkToPimSmCandidateRp OBJECT-TYPE
   SYNTAX     Link 
   ACCESS     read-write
   STATUS     mandatory
   DESCRIPTION
     "This attribute specifies a link to the CandidateRendezvousPoint 
      component which uses this logicalIf as it's RendezvousPoint (Rp)."
::= { vrPpIpPortLogicalIfProvEntry 4 }

vrPpIpPortLogicalIfLinkToPimSmCandidateBsr OBJECT-TYPE
   SYNTAX     Link 
   ACCESS     read-write
   STATUS     mandatory
   DESCRIPTION
     "This attribute specifies a link to the CandidateBootstrapRouter 
      component which uses this logicalIf as it's BootstrapRouter Interface."
::= { vrPpIpPortLogicalIfProvEntry 5 }

vrPpIpPortLogicalIfLinkToMulStaticGpTable OBJECT-TYPE
   SYNTAX     SEQUENCE OF VrPpIpPortLogicalIfLinkToMulStaticGpEntry
   ACCESS     not-accessible
   STATUS     mandatory
   DESCRIPTION
     "This attribute specifies a link to the component InwStaticRouteEntry 
      which uses this logicalIf as it's OutInterface."
::= { vrPpIpPortLogicalIf 706 }

vrPpIpPortLogicalIfLinkToMulStaticGpEntry OBJECT-TYPE
   SYNTAX     VrPpIpPortLogicalIfLinkToMulStaticGpEntry
   ACCESS     not-accessible
   STATUS     mandatory
   DESCRIPTION
     "An entry in the vrPpIpPortLogicalIfLinkToMulStaticGpTable."
   INDEX {
      vrIndex,
      vrPpIndex,
      vrPpIpPortIndex,
      vrPpIpPortLogicalIfAddressIndex,
      vrPpIpPortLogicalIfLinkToMulStaticGpValue }
::= { vrPpIpPortLogicalIfLinkToMulStaticGpTable 1 }

VrPpIpPortLogicalIfLinkToMulStaticGpEntry ::= SEQUENCE {
   vrPpIpPortLogicalIfLinkToMulStaticGpValue
      Link,
   vrPpIpPortLogicalIfLinkToMulStaticGpRowStatus
      RowStatus }

vrPpIpPortLogicalIfLinkToMulStaticGpValue OBJECT-TYPE
   SYNTAX     Link 
   ACCESS     read-write
   STATUS     mandatory
   DESCRIPTION
     "This variable represents both the value and the index for the
      vrPpIpPortLogicalIfLinkToMulStaticGpTable."
::= { vrPpIpPortLogicalIfLinkToMulStaticGpEntry 1 }

vrPpIpPortLogicalIfLinkToMulStaticGpRowStatus OBJECT-TYPE
   SYNTAX     RowStatus 
   ACCESS     write-only
   STATUS     mandatory
   DESCRIPTION
     "This variable is used to control the addition and deletion 
      of individual values of the vrPpIpPortLogicalIfLinkToMulStaticGpTable."
::= { vrPpIpPortLogicalIfLinkToMulStaticGpEntry 2 }


-- Vr/<string> Pp/<string> IpPort logicalIf/<Ip Address> ospfIf
-- An OspfIf component can be created under each logicalIf to run OSPF 
-- protocol.

vrPpIpPortLogicalIfOspfIf OBJECT IDENTIFIER ::= { vrPpIpPortLogicalIf 2 }



vrPpIpPortLogicalIfOspfIfRowStatusTable OBJECT-TYPE
   SYNTAX     SEQUENCE OF VrPpIpPortLogicalIfOspfIfRowStatusEntry
   ACCESS     not-accessible
   STATUS     mandatory
   DESCRIPTION
     "This entry controls the addition and deletion of 
      vrPpIpPortLogicalIfOspfIf components."
::= { vrPpIpPortLogicalIfOspfIf 1 }

vrPpIpPortLogicalIfOspfIfRowStatusEntry OBJECT-TYPE
   SYNTAX     VrPpIpPortLogicalIfOspfIfRowStatusEntry
   ACCESS     not-accessible
   STATUS     mandatory
   DESCRIPTION
     "A single entry in the table represents a single 
      vrPpIpPortLogicalIfOspfIf component."
   INDEX {
      vrIndex,
      vrPpIndex,
      vrPpIpPortIndex,
      vrPpIpPortLogicalIfAddressIndex,
      vrPpIpPortLogicalIfOspfIfIndex }
::= { vrPpIpPortLogicalIfOspfIfRowStatusTable 1 }

VrPpIpPortLogicalIfOspfIfRowStatusEntry ::= SEQUENCE {
   vrPpIpPortLogicalIfOspfIfRowStatus
      RowStatus,
   vrPpIpPortLogicalIfOspfIfComponentName
      DisplayString,
   vrPpIpPortLogicalIfOspfIfStorageType
      StorageType,
   vrPpIpPortLogicalIfOspfIfIndex
      NonReplicated }

vrPpIpPortLogicalIfOspfIfRowStatus OBJECT-TYPE
   SYNTAX     RowStatus 
   ACCESS     read-write
   STATUS     mandatory
   DESCRIPTION
     "This variable is used as the basis for SNMP naming of
      vrPpIpPortLogicalIfOspfIf components.
      These components can be added and deleted."
::= { vrPpIpPortLogicalIfOspfIfRowStatusEntry 1 }

vrPpIpPortLogicalIfOspfIfComponentName OBJECT-TYPE
   SYNTAX     DisplayString 
   ACCESS     read-only
   STATUS     mandatory
   DESCRIPTION
     "This variable provides the component's string name for
      use with the ASCII Console Interface"
::= { vrPpIpPortLogicalIfOspfIfRowStatusEntry 2 }

vrPpIpPortLogicalIfOspfIfStorageType OBJECT-TYPE
   SYNTAX     StorageType 
   ACCESS     read-only
   STATUS     mandatory
   DESCRIPTION
     "This variable represents the storage type value for the
      vrPpIpPortLogicalIfOspfIf tables."
::= { vrPpIpPortLogicalIfOspfIfRowStatusEntry 4 }

vrPpIpPortLogicalIfOspfIfIndex OBJECT-TYPE
   SYNTAX     NonReplicated 
   ACCESS     not-accessible
   STATUS     mandatory
   DESCRIPTION
     "This variable represents the index for the vrPpIpPortLogicalIfOspfIf tables."
::= { vrPpIpPortLogicalIfOspfIfRowStatusEntry 10 }

vrPpIpPortLogicalIfOspfIfProvTable OBJECT-TYPE
   SYNTAX     SEQUENCE OF VrPpIpPortLogicalIfOspfIfProvEntry
   ACCESS     not-accessible
   STATUS     mandatory
   DESCRIPTION
     "This group of attributes identifies a provisionable set of attributes."
::= { vrPpIpPortLogicalIfOspfIf 10 }

vrPpIpPortLogicalIfOspfIfProvEntry OBJECT-TYPE
   SYNTAX     VrPpIpPortLogicalIfOspfIfProvEntry
   ACCESS     not-accessible
   STATUS     mandatory
   DESCRIPTION
     "An entry in the vrPpIpPortLogicalIfOspfIfProvTable."
   INDEX {
      vrIndex,
      vrPpIndex,
      vrPpIpPortIndex,
      vrPpIpPortLogicalIfAddressIndex,
      vrPpIpPortLogicalIfOspfIfIndex }
::= { vrPpIpPortLogicalIfOspfIfProvTable 1 }

VrPpIpPortLogicalIfOspfIfProvEntry ::= SEQUENCE {
   vrPpIpPortLogicalIfOspfIfAreaId
      AreaID,
   vrPpIpPortLogicalIfOspfIfIfType
      INTEGER,
   vrPpIpPortLogicalIfOspfIfSnmpAdminStatus
      INTEGER,
   vrPpIpPortLogicalIfOspfIfRtrPriority
      Unsigned32,
   vrPpIpPortLogicalIfOspfIfTransitDelay
      Unsigned32,
   vrPpIpPortLogicalIfOspfIfRetransInterval
      Unsigned32,
   vrPpIpPortLogicalIfOspfIfHelloInterval
      Unsigned32,
   vrPpIpPortLogicalIfOspfIfRtrDeadInterval
      Unsigned32,
   vrPpIpPortLogicalIfOspfIfPollInterval
      Unsigned32,
   vrPpIpPortLogicalIfOspfIfAuthKey
      HexString,
   vrPpIpPortLogicalIfOspfIfMulticastForwarding
      INTEGER }

vrPpIpPortLogicalIfOspfIfAreaId OBJECT-TYPE
   SYNTAX     AreaID 
   ACCESS     read-write
   STATUS     mandatory
   DESCRIPTION
     "The area Id this Ospf interface belongs to."
   DEFVAL     { '00000000'H }  -- "0.0.0.0"
::= { vrPpIpPortLogicalIfOspfIfProvEntry 1 }

vrPpIpPortLogicalIfOspfIfIfType OBJECT-TYPE
   SYNTAX     INTEGER  {
                 broadcast(1),
                 nbma(2),
                 pointToPoint(3),
                 loopback(5) }
   ACCESS     read-write
   STATUS     mandatory
   DESCRIPTION
     "This attribute indicates the type of this Ospf interface. This interface 
      type does not necessarily correlate with the type of the interface set on 
      the logicalIf entry under IpPort."
::= { vrPpIpPortLogicalIfOspfIfProvEntry 2 }

vrPpIpPortLogicalIfOspfIfSnmpAdminStatus OBJECT-TYPE
   SYNTAX     INTEGER  {
                 up(1),
                 down(2) }
   ACCESS     read-write
   STATUS     mandatory
   DESCRIPTION
     "The administrative status of this Ospf interface."
   DEFVAL     { up }
::= { vrPpIpPortLogicalIfOspfIfProvEntry 3 }

vrPpIpPortLogicalIfOspfIfRtrPriority OBJECT-TYPE
   SYNTAX     Unsigned32 (0..255)
   ACCESS     read-write
   STATUS     mandatory
   DESCRIPTION
     "The priority of this interface. Used in multi-access networks, this field is 
      used in the designated router election algorithm. The value 0 signifies 
      that the router is not eligible to become the designated router on this 
      particular protocol port. In the event of a tie in this value, routers will 
      use their routerId as a tie breaker."
   DEFVAL     { 1 }
::= { vrPpIpPortLogicalIfOspfIfProvEntry 4 }

vrPpIpPortLogicalIfOspfIfTransitDelay OBJECT-TYPE
   SYNTAX     Unsigned32 (1..3600)
   ACCESS     read-write
   STATUS     mandatory
   DESCRIPTION
     "The estimated number of seconds it takes to transmit a link-state update 
      packet over this interface."
   DEFVAL     { 1 }
::= { vrPpIpPortLogicalIfOspfIfProvEntry 5 }

vrPpIpPortLogicalIfOspfIfRetransInterval OBJECT-TYPE
   SYNTAX     Unsigned32 (1..3600)
   ACCESS     read-write
   STATUS     mandatory
   DESCRIPTION
     "The number of seconds between link-state advertisements 
      retransmissions, for adjacencies belonging to this interface. This value is 
      also used when retransmitting database description and link-state 
      request packets."
   DEFVAL     { 5 }
::= { vrPpIpPortLogicalIfOspfIfProvEntry 6 }

vrPpIpPortLogicalIfOspfIfHelloInterval OBJECT-TYPE
   SYNTAX     Unsigned32 (1..3600)
   ACCESS     read-write
   STATUS     mandatory
   DESCRIPTION
     "The length of time, in seconds, between the Hello packets that the router 
      sends on the interface. This value must be the same for all routers 
      attached to a common network."
   DEFVAL     { 10 }
::= { vrPpIpPortLogicalIfOspfIfProvEntry 7 }

vrPpIpPortLogicalIfOspfIfRtrDeadInterval OBJECT-TYPE
   SYNTAX     Unsigned32 (1..3600)
   ACCESS     read-write
   STATUS     mandatory
   DESCRIPTION
     "The number of seconds that a router's hello packets have not been seen 
      before it's neighbors declare the router down. This should be some 
      multiple of the helloIntereval. This value must be the same for all 
      routers attached to a common network."
   DEFVAL     { 40 }
::= { vrPpIpPortLogicalIfOspfIfProvEntry 8 }

vrPpIpPortLogicalIfOspfIfPollInterval OBJECT-TYPE
   SYNTAX     Unsigned32 (1..3600)
   ACCESS     read-write
   STATUS     mandatory
   DESCRIPTION
     "The largest time interval, in seconds, between the hello packets sent to 
      an inactive non-broadcast multi-access neighbor."
   DEFVAL     { 120 }
::= { vrPpIpPortLogicalIfOspfIfProvEntry 9 }

vrPpIpPortLogicalIfOspfIfAuthKey OBJECT-TYPE
   SYNTAX     HexString (SIZE (1..8))
   ACCESS     write-only
   STATUS     mandatory
   DESCRIPTION
     "The Authentication Key. If the value of the attribute authType of an 
      AreaEntry is simplePassword, and the authKey length is shorter than 8 
      octets, then the value of authKey will be left adjusted zero-filled to 8 
      octets."
   DEFVAL     { '0000000000000000'H }  -- "0000000000000000"
::= { vrPpIpPortLogicalIfOspfIfProvEntry 10 }

vrPpIpPortLogicalIfOspfIfMulticastForwarding OBJECT-TYPE
   SYNTAX     INTEGER  {
                 blocked(1) }
   ACCESS     read-write
   STATUS     mandatory
   DESCRIPTION
     "The way multicasts should be forwarded on this interface; non 
      forwarded, forwarded as data-link multicasts, or forwarded as data-link 
      unicasts. Data-link multicasting is not meaningful on point-to-point and 
      NBMA(No Broadcast Multi Access) interfaces, and setting this attribute 
      to blocked effectively disables all multicast forwarding."
   DEFVAL     { blocked }
::= { vrPpIpPortLogicalIfOspfIfProvEntry 12 }

vrPpIpPortLogicalIfOspfIfOperTable OBJECT-TYPE
   SYNTAX     SEQUENCE OF VrPpIpPortLogicalIfOspfIfOperEntry
   ACCESS     not-accessible
   STATUS     mandatory
   DESCRIPTION
     "This group of attributes identifies operational state that this interface is 
      performing."
::= { vrPpIpPortLogicalIfOspfIf 11 }

vrPpIpPortLogicalIfOspfIfOperEntry OBJECT-TYPE
   SYNTAX     VrPpIpPortLogicalIfOspfIfOperEntry
   ACCESS     not-accessible
   STATUS     mandatory
   DESCRIPTION
     "An entry in the vrPpIpPortLogicalIfOspfIfOperTable."
   INDEX {
      vrIndex,
      vrPpIndex,
      vrPpIpPortIndex,
      vrPpIpPortLogicalIfAddressIndex,
      vrPpIpPortLogicalIfOspfIfIndex }
::= { vrPpIpPortLogicalIfOspfIfOperTable 1 }

VrPpIpPortLogicalIfOspfIfOperEntry ::= SEQUENCE {
   vrPpIpPortLogicalIfOspfIfState
      INTEGER,
   vrPpIpPortLogicalIfOspfIfDesignatedRouter
      IpAddress,
   vrPpIpPortLogicalIfOspfIfBackupDesignatedRouter
      IpAddress,
   vrPpIpPortLogicalIfOspfIfEvents
      Counter32 }

vrPpIpPortLogicalIfOspfIfState OBJECT-TYPE
   SYNTAX     INTEGER  {
                 down(1),
                 loopback(2),
                 waiting(3),
                 pointToPoint(4),
                 designatedRouter(5),
                 backupDesignatedRouter(6),
                 otherDesignatedRouter(7) }
   ACCESS     read-only
   STATUS     mandatory
   DESCRIPTION
     "The state of the OSPF interface."
   DEFVAL     { designatedRouter }
::= { vrPpIpPortLogicalIfOspfIfOperEntry 1 }

vrPpIpPortLogicalIfOspfIfDesignatedRouter OBJECT-TYPE
   SYNTAX     IpAddress 
   ACCESS     read-only
   STATUS     mandatory
   DESCRIPTION
     "The Ip address of the designated router."
::= { vrPpIpPortLogicalIfOspfIfOperEntry 2 }

vrPpIpPortLogicalIfOspfIfBackupDesignatedRouter OBJECT-TYPE
   SYNTAX     IpAddress 
   ACCESS     read-only
   STATUS     mandatory
   DESCRIPTION
     "The Ip address of the backup designated router"
::= { vrPpIpPortLogicalIfOspfIfOperEntry 3 }

vrPpIpPortLogicalIfOspfIfEvents OBJECT-TYPE
   SYNTAX     Counter32 
   ACCESS     read-only
   STATUS     mandatory
   DESCRIPTION
     "The number of times this OSPF interface has changed its state or an 
      error has occurred."
::= { vrPpIpPortLogicalIfOspfIfOperEntry 4 }

vrPpIpPortLogicalIfOspfIfMetricTable OBJECT-TYPE
   SYNTAX     SEQUENCE OF VrPpIpPortLogicalIfOspfIfMetricEntry
   ACCESS     not-accessible
   STATUS     mandatory
   DESCRIPTION
     "This group contains the operational metric attribute of this interface."
::= { vrPpIpPortLogicalIfOspfIf 12 }

vrPpIpPortLogicalIfOspfIfMetricEntry OBJECT-TYPE
   SYNTAX     VrPpIpPortLogicalIfOspfIfMetricEntry
   ACCESS     not-accessible
   STATUS     mandatory
   DESCRIPTION
     "An entry in the vrPpIpPortLogicalIfOspfIfMetricTable."
   INDEX {
      vrIndex,
      vrPpIndex,
      vrPpIpPortIndex,
      vrPpIpPortLogicalIfAddressIndex,
      vrPpIpPortLogicalIfOspfIfIndex }
::= { vrPpIpPortLogicalIfOspfIfMetricTable 1 }

VrPpIpPortLogicalIfOspfIfMetricEntry ::= SEQUENCE {
   vrPpIpPortLogicalIfOspfIfMetric
      Unsigned32 }

vrPpIpPortLogicalIfOspfIfMetric OBJECT-TYPE
   SYNTAX     Unsigned32 (0..4294967295)
   ACCESS     read-only
   STATUS     mandatory
   DESCRIPTION
     "This attribute indicates the metric being used by this OspfIf. The metric 
      is derived in one of two ways:
      1. If there is a TypeOfService component provisioned under this OspfIf 
      component, then the value of the metric attribute is copied from the 
      provisionable attribute tosMetric.
      2. Otherwise, the metric is computed based on the interface speed. If the 
      interface speed is greater than 100 Mbit/s, then the metric is 1. If the 
      interface speed is less than 100 Mbit/s, then the metric is 100 Mbit/s 
      divided by the interface speed. If the interface speed is unknown, then it 
      is treated as 1.54 Mbit/s during the calculation.
      The value of interface speed is available by displaying the ifSpeed 
      attribute of the corresponding IfTableEntry component."
::= { vrPpIpPortLogicalIfOspfIfMetricEntry 1 }


-- Vr/<string> Pp/<string> IpPort logicalIf/<Ip Address> ospfIf 
-- OspfIfTypeOfService/<Decimal>
-- This component describes the metrics to be advertised for a specified 
-- interface at various types-of-service.

vrPpIpPortLogicalIfOspfIfTOS OBJECT IDENTIFIER ::= { vrPpIpPortLogicalIfOspfIf 2 }



vrPpIpPortLogicalIfOspfIfTOSRowStatusTable OBJECT-TYPE
   SYNTAX     SEQUENCE OF VrPpIpPortLogicalIfOspfIfTOSRowStatusEntry
   ACCESS     not-accessible
   STATUS     mandatory
   DESCRIPTION
     "This entry controls the addition and deletion of 
      vrPpIpPortLogicalIfOspfIfTOS components."
::= { vrPpIpPortLogicalIfOspfIfTOS 1 }

vrPpIpPortLogicalIfOspfIfTOSRowStatusEntry OBJECT-TYPE
   SYNTAX     VrPpIpPortLogicalIfOspfIfTOSRowStatusEntry
   ACCESS     not-accessible
   STATUS     mandatory
   DESCRIPTION
     "A single entry in the table represents a single 
      vrPpIpPortLogicalIfOspfIfTOS component."
   INDEX {
      vrIndex,
      vrPpIndex,
      vrPpIpPortIndex,
      vrPpIpPortLogicalIfAddressIndex,
      vrPpIpPortLogicalIfOspfIfIndex,
      vrPpIpPortLogicalIfOspfIfTOSMetricTosIndex }
::= { vrPpIpPortLogicalIfOspfIfTOSRowStatusTable 1 }

VrPpIpPortLogicalIfOspfIfTOSRowStatusEntry ::= SEQUENCE {
   vrPpIpPortLogicalIfOspfIfTOSRowStatus
      RowStatus,
   vrPpIpPortLogicalIfOspfIfTOSComponentName
      DisplayString,
   vrPpIpPortLogicalIfOspfIfTOSStorageType
      StorageType,
   vrPpIpPortLogicalIfOspfIfTOSMetricTosIndex
      Integer32 }

vrPpIpPortLogicalIfOspfIfTOSRowStatus OBJECT-TYPE
   SYNTAX     RowStatus 
   ACCESS     read-write
   STATUS     mandatory
   DESCRIPTION
     "This variable is used as the basis for SNMP naming of
      vrPpIpPortLogicalIfOspfIfTOS components.
      These components can be added and deleted."
::= { vrPpIpPortLogicalIfOspfIfTOSRowStatusEntry 1 }

vrPpIpPortLogicalIfOspfIfTOSComponentName OBJECT-TYPE
   SYNTAX     DisplayString 
   ACCESS     read-only
   STATUS     mandatory
   DESCRIPTION
     "This variable provides the component's string name for
      use with the ASCII Console Interface"
::= { vrPpIpPortLogicalIfOspfIfTOSRowStatusEntry 2 }

vrPpIpPortLogicalIfOspfIfTOSStorageType OBJECT-TYPE
   SYNTAX     StorageType 
   ACCESS     read-only
   STATUS     mandatory
   DESCRIPTION
     "This variable represents the storage type value for the
      vrPpIpPortLogicalIfOspfIfTOS tables."
::= { vrPpIpPortLogicalIfOspfIfTOSRowStatusEntry 4 }

vrPpIpPortLogicalIfOspfIfTOSMetricTosIndex OBJECT-TYPE
   SYNTAX     Integer32 (0..0)
   ACCESS     not-accessible
   STATUS     mandatory
   DESCRIPTION
     "This variable represents the index for the vrPpIpPortLogicalIfOspfIfTOS tables."
::= { vrPpIpPortLogicalIfOspfIfTOSRowStatusEntry 10 }

vrPpIpPortLogicalIfOspfIfTOSProvTable OBJECT-TYPE
   SYNTAX     SEQUENCE OF VrPpIpPortLogicalIfOspfIfTOSProvEntry
   ACCESS     not-accessible
   STATUS     mandatory
   DESCRIPTION
     "Identifies a provisionable set of attributes."
::= { vrPpIpPortLogicalIfOspfIfTOS 10 }

vrPpIpPortLogicalIfOspfIfTOSProvEntry OBJECT-TYPE
   SYNTAX     VrPpIpPortLogicalIfOspfIfTOSProvEntry
   ACCESS     not-accessible
   STATUS     mandatory
   DESCRIPTION
     "An entry in the vrPpIpPortLogicalIfOspfIfTOSProvTable."
   INDEX {
      vrIndex,
      vrPpIndex,
      vrPpIpPortIndex,
      vrPpIpPortLogicalIfAddressIndex,
      vrPpIpPortLogicalIfOspfIfIndex,
      vrPpIpPortLogicalIfOspfIfTOSMetricTosIndex }
::= { vrPpIpPortLogicalIfOspfIfTOSProvTable 1 }

VrPpIpPortLogicalIfOspfIfTOSProvEntry ::= SEQUENCE {
   vrPpIpPortLogicalIfOspfIfTOSTosMetric
      Unsigned32 }

vrPpIpPortLogicalIfOspfIfTOSTosMetric OBJECT-TYPE
   SYNTAX     Unsigned32 (0..65535)
   ACCESS     read-write
   STATUS     mandatory
   DESCRIPTION
     "The metric using this typeOfService on this interface."
::= { vrPpIpPortLogicalIfOspfIfTOSProvEntry 1 }


-- Vr/<string> Pp/<string> IpPort logicalIf/<Ip Address> ospfIf 
-- OspfIfNeighbor/<Ip Address>
-- This component specifies the neighbors on a multi-access non-broadcast 
-- media. This can also be viewed as the provisioned entries of Ospf 
-- NeighborTable.

vrPpIpPortLogicalIfOspfIfNbr OBJECT IDENTIFIER ::= { vrPpIpPortLogicalIfOspfIf 3 }



vrPpIpPortLogicalIfOspfIfNbrRowStatusTable OBJECT-TYPE
   SYNTAX     SEQUENCE OF VrPpIpPortLogicalIfOspfIfNbrRowStatusEntry
   ACCESS     not-accessible
   STATUS     mandatory
   DESCRIPTION
     "This entry controls the addition and deletion of 
      vrPpIpPortLogicalIfOspfIfNbr components."
::= { vrPpIpPortLogicalIfOspfIfNbr 1 }

vrPpIpPortLogicalIfOspfIfNbrRowStatusEntry OBJECT-TYPE
   SYNTAX     VrPpIpPortLogicalIfOspfIfNbrRowStatusEntry
   ACCESS     not-accessible
   STATUS     mandatory
   DESCRIPTION
     "A single entry in the table represents a single 
      vrPpIpPortLogicalIfOspfIfNbr component."
   INDEX {
      vrIndex,
      vrPpIndex,
      vrPpIpPortIndex,
      vrPpIpPortLogicalIfAddressIndex,
      vrPpIpPortLogicalIfOspfIfIndex,
      vrPpIpPortLogicalIfOspfIfNbrAddressIndex }
::= { vrPpIpPortLogicalIfOspfIfNbrRowStatusTable 1 }

VrPpIpPortLogicalIfOspfIfNbrRowStatusEntry ::= SEQUENCE {
   vrPpIpPortLogicalIfOspfIfNbrRowStatus
      RowStatus,
   vrPpIpPortLogicalIfOspfIfNbrComponentName
      DisplayString,
   vrPpIpPortLogicalIfOspfIfNbrStorageType
      StorageType,
   vrPpIpPortLogicalIfOspfIfNbrAddressIndex
      IpAddress }

vrPpIpPortLogicalIfOspfIfNbrRowStatus OBJECT-TYPE
   SYNTAX     RowStatus 
   ACCESS     read-write
   STATUS     mandatory
   DESCRIPTION
     "This variable is used as the basis for SNMP naming of
      vrPpIpPortLogicalIfOspfIfNbr components.
      These components can be added and deleted."
::= { vrPpIpPortLogicalIfOspfIfNbrRowStatusEntry 1 }

vrPpIpPortLogicalIfOspfIfNbrComponentName OBJECT-TYPE
   SYNTAX     DisplayString 
   ACCESS     read-only
   STATUS     mandatory
   DESCRIPTION
     "This variable provides the component's string name for
      use with the ASCII Console Interface"
::= { vrPpIpPortLogicalIfOspfIfNbrRowStatusEntry 2 }

vrPpIpPortLogicalIfOspfIfNbrStorageType OBJECT-TYPE
   SYNTAX     StorageType 
   ACCESS     read-only
   STATUS     mandatory
   DESCRIPTION
     "This variable represents the storage type value for the
      vrPpIpPortLogicalIfOspfIfNbr tables."
::= { vrPpIpPortLogicalIfOspfIfNbrRowStatusEntry 4 }

vrPpIpPortLogicalIfOspfIfNbrAddressIndex OBJECT-TYPE
   SYNTAX     IpAddress 
   ACCESS     not-accessible
   STATUS     mandatory
   DESCRIPTION
     "This variable represents the index for the vrPpIpPortLogicalIfOspfIfNbr tables."
::= { vrPpIpPortLogicalIfOspfIfNbrRowStatusEntry 10 }

vrPpIpPortLogicalIfOspfIfNbrProvTable OBJECT-TYPE
   SYNTAX     SEQUENCE OF VrPpIpPortLogicalIfOspfIfNbrProvEntry
   ACCESS     not-accessible
   STATUS     mandatory
   DESCRIPTION
     "Identifies a group of Provisionable attributes."
::= { vrPpIpPortLogicalIfOspfIfNbr 10 }

vrPpIpPortLogicalIfOspfIfNbrProvEntry OBJECT-TYPE
   SYNTAX     VrPpIpPortLogicalIfOspfIfNbrProvEntry
   ACCESS     not-accessible
   STATUS     mandatory
   DESCRIPTION
     "An entry in the vrPpIpPortLogicalIfOspfIfNbrProvTable."
   INDEX {
      vrIndex,
      vrPpIndex,
      vrPpIpPortIndex,
      vrPpIpPortLogicalIfAddressIndex,
      vrPpIpPortLogicalIfOspfIfIndex,
      vrPpIpPortLogicalIfOspfIfNbrAddressIndex }
::= { vrPpIpPortLogicalIfOspfIfNbrProvTable 1 }

VrPpIpPortLogicalIfOspfIfNbrProvEntry ::= SEQUENCE {
   vrPpIpPortLogicalIfOspfIfNbrPriority
      Unsigned32 }

vrPpIpPortLogicalIfOspfIfNbrPriority OBJECT-TYPE
   SYNTAX     Unsigned32 (0..255)
   ACCESS     read-write
   STATUS     mandatory
   DESCRIPTION
     "The priority of this neighbor in the designated router election algorithm. 
      The value 0 signifies that the neighbor is not eligible to become the 
      designated router on this particular network. The higher the number, the 
      better are the chances of being a designated router."
   DEFVAL     { 1 }
::= { vrPpIpPortLogicalIfOspfIfNbrProvEntry 1 }

vrPpIpPortLogicalIfOspfIfNbrOperTable OBJECT-TYPE
   SYNTAX     SEQUENCE OF VrPpIpPortLogicalIfOspfIfNbrOperEntry
   ACCESS     not-accessible
   STATUS     mandatory
   DESCRIPTION
     "Contains the Operational set of attributes for the Neighbor."
::= { vrPpIpPortLogicalIfOspfIfNbr 11 }

vrPpIpPortLogicalIfOspfIfNbrOperEntry OBJECT-TYPE
   SYNTAX     VrPpIpPortLogicalIfOspfIfNbrOperEntry
   ACCESS     not-accessible
   STATUS     mandatory
   DESCRIPTION
     "An entry in the vrPpIpPortLogicalIfOspfIfNbrOperTable."
   INDEX {
      vrIndex,
      vrPpIndex,
      vrPpIpPortIndex,
      vrPpIpPortLogicalIfAddressIndex,
      vrPpIpPortLogicalIfOspfIfIndex,
      vrPpIpPortLogicalIfOspfIfNbrAddressIndex }
::= { vrPpIpPortLogicalIfOspfIfNbrOperTable 1 }

VrPpIpPortLogicalIfOspfIfNbrOperEntry ::= SEQUENCE {
   vrPpIpPortLogicalIfOspfIfNbrRtrId
      RouterID,
   vrPpIpPortLogicalIfOspfIfNbrOptions
      Unsigned32,
   vrPpIpPortLogicalIfOspfIfNbrState
      INTEGER,
   vrPpIpPortLogicalIfOspfIfNbrEvents
      Counter32,
   vrPpIpPortLogicalIfOspfIfNbrLsRetransQlen
      Gauge32,
   vrPpIpPortLogicalIfOspfIfNbrExchangeStatus
      INTEGER,
   vrPpIpPortLogicalIfOspfIfNbrPermanance
      INTEGER }

vrPpIpPortLogicalIfOspfIfNbrRtrId OBJECT-TYPE
   SYNTAX     RouterID 
   ACCESS     read-only
   STATUS     mandatory
   DESCRIPTION
     "An Ip Address uniquely identifying the neighboring router in the 
      Autonomous System."
::= { vrPpIpPortLogicalIfOspfIfNbrOperEntry 1 }

vrPpIpPortLogicalIfOspfIfNbrOptions OBJECT-TYPE
   SYNTAX     Unsigned32 (0..15)
   ACCESS     read-only
   STATUS     mandatory
   DESCRIPTION
     "A bit mask corresponding to the neighbor's options field. Bit 0, if set, 
      indicates that the area accepts and operates on external information, if 
      zero, it is a stub area. Bit 1, if set, indicates that the system will operate 
      on Type of Service metrics other than TOS 0. If zero, the neighbor will 
      ignore all metrics except the TOS 0 metric. Bit 2, if set, indicates that 
      the system is Network Multicast capable; i.e., that it implements OSPF 
      Multicast Routing."
::= { vrPpIpPortLogicalIfOspfIfNbrOperEntry 2 }

vrPpIpPortLogicalIfOspfIfNbrState OBJECT-TYPE
   SYNTAX     INTEGER  {
                 down(1),
                 attempt(2),
                 init(3),
                 twoWay(4),
                 exchangeStart(5),
                 exchange(6),
                 loading(7),
                 full(8) }
   ACCESS     read-only
   STATUS     mandatory
   DESCRIPTION
     "The state of the relationship with this neighbor."
::= { vrPpIpPortLogicalIfOspfIfNbrOperEntry 3 }

vrPpIpPortLogicalIfOspfIfNbrEvents OBJECT-TYPE
   SYNTAX     Counter32 
   ACCESS     read-only
   STATUS     mandatory
   DESCRIPTION
     "The number of times this neighbor relationship has changed state, or an 
      error has occurred."
::= { vrPpIpPortLogicalIfOspfIfNbrOperEntry 4 }

vrPpIpPortLogicalIfOspfIfNbrLsRetransQlen OBJECT-TYPE
   SYNTAX     Gauge32 (0..4294967295)
   ACCESS     read-only
   STATUS     mandatory
   DESCRIPTION
     "The current length of the Retransmission queue."
::= { vrPpIpPortLogicalIfOspfIfNbrOperEntry 5 }

vrPpIpPortLogicalIfOspfIfNbrExchangeStatus OBJECT-TYPE
   SYNTAX     INTEGER  {
                 master(1),
                 slave(2) }
   ACCESS     read-only
   STATUS     mandatory
   DESCRIPTION
     "Indicates the exchange status for a neighbor Entry."
::= { vrPpIpPortLogicalIfOspfIfNbrOperEntry 6 }

vrPpIpPortLogicalIfOspfIfNbrPermanance OBJECT-TYPE
   SYNTAX     INTEGER  {
                 permanent(1),
                 dynamic(2) }
   ACCESS     read-only
   STATUS     mandatory
   DESCRIPTION
     "This attribute displays how the neighbor became an entry."
   DEFVAL     { permanent }
::= { vrPpIpPortLogicalIfOspfIfNbrOperEntry 9 }


-- Vr/<X> Pp/<X> IpPort LogicalIf/<Ip Address> RipInterface
-- This component is used to configure a LogicalIf to run RIP protocol.

vrPpIpPortLogicalIfRipIf OBJECT IDENTIFIER ::= { vrPpIpPortLogicalIf 3 }



vrPpIpPortLogicalIfRipIfRowStatusTable OBJECT-TYPE
   SYNTAX     SEQUENCE OF VrPpIpPortLogicalIfRipIfRowStatusEntry
   ACCESS     not-accessible
   STATUS     mandatory
   DESCRIPTION
     "This entry controls the addition and deletion of 
      vrPpIpPortLogicalIfRipIf components."
::= { vrPpIpPortLogicalIfRipIf 1 }

vrPpIpPortLogicalIfRipIfRowStatusEntry OBJECT-TYPE
   SYNTAX     VrPpIpPortLogicalIfRipIfRowStatusEntry
   ACCESS     not-accessible
   STATUS     mandatory
   DESCRIPTION
     "A single entry in the table represents a single 
      vrPpIpPortLogicalIfRipIf component."
   INDEX {
      vrIndex,
      vrPpIndex,
      vrPpIpPortIndex,
      vrPpIpPortLogicalIfAddressIndex,
      vrPpIpPortLogicalIfRipIfIndex }
::= { vrPpIpPortLogicalIfRipIfRowStatusTable 1 }

VrPpIpPortLogicalIfRipIfRowStatusEntry ::= SEQUENCE {
   vrPpIpPortLogicalIfRipIfRowStatus
      RowStatus,
   vrPpIpPortLogicalIfRipIfComponentName
      DisplayString,
   vrPpIpPortLogicalIfRipIfStorageType
      StorageType,
   vrPpIpPortLogicalIfRipIfIndex
      NonReplicated }

vrPpIpPortLogicalIfRipIfRowStatus OBJECT-TYPE
   SYNTAX     RowStatus 
   ACCESS     read-write
   STATUS     mandatory
   DESCRIPTION
     "This variable is used as the basis for SNMP naming of
      vrPpIpPortLogicalIfRipIf components.
      These components can be added and deleted."
::= { vrPpIpPortLogicalIfRipIfRowStatusEntry 1 }

vrPpIpPortLogicalIfRipIfComponentName OBJECT-TYPE
   SYNTAX     DisplayString 
   ACCESS     read-only
   STATUS     mandatory
   DESCRIPTION
     "This variable provides the component's string name for
      use with the ASCII Console Interface"
::= { vrPpIpPortLogicalIfRipIfRowStatusEntry 2 }

vrPpIpPortLogicalIfRipIfStorageType OBJECT-TYPE
   SYNTAX     StorageType 
   ACCESS     read-only
   STATUS     mandatory
   DESCRIPTION
     "This variable represents the storage type value for the
      vrPpIpPortLogicalIfRipIf tables."
::= { vrPpIpPortLogicalIfRipIfRowStatusEntry 4 }

vrPpIpPortLogicalIfRipIfIndex OBJECT-TYPE
   SYNTAX     NonReplicated 
   ACCESS     not-accessible
   STATUS     mandatory
   DESCRIPTION
     "This variable represents the index for the vrPpIpPortLogicalIfRipIf tables."
::= { vrPpIpPortLogicalIfRipIfRowStatusEntry 10 }

vrPpIpPortLogicalIfRipIfProvTable OBJECT-TYPE
   SYNTAX     SEQUENCE OF VrPpIpPortLogicalIfRipIfProvEntry
   ACCESS     not-accessible
   STATUS     mandatory
   DESCRIPTION
     "This group contains the provisionable attributes of the RipIf component."
::= { vrPpIpPortLogicalIfRipIf 10 }

vrPpIpPortLogicalIfRipIfProvEntry OBJECT-TYPE
   SYNTAX     VrPpIpPortLogicalIfRipIfProvEntry
   ACCESS     not-accessible
   STATUS     mandatory
   DESCRIPTION
     "An entry in the vrPpIpPortLogicalIfRipIfProvTable."
   INDEX {
      vrIndex,
      vrPpIndex,
      vrPpIpPortIndex,
      vrPpIpPortLogicalIfAddressIndex,
      vrPpIpPortLogicalIfRipIfIndex }
::= { vrPpIpPortLogicalIfRipIfProvTable 1 }

VrPpIpPortLogicalIfRipIfProvEntry ::= SEQUENCE {
   vrPpIpPortLogicalIfRipIfSnmpAdminStatus
      INTEGER,
   vrPpIpPortLogicalIfRipIfMetric
      Unsigned32,
   vrPpIpPortLogicalIfRipIfSilentFlag
      INTEGER,
   vrPpIpPortLogicalIfRipIfPoisonReverseFlag
      INTEGER,
   vrPpIpPortLogicalIfRipIfFlashUpdateFlag
      INTEGER,
   vrPpIpPortLogicalIfRipIfNetworkRouteStatus
      INTEGER,
   vrPpIpPortLogicalIfRipIfDefaultRouteMetric
      Unsigned32,
   vrPpIpPortLogicalIfRipIfAcceptDefault
      INTEGER,
   vrPpIpPortLogicalIfRipIfIfConfSend
      INTEGER,
   vrPpIpPortLogicalIfRipIfIfConfReceive
      INTEGER }

vrPpIpPortLogicalIfRipIfSnmpAdminStatus OBJECT-TYPE
   SYNTAX     INTEGER  {
                 up(1),
                 down(2) }
   ACCESS     read-write
   STATUS     mandatory
   DESCRIPTION
     "Identifies the administrative status of this RipInterface. Setting this value 
      to disabled will have the effect of rendering it inactive."
   DEFVAL     { up }
::= { vrPpIpPortLogicalIfRipIfProvEntry 1 }

vrPpIpPortLogicalIfRipIfMetric OBJECT-TYPE
   SYNTAX     Unsigned32 (1..16)
   ACCESS     read-write
   STATUS     mandatory
   DESCRIPTION
     "This attribute is the RIP metric for this logical interface."
   DEFVAL     { 1 }
::= { vrPpIpPortLogicalIfRipIfProvEntry 2 }

vrPpIpPortLogicalIfRipIfSilentFlag OBJECT-TYPE
   SYNTAX     INTEGER  {
                 true(1),
                 false(2) }
   ACCESS     read-write
   STATUS     obsolete
   DESCRIPTION
     "If the value of this attribute is set to true, the protocol will only listen to 
      RIP updates, If set to false, then Rip will listen and send RIP 
      updates.This attribute has been migrated to ifConfSend."
   DEFVAL     { false }
::= { vrPpIpPortLogicalIfRipIfProvEntry 3 }

vrPpIpPortLogicalIfRipIfPoisonReverseFlag OBJECT-TYPE
   SYNTAX     INTEGER  {
                 true(1),
                 false(2) }
   ACCESS     read-write
   STATUS     mandatory
   DESCRIPTION
     "If the value of this attribute is set to true, then poison reverse algorithm 
      is used when sending out the updates otherwise use split horizon only."
   DEFVAL     { false }
::= { vrPpIpPortLogicalIfRipIfProvEntry 4 }

vrPpIpPortLogicalIfRipIfFlashUpdateFlag OBJECT-TYPE
   SYNTAX     INTEGER  {
                 true(1),
                 false(2) }
   ACCESS     read-write
   STATUS     mandatory
   DESCRIPTION
     "This attribute when set to true will send updates when updates are 
      received; otherwise RIP will wait till the next update period."
   DEFVAL     { true }
::= { vrPpIpPortLogicalIfRipIfProvEntry 5 }

vrPpIpPortLogicalIfRipIfNetworkRouteStatus OBJECT-TYPE
   SYNTAX     INTEGER  {
                 naturalNetWithOutDefaultRoute(1),
                 naturalNetWithDefaultRoute(2),
                 defaultRouteOnly(3),
                 subnetsOnly(4) }
   ACCESS     read-write
   STATUS     mandatory
   DESCRIPTION
     "This attribute determines what type of network routes will be sent and 
      whether a default route will be generated for this RipInterface. 
      Generated default routes will not go into the routing table, but are sent in 
      the updates going out on the interface. The possible values for this 
      attribute are:
      
      naturalNetWithOutDefaultRoute - This value will cause normal RIP 
      network routes to be put in the update. This means that the address of 
      logicalIf pertaining to this RipInterface knowledge is taken into account 
      in determining if the subnetted network or the natural network is sent for 
      any route going into this update.
      
      naturalNetWithDefaultRoute - Selecting this value will cause a default 
      route to be generated with the value of the metric selected for the 
      attribute defaultRouteMetric.
      
      defaultRouteOnly - Selection of this value causes the default route to be 
      generated with the value of the metric selected for the attribute 
      defaultRouteMetric.
      NOTE: No other routes will go in the update.
      
      subnetsOnly - selection of this value will cause only subnet information 
      to be put in the update. No default routes will be generated or passed on. 
      Only subnetted routes that are part of the same subnetted network that 
      this logicalInterface is on will be put in the update.
      NOTE: this also effects receiving of updates on this interface. Only 
      subnetted routes that are part of the same subnetted network that this 
      logicalInterface is on will be accepted on a received RIP update on this 
      RipInterface."
   DEFVAL     { naturalNetWithOutDefaultRoute }
::= { vrPpIpPortLogicalIfRipIfProvEntry 6 }

vrPpIpPortLogicalIfRipIfDefaultRouteMetric OBJECT-TYPE
   SYNTAX     Unsigned32 (1..16)
   ACCESS     read-write
   STATUS     mandatory
   DESCRIPTION
     "This attribute identifies the metric value for the default route. This value 
      is only used if the attribute networkRouteStatus is configured with a 
      value of either naturalNetWithDefaultRoute or defaultRouteOnly"
   DEFVAL     { 1 }
::= { vrPpIpPortLogicalIfRipIfProvEntry 7 }

vrPpIpPortLogicalIfRipIfAcceptDefault OBJECT-TYPE
   SYNTAX     INTEGER  {
                 true(1),
                 false(2) }
   ACCESS     read-write
   STATUS     mandatory
   DESCRIPTION
     "If this attribute is set to true, then accept the default route from this 
      interface."
   DEFVAL     { true }
::= { vrPpIpPortLogicalIfRipIfProvEntry 8 }

vrPpIpPortLogicalIfRipIfIfConfSend OBJECT-TYPE
   SYNTAX     INTEGER  {
                 doNotSend(1),
                 ripVersion1(2),
                 rip1Compatible(3),
                 ripVersion2(4) }
   ACCESS     read-write
   STATUS     mandatory
   DESCRIPTION
     "This attribute identifies what the router sends on this RipIf. ripVersion1 
      implies sending RIP updates compliant with  RFC  1058.   
      rip1Compatible implies broadcasting RIP-2 updates according to RFC 
      1058.  ripVersion2 implies multicasting RIP-2 updates."
   DEFVAL     { rip1Compatible }
::= { vrPpIpPortLogicalIfRipIfProvEntry 12 }

vrPpIpPortLogicalIfRipIfIfConfReceive OBJECT-TYPE
   SYNTAX     INTEGER  {
                 rip1(1),
                 rip2(2),
                 rip1OrRip2(3),
                 doNotReceive(4) }
   ACCESS     read-write
   STATUS     mandatory
   DESCRIPTION
     "This attribute identifies which version of RIP updates are to be accepted 
      on this RipIf.  Note that rip2 and rip1OrRip2 implies reception of 
      multicast packets."
   DEFVAL     { rip1OrRip2 }
::= { vrPpIpPortLogicalIfRipIfProvEntry 13 }

vrPpIpPortLogicalIfRipIfStatTable OBJECT-TYPE
   SYNTAX     SEQUENCE OF VrPpIpPortLogicalIfRipIfStatEntry
   ACCESS     not-accessible
   STATUS     mandatory
   DESCRIPTION
     "This group contains operational attributes of the RipIf component. These 
      attributes are statistical data corresponding to the RIP-2 standard MIB 
      (rfc 1724) rip2Status table."
::= { vrPpIpPortLogicalIfRipIf 11 }

vrPpIpPortLogicalIfRipIfStatEntry OBJECT-TYPE
   SYNTAX     VrPpIpPortLogicalIfRipIfStatEntry
   ACCESS     not-accessible
   STATUS     mandatory
   DESCRIPTION
     "An entry in the vrPpIpPortLogicalIfRipIfStatTable."
   INDEX {
      vrIndex,
      vrPpIndex,
      vrPpIpPortIndex,
      vrPpIpPortLogicalIfAddressIndex,
      vrPpIpPortLogicalIfRipIfIndex }
::= { vrPpIpPortLogicalIfRipIfStatTable 1 }

VrPpIpPortLogicalIfRipIfStatEntry ::= SEQUENCE {
   vrPpIpPortLogicalIfRipIfIfBadPacketRcv
      Unsigned32,
   vrPpIpPortLogicalIfRipIfIfBadRouteRcv
      Unsigned32,
   vrPpIpPortLogicalIfRipIfIfTriggeredUpdates
      Unsigned32 }

vrPpIpPortLogicalIfRipIfIfBadPacketRcv OBJECT-TYPE
   SYNTAX     Unsigned32 (0..4294967295)
   ACCESS     read-only
   STATUS     mandatory
   DESCRIPTION
     "This attribute counts the number of RIP response packets recieved by 
      the RIP process which were subsequently discarded for any reason."
   DEFVAL     { 0 }
::= { vrPpIpPortLogicalIfRipIfStatEntry 1 }

vrPpIpPortLogicalIfRipIfIfBadRouteRcv OBJECT-TYPE
   SYNTAX     Unsigned32 (0..4294967295)
   ACCESS     read-only
   STATUS     mandatory
   DESCRIPTION
     "This attribute counts how many routes, in valid RIP packets, were 
      ignored for any reason."
   DEFVAL     { 0 }
::= { vrPpIpPortLogicalIfRipIfStatEntry 2 }

vrPpIpPortLogicalIfRipIfIfTriggeredUpdates OBJECT-TYPE
   SYNTAX     Unsigned32 (0..4294967295)
   ACCESS     read-only
   STATUS     mandatory
   DESCRIPTION
     "This attribute counts the number of triggered updates actually sent on 
      this interface. This explicitly does NOT include full updates sent 
      containing new information."
   DEFVAL     { 0 }
::= { vrPpIpPortLogicalIfRipIfStatEntry 3 }


-- Vr/<string> Pp/<string> IpPort logicalIf/<Ip Address> RipIf 
-- Neighbor/<Ip address>
-- This component is used to configure the Ip Address of the non broadcast 
-- multi access (NBMA) neighbor.

vrPpIpPortLogicalIfRipIfNbr OBJECT IDENTIFIER ::= { vrPpIpPortLogicalIfRipIf 2 }



vrPpIpPortLogicalIfRipIfNbrRowStatusTable OBJECT-TYPE
   SYNTAX     SEQUENCE OF VrPpIpPortLogicalIfRipIfNbrRowStatusEntry
   ACCESS     not-accessible
   STATUS     mandatory
   DESCRIPTION
     "This entry controls the addition and deletion of 
      vrPpIpPortLogicalIfRipIfNbr components."
::= { vrPpIpPortLogicalIfRipIfNbr 1 }

vrPpIpPortLogicalIfRipIfNbrRowStatusEntry OBJECT-TYPE
   SYNTAX     VrPpIpPortLogicalIfRipIfNbrRowStatusEntry
   ACCESS     not-accessible
   STATUS     mandatory
   DESCRIPTION
     "A single entry in the table represents a single 
      vrPpIpPortLogicalIfRipIfNbr component."
   INDEX {
      vrIndex,
      vrPpIndex,
      vrPpIpPortIndex,
      vrPpIpPortLogicalIfAddressIndex,
      vrPpIpPortLogicalIfRipIfIndex,
      vrPpIpPortLogicalIfRipIfNbrIndex }
::= { vrPpIpPortLogicalIfRipIfNbrRowStatusTable 1 }

VrPpIpPortLogicalIfRipIfNbrRowStatusEntry ::= SEQUENCE {
   vrPpIpPortLogicalIfRipIfNbrRowStatus
      RowStatus,
   vrPpIpPortLogicalIfRipIfNbrComponentName
      DisplayString,
   vrPpIpPortLogicalIfRipIfNbrStorageType
      StorageType,
   vrPpIpPortLogicalIfRipIfNbrIndex
      IpAddress }

vrPpIpPortLogicalIfRipIfNbrRowStatus OBJECT-TYPE
   SYNTAX     RowStatus 
   ACCESS     read-write
   STATUS     mandatory
   DESCRIPTION
     "This variable is used as the basis for SNMP naming of
      vrPpIpPortLogicalIfRipIfNbr components.
      These components can be added and deleted."
::= { vrPpIpPortLogicalIfRipIfNbrRowStatusEntry 1 }

vrPpIpPortLogicalIfRipIfNbrComponentName OBJECT-TYPE
   SYNTAX     DisplayString 
   ACCESS     read-only
   STATUS     mandatory
   DESCRIPTION
     "This variable provides the component's string name for
      use with the ASCII Console Interface"
::= { vrPpIpPortLogicalIfRipIfNbrRowStatusEntry 2 }

vrPpIpPortLogicalIfRipIfNbrStorageType OBJECT-TYPE
   SYNTAX     StorageType 
   ACCESS     read-only
   STATUS     mandatory
   DESCRIPTION
     "This variable represents the storage type value for the
      vrPpIpPortLogicalIfRipIfNbr tables."
::= { vrPpIpPortLogicalIfRipIfNbrRowStatusEntry 4 }

vrPpIpPortLogicalIfRipIfNbrIndex OBJECT-TYPE
   SYNTAX     IpAddress 
   ACCESS     not-accessible
   STATUS     mandatory
   DESCRIPTION
     "This variable represents the index for the vrPpIpPortLogicalIfRipIfNbr tables."
::= { vrPpIpPortLogicalIfRipIfNbrRowStatusEntry 10 }


-- Vr/<string> Pp/<string> IpPort logicalIf/<Ip Address> IgmpIf
-- This component is used to configure a logicalIf to run the IGMP 
-- protocol.

vrPpIpPortLogicalIfIgmpIf OBJECT IDENTIFIER ::= { vrPpIpPortLogicalIf 5 }



vrPpIpPortLogicalIfIgmpIfRowStatusTable OBJECT-TYPE
   SYNTAX     SEQUENCE OF VrPpIpPortLogicalIfIgmpIfRowStatusEntry
   ACCESS     not-accessible
   STATUS     mandatory
   DESCRIPTION
     "This entry controls the addition and deletion of 
      vrPpIpPortLogicalIfIgmpIf components."
::= { vrPpIpPortLogicalIfIgmpIf 1 }

vrPpIpPortLogicalIfIgmpIfRowStatusEntry OBJECT-TYPE
   SYNTAX     VrPpIpPortLogicalIfIgmpIfRowStatusEntry
   ACCESS     not-accessible
   STATUS     mandatory
   DESCRIPTION
     "A single entry in the table represents a single 
      vrPpIpPortLogicalIfIgmpIf component."
   INDEX {
      vrIndex,
      vrPpIndex,
      vrPpIpPortIndex,
      vrPpIpPortLogicalIfAddressIndex,
      vrPpIpPortLogicalIfIgmpIfIndex }
::= { vrPpIpPortLogicalIfIgmpIfRowStatusTable 1 }

VrPpIpPortLogicalIfIgmpIfRowStatusEntry ::= SEQUENCE {
   vrPpIpPortLogicalIfIgmpIfRowStatus
      RowStatus,
   vrPpIpPortLogicalIfIgmpIfComponentName
      DisplayString,
   vrPpIpPortLogicalIfIgmpIfStorageType
      StorageType,
   vrPpIpPortLogicalIfIgmpIfIndex
      NonReplicated }

vrPpIpPortLogicalIfIgmpIfRowStatus OBJECT-TYPE
   SYNTAX     RowStatus 
   ACCESS     read-write
   STATUS     mandatory
   DESCRIPTION
     "This variable is used as the basis for SNMP naming of
      vrPpIpPortLogicalIfIgmpIf components.
      These components can be added and deleted."
::= { vrPpIpPortLogicalIfIgmpIfRowStatusEntry 1 }

vrPpIpPortLogicalIfIgmpIfComponentName OBJECT-TYPE
   SYNTAX     DisplayString 
   ACCESS     read-only
   STATUS     mandatory
   DESCRIPTION
     "This variable provides the component's string name for
      use with the ASCII Console Interface"
::= { vrPpIpPortLogicalIfIgmpIfRowStatusEntry 2 }

vrPpIpPortLogicalIfIgmpIfStorageType OBJECT-TYPE
   SYNTAX     StorageType 
   ACCESS     read-only
   STATUS     mandatory
   DESCRIPTION
     "This variable represents the storage type value for the
      vrPpIpPortLogicalIfIgmpIf tables."
::= { vrPpIpPortLogicalIfIgmpIfRowStatusEntry 4 }

vrPpIpPortLogicalIfIgmpIfIndex OBJECT-TYPE
   SYNTAX     NonReplicated 
   ACCESS     not-accessible
   STATUS     mandatory
   DESCRIPTION
     "This variable represents the index for the vrPpIpPortLogicalIfIgmpIf tables."
::= { vrPpIpPortLogicalIfIgmpIfRowStatusEntry 10 }

vrPpIpPortLogicalIfIgmpIfProvTable OBJECT-TYPE
   SYNTAX     SEQUENCE OF VrPpIpPortLogicalIfIgmpIfProvEntry
   ACCESS     not-accessible
   STATUS     mandatory
   DESCRIPTION
     "This group contains the provisionable attributes for the InwIpIgmpIf 
      component."
::= { vrPpIpPortLogicalIfIgmpIf 10 }

vrPpIpPortLogicalIfIgmpIfProvEntry OBJECT-TYPE
   SYNTAX     VrPpIpPortLogicalIfIgmpIfProvEntry
   ACCESS     not-accessible
   STATUS     mandatory
   DESCRIPTION
     "An entry in the vrPpIpPortLogicalIfIgmpIfProvTable."
   INDEX {
      vrIndex,
      vrPpIndex,
      vrPpIpPortIndex,
      vrPpIpPortLogicalIfAddressIndex,
      vrPpIpPortLogicalIfIgmpIfIndex }
::= { vrPpIpPortLogicalIfIgmpIfProvTable 1 }

VrPpIpPortLogicalIfIgmpIfProvEntry ::= SEQUENCE {
   vrPpIpPortLogicalIfIgmpIfVersion
      INTEGER,
   vrPpIpPortLogicalIfIgmpIfQueryInterval
      Unsigned32,
   vrPpIpPortLogicalIfIgmpIfQueryMaxRespTime
      Unsigned32 }

vrPpIpPortLogicalIfIgmpIfVersion OBJECT-TYPE
   SYNTAX     INTEGER  {
                 v2(2) }
   ACCESS     read-write
   STATUS     mandatory
   DESCRIPTION
     "This attribute specifies the IGMP protocol version running on this 
      interface. v2 is the only supported version at this time."
   DEFVAL     { v2 }
::= { vrPpIpPortLogicalIfIgmpIfProvEntry 1 }

vrPpIpPortLogicalIfIgmpIfQueryInterval OBJECT-TYPE
   SYNTAX     Unsigned32 (1..3600)
   ACCESS     read-write
   STATUS     mandatory
   DESCRIPTION
     "This attribute specifies the frequency at which IGMP Host-Query 
      packets are transmitted on this interface."
   DEFVAL     { 125 }
::= { vrPpIpPortLogicalIfIgmpIfProvEntry 2 }

vrPpIpPortLogicalIfIgmpIfQueryMaxRespTime OBJECT-TYPE
   SYNTAX     Unsigned32 (1..3600)
   ACCESS     read-write
   STATUS     mandatory
   DESCRIPTION
     "This attribute specifies the maximum query response time 
      advertised in IGMPv2 queries on this interface. The number of 
      seconds represented by the queryMaxRespTime must be less than 
      the Query Interval."
   DEFVAL     { 10 }
::= { vrPpIpPortLogicalIfIgmpIfProvEntry 3 }

vrPpIpPortLogicalIfIgmpIfOperTable OBJECT-TYPE
   SYNTAX     SEQUENCE OF VrPpIpPortLogicalIfIgmpIfOperEntry
   ACCESS     not-accessible
   STATUS     mandatory
   DESCRIPTION
     "This group contains the operational attributes of InwIpIgmpIf 
      component."
::= { vrPpIpPortLogicalIfIgmpIf 11 }

vrPpIpPortLogicalIfIgmpIfOperEntry OBJECT-TYPE
   SYNTAX     VrPpIpPortLogicalIfIgmpIfOperEntry
   ACCESS     not-accessible
   STATUS     mandatory
   DESCRIPTION
     "An entry in the vrPpIpPortLogicalIfIgmpIfOperTable."
   INDEX {
      vrIndex,
      vrPpIndex,
      vrPpIpPortIndex,
      vrPpIpPortLogicalIfAddressIndex,
      vrPpIpPortLogicalIfIgmpIfIndex }
::= { vrPpIpPortLogicalIfIgmpIfOperTable 1 }

VrPpIpPortLogicalIfIgmpIfOperEntry ::= SEQUENCE {
   vrPpIpPortLogicalIfIgmpIfQuerier
      IpAddress,
   vrPpIpPortLogicalIfIgmpIfWrongVersionQuery
      Counter32,
   vrPpIpPortLogicalIfIgmpIfJoins
      Counter32,
   vrPpIpPortLogicalIfIgmpIfGroups
      Gauge32,
   vrPpIpPortLogicalIfIgmpIfQuerierExpiryTime
      Unsigned32 }

vrPpIpPortLogicalIfIgmpIfQuerier OBJECT-TYPE
   SYNTAX     IpAddress 
   ACCESS     read-only
   STATUS     mandatory
   DESCRIPTION
     "This attribute indicates the address of the IGMP Querier on the IP 
      subnet to which this interface is attached."
   DEFVAL     { '00000000'H }  -- "0.0.0.0"
::= { vrPpIpPortLogicalIfIgmpIfOperEntry 2 }

vrPpIpPortLogicalIfIgmpIfWrongVersionQuery OBJECT-TYPE
   SYNTAX     Counter32 
   ACCESS     read-only
   STATUS     mandatory
   DESCRIPTION
     "This attribute indicates the number of queries received whose IGMP 
      version does not match that configured for this interface. IGMP 
      requires that all routers on a LAN be configured to run the same 
      version of IGMP."
::= { vrPpIpPortLogicalIfIgmpIfOperEntry 3 }

vrPpIpPortLogicalIfIgmpIfJoins OBJECT-TYPE
   SYNTAX     Counter32 
   ACCESS     read-only
   STATUS     mandatory
   DESCRIPTION
     "This attribute indicates the number of times a group membership 
      has been added on this interface."
::= { vrPpIpPortLogicalIfIgmpIfOperEntry 4 }

vrPpIpPortLogicalIfIgmpIfGroups OBJECT-TYPE
   SYNTAX     Gauge32 (0..4292967295)
   ACCESS     read-only
   STATUS     mandatory
   DESCRIPTION
     "This attribute indicates the current number of entries for this 
      interface in the cache table."
   DEFVAL     { 0 }
::= { vrPpIpPortLogicalIfIgmpIfOperEntry 5 }

vrPpIpPortLogicalIfIgmpIfQuerierExpiryTime OBJECT-TYPE
   SYNTAX     Unsigned32 (0..3600)
   ACCESS     read-only
   STATUS     mandatory
   DESCRIPTION
     "This attribute indicates the amount of time remaining before the 
      other querier present timer expires. If the local system is the querier, 
      the value of this object is zero."
   DEFVAL     { 0 }
::= { vrPpIpPortLogicalIfIgmpIfOperEntry 6 }


-- This component is used to configure a logicalIf to run PIM-SM 
-- protocol.

vrPpIpPortLogicalIfPimSmIf OBJECT IDENTIFIER ::= { vrPpIpPortLogicalIf 6 }



vrPpIpPortLogicalIfPimSmIfRowStatusTable OBJECT-TYPE
   SYNTAX     SEQUENCE OF VrPpIpPortLogicalIfPimSmIfRowStatusEntry
   ACCESS     not-accessible
   STATUS     mandatory
   DESCRIPTION
     "This entry controls the addition and deletion of 
      vrPpIpPortLogicalIfPimSmIf components."
::= { vrPpIpPortLogicalIfPimSmIf 1 }

vrPpIpPortLogicalIfPimSmIfRowStatusEntry OBJECT-TYPE
   SYNTAX     VrPpIpPortLogicalIfPimSmIfRowStatusEntry
   ACCESS     not-accessible
   STATUS     mandatory
   DESCRIPTION
     "A single entry in the table represents a single 
      vrPpIpPortLogicalIfPimSmIf component."
   INDEX {
      vrIndex,
      vrPpIndex,
      vrPpIpPortIndex,
      vrPpIpPortLogicalIfAddressIndex,
      vrPpIpPortLogicalIfPimSmIfIndex }
::= { vrPpIpPortLogicalIfPimSmIfRowStatusTable 1 }

VrPpIpPortLogicalIfPimSmIfRowStatusEntry ::= SEQUENCE {
   vrPpIpPortLogicalIfPimSmIfRowStatus
      RowStatus,
   vrPpIpPortLogicalIfPimSmIfComponentName
      DisplayString,
   vrPpIpPortLogicalIfPimSmIfStorageType
      StorageType,
   vrPpIpPortLogicalIfPimSmIfIndex
      NonReplicated }

vrPpIpPortLogicalIfPimSmIfRowStatus OBJECT-TYPE
   SYNTAX     RowStatus 
   ACCESS     read-write
   STATUS     mandatory
   DESCRIPTION
     "This variable is used as the basis for SNMP naming of
      vrPpIpPortLogicalIfPimSmIf components.
      These components can be added and deleted."
::= { vrPpIpPortLogicalIfPimSmIfRowStatusEntry 1 }

vrPpIpPortLogicalIfPimSmIfComponentName OBJECT-TYPE
   SYNTAX     DisplayString 
   ACCESS     read-only
   STATUS     mandatory
   DESCRIPTION
     "This variable provides the component's string name for
      use with the ASCII Console Interface"
::= { vrPpIpPortLogicalIfPimSmIfRowStatusEntry 2 }

vrPpIpPortLogicalIfPimSmIfStorageType OBJECT-TYPE
   SYNTAX     StorageType 
   ACCESS     read-only
   STATUS     mandatory
   DESCRIPTION
     "This variable represents the storage type value for the
      vrPpIpPortLogicalIfPimSmIf tables."
::= { vrPpIpPortLogicalIfPimSmIfRowStatusEntry 4 }

vrPpIpPortLogicalIfPimSmIfIndex OBJECT-TYPE
   SYNTAX     NonReplicated 
   ACCESS     not-accessible
   STATUS     mandatory
   DESCRIPTION
     "This variable represents the index for the vrPpIpPortLogicalIfPimSmIf tables."
::= { vrPpIpPortLogicalIfPimSmIfRowStatusEntry 10 }

vrPpIpPortLogicalIfPimSmIfProvTable OBJECT-TYPE
   SYNTAX     SEQUENCE OF VrPpIpPortLogicalIfPimSmIfProvEntry
   ACCESS     not-accessible
   STATUS     mandatory
   DESCRIPTION
     "This group contains the provisionable attributes for the 
      InwIpPimSmIf component."
::= { vrPpIpPortLogicalIfPimSmIf 10 }

vrPpIpPortLogicalIfPimSmIfProvEntry OBJECT-TYPE
   SYNTAX     VrPpIpPortLogicalIfPimSmIfProvEntry
   ACCESS     not-accessible
   STATUS     mandatory
   DESCRIPTION
     "An entry in the vrPpIpPortLogicalIfPimSmIfProvTable."
   INDEX {
      vrIndex,
      vrPpIndex,
      vrPpIpPortIndex,
      vrPpIpPortLogicalIfAddressIndex,
      vrPpIpPortLogicalIfPimSmIfIndex }
::= { vrPpIpPortLogicalIfPimSmIfProvTable 1 }

VrPpIpPortLogicalIfPimSmIfProvEntry ::= SEQUENCE {
   vrPpIpPortLogicalIfPimSmIfHelloInterval
      Unsigned32 }

vrPpIpPortLogicalIfPimSmIfHelloInterval OBJECT-TYPE
   SYNTAX     Unsigned32 (1..3600)
   ACCESS     read-write
   STATUS     mandatory
   DESCRIPTION
     "This attribute specifies the frequency at which PIM-SM hello 
      messages are transmitted on this interface."
   DEFVAL     { 30 }
::= { vrPpIpPortLogicalIfPimSmIfProvEntry 1 }

vrPpIpPortLogicalIfPimSmIfOperTable OBJECT-TYPE
   SYNTAX     SEQUENCE OF VrPpIpPortLogicalIfPimSmIfOperEntry
   ACCESS     not-accessible
   STATUS     mandatory
   DESCRIPTION
     "This group contains the operational attributes for the 
      InwIpPimSmIf component."
::= { vrPpIpPortLogicalIfPimSmIf 11 }

vrPpIpPortLogicalIfPimSmIfOperEntry OBJECT-TYPE
   SYNTAX     VrPpIpPortLogicalIfPimSmIfOperEntry
   ACCESS     not-accessible
   STATUS     mandatory
   DESCRIPTION
     "An entry in the vrPpIpPortLogicalIfPimSmIfOperTable."
   INDEX {
      vrIndex,
      vrPpIndex,
      vrPpIpPortIndex,
      vrPpIpPortLogicalIfAddressIndex,
      vrPpIpPortLogicalIfPimSmIfIndex }
::= { vrPpIpPortLogicalIfPimSmIfOperTable 1 }

VrPpIpPortLogicalIfPimSmIfOperEntry ::= SEQUENCE {
   vrPpIpPortLogicalIfPimSmIfDesignatedRouter
      IpAddress }

vrPpIpPortLogicalIfPimSmIfDesignatedRouter OBJECT-TYPE
   SYNTAX     IpAddress 
   ACCESS     read-only
   STATUS     mandatory
   DESCRIPTION
     "This attribute indicates the Designated Router on this PIM-SM 
      interface. For point-to-point interfaces(wan media), this attribute 
      has the value 0.0.0.0."
::= { vrPpIpPortLogicalIfPimSmIfOperEntry 1 }


-- This component allows the configuration of NetSentry filters for this 
-- IpPort.

vrPpIpPortNs OBJECT IDENTIFIER ::= { vrPpIpPort 3 }



vrPpIpPortNsRowStatusTable OBJECT-TYPE
   SYNTAX     SEQUENCE OF VrPpIpPortNsRowStatusEntry
   ACCESS     not-accessible
   STATUS     mandatory
   DESCRIPTION
     "This entry controls the addition and deletion of 
      vrPpIpPortNs components."
::= { vrPpIpPortNs 1 }

vrPpIpPortNsRowStatusEntry OBJECT-TYPE
   SYNTAX     VrPpIpPortNsRowStatusEntry
   ACCESS     not-accessible
   STATUS     mandatory
   DESCRIPTION
     "A single entry in the table represents a single 
      vrPpIpPortNs component."
   INDEX {
      vrIndex,
      vrPpIndex,
      vrPpIpPortIndex,
      vrPpIpPortNsIndex }
::= { vrPpIpPortNsRowStatusTable 1 }

VrPpIpPortNsRowStatusEntry ::= SEQUENCE {
   vrPpIpPortNsRowStatus
      RowStatus,
   vrPpIpPortNsComponentName
      DisplayString,
   vrPpIpPortNsStorageType
      StorageType,
   vrPpIpPortNsIndex
      NonReplicated }

vrPpIpPortNsRowStatus OBJECT-TYPE
   SYNTAX     RowStatus 
   ACCESS     read-write
   STATUS     mandatory
   DESCRIPTION
     "This variable is used as the basis for SNMP naming of
      vrPpIpPortNs components.
      These components can be added and deleted."
::= { vrPpIpPortNsRowStatusEntry 1 }

vrPpIpPortNsComponentName OBJECT-TYPE
   SYNTAX     DisplayString 
   ACCESS     read-only
   STATUS     mandatory
   DESCRIPTION
     "This variable provides the component's string name for
      use with the ASCII Console Interface"
::= { vrPpIpPortNsRowStatusEntry 2 }

vrPpIpPortNsStorageType OBJECT-TYPE
   SYNTAX     StorageType 
   ACCESS     read-only
   STATUS     mandatory
   DESCRIPTION
     "This variable represents the storage type value for the
      vrPpIpPortNs tables."
::= { vrPpIpPortNsRowStatusEntry 4 }

vrPpIpPortNsIndex OBJECT-TYPE
   SYNTAX     NonReplicated 
   ACCESS     not-accessible
   STATUS     mandatory
   DESCRIPTION
     "This variable represents the index for the vrPpIpPortNs tables."
::= { vrPpIpPortNsRowStatusEntry 10 }

vrPpIpPortNsProvTable OBJECT-TYPE
   SYNTAX     SEQUENCE OF VrPpIpPortNsProvEntry
   ACCESS     not-accessible
   STATUS     mandatory
   DESCRIPTION
     "This group contains the attributes required by NetSentry to be applied to 
      all IP packets going through this IpPort."
::= { vrPpIpPortNs 10 }

vrPpIpPortNsProvEntry OBJECT-TYPE
   SYNTAX     VrPpIpPortNsProvEntry
   ACCESS     not-accessible
   STATUS     mandatory
   DESCRIPTION
     "An entry in the vrPpIpPortNsProvTable."
   INDEX {
      vrIndex,
      vrPpIndex,
      vrPpIpPortIndex,
      vrPpIpPortNsIndex }
::= { vrPpIpPortNsProvTable 1 }

VrPpIpPortNsProvEntry ::= SEQUENCE {
   vrPpIpPortNsIncomingFilter
      AsciiString,
   vrPpIpPortNsOutgoingFilter
      AsciiString }

vrPpIpPortNsIncomingFilter OBJECT-TYPE
   SYNTAX     AsciiString (SIZE (0..32))
   ACCESS     read-write
   STATUS     mandatory
   DESCRIPTION
     "An ASCII string which provides the name of the NetSentry filter which 
      will be applied to all IP datagrams arriving from this IpPort."
   DEFVAL     { ''H }  -- ""
::= { vrPpIpPortNsProvEntry 1 }

vrPpIpPortNsOutgoingFilter OBJECT-TYPE
   SYNTAX     AsciiString (SIZE (0..32))
   ACCESS     read-write
   STATUS     mandatory
   DESCRIPTION
     "An ASCII string which provides the name of NetSentry filter which will 
      be applied to all IP datagrams sent to this IpPort."
   DEFVAL     { ''H }  -- ""
::= { vrPpIpPortNsProvEntry 2 }


-- Vr/<string> Pp/<string> IpPort BootpPort
-- An BootpPort component must be provisioned for each IpPort where 
-- BOOTP request messages will be received. Each BootpPort component 
-- can be provisioned with a set of relay addresses. Each BOOTP request 
-- message received on this port will be sent to the provisioned set of relay 
-- addresses.

vrPpIpPortBootpP OBJECT IDENTIFIER ::= { vrPpIpPort 4 }



vrPpIpPortBootpPRowStatusTable OBJECT-TYPE
   SYNTAX     SEQUENCE OF VrPpIpPortBootpPRowStatusEntry
   ACCESS     not-accessible
   STATUS     mandatory
   DESCRIPTION
     "This entry controls the addition and deletion of 
      vrPpIpPortBootpP components."
::= { vrPpIpPortBootpP 1 }

vrPpIpPortBootpPRowStatusEntry OBJECT-TYPE
   SYNTAX     VrPpIpPortBootpPRowStatusEntry
   ACCESS     not-accessible
   STATUS     mandatory
   DESCRIPTION
     "A single entry in the table represents a single 
      vrPpIpPortBootpP component."
   INDEX {
      vrIndex,
      vrPpIndex,
      vrPpIpPortIndex,
      vrPpIpPortBootpPIndex }
::= { vrPpIpPortBootpPRowStatusTable 1 }

VrPpIpPortBootpPRowStatusEntry ::= SEQUENCE {
   vrPpIpPortBootpPRowStatus
      RowStatus,
   vrPpIpPortBootpPComponentName
      DisplayString,
   vrPpIpPortBootpPStorageType
      StorageType,
   vrPpIpPortBootpPIndex
      NonReplicated }

vrPpIpPortBootpPRowStatus OBJECT-TYPE
   SYNTAX     RowStatus 
   ACCESS     read-write
   STATUS     mandatory
   DESCRIPTION
     "This variable is used as the basis for SNMP naming of
      vrPpIpPortBootpP components.
      These components can be added and deleted."
::= { vrPpIpPortBootpPRowStatusEntry 1 }

vrPpIpPortBootpPComponentName OBJECT-TYPE
   SYNTAX     DisplayString 
   ACCESS     read-only
   STATUS     mandatory
   DESCRIPTION
     "This variable provides the component's string name for
      use with the ASCII Console Interface"
::= { vrPpIpPortBootpPRowStatusEntry 2 }

vrPpIpPortBootpPStorageType OBJECT-TYPE
   SYNTAX     StorageType 
   ACCESS     read-only
   STATUS     mandatory
   DESCRIPTION
     "This variable represents the storage type value for the
      vrPpIpPortBootpP tables."
::= { vrPpIpPortBootpPRowStatusEntry 4 }

vrPpIpPortBootpPIndex OBJECT-TYPE
   SYNTAX     NonReplicated 
   ACCESS     not-accessible
   STATUS     mandatory
   DESCRIPTION
     "This variable represents the index for the vrPpIpPortBootpP tables."
::= { vrPpIpPortBootpPRowStatusEntry 10 }

vrPpIpPortBootpPProvTable OBJECT-TYPE
   SYNTAX     SEQUENCE OF VrPpIpPortBootpPProvEntry
   ACCESS     not-accessible
   STATUS     mandatory
   DESCRIPTION
     "This group contains provisionable attributes for the BootpPort 
      component."
::= { vrPpIpPortBootpP 10 }

vrPpIpPortBootpPProvEntry OBJECT-TYPE
   SYNTAX     VrPpIpPortBootpPProvEntry
   ACCESS     not-accessible
   STATUS     mandatory
   DESCRIPTION
     "An entry in the vrPpIpPortBootpPProvTable."
   INDEX {
      vrIndex,
      vrPpIndex,
      vrPpIpPortIndex,
      vrPpIpPortBootpPIndex }
::= { vrPpIpPortBootpPProvTable 1 }

VrPpIpPortBootpPProvEntry ::= SEQUENCE {
   vrPpIpPortBootpPRelayForwardStatus
      INTEGER,
   vrPpIpPortBootpPBootpLogicalInterface
      IpAddress }

vrPpIpPortBootpPRelayForwardStatus OBJECT-TYPE
   SYNTAX     INTEGER  {
                 enabled(1),
                 disabled(2),
                 auto(3) }
   ACCESS     read-write
   STATUS     mandatory
   DESCRIPTION
     "This attribute controls how BOOTP request packets, received on another 
      port, will be flooded out this port. If relayForwardStatus is enabled, 
      BOOTP requests received on another port will be broadcast out this port. 
      When relayForwardStatus is disabled, BOOTP requests will not be 
      broadcast out this port. If auto is used, the bridge spanning tree database 
      is used to determine if BOOTP requests should be broadcast out this 
      port.
      
      Note that when using enabled, it is possible to create misconfigurations 
      which will result in broadcast storms. When using this feature with 
      multiple routers, make sure there are no broadcast forwarding loops. 
      Using auto with bridge spanning tree is safer to use if the network is 
      running bridge spanning tree.
      
      Note that for auto to have effect, bridge spanning tree must be running 
      on the corresponding VirtualRouter ProtocolPort."
   DEFVAL     { disabled }
::= { vrPpIpPortBootpPProvEntry 2 }

vrPpIpPortBootpPBootpLogicalInterface OBJECT-TYPE
   SYNTAX     IpAddress 
   ACCESS     read-write
   STATUS     mandatory
   DESCRIPTION
     "This attribute identifies the logical interface whose address is to be the 
      GIADDR of this BOOTP port. If not set, the address of the first logical 
      port is chosen."
   DEFVAL     { '00000000'H }  -- "0.0.0.0"
::= { vrPpIpPortBootpPProvEntry 3 }

vrPpIpPortBootpPAdminControlTable OBJECT-TYPE
   SYNTAX     SEQUENCE OF VrPpIpPortBootpPAdminControlEntry
   ACCESS     not-accessible
   STATUS     mandatory
   DESCRIPTION
     "This group includes the Administrative Control attribute. This 
      attribute defines the current administrative state of this component."
::= { vrPpIpPortBootpP 11 }

vrPpIpPortBootpPAdminControlEntry OBJECT-TYPE
   SYNTAX     VrPpIpPortBootpPAdminControlEntry
   ACCESS     not-accessible
   STATUS     mandatory
   DESCRIPTION
     "An entry in the vrPpIpPortBootpPAdminControlTable."
   INDEX {
      vrIndex,
      vrPpIndex,
      vrPpIpPortIndex,
      vrPpIpPortBootpPIndex }
::= { vrPpIpPortBootpPAdminControlTable 1 }

VrPpIpPortBootpPAdminControlEntry ::= SEQUENCE {
   vrPpIpPortBootpPSnmpAdminStatus
      INTEGER }

vrPpIpPortBootpPSnmpAdminStatus OBJECT-TYPE
   SYNTAX     INTEGER  {
                 up(1),
                 down(2),
                 testing(3) }
   ACCESS     read-write
   STATUS     mandatory
   DESCRIPTION
     "The desired state of the interface. The up state indicates the 
      interface is operational and packet forwarding is allowed. The down 
      state indicates the interface is not operational and packet forwarding 
      is unavailable. The testing state indicates that no operational 
      packets can be passed."
   DEFVAL     { up }
::= { vrPpIpPortBootpPAdminControlEntry 1 }

vrPpIpPortBootpPOperStatusTable OBJECT-TYPE
   SYNTAX     SEQUENCE OF VrPpIpPortBootpPOperStatusEntry
   ACCESS     not-accessible
   STATUS     mandatory
   DESCRIPTION
     "This group includes the Operational Status attribute. This attribute 
      defines the current operational state of this component."
::= { vrPpIpPortBootpP 12 }

vrPpIpPortBootpPOperStatusEntry OBJECT-TYPE
   SYNTAX     VrPpIpPortBootpPOperStatusEntry
   ACCESS     not-accessible
   STATUS     mandatory
   DESCRIPTION
     "An entry in the vrPpIpPortBootpPOperStatusTable."
   INDEX {
      vrIndex,
      vrPpIndex,
      vrPpIpPortIndex,
      vrPpIpPortBootpPIndex }
::= { vrPpIpPortBootpPOperStatusTable 1 }

VrPpIpPortBootpPOperStatusEntry ::= SEQUENCE {
   vrPpIpPortBootpPSnmpOperStatus
      INTEGER }

vrPpIpPortBootpPSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { vrPpIpPortBootpPOperStatusEntry 1 }

vrPpIpPortBootpPStateTable OBJECT-TYPE
   SYNTAX     SEQUENCE OF VrPpIpPortBootpPStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { vrPpIpPortBootpP 13 }

vrPpIpPortBootpPStateEntry OBJECT-TYPE
   SYNTAX     VrPpIpPortBootpPStateEntry
   ACCESS     not-accessible
   STATUS     mandatory
   DESCRIPTION
     "An entry in the vrPpIpPortBootpPStateTable."
   INDEX {
      vrIndex,
      vrPpIndex,
      vrPpIpPortIndex,
      vrPpIpPortBootpPIndex }
::= { vrPpIpPortBootpPStateTable 1 }

VrPpIpPortBootpPStateEntry ::= SEQUENCE {
   vrPpIpPortBootpPAdminState
      INTEGER,
   vrPpIpPortBootpPOperationalState
      INTEGER,
   vrPpIpPortBootpPUsageState
      INTEGER }

vrPpIpPortBootpPAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { vrPpIpPortBootpPStateEntry 1 }

vrPpIpPortBootpPOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { vrPpIpPortBootpPStateEntry 2 }

vrPpIpPortBootpPUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { vrPpIpPortBootpPStateEntry 3 }

vrPpIpPortBootpPStatsTable OBJECT-TYPE
   SYNTAX     SEQUENCE OF VrPpIpPortBootpPStatsEntry
   ACCESS     not-accessible
   STATUS     mandatory
   DESCRIPTION
     "This group contains BootpPortEntry component statistics."
::= { vrPpIpPortBootpP 14 }

vrPpIpPortBootpPStatsEntry OBJECT-TYPE
   SYNTAX     VrPpIpPortBootpPStatsEntry
   ACCESS     not-accessible
   STATUS     mandatory
   DESCRIPTION
     "An entry in the vrPpIpPortBootpPStatsTable."
   INDEX {
      vrIndex,
      vrPpIndex,
      vrPpIpPortIndex,
      vrPpIpPortBootpPIndex }
::= { vrPpIpPortBootpPStatsTable 1 }

VrPpIpPortBootpPStatsEntry ::= SEQUENCE {
   vrPpIpPortBootpPInRequests
      Counter32,
   vrPpIpPortBootpPInReplies
      Counter32,
   vrPpIpPortBootpPOutRequests
      Counter32,
   vrPpIpPortBootpPOutReplies
      Counter32,
   vrPpIpPortBootpPInRequestErrors
      Counter32,
   vrPpIpPortBootpPInReplyErrors
      Counter32 }

vrPpIpPortBootpPInRequests OBJECT-TYPE
   SYNTAX     Counter32 
   ACCESS     read-only
   STATUS     mandatory
   DESCRIPTION
     "This attribute counts the total number of BOOTP Request messages 
      received on this port."
::= { vrPpIpPortBootpPStatsEntry 1 }

vrPpIpPortBootpPInReplies OBJECT-TYPE
   SYNTAX     Counter32 
   ACCESS     read-only
   STATUS     mandatory
   DESCRIPTION
     "This attribute counts the total number of BOOTP Reply messages 
      received on this port."
::= { vrPpIpPortBootpPStatsEntry 2 }

vrPpIpPortBootpPOutRequests OBJECT-TYPE
   SYNTAX     Counter32 
   ACCESS     read-only
   STATUS     mandatory
   DESCRIPTION
     "This attribute counts total the number of BOOTP Request messages 
      broadcast out on this port."
::= { vrPpIpPortBootpPStatsEntry 3 }

vrPpIpPortBootpPOutReplies OBJECT-TYPE
   SYNTAX     Counter32 
   ACCESS     read-only
   STATUS     mandatory
   DESCRIPTION
     "This attribute counts the total number of BOOTP Reply messages sent 
      out on this port."
::= { vrPpIpPortBootpPStatsEntry 4 }

vrPpIpPortBootpPInRequestErrors OBJECT-TYPE
   SYNTAX     Counter32 
   ACCESS     read-only
   STATUS     mandatory
   DESCRIPTION
     "This attribute counts the number of BOOTP Request messages received 
      on this port but not forwarded due to an error. An error occurs if the 
      BOOTP hop limit has been exceeded."
::= { vrPpIpPortBootpPStatsEntry 5 }

vrPpIpPortBootpPInReplyErrors OBJECT-TYPE
   SYNTAX     Counter32 
   ACCESS     read-only
   STATUS     mandatory
   DESCRIPTION
     "This attribute counts the number of BOOTP Reply messages received on 
      this port but not forwarded due to an error. An error occurs if the giaddr 
      field in the BOOTP reply does not match an IP address assigned to this 
      VirtualRouter, or if the output IpPort for the BOOTP reply is not 
      provisioned for BOOTP."
::= { vrPpIpPortBootpPStatsEntry 6 }

vrPpIpPortBootpPAddrTable OBJECT-TYPE
   SYNTAX     SEQUENCE OF VrPpIpPortBootpPAddrEntry
   ACCESS     not-accessible
   STATUS     mandatory
   DESCRIPTION
     "This attribute identifies a list of relay addresses. When a BOOTP request 
      message is received on this port, the request will be forwarded to the IP 
      addresses provisioned in relayAddress. Note that BOOTP requests are 
      also broadcast out all other BootpPort's according to the 
      relayForwardStatus of the outgoing port."
::= { vrPpIpPortBootpP 290 }

vrPpIpPortBootpPAddrEntry OBJECT-TYPE
   SYNTAX     VrPpIpPortBootpPAddrEntry
   ACCESS     not-accessible
   STATUS     mandatory
   DESCRIPTION
     "An entry in the vrPpIpPortBootpPAddrTable."
   INDEX {
      vrIndex,
      vrPpIndex,
      vrPpIpPortIndex,
      vrPpIpPortBootpPIndex,
      vrPpIpPortBootpPAddrValue }
::= { vrPpIpPortBootpPAddrTable 1 }

VrPpIpPortBootpPAddrEntry ::= SEQUENCE {
   vrPpIpPortBootpPAddrValue
      IpAddress,
   vrPpIpPortBootpPAddrRowStatus
      RowStatus }

vrPpIpPortBootpPAddrValue OBJECT-TYPE
   SYNTAX     IpAddress 
   ACCESS     read-write
   STATUS     mandatory
   DESCRIPTION
     "This variable represents both the value and the index for the
      vrPpIpPortBootpPAddrTable."
::= { vrPpIpPortBootpPAddrEntry 1 }

vrPpIpPortBootpPAddrRowStatus OBJECT-TYPE
   SYNTAX     RowStatus 
   ACCESS     write-only
   STATUS     mandatory
   DESCRIPTION
     "This variable is used to control the addition and deletion 
      of individual values of the vrPpIpPortBootpPAddrTable."
::= { vrPpIpPortBootpPAddrEntry 2 }


-- Vr/<string> Ip 
-- This component represents the instance of IP protocol running on this 
-- virtual router.

vrIp OBJECT IDENTIFIER ::= { vr 6 }



vrIpRowStatusTable OBJECT-TYPE
   SYNTAX     SEQUENCE OF VrIpRowStatusEntry
   ACCESS     not-accessible
   STATUS     mandatory
   DESCRIPTION
     "This entry controls the addition and deletion of 
      vrIp components."
::= { vrIp 1 }

vrIpRowStatusEntry OBJECT-TYPE
   SYNTAX     VrIpRowStatusEntry
   ACCESS     not-accessible
   STATUS     mandatory
   DESCRIPTION
     "A single entry in the table represents a single 
      vrIp component."
   INDEX {
      vrIndex,
      vrIpIndex }
::= { vrIpRowStatusTable 1 }

VrIpRowStatusEntry ::= SEQUENCE {
   vrIpRowStatus
      RowStatus,
   vrIpComponentName
      DisplayString,
   vrIpStorageType
      StorageType,
   vrIpIndex
      NonReplicated }

vrIpRowStatus OBJECT-TYPE
   SYNTAX     RowStatus 
   ACCESS     read-write
   STATUS     mandatory
   DESCRIPTION
     "This variable is used as the basis for SNMP naming of
      vrIp components.
      These components can be added and deleted."
::= { vrIpRowStatusEntry 1 }

vrIpComponentName OBJECT-TYPE
   SYNTAX     DisplayString 
   ACCESS     read-only
   STATUS     mandatory
   DESCRIPTION
     "This variable provides the component's string name for
      use with the ASCII Console Interface"
::= { vrIpRowStatusEntry 2 }

vrIpStorageType OBJECT-TYPE
   SYNTAX     StorageType 
   ACCESS     read-only
   STATUS     mandatory
   DESCRIPTION
     "This variable represents the storage type value for the
      vrIp tables."
::= { vrIpRowStatusEntry 4 }

vrIpIndex OBJECT-TYPE
   SYNTAX     NonReplicated 
   ACCESS     not-accessible
   STATUS     mandatory
   DESCRIPTION
     "This variable represents the index for the vrIp tables."
::= { vrIpRowStatusEntry 10 }

vrIpProvTable OBJECT-TYPE
   SYNTAX     SEQUENCE OF VrIpProvEntry
   ACCESS     not-accessible
   STATUS     mandatory
   DESCRIPTION
     "This group contains global attributes for IP."
::= { vrIp 100 }

vrIpProvEntry OBJECT-TYPE
   SYNTAX     VrIpProvEntry
   ACCESS     not-accessible
   STATUS     mandatory
   DESCRIPTION
     "An entry in the vrIpProvTable."
   INDEX {
      vrIndex,
      vrIpIndex }
::= { vrIpProvTable 1 }

VrIpProvEntry ::= SEQUENCE {
   vrIpForwarding
      INTEGER,
   vrIpDefaultTtl
      Unsigned32,
   vrIpCosPolicyAssignment
      Link }

vrIpForwarding OBJECT-TYPE
   SYNTAX     INTEGER  {
                 gateway(1) }
   ACCESS     read-write
   STATUS     mandatory
   DESCRIPTION
     "This attribute indicates whether or not this VR is acting as an IP gateway 
      in respect to the forwarding of datagrams received by, but not addressed 
      to, this VR"
   DEFVAL     { gateway }
::= { vrIpProvEntry 2 }

vrIpDefaultTtl OBJECT-TYPE
   SYNTAX     Unsigned32 (255..255)
   ACCESS     read-write
   STATUS     mandatory
   DESCRIPTION
     "This attribute is the default value inserted into the Time-To-Live field of 
      the IP header of datagrams originated at this entity, whenever a Time-
      To-Live value is not supplied by the transport layer protocol.
      
      The value of this attribute deviates from the MIB requirement that it will 
      always have a value of 255."
   DEFVAL     { 255 }
::= { vrIpProvEntry 3 }

vrIpCosPolicyAssignment OBJECT-TYPE
   SYNTAX     Link 
   ACCESS     read-write
   STATUS     mandatory
   DESCRIPTION
     "This attribute specifies the default cosPolicyGroup component that is 
      associated with the IpPort of every protocol port on the vrirtual router. 
      An individual IpPort can override this default using its own 
      cosPolicyAssignment attribute.
      
      If this attribute is empty, CoS policy groups are assigned to only those 
      IP ports where the cosPolicyAssignment attribute under the IpPort 
      component is non-empty."
::= { vrIpProvEntry 4 }

vrIpStatsTable OBJECT-TYPE
   SYNTAX     SEQUENCE OF VrIpStatsEntry
   ACCESS     not-accessible
   STATUS     mandatory
   DESCRIPTION
     "This is the GROUP holding the struct which contains statistical 
      attributes for IP."
::= { vrIp 101 }

vrIpStatsEntry OBJECT-TYPE
   SYNTAX     VrIpStatsEntry
   ACCESS     not-accessible
   STATUS     mandatory
   DESCRIPTION
     "An entry in the vrIpStatsTable."
   INDEX {
      vrIndex,
      vrIpIndex }
::= { vrIpStatsTable 1 }

VrIpStatsEntry ::= SEQUENCE {
   vrIpInReceives
      Counter32,
   vrIpInHdrErrors
      Counter32,
   vrIpInAddrErrors
      Counter32,
   vrIpForwDatagrams
      Counter32,
   vrIpInUnknownProtos
      Counter32,
   vrIpInDiscards
      Counter32,
   vrIpInDelivers
      Counter32,
   vrIpOutRequests
      Counter32,
   vrIpOutDiscards
      Counter32,
   vrIpOutNoRoutes
      Counter32,
   vrIpReasmTimeOut
      Unsigned32,
   vrIpReasmReqds
      Counter32,
   vrIpReasmOks
      Counter32,
   vrIpReasmFails
      Counter32,
   vrIpFragOks
      Counter32,
   vrIpFragFails
      Counter32,
   vrIpFragCreates
      Counter32,
   vrIpRoutingDiscards
      Counter32 }

vrIpInReceives OBJECT-TYPE
   SYNTAX     Counter32 
   ACCESS     read-only
   STATUS     mandatory
   DESCRIPTION
     "This is the number of input datagrams received from the interfaces, 
      including those received in error		. inReceives wraps to zero if reaches its 
      maximum defined value."
::= { vrIpStatsEntry 1 }

vrIpInHdrErrors OBJECT-TYPE
   SYNTAX     Counter32 
   ACCESS     read-only
   STATUS     mandatory
   DESCRIPTION
     "The number of input datagrams discarded due to errors in their IP 
      headers, including bad checksums, version number mismatch, other 
      format errors, time-to-live exceeded, errors discovered in processing 
      their IP options, etc. inHdrErrors wraps to zero if reaches its maximum 
      defined value."
::= { vrIpStatsEntry 2 }

vrIpInAddrErrors OBJECT-TYPE
   SYNTAX     Counter32 
   ACCESS     read-only
   STATUS     mandatory
   DESCRIPTION
     "The number of input datagrams discarded due to errors such as invalid 
      address, unsupported address class. inAddrErrors wraps to zero if 
      reaches its maximum defined value."
::= { vrIpStatsEntry 3 }

vrIpForwDatagrams OBJECT-TYPE
   SYNTAX     Counter32 
   ACCESS     read-only
   STATUS     mandatory
   DESCRIPTION
     "The number of input datagrams for which this router was not their final 
      IP destination, as a result of which an attempt was made to find a route 
      to forward them to that final destination. forwDatagrams wraps to zero 
      if reaches it's maximum defined value."
::= { vrIpStatsEntry 4 }

vrIpInUnknownProtos OBJECT-TYPE
   SYNTAX     Counter32 
   ACCESS     read-only
   STATUS     mandatory
   DESCRIPTION
     "The number of locally-addressed datagrams received successfully but 
      discarded because of an unknown or unsupported protocol 
      inUnknownProtos wraps to zero if reaches its maximum defined value."
::= { vrIpStatsEntry 5 }

vrIpInDiscards OBJECT-TYPE
   SYNTAX     Counter32 
   ACCESS     read-only
   STATUS     mandatory
   DESCRIPTION
     "The number of input datagrams for which no problems were 
      encountered to prevent their continued processing, but which were 
      discarded due to the lack of buffers. This does not include any datagram 
      discarded while awaiting for re-assembly. inDiscards wraps to zero if 
      reaches its maximum defined value."
::= { vrIpStatsEntry 6 }

vrIpInDelivers OBJECT-TYPE
   SYNTAX     Counter32 
   ACCESS     read-only
   STATUS     mandatory
   DESCRIPTION
     "The number of input datagrams successfully delivered to IP user-
      protocols (including ICMP). inDelivers wraps to zero if reaches its 
      maximum defined value."
::= { vrIpStatsEntry 7 }

vrIpOutRequests OBJECT-TYPE
   SYNTAX     Counter32 
   ACCESS     read-only
   STATUS     mandatory
   DESCRIPTION
     "The number of datagrams which local IP user-protocols (including 
      ICMP) supplied to IP in requests for transmission. This sum does not 
      include datagrams counted in ForwDatagrams. outRequests wraps to 
      zero if reaches its maximum defined value."
::= { vrIpStatsEntry 8 }

vrIpOutDiscards OBJECT-TYPE
   SYNTAX     Counter32 
   ACCESS     read-only
   STATUS     mandatory
   DESCRIPTION
     "The number of outbound datagrams that were discarded due to the lack 
      of buffers. This sum also includes datagrams counted in forwDatagrams 
      if any such packets met the discard criterion. outDiscards wraps to zero 
      if reaches its maximum defined value."
::= { vrIpStatsEntry 9 }

vrIpOutNoRoutes OBJECT-TYPE
   SYNTAX     Counter32 
   ACCESS     read-only
   STATUS     mandatory
   DESCRIPTION
     "The number of outbound datagrams discarded because no route could be 
      found to transmit them to their destination. This counter includes any 
      datagrams counted in forwDatagrams. outNoRoutes wraps to zero if 
      reaches its maximum defined value."
::= { vrIpStatsEntry 10 }

vrIpReasmTimeOut OBJECT-TYPE
   SYNTAX     Unsigned32 (0..5)
   ACCESS     read-only
   STATUS     mandatory
   DESCRIPTION
     "The maximum number of seconds, which received fragments are held 
      while they are awaiting reassembly at this gateway."
   DEFVAL     { 5 }
::= { vrIpStatsEntry 11 }

vrIpReasmReqds OBJECT-TYPE
   SYNTAX     Counter32 
   ACCESS     read-only
   STATUS     mandatory
   DESCRIPTION
     "The number of the IP fragments received by this gateway which needed 
      to be reassembled. reasmReqds wraps to zero if reaches its maximum 
      defined value."
::= { vrIpStatsEntry 12 }

vrIpReasmOks OBJECT-TYPE
   SYNTAX     Counter32 
   ACCESS     read-only
   STATUS     mandatory
   DESCRIPTION
     "The number of IP fragments successfully reassembled by this gateway. 
      reasmOks wraps to zero if reaches its maximum defined value."
::= { vrIpStatsEntry 13 }

vrIpReasmFails OBJECT-TYPE
   SYNTAX     Counter32 
   ACCESS     read-only
   STATUS     mandatory
   DESCRIPTION
     "The number of times this gateway is unabled to assemble IP-fragments 
      for whatever reasons. reasmFails wraps to zero if reaches its maximum 
      defined value."
::= { vrIpStatsEntry 14 }

vrIpFragOks OBJECT-TYPE
   SYNTAX     Counter32 
   ACCESS     read-only
   STATUS     mandatory
   DESCRIPTION
     "The number of IP datagrams that have been successfully fragmented by 
      this gateway. fragOks wraps to zero if reaches its maximum defined 
      value."
::= { vrIpStatsEntry 15 }

vrIpFragFails OBJECT-TYPE
   SYNTAX     Counter32 
   ACCESS     read-only
   STATUS     mandatory
   DESCRIPTION
     "The number of IP-fragments that have been discarded because they 
      needed to be fragmented but could not be. For example, their Don't 
      Fragment flag was set. fragFails wraps to zero if reaches its maximum 
      defined value."
::= { vrIpStatsEntry 16 }

vrIpFragCreates OBJECT-TYPE
   SYNTAX     Counter32 
   ACCESS     read-only
   STATUS     mandatory
   DESCRIPTION
     "This number of IP fragments that have been generated as a result of 
      fragmentation by this gateway. fragCreates wraps to zero if reaches its 
      maximum defined value."
::= { vrIpStatsEntry 17 }

vrIpRoutingDiscards OBJECT-TYPE
   SYNTAX     Counter32 
   ACCESS     read-only
   STATUS     mandatory
   DESCRIPTION
     "The number of routing entries which were chosen to be discarded even 
      though they are valid. One possible reason for discarding such an entry 
      could be to free -up buffer space for other routing entries. In this 
      implementation, this number is always zero because IP never deletes a 
      valid routing entry."
::= { vrIpStatsEntry 18 }

vrIpAdminControlTable OBJECT-TYPE
   SYNTAX     SEQUENCE OF VrIpAdminControlEntry
   ACCESS     not-accessible
   STATUS     mandatory
   DESCRIPTION
     "This group includes the Administrative Control attribute. This 
      attribute defines the current administrative state of this component."
::= { vrIp 102 }

vrIpAdminControlEntry OBJECT-TYPE
   SYNTAX     VrIpAdminControlEntry
   ACCESS     not-accessible
   STATUS     mandatory
   DESCRIPTION
     "An entry in the vrIpAdminControlTable."
   INDEX {
      vrIndex,
      vrIpIndex }
::= { vrIpAdminControlTable 1 }

VrIpAdminControlEntry ::= SEQUENCE {
   vrIpSnmpAdminStatus
      INTEGER }

vrIpSnmpAdminStatus OBJECT-TYPE
   SYNTAX     INTEGER  {
                 up(1),
                 down(2),
                 testing(3) }
   ACCESS     read-write
   STATUS     mandatory
   DESCRIPTION
     "The desired state of the interface. The up state indicates the 
      interface is operational and packet forwarding is allowed. The down 
      state indicates the interface is not operational and packet forwarding 
      is unavailable. The testing state indicates that no operational 
      packets can be passed."
   DEFVAL     { up }
::= { vrIpAdminControlEntry 1 }

vrIpStateTable OBJECT-TYPE
   SYNTAX     SEQUENCE OF VrIpStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { vrIp 104 }

vrIpStateEntry OBJECT-TYPE
   SYNTAX     VrIpStateEntry
   ACCESS     not-accessible
   STATUS     mandatory
   DESCRIPTION
     "An entry in the vrIpStateTable."
   INDEX {
      vrIndex,
      vrIpIndex }
::= { vrIpStateTable 1 }

VrIpStateEntry ::= SEQUENCE {
   vrIpAdminState
      INTEGER,
   vrIpOperationalState
      INTEGER,
   vrIpUsageState
      INTEGER }

vrIpAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { vrIpStateEntry 1 }

vrIpOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { vrIpStateEntry 2 }

vrIpUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { vrIpStateEntry 3 }

vrIpOperStatusTable OBJECT-TYPE
   SYNTAX     SEQUENCE OF VrIpOperStatusEntry
   ACCESS     not-accessible
   STATUS     mandatory
   DESCRIPTION
     "This group includes the Operational Status attribute. This attribute 
      defines the current operational state of this component."
::= { vrIp 107 }

vrIpOperStatusEntry OBJECT-TYPE
   SYNTAX     VrIpOperStatusEntry
   ACCESS     not-accessible
   STATUS     mandatory
   DESCRIPTION
     "An entry in the vrIpOperStatusTable."
   INDEX {
      vrIndex,
      vrIpIndex }
::= { vrIpOperStatusTable 1 }

VrIpOperStatusEntry ::= SEQUENCE {
   vrIpSnmpOperStatus
      INTEGER }

vrIpSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { vrIpOperStatusEntry 1 }

vrIpCtsTable OBJECT-TYPE
   SYNTAX     SEQUENCE OF VrIpCtsEntry
   ACCESS     not-accessible
   STATUS     mandatory
   DESCRIPTION
     "This attribute specifies the maximum number of entries that can exist in 
      the IP local cache table on each LP. This attribute provides a way to 
      control the resources allocated to the IP cache tables.
      The default cache table size is 3000 for an FP and 100 for a CP, is used 
      if this attribute is not specified explicitly. The attribute value must be 
      multiple of 100."
::= { vrIp 394 }

vrIpCtsEntry OBJECT-TYPE
   SYNTAX     VrIpCtsEntry
   ACCESS     not-accessible
   STATUS     mandatory
   DESCRIPTION
     "An entry in the vrIpCtsTable."
   INDEX {
      vrIndex,
      vrIpIndex,
      vrIpCtsIndex }
::= { vrIpCtsTable 1 }

VrIpCtsEntry ::= SEQUENCE {
   vrIpCtsIndex
      Integer32,
   vrIpCtsValue
      Unsigned32 }

vrIpCtsIndex OBJECT-TYPE
   SYNTAX     Integer32 (0..15)
   ACCESS     not-accessible
   STATUS     mandatory
   DESCRIPTION
     "This variable represents the vrIpCtsTable
      specific index for the vrIpCtsTable."
::= { vrIpCtsEntry 1 }

vrIpCtsValue OBJECT-TYPE
   SYNTAX     Unsigned32 (100..8000)
   ACCESS     read-write
   STATUS     mandatory
   DESCRIPTION
     "This variable represents an individual value for the
      vrIpCtsTable."
::= { vrIpCtsEntry 2 }

-- 
-- *** THIS SUBTREE CURRENTLY NOT IMPLEMENTED ***
-- 

-- Vr/<string> Ip ForwardTable/<Ip Address>,<Ip 
-- Address>,<Decimal>,<IP Address>
-- This component contains the information to forward data.This table 
-- holds the best route information sent from Routing table.

vrIpFwd OBJECT IDENTIFIER ::= { vrIp 3 }



vrIpFwdRowStatusTable OBJECT-TYPE
   SYNTAX     SEQUENCE OF VrIpFwdRowStatusEntry
   ACCESS     not-accessible
   STATUS     mandatory
   DESCRIPTION
     "*** THIS TABLE CURRENTLY NOT IMPLEMENTED ***

      This entry controls the addition and deletion of 
      vrIpFwd components."
::= { vrIpFwd 1 }

vrIpFwdRowStatusEntry OBJECT-TYPE
   SYNTAX     VrIpFwdRowStatusEntry
   ACCESS     not-accessible
   STATUS     mandatory
   DESCRIPTION
     "A single entry in the table represents a single 
      vrIpFwd component."
   INDEX {
      vrIndex,
      vrIpIndex,
      vrIpFwdDestAddressIndex,
      vrIpFwdDestMaskIndex,
      vrIpFwdTypeOfServiceIndex,
      vrIpFwdGatewayIndex }
::= { vrIpFwdRowStatusTable 1 }

VrIpFwdRowStatusEntry ::= SEQUENCE {
   vrIpFwdRowStatus
      RowStatus,
   vrIpFwdComponentName
      DisplayString,
   vrIpFwdStorageType
      StorageType,
   vrIpFwdDestAddressIndex
      IpAddress,
   vrIpFwdDestMaskIndex
      IpAddress,
   vrIpFwdTypeOfServiceIndex
      Integer32,
   vrIpFwdGatewayIndex
      IpAddress }

vrIpFwdRowStatus OBJECT-TYPE
   SYNTAX     RowStatus 
   ACCESS     read-only
   STATUS     mandatory
   DESCRIPTION
     "This variable is used as the basis for SNMP naming of
      vrIpFwd components.
      These components cannot be added nor deleted."
::= { vrIpFwdRowStatusEntry 1 }

vrIpFwdComponentName OBJECT-TYPE
   SYNTAX     DisplayString 
   ACCESS     read-only
   STATUS     mandatory
   DESCRIPTION
     "This variable provides the component's string name for
      use with the ASCII Console Interface"
::= { vrIpFwdRowStatusEntry 2 }

vrIpFwdStorageType OBJECT-TYPE
   SYNTAX     StorageType 
   ACCESS     read-only
   STATUS     mandatory
   DESCRIPTION
     "This variable represents the storage type value for the
      vrIpFwd tables."
::= { vrIpFwdRowStatusEntry 4 }

vrIpFwdDestAddressIndex OBJECT-TYPE
   SYNTAX     IpAddress 
   ACCESS     not-accessible
   STATUS     mandatory
   DESCRIPTION
     "This variable represents an index for the vrIpFwd tables."
::= { vrIpFwdRowStatusEntry 10 }

vrIpFwdDestMaskIndex OBJECT-TYPE
   SYNTAX     IpAddress 
   ACCESS     not-accessible
   STATUS     mandatory
   DESCRIPTION
     "This variable represents an index for the vrIpFwd tables."
::= { vrIpFwdRowStatusEntry 11 }

vrIpFwdTypeOfServiceIndex OBJECT-TYPE
   SYNTAX     Integer32 (0..31)
   ACCESS     not-accessible
   STATUS     mandatory
   DESCRIPTION
     "This variable represents an index for the vrIpFwd tables."
::= { vrIpFwdRowStatusEntry 12 }

vrIpFwdGatewayIndex OBJECT-TYPE
   SYNTAX     IpAddress 
   ACCESS     not-accessible
   STATUS     mandatory
   DESCRIPTION
     "This variable represents an index for the vrIpFwd tables."
::= { vrIpFwdRowStatusEntry 13 }

vrIpFwdOperTable OBJECT-TYPE
   SYNTAX     SEQUENCE OF VrIpFwdOperEntry
   ACCESS     not-accessible
   STATUS     mandatory
   DESCRIPTION
     "*** THIS TABLE CURRENTLY NOT IMPLEMENTED ***

      Identifies a group of operational attributes associated with each entry in 
      the Forward Table."
::= { vrIpFwd 10 }

vrIpFwdOperEntry OBJECT-TYPE
   SYNTAX     VrIpFwdOperEntry
   ACCESS     not-accessible
   STATUS     mandatory
   DESCRIPTION
     "An entry in the vrIpFwdOperTable."
   INDEX {
      vrIndex,
      vrIpIndex,
      vrIpFwdDestAddressIndex,
      vrIpFwdDestMaskIndex,
      vrIpFwdTypeOfServiceIndex,
      vrIpFwdGatewayIndex }
::= { vrIpFwdOperTable 1 }

VrIpFwdOperEntry ::= SEQUENCE {
   vrIpFwdIfIndex
      InterfaceIndex,
   vrIpFwdType
      INTEGER,
   vrIpFwdProtocol
      INTEGER,
   vrIpFwdAge
      Gauge32,
   vrIpFwdProtocolPortName
      RowPointer,
   vrIpFwdNextHopAs
      Unsigned32,
   vrIpFwdMetric
      INTEGER }

vrIpFwdIfIndex OBJECT-TYPE
   SYNTAX     InterfaceIndex (1..65535)
   ACCESS     read-only
   STATUS     mandatory
   DESCRIPTION
     "This attribute specifies the SNMP index associated with the 
      protocol port represented by the attribute protocolPortName, which 
      identifies the local interface through which the next hop of this route 
      should be reached."
::= { vrIpFwdOperEntry 1 }

vrIpFwdType OBJECT-TYPE
   SYNTAX     INTEGER  {
                 notDefined(1),
                 invalid(2),
                 localInterface(3),
                 remoteDestination(4) }
   ACCESS     read-only
   STATUS     mandatory
   DESCRIPTION
     "Specifies the type of the route,"
::= { vrIpFwdOperEntry 2 }

vrIpFwdProtocol OBJECT-TYPE
   SYNTAX     INTEGER  {
                 other(1),
                 local(2),
                 netmgmt(3),
                 icmp(4),
                 egp(5),
                 ggp(6),
                 hello(7),
                 rip(8),
                 isIs(9),
                 esIs(10),
                 ciscoIgrp(11),
                 bbnSpfIgp(12),
                 ospf(13),
                 bgp(14),
                 idpr(15) }
   ACCESS     read-only
   STATUS     mandatory
   DESCRIPTION
     "This Attribute identifies the routing mechanism by which this route was 
      learned."
::= { vrIpFwdOperEntry 3 }

vrIpFwdAge OBJECT-TYPE
   SYNTAX     Gauge32 (0..4294967295)
   ACCESS     read-only
   STATUS     mandatory
   DESCRIPTION
     "This attribute specifies the number of seconds since this route was last 
      updated or otherwise determined to be correct."
::= { vrIpFwdOperEntry 4 }

vrIpFwdProtocolPortName OBJECT-TYPE
   SYNTAX     RowPointer 
   ACCESS     read-only
   STATUS     mandatory
   DESCRIPTION
     "Indicates the name of the protocol port by which the next hop of this 
      route should be reached."
::= { vrIpFwdOperEntry 5 }

vrIpFwdNextHopAs OBJECT-TYPE
   SYNTAX     Unsigned32 (0..429467295)
   ACCESS     read-only
   STATUS     mandatory
   DESCRIPTION
     "This attribute specifies the Autonomous System number of the Next 
      Hop. If unknown or not relevant to the protocol indicated by the attribute 
      protocol, the value should be zero."
::= { vrIpFwdOperEntry 7 }

vrIpFwdMetric OBJECT-TYPE
   SYNTAX     INTEGER (-1..65535)
   ACCESS     read-only
   STATUS     mandatory
   DESCRIPTION
     "This attribute specifies the primary routing metric for this route. The 
      semantics of this metric are determined by the routing protocol specified 
      by the value of the attribute protocol. If this metric is not used, its value 
      should be set to -1."
   DEFVAL     { -1 }
::= { vrIpFwdOperEntry 8 }

-- 
-- *** THIS SUBTREE CURRENTLY NOT IMPLEMENTED ***
-- 

-- Vr/<string> Ip RouteDataBaseEntry/
-- <destAddress>,<destMask>,<protocol>
-- This component is used to display the information in the Ip routing 
-- database. destAddress and destMask indicates the address and mask of 
-- the route in the RoutingDatabase. protocol indicates the protocol this 
-- entry is learned from. gateway indicates the nextHop address for remote 
-- routes. The value of gateway for the localInterface routes will be the 
-- same value as the destAddress.

vrIpRdb OBJECT IDENTIFIER ::= { vrIp 4 }



vrIpRdbRowStatusTable OBJECT-TYPE
   SYNTAX     SEQUENCE OF VrIpRdbRowStatusEntry
   ACCESS     not-accessible
   STATUS     mandatory
   DESCRIPTION
     "*** THIS TABLE CURRENTLY NOT IMPLEMENTED ***

      This entry controls the addition and deletion of 
      vrIpRdb components."
::= { vrIpRdb 1 }

vrIpRdbRowStatusEntry OBJECT-TYPE
   SYNTAX     VrIpRdbRowStatusEntry
   ACCESS     not-accessible
   STATUS     mandatory
   DESCRIPTION
     "A single entry in the table represents a single 
      vrIpRdb component."
   INDEX {
      vrIndex,
      vrIpIndex,
      vrIpRdbDestAddressIndex,
      vrIpRdbDestMaskIndex,
      vrIpRdbProtocolIndex,
      vrIpRdbGatewayIndex }
::= { vrIpRdbRowStatusTable 1 }

VrIpRdbRowStatusEntry ::= SEQUENCE {
   vrIpRdbRowStatus
      RowStatus,
   vrIpRdbComponentName
      DisplayString,
   vrIpRdbStorageType
      StorageType,
   vrIpRdbDestAddressIndex
      IpAddress,
   vrIpRdbDestMaskIndex
      IpAddress,
   vrIpRdbProtocolIndex
      INTEGER,
   vrIpRdbGatewayIndex
      IpAddress }

vrIpRdbRowStatus OBJECT-TYPE
   SYNTAX     RowStatus 
   ACCESS     read-only
   STATUS     mandatory
   DESCRIPTION
     "This variable is used as the basis for SNMP naming of
      vrIpRdb components.
      These components cannot be added nor deleted."
::= { vrIpRdbRowStatusEntry 1 }

vrIpRdbComponentName OBJECT-TYPE
   SYNTAX     DisplayString 
   ACCESS     read-only
   STATUS     mandatory
   DESCRIPTION
     "This variable provides the component's string name for
      use with the ASCII Console Interface"
::= { vrIpRdbRowStatusEntry 2 }

vrIpRdbStorageType OBJECT-TYPE
   SYNTAX     StorageType 
   ACCESS     read-only
   STATUS     mandatory
   DESCRIPTION
     "This variable represents the storage type value for the
      vrIpRdb tables."
::= { vrIpRdbRowStatusEntry 4 }

vrIpRdbDestAddressIndex OBJECT-TYPE
   SYNTAX     IpAddress 
   ACCESS     not-accessible
   STATUS     mandatory
   DESCRIPTION
     "This variable represents an index for the vrIpRdb tables."
::= { vrIpRdbRowStatusEntry 10 }

vrIpRdbDestMaskIndex OBJECT-TYPE
   SYNTAX     IpAddress 
   ACCESS     not-accessible
   STATUS     mandatory
   DESCRIPTION
     "This variable represents an index for the vrIpRdb tables."
::= { vrIpRdbRowStatusEntry 11 }

vrIpRdbProtocolIndex OBJECT-TYPE
   SYNTAX     INTEGER  {
                 bogus(1),
                 local(2),
                 remote(3),
                 special(4),
                 ospf(5),
                 ospfExternal(6),
                 ospfType3Discard(7),
                 ospfType7Discard(8),
                 rip(9),
                 ripDiscard(10),
                 egp(11),
                 bgpExternal(12),
                 bgpInternal(13),
                 bgpAggrDiscard(14),
                 redistrib(15) }
   ACCESS     not-accessible
   STATUS     mandatory
   DESCRIPTION
     "This variable represents an index for the vrIpRdb tables."
::= { vrIpRdbRowStatusEntry 12 }

vrIpRdbGatewayIndex OBJECT-TYPE
   SYNTAX     IpAddress 
   ACCESS     not-accessible
   STATUS     mandatory
   DESCRIPTION
     "This variable represents an index for the vrIpRdb tables."
::= { vrIpRdbRowStatusEntry 13 }

vrIpRdbOperTable OBJECT-TYPE
   SYNTAX     SEQUENCE OF VrIpRdbOperEntry
   ACCESS     not-accessible
   STATUS     mandatory
   DESCRIPTION
     "*** THIS TABLE CURRENTLY NOT IMPLEMENTED ***

      Identifies a group of operational attributes associated with each entry in 
      the routing database."
::= { vrIpRdb 10 }

vrIpRdbOperEntry OBJECT-TYPE
   SYNTAX     VrIpRdbOperEntry
   ACCESS     not-accessible
   STATUS     mandatory
   DESCRIPTION
     "An entry in the vrIpRdbOperTable."
   INDEX {
      vrIndex,
      vrIpIndex,
      vrIpRdbDestAddressIndex,
      vrIpRdbDestMaskIndex,
      vrIpRdbProtocolIndex,
      vrIpRdbGatewayIndex }
::= { vrIpRdbOperTable 1 }

VrIpRdbOperEntry ::= SEQUENCE {
   vrIpRdbMetric
      INTEGER,
   vrIpRdbPreference
      Unsigned32,
   vrIpRdbAge
      Gauge32 }

vrIpRdbMetric OBJECT-TYPE
   SYNTAX     INTEGER (-1..65535)
   ACCESS     read-only
   STATUS     mandatory
   DESCRIPTION
     "This attribute specifies the primary routing metric for this route. The 
      semantics of this metric are determined by the routing protocol specified 
      by the value of the index to this entry protocol. If this metric is not used, 
      its value should be set to -1."
   DEFVAL     { -1 }
::= { vrIpRdbOperEntry 1 }

vrIpRdbPreference OBJECT-TYPE
   SYNTAX     Unsigned32 (0..255)
   ACCESS     read-only
   STATUS     mandatory
   DESCRIPTION
     "This attribute specifies the the preference value of this particular 
      entry. The value of this attribute affects the way the routeEntries in this 
      database are selected for installing it in the forwardingTable. The lower 
      the preference value of this entry, the higher are the chances that this 
      entry will be selected to install in the ForwardTable."
::= { vrIpRdbOperEntry 2 }

vrIpRdbAge OBJECT-TYPE
   SYNTAX     Gauge32 (0..4294967295)
   ACCESS     read-only
   STATUS     mandatory
   DESCRIPTION
     "This attribute specifies the number of seconds since this route was last 
      updated or otherwise determined to be correct."
::= { vrIpRdbOperEntry 3 }

-- 
-- *** THIS SUBTREE CURRENTLY NOT IMPLEMENTED ***
-- 

-- Vr/<string> Ip InterfaceEntry/<IpAddr>
-- 
-- This component contains information about all the provisioned logicalIf 
-- entries under all ipPort components.

vrIpIf OBJECT IDENTIFIER ::= { vrIp 5 }



vrIpIfRowStatusTable OBJECT-TYPE
   SYNTAX     SEQUENCE OF VrIpIfRowStatusEntry
   ACCESS     not-accessible
   STATUS     mandatory
   DESCRIPTION
     "*** THIS TABLE CURRENTLY NOT IMPLEMENTED ***

      This entry controls the addition and deletion of 
      vrIpIf components."
::= { vrIpIf 1 }

vrIpIfRowStatusEntry OBJECT-TYPE
   SYNTAX     VrIpIfRowStatusEntry
   ACCESS     not-accessible
   STATUS     mandatory
   DESCRIPTION
     "A single entry in the table represents a single 
      vrIpIf component."
   INDEX {
      vrIndex,
      vrIpIndex,
      vrIpIfInterfaceAddressIndex }
::= { vrIpIfRowStatusTable 1 }

VrIpIfRowStatusEntry ::= SEQUENCE {
   vrIpIfRowStatus
      RowStatus,
   vrIpIfComponentName
      DisplayString,
   vrIpIfStorageType
      StorageType,
   vrIpIfInterfaceAddressIndex
      IpAddress }

vrIpIfRowStatus OBJECT-TYPE
   SYNTAX     RowStatus 
   ACCESS     read-only
   STATUS     mandatory
   DESCRIPTION
     "This variable is used as the basis for SNMP naming of
      vrIpIf components.
      These components cannot be added nor deleted."
::= { vrIpIfRowStatusEntry 1 }

vrIpIfComponentName OBJECT-TYPE
   SYNTAX     DisplayString 
   ACCESS     read-only
   STATUS     mandatory
   DESCRIPTION
     "This variable provides the component's string name for
      use with the ASCII Console Interface"
::= { vrIpIfRowStatusEntry 2 }

vrIpIfStorageType OBJECT-TYPE
   SYNTAX     StorageType 
   ACCESS     read-only
   STATUS     mandatory
   DESCRIPTION
     "This variable represents the storage type value for the
      vrIpIf tables."
::= { vrIpIfRowStatusEntry 4 }

vrIpIfInterfaceAddressIndex OBJECT-TYPE
   SYNTAX     IpAddress 
   ACCESS     not-accessible
   STATUS     mandatory
   DESCRIPTION
     "This variable represents the index for the vrIpIf tables."
::= { vrIpIfRowStatusEntry 10 }

vrIpIfOperTable OBJECT-TYPE
   SYNTAX     SEQUENCE OF VrIpIfOperEntry
   ACCESS     not-accessible
   STATUS     mandatory
   DESCRIPTION
     "*** THIS TABLE CURRENTLY NOT IMPLEMENTED ***

      Identifies a group of operational attributes associated with each entry in 
      the Ip interface table."
::= { vrIpIf 10 }

vrIpIfOperEntry OBJECT-TYPE
   SYNTAX     VrIpIfOperEntry
   ACCESS     not-accessible
   STATUS     mandatory
   DESCRIPTION
     "An entry in the vrIpIfOperTable."
   INDEX {
      vrIndex,
      vrIpIndex,
      vrIpIfInterfaceAddressIndex }
::= { vrIpIfOperTable 1 }

VrIpIfOperEntry ::= SEQUENCE {
   vrIpIfInterfaceMask
      IpAddress,
   vrIpIfStatus
      INTEGER,
   vrIpIfPPName
      AsciiString,
   vrIpIfMediaType
      INTEGER,
   vrIpIfHardwareAddress
      DashedHexString,
   vrIpIfMtu
      Unsigned32,
   vrIpIfBroadcastAddress
      IpAddress,
   vrIpIfNcHardwareAddress
      DashedHexString }

vrIpIfInterfaceMask OBJECT-TYPE
   SYNTAX     IpAddress 
   ACCESS     read-only
   STATUS     mandatory
   DESCRIPTION
     "This attribute indicates the mask for this interface entry."
::= { vrIpIfOperEntry 1 }

vrIpIfStatus OBJECT-TYPE
   SYNTAX     INTEGER  {
                 up(1),
                 down(2),
                 disabled(3) }
   ACCESS     read-only
   STATUS     mandatory
   DESCRIPTION
     "This attribute specifies the status of the provisioned Ip 
      logicalInterface entry. A value of disabled is used when the parent 
      components Vr, Ip or ipPort is in a disabled state. A value of up is used 
      when the interface is in an operational state. A state of down is used if 
      the media associated with this interface is not ready or disabled."
::= { vrIpIfOperEntry 2 }

vrIpIfPPName OBJECT-TYPE
   SYNTAX     AsciiString (SIZE (1..23))
   ACCESS     read-only
   STATUS     mandatory
   DESCRIPTION
     "Indicates the name of the protocol port this logicalIfEntry belongs to."
::= { vrIpIfOperEntry 3 }

vrIpIfMediaType OBJECT-TYPE
   SYNTAX     INTEGER  {
                 none(1),
                 tokenRing(2),
                 ethernet(3),
                 fddi(4),
                 x25(5),
                 frameRelay(6),
                 ppp(7),
                 clusterBridge(8),
                 virtualLink(9),
                 vcpEther(10),
                 vcpToken(11),
                 vns(12),
                 smds(13),
                 atmMpeVcEncap(14),
                 atmMpeLlcEncap(15),
                 lecEther(16),
                 lecToken(17),
                 tunnel(18),
                 virtual(19) }
   ACCESS     read-only
   STATUS     mandatory
   DESCRIPTION
     "This attribute indicates the media type of interface. When the 
      interface is down, a value of none indicates the media stays 
      down from the beginning. When the interface is down, a value 
      of some valid media type indicates the media is brought down 
      after it was up. Otherwise, when the interface is up or 
      disabled, this attribute should reflect the proper media type of 
      the interface."
::= { vrIpIfOperEntry 4 }

vrIpIfHardwareAddress OBJECT-TYPE
   SYNTAX     DashedHexString (SIZE (0..8))
   ACCESS     read-only
   STATUS     mandatory
   DESCRIPTION
     "This attribute specifies the hardware address of the media in canonical 
      form if applicable. The non-canonical version of this address is 
      indicated in ncHardwareAddress."
::= { vrIpIfOperEntry 5 }

vrIpIfMtu OBJECT-TYPE
   SYNTAX     Unsigned32 (0..0 | 576..18944)
   ACCESS     read-only
   STATUS     mandatory
   DESCRIPTION
     "This attribute specifies the maximum transmission unit applicable for 
      this logicalInterface. A value of 0 is used for the interfaces where all the 
      necessary information is not available to compute the mtu applicable for 
      this interface."
::= { vrIpIfOperEntry 6 }

vrIpIfBroadcastAddress OBJECT-TYPE
   SYNTAX     IpAddress 
   ACCESS     read-only
   STATUS     mandatory
   DESCRIPTION
     "This attribute indicates the destination IP address to be used by any 
      application which needs to broadcast on this interface. The value is 
      determined by the corresponding LogicalIf component's 
      broadcastAddress attribute."
::= { vrIpIfOperEntry 7 }

vrIpIfNcHardwareAddress OBJECT-TYPE
   SYNTAX     DashedHexString (SIZE (0..8))
   ACCESS     read-only
   STATUS     mandatory
   DESCRIPTION
     "This attribute is the non-canonical version of hardwareAddress. This 
      attribute is not displayed for interfaces on non-LAN media."
::= { vrIpIfOperEntry 8 }


-- Vr/<string> Ip Egp
-- This is used to run the Exterior Gateway Protocol for IP.

vrIpEgp OBJECT IDENTIFIER ::= { vrIp 6 }



vrIpEgpRowStatusTable OBJECT-TYPE
   SYNTAX     SEQUENCE OF VrIpEgpRowStatusEntry
   ACCESS     not-accessible
   STATUS     mandatory
   DESCRIPTION
     "This entry controls the addition and deletion of 
      vrIpEgp components."
::= { vrIpEgp 1 }

vrIpEgpRowStatusEntry OBJECT-TYPE
   SYNTAX     VrIpEgpRowStatusEntry
   ACCESS     not-accessible
   STATUS     mandatory
   DESCRIPTION
     "A single entry in the table represents a single 
      vrIpEgp component."
   INDEX {
      vrIndex,
      vrIpIndex,
      vrIpEgpIndex }
::= { vrIpEgpRowStatusTable 1 }

VrIpEgpRowStatusEntry ::= SEQUENCE {
   vrIpEgpRowStatus
      RowStatus,
   vrIpEgpComponentName
      DisplayString,
   vrIpEgpStorageType
      StorageType,
   vrIpEgpIndex
      NonReplicated }

vrIpEgpRowStatus OBJECT-TYPE
   SYNTAX     RowStatus 
   ACCESS     read-write
   STATUS     mandatory
   DESCRIPTION
     "This variable is used as the basis for SNMP naming of
      vrIpEgp components.
      These components can be added and deleted."
::= { vrIpEgpRowStatusEntry 1 }

vrIpEgpComponentName OBJECT-TYPE
   SYNTAX     DisplayString 
   ACCESS     read-only
   STATUS     mandatory
   DESCRIPTION
     "This variable provides the component's string name for
      use with the ASCII Console Interface"
::= { vrIpEgpRowStatusEntry 2 }

vrIpEgpStorageType OBJECT-TYPE
   SYNTAX     StorageType 
   ACCESS     read-only
   STATUS     mandatory
   DESCRIPTION
     "This variable represents the storage type value for the
      vrIpEgp tables."
::= { vrIpEgpRowStatusEntry 4 }

vrIpEgpIndex OBJECT-TYPE
   SYNTAX     NonReplicated 
   ACCESS     not-accessible
   STATUS     mandatory
   DESCRIPTION
     "This variable represents the index for the vrIpEgp tables."
::= { vrIpEgpRowStatusEntry 10 }

vrIpEgpProvTable OBJECT-TYPE
   SYNTAX     SEQUENCE OF VrIpEgpProvEntry
   ACCESS     not-accessible
   STATUS     mandatory
   DESCRIPTION
     "This group contains the provisionable attributes for the EGP component"
::= { vrIpEgp 10 }

vrIpEgpProvEntry OBJECT-TYPE
   SYNTAX     VrIpEgpProvEntry
   ACCESS     not-accessible
   STATUS     mandatory
   DESCRIPTION
     "An entry in the vrIpEgpProvTable."
   INDEX {
      vrIndex,
      vrIpIndex,
      vrIpEgpIndex }
::= { vrIpEgpProvTable 1 }

VrIpEgpProvEntry ::= SEQUENCE {
   vrIpEgpAsId
      Unsigned32,
   vrIpEgpDefaultHelloInterval
      Unsigned32,
   vrIpEgpDefaultPollInterval
      Unsigned32,
   vrIpEgpMaxNatNets
      Unsigned32,
   vrIpEgpMaxBufferSize
      Unsigned32 }

vrIpEgpAsId OBJECT-TYPE
   SYNTAX     Unsigned32 (1..65535)
   ACCESS     read-write
   STATUS     mandatory
   DESCRIPTION
     "The autonomous system identifier for this EGP entity. The 
      value of this asId can not be equal to the value of 
      EgpNeighborEntry asId."
::= { vrIpEgpProvEntry 2 }

vrIpEgpDefaultHelloInterval OBJECT-TYPE
   SYNTAX     Unsigned32 (30..900)
   ACCESS     read-write
   STATUS     mandatory
   DESCRIPTION
     "This attribute is used to configure the default hello interval for each 
      neighbor. This attribute's value is used by the application for each 
      EgpNeighbor whose helloInterval has not been set."
   DEFVAL     { 30 }
::= { vrIpEgpProvEntry 3 }

vrIpEgpDefaultPollInterval OBJECT-TYPE
   SYNTAX     Unsigned32 (120..3600)
   ACCESS     read-write
   STATUS     mandatory
   DESCRIPTION
     "This attribute is used to configure the default polling interval for the 
      EGP Neighbor. This attribute's value is used by the application for each 
      EgpNeighbor whose pollInterval has not been set."
   DEFVAL     { 120 }
::= { vrIpEgpProvEntry 4 }

vrIpEgpMaxNatNets OBJECT-TYPE
   SYNTAX     Unsigned32 (1..65535)
   ACCESS     read-write
   STATUS     mandatory
   DESCRIPTION
     "This attribute is used to configure the maximum number of external 
      natural networks this virtual router will be advertising via EGP."
   DEFVAL     { 500 }
::= { vrIpEgpProvEntry 5 }

vrIpEgpMaxBufferSize OBJECT-TYPE
   SYNTAX     Unsigned32 (2..16)
   ACCESS     read-write
   STATUS     mandatory
   DESCRIPTION
     "This attribute specifies the maximum buffer size (in 1024 byte memory 
      blocks) to be used for an EGP update to be sent."
   DEFVAL     { 4 }
::= { vrIpEgpProvEntry 6 }

vrIpEgpStatsTable OBJECT-TYPE
   SYNTAX     SEQUENCE OF VrIpEgpStatsEntry
   ACCESS     not-accessible
   STATUS     mandatory
   DESCRIPTION
     "These set of attributes identifies the statistics for the EGP component."
::= { vrIpEgp 11 }

vrIpEgpStatsEntry OBJECT-TYPE
   SYNTAX     VrIpEgpStatsEntry
   ACCESS     not-accessible
   STATUS     mandatory
   DESCRIPTION
     "An entry in the vrIpEgpStatsTable."
   INDEX {
      vrIndex,
      vrIpIndex,
      vrIpEgpIndex }
::= { vrIpEgpStatsTable 1 }

VrIpEgpStatsEntry ::= SEQUENCE {
   vrIpEgpInMsgs
      Counter32,
   vrIpEgpInErrorMsgs
      Counter32,
   vrIpEgpOutErrorMsgs
      Counter32,
   vrIpEgpInErrors
      Counter32,
   vrIpEgpOutMsgs
      Counter32,
   vrIpEgpOutErrors
      Counter32 }

vrIpEgpInMsgs OBJECT-TYPE
   SYNTAX     Counter32 
   ACCESS     read-only
   STATUS     mandatory
   DESCRIPTION
     "Identifies the number of EGP messages received without error. This 
      counter will wraparound once the value reaches the maximum value."
::= { vrIpEgpStatsEntry 1 }

vrIpEgpInErrorMsgs OBJECT-TYPE
   SYNTAX     Counter32 
   ACCESS     read-only
   STATUS     mandatory
   DESCRIPTION
     "Identifies the sum of EGP error messages from all the neighbors. This 
      counter will wraparound once the value reaches the maximum value."
::= { vrIpEgpStatsEntry 2 }

vrIpEgpOutErrorMsgs OBJECT-TYPE
   SYNTAX     Counter32 
   ACCESS     read-only
   STATUS     mandatory
   DESCRIPTION
     "Indicates the sum of Egp error messages sent to all the neighbors. This 
      counter will wraparound once the value reaches the maximum value."
::= { vrIpEgpStatsEntry 3 }

vrIpEgpInErrors OBJECT-TYPE
   SYNTAX     Counter32 
   ACCESS     read-only
   STATUS     mandatory
   DESCRIPTION
     "Identifies the number of EGP messages that proved to be in error. This 
      counter will wraparound once the value reaches the maximum value."
::= { vrIpEgpStatsEntry 4 }

vrIpEgpOutMsgs OBJECT-TYPE
   SYNTAX     Counter32 
   ACCESS     read-only
   STATUS     mandatory
   DESCRIPTION
     "The total number of locally generated EGP messages. This counter will 
      wraparound once the value reaches the maximum value."
::= { vrIpEgpStatsEntry 5 }

vrIpEgpOutErrors OBJECT-TYPE
   SYNTAX     Counter32 
   ACCESS     read-only
   STATUS     mandatory
   DESCRIPTION
     "The number of EGP messages that were locally generated but were not 
      sent out due to resource limitations within an EGP entity.This counter 
      will wraparound once the value reaches the maximum value."
::= { vrIpEgpStatsEntry 6 }

vrIpEgpStateTable OBJECT-TYPE
   SYNTAX     SEQUENCE OF VrIpEgpStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { vrIpEgp 12 }

vrIpEgpStateEntry OBJECT-TYPE
   SYNTAX     VrIpEgpStateEntry
   ACCESS     not-accessible
   STATUS     mandatory
   DESCRIPTION
     "An entry in the vrIpEgpStateTable."
   INDEX {
      vrIndex,
      vrIpIndex,
      vrIpEgpIndex }
::= { vrIpEgpStateTable 1 }

VrIpEgpStateEntry ::= SEQUENCE {
   vrIpEgpAdminState
      INTEGER,
   vrIpEgpOperationalState
      INTEGER,
   vrIpEgpUsageState
      INTEGER }

vrIpEgpAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { vrIpEgpStateEntry 1 }

vrIpEgpOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { vrIpEgpStateEntry 2 }

vrIpEgpUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { vrIpEgpStateEntry 3 }

vrIpEgpAdminControlTable OBJECT-TYPE
   SYNTAX     SEQUENCE OF VrIpEgpAdminControlEntry
   ACCESS     not-accessible
   STATUS     mandatory
   DESCRIPTION
     "This group includes the Administrative Control attribute. This 
      attribute defines the current administrative state of this component."
::= { vrIpEgp 13 }

vrIpEgpAdminControlEntry OBJECT-TYPE
   SYNTAX     VrIpEgpAdminControlEntry
   ACCESS     not-accessible
   STATUS     mandatory
   DESCRIPTION
     "An entry in the vrIpEgpAdminControlTable."
   INDEX {
      vrIndex,
      vrIpIndex,
      vrIpEgpIndex }
::= { vrIpEgpAdminControlTable 1 }

VrIpEgpAdminControlEntry ::= SEQUENCE {
   vrIpEgpSnmpAdminStatus
      INTEGER }

vrIpEgpSnmpAdminStatus OBJECT-TYPE
   SYNTAX     INTEGER  {
                 up(1),
                 down(2),
                 testing(3) }
   ACCESS     read-write
   STATUS     mandatory
   DESCRIPTION
     "The desired state of the interface. The up state indicates the 
      interface is operational and packet forwarding is allowed. The down 
      state indicates the interface is not operational and packet forwarding 
      is unavailable. The testing state indicates that no operational 
      packets can be passed."
   DEFVAL     { up }
::= { vrIpEgpAdminControlEntry 1 }

vrIpEgpOperStatusTable OBJECT-TYPE
   SYNTAX     SEQUENCE OF VrIpEgpOperStatusEntry
   ACCESS     not-accessible
   STATUS     mandatory
   DESCRIPTION
     "This group includes the Operational Status attribute. This attribute 
      defines the current operational state of this component."
::= { vrIpEgp 16 }

vrIpEgpOperStatusEntry OBJECT-TYPE
   SYNTAX     VrIpEgpOperStatusEntry
   ACCESS     not-accessible
   STATUS     mandatory
   DESCRIPTION
     "An entry in the vrIpEgpOperStatusTable."
   INDEX {
      vrIndex,
      vrIpIndex,
      vrIpEgpIndex }
::= { vrIpEgpOperStatusTable 1 }

VrIpEgpOperStatusEntry ::= SEQUENCE {
   vrIpEgpSnmpOperStatus
      INTEGER }

vrIpEgpSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { vrIpEgpOperStatusEntry 1 }


-- Vr/<string> Ip Egp NeighborEntry/<Ip Address>
-- This component identifies the properties of each EGP neighbor.
-- The index value of this entry should belong to one of the subnets 
-- provisioned as logicalIfEntry under one of the IpPort.

vrIpEgpNbr OBJECT IDENTIFIER ::= { vrIpEgp 2 }



vrIpEgpNbrRowStatusTable OBJECT-TYPE
   SYNTAX     SEQUENCE OF VrIpEgpNbrRowStatusEntry
   ACCESS     not-accessible
   STATUS     mandatory
   DESCRIPTION
     "This entry controls the addition and deletion of 
      vrIpEgpNbr components."
::= { vrIpEgpNbr 1 }

vrIpEgpNbrRowStatusEntry OBJECT-TYPE
   SYNTAX     VrIpEgpNbrRowStatusEntry
   ACCESS     not-accessible
   STATUS     mandatory
   DESCRIPTION
     "A single entry in the table represents a single 
      vrIpEgpNbr component."
   INDEX {
      vrIndex,
      vrIpIndex,
      vrIpEgpIndex,
      vrIpEgpNbrNeighborAddressIndex }
::= { vrIpEgpNbrRowStatusTable 1 }

VrIpEgpNbrRowStatusEntry ::= SEQUENCE {
   vrIpEgpNbrRowStatus
      RowStatus,
   vrIpEgpNbrComponentName
      DisplayString,
   vrIpEgpNbrStorageType
      StorageType,
   vrIpEgpNbrNeighborAddressIndex
      IpAddress }

vrIpEgpNbrRowStatus OBJECT-TYPE
   SYNTAX     RowStatus 
   ACCESS     read-write
   STATUS     mandatory
   DESCRIPTION
     "This variable is used as the basis for SNMP naming of
      vrIpEgpNbr components.
      These components can be added and deleted."
::= { vrIpEgpNbrRowStatusEntry 1 }

vrIpEgpNbrComponentName OBJECT-TYPE
   SYNTAX     DisplayString 
   ACCESS     read-only
   STATUS     mandatory
   DESCRIPTION
     "This variable provides the component's string name for
      use with the ASCII Console Interface"
::= { vrIpEgpNbrRowStatusEntry 2 }

vrIpEgpNbrStorageType OBJECT-TYPE
   SYNTAX     StorageType 
   ACCESS     read-only
   STATUS     mandatory
   DESCRIPTION
     "This variable represents the storage type value for the
      vrIpEgpNbr tables."
::= { vrIpEgpNbrRowStatusEntry 4 }

vrIpEgpNbrNeighborAddressIndex OBJECT-TYPE
   SYNTAX     IpAddress 
   ACCESS     not-accessible
   STATUS     mandatory
   DESCRIPTION
     "This variable represents the index for the vrIpEgpNbr tables."
::= { vrIpEgpNbrRowStatusEntry 10 }

vrIpEgpNbrProvTable OBJECT-TYPE
   SYNTAX     SEQUENCE OF VrIpEgpNbrProvEntry
   ACCESS     not-accessible
   STATUS     mandatory
   DESCRIPTION
     "This group of attributes identify the provisionable attributes for this EGP 
      neighbor."
::= { vrIpEgpNbr 10 }

vrIpEgpNbrProvEntry OBJECT-TYPE
   SYNTAX     VrIpEgpNbrProvEntry
   ACCESS     not-accessible
   STATUS     mandatory
   DESCRIPTION
     "An entry in the vrIpEgpNbrProvTable."
   INDEX {
      vrIndex,
      vrIpIndex,
      vrIpEgpIndex,
      vrIpEgpNbrNeighborAddressIndex }
::= { vrIpEgpNbrProvTable 1 }

VrIpEgpNbrProvEntry ::= SEQUENCE {
   vrIpEgpNbrAsId
      Unsigned32,
   vrIpEgpNbrMode
      INTEGER,
   vrIpEgpNbrGenerateDefaultRoute
      INTEGER,
   vrIpEgpNbrDefaultRouteMetric
      Unsigned32,
   vrIpEgpNbrDefaultMetric
      Unsigned32,
   vrIpEgpNbrHelloInterval
      Unsigned32,
   vrIpEgpNbrPollInterval
      Unsigned32 }

vrIpEgpNbrAsId OBJECT-TYPE
   SYNTAX     Unsigned32 (1..65535)
   ACCESS     read-write
   STATUS     mandatory
   DESCRIPTION
     "The autonomous system identifier of this EGP peer. 
      The value of this neighbor's asId should not be equal to the asId value 
      of Egp entity"
::= { vrIpEgpNbrProvEntry 1 }

vrIpEgpNbrMode OBJECT-TYPE
   SYNTAX     INTEGER  {
                 active(1),
                 passive(2) }
   ACCESS     read-write
   STATUS     mandatory
   DESCRIPTION
     "This attribute will indicate whether this neighbor is being configured as 
      an active or passive neighbor."
   DEFVAL     { active }
::= { vrIpEgpNbrProvEntry 2 }

vrIpEgpNbrGenerateDefaultRoute OBJECT-TYPE
   SYNTAX     INTEGER  {
                 yes(1),
                 no(2) }
   ACCESS     read-write
   STATUS     mandatory
   DESCRIPTION
     "This attribute distinguishes whether or not the default route should be 
      generated. This route is put in the EGP update along with the normal 
      EGP update routes when updates are sent to this EGP neighbor"
   DEFVAL     { no }
::= { vrIpEgpNbrProvEntry 3 }

vrIpEgpNbrDefaultRouteMetric OBJECT-TYPE
   SYNTAX     Unsigned32 (0..255)
   ACCESS     read-write
   STATUS     mandatory
   DESCRIPTION
     "This attribute identifies the Metric to be used for propagating the 
      'Default Route'. The value of defaultRouteMetric is used only in the 
      case where the value of the attribute generateDefaultRoute is set to yes."
   DEFVAL     { 128 }
::= { vrIpEgpNbrProvEntry 4 }

vrIpEgpNbrDefaultMetric OBJECT-TYPE
   SYNTAX     Unsigned32 (0..255)
   ACCESS     read-write
   STATUS     mandatory
   DESCRIPTION
     "This attribute identifies the default metric value for routes that are 
      exported to this EgpNeighbor. This value is used when exporting routes 
      to this neighbor and no Export policy applies a different metric."
   DEFVAL     { 128 }
::= { vrIpEgpNbrProvEntry 5 }

vrIpEgpNbrHelloInterval OBJECT-TYPE
   SYNTAX     Unsigned32 (30..120)
   ACCESS     read-write
   STATUS     mandatory
   DESCRIPTION
     "This attribute identifies the interval in seconds, between EGP hello 
      command retransmissions. This is the P1 timer in the RFC904. This 
      value may change in operation due to negotiations."
   DEFVAL     { 30 }
::= { vrIpEgpNbrProvEntry 6 }

vrIpEgpNbrPollInterval OBJECT-TYPE
   SYNTAX     Unsigned32 (120..480)
   ACCESS     read-write
   STATUS     mandatory
   DESCRIPTION
     "This attribute identifies the interval in seconds, between EGP poll 
      command retransmissions. This is the P2 timer in the RFC904. This 
      value may change in operation due to negotiations."
   DEFVAL     { 120 }
::= { vrIpEgpNbrProvEntry 7 }

vrIpEgpNbrOperTable OBJECT-TYPE
   SYNTAX     SEQUENCE OF VrIpEgpNbrOperEntry
   ACCESS     not-accessible
   STATUS     mandatory
   DESCRIPTION
     "This group of attributes identifies the operational set of attributes for the 
      NeighborEntry component."
::= { vrIpEgpNbr 11 }

vrIpEgpNbrOperEntry OBJECT-TYPE
   SYNTAX     VrIpEgpNbrOperEntry
   ACCESS     not-accessible
   STATUS     mandatory
   DESCRIPTION
     "An entry in the vrIpEgpNbrOperTable."
   INDEX {
      vrIndex,
      vrIpIndex,
      vrIpEgpIndex,
      vrIpEgpNbrNeighborAddressIndex }
::= { vrIpEgpNbrOperTable 1 }

VrIpEgpNbrOperEntry ::= SEQUENCE {
   vrIpEgpNbrState
      INTEGER,
   vrIpEgpNbrInMsgs
      Counter32,
   vrIpEgpNbrInErrors
      Counter32,
   vrIpEgpNbrOutMsgs
      Counter32,
   vrIpEgpNbrOutErrors
      Counter32,
   vrIpEgpNbrInErrorMsgs
      Counter32,
   vrIpEgpNbrOutErrorMsgs
      Counter32,
   vrIpEgpNbrStateUps
      Counter32,
   vrIpEgpNbrStateDowns
      Counter32,
   vrIpEgpNbrEventTrigger
      INTEGER }

vrIpEgpNbrState OBJECT-TYPE
   SYNTAX     INTEGER  {
                 idle(1),
                 acquisition(2),
                 down(3),
                 up(4),
                 cease(5) }
   ACCESS     read-only
   STATUS     mandatory
   DESCRIPTION
     "This attribute describes the state of the local system with respect to this 
      entry's EGP Neighbor."
::= { vrIpEgpNbrOperEntry 1 }

vrIpEgpNbrInMsgs OBJECT-TYPE
   SYNTAX     Counter32 
   ACCESS     read-only
   STATUS     mandatory
   DESCRIPTION
     "The number of EGP messages received without error from the EGP 
      peer. This counter will wraparound once the value reaches the maximum 
      value."
::= { vrIpEgpNbrOperEntry 2 }

vrIpEgpNbrInErrors OBJECT-TYPE
   SYNTAX     Counter32 
   ACCESS     read-only
   STATUS     mandatory
   DESCRIPTION
     "The number of messages received from this EGP peer that proved to be 
      in error. This counter will wraparound once the value reaches the 
      maximum value."
::= { vrIpEgpNbrOperEntry 3 }

vrIpEgpNbrOutMsgs OBJECT-TYPE
   SYNTAX     Counter32 
   ACCESS     read-only
   STATUS     mandatory
   DESCRIPTION
     "The number of locally generated EGP messages for this EGP peer. This 
      counter will wraparound once the value reaches the maximum value."
::= { vrIpEgpNbrOperEntry 4 }

vrIpEgpNbrOutErrors OBJECT-TYPE
   SYNTAX     Counter32 
   ACCESS     read-only
   STATUS     mandatory
   DESCRIPTION
     "The number of locally generated EGP messages not sent to this EGP 
      peer due to resource limitations within an EGP entity.This counter will 
      wraparound once the value reaches the maximum value."
::= { vrIpEgpNbrOperEntry 5 }

vrIpEgpNbrInErrorMsgs OBJECT-TYPE
   SYNTAX     Counter32 
   ACCESS     read-only
   STATUS     mandatory
   DESCRIPTION
     "The number of EGP-defined error messages received from this EGP 
      peer.This counter will wraparound once the value reaches the maximum 
      value."
::= { vrIpEgpNbrOperEntry 6 }

vrIpEgpNbrOutErrorMsgs OBJECT-TYPE
   SYNTAX     Counter32 
   ACCESS     read-only
   STATUS     mandatory
   DESCRIPTION
     "The number of EGP-defined error messages sent to this EGP peer.This 
      counter will wraparound once the value reaches the maximum value."
::= { vrIpEgpNbrOperEntry 7 }

vrIpEgpNbrStateUps OBJECT-TYPE
   SYNTAX     Counter32 
   ACCESS     read-only
   STATUS     mandatory
   DESCRIPTION
     "The number of EGP state transitions to the UP state with this EGP peer. 
      This counter will wraparound once the value reaches the maximum 
      value."
::= { vrIpEgpNbrOperEntry 8 }

vrIpEgpNbrStateDowns OBJECT-TYPE
   SYNTAX     Counter32 
   ACCESS     read-only
   STATUS     mandatory
   DESCRIPTION
     "The number of EGP state transitions from the UP state to any other state 
      with this EGP peer. This counter will wraparound once the value reaches 
      the maximum value."
::= { vrIpEgpNbrOperEntry 9 }

vrIpEgpNbrEventTrigger OBJECT-TYPE
   SYNTAX     INTEGER  {
                 start(1),
                 stop(2) }
   ACCESS     read-only
   STATUS     mandatory
   DESCRIPTION
     "This attribute is used to control the state of the Neighbor. It is not 
      allowed to change.
      This attribute from SNMP perspective deviates from MIB that it is made 
      READONLY."
   DEFVAL     { start }
::= { vrIpEgpNbrOperEntry 10 }


-- Vr/<string> Ip Egp Import/n
-- This component controls the functionality of route leaking. In other 
-- words, this component will determine what routes are used by EGP.

vrIpEgpImport OBJECT IDENTIFIER ::= { vrIpEgp 3 }



vrIpEgpImportRowStatusTable OBJECT-TYPE
   SYNTAX     SEQUENCE OF VrIpEgpImportRowStatusEntry
   ACCESS     not-accessible
   STATUS     mandatory
   DESCRIPTION
     "This entry controls the addition and deletion of 
      vrIpEgpImport components."
::= { vrIpEgpImport 1 }

vrIpEgpImportRowStatusEntry OBJECT-TYPE
   SYNTAX     VrIpEgpImportRowStatusEntry
   ACCESS     not-accessible
   STATUS     mandatory
   DESCRIPTION
     "A single entry in the table represents a single 
      vrIpEgpImport component."
   INDEX {
      vrIndex,
      vrIpIndex,
      vrIpEgpIndex,
      vrIpEgpImportIndex }
::= { vrIpEgpImportRowStatusTable 1 }

VrIpEgpImportRowStatusEntry ::= SEQUENCE {
   vrIpEgpImportRowStatus
      RowStatus,
   vrIpEgpImportComponentName
      DisplayString,
   vrIpEgpImportStorageType
      StorageType,
   vrIpEgpImportIndex
      Integer32 }

vrIpEgpImportRowStatus OBJECT-TYPE
   SYNTAX     RowStatus 
   ACCESS     read-write
   STATUS     mandatory
   DESCRIPTION
     "This variable is used as the basis for SNMP naming of
      vrIpEgpImport components.
      These components can be added and deleted."
::= { vrIpEgpImportRowStatusEntry 1 }

vrIpEgpImportComponentName OBJECT-TYPE
   SYNTAX     DisplayString 
   ACCESS     read-only
   STATUS     mandatory
   DESCRIPTION
     "This variable provides the component's string name for
      use with the ASCII Console Interface"
::= { vrIpEgpImportRowStatusEntry 2 }

vrIpEgpImportStorageType OBJECT-TYPE
   SYNTAX     StorageType 
   ACCESS     read-only
   STATUS     mandatory
   DESCRIPTION
     "This variable represents the storage type value for the
      vrIpEgpImport tables."
::= { vrIpEgpImportRowStatusEntry 4 }

vrIpEgpImportIndex OBJECT-TYPE
   SYNTAX     Integer32 (0..65535)
   ACCESS     not-accessible
   STATUS     mandatory
   DESCRIPTION
     "This variable represents the index for the vrIpEgpImport tables."
::= { vrIpEgpImportRowStatusEntry 10 }

vrIpEgpImportProvTable OBJECT-TYPE
   SYNTAX     SEQUENCE OF VrIpEgpImportProvEntry
   ACCESS     not-accessible
   STATUS     mandatory
   DESCRIPTION
     "These set of attributes describe the provisionable attributes for the 
      import component."
::= { vrIpEgpImport 10 }

vrIpEgpImportProvEntry OBJECT-TYPE
   SYNTAX     VrIpEgpImportProvEntry
   ACCESS     not-accessible
   STATUS     mandatory
   DESCRIPTION
     "An entry in the vrIpEgpImportProvTable."
   INDEX {
      vrIndex,
      vrIpIndex,
      vrIpEgpIndex,
      vrIpEgpImportIndex }
::= { vrIpEgpImportProvTable 1 }

VrIpEgpImportProvEntry ::= SEQUENCE {
   vrIpEgpImportUsageFlag
      INTEGER,
   vrIpEgpImportImportMetric
      Unsigned32,
   vrIpEgpImportNbrAsId
      Unsigned32 }

vrIpEgpImportUsageFlag OBJECT-TYPE
   SYNTAX     INTEGER  {
                 use(1),
                 ignore(2) }
   ACCESS     read-write
   STATUS     mandatory
   DESCRIPTION
     "This flag will determine whether or not EGP will use or ignore 
      information in updates received. If the attribute nbrAsId is not specified 
      or any of the NetworkList components are not added, then this attribute 
      when set to ignore will ignore all incoming information."
   DEFVAL     { use }
::= { vrIpEgpImportProvEntry 1 }

vrIpEgpImportImportMetric OBJECT-TYPE
   SYNTAX     Unsigned32 (0..255)
   ACCESS     read-write
   STATUS     mandatory
   DESCRIPTION
     "This attribute is used to set the metric value to be included in the routing 
      table for any routes sent because this particular import instance was it's 
      'best match' policy.
      However this attribute is not a selection key. It should not use or ignore 
      a particular metric value. If the value for this attribute is not specified, 
      then the metric value received in an Egp update will be used.
      
      Note: 
      
      When setting this value, caution should be taken to set the metric value 
      in all relevant Import components to make sure that all matching 
      policies for a given route have the same metric set. This will insure that 
      there are no situations where a specific metric was desired, but doesn't 
      get used in the update because the 'best match' policy for that situation 
      did not set the metric parameter.
      
      If the attribute usageFlag for this import policy is set to ignore, then the 
      importMetric value will be ignored by the application. The importMetric 
      value is not used to select which routes to use or ignore but is used to set 
      the metric value for the routes being imported. A value of zero indicates 
      that the metric 
      received in the update will be used."
   DEFVAL     { 0 }
::= { vrIpEgpImportProvEntry 2 }

vrIpEgpImportNbrAsId OBJECT-TYPE
   SYNTAX     Unsigned32 (0..65535)
   ACCESS     read-write
   STATUS     mandatory
   DESCRIPTION
     "The autonomous system Id this import policy will apply to.
      Note: The Valid value of an asId is from 1 to 65,535.
      This attribute's value when set to 0 will be ignored."
::= { vrIpEgpImportProvEntry 3 }


-- Vr/<string> Ip Egp Import/<Decimal> NetworkList/<Decimal>
-- This is an optional subcomponent of Import and identifies a set of 
-- networks that this import policy will apply to.

vrIpEgpImportNet OBJECT IDENTIFIER ::= { vrIpEgpImport 2 }



vrIpEgpImportNetRowStatusTable OBJECT-TYPE
   SYNTAX     SEQUENCE OF VrIpEgpImportNetRowStatusEntry
   ACCESS     not-accessible
   STATUS     mandatory
   DESCRIPTION
     "This entry controls the addition and deletion of 
      vrIpEgpImportNet components."
::= { vrIpEgpImportNet 1 }

vrIpEgpImportNetRowStatusEntry OBJECT-TYPE
   SYNTAX     VrIpEgpImportNetRowStatusEntry
   ACCESS     not-accessible
   STATUS     mandatory
   DESCRIPTION
     "A single entry in the table represents a single 
      vrIpEgpImportNet component."
   INDEX {
      vrIndex,
      vrIpIndex,
      vrIpEgpIndex,
      vrIpEgpImportIndex,
      vrIpEgpImportNetIndex }
::= { vrIpEgpImportNetRowStatusTable 1 }

VrIpEgpImportNetRowStatusEntry ::= SEQUENCE {
   vrIpEgpImportNetRowStatus
      RowStatus,
   vrIpEgpImportNetComponentName
      DisplayString,
   vrIpEgpImportNetStorageType
      StorageType,
   vrIpEgpImportNetIndex
      Integer32 }

vrIpEgpImportNetRowStatus OBJECT-TYPE
   SYNTAX     RowStatus 
   ACCESS     read-write
   STATUS     mandatory
   DESCRIPTION
     "This variable is used as the basis for SNMP naming of
      vrIpEgpImportNet components.
      These components can be added and deleted."
::= { vrIpEgpImportNetRowStatusEntry 1 }

vrIpEgpImportNetComponentName OBJECT-TYPE
   SYNTAX     DisplayString 
   ACCESS     read-only
   STATUS     mandatory
   DESCRIPTION
     "This variable provides the component's string name for
      use with the ASCII Console Interface"
::= { vrIpEgpImportNetRowStatusEntry 2 }

vrIpEgpImportNetStorageType OBJECT-TYPE
   SYNTAX     StorageType 
   ACCESS     read-only
   STATUS     mandatory
   DESCRIPTION
     "This variable represents the storage type value for the
      vrIpEgpImportNet tables."
::= { vrIpEgpImportNetRowStatusEntry 4 }

vrIpEgpImportNetIndex OBJECT-TYPE
   SYNTAX     Integer32 (0..65535)
   ACCESS     not-accessible
   STATUS     mandatory
   DESCRIPTION
     "This variable represents the index for the vrIpEgpImportNet tables."
::= { vrIpEgpImportNetRowStatusEntry 10 }

vrIpEgpImportNetProvTable OBJECT-TYPE
   SYNTAX     SEQUENCE OF VrIpEgpImportNetProvEntry
   ACCESS     not-accessible
   STATUS     mandatory
   DESCRIPTION
     "This group identifies attributes for the NetworkList component for 
      which the import policy will be applied to"
::= { vrIpEgpImportNet 10 }

vrIpEgpImportNetProvEntry OBJECT-TYPE
   SYNTAX     VrIpEgpImportNetProvEntry
   ACCESS     not-accessible
   STATUS     mandatory
   DESCRIPTION
     "An entry in the vrIpEgpImportNetProvTable."
   INDEX {
      vrIndex,
      vrIpIndex,
      vrIpEgpIndex,
      vrIpEgpImportIndex,
      vrIpEgpImportNetIndex }
::= { vrIpEgpImportNetProvTable 1 }

VrIpEgpImportNetProvEntry ::= SEQUENCE {
   vrIpEgpImportNetIpAddress
      IpAddress }

vrIpEgpImportNetIpAddress OBJECT-TYPE
   SYNTAX     IpAddress 
   ACCESS     read-write
   STATUS     mandatory
   DESCRIPTION
     "This attribute identifies the IP address that needs to be matched against 
      in this network list for the Import policy to be applied to."
::= { vrIpEgpImportNetProvEntry 1 }


-- Vr/<string> Ip Egp Export/n
-- Each instance of this component specifies an EGP export policy. An 
-- EGP export policy is used to decide if a route in the IP forwarding table 
-- should be blocked or advertised as EGP routes onto one or all attached 
-- EGP autonomous systems of the virtual router.
-- Passport IP EGP by default advertises all local routes to all attached 
-- EGP autonomous systems using the metric 128.

vrIpEgpExport OBJECT IDENTIFIER ::= { vrIpEgp 4 }



vrIpEgpExportRowStatusTable OBJECT-TYPE
   SYNTAX     SEQUENCE OF VrIpEgpExportRowStatusEntry
   ACCESS     not-accessible
   STATUS     mandatory
   DESCRIPTION
     "This entry controls the addition and deletion of 
      vrIpEgpExport components."
::= { vrIpEgpExport 1 }

vrIpEgpExportRowStatusEntry OBJECT-TYPE
   SYNTAX     VrIpEgpExportRowStatusEntry
   ACCESS     not-accessible
   STATUS     mandatory
   DESCRIPTION
     "A single entry in the table represents a single 
      vrIpEgpExport component."
   INDEX {
      vrIndex,
      vrIpIndex,
      vrIpEgpIndex,
      vrIpEgpExportIndex }
::= { vrIpEgpExportRowStatusTable 1 }

VrIpEgpExportRowStatusEntry ::= SEQUENCE {
   vrIpEgpExportRowStatus
      RowStatus,
   vrIpEgpExportComponentName
      DisplayString,
   vrIpEgpExportStorageType
      StorageType,
   vrIpEgpExportIndex
      Integer32 }

vrIpEgpExportRowStatus OBJECT-TYPE
   SYNTAX     RowStatus 
   ACCESS     read-write
   STATUS     mandatory
   DESCRIPTION
     "This variable is used as the basis for SNMP naming of
      vrIpEgpExport components.
      These components can be added and deleted."
::= { vrIpEgpExportRowStatusEntry 1 }

vrIpEgpExportComponentName OBJECT-TYPE
   SYNTAX     DisplayString 
   ACCESS     read-only
   STATUS     mandatory
   DESCRIPTION
     "This variable provides the component's string name for
      use with the ASCII Console Interface"
::= { vrIpEgpExportRowStatusEntry 2 }

vrIpEgpExportStorageType OBJECT-TYPE
   SYNTAX     StorageType 
   ACCESS     read-only
   STATUS     mandatory
   DESCRIPTION
     "This variable represents the storage type value for the
      vrIpEgpExport tables."
::= { vrIpEgpExportRowStatusEntry 4 }

vrIpEgpExportIndex OBJECT-TYPE
   SYNTAX     Integer32 (0..65535)
   ACCESS     not-accessible
   STATUS     mandatory
   DESCRIPTION
     "This variable represents the index for the vrIpEgpExport tables."
::= { vrIpEgpExportRowStatusEntry 10 }

vrIpEgpExportProvTable OBJECT-TYPE
   SYNTAX     SEQUENCE OF VrIpEgpExportProvEntry
   ACCESS     not-accessible
   STATUS     mandatory
   DESCRIPTION
     "This group contains all the provisioned attributes for the Export 
      component."
::= { vrIpEgpExport 10 }

vrIpEgpExportProvEntry OBJECT-TYPE
   SYNTAX     VrIpEgpExportProvEntry
   ACCESS     not-accessible
   STATUS     mandatory
   DESCRIPTION
     "An entry in the vrIpEgpExportProvTable."
   INDEX {
      vrIndex,
      vrIpIndex,
      vrIpEgpIndex,
      vrIpEgpExportIndex }
::= { vrIpEgpExportProvTable 1 }

VrIpEgpExportProvEntry ::= SEQUENCE {
   vrIpEgpExportAdvertiseStatus
      INTEGER,
   vrIpEgpExportExportMetric
      Unsigned32,
   vrIpEgpExportProtocol
      INTEGER,
   vrIpEgpExportRipInterface
      IpAddress,
   vrIpEgpExportRipNeighbor
      IpAddress,
   vrIpEgpExportInEgpAsId
      Unsigned32,
   vrIpEgpExportOspfTag
      Unsigned32,
   vrIpEgpExportOutAutonomousSystem
      Unsigned32 }

vrIpEgpExportAdvertiseStatus OBJECT-TYPE
   SYNTAX     INTEGER  {
                 send(1),
                 block(2) }
   ACCESS     read-write
   STATUS     mandatory
   DESCRIPTION
     "This attribute specifies if the routes that match this export policy are 
      advertised (send) or not advertised (block)."
   DEFVAL     { send }
::= { vrIpEgpExportProvEntry 1 }

vrIpEgpExportExportMetric OBJECT-TYPE
   SYNTAX     Unsigned32 (0..255)
   ACCESS     read-write
   STATUS     mandatory
   DESCRIPTION
     "This attribute specifies the metric to be used on the routes being 
      exported as a result of matching this export policy.
      If the attribute advertiseStatus is set to block, then the value of 
      exportMetric is ignored. The exportMetric value is not used to select 
      which routes to block or send, but rather the metric value advertised for 
      the routes.
      A value of 0 indicates that the metric associated with the route in the 
      forwarding table is used."
   DEFVAL     { 0 }
::= { vrIpEgpExportProvEntry 2 }

vrIpEgpExportProtocol OBJECT-TYPE
   SYNTAX     INTEGER  {
                 all(1),
                 egp(2),
                 rip(3),
                 ospfInternal(4),
                 ospfExternal(5),
                 staticLocal(6),
                 staticRemote(7) }
   ACCESS     read-write
   STATUS     mandatory
   DESCRIPTION
     "This attribute specifies the routes to which this export policy applies 
      based on the routing protocol of how the routes are learned. If it is set to 
      all, this export policy applies to all routes in the forwarding table."
   DEFVAL     { all }
::= { vrIpEgpExportProvEntry 3 }

vrIpEgpExportRipInterface OBJECT-TYPE
   SYNTAX     IpAddress 
   ACCESS     read-write
   STATUS     mandatory
   DESCRIPTION
     "This attribute specifies the RIP learned routes to which this export policy 
      applies, based on the RIP interface from which the routes are learned.
      This attribute can only be non zero when the protocol is set to rip. The 
      value of 0.0.0.0 implies any RIP interface on the same virtual router; 
      otherwise the value of this attribute must match the interface address of 
      a LogicalIf that has a RipIf on the same virtual router."
   DEFVAL     { '00000000'H }  -- "0.0.0.0"
::= { vrIpEgpExportProvEntry 4 }

vrIpEgpExportRipNeighbor OBJECT-TYPE
   SYNTAX     IpAddress 
   ACCESS     read-write
   STATUS     mandatory
   DESCRIPTION
     "This attribute specifies the RIP learned routes to which this export policy 
      applies, based on the RIP neighbor of which the routes are learned from.
      This attribute can only be non zero when the protocol is set to rip. The 
      value of 0.0.0.0 implies any RIP neighbor."
   DEFVAL     { '00000000'H }  -- "0.0.0.0"
::= { vrIpEgpExportProvEntry 5 }

vrIpEgpExportInEgpAsId OBJECT-TYPE
   SYNTAX     Unsigned32 (0..65535)
   ACCESS     read-write
   STATUS     mandatory
   DESCRIPTION
     "This attribute specifies the EGP learned routes to which this export 
      policy applies, based on the EGP autonomous system identifier of which 
      the routes are learned from.
      This attribute can only be non zero when protocol is set to egp. The 
      value of 0 implies any EGP autonomous system; otherwise the value of 
      this attribute must match the asId of an EGP neighbor on the same 
      virtual router."
   DEFVAL     { 0 }
::= { vrIpEgpExportProvEntry 6 }

vrIpEgpExportOspfTag OBJECT-TYPE
   SYNTAX     Unsigned32 (0..4294967295)
   ACCESS     read-write
   STATUS     mandatory
   DESCRIPTION
     "This attribute specifies the OSPF learned external routes to which this 
      export policy applies, based on the learned OSPF tag of the routes.
      This attribute can only be set to a non default value when protocol is set 
      to ospfExternal. The value of 4294967295 implies any tag."
   DEFVAL     { 4294967295 }
::= { vrIpEgpExportProvEntry 7 }

vrIpEgpExportOutAutonomousSystem OBJECT-TYPE
   SYNTAX     Unsigned32 (0..65535)
   ACCESS     read-write
   STATUS     mandatory
   DESCRIPTION
     "This attribute specifies the EGP autonomous system to which routes are 
      exported to as a result of matching this export policy.
      If the attribute advertiseStatus is set to block, then the value of 
      outAutonomousSystem is ignored. The outAutonomousSystem value is 
      not used to select which routes to block or send but where to export the 
      routes.
      A value of 0 indicates that the routes are exported to all EGP 
      autonomous systems of which the virtual router is a neighbor. 
      Otherwise, the value of this attribute must match the asId of an EGP 
      neighbor on the same virtual router."
   DEFVAL     { 0 }
::= { vrIpEgpExportProvEntry 8 }


-- Vr/<string> Ip Egp Export/<Decimal> NetworkList/<Decimal>
-- This component identifies a set of attributes when matched determines 
-- the export policy applied. 

vrIpEgpExportNet OBJECT IDENTIFIER ::= { vrIpEgpExport 2 }



vrIpEgpExportNetRowStatusTable OBJECT-TYPE
   SYNTAX     SEQUENCE OF VrIpEgpExportNetRowStatusEntry
   ACCESS     not-accessible
   STATUS     mandatory
   DESCRIPTION
     "This entry controls the addition and deletion of 
      vrIpEgpExportNet components."
::= { vrIpEgpExportNet 1 }

vrIpEgpExportNetRowStatusEntry OBJECT-TYPE
   SYNTAX     VrIpEgpExportNetRowStatusEntry
   ACCESS     not-accessible
   STATUS     mandatory
   DESCRIPTION
     "A single entry in the table represents a single 
      vrIpEgpExportNet component."
   INDEX {
      vrIndex,
      vrIpIndex,
      vrIpEgpIndex,
      vrIpEgpExportIndex,
      vrIpEgpExportNetIndex }
::= { vrIpEgpExportNetRowStatusTable 1 }

VrIpEgpExportNetRowStatusEntry ::= SEQUENCE {
   vrIpEgpExportNetRowStatus
      RowStatus,
   vrIpEgpExportNetComponentName
      DisplayString,
   vrIpEgpExportNetStorageType
      StorageType,
   vrIpEgpExportNetIndex
      Integer32 }

vrIpEgpExportNetRowStatus OBJECT-TYPE
   SYNTAX     RowStatus 
   ACCESS     read-write
   STATUS     mandatory
   DESCRIPTION
     "This variable is used as the basis for SNMP naming of
      vrIpEgpExportNet components.
      These components can be added and deleted."
::= { vrIpEgpExportNetRowStatusEntry 1 }

vrIpEgpExportNetComponentName OBJECT-TYPE
   SYNTAX     DisplayString 
   ACCESS     read-only
   STATUS     mandatory
   DESCRIPTION
     "This variable provides the component's string name for
      use with the ASCII Console Interface"
::= { vrIpEgpExportNetRowStatusEntry 2 }

vrIpEgpExportNetStorageType OBJECT-TYPE
   SYNTAX     StorageType 
   ACCESS     read-only
   STATUS     mandatory
   DESCRIPTION
     "This variable represents the storage type value for the
      vrIpEgpExportNet tables."
::= { vrIpEgpExportNetRowStatusEntry 4 }

vrIpEgpExportNetIndex OBJECT-TYPE
   SYNTAX     Integer32 (0..65535)
   ACCESS     not-accessible
   STATUS     mandatory
   DESCRIPTION
     "This variable represents the index for the vrIpEgpExportNet tables."
::= { vrIpEgpExportNetRowStatusEntry 10 }

vrIpEgpExportNetProvTable OBJECT-TYPE
   SYNTAX     SEQUENCE OF VrIpEgpExportNetProvEntry
   ACCESS     not-accessible
   STATUS     mandatory
   DESCRIPTION
     "This group identifies the set of provisionable attributes for the 
      ExportNetworkList component."
::= { vrIpEgpExportNet 10 }

vrIpEgpExportNetProvEntry OBJECT-TYPE
   SYNTAX     VrIpEgpExportNetProvEntry
   ACCESS     not-accessible
   STATUS     mandatory
   DESCRIPTION
     "An entry in the vrIpEgpExportNetProvTable."
   INDEX {
      vrIndex,
      vrIpIndex,
      vrIpEgpIndex,
      vrIpEgpExportIndex,
      vrIpEgpExportNetIndex }
::= { vrIpEgpExportNetProvTable 1 }

VrIpEgpExportNetProvEntry ::= SEQUENCE {
   vrIpEgpExportNetIpAddress
      IpAddress }

vrIpEgpExportNetIpAddress OBJECT-TYPE
   SYNTAX     IpAddress 
   ACCESS     read-write
   STATUS     mandatory
   DESCRIPTION
     "This attribute identifies the 32 bit IP address to match against."
::= { vrIpEgpExportNetProvEntry 1 }


-- This component is configured to control the Open Shortest Path First IP 
-- routing protocol.

vrIpOspf OBJECT IDENTIFIER ::= { vrIp 7 }



vrIpOspfRowStatusTable OBJECT-TYPE
   SYNTAX     SEQUENCE OF VrIpOspfRowStatusEntry
   ACCESS     not-accessible
   STATUS     mandatory
   DESCRIPTION
     "This entry controls the addition and deletion of 
      vrIpOspf components."
::= { vrIpOspf 1 }

vrIpOspfRowStatusEntry OBJECT-TYPE
   SYNTAX     VrIpOspfRowStatusEntry
   ACCESS     not-accessible
   STATUS     mandatory
   DESCRIPTION
     "A single entry in the table represents a single 
      vrIpOspf component."
   INDEX {
      vrIndex,
      vrIpIndex,
      vrIpOspfIndex }
::= { vrIpOspfRowStatusTable 1 }

VrIpOspfRowStatusEntry ::= SEQUENCE {
   vrIpOspfRowStatus
      RowStatus,
   vrIpOspfComponentName
      DisplayString,
   vrIpOspfStorageType
      StorageType,
   vrIpOspfIndex
      NonReplicated }

vrIpOspfRowStatus OBJECT-TYPE
   SYNTAX     RowStatus 
   ACCESS     read-write
   STATUS     mandatory
   DESCRIPTION
     "This variable is used as the basis for SNMP naming of
      vrIpOspf components.
      These components can be added and deleted."
::= { vrIpOspfRowStatusEntry 1 }

vrIpOspfComponentName OBJECT-TYPE
   SYNTAX     DisplayString 
   ACCESS     read-only
   STATUS     mandatory
   DESCRIPTION
     "This variable provides the component's string name for
      use with the ASCII Console Interface"
::= { vrIpOspfRowStatusEntry 2 }

vrIpOspfStorageType OBJECT-TYPE
   SYNTAX     StorageType 
   ACCESS     read-only
   STATUS     mandatory
   DESCRIPTION
     "This variable represents the storage type value for the
      vrIpOspf tables."
::= { vrIpOspfRowStatusEntry 4 }

vrIpOspfIndex OBJECT-TYPE
   SYNTAX     NonReplicated 
   ACCESS     not-accessible
   STATUS     mandatory
   DESCRIPTION
     "This variable represents the index for the vrIpOspf tables."
::= { vrIpOspfRowStatusEntry 10 }

vrIpOspfProvTable OBJECT-TYPE
   SYNTAX     SEQUENCE OF VrIpOspfProvEntry
   ACCESS     not-accessible
   STATUS     mandatory
   DESCRIPTION
     "This group of attributes are used to configure the OSPF component."
::= { vrIpOspf 100 }

vrIpOspfProvEntry OBJECT-TYPE
   SYNTAX     VrIpOspfProvEntry
   ACCESS     not-accessible
   STATUS     mandatory
   DESCRIPTION
     "An entry in the vrIpOspfProvTable."
   INDEX {
      vrIndex,
      vrIpIndex,
      vrIpOspfIndex }
::= { vrIpOspfProvTable 1 }

VrIpOspfProvEntry ::= SEQUENCE {
   vrIpOspfRouterId
      RouterID,
   vrIpOspfSnmpAdminStatus
      INTEGER,
   vrIpOspfAsBdrRtrStatus
      INTEGER,
   vrIpOspfTosSupport
      INTEGER,
   vrIpOspfExtLsdbLimit
      INTEGER,
   vrIpOspfMulticastForward
      Unsigned32,
   vrIpOspfMigrateRip
      INTEGER,
   vrIpOspfGenerateDefaultRouteMetric
      INTEGER }

vrIpOspfRouterId OBJECT-TYPE
   SYNTAX     RouterID 
   ACCESS     read-write
   STATUS     mandatory
   DESCRIPTION
     "This attribute is an Ip Address that uniquely identifies the router in the 
      autonomous system."
::= { vrIpOspfProvEntry 1 }

vrIpOspfSnmpAdminStatus OBJECT-TYPE
   SYNTAX     INTEGER  {
                 up(1),
                 down(2),
                 testing(3) }
   ACCESS     read-write
   STATUS     mandatory
   DESCRIPTION
     "The administrative status of the OSPF Component in this Virtual Router."
   DEFVAL     { up }
::= { vrIpOspfProvEntry 2 }

vrIpOspfAsBdrRtrStatus OBJECT-TYPE
   SYNTAX     INTEGER  {
                 true(1),
                 false(2) }
   ACCESS     read-write
   STATUS     mandatory
   DESCRIPTION
     "This attribute is a flag to note whether this router is an autonomous 
      system border router. If this router is configured to export any routes 
      learned from other than OSPF-internal protocol, this attribute should be 
      configured as autonomous system border router."
   DEFVAL     { false }
::= { vrIpOspfProvEntry 3 }

vrIpOspfTosSupport OBJECT-TYPE
   SYNTAX     INTEGER  {
                 false(2) }
   ACCESS     read-write
   STATUS     mandatory
   DESCRIPTION
     "The router's support for type-of-service routing. Only one value will be 
      allowed. This is a deviation from supporting the MIB."
   DEFVAL     { false }
::= { vrIpOspfProvEntry 4 }

vrIpOspfExtLsdbLimit OBJECT-TYPE
   SYNTAX     INTEGER (-1..2147483647)
   ACCESS     read-write
   STATUS     mandatory
   DESCRIPTION
     "The maximum number of external link-state entries that can be stored in 
      the link-state database. If the value is -1, then there is no limit,
      that is the maximum number of external OSPF routes that this 
      autonomous system border router will originate. 
      It will begin to flush LSA(Link State Advertisement)s, if an ASBR 
      might receive bursts of external routes (for example, a regional 
      network), then the parameter should be configured to a reasonable level. 
      If there are less than two thousand routes and large bursts are unlikely, 
      then the default should be adequate. This parameter will not affect the 
      number of external OSPF routes a router will store in it's database."
   DEFVAL     { -1 }
::= { vrIpOspfProvEntry 5 }

vrIpOspfMulticastForward OBJECT-TYPE
   SYNTAX     Unsigned32 (0..0)
   ACCESS     read-write
   STATUS     mandatory
   DESCRIPTION
     "A bit mask indicating the limits on Network Layer Multicast(class D) 
      forwarding. It is represented as a sum of the following:
      if intra-Area forwarding is permitted, 1; else 0
      if inter-Area forwarding is permitted 2; else 0
      if inter-AS forwarding is permitted, 4; else 0
      Only the value of 0 is being supported and this is a MIB deviation."
   DEFVAL     { 0 }
::= { vrIpOspfProvEntry 6 }

vrIpOspfMigrateRip OBJECT-TYPE
   SYNTAX     INTEGER  {
                 enabled(1),
                 disabled(2) }
   ACCESS     read-write
   STATUS     mandatory
   DESCRIPTION
     "This Attribute sets the preference level of OSPF-internal routes to be 
      less preferred than RIP. 
      This Parameter should only be used when starting migration of network 
      from RIP to OSPF. When ready to cutover to OSPF, set this attribute 
      disabled and run under normal preferences. All OSPF routers in the 
      Autonomous System should be running with migraterip enabled or with 
      migraterip disabled to prevent routing loops. It is important that the 
      changeover period from RIP to OSPF be performed quickly on all OSPF 
      routers so that no routing loops are formed. These routing loops could 
      be caused by conflicts in the internal RIP and OSPF databases."
   DEFVAL     { disabled }
::= { vrIpOspfProvEntry 7 }

vrIpOspfGenerateDefaultRouteMetric OBJECT-TYPE
   SYNTAX     INTEGER (-1..65535)
   ACCESS     read-write
   STATUS     mandatory
   DESCRIPTION
     "If this router is configured as an autonomous system border router, then 
      this attribute causes the default route to be generated with a metric value 
      equal to generateDefaultRouteMetric value. This route is put in the 
      OSPF update along with the normal update routes when updates are sent 
      to the neighbors. No default route will be generated if the value is 0."
   DEFVAL     { 0 }
::= { vrIpOspfProvEntry 8 }

vrIpOspfOperTable OBJECT-TYPE
   SYNTAX     SEQUENCE OF VrIpOspfOperEntry
   ACCESS     not-accessible
   STATUS     mandatory
   DESCRIPTION
     "These group of attributes identifies the operational attributes for this 
      OSPF Component."
::= { vrIpOspf 101 }

vrIpOspfOperEntry OBJECT-TYPE
   SYNTAX     VrIpOspfOperEntry
   ACCESS     not-accessible
   STATUS     mandatory
   DESCRIPTION
     "An entry in the vrIpOspfOperTable."
   INDEX {
      vrIndex,
      vrIpIndex,
      vrIpOspfIndex }
::= { vrIpOspfOperTable 1 }

VrIpOspfOperEntry ::= SEQUENCE {
   vrIpOspfVersionNumber
      Unsigned32,
   vrIpOspfAreaBdrRtrStatus
      INTEGER,
   vrIpOspfExternLsaCount
      Gauge32,
   vrIpOspfExternLsaChecksumSum
      Unsigned32,
   vrIpOspfOriginateNewLsas
      Counter32,
   vrIpOspfRxNewLsas
      Counter32 }

vrIpOspfVersionNumber OBJECT-TYPE
   SYNTAX     Unsigned32 (2..2)
   ACCESS     read-only
   STATUS     mandatory
   DESCRIPTION
     "The Current Version number of the OSPF Protocol. (2)."
   DEFVAL     { 2 }
::= { vrIpOspfOperEntry 1 }

vrIpOspfAreaBdrRtrStatus OBJECT-TYPE
   SYNTAX     INTEGER  {
                 true(1),
                 false(2) }
   ACCESS     read-only
   STATUS     mandatory
   DESCRIPTION
     "This attribute is used to specify whether this router is configured as an 
      area border router."
::= { vrIpOspfOperEntry 2 }

vrIpOspfExternLsaCount OBJECT-TYPE
   SYNTAX     Gauge32 (0..4294967295)
   ACCESS     read-only
   STATUS     mandatory
   DESCRIPTION
     "The number of external (LS type 5) link-state advertisements in the link-
      state database."
   DEFVAL     { 0 }
::= { vrIpOspfOperEntry 3 }

vrIpOspfExternLsaChecksumSum OBJECT-TYPE
   SYNTAX     Unsigned32 (0..4294967295)
   ACCESS     read-only
   STATUS     mandatory
   DESCRIPTION
     "The 32-bit unsigned sum of the LS checksums of the external link-state 
      database. This sum can be used to determine if there has been a change 
      in a router's link state database, and to compare the link-state database 
      of two routers."
::= { vrIpOspfOperEntry 4 }

vrIpOspfOriginateNewLsas OBJECT-TYPE
   SYNTAX     Counter32 
   ACCESS     read-only
   STATUS     mandatory
   DESCRIPTION
     "The number of new link-state advertisements that have been originated. 
      This number is incremented each time the router originates a new LSA."
::= { vrIpOspfOperEntry 5 }

vrIpOspfRxNewLsas OBJECT-TYPE
   SYNTAX     Counter32 
   ACCESS     read-only
   STATUS     mandatory
   DESCRIPTION
     "The number of link-state advertisements received determined to be new 
      instantiations. This number does not include newer instantiations of self-
      originated link-state advertisements."
::= { vrIpOspfOperEntry 6 }

vrIpOspfStateTable OBJECT-TYPE
   SYNTAX     SEQUENCE OF VrIpOspfStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { vrIpOspf 102 }

vrIpOspfStateEntry OBJECT-TYPE
   SYNTAX     VrIpOspfStateEntry
   ACCESS     not-accessible
   STATUS     mandatory
   DESCRIPTION
     "An entry in the vrIpOspfStateTable."
   INDEX {
      vrIndex,
      vrIpIndex,
      vrIpOspfIndex }
::= { vrIpOspfStateTable 1 }

VrIpOspfStateEntry ::= SEQUENCE {
   vrIpOspfAdminState
      INTEGER,
   vrIpOspfOperationalState
      INTEGER,
   vrIpOspfUsageState
      INTEGER }

vrIpOspfAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { vrIpOspfStateEntry 1 }

vrIpOspfOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { vrIpOspfStateEntry 2 }

vrIpOspfUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { vrIpOspfStateEntry 3 }

vrIpOspfOperStatusTable OBJECT-TYPE
   SYNTAX     SEQUENCE OF VrIpOspfOperStatusEntry
   ACCESS     not-accessible
   STATUS     mandatory
   DESCRIPTION
     "This group includes the Operational Status attribute. This attribute 
      defines the current operational state of this component."
::= { vrIpOspf 105 }

vrIpOspfOperStatusEntry OBJECT-TYPE
   SYNTAX     VrIpOspfOperStatusEntry
   ACCESS     not-accessible
   STATUS     mandatory
   DESCRIPTION
     "An entry in the vrIpOspfOperStatusTable."
   INDEX {
      vrIndex,
      vrIpIndex,
      vrIpOspfIndex }
::= { vrIpOspfOperStatusTable 1 }

VrIpOspfOperStatusEntry ::= SEQUENCE {
   vrIpOspfSnmpOperStatus
      INTEGER }

vrIpOspfSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { vrIpOspfOperStatusEntry 1 }


-- Vr/<string> Ip Ospf AreaEntry/<Ip Address>
-- This component contains the information about various areas that the 
-- router is connected to.

vrIpOspfArea OBJECT IDENTIFIER ::= { vrIpOspf 2 }



vrIpOspfAreaRowStatusTable OBJECT-TYPE
   SYNTAX     SEQUENCE OF VrIpOspfAreaRowStatusEntry
   ACCESS     not-accessible
   STATUS     mandatory
   DESCRIPTION
     "This entry controls the addition and deletion of 
      vrIpOspfArea components."
::= { vrIpOspfArea 1 }

vrIpOspfAreaRowStatusEntry OBJECT-TYPE
   SYNTAX     VrIpOspfAreaRowStatusEntry
   ACCESS     not-accessible
   STATUS     mandatory
   DESCRIPTION
     "A single entry in the table represents a single 
      vrIpOspfArea component."
   INDEX {
      vrIndex,
      vrIpIndex,
      vrIpOspfIndex,
      vrIpOspfAreaAreaIdIndex }
::= { vrIpOspfAreaRowStatusTable 1 }

VrIpOspfAreaRowStatusEntry ::= SEQUENCE {
   vrIpOspfAreaRowStatus
      RowStatus,
   vrIpOspfAreaComponentName
      DisplayString,
   vrIpOspfAreaStorageType
      StorageType,
   vrIpOspfAreaAreaIdIndex
      IpAddress }

vrIpOspfAreaRowStatus OBJECT-TYPE
   SYNTAX     RowStatus 
   ACCESS     read-write
   STATUS     mandatory
   DESCRIPTION
     "This variable is used as the basis for SNMP naming of
      vrIpOspfArea components.
      These components can be added and deleted."
::= { vrIpOspfAreaRowStatusEntry 1 }

vrIpOspfAreaComponentName OBJECT-TYPE
   SYNTAX     DisplayString 
   ACCESS     read-only
   STATUS     mandatory
   DESCRIPTION
     "This variable provides the component's string name for
      use with the ASCII Console Interface"
::= { vrIpOspfAreaRowStatusEntry 2 }

vrIpOspfAreaStorageType OBJECT-TYPE
   SYNTAX     StorageType 
   ACCESS     read-only
   STATUS     mandatory
   DESCRIPTION
     "This variable represents the storage type value for the
      vrIpOspfArea tables."
::= { vrIpOspfAreaRowStatusEntry 4 }

vrIpOspfAreaAreaIdIndex OBJECT-TYPE
   SYNTAX     IpAddress 
   ACCESS     not-accessible
   STATUS     mandatory
   DESCRIPTION
     "This variable represents the index for the vrIpOspfArea tables."
::= { vrIpOspfAreaRowStatusEntry 10 }

vrIpOspfAreaProvTable OBJECT-TYPE
   SYNTAX     SEQUENCE OF VrIpOspfAreaProvEntry
   ACCESS     not-accessible
   STATUS     mandatory
   DESCRIPTION
     "This group describes the set of provisionable attributes for the 
      AreaEntry Component."
::= { vrIpOspfArea 10 }

vrIpOspfAreaProvEntry OBJECT-TYPE
   SYNTAX     VrIpOspfAreaProvEntry
   ACCESS     not-accessible
   STATUS     mandatory
   DESCRIPTION
     "An entry in the vrIpOspfAreaProvTable."
   INDEX {
      vrIndex,
      vrIpIndex,
      vrIpOspfIndex,
      vrIpOspfAreaAreaIdIndex }
::= { vrIpOspfAreaProvTable 1 }

VrIpOspfAreaProvEntry ::= SEQUENCE {
   vrIpOspfAreaAuthType
      INTEGER,
   vrIpOspfAreaImportAsExtern
      INTEGER,
   vrIpOspfAreaAreaSummary
      INTEGER }

vrIpOspfAreaAuthType OBJECT-TYPE
   SYNTAX     INTEGER  {
                 none(0),
                 simplePassword(1) }
   ACCESS     read-write
   STATUS     mandatory
   DESCRIPTION
     "The authentication type specified for this area."
   DEFVAL     { none }
::= { vrIpOspfAreaProvEntry 1 }

vrIpOspfAreaImportAsExtern OBJECT-TYPE
   SYNTAX     INTEGER  {
                 importExternal(1),
                 importNoExternal(2),
                 importNssa(3) }
   ACCESS     read-write
   STATUS     mandatory
   DESCRIPTION
     "The area's support for importing AS external link-state advertisements. 
      For backbone area (that is, areaId 0.0.0.0), this attribute must be set to 
      importExternal."
   DEFVAL     { importExternal }
::= { vrIpOspfAreaProvEntry 2 }

vrIpOspfAreaAreaSummary OBJECT-TYPE
   SYNTAX     INTEGER  {
                 noAreaSummary(1),
                 sendAreaSummary(2) }
   ACCESS     read-write
   STATUS     mandatory
   DESCRIPTION
     "This variable controls the import of summary LSAs into stub areas. If it 
      is noAreaSummary, the router will neither originate nor propagate 
      summary LSAs into the stub areas. It will rely entirely on its default 
      route. If it is sendAreaSummary, the router will both summarize and 
      propagate summary LSAs."
   DEFVAL     { noAreaSummary }
::= { vrIpOspfAreaProvEntry 3 }

vrIpOspfAreaOperTable OBJECT-TYPE
   SYNTAX     SEQUENCE OF VrIpOspfAreaOperEntry
   ACCESS     not-accessible
   STATUS     mandatory
   DESCRIPTION
     "This group of attributes describes the Operational set of attributes for the 
      AreaEntry component."
::= { vrIpOspfArea 11 }

vrIpOspfAreaOperEntry OBJECT-TYPE
   SYNTAX     VrIpOspfAreaOperEntry
   ACCESS     not-accessible
   STATUS     mandatory
   DESCRIPTION
     "An entry in the vrIpOspfAreaOperTable."
   INDEX {
      vrIndex,
      vrIpIndex,
      vrIpOspfIndex,
      vrIpOspfAreaAreaIdIndex }
::= { vrIpOspfAreaOperTable 1 }

VrIpOspfAreaOperEntry ::= SEQUENCE {
   vrIpOspfAreaSpfRuns
      Counter32,
   vrIpOspfAreaAreaBdrRtrCount
      Gauge32,
   vrIpOspfAreaAsBdrRtrCount
      Gauge32,
   vrIpOspfAreaLsaCount
      Gauge32,
   vrIpOspfAreaAreaLsaCksumSum
      Unsigned32 }

vrIpOspfAreaSpfRuns OBJECT-TYPE
   SYNTAX     Counter32 
   ACCESS     read-only
   STATUS     mandatory
   DESCRIPTION
     "The number of times that the intra-area route table has been calculated 
      using this area's link-state database since the protocol became 
      operational."
::= { vrIpOspfAreaOperEntry 1 }

vrIpOspfAreaAreaBdrRtrCount OBJECT-TYPE
   SYNTAX     Gauge32 (0..4294967295)
   ACCESS     read-only
   STATUS     mandatory
   DESCRIPTION
     "The total number of area border routers reachable within this area. This 
      is initially zero, and is calculated in each Shortest Path First Pass."
::= { vrIpOspfAreaOperEntry 2 }

vrIpOspfAreaAsBdrRtrCount OBJECT-TYPE
   SYNTAX     Gauge32 (0..4294967295)
   ACCESS     read-only
   STATUS     mandatory
   DESCRIPTION
     "The total number of Autonomous System border routers reachable 
      within this area. This is initially zero, and is calculated in each Shortest 
      Path First Pass."
::= { vrIpOspfAreaOperEntry 3 }

vrIpOspfAreaLsaCount OBJECT-TYPE
   SYNTAX     Gauge32 (0..4294967295)
   ACCESS     read-only
   STATUS     mandatory
   DESCRIPTION
     "The total number of link-state advertisements in this area's link-state 
      database, excluding AS External LSA's."
::= { vrIpOspfAreaOperEntry 4 }

vrIpOspfAreaAreaLsaCksumSum OBJECT-TYPE
   SYNTAX     Unsigned32 (0..4294967295)
   ACCESS     read-only
   STATUS     mandatory
   DESCRIPTION
     "The 32-bit unsigned sum of the link-state advertisement's LS checksums 
      contained in this area's link-state database. This sum excludes external 
      (LS type 5) link-state advertisements. The sum can be used to determine 
      if there has been a change in a router's link state database, and to 
      compare the link-state database of two routers."
::= { vrIpOspfAreaOperEntry 5 }


-- Vr/<string> Ip Ospf StubAreaEntry/<Ip Address>,<Decimal>
-- This component describes metrics that a default area border router will 
-- advertise into a stub area. 

vrIpOspfStub OBJECT IDENTIFIER ::= { vrIpOspf 3 }



vrIpOspfStubRowStatusTable OBJECT-TYPE
   SYNTAX     SEQUENCE OF VrIpOspfStubRowStatusEntry
   ACCESS     not-accessible
   STATUS     mandatory
   DESCRIPTION
     "This entry controls the addition and deletion of 
      vrIpOspfStub components."
::= { vrIpOspfStub 1 }

vrIpOspfStubRowStatusEntry OBJECT-TYPE
   SYNTAX     VrIpOspfStubRowStatusEntry
   ACCESS     not-accessible
   STATUS     mandatory
   DESCRIPTION
     "A single entry in the table represents a single 
      vrIpOspfStub component."
   INDEX {
      vrIndex,
      vrIpIndex,
      vrIpOspfIndex,
      vrIpOspfStubAreaIdIndex,
      vrIpOspfStubTosIndex }
::= { vrIpOspfStubRowStatusTable 1 }

VrIpOspfStubRowStatusEntry ::= SEQUENCE {
   vrIpOspfStubRowStatus
      RowStatus,
   vrIpOspfStubComponentName
      DisplayString,
   vrIpOspfStubStorageType
      StorageType,
   vrIpOspfStubAreaIdIndex
      IpAddress,
   vrIpOspfStubTosIndex
      Integer32 }

vrIpOspfStubRowStatus OBJECT-TYPE
   SYNTAX     RowStatus 
   ACCESS     read-write
   STATUS     mandatory
   DESCRIPTION
     "This variable is used as the basis for SNMP naming of
      vrIpOspfStub components.
      These components can be added and deleted."
::= { vrIpOspfStubRowStatusEntry 1 }

vrIpOspfStubComponentName OBJECT-TYPE
   SYNTAX     DisplayString 
   ACCESS     read-only
   STATUS     mandatory
   DESCRIPTION
     "This variable provides the component's string name for
      use with the ASCII Console Interface"
::= { vrIpOspfStubRowStatusEntry 2 }

vrIpOspfStubStorageType OBJECT-TYPE
   SYNTAX     StorageType 
   ACCESS     read-only
   STATUS     mandatory
   DESCRIPTION
     "This variable represents the storage type value for the
      vrIpOspfStub tables."
::= { vrIpOspfStubRowStatusEntry 4 }

vrIpOspfStubAreaIdIndex OBJECT-TYPE
   SYNTAX     IpAddress 
   ACCESS     not-accessible
   STATUS     mandatory
   DESCRIPTION
     "This variable represents an index for the vrIpOspfStub tables."
::= { vrIpOspfStubRowStatusEntry 10 }

vrIpOspfStubTosIndex OBJECT-TYPE
   SYNTAX     Integer32 (0..0)
   ACCESS     not-accessible
   STATUS     mandatory
   DESCRIPTION
     "This variable represents an index for the vrIpOspfStub tables."
::= { vrIpOspfStubRowStatusEntry 11 }

vrIpOspfStubProvTable OBJECT-TYPE
   SYNTAX     SEQUENCE OF VrIpOspfStubProvEntry
   ACCESS     not-accessible
   STATUS     mandatory
   DESCRIPTION
     "These set of attributes explain the provisionable group for the 
      StubAreaEntry."
::= { vrIpOspfStub 10 }

vrIpOspfStubProvEntry OBJECT-TYPE
   SYNTAX     VrIpOspfStubProvEntry
   ACCESS     not-accessible
   STATUS     mandatory
   DESCRIPTION
     "An entry in the vrIpOspfStubProvTable."
   INDEX {
      vrIndex,
      vrIpIndex,
      vrIpOspfIndex,
      vrIpOspfStubAreaIdIndex,
      vrIpOspfStubTosIndex }
::= { vrIpOspfStubProvTable 1 }

VrIpOspfStubProvEntry ::= SEQUENCE {
   vrIpOspfStubMetric
      Unsigned32,
   vrIpOspfStubMetricType
      INTEGER,
   vrIpOspfStubAdvertiseDefault
      INTEGER }

vrIpOspfStubMetric OBJECT-TYPE
   SYNTAX     Unsigned32 (1..4294967295)
   ACCESS     read-write
   STATUS     mandatory
   DESCRIPTION
     "The metric value applied at the indicated type of service."
   DEFVAL     { 1 }
::= { vrIpOspfStubProvEntry 1 }

vrIpOspfStubMetricType OBJECT-TYPE
   SYNTAX     INTEGER  {
                 ospfMetric(1),
                 comparableCost(2),
                 nonComparable(3) }
   ACCESS     read-write
   STATUS     mandatory
   DESCRIPTION
     "This type of the metric advertised as a default route."
   DEFVAL     { ospfMetric }
::= { vrIpOspfStubProvEntry 2 }

vrIpOspfStubAdvertiseDefault OBJECT-TYPE
   SYNTAX     INTEGER  {
                 yes(1),
                 no(2) }
   ACCESS     read-write
   STATUS     mandatory
   DESCRIPTION
     "This attribute determines whether or not the default routing information 
      will be advertised, depending on other criterion. Setting this value to no 
      can prevent advertising default routing information.
      
      If the value of the attribute is set to yes, then the value of the attribute 
      importAsExtern for that particular AreaEntry should be set to 
      importNssa."
   DEFVAL     { yes }
::= { vrIpOspfStubProvEntry 3 }


-- Vr/<string> Ip Ospf AreaRangeEntry/<Ip Address>,<enum>,
-- <Ip Address>,<Ip Address>
-- This table entry replaces the Area Summary table from RFC1253 and is 
-- used as an extension for CIDR support.

vrIpOspfAggregate OBJECT IDENTIFIER ::= { vrIpOspf 5 }



vrIpOspfAggregateRowStatusTable OBJECT-TYPE
   SYNTAX     SEQUENCE OF VrIpOspfAggregateRowStatusEntry
   ACCESS     not-accessible
   STATUS     mandatory
   DESCRIPTION
     "This entry controls the addition and deletion of 
      vrIpOspfAggregate components."
::= { vrIpOspfAggregate 1 }

vrIpOspfAggregateRowStatusEntry OBJECT-TYPE
   SYNTAX     VrIpOspfAggregateRowStatusEntry
   ACCESS     not-accessible
   STATUS     mandatory
   DESCRIPTION
     "A single entry in the table represents a single 
      vrIpOspfAggregate component."
   INDEX {
      vrIndex,
      vrIpIndex,
      vrIpOspfIndex,
      vrIpOspfAggregateAreaIdIndex,
      vrIpOspfAggregateLsdbTypeIndex,
      vrIpOspfAggregateAggregateNetIndex,
      vrIpOspfAggregateAggregateMaskIndex }
::= { vrIpOspfAggregateRowStatusTable 1 }

VrIpOspfAggregateRowStatusEntry ::= SEQUENCE {
   vrIpOspfAggregateRowStatus
      RowStatus,
   vrIpOspfAggregateComponentName
      DisplayString,
   vrIpOspfAggregateStorageType
      StorageType,
   vrIpOspfAggregateAreaIdIndex
      IpAddress,
   vrIpOspfAggregateLsdbTypeIndex
      INTEGER,
   vrIpOspfAggregateAggregateNetIndex
      IpAddress,
   vrIpOspfAggregateAggregateMaskIndex
      IpAddress }

vrIpOspfAggregateRowStatus OBJECT-TYPE
   SYNTAX     RowStatus 
   ACCESS     read-write
   STATUS     mandatory
   DESCRIPTION
     "This variable is used as the basis for SNMP naming of
      vrIpOspfAggregate components.
      These components can be added and deleted."
::= { vrIpOspfAggregateRowStatusEntry 1 }

vrIpOspfAggregateComponentName OBJECT-TYPE
   SYNTAX     DisplayString 
   ACCESS     read-only
   STATUS     mandatory
   DESCRIPTION
     "This variable provides the component's string name for
      use with the ASCII Console Interface"
::= { vrIpOspfAggregateRowStatusEntry 2 }

vrIpOspfAggregateStorageType OBJECT-TYPE
   SYNTAX     StorageType 
   ACCESS     read-only
   STATUS     mandatory
   DESCRIPTION
     "This variable represents the storage type value for the
      vrIpOspfAggregate tables."
::= { vrIpOspfAggregateRowStatusEntry 4 }

vrIpOspfAggregateAreaIdIndex OBJECT-TYPE
   SYNTAX     IpAddress 
   ACCESS     not-accessible
   STATUS     mandatory
   DESCRIPTION
     "This variable represents an index for the vrIpOspfAggregate tables."
::= { vrIpOspfAggregateRowStatusEntry 10 }

vrIpOspfAggregateLsdbTypeIndex OBJECT-TYPE
   SYNTAX     INTEGER  {
                 summaryLink(3),
                 nssaExternalLink(7) }
   ACCESS     not-accessible
   STATUS     mandatory
   DESCRIPTION
     "This variable represents an index for the vrIpOspfAggregate tables."
::= { vrIpOspfAggregateRowStatusEntry 11 }

vrIpOspfAggregateAggregateNetIndex OBJECT-TYPE
   SYNTAX     IpAddress 
   ACCESS     not-accessible
   STATUS     mandatory
   DESCRIPTION
     "This variable represents an index for the vrIpOspfAggregate tables."
::= { vrIpOspfAggregateRowStatusEntry 12 }

vrIpOspfAggregateAggregateMaskIndex OBJECT-TYPE
   SYNTAX     IpAddress 
   ACCESS     not-accessible
   STATUS     mandatory
   DESCRIPTION
     "This variable represents an index for the vrIpOspfAggregate tables."
::= { vrIpOspfAggregateRowStatusEntry 13 }

vrIpOspfAggregateProvTable OBJECT-TYPE
   SYNTAX     SEQUENCE OF VrIpOspfAggregateProvEntry
   ACCESS     not-accessible
   STATUS     mandatory
   DESCRIPTION
     "Identifies a group of provisionable attributes."
::= { vrIpOspfAggregate 10 }

vrIpOspfAggregateProvEntry OBJECT-TYPE
   SYNTAX     VrIpOspfAggregateProvEntry
   ACCESS     not-accessible
   STATUS     mandatory
   DESCRIPTION
     "An entry in the vrIpOspfAggregateProvTable."
   INDEX {
      vrIndex,
      vrIpIndex,
      vrIpOspfIndex,
      vrIpOspfAggregateAreaIdIndex,
      vrIpOspfAggregateLsdbTypeIndex,
      vrIpOspfAggregateAggregateNetIndex,
      vrIpOspfAggregateAggregateMaskIndex }
::= { vrIpOspfAggregateProvTable 1 }

VrIpOspfAggregateProvEntry ::= SEQUENCE {
   vrIpOspfAggregateEffect
      INTEGER }

vrIpOspfAggregateEffect OBJECT-TYPE
   SYNTAX     INTEGER  {
                 advertiseMatching(1),
                 doNotAdvertiseMatching(2),
                 invalid(3) }
   ACCESS     read-write
   STATUS     mandatory
   DESCRIPTION
     "This attribute determines whether or not the routing information will be 
      advertised, depending on other criterion. Setting this value to 
      doNotAdvertiseMatching can prevent advertising routing information 
      for the address and mask values specified as the indices for this entry."
   DEFVAL     { advertiseMatching }
::= { vrIpOspfAggregateProvEntry 1 }


-- Vr/<string> Ip Ospf HostEntry/<Ip Address>,<Decimal>
-- This component indicates what hosts are directly attached to the router, 
-- and what metrics and types of service should be advertised for them. 
-- This component is an optional subcomponent of Ospf.

vrIpOspfHost OBJECT IDENTIFIER ::= { vrIpOspf 6 }



vrIpOspfHostRowStatusTable OBJECT-TYPE
   SYNTAX     SEQUENCE OF VrIpOspfHostRowStatusEntry
   ACCESS     not-accessible
   STATUS     mandatory
   DESCRIPTION
     "This entry controls the addition and deletion of 
      vrIpOspfHost components."
::= { vrIpOspfHost 1 }

vrIpOspfHostRowStatusEntry OBJECT-TYPE
   SYNTAX     VrIpOspfHostRowStatusEntry
   ACCESS     not-accessible
   STATUS     mandatory
   DESCRIPTION
     "A single entry in the table represents a single 
      vrIpOspfHost component."
   INDEX {
      vrIndex,
      vrIpIndex,
      vrIpOspfIndex,
      vrIpOspfHostAddressIndex,
      vrIpOspfHostTosIndex }
::= { vrIpOspfHostRowStatusTable 1 }

VrIpOspfHostRowStatusEntry ::= SEQUENCE {
   vrIpOspfHostRowStatus
      RowStatus,
   vrIpOspfHostComponentName
      DisplayString,
   vrIpOspfHostStorageType
      StorageType,
   vrIpOspfHostAddressIndex
      IpAddress,
   vrIpOspfHostTosIndex
      Integer32 }

vrIpOspfHostRowStatus OBJECT-TYPE
   SYNTAX     RowStatus 
   ACCESS     read-write
   STATUS     mandatory
   DESCRIPTION
     "This variable is used as the basis for SNMP naming of
      vrIpOspfHost components.
      These components can be added and deleted."
::= { vrIpOspfHostRowStatusEntry 1 }

vrIpOspfHostComponentName OBJECT-TYPE
   SYNTAX     DisplayString 
   ACCESS     read-only
   STATUS     mandatory
   DESCRIPTION
     "This variable provides the component's string name for
      use with the ASCII Console Interface"
::= { vrIpOspfHostRowStatusEntry 2 }

vrIpOspfHostStorageType OBJECT-TYPE
   SYNTAX     StorageType 
   ACCESS     read-only
   STATUS     mandatory
   DESCRIPTION
     "This variable represents the storage type value for the
      vrIpOspfHost tables."
::= { vrIpOspfHostRowStatusEntry 4 }

vrIpOspfHostAddressIndex OBJECT-TYPE
   SYNTAX     IpAddress 
   ACCESS     not-accessible
   STATUS     mandatory
   DESCRIPTION
     "This variable represents an index for the vrIpOspfHost tables."
::= { vrIpOspfHostRowStatusEntry 10 }

vrIpOspfHostTosIndex OBJECT-TYPE
   SYNTAX     Integer32 (0..0)
   ACCESS     not-accessible
   STATUS     mandatory
   DESCRIPTION
     "This variable represents an index for the vrIpOspfHost tables."
::= { vrIpOspfHostRowStatusEntry 11 }

vrIpOspfHostProvTable OBJECT-TYPE
   SYNTAX     SEQUENCE OF VrIpOspfHostProvEntry
   ACCESS     not-accessible
   STATUS     mandatory
   DESCRIPTION
     "Provisionable set of attributes for the Host entry."
::= { vrIpOspfHost 10 }

vrIpOspfHostProvEntry OBJECT-TYPE
   SYNTAX     VrIpOspfHostProvEntry
   ACCESS     not-accessible
   STATUS     mandatory
   DESCRIPTION
     "An entry in the vrIpOspfHostProvTable."
   INDEX {
      vrIndex,
      vrIpIndex,
      vrIpOspfIndex,
      vrIpOspfHostAddressIndex,
      vrIpOspfHostTosIndex }
::= { vrIpOspfHostProvTable 1 }

VrIpOspfHostProvEntry ::= SEQUENCE {
   vrIpOspfHostAreaId
      AreaID,
   vrIpOspfHostMetric
      Unsigned32 }

vrIpOspfHostAreaId OBJECT-TYPE
   SYNTAX     AreaID 
   ACCESS     read-write
   STATUS     mandatory
   DESCRIPTION
     "This is an Ip address for the Host Entry that indicates the area it belongs 
      to."
::= { vrIpOspfHostProvEntry 1 }

vrIpOspfHostMetric OBJECT-TYPE
   SYNTAX     Unsigned32 (1..65535)
   ACCESS     read-write
   STATUS     mandatory
   DESCRIPTION
     "The metric to be advertised."
   DEFVAL     { 1 }
::= { vrIpOspfHostProvEntry 2 }


-- Vr/<string> Ip Ospf VirtIfEntry/<Ip Address>,<Ip Address>
-- This component describes all the virtual links configured for this OSPF 
-- Router.

vrIpOspfVirtIf OBJECT IDENTIFIER ::= { vrIpOspf 7 }



vrIpOspfVirtIfRowStatusTable OBJECT-TYPE
   SYNTAX     SEQUENCE OF VrIpOspfVirtIfRowStatusEntry
   ACCESS     not-accessible
   STATUS     mandatory
   DESCRIPTION
     "This entry controls the addition and deletion of 
      vrIpOspfVirtIf components."
::= { vrIpOspfVirtIf 1 }

vrIpOspfVirtIfRowStatusEntry OBJECT-TYPE
   SYNTAX     VrIpOspfVirtIfRowStatusEntry
   ACCESS     not-accessible
   STATUS     mandatory
   DESCRIPTION
     "A single entry in the table represents a single 
      vrIpOspfVirtIf component."
   INDEX {
      vrIndex,
      vrIpIndex,
      vrIpOspfIndex,
      vrIpOspfVirtIfAreaIdIndex,
      vrIpOspfVirtIfNbrRouterIdIndex }
::= { vrIpOspfVirtIfRowStatusTable 1 }

VrIpOspfVirtIfRowStatusEntry ::= SEQUENCE {
   vrIpOspfVirtIfRowStatus
      RowStatus,
   vrIpOspfVirtIfComponentName
      DisplayString,
   vrIpOspfVirtIfStorageType
      StorageType,
   vrIpOspfVirtIfAreaIdIndex
      IpAddress,
   vrIpOspfVirtIfNbrRouterIdIndex
      IpAddress }

vrIpOspfVirtIfRowStatus OBJECT-TYPE
   SYNTAX     RowStatus 
   ACCESS     read-write
   STATUS     mandatory
   DESCRIPTION
     "This variable is used as the basis for SNMP naming of
      vrIpOspfVirtIf components.
      These components can be added and deleted."
::= { vrIpOspfVirtIfRowStatusEntry 1 }

vrIpOspfVirtIfComponentName OBJECT-TYPE
   SYNTAX     DisplayString 
   ACCESS     read-only
   STATUS     mandatory
   DESCRIPTION
     "This variable provides the component's string name for
      use with the ASCII Console Interface"
::= { vrIpOspfVirtIfRowStatusEntry 2 }

vrIpOspfVirtIfStorageType OBJECT-TYPE
   SYNTAX     StorageType 
   ACCESS     read-only
   STATUS     mandatory
   DESCRIPTION
     "This variable represents the storage type value for the
      vrIpOspfVirtIf tables."
::= { vrIpOspfVirtIfRowStatusEntry 4 }

vrIpOspfVirtIfAreaIdIndex OBJECT-TYPE
   SYNTAX     IpAddress 
   ACCESS     not-accessible
   STATUS     mandatory
   DESCRIPTION
     "This variable represents an index for the vrIpOspfVirtIf tables."
::= { vrIpOspfVirtIfRowStatusEntry 10 }

vrIpOspfVirtIfNbrRouterIdIndex OBJECT-TYPE
   SYNTAX     IpAddress 
   ACCESS     not-accessible
   STATUS     mandatory
   DESCRIPTION
     "This variable represents an index for the vrIpOspfVirtIf tables."
::= { vrIpOspfVirtIfRowStatusEntry 11 }

vrIpOspfVirtIfProvTable OBJECT-TYPE
   SYNTAX     SEQUENCE OF VrIpOspfVirtIfProvEntry
   ACCESS     not-accessible
   STATUS     mandatory
   DESCRIPTION
     "This group of attributes provide provisioning data for the VirtIfEntry."
::= { vrIpOspfVirtIf 10 }

vrIpOspfVirtIfProvEntry OBJECT-TYPE
   SYNTAX     VrIpOspfVirtIfProvEntry
   ACCESS     not-accessible
   STATUS     mandatory
   DESCRIPTION
     "An entry in the vrIpOspfVirtIfProvTable."
   INDEX {
      vrIndex,
      vrIpIndex,
      vrIpOspfIndex,
      vrIpOspfVirtIfAreaIdIndex,
      vrIpOspfVirtIfNbrRouterIdIndex }
::= { vrIpOspfVirtIfProvTable 1 }

VrIpOspfVirtIfProvEntry ::= SEQUENCE {
   vrIpOspfVirtIfTransitDelay
      Unsigned32,
   vrIpOspfVirtIfRetransInterval
      Unsigned32,
   vrIpOspfVirtIfHelloInterval
      Unsigned32,
   vrIpOspfVirtIfRtrDeadInterval
      Unsigned32,
   vrIpOspfVirtIfAuthKey
      HexString }

vrIpOspfVirtIfTransitDelay OBJECT-TYPE
   SYNTAX     Unsigned32 (1..3600)
   ACCESS     read-write
   STATUS     mandatory
   DESCRIPTION
     "The estimated number of seconds it takes to transmit a link-state update 
      packet over this interface."
   DEFVAL     { 1 }
::= { vrIpOspfVirtIfProvEntry 1 }

vrIpOspfVirtIfRetransInterval OBJECT-TYPE
   SYNTAX     Unsigned32 (1..3600)
   ACCESS     read-write
   STATUS     mandatory
   DESCRIPTION
     "The number of seconds between link-state advertisement 
      retransmissions, for adjacencies belonging to this interface. This value is 
      also used when retransmitting database description 
      and link-state request packets. This value would be well over the 
      expected round-trip time."
   DEFVAL     { 5 }
::= { vrIpOspfVirtIfProvEntry 2 }

vrIpOspfVirtIfHelloInterval OBJECT-TYPE
   SYNTAX     Unsigned32 (1..3600)
   ACCESS     read-write
   STATUS     mandatory
   DESCRIPTION
     "The length of time, in seconds, between the Hello packets that the router 
      sends on the interface. This value must be the same for the virtual 
      neighbor."
   DEFVAL     { 10 }
::= { vrIpOspfVirtIfProvEntry 3 }

vrIpOspfVirtIfRtrDeadInterval OBJECT-TYPE
   SYNTAX     Unsigned32 (1..3600)
   ACCESS     read-write
   STATUS     mandatory
   DESCRIPTION
     "The number of seconds that a router's Hello packets have not been seen 
      before its neighbors declare the router down. This should be some 
      multiple of the Hello interval. This value must be the same for the 
      virtual neighbor."
   DEFVAL     { 60 }
::= { vrIpOspfVirtIfProvEntry 4 }

vrIpOspfVirtIfAuthKey OBJECT-TYPE
   SYNTAX     HexString (SIZE (1..8))
   ACCESS     write-only
   STATUS     mandatory
   DESCRIPTION
     "If authentication type is simple password, the password for this virtual 
      circuit. If the value of the attribute is not set, then this attribute is 
      ignored by the application.
      If the value of this attribute is set, then the value of the attribute 
      authType under this particular Area should be set to simplePassword, 
      otherwise the application will ignore this authentication key."
   DEFVAL     { '0000000000000000'H }  -- "0000000000000000"
::= { vrIpOspfVirtIfProvEntry 5 }

vrIpOspfVirtIfOperTable OBJECT-TYPE
   SYNTAX     SEQUENCE OF VrIpOspfVirtIfOperEntry
   ACCESS     not-accessible
   STATUS     mandatory
   DESCRIPTION
     "Represents a group of operational attributes for the VirtIfEntry 
      component."
::= { vrIpOspfVirtIf 11 }

vrIpOspfVirtIfOperEntry OBJECT-TYPE
   SYNTAX     VrIpOspfVirtIfOperEntry
   ACCESS     not-accessible
   STATUS     mandatory
   DESCRIPTION
     "An entry in the vrIpOspfVirtIfOperTable."
   INDEX {
      vrIndex,
      vrIpIndex,
      vrIpOspfIndex,
      vrIpOspfVirtIfAreaIdIndex,
      vrIpOspfVirtIfNbrRouterIdIndex }
::= { vrIpOspfVirtIfOperTable 1 }

VrIpOspfVirtIfOperEntry ::= SEQUENCE {
   vrIpOspfVirtIfState
      INTEGER,
   vrIpOspfVirtIfEvents
      Counter32 }

vrIpOspfVirtIfState OBJECT-TYPE
   SYNTAX     INTEGER  {
                 down(1),
                 pointToPoint(4) }
   ACCESS     read-only
   STATUS     mandatory
   DESCRIPTION
     "The state of the OSPF virtual interface."
::= { vrIpOspfVirtIfOperEntry 1 }

vrIpOspfVirtIfEvents OBJECT-TYPE
   SYNTAX     Counter32 
   ACCESS     read-only
   STATUS     mandatory
   DESCRIPTION
     "The number of state changes or error events on the virtual link."
::= { vrIpOspfVirtIfOperEntry 2 }


-- Vr/<string> Ip Ospf Export/n
-- Each instance of this component specifies an OSPF export policy. An 
-- OSPF export policy is used to decide if a route in the IP forwarding 
-- table should be blocked or advertised as OSPF external routes onto 
-- attached OSPF areas of the virtual router.
-- Passport IP OSPF by default advertises all OSPF external routes based 
-- on the metric and tag in the IP forwarding table.

vrIpOspfExport OBJECT IDENTIFIER ::= { vrIpOspf 8 }



vrIpOspfExportRowStatusTable OBJECT-TYPE
   SYNTAX     SEQUENCE OF VrIpOspfExportRowStatusEntry
   ACCESS     not-accessible
   STATUS     mandatory
   DESCRIPTION
     "This entry controls the addition and deletion of 
      vrIpOspfExport components."
::= { vrIpOspfExport 1 }

vrIpOspfExportRowStatusEntry OBJECT-TYPE
   SYNTAX     VrIpOspfExportRowStatusEntry
   ACCESS     not-accessible
   STATUS     mandatory
   DESCRIPTION
     "A single entry in the table represents a single 
      vrIpOspfExport component."
   INDEX {
      vrIndex,
      vrIpIndex,
      vrIpOspfIndex,
      vrIpOspfExportIndex }
::= { vrIpOspfExportRowStatusTable 1 }

VrIpOspfExportRowStatusEntry ::= SEQUENCE {
   vrIpOspfExportRowStatus
      RowStatus,
   vrIpOspfExportComponentName
      DisplayString,
   vrIpOspfExportStorageType
      StorageType,
   vrIpOspfExportIndex
      Integer32 }

vrIpOspfExportRowStatus OBJECT-TYPE
   SYNTAX     RowStatus 
   ACCESS     read-write
   STATUS     mandatory
   DESCRIPTION
     "This variable is used as the basis for SNMP naming of
      vrIpOspfExport components.
      These components can be added and deleted."
::= { vrIpOspfExportRowStatusEntry 1 }

vrIpOspfExportComponentName OBJECT-TYPE
   SYNTAX     DisplayString 
   ACCESS     read-only
   STATUS     mandatory
   DESCRIPTION
     "This variable provides the component's string name for
      use with the ASCII Console Interface"
::= { vrIpOspfExportRowStatusEntry 2 }

vrIpOspfExportStorageType OBJECT-TYPE
   SYNTAX     StorageType 
   ACCESS     read-only
   STATUS     mandatory
   DESCRIPTION
     "This variable represents the storage type value for the
      vrIpOspfExport tables."
::= { vrIpOspfExportRowStatusEntry 4 }

vrIpOspfExportIndex OBJECT-TYPE
   SYNTAX     Integer32 (0..65535)
   ACCESS     not-accessible
   STATUS     mandatory
   DESCRIPTION
     "This variable represents the index for the vrIpOspfExport tables."
::= { vrIpOspfExportRowStatusEntry 10 }

vrIpOspfExportProvTable OBJECT-TYPE
   SYNTAX     SEQUENCE OF VrIpOspfExportProvEntry
   ACCESS     not-accessible
   STATUS     mandatory
   DESCRIPTION
     "This Group contains all the Provisioned attributes for the Export 
      Component."
::= { vrIpOspfExport 10 }

vrIpOspfExportProvEntry OBJECT-TYPE
   SYNTAX     VrIpOspfExportProvEntry
   ACCESS     not-accessible
   STATUS     mandatory
   DESCRIPTION
     "An entry in the vrIpOspfExportProvTable."
   INDEX {
      vrIndex,
      vrIpIndex,
      vrIpOspfIndex,
      vrIpOspfExportIndex }
::= { vrIpOspfExportProvTable 1 }

VrIpOspfExportProvEntry ::= SEQUENCE {
   vrIpOspfExportAdvertiseStatus
      INTEGER,
   vrIpOspfExportMetric
      INTEGER,
   vrIpOspfExportProtocol
      INTEGER,
   vrIpOspfExportRipInterface
      IpAddress,
   vrIpOspfExportRipNeighbor
      IpAddress,
   vrIpOspfExportEgpAsId
      Unsigned32,
   vrIpOspfExportTag
      Unsigned32,
   vrIpOspfExportExtLsaMetricType
      INTEGER,
   vrIpOspfExportBgpAsId
      Unsigned32,
   vrIpOspfExportBgpPeerIp
      IpAddress }

vrIpOspfExportAdvertiseStatus OBJECT-TYPE
   SYNTAX     INTEGER  {
                 send(1),
                 block(2) }
   ACCESS     read-write
   STATUS     mandatory
   DESCRIPTION
     "This attribute specifies if the routes that match this export policy are 
      advertised (send) or not advertised (block)."
   DEFVAL     { send }
::= { vrIpOspfExportProvEntry 1 }

vrIpOspfExportMetric OBJECT-TYPE
   SYNTAX     INTEGER (-1..16777215)
   ACCESS     read-write
   STATUS     mandatory
   DESCRIPTION
     "This attribute specifies the metric to be used on the routes being 
      exported as a result of matching this export policy.
      If the attribute advertiseStatus is set to block, then the value of metric is 
      ignored. The metric value is not used to select which routes to block or 
      send, but rather the metric value advertised for the routes.
      A value of -1 indicates that the metric associated with the route in the 
      forwarding table is used."
   DEFVAL     { -1 }
::= { vrIpOspfExportProvEntry 2 }

vrIpOspfExportProtocol OBJECT-TYPE
   SYNTAX     INTEGER  {
                 all(1),
                 egp(2),
                 rip(3),
                 staticLocal(6),
                 staticRemote(7),
                 bgpExternal(9) }
   ACCESS     read-write
   STATUS     mandatory
   DESCRIPTION
     "This attribute specifies the routes to which this export policy applies 
      based on the routing protocol of how the routes are learned. If it is set to 
      all, this export policy applies to all routes in the forwarding table."
   DEFVAL     { all }
::= { vrIpOspfExportProvEntry 3 }

vrIpOspfExportRipInterface OBJECT-TYPE
   SYNTAX     IpAddress 
   ACCESS     read-write
   STATUS     mandatory
   DESCRIPTION
     "This attribute specifies the RIP learned routes to which this export policy 
      applies, based on the RIP interface from which the routes are learned.
      This attribute can only be non zero when the protocol is set to rip. The 
      value of 0.0.0.0 implies any RIP interface on the same virtual router; 
      otherwise the value of this attribute must match the interface address of 
      a LogicalIf that has a RipIf on the same virtual router."
   DEFVAL     { '00000000'H }  -- "0.0.0.0"
::= { vrIpOspfExportProvEntry 4 }

vrIpOspfExportRipNeighbor OBJECT-TYPE
   SYNTAX     IpAddress 
   ACCESS     read-write
   STATUS     mandatory
   DESCRIPTION
     "This attribute specifies the RIP learned routes to which this export policy 
      applies, based on the RIP neighbor of which the routes are learned from.
      This attribute can only be non zero when the protocol is set to rip. The 
      value of 0.0.0.0 implies any RIP neighbor."
   DEFVAL     { '00000000'H }  -- "0.0.0.0"
::= { vrIpOspfExportProvEntry 5 }

vrIpOspfExportEgpAsId OBJECT-TYPE
   SYNTAX     Unsigned32 (0..65535)
   ACCESS     read-write
   STATUS     mandatory
   DESCRIPTION
     "This attribute specifies the EGP learned routes to which this export 
      policy applies, based on the EGP autonomous system identifier of which 
      the routes are learned from.
      This attribute can only be non zero when protocol is set to egp. The 
      value of 0 implies any EGP autonomous system; otherwise the value of 
      this attribute must match the asId of an EGP neighbor on the same 
      virtual router."
   DEFVAL     { 0 }
::= { vrIpOspfExportProvEntry 6 }

vrIpOspfExportTag OBJECT-TYPE
   SYNTAX     Unsigned32 (0..4294967295)
   ACCESS     read-write
   STATUS     mandatory
   DESCRIPTION
     "This attribute specifies the OSPF tag to be used on the routes being 
      exported as a result of matching this export policy.
      If the attribute advertiseStatus is set to block, then the value of tag is 
      ignored. The tag value is not used to select which routes to block or 
      send, but rather the tag value advertised for the routes.
      A value of 4294967295 indicates that the tag associated with the route in 
      the forwarding table is used."
   DEFVAL     { 4294967295 }
::= { vrIpOspfExportProvEntry 7 }

vrIpOspfExportExtLsaMetricType OBJECT-TYPE
   SYNTAX     INTEGER  {
                 useProtocolDefault(0),
                 type1(1),
                 type2(2) }
   ACCESS     read-write
   STATUS     mandatory
   DESCRIPTION
     "This attribute specifies the metric type in the OSPF external link state 
      advertisement of the routes being exported as a result of matching this 
      export policy.
      If the attribute advertiseStatus is set to block, then the value of 
      extLsaMetricType is ignored. The extLsaMetricType value is not used to 
      select which routes to block or send, but rather the metric value 
      advertised for the routes.
      The value useProtocolDefault indicates the metric type is automatically 
      chosen based on the routing protocol which the route was learned from."
   DEFVAL     { useProtocolDefault }
::= { vrIpOspfExportProvEntry 8 }

vrIpOspfExportBgpAsId OBJECT-TYPE
   SYNTAX     Unsigned32 (0..65535)
   ACCESS     read-write
   STATUS     mandatory
   DESCRIPTION
     "This key attribute specifies the bgp AS from which a bgp route is 
      learned from. This key is used only if the protocol is bgpExternal. 
      bgpAsId of value 0 mathces all ASs."
   DEFVAL     { 0 }
::= { vrIpOspfExportProvEntry 9 }

vrIpOspfExportBgpPeerIp OBJECT-TYPE
   SYNTAX     IpAddress 
   ACCESS     read-write
   STATUS     mandatory
   DESCRIPTION
     "This key attribute specifies the bgp peer where the routes were learned 
      from. bgpPeerIp of 0 matches all bgp peers. This attribute is used as a 
      key when protocol is set to bgpInternal or bgpExternal."
   DEFVAL     { '00000000'H }  -- "0.0.0.0"
::= { vrIpOspfExportProvEntry 10 }


-- This component identifies a set of attributes when matched determines 
-- the export policy applied. 

vrIpOspfExportNetList OBJECT IDENTIFIER ::= { vrIpOspfExport 2 }



vrIpOspfExportNetListRowStatusTable OBJECT-TYPE
   SYNTAX     SEQUENCE OF VrIpOspfExportNetListRowStatusEntry
   ACCESS     not-accessible
   STATUS     mandatory
   DESCRIPTION
     "This entry controls the addition and deletion of 
      vrIpOspfExportNetList components."
::= { vrIpOspfExportNetList 1 }

vrIpOspfExportNetListRowStatusEntry OBJECT-TYPE
   SYNTAX     VrIpOspfExportNetListRowStatusEntry
   ACCESS     not-accessible
   STATUS     mandatory
   DESCRIPTION
     "A single entry in the table represents a single 
      vrIpOspfExportNetList component."
   INDEX {
      vrIndex,
      vrIpIndex,
      vrIpOspfIndex,
      vrIpOspfExportIndex,
      vrIpOspfExportNetListIndex }
::= { vrIpOspfExportNetListRowStatusTable 1 }

VrIpOspfExportNetListRowStatusEntry ::= SEQUENCE {
   vrIpOspfExportNetListRowStatus
      RowStatus,
   vrIpOspfExportNetListComponentName
      DisplayString,
   vrIpOspfExportNetListStorageType
      StorageType,
   vrIpOspfExportNetListIndex
      Integer32 }

vrIpOspfExportNetListRowStatus OBJECT-TYPE
   SYNTAX     RowStatus 
   ACCESS     read-write
   STATUS     mandatory
   DESCRIPTION
     "This variable is used as the basis for SNMP naming of
      vrIpOspfExportNetList components.
      These components can be added and deleted."
::= { vrIpOspfExportNetListRowStatusEntry 1 }

vrIpOspfExportNetListComponentName OBJECT-TYPE
   SYNTAX     DisplayString 
   ACCESS     read-only
   STATUS     mandatory
   DESCRIPTION
     "This variable provides the component's string name for
      use with the ASCII Console Interface"
::= { vrIpOspfExportNetListRowStatusEntry 2 }

vrIpOspfExportNetListStorageType OBJECT-TYPE
   SYNTAX     StorageType 
   ACCESS     read-only
   STATUS     mandatory
   DESCRIPTION
     "This variable represents the storage type value for the
      vrIpOspfExportNetList tables."
::= { vrIpOspfExportNetListRowStatusEntry 4 }

vrIpOspfExportNetListIndex OBJECT-TYPE
   SYNTAX     Integer32 (0..65535)
   ACCESS     not-accessible
   STATUS     mandatory
   DESCRIPTION
     "This variable represents the index for the vrIpOspfExportNetList tables."
::= { vrIpOspfExportNetListRowStatusEntry 10 }

vrIpOspfExportNetListProvTable OBJECT-TYPE
   SYNTAX     SEQUENCE OF VrIpOspfExportNetListProvEntry
   ACCESS     not-accessible
   STATUS     mandatory
   DESCRIPTION
     "This group identifies the set of provisionable attributes for the 
      ExportNetworkList component."
::= { vrIpOspfExportNetList 10 }

vrIpOspfExportNetListProvEntry OBJECT-TYPE
   SYNTAX     VrIpOspfExportNetListProvEntry
   ACCESS     not-accessible
   STATUS     mandatory
   DESCRIPTION
     "An entry in the vrIpOspfExportNetListProvTable."
   INDEX {
      vrIndex,
      vrIpIndex,
      vrIpOspfIndex,
      vrIpOspfExportIndex,
      vrIpOspfExportNetListIndex }
::= { vrIpOspfExportNetListProvTable 1 }

VrIpOspfExportNetListProvEntry ::= SEQUENCE {
   vrIpOspfExportNetListIpAddress
      IpAddress,
   vrIpOspfExportNetListIpMask
      IpAddress }

vrIpOspfExportNetListIpAddress OBJECT-TYPE
   SYNTAX     IpAddress 
   ACCESS     read-write
   STATUS     mandatory
   DESCRIPTION
     "This attribute identifies the 32 bit IP address to match against."
::= { vrIpOspfExportNetListProvEntry 1 }

vrIpOspfExportNetListIpMask OBJECT-TYPE
   SYNTAX     IpAddress 
   ACCESS     read-write
   STATUS     mandatory
   DESCRIPTION
     "This attribute is the IP Mask to be used with the IP Address to match 
      against."
::= { vrIpOspfExportNetListProvEntry 2 }

-- 
-- *** THIS SUBTREE CURRENTLY NOT IMPLEMENTED ***
-- 

-- Vr/<string> Ip Ospf VirtNbrEntry/<Ip Address>,<Ip Address>
-- This component describes all of OSPF's Virtual Neighbors.

vrIpOspfVirtNbr OBJECT IDENTIFIER ::= { vrIpOspf 9 }



vrIpOspfVirtNbrRowStatusTable OBJECT-TYPE
   SYNTAX     SEQUENCE OF VrIpOspfVirtNbrRowStatusEntry
   ACCESS     not-accessible
   STATUS     mandatory
   DESCRIPTION
     "*** THIS TABLE CURRENTLY NOT IMPLEMENTED ***

      This entry controls the addition and deletion of 
      vrIpOspfVirtNbr components."
::= { vrIpOspfVirtNbr 1 }

vrIpOspfVirtNbrRowStatusEntry OBJECT-TYPE
   SYNTAX     VrIpOspfVirtNbrRowStatusEntry
   ACCESS     not-accessible
   STATUS     mandatory
   DESCRIPTION
     "A single entry in the table represents a single 
      vrIpOspfVirtNbr component."
   INDEX {
      vrIndex,
      vrIpIndex,
      vrIpOspfIndex,
      vrIpOspfVirtNbrAreaIdIndex,
      vrIpOspfVirtNbrNbrRouterIdIndex }
::= { vrIpOspfVirtNbrRowStatusTable 1 }

VrIpOspfVirtNbrRowStatusEntry ::= SEQUENCE {
   vrIpOspfVirtNbrRowStatus
      RowStatus,
   vrIpOspfVirtNbrComponentName
      DisplayString,
   vrIpOspfVirtNbrStorageType
      StorageType,
   vrIpOspfVirtNbrAreaIdIndex
      IpAddress,
   vrIpOspfVirtNbrNbrRouterIdIndex
      IpAddress }

vrIpOspfVirtNbrRowStatus OBJECT-TYPE
   SYNTAX     RowStatus 
   ACCESS     read-only
   STATUS     mandatory
   DESCRIPTION
     "This variable is used as the basis for SNMP naming of
      vrIpOspfVirtNbr components.
      These components cannot be added nor deleted."
::= { vrIpOspfVirtNbrRowStatusEntry 1 }

vrIpOspfVirtNbrComponentName OBJECT-TYPE
   SYNTAX     DisplayString 
   ACCESS     read-only
   STATUS     mandatory
   DESCRIPTION
     "This variable provides the component's string name for
      use with the ASCII Console Interface"
::= { vrIpOspfVirtNbrRowStatusEntry 2 }

vrIpOspfVirtNbrStorageType OBJECT-TYPE
   SYNTAX     StorageType 
   ACCESS     read-only
   STATUS     mandatory
   DESCRIPTION
     "This variable represents the storage type value for the
      vrIpOspfVirtNbr tables."
::= { vrIpOspfVirtNbrRowStatusEntry 4 }

vrIpOspfVirtNbrAreaIdIndex OBJECT-TYPE
   SYNTAX     IpAddress 
   ACCESS     not-accessible
   STATUS     mandatory
   DESCRIPTION
     "This variable represents an index for the vrIpOspfVirtNbr tables."
::= { vrIpOspfVirtNbrRowStatusEntry 10 }

vrIpOspfVirtNbrNbrRouterIdIndex OBJECT-TYPE
   SYNTAX     IpAddress 
   ACCESS     not-accessible
   STATUS     mandatory
   DESCRIPTION
     "This variable represents an index for the vrIpOspfVirtNbr tables."
::= { vrIpOspfVirtNbrRowStatusEntry 11 }

vrIpOspfVirtNbrOperTable OBJECT-TYPE
   SYNTAX     SEQUENCE OF VrIpOspfVirtNbrOperEntry
   ACCESS     not-accessible
   STATUS     mandatory
   DESCRIPTION
     "*** THIS TABLE CURRENTLY NOT IMPLEMENTED ***

      This group identifies a set of operational attributes."
::= { vrIpOspfVirtNbr 10 }

vrIpOspfVirtNbrOperEntry OBJECT-TYPE
   SYNTAX     VrIpOspfVirtNbrOperEntry
   ACCESS     not-accessible
   STATUS     mandatory
   DESCRIPTION
     "An entry in the vrIpOspfVirtNbrOperTable."
   INDEX {
      vrIndex,
      vrIpIndex,
      vrIpOspfIndex,
      vrIpOspfVirtNbrAreaIdIndex,
      vrIpOspfVirtNbrNbrRouterIdIndex }
::= { vrIpOspfVirtNbrOperTable 1 }

VrIpOspfVirtNbrOperEntry ::= SEQUENCE {
   vrIpOspfVirtNbrNbrIpAddress
      IpAddress,
   vrIpOspfVirtNbrOptions
      Unsigned32,
   vrIpOspfVirtNbrState
      INTEGER,
   vrIpOspfVirtNbrEvents
      Counter32,
   vrIpOspfVirtNbrLsRetransQlen
      Gauge32,
   vrIpOspfVirtNbrExchangeStatus
      INTEGER }

vrIpOspfVirtNbrNbrIpAddress OBJECT-TYPE
   SYNTAX     IpAddress 
   ACCESS     read-only
   STATUS     mandatory
   DESCRIPTION
     "Indicates the Ip address this interface this virtual neighbor is using."
::= { vrIpOspfVirtNbrOperEntry 1 }

vrIpOspfVirtNbrOptions OBJECT-TYPE
   SYNTAX     Unsigned32 (0..7)
   ACCESS     read-only
   STATUS     mandatory
   DESCRIPTION
     "A bit mask corresponding to the neighbor's options field. Bit 1, if set 
      indicates that the system will operate on Type of Service metrics other 
      than TOS 0. If zero, the neighbor will ignore all metrics except the TOS 
      0 metric. Bit 2, if set, indicates that the system is Network Multicast 
      capable; i.e., that it implements OSPF Multicast Routing."
::= { vrIpOspfVirtNbrOperEntry 2 }

vrIpOspfVirtNbrState OBJECT-TYPE
   SYNTAX     INTEGER  {
                 down(1),
                 attempt(2),
                 init(3),
                 twoWay(4),
                 exchange(5),
                 exchangeStatrt(6),
                 loading(7),
                 full(8) }
   ACCESS     read-only
   STATUS     mandatory
   DESCRIPTION
     "The state of the virtual neighbor relationship."
::= { vrIpOspfVirtNbrOperEntry 3 }

vrIpOspfVirtNbrEvents OBJECT-TYPE
   SYNTAX     Counter32 
   ACCESS     read-only
   STATUS     mandatory
   DESCRIPTION
     "The number of times this virtual link has changed its state, or an error 
      has occurred."
::= { vrIpOspfVirtNbrOperEntry 4 }

vrIpOspfVirtNbrLsRetransQlen OBJECT-TYPE
   SYNTAX     Gauge32 (0..4294967295)
   ACCESS     read-only
   STATUS     mandatory
   DESCRIPTION
     "The current length of the Retransmission queue."
::= { vrIpOspfVirtNbrOperEntry 5 }

vrIpOspfVirtNbrExchangeStatus OBJECT-TYPE
   SYNTAX     INTEGER  {
                 master(1),
                 slave(2) }
   ACCESS     read-only
   STATUS     mandatory
   DESCRIPTION
     "Indicates the exchange status of the entry in this table."
::= { vrIpOspfVirtNbrOperEntry 6 }

-- 
-- *** THIS SUBTREE CURRENTLY NOT IMPLEMENTED ***
-- 

-- Vr/<string> Ip Ospf NbrEntry/<Ip Address>,<Decimal>
-- This component is a dynamic subcomponent of OSPF that describes all 
-- the OSPF Neighbors.

vrIpOspfNbr OBJECT IDENTIFIER ::= { vrIpOspf 10 }



vrIpOspfNbrRowStatusTable OBJECT-TYPE
   SYNTAX     SEQUENCE OF VrIpOspfNbrRowStatusEntry
   ACCESS     not-accessible
   STATUS     mandatory
   DESCRIPTION
     "*** THIS TABLE CURRENTLY NOT IMPLEMENTED ***

      This entry controls the addition and deletion of 
      vrIpOspfNbr components."
::= { vrIpOspfNbr 1 }

vrIpOspfNbrRowStatusEntry OBJECT-TYPE
   SYNTAX     VrIpOspfNbrRowStatusEntry
   ACCESS     not-accessible
   STATUS     mandatory
   DESCRIPTION
     "A single entry in the table represents a single 
      vrIpOspfNbr component."
   INDEX {
      vrIndex,
      vrIpIndex,
      vrIpOspfIndex,
      vrIpOspfNbrAddressIndex,
      vrIpOspfNbrAddressLessIndex }
::= { vrIpOspfNbrRowStatusTable 1 }

VrIpOspfNbrRowStatusEntry ::= SEQUENCE {
   vrIpOspfNbrRowStatus
      RowStatus,
   vrIpOspfNbrComponentName
      DisplayString,
   vrIpOspfNbrStorageType
      StorageType,
   vrIpOspfNbrAddressIndex
      IpAddress,
   vrIpOspfNbrAddressLessIndex
      Integer32 }

vrIpOspfNbrRowStatus OBJECT-TYPE
   SYNTAX     RowStatus 
   ACCESS     read-only
   STATUS     mandatory
   DESCRIPTION
     "This variable is used as the basis for SNMP naming of
      vrIpOspfNbr components.
      These components cannot be added nor deleted."
::= { vrIpOspfNbrRowStatusEntry 1 }

vrIpOspfNbrComponentName OBJECT-TYPE
   SYNTAX     DisplayString 
   ACCESS     read-only
   STATUS     mandatory
   DESCRIPTION
     "This variable provides the component's string name for
      use with the ASCII Console Interface"
::= { vrIpOspfNbrRowStatusEntry 2 }

vrIpOspfNbrStorageType OBJECT-TYPE
   SYNTAX     StorageType 
   ACCESS     read-only
   STATUS     mandatory
   DESCRIPTION
     "This variable represents the storage type value for the
      vrIpOspfNbr tables."
::= { vrIpOspfNbrRowStatusEntry 4 }

vrIpOspfNbrAddressIndex OBJECT-TYPE
   SYNTAX     IpAddress 
   ACCESS     not-accessible
   STATUS     mandatory
   DESCRIPTION
     "This variable represents an index for the vrIpOspfNbr tables."
::= { vrIpOspfNbrRowStatusEntry 10 }

vrIpOspfNbrAddressLessIndex OBJECT-TYPE
   SYNTAX     Integer32 (0)
   ACCESS     not-accessible
   STATUS     mandatory
   DESCRIPTION
     "This variable represents an index for the vrIpOspfNbr tables."
::= { vrIpOspfNbrRowStatusEntry 11 }

vrIpOspfNbrOperTable OBJECT-TYPE
   SYNTAX     SEQUENCE OF VrIpOspfNbrOperEntry
   ACCESS     not-accessible
   STATUS     mandatory
   DESCRIPTION
     "*** THIS TABLE CURRENTLY NOT IMPLEMENTED ***

      This group identifies the operational set of attributes for the 
      NeighborEntry."
::= { vrIpOspfNbr 10 }

vrIpOspfNbrOperEntry OBJECT-TYPE
   SYNTAX     VrIpOspfNbrOperEntry
   ACCESS     not-accessible
   STATUS     mandatory
   DESCRIPTION
     "An entry in the vrIpOspfNbrOperTable."
   INDEX {
      vrIndex,
      vrIpIndex,
      vrIpOspfIndex,
      vrIpOspfNbrAddressIndex,
      vrIpOspfNbrAddressLessIndex }
::= { vrIpOspfNbrOperTable 1 }

VrIpOspfNbrOperEntry ::= SEQUENCE {
   vrIpOspfNbrRtrId
      IpAddress,
   vrIpOspfNbrOptions
      Unsigned32,
   vrIpOspfNbrPriority
      Unsigned32,
   vrIpOspfNbrState
      INTEGER,
   vrIpOspfNbrEvents
      Counter32,
   vrIpOspfNbrLsRetransQlen
      Gauge32,
   vrIpOspfNbrNbmaNbrStatus
      INTEGER,
   vrIpOspfNbrExchangeStatus
      INTEGER,
   vrIpOspfNbrPermanence
      INTEGER }

vrIpOspfNbrRtrId OBJECT-TYPE
   SYNTAX     IpAddress 
   ACCESS     read-only
   STATUS     mandatory
   DESCRIPTION
     "An Ip Address that uniquely identifies the neighboring router in the 
      autonomous system."
::= { vrIpOspfNbrOperEntry 1 }

vrIpOspfNbrOptions OBJECT-TYPE
   SYNTAX     Unsigned32 (0..7)
   ACCESS     read-only
   STATUS     mandatory
   DESCRIPTION
     "A bit mask corresponding to the neighbor's options field. Bit 0, if set, 
      indicates that the area accepts and operates on external information, if 
      zero, it is a stub area. Bit 1, if set, indicates that the system will operate 
      on Type of Service metrics other than TOS 0. If zero, the neighbor will 
      ignore all metrics except the TOS 0 metric. Bit 2, if set, indicates that 
      the system is Network Multicast capable; i.e., that it implements OSPF 
      Multicast Routing."
::= { vrIpOspfNbrOperEntry 2 }

vrIpOspfNbrPriority OBJECT-TYPE
   SYNTAX     Unsigned32 (0..255)
   ACCESS     read-only
   STATUS     mandatory
   DESCRIPTION
     "The priority of this neighbor in the designated router election algorithm. 
      The value 0 signifies that the neighbor is not eligible to become the 
      designated router on this particular network."
::= { vrIpOspfNbrOperEntry 3 }

vrIpOspfNbrState OBJECT-TYPE
   SYNTAX     INTEGER  {
                 down(1),
                 attempt(2),
                 init(3),
                 twoWay(4),
                 exchangeStart(5),
                 exchange(6),
                 loading(7),
                 full(8) }
   ACCESS     read-only
   STATUS     mandatory
   DESCRIPTION
     "The state of the relationship with this neighbor."
::= { vrIpOspfNbrOperEntry 4 }

vrIpOspfNbrEvents OBJECT-TYPE
   SYNTAX     Counter32 
   ACCESS     read-only
   STATUS     mandatory
   DESCRIPTION
     "The number of times this neighbor relationship has changed state, or an 
      error has occurred."
::= { vrIpOspfNbrOperEntry 5 }

vrIpOspfNbrLsRetransQlen OBJECT-TYPE
   SYNTAX     Gauge32 (0..4294967295)
   ACCESS     read-only
   STATUS     mandatory
   DESCRIPTION
     "The current length of the Retransmission queue."
::= { vrIpOspfNbrOperEntry 6 }

vrIpOspfNbrNbmaNbrStatus OBJECT-TYPE
   SYNTAX     INTEGER  {
                 valid(1),
                 invalid(2) }
   ACCESS     read-only
   STATUS     mandatory
   DESCRIPTION
     "This attribute describes the status of the entry."
::= { vrIpOspfNbrOperEntry 7 }

vrIpOspfNbrExchangeStatus OBJECT-TYPE
   SYNTAX     INTEGER  {
                 master(1),
                 slave(2) }
   ACCESS     read-only
   STATUS     mandatory
   DESCRIPTION
     "Indicates the exchange status for a neighbor entry."
::= { vrIpOspfNbrOperEntry 8 }

vrIpOspfNbrPermanence OBJECT-TYPE
   SYNTAX     INTEGER  {
                 dynamic(1),
                 permanent(2) }
   ACCESS     read-only
   STATUS     mandatory
   DESCRIPTION
     "This attribute displays how the neighbor became an entry."
   DEFVAL     { dynamic }
::= { vrIpOspfNbrOperEntry 11 }

-- 
-- *** THIS SUBTREE CURRENTLY NOT IMPLEMENTED ***
-- 

-- Vr/<string> Ip Ospf LsdbEntry/<Ip Address>,<Decimal>, 
-- <Ip Address>, <Ip Address>
-- This dynamic component contains the Link State Advertiements (LSA) 
-- from all areas the device is connected to.

vrIpOspfLsdb OBJECT IDENTIFIER ::= { vrIpOspf 11 }



vrIpOspfLsdbRowStatusTable OBJECT-TYPE
   SYNTAX     SEQUENCE OF VrIpOspfLsdbRowStatusEntry
   ACCESS     not-accessible
   STATUS     mandatory
   DESCRIPTION
     "*** THIS TABLE CURRENTLY NOT IMPLEMENTED ***

      This entry controls the addition and deletion of 
      vrIpOspfLsdb components."
::= { vrIpOspfLsdb 1 }

vrIpOspfLsdbRowStatusEntry OBJECT-TYPE
   SYNTAX     VrIpOspfLsdbRowStatusEntry
   ACCESS     not-accessible
   STATUS     mandatory
   DESCRIPTION
     "A single entry in the table represents a single 
      vrIpOspfLsdb component."
   INDEX {
      vrIndex,
      vrIpIndex,
      vrIpOspfIndex,
      vrIpOspfLsdbAreaIdIndex,
      vrIpOspfLsdbLsdbTypeIndex,
      vrIpOspfLsdbLsIdIndex,
      vrIpOspfLsdbRouterIdIndex }
::= { vrIpOspfLsdbRowStatusTable 1 }

VrIpOspfLsdbRowStatusEntry ::= SEQUENCE {
   vrIpOspfLsdbRowStatus
      RowStatus,
   vrIpOspfLsdbComponentName
      DisplayString,
   vrIpOspfLsdbStorageType
      StorageType,
   vrIpOspfLsdbAreaIdIndex
      IpAddress,
   vrIpOspfLsdbLsdbTypeIndex
      Integer32,
   vrIpOspfLsdbLsIdIndex
      IpAddress,
   vrIpOspfLsdbRouterIdIndex
      IpAddress }

vrIpOspfLsdbRowStatus OBJECT-TYPE
   SYNTAX     RowStatus 
   ACCESS     read-only
   STATUS     mandatory
   DESCRIPTION
     "This variable is used as the basis for SNMP naming of
      vrIpOspfLsdb components.
      These components cannot be added nor deleted."
::= { vrIpOspfLsdbRowStatusEntry 1 }

vrIpOspfLsdbComponentName OBJECT-TYPE
   SYNTAX     DisplayString 
   ACCESS     read-only
   STATUS     mandatory
   DESCRIPTION
     "This variable provides the component's string name for
      use with the ASCII Console Interface"
::= { vrIpOspfLsdbRowStatusEntry 2 }

vrIpOspfLsdbStorageType OBJECT-TYPE
   SYNTAX     StorageType 
   ACCESS     read-only
   STATUS     mandatory
   DESCRIPTION
     "This variable represents the storage type value for the
      vrIpOspfLsdb tables."
::= { vrIpOspfLsdbRowStatusEntry 4 }

vrIpOspfLsdbAreaIdIndex OBJECT-TYPE
   SYNTAX     IpAddress 
   ACCESS     not-accessible
   STATUS     mandatory
   DESCRIPTION
     "This variable represents an index for the vrIpOspfLsdb tables."
::= { vrIpOspfLsdbRowStatusEntry 10 }

vrIpOspfLsdbLsdbTypeIndex OBJECT-TYPE
   SYNTAX     Integer32 (1..7)
   ACCESS     not-accessible
   STATUS     mandatory
   DESCRIPTION
     "This variable represents an index for the vrIpOspfLsdb tables."
::= { vrIpOspfLsdbRowStatusEntry 11 }

vrIpOspfLsdbLsIdIndex OBJECT-TYPE
   SYNTAX     IpAddress 
   ACCESS     not-accessible
   STATUS     mandatory
   DESCRIPTION
     "This variable represents an index for the vrIpOspfLsdb tables."
::= { vrIpOspfLsdbRowStatusEntry 12 }

vrIpOspfLsdbRouterIdIndex OBJECT-TYPE
   SYNTAX     IpAddress 
   ACCESS     not-accessible
   STATUS     mandatory
   DESCRIPTION
     "This variable represents an index for the vrIpOspfLsdb tables."
::= { vrIpOspfLsdbRowStatusEntry 13 }

vrIpOspfLsdbOperTable OBJECT-TYPE
   SYNTAX     SEQUENCE OF VrIpOspfLsdbOperEntry
   ACCESS     not-accessible
   STATUS     mandatory
   DESCRIPTION
     "*** THIS TABLE CURRENTLY NOT IMPLEMENTED ***

      This group describes the Operational set of attributes for the LsdbEntry."
::= { vrIpOspfLsdb 10 }

vrIpOspfLsdbOperEntry OBJECT-TYPE
   SYNTAX     VrIpOspfLsdbOperEntry
   ACCESS     not-accessible
   STATUS     mandatory
   DESCRIPTION
     "An entry in the vrIpOspfLsdbOperTable."
   INDEX {
      vrIndex,
      vrIpIndex,
      vrIpOspfIndex,
      vrIpOspfLsdbAreaIdIndex,
      vrIpOspfLsdbLsdbTypeIndex,
      vrIpOspfLsdbLsIdIndex,
      vrIpOspfLsdbRouterIdIndex }
::= { vrIpOspfLsdbOperTable 1 }

VrIpOspfLsdbOperEntry ::= SEQUENCE {
   vrIpOspfLsdbSequence
      Unsigned32,
   vrIpOspfLsdbAge
      Gauge32,
   vrIpOspfLsdbChecksum
      Unsigned32,
   vrIpOspfLsdbAdvertisement
      HexString }

vrIpOspfLsdbSequence OBJECT-TYPE
   SYNTAX     Unsigned32 (0..4294967295)
   ACCESS     read-only
   STATUS     mandatory
   DESCRIPTION
     "A signed 32-bit integer, used to detect old and duplicate LSAs. The 
      space of sequence numbers is linearly ordered. The larger the sequence 
      number, the more recent the advertisement."
::= { vrIpOspfLsdbOperEntry 1 }

vrIpOspfLsdbAge OBJECT-TYPE
   SYNTAX     Gauge32 (0..3600)
   ACCESS     read-only
   STATUS     mandatory
   DESCRIPTION
     "The age of the Link State Advertisement in seconds."
::= { vrIpOspfLsdbOperEntry 2 }

vrIpOspfLsdbChecksum OBJECT-TYPE
   SYNTAX     Unsigned32 (0..4294967295)
   ACCESS     read-only
   STATUS     mandatory
   DESCRIPTION
     "The checksum of the complete contents of the advertisement, excepting 
      the age field. The checksum used is the Fletcher checksum."
::= { vrIpOspfLsdbOperEntry 3 }

vrIpOspfLsdbAdvertisement OBJECT-TYPE
   SYNTAX     HexString (SIZE (1..1024))
   ACCESS     read-only
   STATUS     mandatory
   DESCRIPTION
     "The entire LSA including its header."
::= { vrIpOspfLsdbOperEntry 4 }

-- 
-- *** THIS SUBTREE CURRENTLY NOT IMPLEMENTED ***
-- 

-- Vr/<string> Ip Ospf ExtLsdbEntry/<Decimal>, <Ip Address>, 
-- <Ip Address>
-- This dynamic component contains the Link State Advertiements(LSA) 
-- from other Autonomous systems. It is identical in format to the Lsdb. 
-- The purpose is to allow all external LSAs to be displayed together rather 
-- than distributed over the different non-stub areas.

vrIpOspfExtLsdb OBJECT IDENTIFIER ::= { vrIpOspf 12 }



vrIpOspfExtLsdbRowStatusTable OBJECT-TYPE
   SYNTAX     SEQUENCE OF VrIpOspfExtLsdbRowStatusEntry
   ACCESS     not-accessible
   STATUS     mandatory
   DESCRIPTION
     "*** THIS TABLE CURRENTLY NOT IMPLEMENTED ***

      This entry controls the addition and deletion of 
      vrIpOspfExtLsdb components."
::= { vrIpOspfExtLsdb 1 }

vrIpOspfExtLsdbRowStatusEntry OBJECT-TYPE
   SYNTAX     VrIpOspfExtLsdbRowStatusEntry
   ACCESS     not-accessible
   STATUS     mandatory
   DESCRIPTION
     "A single entry in the table represents a single 
      vrIpOspfExtLsdb component."
   INDEX {
      vrIndex,
      vrIpIndex,
      vrIpOspfIndex,
      vrIpOspfExtLsdbLsdbTypeIndex,
      vrIpOspfExtLsdbLsIdIndex,
      vrIpOspfExtLsdbRouterIdIndex }
::= { vrIpOspfExtLsdbRowStatusTable 1 }

VrIpOspfExtLsdbRowStatusEntry ::= SEQUENCE {
   vrIpOspfExtLsdbRowStatus
      RowStatus,
   vrIpOspfExtLsdbComponentName
      DisplayString,
   vrIpOspfExtLsdbStorageType
      StorageType,
   vrIpOspfExtLsdbLsdbTypeIndex
      Integer32,
   vrIpOspfExtLsdbLsIdIndex
      IpAddress,
   vrIpOspfExtLsdbRouterIdIndex
      IpAddress }

vrIpOspfExtLsdbRowStatus OBJECT-TYPE
   SYNTAX     RowStatus 
   ACCESS     read-only
   STATUS     mandatory
   DESCRIPTION
     "This variable is used as the basis for SNMP naming of
      vrIpOspfExtLsdb components.
      These components cannot be added nor deleted."
::= { vrIpOspfExtLsdbRowStatusEntry 1 }

vrIpOspfExtLsdbComponentName OBJECT-TYPE
   SYNTAX     DisplayString 
   ACCESS     read-only
   STATUS     mandatory
   DESCRIPTION
     "This variable provides the component's string name for
      use with the ASCII Console Interface"
::= { vrIpOspfExtLsdbRowStatusEntry 2 }

vrIpOspfExtLsdbStorageType OBJECT-TYPE
   SYNTAX     StorageType 
   ACCESS     read-only
   STATUS     mandatory
   DESCRIPTION
     "This variable represents the storage type value for the
      vrIpOspfExtLsdb tables."
::= { vrIpOspfExtLsdbRowStatusEntry 4 }

vrIpOspfExtLsdbLsdbTypeIndex OBJECT-TYPE
   SYNTAX     Integer32 (1..7)
   ACCESS     not-accessible
   STATUS     mandatory
   DESCRIPTION
     "This variable represents an index for the vrIpOspfExtLsdb tables."
::= { vrIpOspfExtLsdbRowStatusEntry 10 }

vrIpOspfExtLsdbLsIdIndex OBJECT-TYPE
   SYNTAX     IpAddress 
   ACCESS     not-accessible
   STATUS     mandatory
   DESCRIPTION
     "This variable represents an index for the vrIpOspfExtLsdb tables."
::= { vrIpOspfExtLsdbRowStatusEntry 11 }

vrIpOspfExtLsdbRouterIdIndex OBJECT-TYPE
   SYNTAX     IpAddress 
   ACCESS     not-accessible
   STATUS     mandatory
   DESCRIPTION
     "This variable represents an index for the vrIpOspfExtLsdb tables."
::= { vrIpOspfExtLsdbRowStatusEntry 12 }

vrIpOspfExtLsdbOperTable OBJECT-TYPE
   SYNTAX     SEQUENCE OF VrIpOspfExtLsdbOperEntry
   ACCESS     not-accessible
   STATUS     mandatory
   DESCRIPTION
     "*** THIS TABLE CURRENTLY NOT IMPLEMENTED ***

      This group describes the operational set of attributes 
      for the ExtLsdbEntry."
::= { vrIpOspfExtLsdb 10 }

vrIpOspfExtLsdbOperEntry OBJECT-TYPE
   SYNTAX     VrIpOspfExtLsdbOperEntry
   ACCESS     not-accessible
   STATUS     mandatory
   DESCRIPTION
     "An entry in the vrIpOspfExtLsdbOperTable."
   INDEX {
      vrIndex,
      vrIpIndex,
      vrIpOspfIndex,
      vrIpOspfExtLsdbLsdbTypeIndex,
      vrIpOspfExtLsdbLsIdIndex,
      vrIpOspfExtLsdbRouterIdIndex }
::= { vrIpOspfExtLsdbOperTable 1 }

VrIpOspfExtLsdbOperEntry ::= SEQUENCE {
   vrIpOspfExtLsdbSequence
      Unsigned32,
   vrIpOspfExtLsdbAge
      Gauge32,
   vrIpOspfExtLsdbChecksum
      Unsigned32,
   vrIpOspfExtLsdbAdvertisement
      HexString }

vrIpOspfExtLsdbSequence OBJECT-TYPE
   SYNTAX     Unsigned32 (0..4294967295)
   ACCESS     read-only
   STATUS     mandatory
   DESCRIPTION
     "A signed 32-bit integer, used to detect old and duplicate
      LSAs. The space of sequence numbers is linearly ordered. 
      The larger the sequence number, the more recent the 
      advertisement."
::= { vrIpOspfExtLsdbOperEntry 1 }

vrIpOspfExtLsdbAge OBJECT-TYPE
   SYNTAX     Gauge32 (0..3600)
   ACCESS     read-only
   STATUS     mandatory
   DESCRIPTION
     "The age of the Link State Advertisement in seconds."
::= { vrIpOspfExtLsdbOperEntry 2 }

vrIpOspfExtLsdbChecksum OBJECT-TYPE
   SYNTAX     Unsigned32 (0..4294967295)
   ACCESS     read-only
   STATUS     mandatory
   DESCRIPTION
     "The checksum of the complete contents of the 
      advertisement, excepting the age field. The checksum 
      used is the Fletcher checksum."
::= { vrIpOspfExtLsdbOperEntry 3 }

vrIpOspfExtLsdbAdvertisement OBJECT-TYPE
   SYNTAX     HexString (SIZE (1..36))
   ACCESS     read-only
   STATUS     mandatory
   DESCRIPTION
     "The entire LSA including its header."
::= { vrIpOspfExtLsdbOperEntry 4 }


-- Vr/<string> Ip Rip
-- This component represents the Routing Information Protocol for the IP.
-- There should be at least one RipInterface provisioned below a LogicalIf 
-- under an IpPort.

vrIpRip OBJECT IDENTIFIER ::= { vrIp 8 }



vrIpRipRowStatusTable OBJECT-TYPE
   SYNTAX     SEQUENCE OF VrIpRipRowStatusEntry
   ACCESS     not-accessible
   STATUS     mandatory
   DESCRIPTION
     "This entry controls the addition and deletion of 
      vrIpRip components."
::= { vrIpRip 1 }

vrIpRipRowStatusEntry OBJECT-TYPE
   SYNTAX     VrIpRipRowStatusEntry
   ACCESS     not-accessible
   STATUS     mandatory
   DESCRIPTION
     "A single entry in the table represents a single 
      vrIpRip component."
   INDEX {
      vrIndex,
      vrIpIndex,
      vrIpRipIndex }
::= { vrIpRipRowStatusTable 1 }

VrIpRipRowStatusEntry ::= SEQUENCE {
   vrIpRipRowStatus
      RowStatus,
   vrIpRipComponentName
      DisplayString,
   vrIpRipStorageType
      StorageType,
   vrIpRipIndex
      NonReplicated }

vrIpRipRowStatus OBJECT-TYPE
   SYNTAX     RowStatus 
   ACCESS     read-write
   STATUS     mandatory
   DESCRIPTION
     "This variable is used as the basis for SNMP naming of
      vrIpRip components.
      These components can be added and deleted."
::= { vrIpRipRowStatusEntry 1 }

vrIpRipComponentName OBJECT-TYPE
   SYNTAX     DisplayString 
   ACCESS     read-only
   STATUS     mandatory
   DESCRIPTION
     "This variable provides the component's string name for
      use with the ASCII Console Interface"
::= { vrIpRipRowStatusEntry 2 }

vrIpRipStorageType OBJECT-TYPE
   SYNTAX     StorageType 
   ACCESS     read-only
   STATUS     mandatory
   DESCRIPTION
     "This variable represents the storage type value for the
      vrIpRip tables."
::= { vrIpRipRowStatusEntry 4 }

vrIpRipIndex OBJECT-TYPE
   SYNTAX     NonReplicated 
   ACCESS     not-accessible
   STATUS     mandatory
   DESCRIPTION
     "This variable represents the index for the vrIpRip tables."
::= { vrIpRipRowStatusEntry 10 }

vrIpRipProvTable OBJECT-TYPE
   SYNTAX     SEQUENCE OF VrIpRipProvEntry
   ACCESS     not-accessible
   STATUS     mandatory
   DESCRIPTION
     "This group contains the provisionable attributes for the RIP component"
::= { vrIpRip 10 }

vrIpRipProvEntry OBJECT-TYPE
   SYNTAX     VrIpRipProvEntry
   ACCESS     not-accessible
   STATUS     mandatory
   DESCRIPTION
     "An entry in the vrIpRipProvTable."
   INDEX {
      vrIndex,
      vrIpIndex,
      vrIpRipIndex }
::= { vrIpRipProvTable 1 }

VrIpRipProvEntry ::= SEQUENCE {
   vrIpRipMigrateRip
      INTEGER,
   vrIpRipRfc1058MetricUsage
      INTEGER,
   vrIpRipGenerateDiscardRoute
      INTEGER,
   vrIpRipRipUpdate
      INTEGER,
   vrIpRipRipTimeout
      INTEGER,
   vrIpRipGarbageCollectTimer
      INTEGER }

vrIpRipMigrateRip OBJECT-TYPE
   SYNTAX     INTEGER  {
                 enabled(1),
                 disabled(2) }
   ACCESS     read-write
   STATUS     mandatory
   DESCRIPTION
     "This attribute sets the preference level of OSPF-internal routes to be less 
      preferred than RIP. 
      Note:
      This parameter should only be used when starting migration of network 
      from RIP to OSPF. When ready to cutover to OSPF, set this attribute 
      value to disabled and run under normal preferences. All OSPF routers in 
      the Autonomous System should be running with migrateRip enabled or 
      with migrateRip disabled to prevent routing loops. It is important that 
      the changeover period from RIP to OSPF be performed quickly on all 
      OSPF routers so that no routing loops are formed. These routing loops 
      could be caused by conflicts in the internal RIP and OSPF databases."
   DEFVAL     { disabled }
::= { vrIpRipProvEntry 2 }

vrIpRipRfc1058MetricUsage OBJECT-TYPE
   SYNTAX     INTEGER  {
                 enabled(1),
                 disabled(2) }
   ACCESS     read-write
   STATUS     mandatory
   DESCRIPTION
     "This attribute determines the metric usage for this RIP instance.
      This flag is used to determine the way metrics are incremented.
      RFC1058 way :
      Sending Update: This is to use the metric for the route from the routing 
      table as the advertised metric to be sent for that route. Nothing is ever 
      added to this value from the sending side. The only special case 
      handling is that if the route being advertised is the network route of a 
      directly connectednetwork, the metric in the routing table will be zero. 
      Then the RipIf interface metric for the interface being advertised is used 
      as the advertise metric. If the interface being advertised is not a Rip 
      interface, then metric value of 1 is used.
      Receiving Update: Add receiving interface's RIP metric to the metric for 
      the route in the received advertisement and install the result in the 
      receiver's routing table as the metric for that route.
      Older way:
      Sending Updates: Add the out going interfaces rip metric to the metric 
      for a route in the routing table to form the metric to be advertised for 
      that route.
      Receiving Updates: The metric received in the advertisement for a route 
      is put directly in the routing table as the metric for that route.
      
      Note: It is recommended that, all the routers in this autonomous system 
      should be following the rfc1058 metric system.
      Setting this flag to disabled will have the effect of running the RIP with 
      old metric incrementing system."
   DEFVAL     { enabled }
::= { vrIpRipProvEntry 3 }

vrIpRipGenerateDiscardRoute OBJECT-TYPE
   SYNTAX     INTEGER  {
                 yes(1),
                 no(2) }
   ACCESS     read-write
   STATUS     mandatory
   DESCRIPTION
     "This attribute when set to yes will add network disacrd routes to the 
      routing and forwarding table for the subnetted interfaces that are running 
      RIP."
   DEFVAL     { yes }
::= { vrIpRipProvEntry 4 }

vrIpRipRipUpdate OBJECT-TYPE
   SYNTAX     INTEGER (15..500)
   ACCESS     read-write
   STATUS     mandatory
   DESCRIPTION
     "This attribute sets the interval for sending updates bewteen RIP 
      neighbours. Set this attribute with a value less than that of the timeout 
      and garbage collect timers.  The ripUpdate timer starts when a route 
      comes up and when updates are received."
   DEFVAL     { 30 }
::= { vrIpRipProvEntry 5 }

vrIpRipRipTimeout OBJECT-TYPE
   SYNTAX     INTEGER (15..500)
   ACCESS     read-write
   STATUS     mandatory
   DESCRIPTION
     "This attribute sets the RIP timeout interval. If this timer expires, the 
      route is no longer valid. The ripTimeout timer starts when a route comes 
      up and when updates are received."
   DEFVAL     { 180 }
::= { vrIpRipProvEntry 6 }

vrIpRipGarbageCollectTimer OBJECT-TYPE
   SYNTAX     INTEGER (15..500)
   ACCESS     read-write
   STATUS     mandatory
   DESCRIPTION
     "This attribute sets the interval between a route's timeout expiring and the 
      deletion of that route's information from the routing table. The garbage 
      collect timer starts when the ripTimeout period expires."
   DEFVAL     { 120 }
::= { vrIpRipProvEntry 7 }

vrIpRipStateTable OBJECT-TYPE
   SYNTAX     SEQUENCE OF VrIpRipStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { vrIpRip 11 }

vrIpRipStateEntry OBJECT-TYPE
   SYNTAX     VrIpRipStateEntry
   ACCESS     not-accessible
   STATUS     mandatory
   DESCRIPTION
     "An entry in the vrIpRipStateTable."
   INDEX {
      vrIndex,
      vrIpIndex,
      vrIpRipIndex }
::= { vrIpRipStateTable 1 }

VrIpRipStateEntry ::= SEQUENCE {
   vrIpRipAdminState
      INTEGER,
   vrIpRipOperationalState
      INTEGER,
   vrIpRipUsageState
      INTEGER }

vrIpRipAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { vrIpRipStateEntry 1 }

vrIpRipOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { vrIpRipStateEntry 2 }

vrIpRipUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { vrIpRipStateEntry 3 }

vrIpRipAdminControlTable OBJECT-TYPE
   SYNTAX     SEQUENCE OF VrIpRipAdminControlEntry
   ACCESS     not-accessible
   STATUS     mandatory
   DESCRIPTION
     "This group includes the Administrative Control attribute. This 
      attribute defines the current administrative state of this component."
::= { vrIpRip 12 }

vrIpRipAdminControlEntry OBJECT-TYPE
   SYNTAX     VrIpRipAdminControlEntry
   ACCESS     not-accessible
   STATUS     mandatory
   DESCRIPTION
     "An entry in the vrIpRipAdminControlTable."
   INDEX {
      vrIndex,
      vrIpIndex,
      vrIpRipIndex }
::= { vrIpRipAdminControlTable 1 }

VrIpRipAdminControlEntry ::= SEQUENCE {
   vrIpRipSnmpAdminStatus
      INTEGER }

vrIpRipSnmpAdminStatus OBJECT-TYPE
   SYNTAX     INTEGER  {
                 up(1),
                 down(2),
                 testing(3) }
   ACCESS     read-write
   STATUS     mandatory
   DESCRIPTION
     "The desired state of the interface. The up state indicates the 
      interface is operational and packet forwarding is allowed. The down 
      state indicates the interface is not operational and packet forwarding 
      is unavailable. The testing state indicates that no operational 
      packets can be passed."
   DEFVAL     { up }
::= { vrIpRipAdminControlEntry 1 }

vrIpRipOperStatusTable OBJECT-TYPE
   SYNTAX     SEQUENCE OF VrIpRipOperStatusEntry
   ACCESS     not-accessible
   STATUS     mandatory
   DESCRIPTION
     "This group includes the Operational Status attribute. This attribute 
      defines the current operational state of this component."
::= { vrIpRip 15 }

vrIpRipOperStatusEntry OBJECT-TYPE
   SYNTAX     VrIpRipOperStatusEntry
   ACCESS     not-accessible
   STATUS     mandatory
   DESCRIPTION
     "An entry in the vrIpRipOperStatusTable."
   INDEX {
      vrIndex,
      vrIpIndex,
      vrIpRipIndex }
::= { vrIpRipOperStatusTable 1 }

VrIpRipOperStatusEntry ::= SEQUENCE {
   vrIpRipSnmpOperStatus
      INTEGER }

vrIpRipSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { vrIpRipOperStatusEntry 1 }

vrIpRipOperTable OBJECT-TYPE
   SYNTAX     SEQUENCE OF VrIpRipOperEntry
   ACCESS     not-accessible
   STATUS     mandatory
   DESCRIPTION
     "This group defines a set of operational attributes belonging to the RIP 
      component. It corresponds to the rip2Globals table in the RIP-2 standard 
      MIB."
::= { vrIpRip 16 }

vrIpRipOperEntry OBJECT-TYPE
   SYNTAX     VrIpRipOperEntry
   ACCESS     not-accessible
   STATUS     mandatory
   DESCRIPTION
     "An entry in the vrIpRipOperTable."
   INDEX {
      vrIndex,
      vrIpIndex,
      vrIpRipIndex }
::= { vrIpRipOperTable 1 }

VrIpRipOperEntry ::= SEQUENCE {
   vrIpRipRouteChangesMade
      Counter32,
   vrIpRipQueryResponses
      Counter32 }

vrIpRipRouteChangesMade OBJECT-TYPE
   SYNTAX     Counter32 
   ACCESS     read-only
   STATUS     mandatory
   DESCRIPTION
     "This attribute counts the route changes made to the IP Route Database 
      by Rip. This does not include the refresh of the route's age."
::= { vrIpRipOperEntry 1 }

vrIpRipQueryResponses OBJECT-TYPE
   SYNTAX     Counter32 
   ACCESS     read-only
   STATUS     mandatory
   DESCRIPTION
     "This attribute counts the responses sent to RIP queries from other 
      systems."
::= { vrIpRipOperEntry 2 }


-- Vr/<string> Ip Rip Import/<Decimal> 
-- This component controls the functionality of Route Leaking. In other 
-- words, this component will determine what routes are used by RIP.

vrIpRipImport OBJECT IDENTIFIER ::= { vrIpRip 2 }



vrIpRipImportRowStatusTable OBJECT-TYPE
   SYNTAX     SEQUENCE OF VrIpRipImportRowStatusEntry
   ACCESS     not-accessible
   STATUS     mandatory
   DESCRIPTION
     "This entry controls the addition and deletion of 
      vrIpRipImport components."
::= { vrIpRipImport 1 }

vrIpRipImportRowStatusEntry OBJECT-TYPE
   SYNTAX     VrIpRipImportRowStatusEntry
   ACCESS     not-accessible
   STATUS     mandatory
   DESCRIPTION
     "A single entry in the table represents a single 
      vrIpRipImport component."
   INDEX {
      vrIndex,
      vrIpIndex,
      vrIpRipIndex,
      vrIpRipImportIndex }
::= { vrIpRipImportRowStatusTable 1 }

VrIpRipImportRowStatusEntry ::= SEQUENCE {
   vrIpRipImportRowStatus
      RowStatus,
   vrIpRipImportComponentName
      DisplayString,
   vrIpRipImportStorageType
      StorageType,
   vrIpRipImportIndex
      Integer32 }

vrIpRipImportRowStatus OBJECT-TYPE
   SYNTAX     RowStatus 
   ACCESS     read-write
   STATUS     mandatory
   DESCRIPTION
     "This variable is used as the basis for SNMP naming of
      vrIpRipImport components.
      These components can be added and deleted."
::= { vrIpRipImportRowStatusEntry 1 }

vrIpRipImportComponentName OBJECT-TYPE
   SYNTAX     DisplayString 
   ACCESS     read-only
   STATUS     mandatory
   DESCRIPTION
     "This variable provides the component's string name for
      use with the ASCII Console Interface"
::= { vrIpRipImportRowStatusEntry 2 }

vrIpRipImportStorageType OBJECT-TYPE
   SYNTAX     StorageType 
   ACCESS     read-only
   STATUS     mandatory
   DESCRIPTION
     "This variable represents the storage type value for the
      vrIpRipImport tables."
::= { vrIpRipImportRowStatusEntry 4 }

vrIpRipImportIndex OBJECT-TYPE
   SYNTAX     Integer32 (0..65535)
   ACCESS     not-accessible
   STATUS     mandatory
   DESCRIPTION
     "This variable represents the index for the vrIpRipImport tables."
::= { vrIpRipImportRowStatusEntry 10 }

vrIpRipImportProvTable OBJECT-TYPE
   SYNTAX     SEQUENCE OF VrIpRipImportProvEntry
   ACCESS     not-accessible
   STATUS     mandatory
   DESCRIPTION
     "This is the group of provisionable attributes for the XXXX Import 
      Subcomponent."
::= { vrIpRipImport 10 }

vrIpRipImportProvEntry OBJECT-TYPE
   SYNTAX     VrIpRipImportProvEntry
   ACCESS     not-accessible
   STATUS     mandatory
   DESCRIPTION
     "An entry in the vrIpRipImportProvTable."
   INDEX {
      vrIndex,
      vrIpIndex,
      vrIpRipIndex,
      vrIpRipImportIndex }
::= { vrIpRipImportProvTable 1 }

VrIpRipImportProvEntry ::= SEQUENCE {
   vrIpRipImportUsageFlag
      INTEGER,
   vrIpRipImportImportMetric
      Unsigned32,
   vrIpRipImportNeighbor
      IpAddress,
   vrIpRipImportInterface
      IpAddress }

vrIpRipImportUsageFlag OBJECT-TYPE
   SYNTAX     INTEGER  {
                 use(1),
                 ignore(2) }
   ACCESS     read-write
   STATUS     mandatory
   DESCRIPTION
     "This flag when set to ignore indicates the routes that are not used and if 
      set to use, indicates the routes which are used."
   DEFVAL     { use }
::= { vrIpRipImportProvEntry 1 }

vrIpRipImportImportMetric OBJECT-TYPE
   SYNTAX     Unsigned32 (0..16)
   ACCESS     read-write
   STATUS     mandatory
   DESCRIPTION
     "This attribute is used to override the default import metric for the RIP 
      protocol. This value is not used to select which routes to use or ignore, 
      rather it is the metric to be used in the routing table for the routes 
      imported for this import policy. A value of zero indicates that the metric 
      received in the update will be used."
   DEFVAL     { 0 }
::= { vrIpRipImportProvEntry 2 }

vrIpRipImportNeighbor OBJECT-TYPE
   SYNTAX     IpAddress 
   ACCESS     read-write
   STATUS     mandatory
   DESCRIPTION
     "This attribute indicates the IP Address of the neighbor this policy will 
      apply to."
   DEFVAL     { '00000000'H }  -- "0.0.0.0"
::= { vrIpRipImportProvEntry 3 }

vrIpRipImportInterface OBJECT-TYPE
   SYNTAX     IpAddress 
   ACCESS     read-write
   STATUS     mandatory
   DESCRIPTION
     "This attribute specifies the RIP interface to which this import policy 
      applies.
      The value of 0.0.0.0 implies any RIP interface on the virtual router; 
      otherwise the value of this attribute must match the interface address of 
      a LogicalIf that has a RipIf on the same virtual router."
   DEFVAL     { '00000000'H }  -- "0.0.0.0"
::= { vrIpRipImportProvEntry 4 }


-- Vr/<string> Ip Rip Import/<Decimal> NetworkList/<Decimal>
-- This component identifies a set of networks that this Import policy will 
-- apply to.

vrIpRipImportNet OBJECT IDENTIFIER ::= { vrIpRipImport 2 }



vrIpRipImportNetRowStatusTable OBJECT-TYPE
   SYNTAX     SEQUENCE OF VrIpRipImportNetRowStatusEntry
   ACCESS     not-accessible
   STATUS     mandatory
   DESCRIPTION
     "This entry controls the addition and deletion of 
      vrIpRipImportNet components."
::= { vrIpRipImportNet 1 }

vrIpRipImportNetRowStatusEntry OBJECT-TYPE
   SYNTAX     VrIpRipImportNetRowStatusEntry
   ACCESS     not-accessible
   STATUS     mandatory
   DESCRIPTION
     "A single entry in the table represents a single 
      vrIpRipImportNet component."
   INDEX {
      vrIndex,
      vrIpIndex,
      vrIpRipIndex,
      vrIpRipImportIndex,
      vrIpRipImportNetIndex }
::= { vrIpRipImportNetRowStatusTable 1 }

VrIpRipImportNetRowStatusEntry ::= SEQUENCE {
   vrIpRipImportNetRowStatus
      RowStatus,
   vrIpRipImportNetComponentName
      DisplayString,
   vrIpRipImportNetStorageType
      StorageType,
   vrIpRipImportNetIndex
      Integer32 }

vrIpRipImportNetRowStatus OBJECT-TYPE
   SYNTAX     RowStatus 
   ACCESS     read-write
   STATUS     mandatory
   DESCRIPTION
     "This variable is used as the basis for SNMP naming of
      vrIpRipImportNet components.
      These components can be added and deleted."
::= { vrIpRipImportNetRowStatusEntry 1 }

vrIpRipImportNetComponentName OBJECT-TYPE
   SYNTAX     DisplayString 
   ACCESS     read-only
   STATUS     mandatory
   DESCRIPTION
     "This variable provides the component's string name for
      use with the ASCII Console Interface"
::= { vrIpRipImportNetRowStatusEntry 2 }

vrIpRipImportNetStorageType OBJECT-TYPE
   SYNTAX     StorageType 
   ACCESS     read-only
   STATUS     mandatory
   DESCRIPTION
     "This variable represents the storage type value for the
      vrIpRipImportNet tables."
::= { vrIpRipImportNetRowStatusEntry 4 }

vrIpRipImportNetIndex OBJECT-TYPE
   SYNTAX     Integer32 (0..65535)
   ACCESS     not-accessible
   STATUS     mandatory
   DESCRIPTION
     "This variable represents the index for the vrIpRipImportNet tables."
::= { vrIpRipImportNetRowStatusEntry 10 }

vrIpRipImportNetProvTable OBJECT-TYPE
   SYNTAX     SEQUENCE OF VrIpRipImportNetProvEntry
   ACCESS     not-accessible
   STATUS     mandatory
   DESCRIPTION
     "This group contains attributes for the XXXX NetworkList component 
      for the Import Policy to be applied to"
::= { vrIpRipImportNet 10 }

vrIpRipImportNetProvEntry OBJECT-TYPE
   SYNTAX     VrIpRipImportNetProvEntry
   ACCESS     not-accessible
   STATUS     mandatory
   DESCRIPTION
     "An entry in the vrIpRipImportNetProvTable."
   INDEX {
      vrIndex,
      vrIpIndex,
      vrIpRipIndex,
      vrIpRipImportIndex,
      vrIpRipImportNetIndex }
::= { vrIpRipImportNetProvTable 1 }

VrIpRipImportNetProvEntry ::= SEQUENCE {
   vrIpRipImportNetIpAddress
      IpAddress,
   vrIpRipImportNetIpMask
      IpAddress }

vrIpRipImportNetIpAddress OBJECT-TYPE
   SYNTAX     IpAddress 
   ACCESS     read-write
   STATUS     mandatory
   DESCRIPTION
     "This attribute specifies the IP address that needs to be matched against in 
      this network list for the Import Policy to be applied to."
::= { vrIpRipImportNetProvEntry 1 }

vrIpRipImportNetIpMask OBJECT-TYPE
   SYNTAX     IpAddress 
   ACCESS     read-write
   STATUS     mandatory
   DESCRIPTION
     "This attribute specifies the IP mask for the attribute ipAddress."
::= { vrIpRipImportNetProvEntry 2 }


-- Vr/<string> Ip Rip Export/<Decimal> 
-- Each instance of this component specifies a RIP export policy. A RIP 
-- export policy is used to decide if a route in the IP forwarding table 
-- should be blocked or advertised as a RIP route on one or all RIP 
-- interfaces of the virtual router.
-- Passport IP RIP by default advertises all local routes and all RIP learned 
-- routes to all RIP interfaces based on the metric in the IP forwarding 
-- table.

vrIpRipExport OBJECT IDENTIFIER ::= { vrIpRip 3 }



vrIpRipExportRowStatusTable OBJECT-TYPE
   SYNTAX     SEQUENCE OF VrIpRipExportRowStatusEntry
   ACCESS     not-accessible
   STATUS     mandatory
   DESCRIPTION
     "This entry controls the addition and deletion of 
      vrIpRipExport components."
::= { vrIpRipExport 1 }

vrIpRipExportRowStatusEntry OBJECT-TYPE
   SYNTAX     VrIpRipExportRowStatusEntry
   ACCESS     not-accessible
   STATUS     mandatory
   DESCRIPTION
     "A single entry in the table represents a single 
      vrIpRipExport component."
   INDEX {
      vrIndex,
      vrIpIndex,
      vrIpRipIndex,
      vrIpRipExportIndex }
::= { vrIpRipExportRowStatusTable 1 }

VrIpRipExportRowStatusEntry ::= SEQUENCE {
   vrIpRipExportRowStatus
      RowStatus,
   vrIpRipExportComponentName
      DisplayString,
   vrIpRipExportStorageType
      StorageType,
   vrIpRipExportIndex
      Integer32 }

vrIpRipExportRowStatus OBJECT-TYPE
   SYNTAX     RowStatus 
   ACCESS     read-write
   STATUS     mandatory
   DESCRIPTION
     "This variable is used as the basis for SNMP naming of
      vrIpRipExport components.
      These components can be added and deleted."
::= { vrIpRipExportRowStatusEntry 1 }

vrIpRipExportComponentName OBJECT-TYPE
   SYNTAX     DisplayString 
   ACCESS     read-only
   STATUS     mandatory
   DESCRIPTION
     "This variable provides the component's string name for
      use with the ASCII Console Interface"
::= { vrIpRipExportRowStatusEntry 2 }

vrIpRipExportStorageType OBJECT-TYPE
   SYNTAX     StorageType 
   ACCESS     read-only
   STATUS     mandatory
   DESCRIPTION
     "This variable represents the storage type value for the
      vrIpRipExport tables."
::= { vrIpRipExportRowStatusEntry 4 }

vrIpRipExportIndex OBJECT-TYPE
   SYNTAX     Integer32 (0..65535)
   ACCESS     not-accessible
   STATUS     mandatory
   DESCRIPTION
     "This variable represents the index for the vrIpRipExport tables."
::= { vrIpRipExportRowStatusEntry 10 }

vrIpRipExportProvTable OBJECT-TYPE
   SYNTAX     SEQUENCE OF VrIpRipExportProvEntry
   ACCESS     not-accessible
   STATUS     mandatory
   DESCRIPTION
     "This group contains all the provisioned attributes for the Export 
      component."
::= { vrIpRipExport 10 }

vrIpRipExportProvEntry OBJECT-TYPE
   SYNTAX     VrIpRipExportProvEntry
   ACCESS     not-accessible
   STATUS     mandatory
   DESCRIPTION
     "An entry in the vrIpRipExportProvTable."
   INDEX {
      vrIndex,
      vrIpIndex,
      vrIpRipIndex,
      vrIpRipExportIndex }
::= { vrIpRipExportProvTable 1 }

VrIpRipExportProvEntry ::= SEQUENCE {
   vrIpRipExportAdvertiseStatus
      INTEGER,
   vrIpRipExportExportMetric
      Unsigned32,
   vrIpRipExportProtocol
      INTEGER,
   vrIpRipExportRipInterface
      IpAddress,
   vrIpRipExportEgpAsId
      Unsigned32,
   vrIpRipExportOspfTag
      Unsigned32,
   vrIpRipExportOutInterface
      IpAddress,
   vrIpRipExportBgpAsId
      Unsigned32 }

vrIpRipExportAdvertiseStatus OBJECT-TYPE
   SYNTAX     INTEGER  {
                 send(1),
                 block(2) }
   ACCESS     read-write
   STATUS     mandatory
   DESCRIPTION
     "This attribute specifies if the routes that match this export policy are 
      advertised (send) or not advertised (block)."
   DEFVAL     { send }
::= { vrIpRipExportProvEntry 1 }

vrIpRipExportExportMetric OBJECT-TYPE
   SYNTAX     Unsigned32 (0..16)
   ACCESS     read-write
   STATUS     mandatory
   DESCRIPTION
     "This attribute specifies the metric to be used on the routes being 
      exported as a result of matching this export policy.
      If the attribute advertiseStatus is set to block, then the value of 
      exportMetric is ignored. The exportMetric value is not used to select 
      which routes to block or send, but rather the metric value advertised for 
      the routes.
      A value of 0 indicates that the metric associated with the route in the 
      forwarding table is used."
   DEFVAL     { 0 }
::= { vrIpRipExportProvEntry 2 }

vrIpRipExportProtocol OBJECT-TYPE
   SYNTAX     INTEGER  {
                 all(1),
                 egp(2),
                 rip(3),
                 ospfInternal(4),
                 ospfExternal(5),
                 staticLocal(6),
                 staticRemote(7),
                 bgpInternal(8),
                 bgpExternal(9) }
   ACCESS     read-write
   STATUS     mandatory
   DESCRIPTION
     "This attribute specifies the routes to which this export policy applies 
      based on the routing protocol of how the routes are learned. If it is set to 
      all, this export policy applies to all routes in the forwarding table."
   DEFVAL     { all }
::= { vrIpRipExportProvEntry 3 }

vrIpRipExportRipInterface OBJECT-TYPE
   SYNTAX     IpAddress 
   ACCESS     read-write
   STATUS     mandatory
   DESCRIPTION
     "This attribute specifies the RIP learned routes to which this export policy 
      applies, based on the RIP interface from which the routes are learned.
      This attribute can only be non zero when the protocol is set to rip. The 
      value of 0.0.0.0 implies any RIP interface on the same virtual router; 
      otherwise the value of this attribute must match the interface address of 
      a LogicalIf that has a RipIf on the same virtual router.
      DESCRIPTION"
   DEFVAL     { '00000000'H }  -- "0.0.0.0"
::= { vrIpRipExportProvEntry 4 }

vrIpRipExportEgpAsId OBJECT-TYPE
   SYNTAX     Unsigned32 (0..65536)
   ACCESS     read-write
   STATUS     mandatory
   DESCRIPTION
     "This attribute specifies the EGP learned routes to which this export 
      policy applies, based on the EGP autonomous system identifier of which 
      the routes are learned from.
      This attribute can only be non zero when protocol is set to egp. The 
      value of 0 implies any EGP autonomous system; otherwise the value of 
      this attribute must match the asId of an EGP neighbor on the same 
      virtual router."
   DEFVAL     { 0 }
::= { vrIpRipExportProvEntry 5 }

vrIpRipExportOspfTag OBJECT-TYPE
   SYNTAX     Unsigned32 (0..4294967295)
   ACCESS     read-write
   STATUS     mandatory
   DESCRIPTION
     "This attribute specifies the OSPF learned external routes to which this 
      export policy applies, based on the learned OSPF tag of the routes.
      This attribute can only be set to a non default value when protocol is set 
      to ospfExternal. The default value of 4294967295 implies any tag."
   DEFVAL     { 4294967295 }
::= { vrIpRipExportProvEntry 6 }

vrIpRipExportOutInterface OBJECT-TYPE
   SYNTAX     IpAddress 
   ACCESS     read-write
   STATUS     mandatory
   DESCRIPTION
     "This attribute specifies the RIP interface on the virtual router which 
      routes are exported onto as a result of matching this export policy.
      If the attribute advertiseStatus is set to block, then the value of 
      outInterface is ignored. The outInterface value is not used to select 
      which routes to block or send, but rather where to export the routes.
      A value of 0.0.0.0 indicates that the routes are exported to all RIP 
      interfaces on the virtual router. Otherwise, the value of this attribute 
      must match the interface address of a LogicalIf that has a RipIf on the 
      same virtual router."
   DEFVAL     { '00000000'H }  -- "0.0.0.0"
::= { vrIpRipExportProvEntry 7 }

vrIpRipExportBgpAsId OBJECT-TYPE
   SYNTAX     Unsigned32 (0..65535)
   ACCESS     read-write
   STATUS     mandatory
   DESCRIPTION
     "This key attribute specifies the BGP AS from which the routes are 
      learned. This key will be used only when the protocol is set to 
      bgpExternal. bgpAsId of 0 matches all BGP ASs."
   DEFVAL     { 0 }
::= { vrIpRipExportProvEntry 8 }


-- Vr/<string> Ip Rip Export/<Decimal> NetworkList/<Decimal>
-- This component identifies a set of attributes when matched determines 
-- the export policy applied. 

vrIpRipExportNet OBJECT IDENTIFIER ::= { vrIpRipExport 2 }



vrIpRipExportNetRowStatusTable OBJECT-TYPE
   SYNTAX     SEQUENCE OF VrIpRipExportNetRowStatusEntry
   ACCESS     not-accessible
   STATUS     mandatory
   DESCRIPTION
     "This entry controls the addition and deletion of 
      vrIpRipExportNet components."
::= { vrIpRipExportNet 1 }

vrIpRipExportNetRowStatusEntry OBJECT-TYPE
   SYNTAX     VrIpRipExportNetRowStatusEntry
   ACCESS     not-accessible
   STATUS     mandatory
   DESCRIPTION
     "A single entry in the table represents a single 
      vrIpRipExportNet component."
   INDEX {
      vrIndex,
      vrIpIndex,
      vrIpRipIndex,
      vrIpRipExportIndex,
      vrIpRipExportNetIndex }
::= { vrIpRipExportNetRowStatusTable 1 }

VrIpRipExportNetRowStatusEntry ::= SEQUENCE {
   vrIpRipExportNetRowStatus
      RowStatus,
   vrIpRipExportNetComponentName
      DisplayString,
   vrIpRipExportNetStorageType
      StorageType,
   vrIpRipExportNetIndex
      Integer32 }

vrIpRipExportNetRowStatus OBJECT-TYPE
   SYNTAX     RowStatus 
   ACCESS     read-write
   STATUS     mandatory
   DESCRIPTION
     "This variable is used as the basis for SNMP naming of
      vrIpRipExportNet components.
      These components can be added and deleted."
::= { vrIpRipExportNetRowStatusEntry 1 }

vrIpRipExportNetComponentName OBJECT-TYPE
   SYNTAX     DisplayString 
   ACCESS     read-only
   STATUS     mandatory
   DESCRIPTION
     "This variable provides the component's string name for
      use with the ASCII Console Interface"
::= { vrIpRipExportNetRowStatusEntry 2 }

vrIpRipExportNetStorageType OBJECT-TYPE
   SYNTAX     StorageType 
   ACCESS     read-only
   STATUS     mandatory
   DESCRIPTION
     "This variable represents the storage type value for the
      vrIpRipExportNet tables."
::= { vrIpRipExportNetRowStatusEntry 4 }

vrIpRipExportNetIndex OBJECT-TYPE
   SYNTAX     Integer32 (0..65535)
   ACCESS     not-accessible
   STATUS     mandatory
   DESCRIPTION
     "This variable represents the index for the vrIpRipExportNet tables."
::= { vrIpRipExportNetRowStatusEntry 10 }

vrIpRipExportNetProvTable OBJECT-TYPE
   SYNTAX     SEQUENCE OF VrIpRipExportNetProvEntry
   ACCESS     not-accessible
   STATUS     mandatory
   DESCRIPTION
     "This group identifies the set of Provisionable attributes for the 
      ExportNetworkList component."
::= { vrIpRipExportNet 10 }

vrIpRipExportNetProvEntry OBJECT-TYPE
   SYNTAX     VrIpRipExportNetProvEntry
   ACCESS     not-accessible
   STATUS     mandatory
   DESCRIPTION
     "An entry in the vrIpRipExportNetProvTable."
   INDEX {
      vrIndex,
      vrIpIndex,
      vrIpRipIndex,
      vrIpRipExportIndex,
      vrIpRipExportNetIndex }
::= { vrIpRipExportNetProvTable 1 }

VrIpRipExportNetProvEntry ::= SEQUENCE {
   vrIpRipExportNetIpAddress
      IpAddress,
   vrIpRipExportNetIpMask
      IpAddress }

vrIpRipExportNetIpAddress OBJECT-TYPE
   SYNTAX     IpAddress 
   ACCESS     read-write
   STATUS     mandatory
   DESCRIPTION
     "This attribute identifies the 32 bit IP address to match against."
::= { vrIpRipExportNetProvEntry 1 }

vrIpRipExportNetIpMask OBJECT-TYPE
   SYNTAX     IpAddress 
   ACCESS     read-write
   STATUS     mandatory
   DESCRIPTION
     "This attribute is the IP Mask to be used with the IP Address to match 
      against."
::= { vrIpRipExportNetProvEntry 2 }


-- Vr/<string> Ip Static
-- The Static component is used to configure addition, deletion and 
-- modification of static routing information.

vrIpStatic OBJECT IDENTIFIER ::= { vrIp 9 }



vrIpStaticRowStatusTable OBJECT-TYPE
   SYNTAX     SEQUENCE OF VrIpStaticRowStatusEntry
   ACCESS     not-accessible
   STATUS     mandatory
   DESCRIPTION
     "This entry controls the addition and deletion of 
      vrIpStatic components."
::= { vrIpStatic 1 }

vrIpStaticRowStatusEntry OBJECT-TYPE
   SYNTAX     VrIpStaticRowStatusEntry
   ACCESS     not-accessible
   STATUS     mandatory
   DESCRIPTION
     "A single entry in the table represents a single 
      vrIpStatic component."
   INDEX {
      vrIndex,
      vrIpIndex,
      vrIpStaticIndex }
::= { vrIpStaticRowStatusTable 1 }

VrIpStaticRowStatusEntry ::= SEQUENCE {
   vrIpStaticRowStatus
      RowStatus,
   vrIpStaticComponentName
      DisplayString,
   vrIpStaticStorageType
      StorageType,
   vrIpStaticIndex
      NonReplicated }

vrIpStaticRowStatus OBJECT-TYPE
   SYNTAX     RowStatus 
   ACCESS     read-write
   STATUS     mandatory
   DESCRIPTION
     "This variable is used as the basis for SNMP naming of
      vrIpStatic components.
      These components can be added and deleted."
::= { vrIpStaticRowStatusEntry 1 }

vrIpStaticComponentName OBJECT-TYPE
   SYNTAX     DisplayString 
   ACCESS     read-only
   STATUS     mandatory
   DESCRIPTION
     "This variable provides the component's string name for
      use with the ASCII Console Interface"
::= { vrIpStaticRowStatusEntry 2 }

vrIpStaticStorageType OBJECT-TYPE
   SYNTAX     StorageType 
   ACCESS     read-only
   STATUS     mandatory
   DESCRIPTION
     "This variable represents the storage type value for the
      vrIpStatic tables."
::= { vrIpStaticRowStatusEntry 4 }

vrIpStaticIndex OBJECT-TYPE
   SYNTAX     NonReplicated 
   ACCESS     not-accessible
   STATUS     mandatory
   DESCRIPTION
     "This variable represents the index for the vrIpStatic tables."
::= { vrIpStaticRowStatusEntry 10 }

vrIpStaticStateTable OBJECT-TYPE
   SYNTAX     SEQUENCE OF VrIpStaticStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { vrIpStatic 10 }

vrIpStaticStateEntry OBJECT-TYPE
   SYNTAX     VrIpStaticStateEntry
   ACCESS     not-accessible
   STATUS     mandatory
   DESCRIPTION
     "An entry in the vrIpStaticStateTable."
   INDEX {
      vrIndex,
      vrIpIndex,
      vrIpStaticIndex }
::= { vrIpStaticStateTable 1 }

VrIpStaticStateEntry ::= SEQUENCE {
   vrIpStaticAdminState
      INTEGER,
   vrIpStaticOperationalState
      INTEGER,
   vrIpStaticUsageState
      INTEGER }

vrIpStaticAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { vrIpStaticStateEntry 1 }

vrIpStaticOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { vrIpStaticStateEntry 2 }

vrIpStaticUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { vrIpStaticStateEntry 3 }


-- Vr/<string> Ip Static RouteEntry/<Ip Address>, <Ip Address>, 
-- <Decimal>
-- This component describes the IP static routes.
-- 
-- For a RouteEntry to be valid, there should be at least one NextHop 
-- provisioned. Up to three NextHops can be provisioned for each instance 
-- of a RouteEntry. 
-- 
-- The value of index destMask should be contiguous.
-- 
-- Only the value zero is supported. Zero will be substituted for any value 
-- that is entered.

vrIpStaticRoute OBJECT IDENTIFIER ::= { vrIpStatic 2 }



vrIpStaticRouteRowStatusTable OBJECT-TYPE
   SYNTAX     SEQUENCE OF VrIpStaticRouteRowStatusEntry
   ACCESS     not-accessible
   STATUS     mandatory
   DESCRIPTION
     "This entry controls the addition and deletion of 
      vrIpStaticRoute components."
::= { vrIpStaticRoute 1 }

vrIpStaticRouteRowStatusEntry OBJECT-TYPE
   SYNTAX     VrIpStaticRouteRowStatusEntry
   ACCESS     not-accessible
   STATUS     mandatory
   DESCRIPTION
     "A single entry in the table represents a single 
      vrIpStaticRoute component."
   INDEX {
      vrIndex,
      vrIpIndex,
      vrIpStaticIndex,
      vrIpStaticRouteDestAddressIndex,
      vrIpStaticRouteDestMaskIndex,
      vrIpStaticRouteTypeOfServiceIndex }
::= { vrIpStaticRouteRowStatusTable 1 }

VrIpStaticRouteRowStatusEntry ::= SEQUENCE {
   vrIpStaticRouteRowStatus
      RowStatus,
   vrIpStaticRouteComponentName
      DisplayString,
   vrIpStaticRouteStorageType
      StorageType,
   vrIpStaticRouteDestAddressIndex
      IpAddress,
   vrIpStaticRouteDestMaskIndex
      IpAddress,
   vrIpStaticRouteTypeOfServiceIndex
      Integer32 }

vrIpStaticRouteRowStatus OBJECT-TYPE
   SYNTAX     RowStatus 
   ACCESS     read-write
   STATUS     mandatory
   DESCRIPTION
     "This variable is used as the basis for SNMP naming of
      vrIpStaticRoute components.
      These components can be added and deleted."
::= { vrIpStaticRouteRowStatusEntry 1 }

vrIpStaticRouteComponentName OBJECT-TYPE
   SYNTAX     DisplayString 
   ACCESS     read-only
   STATUS     mandatory
   DESCRIPTION
     "This variable provides the component's string name for
      use with the ASCII Console Interface"
::= { vrIpStaticRouteRowStatusEntry 2 }

vrIpStaticRouteStorageType OBJECT-TYPE
   SYNTAX     StorageType 
   ACCESS     read-only
   STATUS     mandatory
   DESCRIPTION
     "This variable represents the storage type value for the
      vrIpStaticRoute tables."
::= { vrIpStaticRouteRowStatusEntry 4 }

vrIpStaticRouteDestAddressIndex OBJECT-TYPE
   SYNTAX     IpAddress 
   ACCESS     not-accessible
   STATUS     mandatory
   DESCRIPTION
     "This variable represents an index for the vrIpStaticRoute tables."
::= { vrIpStaticRouteRowStatusEntry 10 }

vrIpStaticRouteDestMaskIndex OBJECT-TYPE
   SYNTAX     IpAddress 
   ACCESS     not-accessible
   STATUS     mandatory
   DESCRIPTION
     "This variable represents an index for the vrIpStaticRoute tables."
::= { vrIpStaticRouteRowStatusEntry 11 }

vrIpStaticRouteTypeOfServiceIndex OBJECT-TYPE
   SYNTAX     Integer32 (0..0)
   ACCESS     not-accessible
   STATUS     mandatory
   DESCRIPTION
     "This variable represents an index for the vrIpStaticRoute tables."
::= { vrIpStaticRouteRowStatusEntry 12 }

vrIpStaticRouteProvTable OBJECT-TYPE
   SYNTAX     SEQUENCE OF VrIpStaticRouteProvEntry
   ACCESS     not-accessible
   STATUS     mandatory
   DESCRIPTION
     "This group contains a provisionable set of attributes for the static route 
      entry component."
::= { vrIpStaticRoute 10 }

vrIpStaticRouteProvEntry OBJECT-TYPE
   SYNTAX     VrIpStaticRouteProvEntry
   ACCESS     not-accessible
   STATUS     mandatory
   DESCRIPTION
     "An entry in the vrIpStaticRouteProvTable."
   INDEX {
      vrIndex,
      vrIpIndex,
      vrIpStaticIndex,
      vrIpStaticRouteDestAddressIndex,
      vrIpStaticRouteDestMaskIndex,
      vrIpStaticRouteTypeOfServiceIndex }
::= { vrIpStaticRouteProvTable 1 }

VrIpStaticRouteProvEntry ::= SEQUENCE {
   vrIpStaticRoutePreferredOver
      INTEGER }

vrIpStaticRoutePreferredOver OBJECT-TYPE
   SYNTAX     INTEGER  {
                 intOspf(5),
                 extOspf(72) }
   ACCESS     read-write
   STATUS     mandatory
   DESCRIPTION
     "This attribute indicates the preference of the static route in comparison 
      with the OSPF route. intOspf means that the static route is chosen over 
      the OSPF internal route, while extOspf means that the OSPF internal 
      route is chosen over the static route. The default static route preference 
      is set to extOspf ."
   DEFVAL     { extOspf }
::= { vrIpStaticRouteProvEntry 12 }


-- Vr/<string> Ip Static Route/<Ip Address>,<Ip Address>,<Decimal> 
-- NextHop/<Ip Address>
-- This component provides the destination Ip address of the NextHop 
-- (some times referred to as the Gateway). 
-- 
-- For a RouteEntry to be valid, there should be at least one NextHop 
-- provisioned. Up to three NextHops can be provisioned for each instance 
-- of a RouteEntry.
-- 
-- Each provisioned NextHop address should belong to a valid subnet.
-- A valid subnet for this IP entity can be provisioned as a logicalIf Entry 
-- under an IpPort.

vrIpStaticRouteNh OBJECT IDENTIFIER ::= { vrIpStaticRoute 2 }



vrIpStaticRouteNhRowStatusTable OBJECT-TYPE
   SYNTAX     SEQUENCE OF VrIpStaticRouteNhRowStatusEntry
   ACCESS     not-accessible
   STATUS     mandatory
   DESCRIPTION
     "This entry controls the addition and deletion of 
      vrIpStaticRouteNh components."
::= { vrIpStaticRouteNh 1 }

vrIpStaticRouteNhRowStatusEntry OBJECT-TYPE
   SYNTAX     VrIpStaticRouteNhRowStatusEntry
   ACCESS     not-accessible
   STATUS     mandatory
   DESCRIPTION
     "A single entry in the table represents a single 
      vrIpStaticRouteNh component."
   INDEX {
      vrIndex,
      vrIpIndex,
      vrIpStaticIndex,
      vrIpStaticRouteDestAddressIndex,
      vrIpStaticRouteDestMaskIndex,
      vrIpStaticRouteTypeOfServiceIndex,
      vrIpStaticRouteNhIndex }
::= { vrIpStaticRouteNhRowStatusTable 1 }

VrIpStaticRouteNhRowStatusEntry ::= SEQUENCE {
   vrIpStaticRouteNhRowStatus
      RowStatus,
   vrIpStaticRouteNhComponentName
      DisplayString,
   vrIpStaticRouteNhStorageType
      StorageType,
   vrIpStaticRouteNhIndex
      IpAddress }

vrIpStaticRouteNhRowStatus OBJECT-TYPE
   SYNTAX     RowStatus 
   ACCESS     read-write
   STATUS     mandatory
   DESCRIPTION
     "This variable is used as the basis for SNMP naming of
      vrIpStaticRouteNh components.
      These components can be added and deleted."
::= { vrIpStaticRouteNhRowStatusEntry 1 }

vrIpStaticRouteNhComponentName OBJECT-TYPE
   SYNTAX     DisplayString 
   ACCESS     read-only
   STATUS     mandatory
   DESCRIPTION
     "This variable provides the component's string name for
      use with the ASCII Console Interface"
::= { vrIpStaticRouteNhRowStatusEntry 2 }

vrIpStaticRouteNhStorageType OBJECT-TYPE
   SYNTAX     StorageType 
   ACCESS     read-only
   STATUS     mandatory
   DESCRIPTION
     "This variable represents the storage type value for the
      vrIpStaticRouteNh tables."
::= { vrIpStaticRouteNhRowStatusEntry 4 }

vrIpStaticRouteNhIndex OBJECT-TYPE
   SYNTAX     IpAddress 
   ACCESS     not-accessible
   STATUS     mandatory
   DESCRIPTION
     "This variable represents the index for the vrIpStaticRouteNh tables."
::= { vrIpStaticRouteNhRowStatusEntry 10 }

vrIpStaticRouteNhProvTable OBJECT-TYPE
   SYNTAX     SEQUENCE OF VrIpStaticRouteNhProvEntry
   ACCESS     not-accessible
   STATUS     mandatory
   DESCRIPTION
     "This group contains a provisionable set of attributes for the Static 
      RouteEntry NextHop component."
::= { vrIpStaticRouteNh 10 }

vrIpStaticRouteNhProvEntry OBJECT-TYPE
   SYNTAX     VrIpStaticRouteNhProvEntry
   ACCESS     not-accessible
   STATUS     mandatory
   DESCRIPTION
     "An entry in the vrIpStaticRouteNhProvTable."
   INDEX {
      vrIndex,
      vrIpIndex,
      vrIpStaticIndex,
      vrIpStaticRouteDestAddressIndex,
      vrIpStaticRouteDestMaskIndex,
      vrIpStaticRouteTypeOfServiceIndex,
      vrIpStaticRouteNhIndex }
::= { vrIpStaticRouteNhProvTable 1 }

VrIpStaticRouteNhProvEntry ::= SEQUENCE {
   vrIpStaticRouteNhMetric
      INTEGER }

vrIpStaticRouteNhMetric OBJECT-TYPE
   SYNTAX     INTEGER (-1..65535)
   ACCESS     read-write
   STATUS     mandatory
   DESCRIPTION
     "This attribute specifies the primary routing metric for this NextHop."
   DEFVAL     { 1 }
::= { vrIpStaticRouteNhProvEntry 1 }


-- Vr/<string> Ip Static DiscardRouteEntry/<Ip Address>,<Ip Address>
-- This table identifies invalid martian networks. Forwarding of packets to 
-- the network address indicated by this entry will be discarded. 

vrIpStaticDiscard OBJECT IDENTIFIER ::= { vrIpStatic 3 }



vrIpStaticDiscardRowStatusTable OBJECT-TYPE
   SYNTAX     SEQUENCE OF VrIpStaticDiscardRowStatusEntry
   ACCESS     not-accessible
   STATUS     mandatory
   DESCRIPTION
     "This entry controls the addition and deletion of 
      vrIpStaticDiscard components."
::= { vrIpStaticDiscard 1 }

vrIpStaticDiscardRowStatusEntry OBJECT-TYPE
   SYNTAX     VrIpStaticDiscardRowStatusEntry
   ACCESS     not-accessible
   STATUS     mandatory
   DESCRIPTION
     "A single entry in the table represents a single 
      vrIpStaticDiscard component."
   INDEX {
      vrIndex,
      vrIpIndex,
      vrIpStaticIndex,
      vrIpStaticDiscardDestAddressIndex,
      vrIpStaticDiscardDestMaskIndex }
::= { vrIpStaticDiscardRowStatusTable 1 }

VrIpStaticDiscardRowStatusEntry ::= SEQUENCE {
   vrIpStaticDiscardRowStatus
      RowStatus,
   vrIpStaticDiscardComponentName
      DisplayString,
   vrIpStaticDiscardStorageType
      StorageType,
   vrIpStaticDiscardDestAddressIndex
      IpAddress,
   vrIpStaticDiscardDestMaskIndex
      IpAddress }

vrIpStaticDiscardRowStatus OBJECT-TYPE
   SYNTAX     RowStatus 
   ACCESS     read-write
   STATUS     mandatory
   DESCRIPTION
     "This variable is used as the basis for SNMP naming of
      vrIpStaticDiscard components.
      These components can be added and deleted."
::= { vrIpStaticDiscardRowStatusEntry 1 }

vrIpStaticDiscardComponentName OBJECT-TYPE
   SYNTAX     DisplayString 
   ACCESS     read-only
   STATUS     mandatory
   DESCRIPTION
     "This variable provides the component's string name for
      use with the ASCII Console Interface"
::= { vrIpStaticDiscardRowStatusEntry 2 }

vrIpStaticDiscardStorageType OBJECT-TYPE
   SYNTAX     StorageType 
   ACCESS     read-only
   STATUS     mandatory
   DESCRIPTION
     "This variable represents the storage type value for the
      vrIpStaticDiscard tables."
::= { vrIpStaticDiscardRowStatusEntry 4 }

vrIpStaticDiscardDestAddressIndex OBJECT-TYPE
   SYNTAX     IpAddress 
   ACCESS     not-accessible
   STATUS     mandatory
   DESCRIPTION
     "This variable represents an index for the vrIpStaticDiscard tables."
::= { vrIpStaticDiscardRowStatusEntry 10 }

vrIpStaticDiscardDestMaskIndex OBJECT-TYPE
   SYNTAX     IpAddress 
   ACCESS     not-accessible
   STATUS     mandatory
   DESCRIPTION
     "This variable represents an index for the vrIpStaticDiscard tables."
::= { vrIpStaticDiscardRowStatusEntry 11 }


-- Vr/<string Ip NetSentry 
-- NetSentry defines a set of filters which are compiled by the 
-- NetSentry process to be applied to all IP packets. IP packets can 
-- be filtered based on IP address and netmask combinations.

vrIpNs OBJECT IDENTIFIER ::= { vrIp 10 }



vrIpNsRowStatusTable OBJECT-TYPE
   SYNTAX     SEQUENCE OF VrIpNsRowStatusEntry
   ACCESS     not-accessible
   STATUS     mandatory
   DESCRIPTION
     "This entry controls the addition and deletion of 
      vrIpNs components."
::= { vrIpNs 1 }

vrIpNsRowStatusEntry OBJECT-TYPE
   SYNTAX     VrIpNsRowStatusEntry
   ACCESS     not-accessible
   STATUS     mandatory
   DESCRIPTION
     "A single entry in the table represents a single 
      vrIpNs component."
   INDEX {
      vrIndex,
      vrIpIndex,
      vrIpNsIndex }
::= { vrIpNsRowStatusTable 1 }

VrIpNsRowStatusEntry ::= SEQUENCE {
   vrIpNsRowStatus
      RowStatus,
   vrIpNsComponentName
      DisplayString,
   vrIpNsStorageType
      StorageType,
   vrIpNsIndex
      NonReplicated }

vrIpNsRowStatus OBJECT-TYPE
   SYNTAX     RowStatus 
   ACCESS     read-write
   STATUS     mandatory
   DESCRIPTION
     "This variable is used as the basis for SNMP naming of
      vrIpNs components.
      These components can be added and deleted."
::= { vrIpNsRowStatusEntry 1 }

vrIpNsComponentName OBJECT-TYPE
   SYNTAX     DisplayString 
   ACCESS     read-only
   STATUS     mandatory
   DESCRIPTION
     "This variable provides the component's string name for
      use with the ASCII Console Interface"
::= { vrIpNsRowStatusEntry 2 }

vrIpNsStorageType OBJECT-TYPE
   SYNTAX     StorageType 
   ACCESS     read-only
   STATUS     mandatory
   DESCRIPTION
     "This variable represents the storage type value for the
      vrIpNs tables."
::= { vrIpNsRowStatusEntry 4 }

vrIpNsIndex OBJECT-TYPE
   SYNTAX     NonReplicated 
   ACCESS     not-accessible
   STATUS     mandatory
   DESCRIPTION
     "This variable represents the index for the vrIpNs tables."
::= { vrIpNsRowStatusEntry 10 }

vrIpNsProvTable OBJECT-TYPE
   SYNTAX     SEQUENCE OF VrIpNsProvEntry
   ACCESS     not-accessible
   STATUS     mandatory
   DESCRIPTION
     "This group contains provisionable attributes for the NetSentry 
      component."
::= { vrIpNs 10 }

vrIpNsProvEntry OBJECT-TYPE
   SYNTAX     VrIpNsProvEntry
   ACCESS     not-accessible
   STATUS     mandatory
   DESCRIPTION
     "An entry in the vrIpNsProvTable."
   INDEX {
      vrIndex,
      vrIpIndex,
      vrIpNsIndex }
::= { vrIpNsProvTable 1 }

VrIpNsProvEntry ::= SEQUENCE {
   vrIpNsFirstFilter
      AsciiString,
   vrIpNsLocalInFilter
      AsciiString,
   vrIpNsLocalOutFilter
      AsciiString,
   vrIpNsLastFilter
      AsciiString }

vrIpNsFirstFilter OBJECT-TYPE
   SYNTAX     AsciiString (SIZE (0..32))
   ACCESS     read-write
   STATUS     mandatory
   DESCRIPTION
     "The firstFilter is the first filter point which affects all IP packets before 
      they have been examined in any way for their origin and destination. 
      The most common use of a firstFilter point is to collect statistis for all 
      packets arriving at the route on any interface, before any subsequent 
      filter processing changes their direction or disposition."
::= { vrIpNsProvEntry 1 }

vrIpNsLocalInFilter OBJECT-TYPE
   SYNTAX     AsciiString (SIZE (0..32))
   ACCESS     read-write
   STATUS     mandatory
   DESCRIPTION
     "The localInFilter is the second filter point which uses by network 
      administrator to perform a common action on all IP packets that 
      physically arrive over a specific logical interface, regardless of the 
      packet's stated source or destination. Typical uses for a localInFilter 
      include verifying that known Ethernet media source addresses match 
      known IP addresses, or confirming that the IP packet source addresses of 
      received IP packet fall within a narrow range."
::= { vrIpNsProvEntry 2 }

vrIpNsLocalOutFilter OBJECT-TYPE
   SYNTAX     AsciiString (SIZE (0..32))
   ACCESS     read-write
   STATUS     mandatory
   DESCRIPTION
     "The localOutFilter is the third filter point which applies to any IP packet 
      that will be transmitted from the router to the medium associated with 
      the interface, regardless of its source, destination, or what type of 
      decision was made to cause the datagram to be transmitted on this 
      interface. localOutFilter generally used to ensure that certain paterns of 
      traffic do not enter the network or reach a second IP router on that 
      network. For example, localOutFilter can be used as the exclusion of all 
      IP packets above a certain security classification, or collecting statistics 
      on the amount of IP fragments performed on an outgoing interface."
::= { vrIpNsProvEntry 3 }

vrIpNsLastFilter OBJECT-TYPE
   SYNTAX     AsciiString (SIZE (0..32))
   ACCESS     read-write
   STATUS     mandatory
   DESCRIPTION
     "lastFilter is the fourth and last filter point to be excecuted after all other 
      routing and filtering decisions have been made on the IP packet, and 
      transmission of the information is imminent. lastFilter is generally used 
      to collect statistics on traffic after all previous control and routing 
      decisions have been made."
::= { vrIpNsProvEntry 4 }


-- Vr/<string> Ip NetSentry ApplyEntry/<Decimal>
-- This component contains a list of NetSentry filters that can be applied to 
-- IP packets and information pertaining to each application of such 
-- NetSentry filters.

vrIpNsApply OBJECT IDENTIFIER ::= { vrIpNs 2 }



vrIpNsApplyRowStatusTable OBJECT-TYPE
   SYNTAX     SEQUENCE OF VrIpNsApplyRowStatusEntry
   ACCESS     not-accessible
   STATUS     mandatory
   DESCRIPTION
     "This entry controls the addition and deletion of 
      vrIpNsApply components."
::= { vrIpNsApply 1 }

vrIpNsApplyRowStatusEntry OBJECT-TYPE
   SYNTAX     VrIpNsApplyRowStatusEntry
   ACCESS     not-accessible
   STATUS     mandatory
   DESCRIPTION
     "A single entry in the table represents a single 
      vrIpNsApply component."
   INDEX {
      vrIndex,
      vrIpIndex,
      vrIpNsIndex,
      vrIpNsApplyIndex }
::= { vrIpNsApplyRowStatusTable 1 }

VrIpNsApplyRowStatusEntry ::= SEQUENCE {
   vrIpNsApplyRowStatus
      RowStatus,
   vrIpNsApplyComponentName
      DisplayString,
   vrIpNsApplyStorageType
      StorageType,
   vrIpNsApplyIndex
      Integer32 }

vrIpNsApplyRowStatus OBJECT-TYPE
   SYNTAX     RowStatus 
   ACCESS     read-write
   STATUS     mandatory
   DESCRIPTION
     "This variable is used as the basis for SNMP naming of
      vrIpNsApply components.
      These components can be added and deleted."
::= { vrIpNsApplyRowStatusEntry 1 }

vrIpNsApplyComponentName OBJECT-TYPE
   SYNTAX     DisplayString 
   ACCESS     read-only
   STATUS     mandatory
   DESCRIPTION
     "This variable provides the component's string name for
      use with the ASCII Console Interface"
::= { vrIpNsApplyRowStatusEntry 2 }

vrIpNsApplyStorageType OBJECT-TYPE
   SYNTAX     StorageType 
   ACCESS     read-only
   STATUS     mandatory
   DESCRIPTION
     "This variable represents the storage type value for the
      vrIpNsApply tables."
::= { vrIpNsApplyRowStatusEntry 4 }

vrIpNsApplyIndex OBJECT-TYPE
   SYNTAX     Integer32 (1..65535)
   ACCESS     not-accessible
   STATUS     mandatory
   DESCRIPTION
     "This variable represents the index for the vrIpNsApply tables."
::= { vrIpNsApplyRowStatusEntry 10 }

vrIpNsApplyProvisionedTable OBJECT-TYPE
   SYNTAX     SEQUENCE OF VrIpNsApplyProvisionedEntry
   ACCESS     not-accessible
   STATUS     mandatory
   DESCRIPTION
     "The instance of provisioned information relating to a filter application to 
      IP packet."
::= { vrIpNsApply 10 }

vrIpNsApplyProvisionedEntry OBJECT-TYPE
   SYNTAX     VrIpNsApplyProvisionedEntry
   ACCESS     not-accessible
   STATUS     mandatory
   DESCRIPTION
     "An entry in the vrIpNsApplyProvisionedTable."
   INDEX {
      vrIndex,
      vrIpIndex,
      vrIpNsIndex,
      vrIpNsApplyIndex }
::= { vrIpNsApplyProvisionedTable 1 }

VrIpNsApplyProvisionedEntry ::= SEQUENCE {
   vrIpNsApplyFilter
      AsciiString,
   vrIpNsApplyIpAddress1
      IpAddress,
   vrIpNsApplyIpMask1
      IpAddress,
   vrIpNsApplyIpAddress2
      IpAddress,
   vrIpNsApplyIpMask2
      IpAddress,
   vrIpNsApplyDirection
      INTEGER }

vrIpNsApplyFilter OBJECT-TYPE
   SYNTAX     AsciiString (SIZE (0..32))
   ACCESS     read-write
   STATUS     mandatory
   DESCRIPTION
     "The name of the filter to be applied to packet matching the 
      conditions in this entry."
::= { vrIpNsApplyProvisionedEntry 1 }

vrIpNsApplyIpAddress1 OBJECT-TYPE
   SYNTAX     IpAddress 
   ACCESS     read-write
   STATUS     mandatory
   DESCRIPTION
     "The first IP address used to compare."
::= { vrIpNsApplyProvisionedEntry 2 }

vrIpNsApplyIpMask1 OBJECT-TYPE
   SYNTAX     IpAddress 
   ACCESS     read-write
   STATUS     mandatory
   DESCRIPTION
     "The first netmask associated with ipAddress1 used to compare."
::= { vrIpNsApplyProvisionedEntry 3 }

vrIpNsApplyIpAddress2 OBJECT-TYPE
   SYNTAX     IpAddress 
   ACCESS     read-write
   STATUS     mandatory
   DESCRIPTION
     "This second IP address used to compare."
::= { vrIpNsApplyProvisionedEntry 4 }

vrIpNsApplyIpMask2 OBJECT-TYPE
   SYNTAX     IpAddress 
   ACCESS     read-write
   STATUS     mandatory
   DESCRIPTION
     "This second netmask associated with ipAddress2 used to compare."
::= { vrIpNsApplyProvisionedEntry 5 }

vrIpNsApplyDirection OBJECT-TYPE
   SYNTAX     INTEGER  {
                 to(1),
                 from(2),
                 tofrom(3) }
   ACCESS     read-write
   STATUS     mandatory
   DESCRIPTION
     "Indicates the direction a packet must be moving between the first and 
      second apply list entries in order for the entries to match. First 'to' 
      second, first 'from' second, or first 'tofrom' second (either direction)."
   DEFVAL     { tofrom }
::= { vrIpNsApplyProvisionedEntry 6 }


-- Vr/<string> Ip Arp
-- The component specifies the Address Resolution Protocol.

vrIpArp OBJECT IDENTIFIER ::= { vrIp 11 }



vrIpArpRowStatusTable OBJECT-TYPE
   SYNTAX     SEQUENCE OF VrIpArpRowStatusEntry
   ACCESS     not-accessible
   STATUS     mandatory
   DESCRIPTION
     "This entry controls the addition and deletion of 
      vrIpArp components."
::= { vrIpArp 1 }

vrIpArpRowStatusEntry OBJECT-TYPE
   SYNTAX     VrIpArpRowStatusEntry
   ACCESS     not-accessible
   STATUS     mandatory
   DESCRIPTION
     "A single entry in the table represents a single 
      vrIpArp component."
   INDEX {
      vrIndex,
      vrIpIndex,
      vrIpArpIndex }
::= { vrIpArpRowStatusTable 1 }

VrIpArpRowStatusEntry ::= SEQUENCE {
   vrIpArpRowStatus
      RowStatus,
   vrIpArpComponentName
      DisplayString,
   vrIpArpStorageType
      StorageType,
   vrIpArpIndex
      NonReplicated }

vrIpArpRowStatus OBJECT-TYPE
   SYNTAX     RowStatus 
   ACCESS     read-only
   STATUS     mandatory
   DESCRIPTION
     "This variable is used as the basis for SNMP naming of
      vrIpArp components.
      These components cannot be added nor deleted."
::= { vrIpArpRowStatusEntry 1 }

vrIpArpComponentName OBJECT-TYPE
   SYNTAX     DisplayString 
   ACCESS     read-only
   STATUS     mandatory
   DESCRIPTION
     "This variable provides the component's string name for
      use with the ASCII Console Interface"
::= { vrIpArpRowStatusEntry 2 }

vrIpArpStorageType OBJECT-TYPE
   SYNTAX     StorageType 
   ACCESS     read-only
   STATUS     mandatory
   DESCRIPTION
     "This variable represents the storage type value for the
      vrIpArp tables."
::= { vrIpArpRowStatusEntry 4 }

vrIpArpIndex OBJECT-TYPE
   SYNTAX     NonReplicated 
   ACCESS     not-accessible
   STATUS     mandatory
   DESCRIPTION
     "This variable represents the index for the vrIpArp tables."
::= { vrIpArpRowStatusEntry 10 }

vrIpArpProvTable OBJECT-TYPE
   SYNTAX     SEQUENCE OF VrIpArpProvEntry
   ACCESS     not-accessible
   STATUS     mandatory
   DESCRIPTION
     "The ARP refresh feature allows the router to periodically verify ARP 
      table entries. Whenever the router updates an ARP entry, or creates a 
      new entry, a timeout value is assigned to the entry. When the timeout for 
      an entry expires, the router will send a unicast ARP request to the 
      currently-known physical address. If an ARP response comes back, the 
      entry will be assigned a new timeout. If, however, the host has gone 
      away or been assigned a new physical address, the host will not respond 
      to the unicast ARP, and the entry will be removed from the ARP table. 
      The new physical address will be discovered through the normal ARP 
      mechanism when the next communication is attempted to the host."
::= { vrIpArp 10 }

vrIpArpProvEntry OBJECT-TYPE
   SYNTAX     VrIpArpProvEntry
   ACCESS     not-accessible
   STATUS     mandatory
   DESCRIPTION
     "An entry in the vrIpArpProvTable."
   INDEX {
      vrIndex,
      vrIpIndex,
      vrIpArpIndex }
::= { vrIpArpProvTable 1 }

VrIpArpProvEntry ::= SEQUENCE {
   vrIpArpAutoRefresh
      INTEGER,
   vrIpArpAutoRefreshTimeout
      Unsigned32 }

vrIpArpAutoRefresh OBJECT-TYPE
   SYNTAX     INTEGER  {
                 enabled(1),
                 disabled(2) }
   ACCESS     read-write
   STATUS     mandatory
   DESCRIPTION
     "This attribute is used to enable or disable the ARP refresh feature."
   DEFVAL     { disabled }
::= { vrIpArpProvEntry 1 }

vrIpArpAutoRefreshTimeout OBJECT-TYPE
   SYNTAX     Unsigned32 (1..1440)
   ACCESS     read-write
   STATUS     mandatory
   DESCRIPTION
     "This attribute defines the timeout value, in minutes, which is assigned to 
      updated ARP entries, or newly created ARP entries. The range for the 
      timeout is 1 minute to 1440 minutes (24 hours)."
   DEFVAL     { 5 }
::= { vrIpArpProvEntry 2 }


-- Vr/<string> Ip Arp HostEntry/<Ip Address>
-- This component defines a static host entry in the Arp table.
-- Each static host entry is assigned Class of Service (CoS) 0 when the 
-- associated media type is one where CoS can be specifed on a per virtual 
-- circuit basis (eg. frameRelayDte or atmMpe). For other media types, the 
-- CoS value notApplicable (not VC dependant) is assigned.

vrIpArpHost OBJECT IDENTIFIER ::= { vrIpArp 2 }



vrIpArpHostRowStatusTable OBJECT-TYPE
   SYNTAX     SEQUENCE OF VrIpArpHostRowStatusEntry
   ACCESS     not-accessible
   STATUS     mandatory
   DESCRIPTION
     "This entry controls the addition and deletion of 
      vrIpArpHost components."
::= { vrIpArpHost 1 }

vrIpArpHostRowStatusEntry OBJECT-TYPE
   SYNTAX     VrIpArpHostRowStatusEntry
   ACCESS     not-accessible
   STATUS     mandatory
   DESCRIPTION
     "A single entry in the table represents a single 
      vrIpArpHost component."
   INDEX {
      vrIndex,
      vrIpIndex,
      vrIpArpIndex,
      vrIpArpHostHostAddressIndex }
::= { vrIpArpHostRowStatusTable 1 }

VrIpArpHostRowStatusEntry ::= SEQUENCE {
   vrIpArpHostRowStatus
      RowStatus,
   vrIpArpHostComponentName
      DisplayString,
   vrIpArpHostStorageType
      StorageType,
   vrIpArpHostHostAddressIndex
      IpAddress }

vrIpArpHostRowStatus OBJECT-TYPE
   SYNTAX     RowStatus 
   ACCESS     read-write
   STATUS     mandatory
   DESCRIPTION
     "This variable is used as the basis for SNMP naming of
      vrIpArpHost components.
      These components can be added and deleted."
::= { vrIpArpHostRowStatusEntry 1 }

vrIpArpHostComponentName OBJECT-TYPE
   SYNTAX     DisplayString 
   ACCESS     read-only
   STATUS     mandatory
   DESCRIPTION
     "This variable provides the component's string name for
      use with the ASCII Console Interface"
::= { vrIpArpHostRowStatusEntry 2 }

vrIpArpHostStorageType OBJECT-TYPE
   SYNTAX     StorageType 
   ACCESS     read-only
   STATUS     mandatory
   DESCRIPTION
     "This variable represents the storage type value for the
      vrIpArpHost tables."
::= { vrIpArpHostRowStatusEntry 4 }

vrIpArpHostHostAddressIndex OBJECT-TYPE
   SYNTAX     IpAddress 
   ACCESS     not-accessible
   STATUS     mandatory
   DESCRIPTION
     "This variable represents the index for the vrIpArpHost tables."
::= { vrIpArpHostRowStatusEntry 10 }

vrIpArpHostProvTable OBJECT-TYPE
   SYNTAX     SEQUENCE OF VrIpArpHostProvEntry
   ACCESS     not-accessible
   STATUS     mandatory
   DESCRIPTION
     "This group contains the provisionable attributes of the HostEntry 
      component."
::= { vrIpArpHost 10 }

vrIpArpHostProvEntry OBJECT-TYPE
   SYNTAX     VrIpArpHostProvEntry
   ACCESS     not-accessible
   STATUS     mandatory
   DESCRIPTION
     "An entry in the vrIpArpHostProvTable."
   INDEX {
      vrIndex,
      vrIpIndex,
      vrIpArpIndex,
      vrIpArpHostHostAddressIndex }
::= { vrIpArpHostProvTable 1 }

VrIpArpHostProvEntry ::= SEQUENCE {
   vrIpArpHostPhysAddress
      PhysAddress,
   vrIpArpHostMaxTxUnit
      Unsigned32,
   vrIpArpHostPermanentVirtualCircuitNumber
      Unsigned32,
   vrIpArpHostEncap
      INTEGER }

vrIpArpHostPhysAddress OBJECT-TYPE
   SYNTAX     PhysAddress (SIZE (0..8))
   ACCESS     read-write
   STATUS     mandatory
   DESCRIPTION
     "This attribute identifies the physical address of the host being defined. 
      The value for this attribute should only be specified for media types 
      supporting physical addresses (eg. ethernet, fddi, tokenRing etc.)"
   DEFVAL     { '000000000000'H }
::= { vrIpArpHostProvEntry 1 }

vrIpArpHostMaxTxUnit OBJECT-TYPE
   SYNTAX     Unsigned32 (0..0 | 576..18944)
   ACCESS     read-write
   STATUS     mandatory
   DESCRIPTION
     "Specify the maximum transmit unit (MTU) size that can be accepted by 
      the host. If this value is not specified, the value for the media interface is 
      used. The specified MTU must be less than or equal to the interface's 
      MTU size."
   DEFVAL     { 0 }
::= { vrIpArpHostProvEntry 2 }

vrIpArpHostPermanentVirtualCircuitNumber OBJECT-TYPE
   SYNTAX     Unsigned32 (0..4095)
   ACCESS     read-write
   STATUS     mandatory
   DESCRIPTION
     "Specify a permanent virtual circuit number to the remote host on X.25 
      or frame relay media.
      The value for this attribute can only be specified for X.25 or 
      frame relay media."
   DEFVAL     { 0 }
::= { vrIpArpHostProvEntry 3 }

vrIpArpHostEncap OBJECT-TYPE
   SYNTAX     INTEGER  {
                 ieee8023(1),
                 ethernet(2),
                 auto(3) }
   ACCESS     read-write
   STATUS     mandatory
   DESCRIPTION
     "Specify the encapsulation type for the host.
      The value for this attribute should only be specified for the hosts on the 
      ethernet media. If a value of auto is specified, the application based on 
      the media will determine the proper applicable encapsulation type."
   DEFVAL     { auto }
::= { vrIpArpHostProvEntry 4 }

vrIpArpHostOperTable OBJECT-TYPE
   SYNTAX     SEQUENCE OF VrIpArpHostOperEntry
   ACCESS     not-accessible
   STATUS     mandatory
   DESCRIPTION
     "This group contains the operational attributes of the HostEntry 
      component."
::= { vrIpArpHost 11 }

vrIpArpHostOperEntry OBJECT-TYPE
   SYNTAX     VrIpArpHostOperEntry
   ACCESS     not-accessible
   STATUS     mandatory
   DESCRIPTION
     "An entry in the vrIpArpHostOperTable."
   INDEX {
      vrIndex,
      vrIpIndex,
      vrIpArpIndex,
      vrIpArpHostHostAddressIndex }
::= { vrIpArpHostOperTable 1 }

VrIpArpHostOperEntry ::= SEQUENCE {
   vrIpArpHostOperMaxTxUnit
      Unsigned32,
   vrIpArpHostOperEncap
      INTEGER }

vrIpArpHostOperMaxTxUnit OBJECT-TYPE
   SYNTAX     Unsigned32 (0..0 | 576..18944)
   ACCESS     read-only
   STATUS     mandatory
   DESCRIPTION
     "This attribute indicates the operational value of the maximum 
      transmission unit."
::= { vrIpArpHostOperEntry 4 }

vrIpArpHostOperEncap OBJECT-TYPE
   SYNTAX     INTEGER  {
                 ieee8023(1),
                 ethernet(2),
                 notApplicable(3) }
   ACCESS     read-only
   STATUS     mandatory
   DESCRIPTION
     "This attribute indicates the operational encapsulation type. if the value of 
      the attribute encap is set to auto, then the application will determine the 
      encapsulation type based on the media being used and assigns the 
      appropriate value."
::= { vrIpArpHostOperEntry 5 }

-- 
-- *** THIS SUBTREE CURRENTLY NOT IMPLEMENTED ***
-- 

-- Vr/<string> Ip Arp DynHostEntry/<Ip Address>
-- This component is a table that contains all Arp host entries (both static 
-- and dynamic)..Each IP ARP entry in the table is uniquely defined by its 
-- IP address and Class of Service (CoS) index.
-- 
-- When the associated media type is one where the CoS can be specifed 
-- on a per virtual circuit basis (eg. frameRelayDte or atmMpe) the CoS 
-- index of the arp entry may be 0, 1, 2, or 3; otherwise, the CoS index is 
-- na (not VC dependent).
-- 
-- An IP packet that has been assigned a particular CoS will be forwarded 
-- using the arp entry where the IP address matches the packet's 
-- destination IP address and where the CoS index matches the packet's 
-- CoS. When there are arp entries that match the packet's destination IP 
-- address, but not the packet's CoS, the packet will be forwarded using the 
-- arp entry that has the next lowest CoS index; failing this, the packet will 
-- be forwarded using the arp entry that has the next highest CoS index.

vrIpArpDynHost OBJECT IDENTIFIER ::= { vrIpArp 3 }



vrIpArpDynHostRowStatusTable OBJECT-TYPE
   SYNTAX     SEQUENCE OF VrIpArpDynHostRowStatusEntry
   ACCESS     not-accessible
   STATUS     mandatory
   DESCRIPTION
     "*** THIS TABLE CURRENTLY NOT IMPLEMENTED ***

      This entry controls the addition and deletion of 
      vrIpArpDynHost components."
::= { vrIpArpDynHost 1 }

vrIpArpDynHostRowStatusEntry OBJECT-TYPE
   SYNTAX     VrIpArpDynHostRowStatusEntry
   ACCESS     not-accessible
   STATUS     mandatory
   DESCRIPTION
     "A single entry in the table represents a single 
      vrIpArpDynHost component."
   INDEX {
      vrIndex,
      vrIpIndex,
      vrIpArpIndex,
      vrIpArpDynHostHostAddressIndex,
      vrIpArpDynHostCosIndex }
::= { vrIpArpDynHostRowStatusTable 1 }

VrIpArpDynHostRowStatusEntry ::= SEQUENCE {
   vrIpArpDynHostRowStatus
      RowStatus,
   vrIpArpDynHostComponentName
      DisplayString,
   vrIpArpDynHostStorageType
      StorageType,
   vrIpArpDynHostHostAddressIndex
      IpAddress,
   vrIpArpDynHostCosIndex
      INTEGER }

vrIpArpDynHostRowStatus OBJECT-TYPE
   SYNTAX     RowStatus 
   ACCESS     read-only
   STATUS     mandatory
   DESCRIPTION
     "This variable is used as the basis for SNMP naming of
      vrIpArpDynHost components.
      These components cannot be added nor deleted."
::= { vrIpArpDynHostRowStatusEntry 1 }

vrIpArpDynHostComponentName OBJECT-TYPE
   SYNTAX     DisplayString 
   ACCESS     read-only
   STATUS     mandatory
   DESCRIPTION
     "This variable provides the component's string name for
      use with the ASCII Console Interface"
::= { vrIpArpDynHostRowStatusEntry 2 }

vrIpArpDynHostStorageType OBJECT-TYPE
   SYNTAX     StorageType 
   ACCESS     read-only
   STATUS     mandatory
   DESCRIPTION
     "This variable represents the storage type value for the
      vrIpArpDynHost tables."
::= { vrIpArpDynHostRowStatusEntry 4 }

vrIpArpDynHostHostAddressIndex OBJECT-TYPE
   SYNTAX     IpAddress 
   ACCESS     not-accessible
   STATUS     mandatory
   DESCRIPTION
     "This variable represents an index for the vrIpArpDynHost tables."
::= { vrIpArpDynHostRowStatusEntry 10 }

vrIpArpDynHostCosIndex OBJECT-TYPE
   SYNTAX     INTEGER  {
                 n0(0),
                 n1(1),
                 n2(2),
                 n3(3),
                 notApplicable(4) }
   ACCESS     not-accessible
   STATUS     mandatory
   DESCRIPTION
     "This variable represents an index for the vrIpArpDynHost tables."
::= { vrIpArpDynHostRowStatusEntry 11 }

vrIpArpDynHostOperTable OBJECT-TYPE
   SYNTAX     SEQUENCE OF VrIpArpDynHostOperEntry
   ACCESS     not-accessible
   STATUS     mandatory
   DESCRIPTION
     "*** THIS TABLE CURRENTLY NOT IMPLEMENTED ***

      This group contains the operational attributes of the DynHostEntry 
      component."
::= { vrIpArpDynHost 10 }

vrIpArpDynHostOperEntry OBJECT-TYPE
   SYNTAX     VrIpArpDynHostOperEntry
   ACCESS     not-accessible
   STATUS     mandatory
   DESCRIPTION
     "An entry in the vrIpArpDynHostOperTable."
   INDEX {
      vrIndex,
      vrIpIndex,
      vrIpArpIndex,
      vrIpArpDynHostHostAddressIndex,
      vrIpArpDynHostCosIndex }
::= { vrIpArpDynHostOperTable 1 }

VrIpArpDynHostOperEntry ::= SEQUENCE {
   vrIpArpDynHostPhysAddress
      PhysAddress,
   vrIpArpDynHostMaxTxUnit
      Unsigned32,
   vrIpArpDynHostEncapsulationType
      INTEGER,
   vrIpArpDynHostPermanentVirtualCircuitNumber
      Unsigned32,
   vrIpArpDynHostIfIndex
      InterfaceIndex,
   vrIpArpDynHostType
      INTEGER,
   vrIpArpDynHostNcPhysAddress
      PhysAddress }

vrIpArpDynHostPhysAddress OBJECT-TYPE
   SYNTAX     PhysAddress (SIZE (0..8))
   ACCESS     read-only
   STATUS     mandatory
   DESCRIPTION
     "This attribute indicates the physical address of the host in canonical 
      form."
::= { vrIpArpDynHostOperEntry 1 }

vrIpArpDynHostMaxTxUnit OBJECT-TYPE
   SYNTAX     Unsigned32 (0..0 | 576..18944)
   ACCESS     read-only
   STATUS     mandatory
   DESCRIPTION
     "This attribute indicates the maximum MTU size that can be accepted by 
      the host."
   DEFVAL     { 0 }
::= { vrIpArpDynHostOperEntry 3 }

vrIpArpDynHostEncapsulationType OBJECT-TYPE
   SYNTAX     INTEGER  {
                 ieee8023(1),
                 ethernet(2),
                 notApplicable(3) }
   ACCESS     read-only
   STATUS     mandatory
   DESCRIPTION
     "This attribute indicates the encapsulation type of the host."
::= { vrIpArpDynHostOperEntry 4 }

vrIpArpDynHostPermanentVirtualCircuitNumber OBJECT-TYPE
   SYNTAX     Unsigned32 (0..4095)
   ACCESS     read-only
   STATUS     mandatory
   DESCRIPTION
     "This attribute indicates the permanent virtual circuit number to the 
      remote host."
::= { vrIpArpDynHostOperEntry 5 }

vrIpArpDynHostIfIndex OBJECT-TYPE
   SYNTAX     InterfaceIndex (1..65535)
   ACCESS     read-only
   STATUS     mandatory
   DESCRIPTION
     "This attribute indicates the ifIndex of the protocol port that is associated 
      with this entry."
   DEFVAL     { 1 }
::= { vrIpArpDynHostOperEntry 6 }

vrIpArpDynHostType OBJECT-TYPE
   SYNTAX     INTEGER  {
                 pending(1),
                 invalid(2),
                 dynamic(3),
                 static(4) }
   ACCESS     read-only
   STATUS     mandatory
   DESCRIPTION
     "This attribute indicates how this entry was learned."
::= { vrIpArpDynHostOperEntry 7 }

vrIpArpDynHostNcPhysAddress OBJECT-TYPE
   SYNTAX     PhysAddress (SIZE (0..8))
   ACCESS     read-only
   STATUS     mandatory
   DESCRIPTION
     "This attribute indicates the physical address of the host in non-canonical 
      form. This attribute is not displayed for hosts on non-LAN media."
::= { vrIpArpDynHostOperEntry 8 }


-- Vr/<string> Ip Icmp
-- The Icmp component controls all ICMP related attributes available to 
-- this router.

vrIpIcmp OBJECT IDENTIFIER ::= { vrIp 12 }



vrIpIcmpRowStatusTable OBJECT-TYPE
   SYNTAX     SEQUENCE OF VrIpIcmpRowStatusEntry
   ACCESS     not-accessible
   STATUS     mandatory
   DESCRIPTION
     "This entry controls the addition and deletion of 
      vrIpIcmp components."
::= { vrIpIcmp 1 }

vrIpIcmpRowStatusEntry OBJECT-TYPE
   SYNTAX     VrIpIcmpRowStatusEntry
   ACCESS     not-accessible
   STATUS     mandatory
   DESCRIPTION
     "A single entry in the table represents a single 
      vrIpIcmp component."
   INDEX {
      vrIndex,
      vrIpIndex,
      vrIpIcmpIndex }
::= { vrIpIcmpRowStatusTable 1 }

VrIpIcmpRowStatusEntry ::= SEQUENCE {
   vrIpIcmpRowStatus
      RowStatus,
   vrIpIcmpComponentName
      DisplayString,
   vrIpIcmpStorageType
      StorageType,
   vrIpIcmpIndex
      NonReplicated }

vrIpIcmpRowStatus OBJECT-TYPE
   SYNTAX     RowStatus 
   ACCESS     read-only
   STATUS     mandatory
   DESCRIPTION
     "This variable is used as the basis for SNMP naming of
      vrIpIcmp components.
      These components cannot be added nor deleted."
::= { vrIpIcmpRowStatusEntry 1 }

vrIpIcmpComponentName OBJECT-TYPE
   SYNTAX     DisplayString 
   ACCESS     read-only
   STATUS     mandatory
   DESCRIPTION
     "This variable provides the component's string name for
      use with the ASCII Console Interface"
::= { vrIpIcmpRowStatusEntry 2 }

vrIpIcmpStorageType OBJECT-TYPE
   SYNTAX     StorageType 
   ACCESS     read-only
   STATUS     mandatory
   DESCRIPTION
     "This variable represents the storage type value for the
      vrIpIcmp tables."
::= { vrIpIcmpRowStatusEntry 4 }

vrIpIcmpIndex OBJECT-TYPE
   SYNTAX     NonReplicated 
   ACCESS     not-accessible
   STATUS     mandatory
   DESCRIPTION
     "This variable represents the index for the vrIpIcmp tables."
::= { vrIpIcmpRowStatusEntry 10 }

vrIpIcmpProvTable OBJECT-TYPE
   SYNTAX     SEQUENCE OF VrIpIcmpProvEntry
   ACCESS     not-accessible
   STATUS     mandatory
   DESCRIPTION
     "This group holds provisioned attributes for ICMP."
::= { vrIpIcmp 10 }

vrIpIcmpProvEntry OBJECT-TYPE
   SYNTAX     VrIpIcmpProvEntry
   ACCESS     not-accessible
   STATUS     mandatory
   DESCRIPTION
     "An entry in the vrIpIcmpProvTable."
   INDEX {
      vrIndex,
      vrIpIndex,
      vrIpIcmpIndex }
::= { vrIpIcmpProvTable 1 }

VrIpIcmpProvEntry ::= SEQUENCE {
   vrIpIcmpSendRedirect
      INTEGER,
   vrIpIcmpSendHostUnreachable
      INTEGER }

vrIpIcmpSendRedirect OBJECT-TYPE
   SYNTAX     INTEGER  {
                 enabled(1),
                 disabled(2) }
   ACCESS     read-write
   STATUS     obsolete
   DESCRIPTION
     "This attribute specifies whether an ICMP redirect will be sent. If 
      enabled, the router may send an ICMP redirect if a an Ip packet is being 
      routed out the same logicalInterface as it was received on. The router 
      will only send host ICMP redirects. If disabled, the router will never 
      send a ICMP redirect."
   DEFVAL     { enabled }
::= { vrIpIcmpProvEntry 1 }

vrIpIcmpSendHostUnreachable OBJECT-TYPE
   SYNTAX     INTEGER  {
                 enabled(1),
                 disabled(2) }
   ACCESS     read-write
   STATUS     obsolete
   DESCRIPTION
     "This attribute specifies whether host unreachable will be sent or not."
   DEFVAL     { disabled }
::= { vrIpIcmpProvEntry 2 }

vrIpIcmpStatsTable OBJECT-TYPE
   SYNTAX     SEQUENCE OF VrIpIcmpStatsEntry
   ACCESS     not-accessible
   STATUS     mandatory
   DESCRIPTION
     "This group holds statistics for ICMP."
::= { vrIpIcmp 11 }

vrIpIcmpStatsEntry OBJECT-TYPE
   SYNTAX     VrIpIcmpStatsEntry
   ACCESS     not-accessible
   STATUS     mandatory
   DESCRIPTION
     "An entry in the vrIpIcmpStatsTable."
   INDEX {
      vrIndex,
      vrIpIndex,
      vrIpIcmpIndex }
::= { vrIpIcmpStatsTable 1 }

VrIpIcmpStatsEntry ::= SEQUENCE {
   vrIpIcmpInMsgs
      Counter32,
   vrIpIcmpInErrors
      Counter32,
   vrIpIcmpInDestUnreachs
      Counter32,
   vrIpIcmpInTimeExcds
      Counter32,
   vrIpIcmpInParmProbs
      Counter32,
   vrIpIcmpInSrcQuenchs
      Counter32,
   vrIpIcmpInRedirects
      Counter32,
   vrIpIcmpInEchos
      Counter32,
   vrIpIcmpInEchoReps
      Counter32,
   vrIpIcmpInTimestamps
      Counter32,
   vrIpIcmpInTimestampReps
      Counter32,
   vrIpIcmpInAddrMasks
      Counter32,
   vrIpIcmpInAddrMaskReps
      Counter32,
   vrIpIcmpOutMsgs
      Counter32,
   vrIpIcmpOutErrors
      Counter32,
   vrIpIcmpOutDestUnreachs
      Counter32,
   vrIpIcmpOutTimeExcds
      Counter32,
   vrIpIcmpOutParmProbs
      Counter32,
   vrIpIcmpOutSrcQuenchs
      Counter32,
   vrIpIcmpOutRedirects
      Counter32,
   vrIpIcmpOutEchos
      Counter32,
   vrIpIcmpOutEchoReps
      Counter32,
   vrIpIcmpOutTimestamps
      Counter32,
   vrIpIcmpOutTimestampReps
      Counter32,
   vrIpIcmpOutAddrMasks
      Counter32,
   vrIpIcmpOutAddrMaskReps
      Counter32,
   vrIpIcmpInRtrAdvs
      Counter32,
   vrIpIcmpInRtrSolicits
      Counter32,
   vrIpIcmpOutRtrAdvs
      Counter32,
   vrIpIcmpOutRtrSolicits
      Counter32 }

vrIpIcmpInMsgs OBJECT-TYPE
   SYNTAX     Counter32 
   ACCESS     read-only
   STATUS     mandatory
   DESCRIPTION
     "This attribute indicates the number of ICMP messages received by this 
      gateway. This number includes inErrors. inMsgs wraps to zero if it 
      reaches its maximum defined value."
::= { vrIpIcmpStatsEntry 1 }

vrIpIcmpInErrors OBJECT-TYPE
   SYNTAX     Counter32 
   ACCESS     read-only
   STATUS     mandatory
   DESCRIPTION
     "This attribute indicates the number of ICMP messages received by this 
      gateway but determined as having ICMP specific errors such as bad 
      ICMP checksums or bad length. inErrors wraps to zero if it reaches its 
      maximum defined value."
::= { vrIpIcmpStatsEntry 2 }

vrIpIcmpInDestUnreachs OBJECT-TYPE
   SYNTAX     Counter32 
   ACCESS     read-only
   STATUS     mandatory
   DESCRIPTION
     "This attribute indicates the number of ICMP destination unreachable 
      messages received by this gateway. inDestUnreachs wraps to zero if it 
      reaches its maximum defined value."
::= { vrIpIcmpStatsEntry 3 }

vrIpIcmpInTimeExcds OBJECT-TYPE
   SYNTAX     Counter32 
   ACCESS     read-only
   STATUS     mandatory
   DESCRIPTION
     "This attribute indicates the number of ICMP time exceeded messages 
      received by this gateway. inTimeExcds wraps to zero if it reaches its 
      maximum defined value."
::= { vrIpIcmpStatsEntry 4 }

vrIpIcmpInParmProbs OBJECT-TYPE
   SYNTAX     Counter32 
   ACCESS     read-only
   STATUS     mandatory
   DESCRIPTION
     "This attribute indicates the number of ICMP parameter problem 
      messages received by this gateway. inParmProbs wraps to zero if it 
      reaches its maximum defined value."
::= { vrIpIcmpStatsEntry 5 }

vrIpIcmpInSrcQuenchs OBJECT-TYPE
   SYNTAX     Counter32 
   ACCESS     read-only
   STATUS     mandatory
   DESCRIPTION
     "This attribute indicates the number of ICMP source quench messages 
      received by this gateway. inSrcQuenchs wraps to zero if it reaches its 
      maximum defined value."
::= { vrIpIcmpStatsEntry 6 }

vrIpIcmpInRedirects OBJECT-TYPE
   SYNTAX     Counter32 
   ACCESS     read-only
   STATUS     mandatory
   DESCRIPTION
     "This attribute indicates the number of ICMP redirect messages received 
      by this gateway. inRedirects wraps to zero if it reaches its maximum 
      defined value."
::= { vrIpIcmpStatsEntry 7 }

vrIpIcmpInEchos OBJECT-TYPE
   SYNTAX     Counter32 
   ACCESS     read-only
   STATUS     mandatory
   DESCRIPTION
     "This attribute indicates the number of ICMP echo request messages 
      received by this gateway. inEchos wraps to zero if it reaches its 
      maximum defined value."
::= { vrIpIcmpStatsEntry 8 }

vrIpIcmpInEchoReps OBJECT-TYPE
   SYNTAX     Counter32 
   ACCESS     read-only
   STATUS     mandatory
   DESCRIPTION
     "This attribute indicates the number of ICMP echo reply messages 
      received by this gateway. inEchoReps wraps to zero if it reaches its 
      maximum defined value."
::= { vrIpIcmpStatsEntry 9 }

vrIpIcmpInTimestamps OBJECT-TYPE
   SYNTAX     Counter32 
   ACCESS     read-only
   STATUS     mandatory
   DESCRIPTION
     "This attribute indicates the number of ICMP timestamp request 
      messages received by this gateway. inTimeStamps wraps to zero if it 
      reaches its maximum defined value."
::= { vrIpIcmpStatsEntry 10 }

vrIpIcmpInTimestampReps OBJECT-TYPE
   SYNTAX     Counter32 
   ACCESS     read-only
   STATUS     mandatory
   DESCRIPTION
     "This attribute indicates the number of ICMP timestamp reply messages 
      received by this gateway. inTimeStampReps wraps to zero if it reaches 
      its maximum defined value."
::= { vrIpIcmpStatsEntry 11 }

vrIpIcmpInAddrMasks OBJECT-TYPE
   SYNTAX     Counter32 
   ACCESS     read-only
   STATUS     mandatory
   DESCRIPTION
     "This attribute indicates the number of ICMP address mask request 
      messages received by this gateway. inAddrMasks wraps to zero if it 
      reaches its maximum defined value."
::= { vrIpIcmpStatsEntry 12 }

vrIpIcmpInAddrMaskReps OBJECT-TYPE
   SYNTAX     Counter32 
   ACCESS     read-only
   STATUS     mandatory
   DESCRIPTION
     "This attribute indicates the number of ICMP address mask reply 
      messages received by this gateway. inAddrMaskReps wraps to zero if it 
      reaches its maximum defined value."
::= { vrIpIcmpStatsEntry 13 }

vrIpIcmpOutMsgs OBJECT-TYPE
   SYNTAX     Counter32 
   ACCESS     read-only
   STATUS     mandatory
   DESCRIPTION
     "This attribute indicates the number of ICMP messages which this 
      gateway attempted to send. This number includes outErrors. outMsgs 
      wraps to zero if it reaches its maximum defined value."
::= { vrIpIcmpStatsEntry 14 }

vrIpIcmpOutErrors OBJECT-TYPE
   SYNTAX     Counter32 
   ACCESS     read-only
   STATUS     mandatory
   DESCRIPTION
     "This attribute indicates the number of ICMP messages which this 
      gateway did not send due to problems discovered within ICMP such as a 
      lack of buffers. outErrors does not included errors discovered outside 
      the ICMP layer such as the inability of IP to route the resultant 
      datagram. outErrors wraps to zero if it reaches its maximum defined 
      value."
::= { vrIpIcmpStatsEntry 15 }

vrIpIcmpOutDestUnreachs OBJECT-TYPE
   SYNTAX     Counter32 
   ACCESS     read-only
   STATUS     mandatory
   DESCRIPTION
     "This attribute indicates the number of ICMP destination unreachable 
      messages sent by this gateway. outDestUnreachs wraps to zero if it 
      reaches its maximum defined value."
::= { vrIpIcmpStatsEntry 16 }

vrIpIcmpOutTimeExcds OBJECT-TYPE
   SYNTAX     Counter32 
   ACCESS     read-only
   STATUS     mandatory
   DESCRIPTION
     "This attribute indicates the number of ICMP time exceeded messages 
      sent by this gateway. outTimeExcds wraps to zero if it reaches its 
      maximum defined value."
::= { vrIpIcmpStatsEntry 17 }

vrIpIcmpOutParmProbs OBJECT-TYPE
   SYNTAX     Counter32 
   ACCESS     read-only
   STATUS     mandatory
   DESCRIPTION
     "This attribute indicates the number of ICMP parameter problem 
      messages sent by this gateway. outParmProbs wraps to zero if it reaches 
      its maximum defined value."
::= { vrIpIcmpStatsEntry 18 }

vrIpIcmpOutSrcQuenchs OBJECT-TYPE
   SYNTAX     Counter32 
   ACCESS     read-only
   STATUS     mandatory
   DESCRIPTION
     "This attribute indicates the number of ICMP source quench messages 
      sent by this gateway. ourSrcQuench wraps to zero if it reaches its 
      maximum defined value."
::= { vrIpIcmpStatsEntry 19 }

vrIpIcmpOutRedirects OBJECT-TYPE
   SYNTAX     Counter32 
   ACCESS     read-only
   STATUS     mandatory
   DESCRIPTION
     "This attribute indicates the number of ICMP redirect messages sent by 
      this gateway. outRedirects wraps to zero if it reaches its maximum 
      defined value."
::= { vrIpIcmpStatsEntry 20 }

vrIpIcmpOutEchos OBJECT-TYPE
   SYNTAX     Counter32 
   ACCESS     read-only
   STATUS     mandatory
   DESCRIPTION
     "This attribute indicates the number of ICMP echo request messages sent 
      by this gateway. outEchos wraps to zero if it reaches its maximum 
      defined value."
::= { vrIpIcmpStatsEntry 21 }

vrIpIcmpOutEchoReps OBJECT-TYPE
   SYNTAX     Counter32 
   ACCESS     read-only
   STATUS     mandatory
   DESCRIPTION
     "This attribute indicates the number of ICMP echo reply messages sent 
      by this gateway. outEchoReps wraps to zero if it reaches its maximum 
      defined value."
::= { vrIpIcmpStatsEntry 22 }

vrIpIcmpOutTimestamps OBJECT-TYPE
   SYNTAX     Counter32 
   ACCESS     read-only
   STATUS     mandatory
   DESCRIPTION
     "This attribute indicates the number of ICMP timestamp request 
      messages sent by this gateway. outTimeStamps wraps to zero if it 
      reaches its maximum defined value."
::= { vrIpIcmpStatsEntry 23 }

vrIpIcmpOutTimestampReps OBJECT-TYPE
   SYNTAX     Counter32 
   ACCESS     read-only
   STATUS     mandatory
   DESCRIPTION
     "This attribute indicates the number of ICMP timestamp reply messages 
      sent by this gateway. outTimeStampReps wraps to zero if it reaches its 
      maximum defined value."
::= { vrIpIcmpStatsEntry 24 }

vrIpIcmpOutAddrMasks OBJECT-TYPE
   SYNTAX     Counter32 
   ACCESS     read-only
   STATUS     mandatory
   DESCRIPTION
     "This attribute indicates the number of ICMP address mask request 
      messages sent by this gateway. outAddrMasks wraps to zero if it reaches 
      its maximum defined value."
::= { vrIpIcmpStatsEntry 25 }

vrIpIcmpOutAddrMaskReps OBJECT-TYPE
   SYNTAX     Counter32 
   ACCESS     read-only
   STATUS     mandatory
   DESCRIPTION
     "This attribute indicates the number of ICMP address mask reply 
      message sent by this gateway. outAddrMaskReps wraps to zero if it 
      reaches its maximum defined value."
::= { vrIpIcmpStatsEntry 26 }

vrIpIcmpInRtrAdvs OBJECT-TYPE
   SYNTAX     Counter32 
   ACCESS     read-only
   STATUS     mandatory
   DESCRIPTION
     "This attribute indicates the number of ICMP router advertisement 
      messages received by this gateway. inRtrAdvs wraps to zero if it reaches 
      its maximum defined value."
::= { vrIpIcmpStatsEntry 27 }

vrIpIcmpInRtrSolicits OBJECT-TYPE
   SYNTAX     Counter32 
   ACCESS     read-only
   STATUS     mandatory
   DESCRIPTION
     "This attribute indicates the number of ICMP router solicitation messages 
      received by this gateway. inRtrSolicits wraps to zero if it reaches its 
      maximum defined value."
::= { vrIpIcmpStatsEntry 28 }

vrIpIcmpOutRtrAdvs OBJECT-TYPE
   SYNTAX     Counter32 
   ACCESS     read-only
   STATUS     mandatory
   DESCRIPTION
     "This attribute indicates the number of ICMP router advertisement 
      messages sent by this gateway. outRtrAdvs wraps to zero if it reaches its 
      maximum defined value."
::= { vrIpIcmpStatsEntry 29 }

vrIpIcmpOutRtrSolicits OBJECT-TYPE
   SYNTAX     Counter32 
   ACCESS     read-only
   STATUS     mandatory
   DESCRIPTION
     "This attribute indicates the number of ICMP router solicitation messages 
      sent by this gateway. outRtrSolicits wraps to zero if it reaches its 
      maximum defined value."
::= { vrIpIcmpStatsEntry 30 }


-- Vr/<string> Ip RelayBC
-- The InwRelayBroadcast component controls the dissemination of IP 
-- broadcast packets received as Link-Layer broadcast.

vrIpRelayBC OBJECT IDENTIFIER ::= { vrIp 13 }



vrIpRelayBCRowStatusTable OBJECT-TYPE
   SYNTAX     SEQUENCE OF VrIpRelayBCRowStatusEntry
   ACCESS     not-accessible
   STATUS     mandatory
   DESCRIPTION
     "This entry controls the addition and deletion of 
      vrIpRelayBC components."
::= { vrIpRelayBC 1 }

vrIpRelayBCRowStatusEntry OBJECT-TYPE
   SYNTAX     VrIpRelayBCRowStatusEntry
   ACCESS     not-accessible
   STATUS     mandatory
   DESCRIPTION
     "A single entry in the table represents a single 
      vrIpRelayBC component."
   INDEX {
      vrIndex,
      vrIpIndex,
      vrIpRelayBCIndex }
::= { vrIpRelayBCRowStatusTable 1 }

VrIpRelayBCRowStatusEntry ::= SEQUENCE {
   vrIpRelayBCRowStatus
      RowStatus,
   vrIpRelayBCComponentName
      DisplayString,
   vrIpRelayBCStorageType
      StorageType,
   vrIpRelayBCIndex
      NonReplicated }

vrIpRelayBCRowStatus OBJECT-TYPE
   SYNTAX     RowStatus 
   ACCESS     read-only
   STATUS     mandatory
   DESCRIPTION
     "This variable is used as the basis for SNMP naming of
      vrIpRelayBC components.
      These components cannot be added nor deleted."
::= { vrIpRelayBCRowStatusEntry 1 }

vrIpRelayBCComponentName OBJECT-TYPE
   SYNTAX     DisplayString 
   ACCESS     read-only
   STATUS     mandatory
   DESCRIPTION
     "This variable provides the component's string name for
      use with the ASCII Console Interface"
::= { vrIpRelayBCRowStatusEntry 2 }

vrIpRelayBCStorageType OBJECT-TYPE
   SYNTAX     StorageType 
   ACCESS     read-only
   STATUS     mandatory
   DESCRIPTION
     "This variable represents the storage type value for the
      vrIpRelayBC tables."
::= { vrIpRelayBCRowStatusEntry 4 }

vrIpRelayBCIndex OBJECT-TYPE
   SYNTAX     NonReplicated 
   ACCESS     not-accessible
   STATUS     mandatory
   DESCRIPTION
     "This variable represents the index for the vrIpRelayBC tables."
::= { vrIpRelayBCRowStatusEntry 10 }

vrIpRelayBCProvTable OBJECT-TYPE
   SYNTAX     SEQUENCE OF VrIpRelayBCProvEntry
   ACCESS     not-accessible
   STATUS     mandatory
   DESCRIPTION
     "This group contains global configuration attributes for the Relay 
      Broadcast component."
::= { vrIpRelayBC 10 }

vrIpRelayBCProvEntry OBJECT-TYPE
   SYNTAX     VrIpRelayBCProvEntry
   ACCESS     not-accessible
   STATUS     mandatory
   DESCRIPTION
     "An entry in the vrIpRelayBCProvTable."
   INDEX {
      vrIndex,
      vrIpIndex,
      vrIpRelayBCIndex }
::= { vrIpRelayBCProvTable 1 }

VrIpRelayBCProvEntry ::= SEQUENCE {
   vrIpRelayBCRelayStatus
      INTEGER,
   vrIpRelayBCRelayNdStatus
      INTEGER }

vrIpRelayBCRelayStatus OBJECT-TYPE
   SYNTAX     INTEGER  {
                 enabled(1),
                 disabled(2) }
   ACCESS     read-write
   STATUS     mandatory
   DESCRIPTION
     "Specifies whether or not IP will forward IP broadcast packets that were 
      received as Link-Layer broadcasts."
   DEFVAL     { disabled }
::= { vrIpRelayBCProvEntry 1 }

vrIpRelayBCRelayNdStatus OBJECT-TYPE
   SYNTAX     INTEGER  {
                 enabled(1),
                 disabled(2) }
   ACCESS     read-write
   STATUS     mandatory
   DESCRIPTION
     "Specifies whether or not IP will forward broadcast packets whose 
      protocol is Sun ND."
   DEFVAL     { disabled }
::= { vrIpRelayBCProvEntry 2 }

vrIpRelayBCOperTable OBJECT-TYPE
   SYNTAX     SEQUENCE OF VrIpRelayBCOperEntry
   ACCESS     not-accessible
   STATUS     mandatory
   DESCRIPTION
     "This group contains RelayBroadcast component statistics."
::= { vrIpRelayBC 11 }

vrIpRelayBCOperEntry OBJECT-TYPE
   SYNTAX     VrIpRelayBCOperEntry
   ACCESS     not-accessible
   STATUS     mandatory
   DESCRIPTION
     "An entry in the vrIpRelayBCOperTable."
   INDEX {
      vrIndex,
      vrIpIndex,
      vrIpRelayBCIndex }
::= { vrIpRelayBCOperTable 1 }

VrIpRelayBCOperEntry ::= SEQUENCE {
   vrIpRelayBCRelayNdCount
      Counter32 }

vrIpRelayBCRelayNdCount OBJECT-TYPE
   SYNTAX     Counter32 
   ACCESS     read-only
   STATUS     mandatory
   DESCRIPTION
     "Indicates the number of Sun ND packets received by this router which 
      were forwarded. relayNdCount wraps to zero if reached its maximum."
::= { vrIpRelayBCOperEntry 1 }


-- Vr/<string> Ip RelayBC PortEntry/<Decimal>
-- This component is a table of destination UDP port numbers. In order for 
-- a packet to be forwarded by Relay Broadcast, the packet's destination 
-- UDP port number must be listed in this table.

vrIpRelayBCPort OBJECT IDENTIFIER ::= { vrIpRelayBC 2 }



vrIpRelayBCPortRowStatusTable OBJECT-TYPE
   SYNTAX     SEQUENCE OF VrIpRelayBCPortRowStatusEntry
   ACCESS     not-accessible
   STATUS     mandatory
   DESCRIPTION
     "This entry controls the addition and deletion of 
      vrIpRelayBCPort components."
::= { vrIpRelayBCPort 1 }

vrIpRelayBCPortRowStatusEntry OBJECT-TYPE
   SYNTAX     VrIpRelayBCPortRowStatusEntry
   ACCESS     not-accessible
   STATUS     mandatory
   DESCRIPTION
     "A single entry in the table represents a single 
      vrIpRelayBCPort component."
   INDEX {
      vrIndex,
      vrIpIndex,
      vrIpRelayBCIndex,
      vrIpRelayBCPortPortNumIndex }
::= { vrIpRelayBCPortRowStatusTable 1 }

VrIpRelayBCPortRowStatusEntry ::= SEQUENCE {
   vrIpRelayBCPortRowStatus
      RowStatus,
   vrIpRelayBCPortComponentName
      DisplayString,
   vrIpRelayBCPortStorageType
      StorageType,
   vrIpRelayBCPortPortNumIndex
      Integer32 }

vrIpRelayBCPortRowStatus OBJECT-TYPE
   SYNTAX     RowStatus 
   ACCESS     read-write
   STATUS     mandatory
   DESCRIPTION
     "This variable is used as the basis for SNMP naming of
      vrIpRelayBCPort components.
      These components can be added and deleted."
::= { vrIpRelayBCPortRowStatusEntry 1 }

vrIpRelayBCPortComponentName OBJECT-TYPE
   SYNTAX     DisplayString 
   ACCESS     read-only
   STATUS     mandatory
   DESCRIPTION
     "This variable provides the component's string name for
      use with the ASCII Console Interface"
::= { vrIpRelayBCPortRowStatusEntry 2 }

vrIpRelayBCPortStorageType OBJECT-TYPE
   SYNTAX     StorageType 
   ACCESS     read-only
   STATUS     mandatory
   DESCRIPTION
     "This variable represents the storage type value for the
      vrIpRelayBCPort tables."
::= { vrIpRelayBCPortRowStatusEntry 4 }

vrIpRelayBCPortPortNumIndex OBJECT-TYPE
   SYNTAX     Integer32 (0..268435455)
   ACCESS     not-accessible
   STATUS     mandatory
   DESCRIPTION
     "This variable represents the index for the vrIpRelayBCPort tables."
::= { vrIpRelayBCPortRowStatusEntry 10 }

vrIpRelayBCPortOperTable OBJECT-TYPE
   SYNTAX     SEQUENCE OF VrIpRelayBCPortOperEntry
   ACCESS     not-accessible
   STATUS     mandatory
   DESCRIPTION
     "This group contains statistics related to InwPortEntry."
::= { vrIpRelayBCPort 10 }

vrIpRelayBCPortOperEntry OBJECT-TYPE
   SYNTAX     VrIpRelayBCPortOperEntry
   ACCESS     not-accessible
   STATUS     mandatory
   DESCRIPTION
     "An entry in the vrIpRelayBCPortOperTable."
   INDEX {
      vrIndex,
      vrIpIndex,
      vrIpRelayBCIndex,
      vrIpRelayBCPortPortNumIndex }
::= { vrIpRelayBCPortOperTable 1 }

VrIpRelayBCPortOperEntry ::= SEQUENCE {
   vrIpRelayBCPortRelayBcUdpCount
      Counter32 }

vrIpRelayBCPortRelayBcUdpCount OBJECT-TYPE
   SYNTAX     Counter32 
   ACCESS     read-only
   STATUS     mandatory
   DESCRIPTION
     "Indicates the number of forwarded packets with this destination UDP 
      port number. relayBcUdpCount wraps to zero if reached its maximum."
::= { vrIpRelayBCPortOperEntry 1 }


-- Vr/<string> Ip Udp
-- Udp component controls all UDP related attributes supported by this 
-- router.

vrIpUdp OBJECT IDENTIFIER ::= { vrIp 14 }



vrIpUdpRowStatusTable OBJECT-TYPE
   SYNTAX     SEQUENCE OF VrIpUdpRowStatusEntry
   ACCESS     not-accessible
   STATUS     mandatory
   DESCRIPTION
     "This entry controls the addition and deletion of 
      vrIpUdp components."
::= { vrIpUdp 1 }

vrIpUdpRowStatusEntry OBJECT-TYPE
   SYNTAX     VrIpUdpRowStatusEntry
   ACCESS     not-accessible
   STATUS     mandatory
   DESCRIPTION
     "A single entry in the table represents a single 
      vrIpUdp component."
   INDEX {
      vrIndex,
      vrIpIndex,
      vrIpUdpIndex }
::= { vrIpUdpRowStatusTable 1 }

VrIpUdpRowStatusEntry ::= SEQUENCE {
   vrIpUdpRowStatus
      RowStatus,
   vrIpUdpComponentName
      DisplayString,
   vrIpUdpStorageType
      StorageType,
   vrIpUdpIndex
      NonReplicated }

vrIpUdpRowStatus OBJECT-TYPE
   SYNTAX     RowStatus 
   ACCESS     read-only
   STATUS     mandatory
   DESCRIPTION
     "This variable is used as the basis for SNMP naming of
      vrIpUdp components.
      These components cannot be added nor deleted."
::= { vrIpUdpRowStatusEntry 1 }

vrIpUdpComponentName OBJECT-TYPE
   SYNTAX     DisplayString 
   ACCESS     read-only
   STATUS     mandatory
   DESCRIPTION
     "This variable provides the component's string name for
      use with the ASCII Console Interface"
::= { vrIpUdpRowStatusEntry 2 }

vrIpUdpStorageType OBJECT-TYPE
   SYNTAX     StorageType 
   ACCESS     read-only
   STATUS     mandatory
   DESCRIPTION
     "This variable represents the storage type value for the
      vrIpUdp tables."
::= { vrIpUdpRowStatusEntry 4 }

vrIpUdpIndex OBJECT-TYPE
   SYNTAX     NonReplicated 
   ACCESS     not-accessible
   STATUS     mandatory
   DESCRIPTION
     "This variable represents the index for the vrIpUdp tables."
::= { vrIpUdpRowStatusEntry 10 }

vrIpUdpStatsTable OBJECT-TYPE
   SYNTAX     SEQUENCE OF VrIpUdpStatsEntry
   ACCESS     not-accessible
   STATUS     mandatory
   DESCRIPTION
     "This group holds statictics for UDP."
::= { vrIpUdp 10 }

vrIpUdpStatsEntry OBJECT-TYPE
   SYNTAX     VrIpUdpStatsEntry
   ACCESS     not-accessible
   STATUS     mandatory
   DESCRIPTION
     "An entry in the vrIpUdpStatsTable."
   INDEX {
      vrIndex,
      vrIpIndex,
      vrIpUdpIndex }
::= { vrIpUdpStatsTable 1 }

VrIpUdpStatsEntry ::= SEQUENCE {
   vrIpUdpInDatagrams
      Counter32,
   vrIpUdpNoPorts
      Counter32,
   vrIpUdpInErrors
      Counter32,
   vrIpUdpOutDatagrams
      Counter32 }

vrIpUdpInDatagrams OBJECT-TYPE
   SYNTAX     Counter32 
   ACCESS     read-only
   STATUS     mandatory
   DESCRIPTION
     "The number of UDP datagrams delivered to UDP users. inDatagrams 
      wraps to zero if reaches its maximum defined value."
::= { vrIpUdpStatsEntry 1 }

vrIpUdpNoPorts OBJECT-TYPE
   SYNTAX     Counter32 
   ACCESS     read-only
   STATUS     mandatory
   DESCRIPTION
     "The number of UDP datagrams received for which there was no 
      application at the destination port. noPorts wraps to zero if reaches its 
      maximum defined value."
::= { vrIpUdpStatsEntry 2 }

vrIpUdpInErrors OBJECT-TYPE
   SYNTAX     Counter32 
   ACCESS     read-only
   STATUS     mandatory
   DESCRIPTION
     "The number of received UDP datagrams that could not be delivered for 
      reasons other than the lack of an application at the destination port. 
      inErrors wraps to zero if reaches its maximum defined value."
::= { vrIpUdpStatsEntry 3 }

vrIpUdpOutDatagrams OBJECT-TYPE
   SYNTAX     Counter32 
   ACCESS     read-only
   STATUS     mandatory
   DESCRIPTION
     "The number of UDP datagrams sent from this gateway. outDatagrams 
      wraps to zero if reaches its maximum defined value."
::= { vrIpUdpStatsEntry 4 }

-- 
-- *** THIS SUBTREE CURRENTLY NOT IMPLEMENTED ***
-- 

-- The table contains UDP listener information.

vrIpUdpListenEntry OBJECT IDENTIFIER ::= { vrIpUdp 2 }



vrIpUdpListenEntryRowStatusTable OBJECT-TYPE
   SYNTAX     SEQUENCE OF VrIpUdpListenEntryRowStatusEntry
   ACCESS     not-accessible
   STATUS     mandatory
   DESCRIPTION
     "*** THIS TABLE CURRENTLY NOT IMPLEMENTED ***

      This entry controls the addition and deletion of 
      vrIpUdpListenEntry components."
::= { vrIpUdpListenEntry 1 }

vrIpUdpListenEntryRowStatusEntry OBJECT-TYPE
   SYNTAX     VrIpUdpListenEntryRowStatusEntry
   ACCESS     not-accessible
   STATUS     mandatory
   DESCRIPTION
     "A single entry in the table represents a single 
      vrIpUdpListenEntry component."
   INDEX {
      vrIndex,
      vrIpIndex,
      vrIpUdpIndex,
      vrIpUdpListenEntryLocalAddressIndex,
      vrIpUdpListenEntryLocalPortIndex }
::= { vrIpUdpListenEntryRowStatusTable 1 }

VrIpUdpListenEntryRowStatusEntry ::= SEQUENCE {
   vrIpUdpListenEntryRowStatus
      RowStatus,
   vrIpUdpListenEntryComponentName
      DisplayString,
   vrIpUdpListenEntryStorageType
      StorageType,
   vrIpUdpListenEntryLocalAddressIndex
      IpAddress,
   vrIpUdpListenEntryLocalPortIndex
      Integer32 }

vrIpUdpListenEntryRowStatus OBJECT-TYPE
   SYNTAX     RowStatus 
   ACCESS     read-only
   STATUS     mandatory
   DESCRIPTION
     "This variable is used as the basis for SNMP naming of
      vrIpUdpListenEntry components.
      These components cannot be added nor deleted."
::= { vrIpUdpListenEntryRowStatusEntry 1 }

vrIpUdpListenEntryComponentName OBJECT-TYPE
   SYNTAX     DisplayString 
   ACCESS     read-only
   STATUS     mandatory
   DESCRIPTION
     "This variable provides the component's string name for
      use with the ASCII Console Interface"
::= { vrIpUdpListenEntryRowStatusEntry 2 }

vrIpUdpListenEntryStorageType OBJECT-TYPE
   SYNTAX     StorageType 
   ACCESS     read-only
   STATUS     mandatory
   DESCRIPTION
     "This variable represents the storage type value for the
      vrIpUdpListenEntry tables."
::= { vrIpUdpListenEntryRowStatusEntry 4 }

vrIpUdpListenEntryLocalAddressIndex OBJECT-TYPE
   SYNTAX     IpAddress 
   ACCESS     not-accessible
   STATUS     mandatory
   DESCRIPTION
     "This variable represents an index for the vrIpUdpListenEntry tables."
::= { vrIpUdpListenEntryRowStatusEntry 10 }

vrIpUdpListenEntryLocalPortIndex OBJECT-TYPE
   SYNTAX     Integer32 (0..65535)
   ACCESS     not-accessible
   STATUS     mandatory
   DESCRIPTION
     "This variable represents an index for the vrIpUdpListenEntry tables."
::= { vrIpUdpListenEntryRowStatusEntry 11 }


-- The Tcp component contains all attributes related to TCP.

vrIpTcp OBJECT IDENTIFIER ::= { vrIp 15 }



vrIpTcpRowStatusTable OBJECT-TYPE
   SYNTAX     SEQUENCE OF VrIpTcpRowStatusEntry
   ACCESS     not-accessible
   STATUS     mandatory
   DESCRIPTION
     "This entry controls the addition and deletion of 
      vrIpTcp components."
::= { vrIpTcp 1 }

vrIpTcpRowStatusEntry OBJECT-TYPE
   SYNTAX     VrIpTcpRowStatusEntry
   ACCESS     not-accessible
   STATUS     mandatory
   DESCRIPTION
     "A single entry in the table represents a single 
      vrIpTcp component."
   INDEX {
      vrIndex,
      vrIpIndex,
      vrIpTcpIndex }
::= { vrIpTcpRowStatusTable 1 }

VrIpTcpRowStatusEntry ::= SEQUENCE {
   vrIpTcpRowStatus
      RowStatus,
   vrIpTcpComponentName
      DisplayString,
   vrIpTcpStorageType
      StorageType,
   vrIpTcpIndex
      NonReplicated }

vrIpTcpRowStatus OBJECT-TYPE
   SYNTAX     RowStatus 
   ACCESS     read-only
   STATUS     mandatory
   DESCRIPTION
     "This variable is used as the basis for SNMP naming of
      vrIpTcp components.
      These components cannot be added nor deleted."
::= { vrIpTcpRowStatusEntry 1 }

vrIpTcpComponentName OBJECT-TYPE
   SYNTAX     DisplayString 
   ACCESS     read-only
   STATUS     mandatory
   DESCRIPTION
     "This variable provides the component's string name for
      use with the ASCII Console Interface"
::= { vrIpTcpRowStatusEntry 2 }

vrIpTcpStorageType OBJECT-TYPE
   SYNTAX     StorageType 
   ACCESS     read-only
   STATUS     mandatory
   DESCRIPTION
     "This variable represents the storage type value for the
      vrIpTcp tables."
::= { vrIpTcpRowStatusEntry 4 }

vrIpTcpIndex OBJECT-TYPE
   SYNTAX     NonReplicated 
   ACCESS     not-accessible
   STATUS     mandatory
   DESCRIPTION
     "This variable represents the index for the vrIpTcp tables."
::= { vrIpTcpRowStatusEntry 10 }

vrIpTcpStatsTable OBJECT-TYPE
   SYNTAX     SEQUENCE OF VrIpTcpStatsEntry
   ACCESS     not-accessible
   STATUS     mandatory
   DESCRIPTION
     "This group contains statistics for TCP."
::= { vrIpTcp 10 }

vrIpTcpStatsEntry OBJECT-TYPE
   SYNTAX     VrIpTcpStatsEntry
   ACCESS     not-accessible
   STATUS     mandatory
   DESCRIPTION
     "An entry in the vrIpTcpStatsTable."
   INDEX {
      vrIndex,
      vrIpIndex,
      vrIpTcpIndex }
::= { vrIpTcpStatsTable 1 }

VrIpTcpStatsEntry ::= SEQUENCE {
   vrIpTcpRToAlgorithm
      INTEGER,
   vrIpTcpRToMin
      Unsigned32,
   vrIpTcpRToMax
      Unsigned32,
   vrIpTcpMaxConn
      INTEGER,
   vrIpTcpActiveOpens
      Counter32,
   vrIpTcpPassiveOpens
      Counter32,
   vrIpTcpAttemptFails
      Counter32,
   vrIpTcpEstabResets
      Counter32,
   vrIpTcpCurrEstab
      Gauge32,
   vrIpTcpInSegs
      Counter32,
   vrIpTcpOutSegs
      Counter32,
   vrIpTcpRetransSegs
      Counter32,
   vrIpTcpInErrs
      Counter32,
   vrIpTcpOutRsts
      Counter32 }

vrIpTcpRToAlgorithm OBJECT-TYPE
   SYNTAX     INTEGER  {
                 other(1),
                 constant(2),
                 rsre(3),
                 vanJacobson(4) }
   ACCESS     read-only
   STATUS     mandatory
   DESCRIPTION
     "Indicate which algorithm was used to calculate the timeout value used 
      for retransmitting unackowledged octet."
::= { vrIpTcpStatsEntry 1 }

vrIpTcpRToMin OBJECT-TYPE
   SYNTAX     Unsigned32 (0..4294967295)
   ACCESS     read-only
   STATUS     mandatory
   DESCRIPTION
     "Indicate the minimum value, measured in milliseconds, allowed for 
      retransmission timeout."
   DEFVAL     { 0 }
::= { vrIpTcpStatsEntry 2 }

vrIpTcpRToMax OBJECT-TYPE
   SYNTAX     Unsigned32 (0..4294967295)
   ACCESS     read-only
   STATUS     mandatory
   DESCRIPTION
     "Indicates the maximun value, measured in milliseconds, allowed for 
      retransmission timeout."
::= { vrIpTcpStatsEntry 3 }

vrIpTcpMaxConn OBJECT-TYPE
   SYNTAX     INTEGER (-1)
   ACCESS     read-only
   STATUS     mandatory
   DESCRIPTION
     "Limit on number of connections the TCP can support. The value is 
      always -1 which indicates that the number of connections supported is 
      dynamic (limited by memory in the system)."
   DEFVAL     { -1 }
::= { vrIpTcpStatsEntry 4 }

vrIpTcpActiveOpens OBJECT-TYPE
   SYNTAX     Counter32 
   ACCESS     read-only
   STATUS     mandatory
   DESCRIPTION
     "The number of times TCP connections have made a direct transition to 
      the synSent state from the closed state."
::= { vrIpTcpStatsEntry 5 }

vrIpTcpPassiveOpens OBJECT-TYPE
   SYNTAX     Counter32 
   ACCESS     read-only
   STATUS     mandatory
   DESCRIPTION
     "The number of times TCP connections have made a direct transition to 
      the synRcvd state from the listen state."
::= { vrIpTcpStatsEntry 6 }

vrIpTcpAttemptFails OBJECT-TYPE
   SYNTAX     Counter32 
   ACCESS     read-only
   STATUS     mandatory
   DESCRIPTION
     "The number of times TCP connections have made a direct transition to 
      the closed state from either the synSent state or the synRcvd state, plus 
      the number of times TCP connections have made a direct transition to 
      the listen state from the synRcvd state."
::= { vrIpTcpStatsEntry 7 }

vrIpTcpEstabResets OBJECT-TYPE
   SYNTAX     Counter32 
   ACCESS     read-only
   STATUS     mandatory
   DESCRIPTION
     "The number of times TCP connections have made a direct transition to 
      the closed state from either the established state or the closedWait state."
::= { vrIpTcpStatsEntry 8 }

vrIpTcpCurrEstab OBJECT-TYPE
   SYNTAX     Gauge32 (0..4294967295)
   ACCESS     read-only
   STATUS     mandatory
   DESCRIPTION
     "The number of TCP connections for which the current state is either 
      established or closedWait."
::= { vrIpTcpStatsEntry 9 }

vrIpTcpInSegs OBJECT-TYPE
   SYNTAX     Counter32 
   ACCESS     read-only
   STATUS     mandatory
   DESCRIPTION
     "The number of segments received, including those received in error. 
      This count includes segments received on currently established 
      connections."
::= { vrIpTcpStatsEntry 10 }

vrIpTcpOutSegs OBJECT-TYPE
   SYNTAX     Counter32 
   ACCESS     read-only
   STATUS     mandatory
   DESCRIPTION
     "The number of segments sent, including those on current connections 
      but excluding those containing only retransmitted octets."
::= { vrIpTcpStatsEntry 11 }

vrIpTcpRetransSegs OBJECT-TYPE
   SYNTAX     Counter32 
   ACCESS     read-only
   STATUS     mandatory
   DESCRIPTION
     "The number of segments retransmitted that is, the number of TCP 
      segments transmitted containing one or more previously transmitted 
      octets."
::= { vrIpTcpStatsEntry 12 }

vrIpTcpInErrs OBJECT-TYPE
   SYNTAX     Counter32 
   ACCESS     read-only
   STATUS     mandatory
   DESCRIPTION
     "Total number of segments received in error, for example bad TCP 
      checksum."
::= { vrIpTcpStatsEntry 13 }

vrIpTcpOutRsts OBJECT-TYPE
   SYNTAX     Counter32 
   ACCESS     read-only
   STATUS     mandatory
   DESCRIPTION
     "Number of TCP segments sent containing the RST flag."
::= { vrIpTcpStatsEntry 14 }

-- 
-- *** THIS SUBTREE CURRENTLY NOT IMPLEMENTED ***
-- 

-- The component defines an entry in the TCP connection table. Each entry 
-- corresponds to TCP end-point identified by 4-tuples, LocalAddress, 
-- LocalPort, RemoteAddress, and RemotePort. 

vrIpTcpTcpEntry OBJECT IDENTIFIER ::= { vrIpTcp 2 }



vrIpTcpTcpEntryRowStatusTable OBJECT-TYPE
   SYNTAX     SEQUENCE OF VrIpTcpTcpEntryRowStatusEntry
   ACCESS     not-accessible
   STATUS     mandatory
   DESCRIPTION
     "*** THIS TABLE CURRENTLY NOT IMPLEMENTED ***

      This entry controls the addition and deletion of 
      vrIpTcpTcpEntry components."
::= { vrIpTcpTcpEntry 1 }

vrIpTcpTcpEntryRowStatusEntry OBJECT-TYPE
   SYNTAX     VrIpTcpTcpEntryRowStatusEntry
   ACCESS     not-accessible
   STATUS     mandatory
   DESCRIPTION
     "A single entry in the table represents a single 
      vrIpTcpTcpEntry component."
   INDEX {
      vrIndex,
      vrIpIndex,
      vrIpTcpIndex,
      vrIpTcpTcpEntryLocalAddressIndex,
      vrIpTcpTcpEntryLocalPortIndex,
      vrIpTcpTcpEntryRemoteAddressIndex,
      vrIpTcpTcpEntryRemotePortIndex }
::= { vrIpTcpTcpEntryRowStatusTable 1 }

VrIpTcpTcpEntryRowStatusEntry ::= SEQUENCE {
   vrIpTcpTcpEntryRowStatus
      RowStatus,
   vrIpTcpTcpEntryComponentName
      DisplayString,
   vrIpTcpTcpEntryStorageType
      StorageType,
   vrIpTcpTcpEntryLocalAddressIndex
      IpAddress,
   vrIpTcpTcpEntryLocalPortIndex
      Integer32,
   vrIpTcpTcpEntryRemoteAddressIndex
      IpAddress,
   vrIpTcpTcpEntryRemotePortIndex
      Integer32 }

vrIpTcpTcpEntryRowStatus OBJECT-TYPE
   SYNTAX     RowStatus 
   ACCESS     read-only
   STATUS     mandatory
   DESCRIPTION
     "This variable is used as the basis for SNMP naming of
      vrIpTcpTcpEntry components.
      These components cannot be added nor deleted."
::= { vrIpTcpTcpEntryRowStatusEntry 1 }

vrIpTcpTcpEntryComponentName OBJECT-TYPE
   SYNTAX     DisplayString 
   ACCESS     read-only
   STATUS     mandatory
   DESCRIPTION
     "This variable provides the component's string name for
      use with the ASCII Console Interface"
::= { vrIpTcpTcpEntryRowStatusEntry 2 }

vrIpTcpTcpEntryStorageType OBJECT-TYPE
   SYNTAX     StorageType 
   ACCESS     read-only
   STATUS     mandatory
   DESCRIPTION
     "This variable represents the storage type value for the
      vrIpTcpTcpEntry tables."
::= { vrIpTcpTcpEntryRowStatusEntry 4 }

vrIpTcpTcpEntryLocalAddressIndex OBJECT-TYPE
   SYNTAX     IpAddress 
   ACCESS     not-accessible
   STATUS     mandatory
   DESCRIPTION
     "This variable represents an index for the vrIpTcpTcpEntry tables."
::= { vrIpTcpTcpEntryRowStatusEntry 10 }

vrIpTcpTcpEntryLocalPortIndex OBJECT-TYPE
   SYNTAX     Integer32 (0..65535)
   ACCESS     not-accessible
   STATUS     mandatory
   DESCRIPTION
     "This variable represents an index for the vrIpTcpTcpEntry tables."
::= { vrIpTcpTcpEntryRowStatusEntry 11 }

vrIpTcpTcpEntryRemoteAddressIndex OBJECT-TYPE
   SYNTAX     IpAddress 
   ACCESS     not-accessible
   STATUS     mandatory
   DESCRIPTION
     "This variable represents an index for the vrIpTcpTcpEntry tables."
::= { vrIpTcpTcpEntryRowStatusEntry 12 }

vrIpTcpTcpEntryRemotePortIndex OBJECT-TYPE
   SYNTAX     Integer32 (0..65535)
   ACCESS     not-accessible
   STATUS     mandatory
   DESCRIPTION
     "This variable represents an index for the vrIpTcpTcpEntry tables."
::= { vrIpTcpTcpEntryRowStatusEntry 13 }

vrIpTcpTcpEntryOperTable OBJECT-TYPE
   SYNTAX     SEQUENCE OF VrIpTcpTcpEntryOperEntry
   ACCESS     not-accessible
   STATUS     mandatory
   DESCRIPTION
     "*** THIS TABLE CURRENTLY NOT IMPLEMENTED ***

      This group contains columnar entries for each end-point on the TCP."
::= { vrIpTcpTcpEntry 10 }

vrIpTcpTcpEntryOperEntry OBJECT-TYPE
   SYNTAX     VrIpTcpTcpEntryOperEntry
   ACCESS     not-accessible
   STATUS     mandatory
   DESCRIPTION
     "An entry in the vrIpTcpTcpEntryOperTable."
   INDEX {
      vrIndex,
      vrIpIndex,
      vrIpTcpIndex,
      vrIpTcpTcpEntryLocalAddressIndex,
      vrIpTcpTcpEntryLocalPortIndex,
      vrIpTcpTcpEntryRemoteAddressIndex,
      vrIpTcpTcpEntryRemotePortIndex }
::= { vrIpTcpTcpEntryOperTable 1 }

VrIpTcpTcpEntryOperEntry ::= SEQUENCE {
   vrIpTcpTcpEntryState
      INTEGER }

vrIpTcpTcpEntryState OBJECT-TYPE
   SYNTAX     INTEGER  {
                 closed(1),
                 listen(2),
                 synSent(3),
                 synReceived(4),
                 established(5),
                 closeWait(6),
                 finWait1(7),
                 closing(8),
                 lastAck(9),
                 finWait2(10),
                 timeWait(11),
                 delete(12) }
   ACCESS     read-write
   STATUS     mandatory
   DESCRIPTION
     "This attribute reflects the current state of this Tcp connection."
::= { vrIpTcpTcpEntryOperEntry 1 }


-- Vr/<string> Ip BootpRelayAgent
-- The BootpRelayAgent component contains all the necessary attributes 
-- and components to provision a BOOTP relay agent. The BOOTP relay 
-- agent functionality conforms to that described in RFCs 951 and 1542.
-- 
-- The purpose of the BOOTP relay agent is to forward BOOTP request 
-- packets from a client to a server, and also to deliver server BOOTP 
-- replies back to the client. When a BOOTP request is received on a port, 
-- the request will be sent to a provisioned list of IP addresses for that port. 
-- In addition, the request will be broadcast out all other BOOTP ports 
-- which allow it.

vrIpBootp OBJECT IDENTIFIER ::= { vrIp 16 }



vrIpBootpRowStatusTable OBJECT-TYPE
   SYNTAX     SEQUENCE OF VrIpBootpRowStatusEntry
   ACCESS     not-accessible
   STATUS     mandatory
   DESCRIPTION
     "This entry controls the addition and deletion of 
      vrIpBootp components."
::= { vrIpBootp 1 }

vrIpBootpRowStatusEntry OBJECT-TYPE
   SYNTAX     VrIpBootpRowStatusEntry
   ACCESS     not-accessible
   STATUS     mandatory
   DESCRIPTION
     "A single entry in the table represents a single 
      vrIpBootp component."
   INDEX {
      vrIndex,
      vrIpIndex,
      vrIpBootpIndex }
::= { vrIpBootpRowStatusTable 1 }

VrIpBootpRowStatusEntry ::= SEQUENCE {
   vrIpBootpRowStatus
      RowStatus,
   vrIpBootpComponentName
      DisplayString,
   vrIpBootpStorageType
      StorageType,
   vrIpBootpIndex
      NonReplicated }

vrIpBootpRowStatus OBJECT-TYPE
   SYNTAX     RowStatus 
   ACCESS     read-write
   STATUS     mandatory
   DESCRIPTION
     "This variable is used as the basis for SNMP naming of
      vrIpBootp components.
      These components can be added and deleted."
::= { vrIpBootpRowStatusEntry 1 }

vrIpBootpComponentName OBJECT-TYPE
   SYNTAX     DisplayString 
   ACCESS     read-only
   STATUS     mandatory
   DESCRIPTION
     "This variable provides the component's string name for
      use with the ASCII Console Interface"
::= { vrIpBootpRowStatusEntry 2 }

vrIpBootpStorageType OBJECT-TYPE
   SYNTAX     StorageType 
   ACCESS     read-only
   STATUS     mandatory
   DESCRIPTION
     "This variable represents the storage type value for the
      vrIpBootp tables."
::= { vrIpBootpRowStatusEntry 4 }

vrIpBootpIndex OBJECT-TYPE
   SYNTAX     NonReplicated 
   ACCESS     not-accessible
   STATUS     mandatory
   DESCRIPTION
     "This variable represents the index for the vrIpBootp tables."
::= { vrIpBootpRowStatusEntry 10 }

vrIpBootpAdminControlTable OBJECT-TYPE
   SYNTAX     SEQUENCE OF VrIpBootpAdminControlEntry
   ACCESS     not-accessible
   STATUS     mandatory
   DESCRIPTION
     "This group includes the Administrative Control attribute. This 
      attribute defines the current administrative state of this component."
::= { vrIpBootp 10 }

vrIpBootpAdminControlEntry OBJECT-TYPE
   SYNTAX     VrIpBootpAdminControlEntry
   ACCESS     not-accessible
   STATUS     mandatory
   DESCRIPTION
     "An entry in the vrIpBootpAdminControlTable."
   INDEX {
      vrIndex,
      vrIpIndex,
      vrIpBootpIndex }
::= { vrIpBootpAdminControlTable 1 }

VrIpBootpAdminControlEntry ::= SEQUENCE {
   vrIpBootpSnmpAdminStatus
      INTEGER }

vrIpBootpSnmpAdminStatus OBJECT-TYPE
   SYNTAX     INTEGER  {
                 up(1),
                 down(2),
                 testing(3) }
   ACCESS     read-write
   STATUS     mandatory
   DESCRIPTION
     "The desired state of the interface. The up state indicates the 
      interface is operational and packet forwarding is allowed. The down 
      state indicates the interface is not operational and packet forwarding 
      is unavailable. The testing state indicates that no operational 
      packets can be passed."
   DEFVAL     { up }
::= { vrIpBootpAdminControlEntry 1 }

vrIpBootpProvTable OBJECT-TYPE
   SYNTAX     SEQUENCE OF VrIpBootpProvEntry
   ACCESS     not-accessible
   STATUS     mandatory
   DESCRIPTION
     "This group contains provisionable attributes for the BootpRelayAgent 
      component."
::= { vrIpBootp 11 }

vrIpBootpProvEntry OBJECT-TYPE
   SYNTAX     VrIpBootpProvEntry
   ACCESS     not-accessible
   STATUS     mandatory
   DESCRIPTION
     "An entry in the vrIpBootpProvTable."
   INDEX {
      vrIndex,
      vrIpIndex,
      vrIpBootpIndex }
::= { vrIpBootpProvTable 1 }

VrIpBootpProvEntry ::= SEQUENCE {
   vrIpBootpHopDiscardThreshold
      Unsigned32 }

vrIpBootpHopDiscardThreshold OBJECT-TYPE
   SYNTAX     Unsigned32 (2..16)
   ACCESS     read-write
   STATUS     mandatory
   DESCRIPTION
     "BOOTP packets contain a 'hops' field which is used to limit the number 
      of relay agents that can process the packet (each relay agent increments 
      the 'hops' field by one). This attribute is used by the relay agent to 
      determine when to discard a BOOTP packet. If the 'hops' field exceeds 
      the hopDiscardThreshold the BOOTP packet will be discarded."
   DEFVAL     { 4 }
::= { vrIpBootpProvEntry 1 }

vrIpBootpStateTable OBJECT-TYPE
   SYNTAX     SEQUENCE OF VrIpBootpStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { vrIpBootp 12 }

vrIpBootpStateEntry OBJECT-TYPE
   SYNTAX     VrIpBootpStateEntry
   ACCESS     not-accessible
   STATUS     mandatory
   DESCRIPTION
     "An entry in the vrIpBootpStateTable."
   INDEX {
      vrIndex,
      vrIpIndex,
      vrIpBootpIndex }
::= { vrIpBootpStateTable 1 }

VrIpBootpStateEntry ::= SEQUENCE {
   vrIpBootpAdminState
      INTEGER,
   vrIpBootpOperationalState
      INTEGER,
   vrIpBootpUsageState
      INTEGER }

vrIpBootpAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { vrIpBootpStateEntry 1 }

vrIpBootpOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { vrIpBootpStateEntry 2 }

vrIpBootpUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { vrIpBootpStateEntry 3 }

vrIpBootpOperStatusTable OBJECT-TYPE
   SYNTAX     SEQUENCE OF VrIpBootpOperStatusEntry
   ACCESS     not-accessible
   STATUS     mandatory
   DESCRIPTION
     "This group includes the Operational Status attribute. This attribute 
      defines the current operational state of this component."
::= { vrIpBootp 13 }

vrIpBootpOperStatusEntry OBJECT-TYPE
   SYNTAX     VrIpBootpOperStatusEntry
   ACCESS     not-accessible
   STATUS     mandatory
   DESCRIPTION
     "An entry in the vrIpBootpOperStatusTable."
   INDEX {
      vrIndex,
      vrIpIndex,
      vrIpBootpIndex }
::= { vrIpBootpOperStatusTable 1 }

VrIpBootpOperStatusEntry ::= SEQUENCE {
   vrIpBootpSnmpOperStatus
      INTEGER }

vrIpBootpSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { vrIpBootpOperStatusEntry 1 }

-- 
-- *** THIS SUBTREE CURRENTLY NOT IMPLEMENTED ***
-- 

-- Vr/<string> Ip BootpRelayAgent BootpPortEntry/<string>
-- The BootpPortEntry component contains information about the 
-- provisioned BootpPort's under IpPort components. This component is 
-- indexed by a string which represents a VirtualRouter ProtocolPort 
-- component name.

vrIpBootpPpE OBJECT IDENTIFIER ::= { vrIpBootp 2 }



vrIpBootpPpERowStatusTable OBJECT-TYPE
   SYNTAX     SEQUENCE OF VrIpBootpPpERowStatusEntry
   ACCESS     not-accessible
   STATUS     mandatory
   DESCRIPTION
     "*** THIS TABLE CURRENTLY NOT IMPLEMENTED ***

      This entry controls the addition and deletion of 
      vrIpBootpPpE components."
::= { vrIpBootpPpE 1 }

vrIpBootpPpERowStatusEntry OBJECT-TYPE
   SYNTAX     VrIpBootpPpERowStatusEntry
   ACCESS     not-accessible
   STATUS     mandatory
   DESCRIPTION
     "A single entry in the table represents a single 
      vrIpBootpPpE component."
   INDEX {
      vrIndex,
      vrIpIndex,
      vrIpBootpIndex,
      vrIpBootpPpEIndex }
::= { vrIpBootpPpERowStatusTable 1 }

VrIpBootpPpERowStatusEntry ::= SEQUENCE {
   vrIpBootpPpERowStatus
      RowStatus,
   vrIpBootpPpEComponentName
      DisplayString,
   vrIpBootpPpEStorageType
      StorageType,
   vrIpBootpPpEIndex
      AsciiStringIndex }

vrIpBootpPpERowStatus OBJECT-TYPE
   SYNTAX     RowStatus 
   ACCESS     read-only
   STATUS     mandatory
   DESCRIPTION
     "This variable is used as the basis for SNMP naming of
      vrIpBootpPpE components.
      These components cannot be added nor deleted."
::= { vrIpBootpPpERowStatusEntry 1 }

vrIpBootpPpEComponentName OBJECT-TYPE
   SYNTAX     DisplayString 
   ACCESS     read-only
   STATUS     mandatory
   DESCRIPTION
     "This variable provides the component's string name for
      use with the ASCII Console Interface"
::= { vrIpBootpPpERowStatusEntry 2 }

vrIpBootpPpEStorageType OBJECT-TYPE
   SYNTAX     StorageType 
   ACCESS     read-only
   STATUS     mandatory
   DESCRIPTION
     "This variable represents the storage type value for the
      vrIpBootpPpE tables."
::= { vrIpBootpPpERowStatusEntry 4 }

vrIpBootpPpEIndex OBJECT-TYPE
   SYNTAX     AsciiStringIndex (SIZE (1..20))
   ACCESS     not-accessible
   STATUS     mandatory
   DESCRIPTION
     "This variable represents the index for the vrIpBootpPpE tables."
::= { vrIpBootpPpERowStatusEntry 10 }

vrIpBootpPpEOperTable OBJECT-TYPE
   SYNTAX     SEQUENCE OF VrIpBootpPpEOperEntry
   ACCESS     not-accessible
   STATUS     mandatory
   DESCRIPTION
     "*** THIS TABLE CURRENTLY NOT IMPLEMENTED ***

      This group contains BootpPortEntry component operational data."
::= { vrIpBootpPpE 10 }

vrIpBootpPpEOperEntry OBJECT-TYPE
   SYNTAX     VrIpBootpPpEOperEntry
   ACCESS     not-accessible
   STATUS     mandatory
   DESCRIPTION
     "An entry in the vrIpBootpPpEOperTable."
   INDEX {
      vrIndex,
      vrIpIndex,
      vrIpBootpIndex,
      vrIpBootpPpEIndex }
::= { vrIpBootpPpEOperTable 1 }

VrIpBootpPpEOperEntry ::= SEQUENCE {
   vrIpBootpPpEStatus
      INTEGER }

vrIpBootpPpEStatus OBJECT-TYPE
   SYNTAX     INTEGER  {
                 up(1),
                 down(2),
                 disabled(3) }
   ACCESS     read-only
   STATUS     mandatory
   DESCRIPTION
     "This attribute indicates the status of the provisioned BootpPortEntry 
      component. A value of disabled is used when the parent components, 
      Vr, Ip, IpPort, or BootpRelayAgent is in a disabled state. A value of up 
      is used when the BootpPortEntry is in an operational state. A state of 
      down is used if the media associated with the BootpPortEntry is not 
      ready or disabled."
::= { vrIpBootpPpEOperEntry 1 }

vrIpBootpPpEStatsTable OBJECT-TYPE
   SYNTAX     SEQUENCE OF VrIpBootpPpEStatsEntry
   ACCESS     not-accessible
   STATUS     mandatory
   DESCRIPTION
     "*** THIS TABLE CURRENTLY NOT IMPLEMENTED ***

      This group contains BootpPortEntry component statistics."
::= { vrIpBootpPpE 11 }

vrIpBootpPpEStatsEntry OBJECT-TYPE
   SYNTAX     VrIpBootpPpEStatsEntry
   ACCESS     not-accessible
   STATUS     mandatory
   DESCRIPTION
     "An entry in the vrIpBootpPpEStatsTable."
   INDEX {
      vrIndex,
      vrIpIndex,
      vrIpBootpIndex,
      vrIpBootpPpEIndex }
::= { vrIpBootpPpEStatsTable 1 }

VrIpBootpPpEStatsEntry ::= SEQUENCE {
   vrIpBootpPpEInRequests
      Counter32,
   vrIpBootpPpEInReplies
      Counter32,
   vrIpBootpPpEOutRequests
      Counter32,
   vrIpBootpPpEOutReplies
      Counter32,
   vrIpBootpPpEInRequestErrors
      Counter32,
   vrIpBootpPpEInReplyErrors
      Counter32 }

vrIpBootpPpEInRequests OBJECT-TYPE
   SYNTAX     Counter32 
   ACCESS     read-only
   STATUS     mandatory
   DESCRIPTION
     "This attribute counts the total number of BOOTP Request messages 
      received on this port."
::= { vrIpBootpPpEStatsEntry 1 }

vrIpBootpPpEInReplies OBJECT-TYPE
   SYNTAX     Counter32 
   ACCESS     read-only
   STATUS     mandatory
   DESCRIPTION
     "This attribute counts the total number of BOOTP Reply messages 
      received on this port."
::= { vrIpBootpPpEStatsEntry 2 }

vrIpBootpPpEOutRequests OBJECT-TYPE
   SYNTAX     Counter32 
   ACCESS     read-only
   STATUS     mandatory
   DESCRIPTION
     "This attribute counts total the number of BOOTP Request messages 
      broadcast out on this port."
::= { vrIpBootpPpEStatsEntry 3 }

vrIpBootpPpEOutReplies OBJECT-TYPE
   SYNTAX     Counter32 
   ACCESS     read-only
   STATUS     mandatory
   DESCRIPTION
     "This attribute counts the total number of BOOTP Reply messages sent 
      out on this port."
::= { vrIpBootpPpEStatsEntry 4 }

vrIpBootpPpEInRequestErrors OBJECT-TYPE
   SYNTAX     Counter32 
   ACCESS     read-only
   STATUS     mandatory
   DESCRIPTION
     "This attribute counts the number of BOOTP Request messages received 
      on this port but not forwarded due to an error. An error occurs if the 
      BOOTP hop limit has been exceeded."
::= { vrIpBootpPpEStatsEntry 5 }

vrIpBootpPpEInReplyErrors OBJECT-TYPE
   SYNTAX     Counter32 
   ACCESS     read-only
   STATUS     mandatory
   DESCRIPTION
     "This attribute counts the number of BOOTP Reply messages received on 
      this port but not forwarded due to an error. An error occurs if the giaddr 
      field in the BOOTP reply does not match an IP address assigned to this 
      VirtualRouter, or if the output IpPort for the BOOTP reply is not 
      provisioned for BOOTP."
::= { vrIpBootpPpEStatsEntry 6 }

-- 
-- *** THIS SUBTREE CURRENTLY NOT IMPLEMENTED ***
-- 

-- Vr/<string> Ip Cache/n
-- This component represents the IP cache table on LP n.

vrIpCache OBJECT IDENTIFIER ::= { vrIp 17 }



vrIpCacheRowStatusTable OBJECT-TYPE
   SYNTAX     SEQUENCE OF VrIpCacheRowStatusEntry
   ACCESS     not-accessible
   STATUS     mandatory
   DESCRIPTION
     "*** THIS TABLE CURRENTLY NOT IMPLEMENTED ***

      This entry controls the addition and deletion of 
      vrIpCache components."
::= { vrIpCache 1 }

vrIpCacheRowStatusEntry OBJECT-TYPE
   SYNTAX     VrIpCacheRowStatusEntry
   ACCESS     not-accessible
   STATUS     mandatory
   DESCRIPTION
     "A single entry in the table represents a single 
      vrIpCache component."
   INDEX {
      vrIndex,
      vrIpIndex,
      vrIpCacheIndex }
::= { vrIpCacheRowStatusTable 1 }

VrIpCacheRowStatusEntry ::= SEQUENCE {
   vrIpCacheRowStatus
      RowStatus,
   vrIpCacheComponentName
      DisplayString,
   vrIpCacheStorageType
      StorageType,
   vrIpCacheIndex
      Integer32 }

vrIpCacheRowStatus OBJECT-TYPE
   SYNTAX     RowStatus 
   ACCESS     read-only
   STATUS     mandatory
   DESCRIPTION
     "This variable is used as the basis for SNMP naming of
      vrIpCache components.
      These components cannot be added nor deleted."
::= { vrIpCacheRowStatusEntry 1 }

vrIpCacheComponentName OBJECT-TYPE
   SYNTAX     DisplayString 
   ACCESS     read-only
   STATUS     mandatory
   DESCRIPTION
     "This variable provides the component's string name for
      use with the ASCII Console Interface"
::= { vrIpCacheRowStatusEntry 2 }

vrIpCacheStorageType OBJECT-TYPE
   SYNTAX     StorageType 
   ACCESS     read-only
   STATUS     mandatory
   DESCRIPTION
     "This variable represents the storage type value for the
      vrIpCache tables."
::= { vrIpCacheRowStatusEntry 4 }

vrIpCacheIndex OBJECT-TYPE
   SYNTAX     Integer32 (0..15)
   ACCESS     not-accessible
   STATUS     mandatory
   DESCRIPTION
     "This variable represents the index for the vrIpCache tables."
::= { vrIpCacheRowStatusEntry 10 }

vrIpCacheStateTable OBJECT-TYPE
   SYNTAX     SEQUENCE OF VrIpCacheStateEntry
   ACCESS     not-accessible
   STATUS     mandatory
   DESCRIPTION
     "*** THIS TABLE CURRENTLY NOT IMPLEMENTED ***

      This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { vrIpCache 10 }

vrIpCacheStateEntry OBJECT-TYPE
   SYNTAX     VrIpCacheStateEntry
   ACCESS     not-accessible
   STATUS     mandatory
   DESCRIPTION
     "An entry in the vrIpCacheStateTable."
   INDEX {
      vrIndex,
      vrIpIndex,
      vrIpCacheIndex }
::= { vrIpCacheStateTable 1 }

VrIpCacheStateEntry ::= SEQUENCE {
   vrIpCacheAdminState
      INTEGER,
   vrIpCacheOperationalState
      INTEGER,
   vrIpCacheUsageState
      INTEGER }

vrIpCacheAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { vrIpCacheStateEntry 1 }

vrIpCacheOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { vrIpCacheStateEntry 2 }

vrIpCacheUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { vrIpCacheStateEntry 3 }

vrIpCacheOperTable OBJECT-TYPE
   SYNTAX     SEQUENCE OF VrIpCacheOperEntry
   ACCESS     not-accessible
   STATUS     mandatory
   DESCRIPTION
     "*** THIS TABLE CURRENTLY NOT IMPLEMENTED ***

      This group houses all the operational attributes of an Ip cache table."
::= { vrIpCache 11 }

vrIpCacheOperEntry OBJECT-TYPE
   SYNTAX     VrIpCacheOperEntry
   ACCESS     not-accessible
   STATUS     mandatory
   DESCRIPTION
     "An entry in the vrIpCacheOperTable."
   INDEX {
      vrIndex,
      vrIpIndex,
      vrIpCacheIndex }
::= { vrIpCacheOperTable 1 }

VrIpCacheOperEntry ::= SEQUENCE {
   vrIpCacheEntriesFree
      Unsigned32,
   vrIpCacheTotalLookups
      Unsigned32,
   vrIpCacheLookupMisses
      Counter32,
   vrIpCacheCacheTableMaxEntries
      Unsigned32 }

vrIpCacheEntriesFree OBJECT-TYPE
   SYNTAX     Unsigned32 (0..8000)
   ACCESS     read-only
   STATUS     mandatory
   DESCRIPTION
     "This attribute is indicative of the number of free Ip cache table entries.
      A consistently high value for this attribute indicates that there is a 
      resource surplus of the memory requirements for cache table. This 
      surplus could be utilized elsewhere if needed by adjusting the 
      cacheTableMaxEntries under the Ip component."
::= { vrIpCacheOperEntry 3 }

vrIpCacheTotalLookups OBJECT-TYPE
   SYNTAX     Unsigned32 (0..4294967295)
   ACCESS     read-only
   STATUS     mandatory
   DESCRIPTION
     "This attribute indicates the total number of local cache lookups. It wraps 
      around to 0 when it reaches the maximum value of 4294967295."
::= { vrIpCacheOperEntry 4 }

vrIpCacheLookupMisses OBJECT-TYPE
   SYNTAX     Counter32 
   ACCESS     read-only
   STATUS     mandatory
   DESCRIPTION
     "This attribute indicates the total number of local cache lookup misses. It 
      wraps around to 0 when it reaches the maximum value of 4294967295."
::= { vrIpCacheOperEntry 5 }

vrIpCacheCacheTableMaxEntries OBJECT-TYPE
   SYNTAX     Unsigned32 (0..8000)
   ACCESS     read-only
   STATUS     mandatory
   DESCRIPTION
     "This attribute indicates the current maximum number of entries that can 
      exist in the IP local cache table on each LP."
::= { vrIpCacheOperEntry 395 }


-- Vr/<string> Ip Tunnel
-- The Tunnel component is used to add, delete and modify tunnel end 
-- points.

vrIpTunnel OBJECT IDENTIFIER ::= { vrIp 18 }



vrIpTunnelRowStatusTable OBJECT-TYPE
   SYNTAX     SEQUENCE OF VrIpTunnelRowStatusEntry
   ACCESS     not-accessible
   STATUS     mandatory
   DESCRIPTION
     "This entry controls the addition and deletion of 
      vrIpTunnel components."
::= { vrIpTunnel 1 }

vrIpTunnelRowStatusEntry OBJECT-TYPE
   SYNTAX     VrIpTunnelRowStatusEntry
   ACCESS     not-accessible
   STATUS     mandatory
   DESCRIPTION
     "A single entry in the table represents a single 
      vrIpTunnel component."
   INDEX {
      vrIndex,
      vrIpIndex,
      vrIpTunnelIndex }
::= { vrIpTunnelRowStatusTable 1 }

VrIpTunnelRowStatusEntry ::= SEQUENCE {
   vrIpTunnelRowStatus
      RowStatus,
   vrIpTunnelComponentName
      DisplayString,
   vrIpTunnelStorageType
      StorageType,
   vrIpTunnelIndex
      NonReplicated }

vrIpTunnelRowStatus OBJECT-TYPE
   SYNTAX     RowStatus 
   ACCESS     read-write
   STATUS     mandatory
   DESCRIPTION
     "This variable is used as the basis for SNMP naming of
      vrIpTunnel components.
      These components can be added and deleted."
::= { vrIpTunnelRowStatusEntry 1 }

vrIpTunnelComponentName OBJECT-TYPE
   SYNTAX     DisplayString 
   ACCESS     read-only
   STATUS     mandatory
   DESCRIPTION
     "This variable provides the component's string name for
      use with the ASCII Console Interface"
::= { vrIpTunnelRowStatusEntry 2 }

vrIpTunnelStorageType OBJECT-TYPE
   SYNTAX     StorageType 
   ACCESS     read-only
   STATUS     mandatory
   DESCRIPTION
     "This variable represents the storage type value for the
      vrIpTunnel tables."
::= { vrIpTunnelRowStatusEntry 4 }

vrIpTunnelIndex OBJECT-TYPE
   SYNTAX     NonReplicated 
   ACCESS     not-accessible
   STATUS     mandatory
   DESCRIPTION
     "This variable represents the index for the vrIpTunnel tables."
::= { vrIpTunnelRowStatusEntry 10 }

vrIpTunnelStateTable OBJECT-TYPE
   SYNTAX     SEQUENCE OF VrIpTunnelStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { vrIpTunnel 10 }

vrIpTunnelStateEntry OBJECT-TYPE
   SYNTAX     VrIpTunnelStateEntry
   ACCESS     not-accessible
   STATUS     mandatory
   DESCRIPTION
     "An entry in the vrIpTunnelStateTable."
   INDEX {
      vrIndex,
      vrIpIndex,
      vrIpTunnelIndex }
::= { vrIpTunnelStateTable 1 }

VrIpTunnelStateEntry ::= SEQUENCE {
   vrIpTunnelAdminState
      INTEGER,
   vrIpTunnelOperationalState
      INTEGER,
   vrIpTunnelUsageState
      INTEGER }

vrIpTunnelAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { vrIpTunnelStateEntry 1 }

vrIpTunnelOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { vrIpTunnelStateEntry 2 }

vrIpTunnelUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { vrIpTunnelStateEntry 3 }


-- Vr/<string> Ip Tunnel StaticEndPoint/n
-- IP tunnel allows two geographically separated networks to be 
-- connected over a shared IP network (e.g. the Internet), either 
-- because the networks at the end points are using private IP address 
-- or they are not running IP as the network protocol.
-- 
-- This component represents a static IP Tunnel End Point. It is static 
-- in the sense that both the tunnel source and destination IP addresses 
-- are static configured. For proper operation of the tunnel, the exact 
-- source and destination IP addresses (in reverse order) must be used 
-- to provision the Tunnel End Point on the far end router.
-- 
-- Two types of IP tunnel encapsulation are supported: IP in IP as 
-- specified in RFC 2003 and Generic Routing Encapsulation as 
-- specified in RFC 1701.
-- 

vrIpTunnelSep OBJECT IDENTIFIER ::= { vrIpTunnel 2 }



vrIpTunnelSepRowStatusTable OBJECT-TYPE
   SYNTAX     SEQUENCE OF VrIpTunnelSepRowStatusEntry
   ACCESS     not-accessible
   STATUS     mandatory
   DESCRIPTION
     "This entry controls the addition and deletion of 
      vrIpTunnelSep components."
::= { vrIpTunnelSep 1 }

vrIpTunnelSepRowStatusEntry OBJECT-TYPE
   SYNTAX     VrIpTunnelSepRowStatusEntry
   ACCESS     not-accessible
   STATUS     mandatory
   DESCRIPTION
     "A single entry in the table represents a single 
      vrIpTunnelSep component."
   INDEX {
      vrIndex,
      vrIpIndex,
      vrIpTunnelIndex,
      vrIpTunnelSepIndex }
::= { vrIpTunnelSepRowStatusTable 1 }

VrIpTunnelSepRowStatusEntry ::= SEQUENCE {
   vrIpTunnelSepRowStatus
      RowStatus,
   vrIpTunnelSepComponentName
      DisplayString,
   vrIpTunnelSepStorageType
      StorageType,
   vrIpTunnelSepIndex
      Integer32 }

vrIpTunnelSepRowStatus OBJECT-TYPE
   SYNTAX     RowStatus 
   ACCESS     read-write
   STATUS     mandatory
   DESCRIPTION
     "This variable is used as the basis for SNMP naming of
      vrIpTunnelSep components.
      These components can be added and deleted."
::= { vrIpTunnelSepRowStatusEntry 1 }

vrIpTunnelSepComponentName OBJECT-TYPE
   SYNTAX     DisplayString 
   ACCESS     read-only
   STATUS     mandatory
   DESCRIPTION
     "This variable provides the component's string name for
      use with the ASCII Console Interface"
::= { vrIpTunnelSepRowStatusEntry 2 }

vrIpTunnelSepStorageType OBJECT-TYPE
   SYNTAX     StorageType 
   ACCESS     read-only
   STATUS     mandatory
   DESCRIPTION
     "This variable represents the storage type value for the
      vrIpTunnelSep tables."
::= { vrIpTunnelSepRowStatusEntry 4 }

vrIpTunnelSepIndex OBJECT-TYPE
   SYNTAX     Integer32 (0..63)
   ACCESS     not-accessible
   STATUS     mandatory
   DESCRIPTION
     "This variable represents the index for the vrIpTunnelSep tables."
::= { vrIpTunnelSepRowStatusEntry 10 }

vrIpTunnelSepIfEntryTable OBJECT-TYPE
   SYNTAX     SEQUENCE OF VrIpTunnelSepIfEntryEntry
   ACCESS     not-accessible
   STATUS     mandatory
   DESCRIPTION
     "This group contains the provisionable attributes for the ifEntry."
::= { vrIpTunnelSep 10 }

vrIpTunnelSepIfEntryEntry OBJECT-TYPE
   SYNTAX     VrIpTunnelSepIfEntryEntry
   ACCESS     not-accessible
   STATUS     mandatory
   DESCRIPTION
     "An entry in the vrIpTunnelSepIfEntryTable."
   INDEX {
      vrIndex,
      vrIpIndex,
      vrIpTunnelIndex,
      vrIpTunnelSepIndex }
::= { vrIpTunnelSepIfEntryTable 1 }

VrIpTunnelSepIfEntryEntry ::= SEQUENCE {
   vrIpTunnelSepIfAdminStatus
      INTEGER,
   vrIpTunnelSepIfIndex
      InterfaceIndex }

vrIpTunnelSepIfAdminStatus OBJECT-TYPE
   SYNTAX     INTEGER  {
                 up(1),
                 down(2),
                 testing(3) }
   ACCESS     read-write
   STATUS     mandatory
   DESCRIPTION
     "The desired state of the interface. The up state indicates the 
      interface is operational. The down state indicates the interface is not 
      operational. The testing state indicates that no operational packets 
      can be passed."
   DEFVAL     { up }
::= { vrIpTunnelSepIfEntryEntry 1 }

vrIpTunnelSepIfIndex OBJECT-TYPE
   SYNTAX     InterfaceIndex (1..65535)
   ACCESS     read-only
   STATUS     mandatory
   DESCRIPTION
     "This is the index for the IfEntry. Its value is automatically initialized 
      during the provisioning process."
::= { vrIpTunnelSepIfEntryEntry 2 }

vrIpTunnelSepMpTable OBJECT-TYPE
   SYNTAX     SEQUENCE OF VrIpTunnelSepMpEntry
   ACCESS     not-accessible
   STATUS     mandatory
   DESCRIPTION
     "This group contains the base provisioning data for the media base 
      component."
::= { vrIpTunnelSep 11 }

vrIpTunnelSepMpEntry OBJECT-TYPE
   SYNTAX     VrIpTunnelSepMpEntry
   ACCESS     not-accessible
   STATUS     mandatory
   DESCRIPTION
     "An entry in the vrIpTunnelSepMpTable."
   INDEX {
      vrIndex,
      vrIpIndex,
      vrIpTunnelIndex,
      vrIpTunnelSepIndex }
::= { vrIpTunnelSepMpTable 1 }

VrIpTunnelSepMpEntry ::= SEQUENCE {
   vrIpTunnelSepLinkToProtocolPort
      Link }

vrIpTunnelSepLinkToProtocolPort OBJECT-TYPE
   SYNTAX     Link 
   ACCESS     read-write
   STATUS     mandatory
   DESCRIPTION
     "This attribute specifies the ProtocolPort to which this interface is 
      linked to. The protocol port is the logical interface to the network. 
      The protocol port component describes the logical characteristics of 
      this interface."
::= { vrIpTunnelSepMpEntry 1 }

vrIpTunnelSepProvTable OBJECT-TYPE
   SYNTAX     SEQUENCE OF VrIpTunnelSepProvEntry
   ACCESS     not-accessible
   STATUS     mandatory
   DESCRIPTION
     "This group contains the provisionable attributes for the 
      StaticEndPoint component."
::= { vrIpTunnelSep 12 }

vrIpTunnelSepProvEntry OBJECT-TYPE
   SYNTAX     VrIpTunnelSepProvEntry
   ACCESS     not-accessible
   STATUS     mandatory
   DESCRIPTION
     "An entry in the vrIpTunnelSepProvTable."
   INDEX {
      vrIndex,
      vrIpIndex,
      vrIpTunnelIndex,
      vrIpTunnelSepIndex }
::= { vrIpTunnelSepProvTable 1 }

VrIpTunnelSepProvEntry ::= SEQUENCE {
   vrIpTunnelSepEncapType
      INTEGER,
   vrIpTunnelSepSourceAddress
      IpAddress,
   vrIpTunnelSepDestinationAddress
      IpAddress }

vrIpTunnelSepEncapType OBJECT-TYPE
   SYNTAX     INTEGER  {
                 ipInIp(0),
                 greIp(1) }
   ACCESS     read-write
   STATUS     mandatory
   DESCRIPTION
     "There are two types of encapsulation techniques for IP tunnel, IP in 
      IP (RFC 2003) and GRE over IP (RFC 1701). This attributes 
      specifies the encapsulation type of the IP tunnel. It defaults to 
      ipInIp.
      
      ipInIp: As defined in RFC 2003, it can be used to encapsulated IP 
      and IP payload only. If IP is the only type of payload to be 
      encapsulated by the tunnel, this type of encapsulation is 
      recommended as it requires less processing and uses less 
      bandwidth.
      
      greIp: As defined in RFC 1701, it can be used to encapsulate IP or 
      IPX payload. To encapsulate IPX payload, this encapsulation type 
      must be used."
   DEFVAL     { ipInIp }
::= { vrIpTunnelSepProvEntry 1 }

vrIpTunnelSepSourceAddress OBJECT-TYPE
   SYNTAX     IpAddress 
   ACCESS     read-write
   STATUS     mandatory
   DESCRIPTION
     "This attribute specifies the IP address of the local end of the tunnel. 
      The source address must be an address in the shared domain, and it 
      must equal to an interface address on its own Virtual Router (under 
      Vr/<string> Pp/<string> IpPort LogicalIf/<IpAddress>). 
      However, it must not be the interface address of the linked protocol 
      port's IpPort."
   DEFVAL     { '00000000'H }  -- "0.0.0.0"
::= { vrIpTunnelSepProvEntry 2 }

vrIpTunnelSepDestinationAddress OBJECT-TYPE
   SYNTAX     IpAddress 
   ACCESS     read-write
   STATUS     mandatory
   DESCRIPTION
     "This attribute specifies the IP address of the far end of the tunnel. It 
      must not match any of the IP interface addresses on this Virtual 
      Router."
   DEFVAL     { '00000000'H }  -- "0.0.0.0"
::= { vrIpTunnelSepProvEntry 3 }

vrIpTunnelSepOperTable OBJECT-TYPE
   SYNTAX     SEQUENCE OF VrIpTunnelSepOperEntry
   ACCESS     not-accessible
   STATUS     mandatory
   DESCRIPTION
     "This group contains the operational status attributes of the 
      StaticEndPoint component."
::= { vrIpTunnelSep 14 }

vrIpTunnelSepOperEntry OBJECT-TYPE
   SYNTAX     VrIpTunnelSepOperEntry
   ACCESS     not-accessible
   STATUS     mandatory
   DESCRIPTION
     "An entry in the vrIpTunnelSepOperTable."
   INDEX {
      vrIndex,
      vrIpIndex,
      vrIpTunnelIndex,
      vrIpTunnelSepIndex }
::= { vrIpTunnelSepOperTable 1 }

VrIpTunnelSepOperEntry ::= SEQUENCE {
   vrIpTunnelSepPathMtu
      Unsigned32 }

vrIpTunnelSepPathMtu OBJECT-TYPE
   SYNTAX     Unsigned32 (0..0 | 576..18944)
   ACCESS     read-only
   STATUS     mandatory
   DESCRIPTION
     "This attribute indicates the latest learned Path MTU of the tunnel.
      
      MTU is the maximum transmission unit of an arbitrary internet 
      path. When a large amount of IP datagrams are to be transmitted, it 
      is usually preferable that the datagrams be of the largest size that 
      does not require fragmentation anywhere along the path from the 
      source to the destination. This datagram size is referred to as the 
      Path MTU (PMTU), and it is equal to the minimum of the MTUs of 
      each hop in the path."
   DEFVAL     { 0 }
::= { vrIpTunnelSepOperEntry 1 }


-- Vr/<string> Ip Multicast
-- This component provides support for IP Multicast.

vrIpMcast OBJECT IDENTIFIER ::= { vrIp 26 }



vrIpMcastRowStatusTable OBJECT-TYPE
   SYNTAX     SEQUENCE OF VrIpMcastRowStatusEntry
   ACCESS     not-accessible
   STATUS     mandatory
   DESCRIPTION
     "This entry controls the addition and deletion of 
      vrIpMcast components."
::= { vrIpMcast 1 }

vrIpMcastRowStatusEntry OBJECT-TYPE
   SYNTAX     VrIpMcastRowStatusEntry
   ACCESS     not-accessible
   STATUS     mandatory
   DESCRIPTION
     "A single entry in the table represents a single 
      vrIpMcast component."
   INDEX {
      vrIndex,
      vrIpIndex,
      vrIpMcastIndex }
::= { vrIpMcastRowStatusTable 1 }

VrIpMcastRowStatusEntry ::= SEQUENCE {
   vrIpMcastRowStatus
      RowStatus,
   vrIpMcastComponentName
      DisplayString,
   vrIpMcastStorageType
      StorageType,
   vrIpMcastIndex
      NonReplicated }

vrIpMcastRowStatus OBJECT-TYPE
   SYNTAX     RowStatus 
   ACCESS     read-write
   STATUS     mandatory
   DESCRIPTION
     "This variable is used as the basis for SNMP naming of
      vrIpMcast components.
      These components can be added and deleted."
::= { vrIpMcastRowStatusEntry 1 }

vrIpMcastComponentName OBJECT-TYPE
   SYNTAX     DisplayString 
   ACCESS     read-only
   STATUS     mandatory
   DESCRIPTION
     "This variable provides the component's string name for
      use with the ASCII Console Interface"
::= { vrIpMcastRowStatusEntry 2 }

vrIpMcastStorageType OBJECT-TYPE
   SYNTAX     StorageType 
   ACCESS     read-only
   STATUS     mandatory
   DESCRIPTION
     "This variable represents the storage type value for the
      vrIpMcast tables."
::= { vrIpMcastRowStatusEntry 4 }

vrIpMcastIndex OBJECT-TYPE
   SYNTAX     NonReplicated 
   ACCESS     not-accessible
   STATUS     mandatory
   DESCRIPTION
     "This variable represents the index for the vrIpMcast tables."
::= { vrIpMcastRowStatusEntry 10 }

vrIpMcastAdminControlTable OBJECT-TYPE
   SYNTAX     SEQUENCE OF VrIpMcastAdminControlEntry
   ACCESS     not-accessible
   STATUS     mandatory
   DESCRIPTION
     "This group includes the Administrative Control attribute. This 
      attribute defines the current administrative state of this component."
::= { vrIpMcast 100 }

vrIpMcastAdminControlEntry OBJECT-TYPE
   SYNTAX     VrIpMcastAdminControlEntry
   ACCESS     not-accessible
   STATUS     mandatory
   DESCRIPTION
     "An entry in the vrIpMcastAdminControlTable."
   INDEX {
      vrIndex,
      vrIpIndex,
      vrIpMcastIndex }
::= { vrIpMcastAdminControlTable 1 }

VrIpMcastAdminControlEntry ::= SEQUENCE {
   vrIpMcastSnmpAdminStatus
      INTEGER }

vrIpMcastSnmpAdminStatus OBJECT-TYPE
   SYNTAX     INTEGER  {
                 up(1),
                 down(2),
                 testing(3) }
   ACCESS     read-write
   STATUS     mandatory
   DESCRIPTION
     "The desired state of the interface. The up state indicates the 
      interface is operational and packet forwarding is allowed. The down 
      state indicates the interface is not operational and packet forwarding 
      is unavailable. The testing state indicates that no operational 
      packets can be passed."
   DEFVAL     { up }
::= { vrIpMcastAdminControlEntry 1 }

vrIpMcastStateTable OBJECT-TYPE
   SYNTAX     SEQUENCE OF VrIpMcastStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { vrIpMcast 103 }

vrIpMcastStateEntry OBJECT-TYPE
   SYNTAX     VrIpMcastStateEntry
   ACCESS     not-accessible
   STATUS     mandatory
   DESCRIPTION
     "An entry in the vrIpMcastStateTable."
   INDEX {
      vrIndex,
      vrIpIndex,
      vrIpMcastIndex }
::= { vrIpMcastStateTable 1 }

VrIpMcastStateEntry ::= SEQUENCE {
   vrIpMcastAdminState
      INTEGER,
   vrIpMcastOperationalState
      INTEGER,
   vrIpMcastUsageState
      INTEGER }

vrIpMcastAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { vrIpMcastStateEntry 1 }

vrIpMcastOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { vrIpMcastStateEntry 2 }

vrIpMcastUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { vrIpMcastStateEntry 3 }

vrIpMcastOperStatusTable OBJECT-TYPE
   SYNTAX     SEQUENCE OF VrIpMcastOperStatusEntry
   ACCESS     not-accessible
   STATUS     mandatory
   DESCRIPTION
     "This group includes the Operational Status attribute. This attribute 
      defines the current operational state of this component."
::= { vrIpMcast 104 }

vrIpMcastOperStatusEntry OBJECT-TYPE
   SYNTAX     VrIpMcastOperStatusEntry
   ACCESS     not-accessible
   STATUS     mandatory
   DESCRIPTION
     "An entry in the vrIpMcastOperStatusTable."
   INDEX {
      vrIndex,
      vrIpIndex,
      vrIpMcastIndex }
::= { vrIpMcastOperStatusTable 1 }

VrIpMcastOperStatusEntry ::= SEQUENCE {
   vrIpMcastSnmpOperStatus
      INTEGER }

vrIpMcastSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { vrIpMcastOperStatusEntry 1 }

vrIpMcastCtsTable OBJECT-TYPE
   SYNTAX     SEQUENCE OF VrIpMcastCtsEntry
   ACCESS     not-accessible
   STATUS     mandatory
   DESCRIPTION
     "This attribute specifies the maximum number of entries supported in 
      the IP Multicast cache table on each LP. The default is 100 for a CP 
      and 200 for an FP. The value must be multiple of 100."
::= { vrIpMcast 701 }

vrIpMcastCtsEntry OBJECT-TYPE
   SYNTAX     VrIpMcastCtsEntry
   ACCESS     not-accessible
   STATUS     mandatory
   DESCRIPTION
     "An entry in the vrIpMcastCtsTable."
   INDEX {
      vrIndex,
      vrIpIndex,
      vrIpMcastIndex,
      vrIpMcastCtsIndex }
::= { vrIpMcastCtsTable 1 }

VrIpMcastCtsEntry ::= SEQUENCE {
   vrIpMcastCtsIndex
      Integer32,
   vrIpMcastCtsValue
      Unsigned32 }

vrIpMcastCtsIndex OBJECT-TYPE
   SYNTAX     Integer32 (0..15)
   ACCESS     not-accessible
   STATUS     mandatory
   DESCRIPTION
     "This variable represents the vrIpMcastCtsTable
      specific index for the vrIpMcastCtsTable."
::= { vrIpMcastCtsEntry 1 }

vrIpMcastCtsValue OBJECT-TYPE
   SYNTAX     Unsigned32 (100..500)
   ACCESS     read-write
   STATUS     mandatory
   DESCRIPTION
     "This variable represents an individual value for the
      vrIpMcastCtsTable."
::= { vrIpMcastCtsEntry 2 }


-- Vr/<string> Ip Mcast Igmp
-- This component provides support for the IGMP protocol.

vrIpMcastIgmp OBJECT IDENTIFIER ::= { vrIpMcast 2 }



vrIpMcastIgmpRowStatusTable OBJECT-TYPE
   SYNTAX     SEQUENCE OF VrIpMcastIgmpRowStatusEntry
   ACCESS     not-accessible
   STATUS     mandatory
   DESCRIPTION
     "This entry controls the addition and deletion of 
      vrIpMcastIgmp components."
::= { vrIpMcastIgmp 1 }

vrIpMcastIgmpRowStatusEntry OBJECT-TYPE
   SYNTAX     VrIpMcastIgmpRowStatusEntry
   ACCESS     not-accessible
   STATUS     mandatory
   DESCRIPTION
     "A single entry in the table represents a single 
      vrIpMcastIgmp component."
   INDEX {
      vrIndex,
      vrIpIndex,
      vrIpMcastIndex,
      vrIpMcastIgmpIndex }
::= { vrIpMcastIgmpRowStatusTable 1 }

VrIpMcastIgmpRowStatusEntry ::= SEQUENCE {
   vrIpMcastIgmpRowStatus
      RowStatus,
   vrIpMcastIgmpComponentName
      DisplayString,
   vrIpMcastIgmpStorageType
      StorageType,
   vrIpMcastIgmpIndex
      NonReplicated }

vrIpMcastIgmpRowStatus OBJECT-TYPE
   SYNTAX     RowStatus 
   ACCESS     read-write
   STATUS     mandatory
   DESCRIPTION
     "This variable is used as the basis for SNMP naming of
      vrIpMcastIgmp components.
      These components can be added and deleted."
::= { vrIpMcastIgmpRowStatusEntry 1 }

vrIpMcastIgmpComponentName OBJECT-TYPE
   SYNTAX     DisplayString 
   ACCESS     read-only
   STATUS     mandatory
   DESCRIPTION
     "This variable provides the component's string name for
      use with the ASCII Console Interface"
::= { vrIpMcastIgmpRowStatusEntry 2 }

vrIpMcastIgmpStorageType OBJECT-TYPE
   SYNTAX     StorageType 
   ACCESS     read-only
   STATUS     mandatory
   DESCRIPTION
     "This variable represents the storage type value for the
      vrIpMcastIgmp tables."
::= { vrIpMcastIgmpRowStatusEntry 4 }

vrIpMcastIgmpIndex OBJECT-TYPE
   SYNTAX     NonReplicated 
   ACCESS     not-accessible
   STATUS     mandatory
   DESCRIPTION
     "This variable represents the index for the vrIpMcastIgmp tables."
::= { vrIpMcastIgmpRowStatusEntry 10 }

vrIpMcastIgmpAdminControlTable OBJECT-TYPE
   SYNTAX     SEQUENCE OF VrIpMcastIgmpAdminControlEntry
   ACCESS     not-accessible
   STATUS     mandatory
   DESCRIPTION
     "This group includes the Administrative Control attribute. This 
      attribute defines the current administrative state of this component."
::= { vrIpMcastIgmp 10 }

vrIpMcastIgmpAdminControlEntry OBJECT-TYPE
   SYNTAX     VrIpMcastIgmpAdminControlEntry
   ACCESS     not-accessible
   STATUS     mandatory
   DESCRIPTION
     "An entry in the vrIpMcastIgmpAdminControlTable."
   INDEX {
      vrIndex,
      vrIpIndex,
      vrIpMcastIndex,
      vrIpMcastIgmpIndex }
::= { vrIpMcastIgmpAdminControlTable 1 }

VrIpMcastIgmpAdminControlEntry ::= SEQUENCE {
   vrIpMcastIgmpSnmpAdminStatus
      INTEGER }

vrIpMcastIgmpSnmpAdminStatus OBJECT-TYPE
   SYNTAX     INTEGER  {
                 up(1),
                 down(2),
                 testing(3) }
   ACCESS     read-write
   STATUS     mandatory
   DESCRIPTION
     "The desired state of the interface. The up state indicates the 
      interface is operational and packet forwarding is allowed. The down 
      state indicates the interface is not operational and packet forwarding 
      is unavailable. The testing state indicates that no operational 
      packets can be passed."
   DEFVAL     { up }
::= { vrIpMcastIgmpAdminControlEntry 1 }

vrIpMcastIgmpStateTable OBJECT-TYPE
   SYNTAX     SEQUENCE OF VrIpMcastIgmpStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { vrIpMcastIgmp 12 }

vrIpMcastIgmpStateEntry OBJECT-TYPE
   SYNTAX     VrIpMcastIgmpStateEntry
   ACCESS     not-accessible
   STATUS     mandatory
   DESCRIPTION
     "An entry in the vrIpMcastIgmpStateTable."
   INDEX {
      vrIndex,
      vrIpIndex,
      vrIpMcastIndex,
      vrIpMcastIgmpIndex }
::= { vrIpMcastIgmpStateTable 1 }

VrIpMcastIgmpStateEntry ::= SEQUENCE {
   vrIpMcastIgmpAdminState
      INTEGER,
   vrIpMcastIgmpOperationalState
      INTEGER,
   vrIpMcastIgmpUsageState
      INTEGER }

vrIpMcastIgmpAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { vrIpMcastIgmpStateEntry 1 }

vrIpMcastIgmpOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { vrIpMcastIgmpStateEntry 2 }

vrIpMcastIgmpUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { vrIpMcastIgmpStateEntry 3 }

vrIpMcastIgmpOperStatusTable OBJECT-TYPE
   SYNTAX     SEQUENCE OF VrIpMcastIgmpOperStatusEntry
   ACCESS     not-accessible
   STATUS     mandatory
   DESCRIPTION
     "This group includes the Operational Status attribute. This attribute 
      defines the current operational state of this component."
::= { vrIpMcastIgmp 13 }

vrIpMcastIgmpOperStatusEntry OBJECT-TYPE
   SYNTAX     VrIpMcastIgmpOperStatusEntry
   ACCESS     not-accessible
   STATUS     mandatory
   DESCRIPTION
     "An entry in the vrIpMcastIgmpOperStatusTable."
   INDEX {
      vrIndex,
      vrIpIndex,
      vrIpMcastIndex,
      vrIpMcastIgmpIndex }
::= { vrIpMcastIgmpOperStatusTable 1 }

VrIpMcastIgmpOperStatusEntry ::= SEQUENCE {
   vrIpMcastIgmpSnmpOperStatus
      INTEGER }

vrIpMcastIgmpSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { vrIpMcastIgmpOperStatusEntry 1 }

-- 
-- *** THIS SUBTREE CURRENTLY NOT IMPLEMENTED ***
-- 

-- Vr/<string> Ip Mcast Igmp CacheEntry <ipAddress>, 
-- <domain>, <ppString> 
-- This component represents an entry in the IGMP cache table.

vrIpMcastIgmpGc OBJECT IDENTIFIER ::= { vrIpMcastIgmp 2 }



vrIpMcastIgmpGcRowStatusTable OBJECT-TYPE
   SYNTAX     SEQUENCE OF VrIpMcastIgmpGcRowStatusEntry
   ACCESS     not-accessible
   STATUS     mandatory
   DESCRIPTION
     "*** THIS TABLE CURRENTLY NOT IMPLEMENTED ***

      This entry controls the addition and deletion of 
      vrIpMcastIgmpGc components."
::= { vrIpMcastIgmpGc 1 }

vrIpMcastIgmpGcRowStatusEntry OBJECT-TYPE
   SYNTAX     VrIpMcastIgmpGcRowStatusEntry
   ACCESS     not-accessible
   STATUS     mandatory
   DESCRIPTION
     "A single entry in the table represents a single 
      vrIpMcastIgmpGc component."
   INDEX {
      vrIndex,
      vrIpIndex,
      vrIpMcastIndex,
      vrIpMcastIgmpIndex,
      vrIpMcastIgmpGcGAddrIndex,
      vrIpMcastIgmpGcDomainIndex,
      vrIpMcastIgmpGcProtocolportStringIndex }
::= { vrIpMcastIgmpGcRowStatusTable 1 }

VrIpMcastIgmpGcRowStatusEntry ::= SEQUENCE {
   vrIpMcastIgmpGcRowStatus
      RowStatus,
   vrIpMcastIgmpGcComponentName
      DisplayString,
   vrIpMcastIgmpGcStorageType
      StorageType,
   vrIpMcastIgmpGcGAddrIndex
      IpAddress,
   vrIpMcastIgmpGcDomainIndex
      Integer32,
   vrIpMcastIgmpGcProtocolportStringIndex
      AsciiStringIndex }

vrIpMcastIgmpGcRowStatus OBJECT-TYPE
   SYNTAX     RowStatus 
   ACCESS     read-only
   STATUS     mandatory
   DESCRIPTION
     "This variable is used as the basis for SNMP naming of
      vrIpMcastIgmpGc components.
      These components cannot be added nor deleted."
::= { vrIpMcastIgmpGcRowStatusEntry 1 }

vrIpMcastIgmpGcComponentName OBJECT-TYPE
   SYNTAX     DisplayString 
   ACCESS     read-only
   STATUS     mandatory
   DESCRIPTION
     "This variable provides the component's string name for
      use with the ASCII Console Interface"
::= { vrIpMcastIgmpGcRowStatusEntry 2 }

vrIpMcastIgmpGcStorageType OBJECT-TYPE
   SYNTAX     StorageType 
   ACCESS     read-only
   STATUS     mandatory
   DESCRIPTION
     "This variable represents the storage type value for the
      vrIpMcastIgmpGc tables."
::= { vrIpMcastIgmpGcRowStatusEntry 4 }

vrIpMcastIgmpGcGAddrIndex OBJECT-TYPE
   SYNTAX     IpAddress 
   ACCESS     not-accessible
   STATUS     mandatory
   DESCRIPTION
     "This variable represents an index for the vrIpMcastIgmpGc tables."
::= { vrIpMcastIgmpGcRowStatusEntry 10 }

vrIpMcastIgmpGcDomainIndex OBJECT-TYPE
   SYNTAX     Integer32 (0..3)
   ACCESS     not-accessible
   STATUS     mandatory
   DESCRIPTION
     "This variable represents an index for the vrIpMcastIgmpGc tables."
::= { vrIpMcastIgmpGcRowStatusEntry 11 }

vrIpMcastIgmpGcProtocolportStringIndex OBJECT-TYPE
   SYNTAX     AsciiStringIndex (SIZE (1..20))
   ACCESS     not-accessible
   STATUS     mandatory
   DESCRIPTION
     "This variable represents an index for the vrIpMcastIgmpGc tables."
::= { vrIpMcastIgmpGcRowStatusEntry 12 }

vrIpMcastIgmpGcOperTable OBJECT-TYPE
   SYNTAX     SEQUENCE OF VrIpMcastIgmpGcOperEntry
   ACCESS     not-accessible
   STATUS     mandatory
   DESCRIPTION
     "*** THIS TABLE CURRENTLY NOT IMPLEMENTED ***

      This group contains the operational attributes of the CacheEntry 
      component."
::= { vrIpMcastIgmpGc 11 }

vrIpMcastIgmpGcOperEntry OBJECT-TYPE
   SYNTAX     VrIpMcastIgmpGcOperEntry
   ACCESS     not-accessible
   STATUS     mandatory
   DESCRIPTION
     "An entry in the vrIpMcastIgmpGcOperTable."
   INDEX {
      vrIndex,
      vrIpIndex,
      vrIpMcastIndex,
      vrIpMcastIgmpIndex,
      vrIpMcastIgmpGcGAddrIndex,
      vrIpMcastIgmpGcDomainIndex,
      vrIpMcastIgmpGcProtocolportStringIndex }
::= { vrIpMcastIgmpGcOperTable 1 }

VrIpMcastIgmpGcOperEntry ::= SEQUENCE {
   vrIpMcastIgmpGcUpTime
      EnterpriseDateAndTime,
   vrIpMcastIgmpGcExpiryTime
      EnterpriseDateAndTime,
   vrIpMcastIgmpGcLastReporter
      IpAddress,
   vrIpMcastIgmpGcVersion1HostTimer
      Unsigned32 }

vrIpMcastIgmpGcUpTime OBJECT-TYPE
   SYNTAX     EnterpriseDateAndTime (SIZE (0 | 19))
   ACCESS     read-only
   STATUS     mandatory
   DESCRIPTION
     "This attribute indicates the time elapsed since this entry was 
      created."
::= { vrIpMcastIgmpGcOperEntry 1 }

vrIpMcastIgmpGcExpiryTime OBJECT-TYPE
   SYNTAX     EnterpriseDateAndTime (SIZE (0 | 8))
   ACCESS     read-only
   STATUS     mandatory
   DESCRIPTION
     "This attribute indicates the minimum amount of time reamining 
      before this entry will be aged out."
::= { vrIpMcastIgmpGcOperEntry 2 }

vrIpMcastIgmpGcLastReporter OBJECT-TYPE
   SYNTAX     IpAddress 
   ACCESS     read-only
   STATUS     mandatory
   DESCRIPTION
     "This attribute indicates the IP address of the source of the last 
      membership report received for this IP Multicast group address on 
      this interface. If no membership report has been received, this 
      attribute has the value 0.0.0.0."
   DEFVAL     { '00000000'H }  -- "0.0.0.0"
::= { vrIpMcastIgmpGcOperEntry 3 }

vrIpMcastIgmpGcVersion1HostTimer OBJECT-TYPE
   SYNTAX     Unsigned32 (0..4294967295)
   ACCESS     read-only
   STATUS     mandatory
   DESCRIPTION
     "This attribute indicates the time remaining until the local router will 
      assume that there are no longer any IGMPv1 members on the IP 
      subnet attached to this interface. Upon hearing any IGMPv1 
      Membership Report, this value is reset to the group membership 
      timer."
   DEFVAL     { 0 }
::= { vrIpMcastIgmpGcOperEntry 4 }


-- Vr/<string> Ip Mcast Static
-- This component provides support for multicast static routes.

vrIpMcastStatic OBJECT IDENTIFIER ::= { vrIpMcast 3 }



vrIpMcastStaticRowStatusTable OBJECT-TYPE
   SYNTAX     SEQUENCE OF VrIpMcastStaticRowStatusEntry
   ACCESS     not-accessible
   STATUS     mandatory
   DESCRIPTION
     "This entry controls the addition and deletion of 
      vrIpMcastStatic components."
::= { vrIpMcastStatic 1 }

vrIpMcastStaticRowStatusEntry OBJECT-TYPE
   SYNTAX     VrIpMcastStaticRowStatusEntry
   ACCESS     not-accessible
   STATUS     mandatory
   DESCRIPTION
     "A single entry in the table represents a single 
      vrIpMcastStatic component."
   INDEX {
      vrIndex,
      vrIpIndex,
      vrIpMcastIndex,
      vrIpMcastStaticIndex }
::= { vrIpMcastStaticRowStatusTable 1 }

VrIpMcastStaticRowStatusEntry ::= SEQUENCE {
   vrIpMcastStaticRowStatus
      RowStatus,
   vrIpMcastStaticComponentName
      DisplayString,
   vrIpMcastStaticStorageType
      StorageType,
   vrIpMcastStaticIndex
      NonReplicated }

vrIpMcastStaticRowStatus OBJECT-TYPE
   SYNTAX     RowStatus 
   ACCESS     read-write
   STATUS     mandatory
   DESCRIPTION
     "This variable is used as the basis for SNMP naming of
      vrIpMcastStatic components.
      These components can be added and deleted."
::= { vrIpMcastStaticRowStatusEntry 1 }

vrIpMcastStaticComponentName OBJECT-TYPE
   SYNTAX     DisplayString 
   ACCESS     read-only
   STATUS     mandatory
   DESCRIPTION
     "This variable provides the component's string name for
      use with the ASCII Console Interface"
::= { vrIpMcastStaticRowStatusEntry 2 }

vrIpMcastStaticStorageType OBJECT-TYPE
   SYNTAX     StorageType 
   ACCESS     read-only
   STATUS     mandatory
   DESCRIPTION
     "This variable represents the storage type value for the
      vrIpMcastStatic tables."
::= { vrIpMcastStaticRowStatusEntry 4 }

vrIpMcastStaticIndex OBJECT-TYPE
   SYNTAX     NonReplicated 
   ACCESS     not-accessible
   STATUS     mandatory
   DESCRIPTION
     "This variable represents the index for the vrIpMcastStatic tables."
::= { vrIpMcastStaticRowStatusEntry 10 }

vrIpMcastStaticStateTable OBJECT-TYPE
   SYNTAX     SEQUENCE OF VrIpMcastStaticStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { vrIpMcastStatic 10 }

vrIpMcastStaticStateEntry OBJECT-TYPE
   SYNTAX     VrIpMcastStaticStateEntry
   ACCESS     not-accessible
   STATUS     mandatory
   DESCRIPTION
     "An entry in the vrIpMcastStaticStateTable."
   INDEX {
      vrIndex,
      vrIpIndex,
      vrIpMcastIndex,
      vrIpMcastStaticIndex }
::= { vrIpMcastStaticStateTable 1 }

VrIpMcastStaticStateEntry ::= SEQUENCE {
   vrIpMcastStaticAdminState
      INTEGER,
   vrIpMcastStaticOperationalState
      INTEGER,
   vrIpMcastStaticUsageState
      INTEGER }

vrIpMcastStaticAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { vrIpMcastStaticStateEntry 1 }

vrIpMcastStaticOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { vrIpMcastStaticStateEntry 2 }

vrIpMcastStaticUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { vrIpMcastStaticStateEntry 3 }


-- Vr/<string> Ip Mcast Static RouteEntry/<Ip Address>,<domain>
-- This component represents a multicast static route entry. For a 
-- RouteEntry to be valid, there should be at least one OutInterface 
-- provisioned. 

vrIpMcastStaticRoute OBJECT IDENTIFIER ::= { vrIpMcastStatic 2 }



vrIpMcastStaticRouteRowStatusTable OBJECT-TYPE
   SYNTAX     SEQUENCE OF VrIpMcastStaticRouteRowStatusEntry
   ACCESS     not-accessible
   STATUS     mandatory
   DESCRIPTION
     "This entry controls the addition and deletion of 
      vrIpMcastStaticRoute components."
::= { vrIpMcastStaticRoute 1 }

vrIpMcastStaticRouteRowStatusEntry OBJECT-TYPE
   SYNTAX     VrIpMcastStaticRouteRowStatusEntry
   ACCESS     not-accessible
   STATUS     mandatory
   DESCRIPTION
     "A single entry in the table represents a single 
      vrIpMcastStaticRoute component."
   INDEX {
      vrIndex,
      vrIpIndex,
      vrIpMcastIndex,
      vrIpMcastStaticIndex,
      vrIpMcastStaticRouteGAddrIndex,
      vrIpMcastStaticRouteDomainIndex }
::= { vrIpMcastStaticRouteRowStatusTable 1 }

VrIpMcastStaticRouteRowStatusEntry ::= SEQUENCE {
   vrIpMcastStaticRouteRowStatus
      RowStatus,
   vrIpMcastStaticRouteComponentName
      DisplayString,
   vrIpMcastStaticRouteStorageType
      StorageType,
   vrIpMcastStaticRouteGAddrIndex
      IpAddress,
   vrIpMcastStaticRouteDomainIndex
      Integer32 }

vrIpMcastStaticRouteRowStatus OBJECT-TYPE
   SYNTAX     RowStatus 
   ACCESS     read-write
   STATUS     mandatory
   DESCRIPTION
     "This variable is used as the basis for SNMP naming of
      vrIpMcastStaticRoute components.
      These components can be added and deleted."
::= { vrIpMcastStaticRouteRowStatusEntry 1 }

vrIpMcastStaticRouteComponentName OBJECT-TYPE
   SYNTAX     DisplayString 
   ACCESS     read-only
   STATUS     mandatory
   DESCRIPTION
     "This variable provides the component's string name for
      use with the ASCII Console Interface"
::= { vrIpMcastStaticRouteRowStatusEntry 2 }

vrIpMcastStaticRouteStorageType OBJECT-TYPE
   SYNTAX     StorageType 
   ACCESS     read-only
   STATUS     mandatory
   DESCRIPTION
     "This variable represents the storage type value for the
      vrIpMcastStaticRoute tables."
::= { vrIpMcastStaticRouteRowStatusEntry 4 }

vrIpMcastStaticRouteGAddrIndex OBJECT-TYPE
   SYNTAX     IpAddress 
   ACCESS     not-accessible
   STATUS     mandatory
   DESCRIPTION
     "This variable represents an index for the vrIpMcastStaticRoute tables."
::= { vrIpMcastStaticRouteRowStatusEntry 10 }

vrIpMcastStaticRouteDomainIndex OBJECT-TYPE
   SYNTAX     Integer32 (0..3)
   ACCESS     not-accessible
   STATUS     mandatory
   DESCRIPTION
     "This variable represents an index for the vrIpMcastStaticRoute tables."
::= { vrIpMcastStaticRouteRowStatusEntry 11 }

vrIpMcastStaticRouteOifsTable OBJECT-TYPE
   SYNTAX     SEQUENCE OF VrIpMcastStaticRouteOifsEntry
   ACCESS     not-accessible
   STATUS     mandatory
   DESCRIPTION
     "This attribute specifies a list of links to logicalInterfaces 
      representing the outgoing interfaces for this multicast static route 
      entry."
::= { vrIpMcastStaticRoute 705 }

vrIpMcastStaticRouteOifsEntry OBJECT-TYPE
   SYNTAX     VrIpMcastStaticRouteOifsEntry
   ACCESS     not-accessible
   STATUS     mandatory
   DESCRIPTION
     "An entry in the vrIpMcastStaticRouteOifsTable."
   INDEX {
      vrIndex,
      vrIpIndex,
      vrIpMcastIndex,
      vrIpMcastStaticIndex,
      vrIpMcastStaticRouteGAddrIndex,
      vrIpMcastStaticRouteDomainIndex,
      vrIpMcastStaticRouteOifsValue }
::= { vrIpMcastStaticRouteOifsTable 1 }

VrIpMcastStaticRouteOifsEntry ::= SEQUENCE {
   vrIpMcastStaticRouteOifsValue
      Link,
   vrIpMcastStaticRouteOifsRowStatus
      RowStatus }

vrIpMcastStaticRouteOifsValue OBJECT-TYPE
   SYNTAX     Link 
   ACCESS     read-write
   STATUS     mandatory
   DESCRIPTION
     "This variable represents both the value and the index for the
      vrIpMcastStaticRouteOifsTable."
::= { vrIpMcastStaticRouteOifsEntry 1 }

vrIpMcastStaticRouteOifsRowStatus OBJECT-TYPE
   SYNTAX     RowStatus 
   ACCESS     write-only
   STATUS     mandatory
   DESCRIPTION
     "This variable is used to control the addition and deletion 
      of individual values of the vrIpMcastStaticRouteOifsTable."
::= { vrIpMcastStaticRouteOifsEntry 2 }


-- Vr/<string> Ip Mcast PolicyGroup/<string>
-- This component represents a multicast group join policy, which 
-- may be applied to one or more IpPorts.

vrIpMcastPg OBJECT IDENTIFIER ::= { vrIpMcast 4 }



vrIpMcastPgRowStatusTable OBJECT-TYPE
   SYNTAX     SEQUENCE OF VrIpMcastPgRowStatusEntry
   ACCESS     not-accessible
   STATUS     mandatory
   DESCRIPTION
     "This entry controls the addition and deletion of 
      vrIpMcastPg components."
::= { vrIpMcastPg 1 }

vrIpMcastPgRowStatusEntry OBJECT-TYPE
   SYNTAX     VrIpMcastPgRowStatusEntry
   ACCESS     not-accessible
   STATUS     mandatory
   DESCRIPTION
     "A single entry in the table represents a single 
      vrIpMcastPg component."
   INDEX {
      vrIndex,
      vrIpIndex,
      vrIpMcastIndex,
      vrIpMcastPgIndex }
::= { vrIpMcastPgRowStatusTable 1 }

VrIpMcastPgRowStatusEntry ::= SEQUENCE {
   vrIpMcastPgRowStatus
      RowStatus,
   vrIpMcastPgComponentName
      DisplayString,
   vrIpMcastPgStorageType
      StorageType,
   vrIpMcastPgIndex
      AsciiStringIndex }

vrIpMcastPgRowStatus OBJECT-TYPE
   SYNTAX     RowStatus 
   ACCESS     read-write
   STATUS     mandatory
   DESCRIPTION
     "This variable is used as the basis for SNMP naming of
      vrIpMcastPg components.
      These components can be added and deleted."
::= { vrIpMcastPgRowStatusEntry 1 }

vrIpMcastPgComponentName OBJECT-TYPE
   SYNTAX     DisplayString 
   ACCESS     read-only
   STATUS     mandatory
   DESCRIPTION
     "This variable provides the component's string name for
      use with the ASCII Console Interface"
::= { vrIpMcastPgRowStatusEntry 2 }

vrIpMcastPgStorageType OBJECT-TYPE
   SYNTAX     StorageType 
   ACCESS     read-only
   STATUS     mandatory
   DESCRIPTION
     "This variable represents the storage type value for the
      vrIpMcastPg tables."
::= { vrIpMcastPgRowStatusEntry 4 }

vrIpMcastPgIndex OBJECT-TYPE
   SYNTAX     AsciiStringIndex (SIZE (1..20))
   ACCESS     not-accessible
   STATUS     mandatory
   DESCRIPTION
     "This variable represents the index for the vrIpMcastPg tables."
::= { vrIpMcastPgRowStatusEntry 10 }

vrIpMcastPgProvTable OBJECT-TYPE
   SYNTAX     SEQUENCE OF VrIpMcastPgProvEntry
   ACCESS     not-accessible
   STATUS     mandatory
   DESCRIPTION
     "This group contains the provisionable attributes for the PolicyGroup 
      component."
::= { vrIpMcastPg 10 }

vrIpMcastPgProvEntry OBJECT-TYPE
   SYNTAX     VrIpMcastPgProvEntry
   ACCESS     not-accessible
   STATUS     mandatory
   DESCRIPTION
     "An entry in the vrIpMcastPgProvTable."
   INDEX {
      vrIndex,
      vrIpIndex,
      vrIpMcastIndex,
      vrIpMcastPgIndex }
::= { vrIpMcastPgProvTable 1 }

VrIpMcastPgProvEntry ::= SEQUENCE {
   vrIpMcastPgAction
      INTEGER }

vrIpMcastPgAction OBJECT-TYPE
   SYNTAX     INTEGER  {
                 deny(1),
                 allow(2) }
   ACCESS     read-write
   STATUS     mandatory
   DESCRIPTION
     "This attribute specifies the action to be taken if a join request is 
      received for any of the multicast group addresses configured as part 
      of this policy. The default action is to deny the join request."
   DEFVAL     { deny }
::= { vrIpMcastPgProvEntry 1 }

vrIpMcastPgLinkToPolicyUserTable OBJECT-TYPE
   SYNTAX     SEQUENCE OF VrIpMcastPgLinkToPolicyUserEntry
   ACCESS     not-accessible
   STATUS     mandatory
   DESCRIPTION
     "This attribute specifies a list of IpPorts on which this policy group is 
      applied."
::= { vrIpMcastPg 704 }

vrIpMcastPgLinkToPolicyUserEntry OBJECT-TYPE
   SYNTAX     VrIpMcastPgLinkToPolicyUserEntry
   ACCESS     not-accessible
   STATUS     mandatory
   DESCRIPTION
     "An entry in the vrIpMcastPgLinkToPolicyUserTable."
   INDEX {
      vrIndex,
      vrIpIndex,
      vrIpMcastIndex,
      vrIpMcastPgIndex,
      vrIpMcastPgLinkToPolicyUserValue }
::= { vrIpMcastPgLinkToPolicyUserTable 1 }

VrIpMcastPgLinkToPolicyUserEntry ::= SEQUENCE {
   vrIpMcastPgLinkToPolicyUserValue
      Link,
   vrIpMcastPgLinkToPolicyUserRowStatus
      RowStatus }

vrIpMcastPgLinkToPolicyUserValue OBJECT-TYPE
   SYNTAX     Link 
   ACCESS     read-write
   STATUS     mandatory
   DESCRIPTION
     "This variable represents both the value and the index for the
      vrIpMcastPgLinkToPolicyUserTable."
::= { vrIpMcastPgLinkToPolicyUserEntry 1 }

vrIpMcastPgLinkToPolicyUserRowStatus OBJECT-TYPE
   SYNTAX     RowStatus 
   ACCESS     write-only
   STATUS     mandatory
   DESCRIPTION
     "This variable is used to control the addition and deletion 
      of individual values of the vrIpMcastPgLinkToPolicyUserTable."
::= { vrIpMcastPgLinkToPolicyUserEntry 2 }


-- Vr/<string> Ip Mcast Pg/<string> Group/<IpAddress>, 
-- <IpAddress>
-- This component specifies a range of multicast addresses for which 
-- the policy group applies. The range is specified as an IP address and 
-- mask combination.

vrIpMcastPgGrp OBJECT IDENTIFIER ::= { vrIpMcastPg 2 }



vrIpMcastPgGrpRowStatusTable OBJECT-TYPE
   SYNTAX     SEQUENCE OF VrIpMcastPgGrpRowStatusEntry
   ACCESS     not-accessible
   STATUS     mandatory
   DESCRIPTION
     "This entry controls the addition and deletion of 
      vrIpMcastPgGrp components."
::= { vrIpMcastPgGrp 1 }

vrIpMcastPgGrpRowStatusEntry OBJECT-TYPE
   SYNTAX     VrIpMcastPgGrpRowStatusEntry
   ACCESS     not-accessible
   STATUS     mandatory
   DESCRIPTION
     "A single entry in the table represents a single 
      vrIpMcastPgGrp component."
   INDEX {
      vrIndex,
      vrIpIndex,
      vrIpMcastIndex,
      vrIpMcastPgIndex,
      vrIpMcastPgGrpGAddrIndex,
      vrIpMcastPgGrpGMaskIndex }
::= { vrIpMcastPgGrpRowStatusTable 1 }

VrIpMcastPgGrpRowStatusEntry ::= SEQUENCE {
   vrIpMcastPgGrpRowStatus
      RowStatus,
   vrIpMcastPgGrpComponentName
      DisplayString,
   vrIpMcastPgGrpStorageType
      StorageType,
   vrIpMcastPgGrpGAddrIndex
      IpAddress,
   vrIpMcastPgGrpGMaskIndex
      IpAddress }

vrIpMcastPgGrpRowStatus OBJECT-TYPE
   SYNTAX     RowStatus 
   ACCESS     read-write
   STATUS     mandatory
   DESCRIPTION
     "This variable is used as the basis for SNMP naming of
      vrIpMcastPgGrp components.
      These components can be added and deleted."
::= { vrIpMcastPgGrpRowStatusEntry 1 }

vrIpMcastPgGrpComponentName OBJECT-TYPE
   SYNTAX     DisplayString 
   ACCESS     read-only
   STATUS     mandatory
   DESCRIPTION
     "This variable provides the component's string name for
      use with the ASCII Console Interface"
::= { vrIpMcastPgGrpRowStatusEntry 2 }

vrIpMcastPgGrpStorageType OBJECT-TYPE
   SYNTAX     StorageType 
   ACCESS     read-only
   STATUS     mandatory
   DESCRIPTION
     "This variable represents the storage type value for the
      vrIpMcastPgGrp tables."
::= { vrIpMcastPgGrpRowStatusEntry 4 }

vrIpMcastPgGrpGAddrIndex OBJECT-TYPE
   SYNTAX     IpAddress 
   ACCESS     not-accessible
   STATUS     mandatory
   DESCRIPTION
     "This variable represents an index for the vrIpMcastPgGrp tables."
::= { vrIpMcastPgGrpRowStatusEntry 10 }

vrIpMcastPgGrpGMaskIndex OBJECT-TYPE
   SYNTAX     IpAddress 
   ACCESS     not-accessible
   STATUS     mandatory
   DESCRIPTION
     "This variable represents an index for the vrIpMcastPgGrp tables."
::= { vrIpMcastPgGrpRowStatusEntry 11 }


-- This component represents a multicast domain. All routers 
-- participating in the domain use the same multicast protocol for all 
-- the intefaces in the domain.

vrIpMcastDomain OBJECT IDENTIFIER ::= { vrIpMcast 5 }



vrIpMcastDomainRowStatusTable OBJECT-TYPE
   SYNTAX     SEQUENCE OF VrIpMcastDomainRowStatusEntry
   ACCESS     not-accessible
   STATUS     mandatory
   DESCRIPTION
     "This entry controls the addition and deletion of 
      vrIpMcastDomain components."
::= { vrIpMcastDomain 1 }

vrIpMcastDomainRowStatusEntry OBJECT-TYPE
   SYNTAX     VrIpMcastDomainRowStatusEntry
   ACCESS     not-accessible
   STATUS     mandatory
   DESCRIPTION
     "A single entry in the table represents a single 
      vrIpMcastDomain component."
   INDEX {
      vrIndex,
      vrIpIndex,
      vrIpMcastIndex,
      vrIpMcastDomainIndex }
::= { vrIpMcastDomainRowStatusTable 1 }

VrIpMcastDomainRowStatusEntry ::= SEQUENCE {
   vrIpMcastDomainRowStatus
      RowStatus,
   vrIpMcastDomainComponentName
      DisplayString,
   vrIpMcastDomainStorageType
      StorageType,
   vrIpMcastDomainIndex
      Integer32 }

vrIpMcastDomainRowStatus OBJECT-TYPE
   SYNTAX     RowStatus 
   ACCESS     read-write
   STATUS     mandatory
   DESCRIPTION
     "This variable is used as the basis for SNMP naming of
      vrIpMcastDomain components.
      These components can be added and deleted."
::= { vrIpMcastDomainRowStatusEntry 1 }

vrIpMcastDomainComponentName OBJECT-TYPE
   SYNTAX     DisplayString 
   ACCESS     read-only
   STATUS     mandatory
   DESCRIPTION
     "This variable provides the component's string name for
      use with the ASCII Console Interface"
::= { vrIpMcastDomainRowStatusEntry 2 }

vrIpMcastDomainStorageType OBJECT-TYPE
   SYNTAX     StorageType 
   ACCESS     read-only
   STATUS     mandatory
   DESCRIPTION
     "This variable represents the storage type value for the
      vrIpMcastDomain tables."
::= { vrIpMcastDomainRowStatusEntry 4 }

vrIpMcastDomainIndex OBJECT-TYPE
   SYNTAX     Integer32 (0..3)
   ACCESS     not-accessible
   STATUS     mandatory
   DESCRIPTION
     "This variable represents the index for the vrIpMcastDomain tables."
::= { vrIpMcastDomainRowStatusEntry 10 }

vrIpMcastDomainOperTable OBJECT-TYPE
   SYNTAX     SEQUENCE OF VrIpMcastDomainOperEntry
   ACCESS     not-accessible
   STATUS     mandatory
   DESCRIPTION
     "This group contains the operational attributes for the Domain 
      component."
::= { vrIpMcastDomain 11 }

vrIpMcastDomainOperEntry OBJECT-TYPE
   SYNTAX     VrIpMcastDomainOperEntry
   ACCESS     not-accessible
   STATUS     mandatory
   DESCRIPTION
     "An entry in the vrIpMcastDomainOperTable."
   INDEX {
      vrIndex,
      vrIpIndex,
      vrIpMcastIndex,
      vrIpMcastDomainIndex }
::= { vrIpMcastDomainOperTable 1 }

VrIpMcastDomainOperEntry ::= SEQUENCE {
   vrIpMcastDomainProtocolActive
      INTEGER }

vrIpMcastDomainProtocolActive OBJECT-TYPE
   SYNTAX     INTEGER  {
                 none(0),
                 pimSm(1),
                 pimDm(2),
                 local(3),
                 dvmrp(4) }
   ACCESS     read-only
   STATUS     mandatory
   DESCRIPTION
     "This attribute indicates the multicast protocol active in this domain."
   DEFVAL     { none }
::= { vrIpMcastDomainOperEntry 1 }

-- 
-- *** THIS SUBTREE CURRENTLY NOT IMPLEMENTED ***
-- 

-- Vr/<string> Ip Mcast ForwardTable/<Ip 
-- Address>,<Decimal>,<IpAddress><IpAddress>
-- This component represents an IP multicast forwarding entry.

vrIpMcastFwd OBJECT IDENTIFIER ::= { vrIpMcast 6 }



vrIpMcastFwdRowStatusTable OBJECT-TYPE
   SYNTAX     SEQUENCE OF VrIpMcastFwdRowStatusEntry
   ACCESS     not-accessible
   STATUS     mandatory
   DESCRIPTION
     "*** THIS TABLE CURRENTLY NOT IMPLEMENTED ***

      This entry controls the addition and deletion of 
      vrIpMcastFwd components."
::= { vrIpMcastFwd 1 }

vrIpMcastFwdRowStatusEntry OBJECT-TYPE
   SYNTAX     VrIpMcastFwdRowStatusEntry
   ACCESS     not-accessible
   STATUS     mandatory
   DESCRIPTION
     "A single entry in the table represents a single 
      vrIpMcastFwd component."
   INDEX {
      vrIndex,
      vrIpIndex,
      vrIpMcastIndex,
      vrIpMcastFwdGAddrIndex,
      vrIpMcastFwdDomainIndex,
      vrIpMcastFwdSrcAddrIndex,
      vrIpMcastFwdSrcMaskIndex }
::= { vrIpMcastFwdRowStatusTable 1 }

VrIpMcastFwdRowStatusEntry ::= SEQUENCE {
   vrIpMcastFwdRowStatus
      RowStatus,
   vrIpMcastFwdComponentName
      DisplayString,
   vrIpMcastFwdStorageType
      StorageType,
   vrIpMcastFwdGAddrIndex
      IpAddress,
   vrIpMcastFwdDomainIndex
      Integer32,
   vrIpMcastFwdSrcAddrIndex
      IpAddress,
   vrIpMcastFwdSrcMaskIndex
      IpAddress }

vrIpMcastFwdRowStatus OBJECT-TYPE
   SYNTAX     RowStatus 
   ACCESS     read-only
   STATUS     mandatory
   DESCRIPTION
     "This variable is used as the basis for SNMP naming of
      vrIpMcastFwd components.
      These components cannot be added nor deleted."
::= { vrIpMcastFwdRowStatusEntry 1 }

vrIpMcastFwdComponentName OBJECT-TYPE
   SYNTAX     DisplayString 
   ACCESS     read-only
   STATUS     mandatory
   DESCRIPTION
     "This variable provides the component's string name for
      use with the ASCII Console Interface"
::= { vrIpMcastFwdRowStatusEntry 2 }

vrIpMcastFwdStorageType OBJECT-TYPE
   SYNTAX     StorageType 
   ACCESS     read-only
   STATUS     mandatory
   DESCRIPTION
     "This variable represents the storage type value for the
      vrIpMcastFwd tables."
::= { vrIpMcastFwdRowStatusEntry 4 }

vrIpMcastFwdGAddrIndex OBJECT-TYPE
   SYNTAX     IpAddress 
   ACCESS     not-accessible
   STATUS     mandatory
   DESCRIPTION
     "This variable represents an index for the vrIpMcastFwd tables."
::= { vrIpMcastFwdRowStatusEntry 10 }

vrIpMcastFwdDomainIndex OBJECT-TYPE
   SYNTAX     Integer32 (0..3)
   ACCESS     not-accessible
   STATUS     mandatory
   DESCRIPTION
     "This variable represents an index for the vrIpMcastFwd tables."
::= { vrIpMcastFwdRowStatusEntry 11 }

vrIpMcastFwdSrcAddrIndex OBJECT-TYPE
   SYNTAX     IpAddress 
   ACCESS     not-accessible
   STATUS     mandatory
   DESCRIPTION
     "This variable represents an index for the vrIpMcastFwd tables."
::= { vrIpMcastFwdRowStatusEntry 12 }

vrIpMcastFwdSrcMaskIndex OBJECT-TYPE
   SYNTAX     IpAddress 
   ACCESS     not-accessible
   STATUS     mandatory
   DESCRIPTION
     "This variable represents an index for the vrIpMcastFwd tables."
::= { vrIpMcastFwdRowStatusEntry 13 }

vrIpMcastFwdOperTable OBJECT-TYPE
   SYNTAX     SEQUENCE OF VrIpMcastFwdOperEntry
   ACCESS     not-accessible
   STATUS     mandatory
   DESCRIPTION
     "*** THIS TABLE CURRENTLY NOT IMPLEMENTED ***

      This group contains the operational attributes associated with a 
      multicast forwarding entry."
::= { vrIpMcastFwd 10 }

vrIpMcastFwdOperEntry OBJECT-TYPE
   SYNTAX     VrIpMcastFwdOperEntry
   ACCESS     not-accessible
   STATUS     mandatory
   DESCRIPTION
     "An entry in the vrIpMcastFwdOperTable."
   INDEX {
      vrIndex,
      vrIpIndex,
      vrIpMcastIndex,
      vrIpMcastFwdGAddrIndex,
      vrIpMcastFwdDomainIndex,
      vrIpMcastFwdSrcAddrIndex,
      vrIpMcastFwdSrcMaskIndex }
::= { vrIpMcastFwdOperTable 1 }

VrIpMcastFwdOperEntry ::= SEQUENCE {
   vrIpMcastFwdAge
      Unsigned32,
   vrIpMcastFwdInProtocolPortName
      RowPointer,
   vrIpMcastFwdProtocol
      INTEGER,
   vrIpMcastFwdReversePathForwardingNeighbor
      IpAddress,
   vrIpMcastFwdFlags
      AsciiString }

vrIpMcastFwdAge OBJECT-TYPE
   SYNTAX     Unsigned32 (0..4294967295)
   ACCESS     read-only
   STATUS     mandatory
   DESCRIPTION
     "This attribute indicates the number of seconds since this route was 
      last updated."
::= { vrIpMcastFwdOperEntry 2 }

vrIpMcastFwdInProtocolPortName OBJECT-TYPE
   SYNTAX     RowPointer 
   ACCESS     read-only
   STATUS     mandatory
   DESCRIPTION
     "This attribute indicates the name of the (incoming) protocol port 
      from which the route was learned."
::= { vrIpMcastFwdOperEntry 3 }

vrIpMcastFwdProtocol OBJECT-TYPE
   SYNTAX     INTEGER  {
                 other(1),
                 local(2),
                 netmgmt(3),
                 dvmrp(4),
                 mospf(5),
                 pimSparseDense(6),
                 cbt(7),
                 pimSparse(8),
                 pimDense(9),
                 igmponly(10) }
   ACCESS     read-only
   STATUS     mandatory
   DESCRIPTION
     "This attribute indicates the multicast routing protocol via which this 
      multicast forwarding entry was learned."
::= { vrIpMcastFwdOperEntry 4 }

vrIpMcastFwdReversePathForwardingNeighbor OBJECT-TYPE
   SYNTAX     IpAddress 
   ACCESS     read-only
   STATUS     mandatory
   DESCRIPTION
     "This attribute indicates the address of the upstream neighbor (RPF 
      neighbor) from which IP datagrams from these sources to this 
      multicast address are received, or 0.0.0.0 if the upstream is 
      unknown (e.g., in CBT)."
::= { vrIpMcastFwdOperEntry 5 }

vrIpMcastFwdFlags OBJECT-TYPE
   SYNTAX     AsciiString (SIZE (3..20))
   ACCESS     read-only
   STATUS     mandatory
   DESCRIPTION
     "This attribute indicates information concerning the forwarding 
      entry. In particular, the flag information indicates wildcard, SPT, 
      RPT, and Reg entries."
::= { vrIpMcastFwdOperEntry 703 }

-- 
-- *** THIS SUBTREE CURRENTLY NOT IMPLEMENTED ***
-- 

-- Vr/<string> Ip Mcast Fwd/
-- <IpAddress>,<Decimal>,<IpAddress><IpAddress> OutInterface/
-- <IpAddress>,<Decimal>
-- This component represents an out interface for a multicast 
-- forwarding entry.

vrIpMcastFwdOif OBJECT IDENTIFIER ::= { vrIpMcastFwd 2 }



vrIpMcastFwdOifRowStatusTable OBJECT-TYPE
   SYNTAX     SEQUENCE OF VrIpMcastFwdOifRowStatusEntry
   ACCESS     not-accessible
   STATUS     mandatory
   DESCRIPTION
     "*** THIS TABLE CURRENTLY NOT IMPLEMENTED ***

      This entry controls the addition and deletion of 
      vrIpMcastFwdOif components."
::= { vrIpMcastFwdOif 1 }

vrIpMcastFwdOifRowStatusEntry OBJECT-TYPE
   SYNTAX     VrIpMcastFwdOifRowStatusEntry
   ACCESS     not-accessible
   STATUS     mandatory
   DESCRIPTION
     "A single entry in the table represents a single 
      vrIpMcastFwdOif component."
   INDEX {
      vrIndex,
      vrIpIndex,
      vrIpMcastIndex,
      vrIpMcastFwdGAddrIndex,
      vrIpMcastFwdDomainIndex,
      vrIpMcastFwdSrcAddrIndex,
      vrIpMcastFwdSrcMaskIndex,
      vrIpMcastFwdOifOutIfAddressIndex,
      vrIpMcastFwdOifConnectionIndex }
::= { vrIpMcastFwdOifRowStatusTable 1 }

VrIpMcastFwdOifRowStatusEntry ::= SEQUENCE {
   vrIpMcastFwdOifRowStatus
      RowStatus,
   vrIpMcastFwdOifComponentName
      DisplayString,
   vrIpMcastFwdOifStorageType
      StorageType,
   vrIpMcastFwdOifOutIfAddressIndex
      IpAddress,
   vrIpMcastFwdOifConnectionIndex
      Integer32 }

vrIpMcastFwdOifRowStatus OBJECT-TYPE
   SYNTAX     RowStatus 
   ACCESS     read-only
   STATUS     mandatory
   DESCRIPTION
     "This variable is used as the basis for SNMP naming of
      vrIpMcastFwdOif components.
      These components cannot be added nor deleted."
::= { vrIpMcastFwdOifRowStatusEntry 1 }

vrIpMcastFwdOifComponentName OBJECT-TYPE
   SYNTAX     DisplayString 
   ACCESS     read-only
   STATUS     mandatory
   DESCRIPTION
     "This variable provides the component's string name for
      use with the ASCII Console Interface"
::= { vrIpMcastFwdOifRowStatusEntry 2 }

vrIpMcastFwdOifStorageType OBJECT-TYPE
   SYNTAX     StorageType 
   ACCESS     read-only
   STATUS     mandatory
   DESCRIPTION
     "This variable represents the storage type value for the
      vrIpMcastFwdOif tables."
::= { vrIpMcastFwdOifRowStatusEntry 4 }

vrIpMcastFwdOifOutIfAddressIndex OBJECT-TYPE
   SYNTAX     IpAddress 
   ACCESS     not-accessible
   STATUS     mandatory
   DESCRIPTION
     "This variable represents an index for the vrIpMcastFwdOif tables."
::= { vrIpMcastFwdOifRowStatusEntry 10 }

vrIpMcastFwdOifConnectionIndex OBJECT-TYPE
   SYNTAX     Integer32 (0..65535)
   ACCESS     not-accessible
   STATUS     mandatory
   DESCRIPTION
     "This variable represents an index for the vrIpMcastFwdOif tables."
::= { vrIpMcastFwdOifRowStatusEntry 11 }

vrIpMcastFwdOifOperTable OBJECT-TYPE
   SYNTAX     SEQUENCE OF VrIpMcastFwdOifOperEntry
   ACCESS     not-accessible
   STATUS     mandatory
   DESCRIPTION
     "*** THIS TABLE CURRENTLY NOT IMPLEMENTED ***

      This group contains the operational attributes for the 
      InwIpOutInterface component."
::= { vrIpMcastFwdOif 10 }

vrIpMcastFwdOifOperEntry OBJECT-TYPE
   SYNTAX     VrIpMcastFwdOifOperEntry
   ACCESS     not-accessible
   STATUS     mandatory
   DESCRIPTION
     "An entry in the vrIpMcastFwdOifOperTable."
   INDEX {
      vrIndex,
      vrIpIndex,
      vrIpMcastIndex,
      vrIpMcastFwdGAddrIndex,
      vrIpMcastFwdDomainIndex,
      vrIpMcastFwdSrcAddrIndex,
      vrIpMcastFwdSrcMaskIndex,
      vrIpMcastFwdOifOutIfAddressIndex,
      vrIpMcastFwdOifConnectionIndex }
::= { vrIpMcastFwdOifOperTable 1 }

VrIpMcastFwdOifOperEntry ::= SEQUENCE {
   vrIpMcastFwdOifIfIndex
      InterfaceIndex,
   vrIpMcastFwdOifProtocol
      INTEGER,
   vrIpMcastFwdOifAge
      Unsigned32,
   vrIpMcastFwdOifOutProtocolPortName
      RowPointer }

vrIpMcastFwdOifIfIndex OBJECT-TYPE
   SYNTAX     InterfaceIndex (1..65535)
   ACCESS     read-only
   STATUS     mandatory
   DESCRIPTION
     "This attribute indicates the ifIndex value of this outgoing 
      interface entry."
::= { vrIpMcastFwdOifOperEntry 2 }

vrIpMcastFwdOifProtocol OBJECT-TYPE
   SYNTAX     INTEGER  {
                 other(1),
                 local(2),
                 netmgmt(3),
                 dvmrp(4),
                 mospf(5),
                 pimSparseDense(6),
                 cbt(7),
                 pimSparse(8),
                 pimDense(9),
                 igmponly(10) }
   ACCESS     read-only
   STATUS     mandatory
   DESCRIPTION
     "This attribute indicates the multicast routing protocol via which this 
      multicast forwarding outinterface entry was learned."
::= { vrIpMcastFwdOifOperEntry 3 }

vrIpMcastFwdOifAge OBJECT-TYPE
   SYNTAX     Unsigned32 (0..4294967295)
   ACCESS     read-only
   STATUS     mandatory
   DESCRIPTION
     "This attribute indicates the number of seconds since this route was 
      last updated"
::= { vrIpMcastFwdOifOperEntry 4 }

vrIpMcastFwdOifOutProtocolPortName OBJECT-TYPE
   SYNTAX     RowPointer 
   ACCESS     read-only
   STATUS     mandatory
   DESCRIPTION
     "This attribute indicates the name of the protocol port by which the 
      next hop of this route should be reached."
::= { vrIpMcastFwdOifOperEntry 702 }

-- 
-- *** THIS SUBTREE CURRENTLY NOT IMPLEMENTED ***
-- 

-- Vr/<string> Ip Mcast CacheStats/n
-- This component represents the IP MCAST cache table on an LP.

vrIpMcastCacheStats OBJECT IDENTIFIER ::= { vrIpMcast 8 }



vrIpMcastCacheStatsRowStatusTable OBJECT-TYPE
   SYNTAX     SEQUENCE OF VrIpMcastCacheStatsRowStatusEntry
   ACCESS     not-accessible
   STATUS     mandatory
   DESCRIPTION
     "*** THIS TABLE CURRENTLY NOT IMPLEMENTED ***

      This entry controls the addition and deletion of 
      vrIpMcastCacheStats components."
::= { vrIpMcastCacheStats 1 }

vrIpMcastCacheStatsRowStatusEntry OBJECT-TYPE
   SYNTAX     VrIpMcastCacheStatsRowStatusEntry
   ACCESS     not-accessible
   STATUS     mandatory
   DESCRIPTION
     "A single entry in the table represents a single 
      vrIpMcastCacheStats component."
   INDEX {
      vrIndex,
      vrIpIndex,
      vrIpMcastIndex,
      vrIpMcastCacheStatsIndex }
::= { vrIpMcastCacheStatsRowStatusTable 1 }

VrIpMcastCacheStatsRowStatusEntry ::= SEQUENCE {
   vrIpMcastCacheStatsRowStatus
      RowStatus,
   vrIpMcastCacheStatsComponentName
      DisplayString,
   vrIpMcastCacheStatsStorageType
      StorageType,
   vrIpMcastCacheStatsIndex
      Integer32 }

vrIpMcastCacheStatsRowStatus OBJECT-TYPE
   SYNTAX     RowStatus 
   ACCESS     read-only
   STATUS     mandatory
   DESCRIPTION
     "This variable is used as the basis for SNMP naming of
      vrIpMcastCacheStats components.
      These components cannot be added nor deleted."
::= { vrIpMcastCacheStatsRowStatusEntry 1 }

vrIpMcastCacheStatsComponentName OBJECT-TYPE
   SYNTAX     DisplayString 
   ACCESS     read-only
   STATUS     mandatory
   DESCRIPTION
     "This variable provides the component's string name for
      use with the ASCII Console Interface"
::= { vrIpMcastCacheStatsRowStatusEntry 2 }

vrIpMcastCacheStatsStorageType OBJECT-TYPE
   SYNTAX     StorageType 
   ACCESS     read-only
   STATUS     mandatory
   DESCRIPTION
     "This variable represents the storage type value for the
      vrIpMcastCacheStats tables."
::= { vrIpMcastCacheStatsRowStatusEntry 4 }

vrIpMcastCacheStatsIndex OBJECT-TYPE
   SYNTAX     Integer32 (0..15)
   ACCESS     not-accessible
   STATUS     mandatory
   DESCRIPTION
     "This variable represents the index for the vrIpMcastCacheStats tables."
::= { vrIpMcastCacheStatsRowStatusEntry 10 }

vrIpMcastCacheStatsStateTable OBJECT-TYPE
   SYNTAX     SEQUENCE OF VrIpMcastCacheStatsStateEntry
   ACCESS     not-accessible
   STATUS     mandatory
   DESCRIPTION
     "*** THIS TABLE CURRENTLY NOT IMPLEMENTED ***

      This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { vrIpMcastCacheStats 10 }

vrIpMcastCacheStatsStateEntry OBJECT-TYPE
   SYNTAX     VrIpMcastCacheStatsStateEntry
   ACCESS     not-accessible
   STATUS     mandatory
   DESCRIPTION
     "An entry in the vrIpMcastCacheStatsStateTable."
   INDEX {
      vrIndex,
      vrIpIndex,
      vrIpMcastIndex,
      vrIpMcastCacheStatsIndex }
::= { vrIpMcastCacheStatsStateTable 1 }

VrIpMcastCacheStatsStateEntry ::= SEQUENCE {
   vrIpMcastCacheStatsAdminState
      INTEGER,
   vrIpMcastCacheStatsOperationalState
      INTEGER,
   vrIpMcastCacheStatsUsageState
      INTEGER }

vrIpMcastCacheStatsAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { vrIpMcastCacheStatsStateEntry 1 }

vrIpMcastCacheStatsOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { vrIpMcastCacheStatsStateEntry 2 }

vrIpMcastCacheStatsUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { vrIpMcastCacheStatsStateEntry 3 }

vrIpMcastCacheStatsOperTable OBJECT-TYPE
   SYNTAX     SEQUENCE OF VrIpMcastCacheStatsOperEntry
   ACCESS     not-accessible
   STATUS     mandatory
   DESCRIPTION
     "*** THIS TABLE CURRENTLY NOT IMPLEMENTED ***

      This group houses all the operational attributes of an Ip cache table."
::= { vrIpMcastCacheStats 11 }

vrIpMcastCacheStatsOperEntry OBJECT-TYPE
   SYNTAX     VrIpMcastCacheStatsOperEntry
   ACCESS     not-accessible
   STATUS     mandatory
   DESCRIPTION
     "An entry in the vrIpMcastCacheStatsOperTable."
   INDEX {
      vrIndex,
      vrIpIndex,
      vrIpMcastIndex,
      vrIpMcastCacheStatsIndex }
::= { vrIpMcastCacheStatsOperTable 1 }

VrIpMcastCacheStatsOperEntry ::= SEQUENCE {
   vrIpMcastCacheStatsEntriesFree
      Unsigned32,
   vrIpMcastCacheStatsTotalLookups
      Unsigned32,
   vrIpMcastCacheStatsLookupMisses
      Counter32,
   vrIpMcastCacheStatsCacheTableMaxEntries
      Unsigned32 }

vrIpMcastCacheStatsEntriesFree OBJECT-TYPE
   SYNTAX     Unsigned32 (0..8000)
   ACCESS     read-only
   STATUS     mandatory
   DESCRIPTION
     "This attribute is indicative of the number of free Ip cache table entries.
      A consistently high value for this attribute indicates that there is a 
      resource surplus of the memory requirements for cache table. This 
      surplus could be utilized elsewhere if needed by adjusting the 
      cacheTableMaxEntries under the Ip component."
::= { vrIpMcastCacheStatsOperEntry 3 }

vrIpMcastCacheStatsTotalLookups OBJECT-TYPE
   SYNTAX     Unsigned32 (0..4294967295)
   ACCESS     read-only
   STATUS     mandatory
   DESCRIPTION
     "This attribute indicates the total number of local cache lookups. It wraps 
      around to 0 when it reaches the maximum value of 4294967295."
::= { vrIpMcastCacheStatsOperEntry 4 }

vrIpMcastCacheStatsLookupMisses OBJECT-TYPE
   SYNTAX     Counter32 
   ACCESS     read-only
   STATUS     mandatory
   DESCRIPTION
     "This attribute indicates the total number of local cache lookup misses. It 
      wraps around to 0 when it reaches the maximum value of 4294967295."
::= { vrIpMcastCacheStatsOperEntry 5 }

vrIpMcastCacheStatsCacheTableMaxEntries OBJECT-TYPE
   SYNTAX     Unsigned32 (0..8000)
   ACCESS     read-only
   STATUS     mandatory
   DESCRIPTION
     "This attribute indicates the current maximum number of entries that can 
      exist in the IP local cache table on each LP."
::= { vrIpMcastCacheStatsOperEntry 395 }


-- Vr/<string> Ip Mcast PimSm
-- The Protocol Independent Multicast Sparse Mode (PimSm) 
-- component represents a multicast protocol which can be used for 
-- efficiently routing multicast traffic to multicast groups that may 
-- span wide-area internets. The pimSm is referred as protocol 
-- independent multicast because it it not dependent on any particular 
-- unicast routing protocol and it is designed to support groups which 
-- are sparsely located.

vrIpMcastPimSm OBJECT IDENTIFIER ::= { vrIpMcast 9 }



vrIpMcastPimSmRowStatusTable OBJECT-TYPE
   SYNTAX     SEQUENCE OF VrIpMcastPimSmRowStatusEntry
   ACCESS     not-accessible
   STATUS     mandatory
   DESCRIPTION
     "This entry controls the addition and deletion of 
      vrIpMcastPimSm components."
::= { vrIpMcastPimSm 1 }

vrIpMcastPimSmRowStatusEntry OBJECT-TYPE
   SYNTAX     VrIpMcastPimSmRowStatusEntry
   ACCESS     not-accessible
   STATUS     mandatory
   DESCRIPTION
     "A single entry in the table represents a single 
      vrIpMcastPimSm component."
   INDEX {
      vrIndex,
      vrIpIndex,
      vrIpMcastIndex,
      vrIpMcastPimSmIndex }
::= { vrIpMcastPimSmRowStatusTable 1 }

VrIpMcastPimSmRowStatusEntry ::= SEQUENCE {
   vrIpMcastPimSmRowStatus
      RowStatus,
   vrIpMcastPimSmComponentName
      DisplayString,
   vrIpMcastPimSmStorageType
      StorageType,
   vrIpMcastPimSmIndex
      NonReplicated }

vrIpMcastPimSmRowStatus OBJECT-TYPE
   SYNTAX     RowStatus 
   ACCESS     read-write
   STATUS     mandatory
   DESCRIPTION
     "This variable is used as the basis for SNMP naming of
      vrIpMcastPimSm components.
      These components can be added and deleted."
::= { vrIpMcastPimSmRowStatusEntry 1 }

vrIpMcastPimSmComponentName OBJECT-TYPE
   SYNTAX     DisplayString 
   ACCESS     read-only
   STATUS     mandatory
   DESCRIPTION
     "This variable provides the component's string name for
      use with the ASCII Console Interface"
::= { vrIpMcastPimSmRowStatusEntry 2 }

vrIpMcastPimSmStorageType OBJECT-TYPE
   SYNTAX     StorageType 
   ACCESS     read-only
   STATUS     mandatory
   DESCRIPTION
     "This variable represents the storage type value for the
      vrIpMcastPimSm tables."
::= { vrIpMcastPimSmRowStatusEntry 4 }

vrIpMcastPimSmIndex OBJECT-TYPE
   SYNTAX     NonReplicated 
   ACCESS     not-accessible
   STATUS     mandatory
   DESCRIPTION
     "This variable represents the index for the vrIpMcastPimSm tables."
::= { vrIpMcastPimSmRowStatusEntry 10 }

vrIpMcastPimSmAdminControlTable OBJECT-TYPE
   SYNTAX     SEQUENCE OF VrIpMcastPimSmAdminControlEntry
   ACCESS     not-accessible
   STATUS     mandatory
   DESCRIPTION
     "This group includes the Administrative Control attribute. This 
      attribute defines the current administrative state of this component."
::= { vrIpMcastPimSm 10 }

vrIpMcastPimSmAdminControlEntry OBJECT-TYPE
   SYNTAX     VrIpMcastPimSmAdminControlEntry
   ACCESS     not-accessible
   STATUS     mandatory
   DESCRIPTION
     "An entry in the vrIpMcastPimSmAdminControlTable."
   INDEX {
      vrIndex,
      vrIpIndex,
      vrIpMcastIndex,
      vrIpMcastPimSmIndex }
::= { vrIpMcastPimSmAdminControlTable 1 }

VrIpMcastPimSmAdminControlEntry ::= SEQUENCE {
   vrIpMcastPimSmSnmpAdminStatus
      INTEGER }

vrIpMcastPimSmSnmpAdminStatus OBJECT-TYPE
   SYNTAX     INTEGER  {
                 up(1),
                 down(2),
                 testing(3) }
   ACCESS     read-write
   STATUS     mandatory
   DESCRIPTION
     "The desired state of the interface. The up state indicates the 
      interface is operational and packet forwarding is allowed. The down 
      state indicates the interface is not operational and packet forwarding 
      is unavailable. The testing state indicates that no operational 
      packets can be passed."
   DEFVAL     { up }
::= { vrIpMcastPimSmAdminControlEntry 1 }

vrIpMcastPimSmStateTable OBJECT-TYPE
   SYNTAX     SEQUENCE OF VrIpMcastPimSmStateEntry
   ACCESS     not-accessible
   STATUS     mandatory
   DESCRIPTION
     "This group contains the three OSI State attributes. The descriptions 
      generically indicate what each state attribute implies about the 
      component. Note that not all the values and state combinations 
      described here are supported by every component which uses this 
      group. For component-specific information and the valid state 
      combinations, refer to NTP 241-7001-150, Passport Operations and 
      Maintenance Guide."
::= { vrIpMcastPimSm 13 }

vrIpMcastPimSmStateEntry OBJECT-TYPE
   SYNTAX     VrIpMcastPimSmStateEntry
   ACCESS     not-accessible
   STATUS     mandatory
   DESCRIPTION
     "An entry in the vrIpMcastPimSmStateTable."
   INDEX {
      vrIndex,
      vrIpIndex,
      vrIpMcastIndex,
      vrIpMcastPimSmIndex }
::= { vrIpMcastPimSmStateTable 1 }

VrIpMcastPimSmStateEntry ::= SEQUENCE {
   vrIpMcastPimSmAdminState
      INTEGER,
   vrIpMcastPimSmOperationalState
      INTEGER,
   vrIpMcastPimSmUsageState
      INTEGER }

vrIpMcastPimSmAdminState OBJECT-TYPE
   SYNTAX     INTEGER  {
                 locked(0),
                 unlocked(1),
                 shuttingDown(2) }
   ACCESS     read-only
   STATUS     mandatory
   DESCRIPTION
     "This attribute indicates the OSI Administrative State of the 
      component.
      
      The value locked indicates that the component is administratively 
      prohibited from providing services for its users. A Lock or Lock -
      force command has been previously issued for this component. 
      When the value is locked, the value of usageState must be idle.
      
      The value shuttingDown indicates that the component is 
      administratively permitted to provide service to its existing users 
      only. A Lock command was issued against the component and it is 
      in the process of shutting down.
      
      The value unlocked indicates that the component is administratively 
      permitted to provide services for its users. To enter this state, issue 
      an Unlock command to this component."
   DEFVAL     { unlocked }
::= { vrIpMcastPimSmStateEntry 1 }

vrIpMcastPimSmOperationalState OBJECT-TYPE
   SYNTAX     INTEGER  {
                 disabled(0),
                 enabled(1) }
   ACCESS     read-only
   STATUS     mandatory
   DESCRIPTION
     "This attribute indicates the OSI Operational State of the component.
      
      The value enabled indicates that the component is available for 
      operation. Note that if adminState is locked, it would still not be 
      providing service.
      
      The value disabled indicates that the component is not available for 
      operation. For example, something is wrong with the component 
      itself, or with another component on which this one depends. If the 
      value is disabled, the usageState must be idle."
   DEFVAL     { disabled }
::= { vrIpMcastPimSmStateEntry 2 }

vrIpMcastPimSmUsageState OBJECT-TYPE
   SYNTAX     INTEGER  {
                 idle(0),
                 active(1),
                 busy(2) }
   ACCESS     read-only
   STATUS     mandatory
   DESCRIPTION
     "This attribute indicates the OSI Usage State of the component.
      
      The value idle indicates that the component is not currently in use.
      
      The value active indicates that the component is in use and has 
      spare capacity to provide for additional users.
      
      The value busy indicates that the component is in use and has no 
      spare operating capacity for additional users at this time."
   DEFVAL     { idle }
::= { vrIpMcastPimSmStateEntry 3 }

vrIpMcastPimSmOperStatusTable OBJECT-TYPE
   SYNTAX     SEQUENCE OF VrIpMcastPimSmOperStatusEntry
   ACCESS     not-accessible
   STATUS     mandatory
   DESCRIPTION
     "This group includes the Operational Status attribute. This attribute 
      defines the current operational state of this component."
::= { vrIpMcastPimSm 14 }

vrIpMcastPimSmOperStatusEntry OBJECT-TYPE
   SYNTAX     VrIpMcastPimSmOperStatusEntry
   ACCESS     not-accessible
   STATUS     mandatory
   DESCRIPTION
     "An entry in the vrIpMcastPimSmOperStatusTable."
   INDEX {
      vrIndex,
      vrIpIndex,
      vrIpMcastIndex,
      vrIpMcastPimSmIndex }
::= { vrIpMcastPimSmOperStatusTable 1 }

VrIpMcastPimSmOperStatusEntry ::= SEQUENCE {
   vrIpMcastPimSmSnmpOperStatus
      INTEGER }

vrIpMcastPimSmSnmpOperStatus OBJECT-TYPE
   SYNTAX     INTEGER  {
                 up(1),
                 down(2),
                 testing(3) }
   ACCESS     read-only
   STATUS     mandatory
   DESCRIPTION
     "The current state of the interface. The up state indicates the 
      interface is operational and capable of forwarding packets. The 
      down state indicates the interface is not operational, thus unable to 
      forward packets. testing state indicates that no operational packets 
      can be passed."
   DEFVAL     { up }
::= { vrIpMcastPimSmOperStatusEntry 1 }


-- Vr/<string> Ip Mcast PimSm domain/n
-- The Domain component represents a logical link to the Domain 
-- component under Mcast component. Information relevant to a 
-- domain are included under the PimSm Domain component.

vrIpMcastPimSmDomain OBJECT IDENTIFIER ::= { vrIpMcastPimSm 2 }



vrIpMcastPimSmDomainRowStatusTable OBJECT-TYPE
   SYNTAX     SEQUENCE OF VrIpMcastPimSmDomainRowStatusEntry
   ACCESS     not-accessible
   STATUS     mandatory
   DESCRIPTION
     "This entry controls the addition and deletion of 
      vrIpMcastPimSmDomain components."
::= { vrIpMcastPimSmDomain 1 }

vrIpMcastPimSmDomainRowStatusEntry OBJECT-TYPE
   SYNTAX     VrIpMcastPimSmDomainRowStatusEntry
   ACCESS     not-accessible
   STATUS     mandatory
   DESCRIPTION
     "A single entry in the table represents a single 
      vrIpMcastPimSmDomain component."
   INDEX {
      vrIndex,
      vrIpIndex,
      vrIpMcastIndex,
      vrIpMcastPimSmIndex,
      vrIpMcastPimSmDomainIndex }
::= { vrIpMcastPimSmDomainRowStatusTable 1 }

VrIpMcastPimSmDomainRowStatusEntry ::= SEQUENCE {
   vrIpMcastPimSmDomainRowStatus
      RowStatus,
   vrIpMcastPimSmDomainComponentName
      DisplayString,
   vrIpMcastPimSmDomainStorageType
      StorageType,
   vrIpMcastPimSmDomainIndex
      Integer32 }

vrIpMcastPimSmDomainRowStatus OBJECT-TYPE
   SYNTAX     RowStatus 
   ACCESS     read-write
   STATUS     mandatory
   DESCRIPTION
     "This variable is used as the basis for SNMP naming of
      vrIpMcastPimSmDomain components.
      These components can be added and deleted."
::= { vrIpMcastPimSmDomainRowStatusEntry 1 }

vrIpMcastPimSmDomainComponentName OBJECT-TYPE
   SYNTAX     DisplayString 
   ACCESS     read-only
   STATUS     mandatory
   DESCRIPTION
     "This variable provides the component's string name for
      use with the ASCII Console Interface"
::= { vrIpMcastPimSmDomainRowStatusEntry 2 }

vrIpMcastPimSmDomainStorageType OBJECT-TYPE
   SYNTAX     StorageType 
   ACCESS     read-only
   STATUS     mandatory
   DESCRIPTION
     "This variable represents the storage type value for the
      vrIpMcastPimSmDomain tables."
::= { vrIpMcastPimSmDomainRowStatusEntry 4 }

vrIpMcastPimSmDomainIndex OBJECT-TYPE
   SYNTAX     Integer32 (0..3)
   ACCESS     not-accessible
   STATUS     mandatory
   DESCRIPTION
     "This variable represents the index for the vrIpMcastPimSmDomain tables."
::= { vrIpMcastPimSmDomainRowStatusEntry 10 }

vrIpMcastPimSmDomainProvTable OBJECT-TYPE
   SYNTAX     SEQUENCE OF VrIpMcastPimSmDomainProvEntry
   ACCESS     not-accessible
   STATUS     mandatory
   DESCRIPTION
     "This group contains the provisionable attributes of the Domain 
      component under the PimSm component."
::= { vrIpMcastPimSmDomain 10 }

vrIpMcastPimSmDomainProvEntry OBJECT-TYPE
   SYNTAX     VrIpMcastPimSmDomainProvEntry
   ACCESS     not-accessible
   STATUS     mandatory
   DESCRIPTION
     "An entry in the vrIpMcastPimSmDomainProvTable."
   INDEX {
      vrIndex,
      vrIpIndex,
      vrIpMcastIndex,
      vrIpMcastPimSmIndex,
      vrIpMcastPimSmDomainIndex }
::= { vrIpMcastPimSmDomainProvTable 1 }

VrIpMcastPimSmDomainProvEntry ::= SEQUENCE {
   vrIpMcastPimSmDomainJoinPruneInterval
      Unsigned32,
   vrIpMcastPimSmDomainSptJoinThreshold
      Unsigned32 }

vrIpMcastPimSmDomainJoinPruneInterval OBJECT-TYPE
   SYNTAX     Unsigned32 (5..4292967295)
   ACCESS     read-write
   STATUS     mandatory
   DESCRIPTION
     "This attribute specifies the frequency at which PIM Join/Prune 
      messages are transmitted on this PIM interface."
   DEFVAL     { 60 }
::= { vrIpMcastPimSmDomainProvEntry 1 }

vrIpMcastPimSmDomainSptJoinThreshold OBJECT-TYPE
   SYNTAX     Unsigned32 (0 | 1)
   ACCESS     read-write
   STATUS     mandatory
   DESCRIPTION
     "The attribute specifies the threshold at which the last-hop router 
      joins the shortest-path tree. If 0 is selected then the router 
      immediately joins the shortest path tree upon receipt of the first data 
      packet. If infinity is selected then the router never joins the shortest 
      path tree.

      VALUES (

      1 = infinity

      )"
   DEFVAL     { 1 }
::= { vrIpMcastPimSmDomainProvEntry 2 }

vrIpMcastPimSmDomainOperTable OBJECT-TYPE
   SYNTAX     SEQUENCE OF VrIpMcastPimSmDomainOperEntry
   ACCESS     not-accessible
   STATUS     mandatory
   DESCRIPTION
     "This group contains the operational attributes of the Domain 
      component under the PimSm component."
::= { vrIpMcastPimSmDomain 11 }

vrIpMcastPimSmDomainOperEntry OBJECT-TYPE
   SYNTAX     VrIpMcastPimSmDomainOperEntry
   ACCESS     not-accessible
   STATUS     mandatory
   DESCRIPTION
     "An entry in the vrIpMcastPimSmDomainOperTable."
   INDEX {
      vrIndex,
      vrIpIndex,
      vrIpMcastIndex,
      vrIpMcastPimSmIndex,
      vrIpMcastPimSmDomainIndex }
::= { vrIpMcastPimSmDomainOperTable 1 }

VrIpMcastPimSmDomainOperEntry ::= SEQUENCE {
   vrIpMcastPimSmDomainBsrAddress
      IpAddress,
   vrIpMcastPimSmDomainBsrExpiryTimer
      TimeTicks }

vrIpMcastPimSmDomainBsrAddress OBJECT-TYPE
   SYNTAX     IpAddress 
   ACCESS     read-only
   STATUS     mandatory
   DESCRIPTION
     "This attribute indicates the IP address of the bootstrap router (BSR) 
      for this PIM domain."
::= { vrIpMcastPimSmDomainOperEntry 1 }

vrIpMcastPimSmDomainBsrExpiryTimer OBJECT-TYPE
   SYNTAX     TimeTicks 
   ACCESS     read-only
   STATUS     mandatory
   DESCRIPTION
     "This attribute indicates the minimum time remaining before the 
      bootstrap router in this domain will be declared down."
::= { vrIpMcastPimSmDomainOperEntry 2 }

vrIpMcastPimSmDomainStatsTable OBJECT-TYPE
   SYNTAX     SEQUENCE OF VrIpMcastPimSmDomainStatsEntry
   ACCESS     not-accessible
   STATUS     mandatory
   DESCRIPTION
     "This group contains the statistics attributes of the Domain 
      component under the PimSm component."
::= { vrIpMcastPimSmDomain 12 }

vrIpMcastPimSmDomainStatsEntry OBJECT-TYPE
   SYNTAX     VrIpMcastPimSmDomainStatsEntry
   ACCESS     not-accessible
   STATUS     mandatory
   DESCRIPTION
     "An entry in the vrIpMcastPimSmDomainStatsTable."
   INDEX {
      vrIndex,
      vrIpIndex,
      vrIpMcastIndex,
      vrIpMcastPimSmIndex,
      vrIpMcastPimSmDomainIndex }
::= { vrIpMcastPimSmDomainStatsTable 1 }

VrIpMcastPimSmDomainStatsEntry ::= SEQUENCE {
   vrIpMcastPimSmDomainTxBsrMsg
      Counter32,
   vrIpMcastPimSmDomainRxBsrMsg
      Counter32,
   vrIpMcastPimSmDomainTxCRpAdvMsg
      Counter32,
   vrIpMcastPimSmDomainRxCRpAdvMsg
      Counter32,
   vrIpMcastPimSmDomainTxHelloMsg
      Counter32,
   vrIpMcastPimSmDomainRxHelloMsg
      Counter32,
   vrIpMcastPimSmDomainTxRegisterMsg
      Counter32,
   vrIpMcastPimSmDomainRxRegisterMsg
      Counter32,
   vrIpMcastPimSmDomainTxRegisterStopMsg
      Counter32,
   vrIpMcastPimSmDomainRxRegisterStopMsg
      Counter32,
   vrIpMcastPimSmDomainTxAssertMsg
      Counter32,
   vrIpMcastPimSmDomainRxAssertMsg
      Counter32,
   vrIpMcastPimSmDomainTxJPMsg
      Counter32,
   vrIpMcastPimSmDomainRxJPMsg
      Counter32,
   vrIpMcastPimSmDomainDiscardBsrMsg
      Counter32,
   vrIpMcastPimSmDomainDiscardCRpAdvMsg
      Counter32,
   vrIpMcastPimSmDomainDiscardHelloMsg
      Counter32,
   vrIpMcastPimSmDomainDiscardRegisterMsg
      Counter32,
   vrIpMcastPimSmDomainDiscardRegisterStopMsg
      Counter32,
   vrIpMcastPimSmDomainDiscardAssertMsg
      Counter32,
   vrIpMcastPimSmDomainDiscardJPMsg
      Counter32 }

vrIpMcastPimSmDomainTxBsrMsg OBJECT-TYPE
   SYNTAX     Counter32 
   ACCESS     read-only
   STATUS     mandatory
   DESCRIPTION
     "This attribute counts the Bootstrap Message transmitted by the 
      bootstrap router (BSR) for this pim domain.
      This counter wraps to zero when the maximum value is exceeded."
::= { vrIpMcastPimSmDomainStatsEntry 1 }

vrIpMcastPimSmDomainRxBsrMsg OBJECT-TYPE
   SYNTAX     Counter32 
   ACCESS     read-only
   STATUS     mandatory
   DESCRIPTION
     "This attribute counts the Bootstrap Message received by this pim 
      domain.
      This counter wraps to zero when the maximum value is exceeded."
::= { vrIpMcastPimSmDomainStatsEntry 2 }

vrIpMcastPimSmDomainTxCRpAdvMsg OBJECT-TYPE
   SYNTAX     Counter32 
   ACCESS     read-only
   STATUS     mandatory
   DESCRIPTION
     "This attribute counts the Candidate-RP advertisement Message 
      transmitted by the configured CRp for this pim domain.
      This counter wraps to zero when the maximum value is exceeded."
::= { vrIpMcastPimSmDomainStatsEntry 3 }

vrIpMcastPimSmDomainRxCRpAdvMsg OBJECT-TYPE
   SYNTAX     Counter32 
   ACCESS     read-only
   STATUS     mandatory
   DESCRIPTION
     "This attribute counts the Candidate-RP advertisement Message 
      received by the bootstrap router (BSR) for this pim domain.
      This counter wraps to zero when the maximum value is exceeded."
::= { vrIpMcastPimSmDomainStatsEntry 4 }

vrIpMcastPimSmDomainTxHelloMsg OBJECT-TYPE
   SYNTAX     Counter32 
   ACCESS     read-only
   STATUS     mandatory
   DESCRIPTION
     "This attribute counts the Hello Message transmitted from PimIf 
      belonging to this pim domain.
      This counter wraps to zero when the maximum value is exceeded."
::= { vrIpMcastPimSmDomainStatsEntry 5 }

vrIpMcastPimSmDomainRxHelloMsg OBJECT-TYPE
   SYNTAX     Counter32 
   ACCESS     read-only
   STATUS     mandatory
   DESCRIPTION
     "This attribute counts the Hello Message received from pimif 
      belonging to this pim domain.
      This counter wraps to zero when the maximum value is exceeded."
::= { vrIpMcastPimSmDomainStatsEntry 6 }

vrIpMcastPimSmDomainTxRegisterMsg OBJECT-TYPE
   SYNTAX     Counter32 
   ACCESS     read-only
   STATUS     mandatory
   DESCRIPTION
     "This attribute counts the Register Message transmitted by the 
      Designated Router (DR) for this pim domain.
      This counter wraps to zero when the maximum value is exceeded."
::= { vrIpMcastPimSmDomainStatsEntry 7 }

vrIpMcastPimSmDomainRxRegisterMsg OBJECT-TYPE
   SYNTAX     Counter32 
   ACCESS     read-only
   STATUS     mandatory
   DESCRIPTION
     "This attribute counts the Register Message received by the RP for 
      this pim domain.
      This counter wraps to zero when the maximum value is exceeded."
::= { vrIpMcastPimSmDomainStatsEntry 8 }

vrIpMcastPimSmDomainTxRegisterStopMsg OBJECT-TYPE
   SYNTAX     Counter32 
   ACCESS     read-only
   STATUS     mandatory
   DESCRIPTION
     "This attribute counts the RegisterStop Message transmitted by the 
      RP for this pim domain.
      This counter wraps to zero when the maximum value is exceeded."
::= { vrIpMcastPimSmDomainStatsEntry 9 }

vrIpMcastPimSmDomainRxRegisterStopMsg OBJECT-TYPE
   SYNTAX     Counter32 
   ACCESS     read-only
   STATUS     mandatory
   DESCRIPTION
     "This attribute counts the RegisterStop Message received by the 
      Designated router (DR) for this pim domain.
      This counter wraps to zero when the maximum value is exceeded."
::= { vrIpMcastPimSmDomainStatsEntry 10 }

vrIpMcastPimSmDomainTxAssertMsg OBJECT-TYPE
   SYNTAX     Counter32 
   ACCESS     read-only
   STATUS     mandatory
   DESCRIPTION
     "This attribute counts the assert Message transmitted from this pim 
      domain.
      This counter wraps to zero when the maximum value is exceeded."
::= { vrIpMcastPimSmDomainStatsEntry 11 }

vrIpMcastPimSmDomainRxAssertMsg OBJECT-TYPE
   SYNTAX     Counter32 
   ACCESS     read-only
   STATUS     mandatory
   DESCRIPTION
     "This attribute counts the Assert Message received by this pim 
      domain.
      This counter wraps to zero when the maximum value is exceeded."
::= { vrIpMcastPimSmDomainStatsEntry 12 }

vrIpMcastPimSmDomainTxJPMsg OBJECT-TYPE
   SYNTAX     Counter32 
   ACCESS     read-only
   STATUS     mandatory
   DESCRIPTION
     "This attribute counts the JP Message transmitted for this pim 
      domain.
      This counter wraps to zero when the maximum value is exceeded."
::= { vrIpMcastPimSmDomainStatsEntry 13 }

vrIpMcastPimSmDomainRxJPMsg OBJECT-TYPE
   SYNTAX     Counter32 
   ACCESS     read-only
   STATUS     mandatory
   DESCRIPTION
     "This attribute counts the JP Message received by this pim domain.
      This counter wraps to zero when the maximum value is exceeded."
::= { vrIpMcastPimSmDomainStatsEntry 14 }

vrIpMcastPimSmDomainDiscardBsrMsg OBJECT-TYPE
   SYNTAX     Counter32 
   ACCESS     read-only
   STATUS     mandatory
   DESCRIPTION
     "This attribute counts the Bootstrap Message discarded by this pim 
      domain.
      This counter wraps to zero when the maximum value is exceeded."
::= { vrIpMcastPimSmDomainStatsEntry 17 }

vrIpMcastPimSmDomainDiscardCRpAdvMsg OBJECT-TYPE
   SYNTAX     Counter32 
   ACCESS     read-only
   STATUS     mandatory
   DESCRIPTION
     "This attribute counts the Candidate-RP advertisement Message 
      discarded by the bootstrap router (BSR) for this pim domain.
      This counter wraps to zero when the maximum value is exceeded."
::= { vrIpMcastPimSmDomainStatsEntry 18 }

vrIpMcastPimSmDomainDiscardHelloMsg OBJECT-TYPE
   SYNTAX     Counter32 
   ACCESS     read-only
   STATUS     mandatory
   DESCRIPTION
     "This attribute counts the Hello Message discarded if it is not 
      destined for us.
      This counter wraps to zero when the maximum value is exceeded."
::= { vrIpMcastPimSmDomainStatsEntry 19 }

vrIpMcastPimSmDomainDiscardRegisterMsg OBJECT-TYPE
   SYNTAX     Counter32 
   ACCESS     read-only
   STATUS     mandatory
   DESCRIPTION
     "This attribute counts the Register Message discarded if we are not 
      RP for this Pim domain.
      This counter wraps to zero when the maximum value is exceeded."
::= { vrIpMcastPimSmDomainStatsEntry 20 }

vrIpMcastPimSmDomainDiscardRegisterStopMsg OBJECT-TYPE
   SYNTAX     Counter32 
   ACCESS     read-only
   STATUS     mandatory
   DESCRIPTION
     "This attribute counts the RegisterStop Message discarded.
      This counter wraps to zero when the maximum value is exceeded."
::= { vrIpMcastPimSmDomainStatsEntry 21 }

vrIpMcastPimSmDomainDiscardAssertMsg OBJECT-TYPE
   SYNTAX     Counter32 
   ACCESS     read-only
   STATUS     mandatory
   DESCRIPTION
     "This attribute counts the Assert Message discarded if we are not 
      expecting it.
      This counter wraps to zero when the maximum value is exceeded."
::= { vrIpMcastPimSmDomainStatsEntry 22 }

vrIpMcastPimSmDomainDiscardJPMsg OBJECT-TYPE
   SYNTAX     Counter32 
   ACCESS     read-only
   STATUS     mandatory
   DESCRIPTION
     "This attribute counts the JP Message discarded by this pim domain 
      if it is not destined for us.
      This counter wraps to zero when the maximum value is exceeded."
::= { vrIpMcastPimSmDomainStatsEntry 23 }


-- This component specifies that this router should advertise itself as a 
-- Candidiate RP (CRP).

vrIpMcastPimSmDomainCRp OBJECT IDENTIFIER ::= { vrIpMcastPimSmDomain 2 }



vrIpMcastPimSmDomainCRpRowStatusTable OBJECT-TYPE
   SYNTAX     SEQUENCE OF VrIpMcastPimSmDomainCRpRowStatusEntry
   ACCESS     not-accessible
   STATUS     mandatory
   DESCRIPTION
     "This entry controls the addition and deletion of 
      vrIpMcastPimSmDomainCRp components."
::= { vrIpMcastPimSmDomainCRp 1 }

vrIpMcastPimSmDomainCRpRowStatusEntry OBJECT-TYPE
   SYNTAX     VrIpMcastPimSmDomainCRpRowStatusEntry
   ACCESS     not-accessible
   STATUS     mandatory
   DESCRIPTION
     "A single entry in the table represents a single 
      vrIpMcastPimSmDomainCRp component."
   INDEX {
      vrIndex,
      vrIpIndex,
      vrIpMcastIndex,
      vrIpMcastPimSmIndex,
      vrIpMcastPimSmDomainIndex,
      vrIpMcastPimSmDomainCRpIndex }
::= { vrIpMcastPimSmDomainCRpRowStatusTable 1 }

VrIpMcastPimSmDomainCRpRowStatusEntry ::= SEQUENCE {
   vrIpMcastPimSmDomainCRpRowStatus
      RowStatus,
   vrIpMcastPimSmDomainCRpComponentName
      DisplayString,
   vrIpMcastPimSmDomainCRpStorageType
      StorageType,
   vrIpMcastPimSmDomainCRpIndex
      NonReplicated }

vrIpMcastPimSmDomainCRpRowStatus OBJECT-TYPE
   SYNTAX     RowStatus 
   ACCESS     read-write
   STATUS     mandatory
   DESCRIPTION
     "This variable is used as the basis for SNMP naming of
      vrIpMcastPimSmDomainCRp components.
      These components can be added and deleted."
::= { vrIpMcastPimSmDomainCRpRowStatusEntry 1 }

vrIpMcastPimSmDomainCRpComponentName OBJECT-TYPE
   SYNTAX     DisplayString 
   ACCESS     read-only
   STATUS     mandatory
   DESCRIPTION
     "This variable provides the component's string name for
      use with the ASCII Console Interface"
::= { vrIpMcastPimSmDomainCRpRowStatusEntry 2 }

vrIpMcastPimSmDomainCRpStorageType OBJECT-TYPE
   SYNTAX     StorageType 
   ACCESS     read-only
   STATUS     mandatory
   DESCRIPTION
     "This variable represents the storage type value for the
      vrIpMcastPimSmDomainCRp tables."
::= { vrIpMcastPimSmDomainCRpRowStatusEntry 4 }

vrIpMcastPimSmDomainCRpIndex OBJECT-TYPE
   SYNTAX     NonReplicated 
   ACCESS     not-accessible
   STATUS     mandatory
   DESCRIPTION
     "This variable represents the index for the vrIpMcastPimSmDomainCRp tables."
::= { vrIpMcastPimSmDomainCRpRowStatusEntry 10 }

vrIpMcastPimSmDomainCRpProvTable OBJECT-TYPE
   SYNTAX     SEQUENCE OF VrIpMcastPimSmDomainCRpProvEntry
   ACCESS     not-accessible
   STATUS     mandatory
   DESCRIPTION
     "This group specifies all the attributes for component 
      CandidateRendezvousPoint."
::= { vrIpMcastPimSmDomainCRp 10 }

vrIpMcastPimSmDomainCRpProvEntry OBJECT-TYPE
   SYNTAX     VrIpMcastPimSmDomainCRpProvEntry
   ACCESS     not-accessible
   STATUS     mandatory
   DESCRIPTION
     "An entry in the vrIpMcastPimSmDomainCRpProvTable."
   INDEX {
      vrIndex,
      vrIpIndex,
      vrIpMcastIndex,
      vrIpMcastPimSmIndex,
      vrIpMcastPimSmDomainIndex,
      vrIpMcastPimSmDomainCRpIndex }
::= { vrIpMcastPimSmDomainCRpProvTable 1 }

VrIpMcastPimSmDomainCRpProvEntry ::= SEQUENCE {
   vrIpMcastPimSmDomainCRpCandidateRpAddress
      Link,
   vrIpMcastPimSmDomainCRpCandidateRpPreference
      INTEGER }

vrIpMcastPimSmDomainCRpCandidateRpAddress OBJECT-TYPE
   SYNTAX     Link 
   ACCESS     read-write
   STATUS     mandatory
   DESCRIPTION
     "This attribute specifies a link to a logical interface component which 
      specifies an IP address to be used as the local identifier in CRP 
      advertisement messages."
::= { vrIpMcastPimSmDomainCRpProvEntry 1 }

vrIpMcastPimSmDomainCRpCandidateRpPreference OBJECT-TYPE
   SYNTAX     INTEGER (0..255)
   ACCESS     read-write
   STATUS     mandatory
   DESCRIPTION
     "This attribute specifies the preference value to be used in CRP 
      advertisement messages. Lower values indicate higher preference."
   DEFVAL     { 0 }
::= { vrIpMcastPimSmDomainCRpProvEntry 2 }


-- This component specifies an IP multicast group address and mask 
-- which when combined identifies a group prefix for which the local 
-- router will advertise itself as a Candidate-RP.

vrIpMcastPimSmDomainCRpGrp OBJECT IDENTIFIER ::= { vrIpMcastPimSmDomainCRp 2 }



vrIpMcastPimSmDomainCRpGrpRowStatusTable OBJECT-TYPE
   SYNTAX     SEQUENCE OF VrIpMcastPimSmDomainCRpGrpRowStatusEntry
   ACCESS     not-accessible
   STATUS     mandatory
   DESCRIPTION
     "This entry controls the addition and deletion of 
      vrIpMcastPimSmDomainCRpGrp components."
::= { vrIpMcastPimSmDomainCRpGrp 1 }

vrIpMcastPimSmDomainCRpGrpRowStatusEntry OBJECT-TYPE
   SYNTAX     VrIpMcastPimSmDomainCRpGrpRowStatusEntry
   ACCESS     not-accessible
   STATUS     mandatory
   DESCRIPTION
     "A single entry in the table represents a single 
      vrIpMcastPimSmDomainCRpGrp component."
   INDEX {
      vrIndex,
      vrIpIndex,
      vrIpMcastIndex,
      vrIpMcastPimSmIndex,
      vrIpMcastPimSmDomainIndex,
      vrIpMcastPimSmDomainCRpIndex,
      vrIpMcastPimSmDomainCRpGrpGrpAddressIndex,
      vrIpMcastPimSmDomainCRpGrpGrpMaskIndex }
::= { vrIpMcastPimSmDomainCRpGrpRowStatusTable 1 }

VrIpMcastPimSmDomainCRpGrpRowStatusEntry ::= SEQUENCE {
   vrIpMcastPimSmDomainCRpGrpRowStatus
      RowStatus,
   vrIpMcastPimSmDomainCRpGrpComponentName
      DisplayString,
   vrIpMcastPimSmDomainCRpGrpStorageType
      StorageType,
   vrIpMcastPimSmDomainCRpGrpGrpAddressIndex
      IpAddress,
   vrIpMcastPimSmDomainCRpGrpGrpMaskIndex
      IpAddress }

vrIpMcastPimSmDomainCRpGrpRowStatus OBJECT-TYPE
   SYNTAX     RowStatus 
   ACCESS     read-write
   STATUS     mandatory
   DESCRIPTION
     "This variable is used as the basis for SNMP naming of
      vrIpMcastPimSmDomainCRpGrp components.
      These components can be added and deleted."
::= { vrIpMcastPimSmDomainCRpGrpRowStatusEntry 1 }

vrIpMcastPimSmDomainCRpGrpComponentName OBJECT-TYPE
   SYNTAX     DisplayString 
   ACCESS     read-only
   STATUS     mandatory
   DESCRIPTION
     "This variable provides the component's string name for
      use with the ASCII Console Interface"
::= { vrIpMcastPimSmDomainCRpGrpRowStatusEntry 2 }

vrIpMcastPimSmDomainCRpGrpStorageType OBJECT-TYPE
   SYNTAX     StorageType 
   ACCESS     read-only
   STATUS     mandatory
   DESCRIPTION
     "This variable represents the storage type value for the
      vrIpMcastPimSmDomainCRpGrp tables."
::= { vrIpMcastPimSmDomainCRpGrpRowStatusEntry 4 }

vrIpMcastPimSmDomainCRpGrpGrpAddressIndex OBJECT-TYPE
   SYNTAX     IpAddress 
   ACCESS     not-accessible
   STATUS     mandatory
   DESCRIPTION
     "This variable represents an index for the vrIpMcastPimSmDomainCRpGrp tables."
::= { vrIpMcastPimSmDomainCRpGrpRowStatusEntry 10 }

vrIpMcastPimSmDomainCRpGrpGrpMaskIndex OBJECT-TYPE
   SYNTAX     IpAddress 
   ACCESS     not-accessible
   STATUS     mandatory
   DESCRIPTION
     "This variable represents an index for the vrIpMcastPimSmDomainCRpGrp tables."
::= { vrIpMcastPimSmDomainCRpGrpRowStatusEntry 11 }

-- 
-- *** THIS SUBTREE CURRENTLY NOT IMPLEMENTED ***
-- 

-- This component indicates the IP address of a router which 
-- advertises itself as a Candidate-RP.

vrIpMcastPimSmDomainRpSet OBJECT IDENTIFIER ::= { vrIpMcastPimSmDomain 3 }



vrIpMcastPimSmDomainRpSetRowStatusTable OBJECT-TYPE
   SYNTAX     SEQUENCE OF VrIpMcastPimSmDomainRpSetRowStatusEntry
   ACCESS     not-accessible
   STATUS     mandatory
   DESCRIPTION
     "*** THIS TABLE CURRENTLY NOT IMPLEMENTED ***

      This entry controls the addition and deletion of 
      vrIpMcastPimSmDomainRpSet components."
::= { vrIpMcastPimSmDomainRpSet 1 }

vrIpMcastPimSmDomainRpSetRowStatusEntry OBJECT-TYPE
   SYNTAX     VrIpMcastPimSmDomainRpSetRowStatusEntry
   ACCESS     not-accessible
   STATUS     mandatory
   DESCRIPTION
     "A single entry in the table represents a single 
      vrIpMcastPimSmDomainRpSet component."
   INDEX {
      vrIndex,
      vrIpIndex,
      vrIpMcastIndex,
      vrIpMcastPimSmIndex,
      vrIpMcastPimSmDomainIndex,
      vrIpMcastPimSmDomainRpSetGrpAddressIndex,
      vrIpMcastPimSmDomainRpSetGrpMaskIndex,
      vrIpMcastPimSmDomainRpSetRpAddressIndex }
::= { vrIpMcastPimSmDomainRpSetRowStatusTable 1 }

VrIpMcastPimSmDomainRpSetRowStatusEntry ::= SEQUENCE {
   vrIpMcastPimSmDomainRpSetRowStatus
      RowStatus,
   vrIpMcastPimSmDomainRpSetComponentName
      DisplayString,
   vrIpMcastPimSmDomainRpSetStorageType
      StorageType,
   vrIpMcastPimSmDomainRpSetGrpAddressIndex
      IpAddress,
   vrIpMcastPimSmDomainRpSetGrpMaskIndex
      IpAddress,
   vrIpMcastPimSmDomainRpSetRpAddressIndex
      IpAddress }

vrIpMcastPimSmDomainRpSetRowStatus OBJECT-TYPE
   SYNTAX     RowStatus 
   ACCESS     read-only
   STATUS     mandatory
   DESCRIPTION
     "This variable is used as the basis for SNMP naming of
      vrIpMcastPimSmDomainRpSet components.
      These components cannot be added nor deleted."
::= { vrIpMcastPimSmDomainRpSetRowStatusEntry 1 }

vrIpMcastPimSmDomainRpSetComponentName OBJECT-TYPE
   SYNTAX     DisplayString 
   ACCESS     read-only
   STATUS     mandatory
   DESCRIPTION
     "This variable provides the component's string name for
      use with the ASCII Console Interface"
::= { vrIpMcastPimSmDomainRpSetRowStatusEntry 2 }

vrIpMcastPimSmDomainRpSetStorageType OBJECT-TYPE
   SYNTAX     StorageType 
   ACCESS     read-only
   STATUS     mandatory
   DESCRIPTION
     "This variable represents the storage type value for the
      vrIpMcastPimSmDomainRpSet tables."
::= { vrIpMcastPimSmDomainRpSetRowStatusEntry 4 }

vrIpMcastPimSmDomainRpSetGrpAddressIndex OBJECT-TYPE
   SYNTAX     IpAddress 
   ACCESS     not-accessible
   STATUS     mandatory
   DESCRIPTION
     "This variable represents an index for the vrIpMcastPimSmDomainRpSet tables."
::= { vrIpMcastPimSmDomainRpSetRowStatusEntry 10 }

vrIpMcastPimSmDomainRpSetGrpMaskIndex OBJECT-TYPE
   SYNTAX     IpAddress 
   ACCESS     not-accessible
   STATUS     mandatory
   DESCRIPTION
     "This variable represents an index for the vrIpMcastPimSmDomainRpSet tables."
::= { vrIpMcastPimSmDomainRpSetRowStatusEntry 11 }

vrIpMcastPimSmDomainRpSetRpAddressIndex OBJECT-TYPE
   SYNTAX     IpAddress 
   ACCESS     not-accessible
   STATUS     mandatory
   DESCRIPTION
     "This variable represents an index for the vrIpMcastPimSmDomainRpSet tables."
::= { vrIpMcastPimSmDomainRpSetRowStatusEntry 12 }

vrIpMcastPimSmDomainRpSetOperTable OBJECT-TYPE
   SYNTAX     SEQUENCE OF VrIpMcastPimSmDomainRpSetOperEntry
   ACCESS     not-accessible
   STATUS     mandatory
   DESCRIPTION
     "*** THIS TABLE CURRENTLY NOT IMPLEMENTED ***

      This group contains the operational attributes for a candidate RP."
::= { vrIpMcastPimSmDomainRpSet 11 }

vrIpMcastPimSmDomainRpSetOperEntry OBJECT-TYPE
   SYNTAX     VrIpMcastPimSmDomainRpSetOperEntry
   ACCESS     not-accessible
   STATUS     mandatory
   DESCRIPTION
     "An entry in the vrIpMcastPimSmDomainRpSetOperTable."
   INDEX {
      vrIndex,
      vrIpIndex,
      vrIpMcastIndex,
      vrIpMcastPimSmIndex,
      vrIpMcastPimSmDomainIndex,
      vrIpMcastPimSmDomainRpSetGrpAddressIndex,
      vrIpMcastPimSmDomainRpSetGrpMaskIndex,
      vrIpMcastPimSmDomainRpSetRpAddressIndex }
::= { vrIpMcastPimSmDomainRpSetOperTable 1 }

VrIpMcastPimSmDomainRpSetOperEntry ::= SEQUENCE {
   vrIpMcastPimSmDomainRpSetRpSetHoldTime
      Unsigned32,
   vrIpMcastPimSmDomainRpSetRpSetExpiryTime
      TimeTicks,
   vrIpMcastPimSmDomainRpSetRpSetPriority
      INTEGER }

vrIpMcastPimSmDomainRpSetRpSetHoldTime OBJECT-TYPE
   SYNTAX     Unsigned32 (0..255)
   ACCESS     read-only
   STATUS     mandatory
   DESCRIPTION
     "This attribute indicates the holdtime of a Candidate-RP. If the local 
      router is not the BSR, this value is 0."
::= { vrIpMcastPimSmDomainRpSetOperEntry 1 }

vrIpMcastPimSmDomainRpSetRpSetExpiryTime OBJECT-TYPE
   SYNTAX     TimeTicks 
   ACCESS     read-only
   STATUS     mandatory
   DESCRIPTION
     "This attribute indicates the minimum time remaining before the 
      Candidate-RP will be declared down. If the local router is not the 
      BSR, this value is 0."
::= { vrIpMcastPimSmDomainRpSetOperEntry 2 }

vrIpMcastPimSmDomainRpSetRpSetPriority OBJECT-TYPE
   SYNTAX     INTEGER (0..255)
   ACCESS     read-only
   STATUS     mandatory
   DESCRIPTION
     "This attribute indicates the priority advertised by BSR for this CRP. 
      If the local router is the BSR, this value specifies the priority 
      advertised by CRP."
::= { vrIpMcastPimSmDomainRpSetOperEntry 3 }


-- This component specifies that this router should advertise iteself as 
-- a candidate bootstrap router (CBSR).

vrIpMcastPimSmDomainCBsr OBJECT IDENTIFIER ::= { vrIpMcastPimSmDomain 4 }



vrIpMcastPimSmDomainCBsrRowStatusTable OBJECT-TYPE
   SYNTAX     SEQUENCE OF VrIpMcastPimSmDomainCBsrRowStatusEntry
   ACCESS     not-accessible
   STATUS     mandatory
   DESCRIPTION
     "This entry controls the addition and deletion of 
      vrIpMcastPimSmDomainCBsr components."
::= { vrIpMcastPimSmDomainCBsr 1 }

vrIpMcastPimSmDomainCBsrRowStatusEntry OBJECT-TYPE
   SYNTAX     VrIpMcastPimSmDomainCBsrRowStatusEntry
   ACCESS     not-accessible
   STATUS     mandatory
   DESCRIPTION
     "A single entry in the table represents a single 
      vrIpMcastPimSmDomainCBsr component."
   INDEX {
      vrIndex,
      vrIpIndex,
      vrIpMcastIndex,
      vrIpMcastPimSmIndex,
      vrIpMcastPimSmDomainIndex,
      vrIpMcastPimSmDomainCBsrIndex }
::= { vrIpMcastPimSmDomainCBsrRowStatusTable 1 }

VrIpMcastPimSmDomainCBsrRowStatusEntry ::= SEQUENCE {
   vrIpMcastPimSmDomainCBsrRowStatus
      RowStatus,
   vrIpMcastPimSmDomainCBsrComponentName
      DisplayString,
   vrIpMcastPimSmDomainCBsrStorageType
      StorageType,
   vrIpMcastPimSmDomainCBsrIndex
      NonReplicated }

vrIpMcastPimSmDomainCBsrRowStatus OBJECT-TYPE
   SYNTAX     RowStatus 
   ACCESS     read-write
   STATUS     mandatory
   DESCRIPTION
     "This variable is used as the basis for SNMP naming of
      vrIpMcastPimSmDomainCBsr components.
      These components can be added and deleted."
::= { vrIpMcastPimSmDomainCBsrRowStatusEntry 1 }

vrIpMcastPimSmDomainCBsrComponentName OBJECT-TYPE
   SYNTAX     DisplayString 
   ACCESS     read-only
   STATUS     mandatory
   DESCRIPTION
     "This variable provides the component's string name for
      use with the ASCII Console Interface"
::= { vrIpMcastPimSmDomainCBsrRowStatusEntry 2 }

vrIpMcastPimSmDomainCBsrStorageType OBJECT-TYPE
   SYNTAX     StorageType 
   ACCESS     read-only
   STATUS     mandatory
   DESCRIPTION
     "This variable represents the storage type value for the
      vrIpMcastPimSmDomainCBsr tables."
::= { vrIpMcastPimSmDomainCBsrRowStatusEntry 4 }

vrIpMcastPimSmDomainCBsrIndex OBJECT-TYPE
   SYNTAX     NonReplicated 
   ACCESS     not-accessible
   STATUS     mandatory
   DESCRIPTION
     "This variable represents the index for the vrIpMcastPimSmDomainCBsr tables."
::= { vrIpMcastPimSmDomainCBsrRowStatusEntry 10 }

vrIpMcastPimSmDomainCBsrProvTable OBJECT-TYPE
   SYNTAX     SEQUENCE OF VrIpMcastPimSmDomainCBsrProvEntry
   ACCESS     not-accessible
   STATUS     mandatory
   DESCRIPTION
     "This group contains all the provisionable attributes for component 
      CandidateBootstrapRouter."
::= { vrIpMcastPimSmDomainCBsr 10 }

vrIpMcastPimSmDomainCBsrProvEntry OBJECT-TYPE
   SYNTAX     VrIpMcastPimSmDomainCBsrProvEntry
   ACCESS     not-accessible
   STATUS     mandatory
   DESCRIPTION
     "An entry in the vrIpMcastPimSmDomainCBsrProvTable."
   INDEX {
      vrIndex,
      vrIpIndex,
      vrIpMcastIndex,
      vrIpMcastPimSmIndex,
      vrIpMcastPimSmDomainIndex,
      vrIpMcastPimSmDomainCBsrIndex }
::= { vrIpMcastPimSmDomainCBsrProvTable 1 }

VrIpMcastPimSmDomainCBsrProvEntry ::= SEQUENCE {
   vrIpMcastPimSmDomainCBsrCandidateBsrAddress
      Link,
   vrIpMcastPimSmDomainCBsrCandidateBsrPreference
      INTEGER }

vrIpMcastPimSmDomainCBsrCandidateBsrAddress OBJECT-TYPE
   SYNTAX     Link 
   ACCESS     read-write
   STATUS     mandatory
   DESCRIPTION
     "This attribute specifies a link to a logical interface component which 
      specifies an IP address to use as the local system identifier in 
      bootstrap messages."
::= { vrIpMcastPimSmDomainCBsrProvEntry 1 }

vrIpMcastPimSmDomainCBsrCandidateBsrPreference OBJECT-TYPE
   SYNTAX     INTEGER (0..255)
   ACCESS     read-write
   STATUS     mandatory
   DESCRIPTION
     "This attribute specifies the preference value used in bootstrap 
      messages. Higher values indicate higher priority."
   DEFVAL     { 0 }
::= { vrIpMcastPimSmDomainCBsrProvEntry 2 }

-- 
-- *** THIS SUBTREE CURRENTLY NOT IMPLEMENTED ***
-- 

-- Vr/<string. Ip Mcast NeighborEntry/<Ip Address>, <Decimal>
-- This component represent a neighbouring PIM-enabled router.

vrIpMcastPimNbr OBJECT IDENTIFIER ::= { vrIpMcast 10 }



vrIpMcastPimNbrRowStatusTable OBJECT-TYPE
   SYNTAX     SEQUENCE OF VrIpMcastPimNbrRowStatusEntry
   ACCESS     not-accessible
   STATUS     mandatory
   DESCRIPTION
     "*** THIS TABLE CURRENTLY NOT IMPLEMENTED ***

      This entry controls the addition and deletion of 
      vrIpMcastPimNbr components."
::= { vrIpMcastPimNbr 1 }

vrIpMcastPimNbrRowStatusEntry OBJECT-TYPE
   SYNTAX     VrIpMcastPimNbrRowStatusEntry
   ACCESS     not-accessible
   STATUS     mandatory
   DESCRIPTION
     "A single entry in the table represents a single 
      vrIpMcastPimNbr component."
   INDEX {
      vrIndex,
      vrIpIndex,
      vrIpMcastIndex,
      vrIpMcastPimNbrNbrAddressIndex,
      vrIpMcastPimNbrDomainIndex }
::= { vrIpMcastPimNbrRowStatusTable 1 }

VrIpMcastPimNbrRowStatusEntry ::= SEQUENCE {
   vrIpMcastPimNbrRowStatus
      RowStatus,
   vrIpMcastPimNbrComponentName
      DisplayString,
   vrIpMcastPimNbrStorageType
      StorageType,
   vrIpMcastPimNbrNbrAddressIndex
      IpAddress,
   vrIpMcastPimNbrDomainIndex
      Integer32 }

vrIpMcastPimNbrRowStatus OBJECT-TYPE
   SYNTAX     RowStatus 
   ACCESS     read-only
   STATUS     mandatory
   DESCRIPTION
     "This variable is used as the basis for SNMP naming of
      vrIpMcastPimNbr components.
      These components cannot be added nor deleted."
::= { vrIpMcastPimNbrRowStatusEntry 1 }

vrIpMcastPimNbrComponentName OBJECT-TYPE
   SYNTAX     DisplayString 
   ACCESS     read-only
   STATUS     mandatory
   DESCRIPTION
     "This variable provides the component's string name for
      use with the ASCII Console Interface"
::= { vrIpMcastPimNbrRowStatusEntry 2 }

vrIpMcastPimNbrStorageType OBJECT-TYPE
   SYNTAX     StorageType 
   ACCESS     read-only
   STATUS     mandatory
   DESCRIPTION
     "This variable represents the storage type value for the
      vrIpMcastPimNbr tables."
::= { vrIpMcastPimNbrRowStatusEntry 4 }

vrIpMcastPimNbrNbrAddressIndex OBJECT-TYPE
   SYNTAX     IpAddress 
   ACCESS     not-accessible
   STATUS     mandatory
   DESCRIPTION
     "This variable represents an index for the vrIpMcastPimNbr tables."
::= { vrIpMcastPimNbrRowStatusEntry 10 }

vrIpMcastPimNbrDomainIndex OBJECT-TYPE
   SYNTAX     Integer32 (0..3)
   ACCESS     not-accessible
   STATUS     mandatory
   DESCRIPTION
     "This variable represents an index for the vrIpMcastPimNbr tables."
::= { vrIpMcastPimNbrRowStatusEntry 11 }

vrIpMcastPimNbrOperTable OBJECT-TYPE
   SYNTAX     SEQUENCE OF VrIpMcastPimNbrOperEntry
   ACCESS     not-accessible
   STATUS     mandatory
   DESCRIPTION
     "*** THIS TABLE CURRENTLY NOT IMPLEMENTED ***

      This group contains the operational attributes of the 
      PimNeighborEntry componnent."
::= { vrIpMcastPimNbr 10 }

vrIpMcastPimNbrOperEntry OBJECT-TYPE
   SYNTAX     VrIpMcastPimNbrOperEntry
   ACCESS     not-accessible
   STATUS     mandatory
   DESCRIPTION
     "An entry in the vrIpMcastPimNbrOperTable."
   INDEX {
      vrIndex,
      vrIpIndex,
      vrIpMcastIndex,
      vrIpMcastPimNbrNbrAddressIndex,
      vrIpMcastPimNbrDomainIndex }
::= { vrIpMcastPimNbrOperTable 1 }

VrIpMcastPimNbrOperEntry ::= SEQUENCE {
   vrIpMcastPimNbrIfIndex
      InterfaceIndex,
   vrIpMcastPimNbrUpTime
      TimeTicks,
   vrIpMcastPimNbrExpiryTimer
      TimeTicks }

vrIpMcastPimNbrIfIndex OBJECT-TYPE
   SYNTAX     InterfaceIndex (1..65535)
   ACCESS     read-only
   STATUS     mandatory
   DESCRIPTION
     "This attribute indicates the value of ifIndex for the interface used to 
      reach this PIM neighbor."
::= { vrIpMcastPimNbrOperEntry 1 }

vrIpMcastPimNbrUpTime OBJECT-TYPE
   SYNTAX     TimeTicks 
   ACCESS     read-only
   STATUS     mandatory
   DESCRIPTION
     "This attribute indicates the time since this PIM neighbor became a 
      neighbor of this local router."
::= { vrIpMcastPimNbrOperEntry 2 }

vrIpMcastPimNbrExpiryTimer OBJECT-TYPE
   SYNTAX     TimeTicks 
   ACCESS     read-only
   STATUS     mandatory
   DESCRIPTION
     "This attribute indicates the minimum time remaining before this 
      PIM neighbor will be aged out."
::= { vrIpMcastPimNbrOperEntry 3 }




-- 
-- Version and Compliance statements
-- 



-- Object-Group Statement:
-- A list of all current accessible leaf objects.

-- OBJECTS { vrIpRipGenerateDiscardRoute,
--           vrIpStaticRowStatus,
--           vrIpRipImportNetRowStatus,
--           vrIpBootpAdminState,
--           vrIpOspfExportRipNeighbor,
--           vrIpFwdStorageType,
--           vrIpRipImportStorageType,
--           vrIpOutRequests,
--           vrIpCacheAdminState,
--           vrIpStaticRouteNhMetric,
--           vrIpStaticDiscardComponentName,
--           vrIpArpHostEncap,
--           vrIpBootpPpERowStatus,
--           vrPpIpPortLogicalIfLinkToPimSmCandidateBsr,
--           vrIpCacheCacheTableMaxEntries,
--           vrIpMcastPimSmDomainTxHelloMsg,
--           vrIpNsApplyStorageType,
--           vrPpIpPortLogicalIfIgmpIfVersion,
--           vrIpEgpInErrorMsgs,
--           vrIpEgpNbrDefaultRouteMetric,
--           vrPpIpPortLogicalIfOspfIfTOSTosMetric,
--           vrPpIpPortLogicalIfOspfIfRtrPriority,
--           vrIpEgpNbrOutErrorMsgs,
--           vrPpIpPortLogicalIfLinkToPimSmCandidateRp,
--           vrPpIpPortLogicalIfOspfIfNbrOptions,
--           vrIpOspfExtLsdbAdvertisement,
--           vrIpMcastSnmpAdminStatus,
--           vrIpForwarding,
--           vrIpNsApplyIpAddress2,
--           vrPpIpPortOperArpStatus,
--           vrIpMcastPgLinkToPolicyUserValue,
--           vrPpIpPortBootpPAddrValue,
--           vrIpMcastPimSmDomainRxAssertMsg,
--           vrPpIpPortLogicalIfRipIfIfTriggeredUpdates,
--           vrIpBootpPpEInReplies,
--           vrIpArpDynHostNcPhysAddress,
--           vrIpMcastIgmpUsageState,
--           vrIpRipExportNetIpMask,
--           vrIpCacheComponentName,
--           vrIpRipSnmpOperStatus,
--           vrIpTunnelStorageType,
--           vrIpBootpStorageType,
--           vrPpIpPortArpNoLearn,
--           vrPpIpPortDirectedBroadcast,
--           vrIpMcastIgmpGcStorageType,
--           vrIpOspfTosSupport,
--           vrIpIfPPName,
--           vrIpOspfRxNewLsas,
--           vrIpCosPolicyAssignment,
--           vrPpIpPortCosPolicyAssignment,
--           vrIpArpHostStorageType,
--           vrIpUdpInErrors,
--           vrIpFragCreates,
--           vrIpOspfComponentName,
--           vrPpIpPortRelayAddressCount,
--           vrIpMcastCacheStatsStorageType,
--           vrIpOspfExportRipInterface,
--           vrIpMcastPimSmDomainCRpCandidateRpAddress,
--           vrIpNsApplyDirection,
--           vrIpFwdProtocolPortName,
--           vrIpOspfStubRowStatus,
--           vrIpMcastFwdInProtocolPortName,
--           vrIpOspfStubStorageType,
--           vrIpOspfExternLsaCount,
--           vrIpIcmpInAddrMaskReps,
--           vrIpUdpListenEntryRowStatus,
--           vrIpMcastPimSmDomainRxCRpAdvMsg,
--           vrIpMcastPimSmDomainCRpGrpComponentName,
--           vrIpTcpPassiveOpens,
--           vrPpIpPortLogicalIfOspfIfRetransInterval,
--           vrIpArpHostComponentName,
--           vrPpIpPortLogicalIfLinkToMulStaticGpRowStatus,
--           vrPpIpPortProxyArpStatus,
--           vrIpEgpStorageType,
--           vrIpMcastPimSmDomainRpSetComponentName,
--           vrIpRipRipTimeout,
--           vrPpIpPortLogicalIfRipIfIfBadPacketRcv,
--           vrIpRipRowStatus,
--           vrIpArpDynHostPermanentVirtualCircuitNumber,
--           vrIpRipSnmpAdminStatus,
--           vrIpIcmpOutMsgs,
--           vrPpIpPortLogicalIfRipIfStorageType,
--           vrIpOspfStubAdvertiseDefault,
--           vrPpIpPortLogicalIfOspfIfDesignatedRouter,
--           vrPpIpPortLogicalIfOspfIfTOSStorageType,
--           vrIpMcastStaticRouteStorageType,
--           vrIpEgpNbrInErrors,
--           vrIpMcastCacheStatsCacheTableMaxEntries,
--           vrIpBootpOperationalState,
--           vrPpIpPortLogicalIfStorageType,
--           vrIpMcastDomainProtocolActive,
--           vrIpOspfVirtIfRetransInterval,
--           vrIpBootpPpEOutReplies,
--           vrIpMcastFwdReversePathForwardingNeighbor,
--           vrIpRipExportProtocol,
--           vrIpCacheRowStatus,
--           vrIpOspfExportComponentName,
--           vrPpIpPortNsOutgoingFilter,
--           vrPpIpPortLogicalIfOspfIfNbrRtrId,
--           vrPpIpPortLogicalIfNetMask,
--           vrIpRipImportNetIpAddress,
--           vrPpIpPortLanModel,
--           vrIpNsApplyIpMask2,
--           vrIpIcmpInRtrAdvs,
--           vrIpUdpRowStatus,
--           vrIpRipOperationalState,
--           vrIpInAddrErrors,
--           vrIpIfNcHardwareAddress,
--           vrIpMcastFwdOifIfIndex,
--           vrIpFwdMetric,
--           vrPpIpPortLogicalIfBroadcastAddress,
--           vrIpInReceives,
--           vrIpEgpExportOspfTag,
--           vrPpIpPortLogicalIfRipIfNetworkRouteStatus,
--           vrIpOspfNbrPriority,
--           vrIpEgpExportNetRowStatus,
--           vrIpIcmpInTimeExcds,
--           vrIpMcastStaticRowStatus,
--           vrIpOspfGenerateDefaultRouteMetric,
--           vrIpEgpExportStorageType,
--           vrPpIpPortLogicalIfOspfIfMetric,
--           vrIpRipExportRowStatus,
--           vrIpTcpOutRsts,
--           vrPpIpPortLogicalIfIgmpIfQuerierExpiryTime,
--           vrIpMcastPimSmDomainTxRegisterStopMsg,
--           vrIpOspfExtLsdbComponentName,
--           vrPpIpPortLogicalIfIgmpIfRowStatus,
--           vrPpIpPortLogicalIfOspfIfNbrComponentName,
--           vrIpOspfVirtIfRtrDeadInterval,
--           vrIpOspfVirtNbrStorageType,
--           vrIpIcmpInRedirects,
--           vrIpOspfStubComponentName,
--           vrIpRdbStorageType,
--           vrIpMcastPimNbrStorageType,
--           vrIpTunnelSepSourceAddress,
--           vrIpArpDynHostMaxTxUnit,
--           vrIpTcpRowStatus,
--           vrIpOspfAreaStorageType,
--           vrPpIpPortBootpPComponentName,
--           vrIpRipImportNetIpMask,
--           vrIpStorageType,
--           vrPpIpPortStorageType,
--           vrIpMcastDomainStorageType,
--           vrIpMcastPimSmDomainComponentName,
--           vrIpEgpNbrRowStatus,
--           vrPpIpPortMulticastStatus,
--           vrIpMcastStaticOperationalState,
--           vrIpRipExportRipInterface,
--           vrIpOspfUsageState,
--           vrIpCacheOperationalState,
--           vrIpStaticRouteNhComponentName,
--           vrPpIpPortNsStorageType,
--           vrIpTunnelSepStorageType,
--           vrPpIpPortLogicalIfRipIfNbrRowStatus,
--           vrIpOspfNbrStorageType,
--           vrIpMcastPimSmSnmpOperStatus,
--           vrIpCacheTotalLookups,
--           vrIpAdminState,
--           vrPpIpPortAdminState,
--           vrIpMcastPimSmDomainCBsrCandidateBsrPreference,
--           vrPpIpPortLogicalIfOspfIfNbrState,
--           vrIpIfComponentName,
--           vrIpOspfHostRowStatus,
--           vrPpIpPortBootpPSnmpOperStatus,
--           vrIpNsComponentName,
--           vrIpFwdNextHopAs,
--           vrIpMcastPgGrpStorageType,
--           vrPpIpPortRelayBcCount,
--           vrIpMcastPimSmDomainTxAssertMsg,
--           vrIpTunnelSepLinkToProtocolPort,
--           vrIpEgpOutErrorMsgs,
--           vrIpEgpDefaultPollInterval,
--           vrIpMcastAdminState,
--           vrIpIcmpOutAddrMaskReps,
--           vrIpOspfMigrateRip,
--           vrIpTcpAttemptFails,
--           vrIpOspfExportTag,
--           vrPpIpPortLogicalIfPimSmIfStorageType,
--           vrIpReasmReqds,
--           vrIpRdbAge,
--           vrIpMcastPimSmDomainCRpComponentName,
--           vrIpOspfLsdbRowStatus,
--           vrIpUdpNoPorts,
--           vrIpNsApplyRowStatus,
--           vrIpFwdIfIndex,
--           vrIpOspfExtLsdbLimit,
--           vrIpOspfHostComponentName,
--           vrIpIcmpOutTimeExcds,
--           vrIpBootpPpEInRequests,
--           vrIpArpAutoRefresh,
--           vrPpIpPortLogicalIfRipIfRowStatus,
--           vrIpIcmpOutErrors,
--           vrIpMcastPimSmRowStatus,
--           vrIpArpRowStatus,
--           vrIpMcastPimSmSnmpAdminStatus,
--           vrIpBootpRowStatus,
--           vrIpFwdProtocol,
--           vrIpCacheLookupMisses,
--           vrIpReasmFails,
--           vrIpTunnelUsageState,
--           vrIpMcastStorageType,
--           vrPpIpPortSourceRouteEndStationSupport,
--           vrIpOspfVirtNbrComponentName,
--           vrPpIpPortLogicalIfOspfIfHelloInterval,
--           vrIpTcpInErrs,
--           vrIpRipExportNetComponentName,
--           vrIpInHdrErrors,
--           vrIpNsApplyIpMask1,
--           vrIpMcastPimSmDomainRpSetRpSetExpiryTime,
--           vrIpEgpComponentName,
--           vrIpTunnelSepComponentName,
--           vrIpTcpInSegs,
--           vrIpEgpExportRipNeighbor,
--           vrIpEgpImportNetRowStatus,
--           vrIpEgpExportNetIpAddress,
--           vrIpEgpImportStorageType,
--           vrIpEgpDefaultHelloInterval,
--           vrIpFwdRowStatus,
--           vrIpRipImportRowStatus,
--           vrIpOspfAggregateEffect,
--           vrIpMcastCacheStatsUsageState,
--           vrIpIcmpInEchos,
--           vrPpIpPortLogicalIfRipIfIfConfReceive,
--           vrPpIpPortLogicalIfLinkDestinationAddress,
--           vrIpRipExportEgpAsId,
--           vrPpIpPortBootpPUsageState,
--           vrIpEgpNbrStateUps,
--           vrIpMcastIgmpComponentName,
--           vrIpIcmpOutTimestamps,
--           vrIpTcpActiveOpens,
--           vrIpFragOks,
--           vrIpOspfExtLsdbChecksum,
--           vrIpOspfVirtNbrExchangeStatus,
--           vrIpArpHostPhysAddress,
--           vrIpEgpInErrors,
--           vrIpMcastFwdRowStatus,
--           vrIpStaticRoutePreferredOver,
--           vrIpInDiscards,
--           vrPpIpPortOperCosPolicyAssignment,
--           vrIpStaticRouteStorageType,
--           vrIpEgpNbrOutErrors,
--           vrIpMcastFwdOifProtocol,
--           vrIpMcastDomainRowStatus,
--           vrIpOspfExportExtLsaMetricType,
--           vrIpRelayBCComponentName,
--           vrIpRelayBCPortRelayBcUdpCount,
--           vrIpForwDatagrams,
--           vrIpOspfVirtNbrEvents,
--           vrIpStaticDiscardStorageType,
--           vrIpInDelivers,
--           vrIpEgpNbrMode,
--           vrIpOspfStubMetric,
--           vrIpEgpInMsgs,
--           vrIpMcastFwdFlags,
--           vrIpOspfNbrExchangeStatus,
--           vrPpIpPortMcastPolicyAssignment,
--           vrPpIpPortLogicalIfRipIfIfBadRouteRcv,
--           vrIpEgpNbrOutMsgs,
--           vrIpMcastPimSmDomainJoinPruneInterval,
--           vrIpMcastPimSmDomainDiscardAssertMsg,
--           vrIpMcastPimSmDomainRpSetRpSetHoldTime,
--           vrIpMcastCacheStatsComponentName,
--           vrIpArpHostRowStatus,
--           vrIpOspfVirtIfAuthKey,
--           vrIpRipExportBgpAsId,
--           vrIpCacheUsageState,
--           vrIpMcastIgmpGcVersion1HostTimer,
--           vrPpIpPortLogicalIfOspfIfComponentName,
--           vrIpOspfNbrEvents,
--           vrIpNsLastFilter,
--           vrPpIpPortBootpPInReplyErrors,
--           vrPpIpPortLogicalIfRipIfAcceptDefault,
--           vrPpIpPortRelayAddress,
--           vrIpOspfVirtNbrLsRetransQlen,
--           vrIpMcastCacheStatsAdminState,
--           vrIpFwdComponentName,
--           vrIpMcastPimSmDomainRxJPMsg,
--           vrIpIcmpOutRedirects,
--           vrIpCacheEntriesFree,
--           vrIpIcmpInAddrMasks,
--           vrIpMcastIgmpGcExpiryTime,
--           vrIpArpDynHostEncapsulationType,
--           vrIpMcastPimSmDomainDiscardCRpAdvMsg,
--           vrIpRelayBCRelayNdCount,
--           vrIpEgpRowStatus,
--           vrIpEgpSnmpAdminStatus,
--           vrPpIpPortEncap,
--           vrIpOspfAggregateStorageType,
--           vrIpOspfVirtIfComponentName,
--           vrIpOspfAreaAuthType,
--           vrIpOspfStorageType,
--           vrPpIpPortLogicalIfRipIfSnmpAdminStatus,
--           vrIpMcastPimSmDomainTxRegisterMsg,
--           vrIpOspfAreaAsBdrRtrCount,
--           vrIpOspfVirtNbrNbrIpAddress,
--           vrPpIpPortLogicalIfOspfIfTOSRowStatus,
--           vrIpNsApplyFilter,
--           vrPpIpPortLogicalIfOspfIfPollInterval,
--           vrPpIpPortLogicalIfOspfIfState,
--           vrIpStaticComponentName,
--           vrIpRipImportNetComponentName,
--           vrIpArpDynHostComponentName,
--           vrPpIpPortLogicalIfRowStatus,
--           vrIpEgpExportProtocol,
--           vrIpEgpNbrAsId,
--           vrIpMcastPimSmDomainCRpGrpStorageType,
--           vrIpMcastPimSmDomainBsrExpiryTimer,
--           vrIpUdpInDatagrams,
--           vrIpRipExportExportMetric,
--           vrIpSnmpOperStatus,
--           vrIpEgpImportNetIpAddress,
--           vrIpOspfAdminState,
--           vrIpEgpOperationalState,
--           vrIpMcastFwdOifRowStatus,
--           vrIpRipExportAdvertiseStatus,
--           vrIpMcastPimSmDomainCBsrCandidateBsrAddress,
--           vrPpIpPortBootpPRelayForwardStatus,
--           vrIpMcastStaticComponentName,
--           vrIpMcastPimSmDomainRowStatus,
--           vrIpOspfVirtIfState,
--           vrIpMcastPimSmDomainTxBsrMsg,
--           vrIpTcpTcpEntryRowStatus,
--           vrIpTcpTcpEntryStorageType,
--           vrPpIpPortOperMulticastStatus,
--           vrPpIpPortLogicalIfOspfIfNbrPriority,
--           vrIpMcastPimSmDomainCRpCandidateRpPreference,
--           vrIpEgpExportAdvertiseStatus,
--           vrPpIpPortUsageState,
--           vrIpRelayBCRelayNdStatus,
--           vrIpOspfNbrPermanence,
--           vrPpIpPortAllowMcastMacDest,
--           vrIpOspfExportStorageType,
--           vrPpIpPortBootpPInRequestErrors,
--           vrIpOspfVirtNbrRowStatus,
--           vrIpOspfAreaBdrRtrStatus,
--           vrIpRdbRowStatus,
--           vrIpMcastStaticAdminState,
--           vrIpRelayBCPortComponentName,
--           vrIpRelayBCRelayStatus,
--           vrIpOspfAreaRowStatus,
--           vrIpBootpHopDiscardThreshold,
--           vrIpRowStatus,
--           vrPpIpPortRowStatus,
--           vrIpIcmpOutEchos,
--           vrIpSnmpAdminStatus,
--           vrPpIpPortSnmpAdminStatus,
--           vrIpEgpExportRipInterface,
--           vrIpTunnelAdminState,
--           vrIpOspfAreaAreaSummary,
--           vrPpIpPortArpStatus,
--           vrPpIpPortNsRowStatus,
--           vrIpTunnelOperationalState,
--           vrIpBootpPpEOutRequests,
--           vrIpTcpOutSegs,
--           vrIpOspfNbrRowStatus,
--           vrIpOspfAggregateComponentName,
--           vrIpOspfExtLsdbStorageType,
--           vrIpArpComponentName,
--           vrPpIpPortLogicalIfOspfIfNbrStorageType,
--           vrIpMcastRowStatus,
--           vrIpUdpListenEntryComponentName,
--           vrIpOspfMulticastForward,
--           vrIpOspfHostStorageType,
--           vrIpTcpRetransSegs,
--           vrIpEgpNbrHelloInterval,
--           vrPpIpPortSendRedirect,
--           vrIpMcastPimSmAdminState,
--           vrIpMcastPimSmOperationalState,
--           vrPpIpPortOperEncap,
--           vrIpOperationalState,
--           vrPpIpPortOperationalState,
--           vrIpBootpPpEInRequestErrors,
--           vrIpIcmpOutRtrAdvs,
--           vrIpOspfLsdbAdvertisement,
--           vrIpMcastComponentName,
--           vrPpIpPortLogicalIfIgmpIfGroups,
--           vrIpEgpOutErrors,
--           vrPpIpPortBootpPStorageType,
--           vrIpMcastPimSmDomainRxBsrMsg,
--           vrPpIpPortLogicalIfPimSmIfRowStatus,
--           vrIpOutDiscards,
--           vrIpTcpRToAlgorithm,
--           vrIpArpStorageType,
--           vrIpTunnelComponentName,
--           vrIpRipImportImportMetric,
--           vrPpIpPortBootpPAdminState,
--           vrIpMcastPimSmUsageState,
--           vrIpMcastOperationalState,
--           vrIpOspfHostAreaId,
--           vrIpIfStorageType,
--           vrIpMcastPgLinkToPolicyUserRowStatus,
--           vrPpIpPortBootpPAddrRowStatus,
--           vrIpMcastFwdStorageType,
--           vrIpRipExportComponentName,
--           vrIpIcmpComponentName,
--           vrIpStaticRouteNhStorageType,
--           vrIpEgpOutMsgs,
--           vrIpArpHostMaxTxUnit,
--           vrIpIcmpInRtrSolicits,
--           vrIpUdpComponentName,
--           vrIpMcastPimNbrExpiryTimer,
--           vrPpIpPortMediaType,
--           vrPpIpPortLogicalIfOspfIfAuthKey,
--           vrIpMcastStaticUsageState,
--           vrIpOspfExtLsdbAge,
--           vrPpIpPortLogicalIfOspfIfTransitDelay,
--           vrIpDefaultTtl,
--           vrIpEgpExportNetComponentName,
--           vrPpIpPortLogicalIfIgmpIfQueryMaxRespTime,
--           vrIpUdpOutDatagrams,
--           vrIpIfBroadcastAddress,
--           vrIpMcastPimSmDomainCRpStorageType,
--           vrIpMcastPimSmDomainCBsrRowStatus,
--           vrPpIpPortLogicalIfOspfIfRtrDeadInterval,
--           vrIpMcastPimSmDomainSptJoinThreshold,
--           vrIpNsRowStatus,
--           vrIpMcastUsageState,
--           vrPpIpPortLogicalIfIgmpIfComponentName,
--           vrPpIpPortBootpPBootpLogicalInterface,
--           vrPpIpPortLogicalIfIgmpIfJoins,
--           vrIpEgpImportRowStatus,
--           vrIpTunnelSepRowStatus,
--           vrIpEgpExportExportMetric,
--           vrIpMcastPimSmDomainDiscardRegisterStopMsg,
--           vrIpOspfVersionNumber,
--           vrIpMcastPimSmDomainCBsrStorageType,
--           vrIpMcastIgmpGcLastReporter,
--           vrIpIcmpOutAddrMasks,
--           vrPpIpPortNsIncomingFilter,
--           vrIpMcastStaticRouteOifsValue,
--           vrIpStaticUsageState,
--           vrPpIpPortLogicalIfRipIfFlashUpdateFlag,
--           vrIpOspfExportNetListRowStatus,
--           vrIpOspfNbrNbmaNbrStatus,
--           vrIpRipExportOutInterface,
--           vrPpIpPortLogicalIfRipIfMetric,
--           vrIpEgpNbrComponentName,
--           vrIpOutNoRoutes,
--           vrIpMcastPimSmDomainCRpGrpRowStatus,
--           vrPpIpPortLogicalIfRipIfDefaultRouteMetric,
--           vrPpIpPortAssignedQos,
--           vrIpRipExportNetStorageType,
--           vrIpEgpImportNbrAsId,
--           vrPpIpPortLogicalIfRipIfNbrComponentName,
--           vrPpIpPortLinkModel,
--           vrIpBootpPpEInReplyErrors,
--           vrIpArpDynHostType,
--           vrIpStaticRouteRowStatus,
--           vrIpEgpAsId,
--           vrIpMcastStaticStorageType,
--           vrIpMcastDomainComponentName,
--           vrIpOspfVirtIfTransitDelay,
--           vrPpIpPortSnmpOperStatus,
--           vrPpIpPortLogicalIfLinkToMulStaticGpValue,
--           vrIpFwdAge,
--           vrIpTunnelRowStatus,
--           vrIpNsApplyIpAddress1,
--           vrIpStaticDiscardRowStatus,
--           vrIpRipComponentName,
--           vrIpBootpPpEStatus,
--           vrIpMcastPimSmDomainDiscardJPMsg,
--           vrIpArpDynHostStorageType,
--           vrIpRipUsageState,
--           vrPpIpPortIcmpMaskReply,
--           vrIpMcastStaticRouteRowStatus,
--           vrIpOspfSnmpOperStatus,
--           vrIpEgpNbrPollInterval,
--           vrPpIpPortLogicalIfOspfIfNbrExchangeStatus,
--           vrIpIcmpInTimestampReps,
--           vrIpTunnelSepPathMtu,
--           vrIpOspfAreaSpfRuns,
--           vrIpCtsValue,
--           vrIpIfInterfaceMask,
--           vrIpOspfLsdbComponentName,
--           vrIpMcastPimSmDomainRxRegisterStopMsg,
--           vrIpNsApplyComponentName,
--           vrIpArpHostOperEncap,
--           vrIpIcmpInEchoReps,
--           vrIpMcastIgmpAdminState,
--           vrPpIpPortLogicalIfIgmpIfWrongVersionQuery,
--           vrIpRelayBCStorageType,
--           vrIpTcpRToMax,
--           vrIpEgpNbrState,
--           vrPpIpPortLogicalIfOspfIfNbrEvents,
--           vrIpMcastPimSmComponentName,
--           vrIpEgpMaxBufferSize,
--           vrIpRdbMetric,
--           vrIpMcastPgGrpComponentName,
--           vrPpIpPortLogicalIfOspfIfMulticastForwarding,
--           vrIpMcastPimSmDomainRxHelloMsg,
--           vrIpStaticRouteComponentName,
--           vrPpIpPortLogicalIfPimSmIfDesignatedRouter,
--           vrIpEgpNbrInMsgs,
--           vrIpTcpTcpEntryState,
--           vrIpNsLocalOutFilter,
--           vrIpOspfLsdbSequence,
--           vrIpOspfAggregateRowStatus,
--           vrIpIcmpStorageType,
--           vrIpReasmOks,
--           vrIpOspfExportBgpAsId,
--           vrIpOspfRowStatus,
--           vrIpOspfSnmpAdminStatus,
--           vrPpIpPortLogicalIfOspfIfStorageType,
--           vrIpEgpImportNetComponentName,
--           vrIpRipImportInterface,
--           vrIpEgpMaxNatNets,
--           vrPpIpPortLogicalIfOspfIfNbrLsRetransQlen,
--           vrIpMcastPgRowStatus,
--           vrIpEgpExportOutAutonomousSystem,
--           vrIpRipImportComponentName,
--           vrIpOspfExportNetListStorageType,
--           vrPpIpPortBootpPInReplies,
--           vrIpOspfLsdbAge,
--           vrIpMcastFwdAge,
--           vrIpBootpUsageState,
--           vrIpOspfExportProtocol,
--           vrIpOspfVirtIfEvents,
--           vrIpIcmpOutSrcQuenchs,
--           vrIpBootpPpEComponentName,
--           vrIpEgpSnmpOperStatus,
--           vrIpRipMigrateRip,
--           vrIpMcastPimSmDomainDiscardBsrMsg,
--           vrIpOspfVirtIfStorageType,
--           vrPpIpPortLogicalIfIgmpIfQuerier,
--           vrIpMcastFwdComponentName,
--           vrIpOspfOriginateNewLsas,
--           vrPpIpPortLogicalIfOspfIfAreaId,
--           vrIpRelayBCPortRowStatus,
--           vrIpOspfRouterId,
--           vrIpOspfVirtNbrOptions,
--           vrIpBootpSnmpOperStatus,
--           vrIpRipImportUsageFlag,
--           vrIpStaticStorageType,
--           vrIpRipImportNetStorageType,
--           vrIpArpHostPermanentVirtualCircuitNumber,
--           vrIpTunnelSepEncapType,
--           vrIpIcmpInSrcQuenchs,
--           vrIpTcpComponentName,
--           vrPpIpPortOperMtu,
--           vrIpOspfExportRowStatus,
--           vrIpBootpPpEStorageType,
--           vrIpOspfExportAdvertiseStatus,
--           vrIpRipRouteChangesMade,
--           vrIpEgpNbrEventTrigger,
--           vrIpMcastPgGrpRowStatus,
--           vrIpMcastIgmpGcComponentName,
--           vrIpStaticAdminState,
--           vrIpArpDynHostRowStatus,
--           vrIpOspfNbrOptions,
--           vrIpMcastIgmpStorageType,
--           vrIpRelayBCPortStorageType,
--           vrPpIpPortRelayBroadcast,
--           vrIpMcastPimSmDomainRpSetRowStatus,
--           vrIpTunnelSepIfIndex,
--           vrIpMcastCtsValue,
--           vrIpOspfExportNetListIpMask,
--           vrIpTunnelSepDestinationAddress,
--           vrPpIpPortBootpPInRequests,
--           vrIpMcastFwdOifOutProtocolPortName,
--           vrIpOspfAreaImportAsExtern,
--           vrIpMcastPimSmDomainDiscardHelloMsg,
--           vrIpMcastPimSmDomainDiscardRegisterMsg,
--           vrIpOspfExtLsdbRowStatus,
--           vrPpIpPortLogicalIfOspfIfNbrRowStatus,
--           vrIpMcastPimSmDomainRpSetStorageType,
--           vrIpMcastPimSmDomainBsrAddress,
--           vrIpMcastPimSmDomainRxRegisterMsg,
--           vrIpEgpExportInEgpAsId,
--           vrIpMcastCacheStatsRowStatus,
--           vrIpOspfAreaLsaCount,
--           vrIpOspfLsdbChecksum,
--           vrPpIpPortBootpPRowStatus,
--           vrIpIcmpOutEchoReps,
--           vrPpIpPortBootpPSnmpAdminStatus,
--           vrIpArpHostOperMaxTxUnit,
--           vrIpUdpListenEntryStorageType,
--           vrPpIpPortLogicalIfRipIfComponentName,
--           vrIpEgpNbrDefaultMetric,
--           vrIpOspfExternLsaChecksumSum,
--           vrIpMcastPimNbrUpTime,
--           vrPpIpPortLogicalIfOspfIfTOSComponentName,
--           vrIpIcmpOutTimestampReps,
--           vrPpIpPortLogicalIfComponentName,
--           vrIpIfStatus,
--           vrIpMcastPimSmDomainStorageType,
--           vrPpIpPortLogicalIfOspfIfNbrPermanance,
--           vrIpMcastPimNbrComponentName,
--           vrIpEgpImportUsageFlag,
--           vrIpIfRowStatus,
--           vrIpNsLocalInFilter,
--           vrIpMcastPimSmDomainTxJPMsg,
--           vrIpMcastCacheStatsOperationalState,
--           vrIpEgpExportRowStatus,
--           vrIpStaticRouteNhRowStatus,
--           vrIpInUnknownProtos,
--           vrPpIpPortBootpPOperationalState,
--           vrPpIpPortLogicalIfPimSmIfHelloInterval,
--           vrIpRipStorageType,
--           vrIpMcastCacheStatsTotalLookups,
--           vrIpRipExportNetIpAddress,
--           vrIpStaticOperationalState,
--           vrIpIfMtu,
--           vrIpIcmpOutDestUnreachs,
--           vrIpTcpTcpEntryComponentName,
--           vrIpEgpNbrInErrorMsgs,
--           vrIpIfHardwareAddress,
--           vrIpEgpExportComponentName,
--           vrIpMcastPgStorageType,
--           vrPpIpPortLogicalIfIgmpIfQueryInterval,
--           vrPpIpPortLogicalIfOspfIfEvents,
--           vrIpRipAdminState,
--           vrIpReasmTimeOut,
--           vrIpTcpEstabResets,
--           vrIpOspfExportNetListIpAddress,
--           vrIpMcastIgmpSnmpOperStatus,
--           vrIpMcastIgmpGcUpTime,
--           vrIpRdbComponentName,
--           vrIpIcmpInParmProbs,
--           vrIpRipGarbageCollectTimer,
--           vrIpUdpStorageType,
--           vrIpOspfAreaComponentName,
--           vrIpComponentName,
--           vrPpIpPortComponentName,
--           vrPpIpPortLogicalIfRipIfIfConfSend,
--           vrIpIcmpOutRtrSolicits,
--           vrIpRipRfc1058MetricUsage,
--           vrIpOspfNbrRtrId,
--           vrIpOspfExportEgpAsId,
--           vrIpEgpExportNetStorageType,
--           vrIpRipExportOspfTag,
--           vrIpMcastIgmpRowStatus,
--           vrIpCacheStorageType,
--           vrIpRipExportNetRowStatus,
--           vrIpRoutingDiscards,
--           vrPpIpPortNsComponentName,
--           vrIpRipExportStorageType,
--           vrIpMcastCacheStatsLookupMisses,
--           vrIpOspfNbrComponentName,
--           vrIpTunnelSepIfAdminStatus,
--           vrIpOspfExportBgpPeerIp,
--           vrIpEgpNbrGenerateDefaultRoute,
--           vrPpIpPortLogicalIfIgmpIfStorageType,
--           vrIpNsFirstFilter,
--           vrIpIfMediaType,
--           vrIpTcpMaxConn,
--           vrIpOspfVirtNbrState,
--           vrPpIpPortBootpPOutReplies,
--           vrIpIcmpOutParmProbs,
--           vrIpFragFails,
--           vrIpTcpStorageType,
--           vrIpFwdType,
--           vrIpMcastPgComponentName,
--           vrIpEgpUsageState,
--           vrIpArpDynHostPhysAddress,
--           vrIpOspfNbrLsRetransQlen,
--           vrIpArpAutoRefreshTimeout,
--           vrIpEgpNbrStorageType,
--           vrIpIcmpInMsgs,
--           vrIpMcastPimSmDomainCRpRowStatus,
--           vrIpIcmpInTimestamps,
--           vrIpMcastFwdOifStorageType,
--           vrIpBootpComponentName,
--           vrPpIpPortLogicalIfPimSmIfComponentName,
--           vrPpIpPortLogicalIfRipIfNbrStorageType,
--           vrPpIpPortLogicalIfOspfIfIfType,
--           vrIpMcastFwdOifComponentName,
--           vrIpOspfNbrState,
--           vrIpOspfAsBdrRtrStatus,
--           vrIpMcastPimNbrRowStatus,
--           vrIpMcastIgmpSnmpAdminStatus,
--           vrIpNsStorageType,
--           vrIpRipImportNeighbor,
--           vrIpEgpAdminState,
--           vrIpOspfExportMetric,
--           vrIpOspfAreaAreaBdrRtrCount,
--           vrPpIpPortMaxTxUnit,
--           vrIpMcastFwdProtocol,
--           vrIpMcastPimSmDomainCBsrComponentName,
--           vrPpIpPortMcastDomain,
--           vrIpMcastSnmpOperStatus,
--           vrIpBootpSnmpAdminStatus,
--           vrIpMcastIgmpOperationalState,
--           vrIpIcmpInDestUnreachs,
--           vrIpMcastStaticRouteComponentName,
--           vrIpArpDynHostIfIndex,
--           vrIpTcpCurrEstab,
--           vrIpRdbPreference,
--           vrIpOspfAreaAreaLsaCksumSum,
--           vrIpEgpImportImportMetric,
--           vrIpIcmpRowStatus,
--           vrIpOspfLsdbStorageType,
--           vrIpRipRipUpdate,
--           vrIpRipQueryResponses,
--           vrPpIpPortBootpPOutRequests,
--           vrPpIpPortLogicalIfOspfIfRowStatus,
--           vrPpIpPortLogicalIfRipIfPoisonReverseFlag,
--           vrIpMcastStaticRouteOifsRowStatus,
--           vrPpIpPortLogicalIfOspfIfSnmpAdminStatus,
--           vrIpEgpImportComponentName,
--           vrIpIcmpInErrors,
--           vrIpMcastPimSmStorageType,
--           vrIpOspfHostMetric,
--           vrIpMcastFwdOifAge,
--           vrIpMcastPimNbrIfIndex,
--           vrIpOspfExtLsdbSequence,
--           vrIpOspfExportNetListComponentName,
--           vrIpUsageState,
--           vrIpEgpNbrStateDowns,
--           vrIpTcpRToMin,
--           vrPpIpPortLogicalIfOspfIfBackupDesignatedRouter,
--           vrIpRelayBCRowStatus,
--           vrIpMcastPimSmDomainRpSetRpSetPriority,
--           vrIpOspfVirtIfRowStatus,
--           vrIpMcastPgAction,
--           vrIpMcastCacheStatsEntriesFree,
--           vrIpOspfStubMetricType,
--           vrIpOspfOperationalState,
--           vrIpOspfVirtIfHelloInterval,
--           vrIpMcastPimSmDomainTxCRpAdvMsg,
--           vrIpEgpImportNetStorageType,
--           vrIpMcastIgmpGcRowStatus }
-- STATUS  mandatory
-- DESCRIPTION
--   "A list of all current accessible leaf objects."

ipGroup OBJECT IDENTIFIER ::= { ipMIB 1 }
ipGroupBE OBJECT IDENTIFIER ::= { ipGroup 5 }
ipGroupBE01 OBJECT IDENTIFIER ::= { ipGroupBE 2 }
ipGroupBE01A OBJECT IDENTIFIER ::= { ipGroupBE01 2 }



-- Agent-Capabilities Statement:

-- PRODUCT-RELEASE "Passport Release 7.0 Ip."
-- STATUS          mandatory
-- DESCRIPTION     "Ip MIB: MIB Version BE01A,
--                  Software Version BG00S4C."
-- SUPPORTS        Nortel-Magellan-Passport-IpMIB
--    INCLUDES     { ipGroupBE01A }
--       rfc1213 (MIB II)
-- 
-- SUPPORTS          RFC1213-MIB
--    INCLUDES		{ at, ip, icmp, udp, egp } 
--                            tcp group not supported
-- 
-- 	   variations for at group
-- 	
-- 	VARIATION	atIfIndex
--  	   ACCESS       read-only
--  	   DESCRIPTION	"SET not allowed, because it is an index"
-- 
--  	VARIATION       atNetAddress
--   	   ACCESS       read-only
--            DESCRIPTION  "SET not allowed, because it is an index"
--  
-- 
-- 	   variations for the ip group
-- 
--  	VARIATION       ipForwarding
-- 	   WRITE-SYNTAX INTEGER { forwarding(1) }
--    	   DESCRIPTION  "Only valid value is forwarding(1)"
-- 
-- 	VARIATION	ipRouteDest
-- 	   ACCESS	read-only
-- 	   DESCRIPTION	"SET not allowed"
-- 
-- 	VARIATION	ipRouteIfIndex
-- 	   ACCESS	read-only
-- 	   DESCRIPTION	"SET not allowed"
-- 
-- 	VARIATION	ipRouteMetric1
-- 	   ACCESS	read-only
-- 	   DESCRIPTION	"SET not allowed"
-- 
-- 	VARIATION	ipRouteMetric2
-- 	   ACCESS	read-only
-- 	   DESCRIPTION	"SET not allowed"
-- 
-- 	VARIATION	ipRouteMetric3
-- 	   ACCESS	read-only
-- 	   DESCRIPTION	"SET not allowed"
-- 
-- 	VARIATION	ipRouteMetric4
-- 	   ACCESS	read-only
-- 	   DESCRIPTION	"SET not allowed"
-- 
-- 	VARIATION	ipRouteNextHop
-- 	   ACCESS	read-only
-- 	   DESCRIPTION	"SET not allowed"
-- 
-- 	VARIATION	ipRouteType
-- 	   ACCESS	read-only
-- 	   DESCRIPTION	"SET not allowed"
-- 
-- 	VARIATION	ipRouteAge
-- 	   ACCESS	read-only
-- 	   DESCRIPTION	"SET not allowed"
-- 
-- 	VARIATION	ipRouteMask
-- 	   ACCESS	read-only
-- 	   DESCRIPTION	"SET not allowed"
-- 
-- 	VARIATION	ipRouteMetric5
-- 	   ACCESS	read-only
-- 	   DESCRIPTION	"SET not allowed"
-- 
-- 
-- 	   variations for the egp group
-- 
--  	VARIATION       egpNeighEventTrigger
--  	   ACCESS       read-only
--  	   DESCRIPTION  "SET not allowed"
-- 
-- 
--    rfc1354 (IP Forwarding Table)
-- 
-- SUPPORTS RFC1354-MIB
-- INCLUDES { ipForward }
-- 
-- 	VARIATION       ipForwardMask
-- 	   ACCESS       read-only
-- 	   DESCRIPTION  "SET not allowed"
-- 
-- 	VARIATION       ipForwardIfIndex
-- 	   ACCESS       read-only
-- 	   DESCRIPTION  "SET not allowed"
-- 
-- 	VARIATION       ipForwardType
-- 	   ACCESS       read-only
-- 	   DESCRIPTION  "SET not allowed"
-- 
-- 	VARIATION       ipForwardInfo
-- 	   ACCESS       read-only
-- 	   DESCRIPTION  "SET not allowed"
-- 
-- 	VARIATION       ipForwardNextHopAS
-- 	   ACCESS       read-only
-- 	   DESCRIPTION  "SET not allowed"
-- 
-- 	VARIATION       ipForwardMetric1
-- 	   ACCESS       read-only
-- 	   DESCRIPTION  "SET not allowed"
-- 
-- 	VARIATION       ipForwardMetric2
-- 	   ACCESS       read-only
-- 	   DESCRIPTION  "SET not allowed"
-- 
-- 	VARIATION       ipForwardMetric3
-- 	   ACCESS       read-only
-- 	   DESCRIPTION  "SET not allowed"
-- 
-- 	VARIATION       ipForwardMetric4
-- 	   ACCESS       read-only
-- 	   DESCRIPTION  "SET not allowed"
-- 
-- 	VARIATION       ipForwardMetric5
-- 	   ACCESS       read-only
-- 	   DESCRIPTION  "SET not allowed"
-- 
-- 
--      rfc1253 (OSPF Version 2 MIB)
-- 
--   SUPPORTS RFC1253-MIB
--   INCLUDES { ospfAreaRangeTable }
-- 
-- 	VARIATION	ospfAreaRangeAreaID
-- 	ACCESS		read-only
-- 	DESCRIPTION	"Table will be obsoleted. Read access provided"
-- 
-- 	VARIATION	ospfAreaRangeNet
-- 	ACCESS		read-only
-- 	DESCRIPTION	"Table will be obsoleted. Read access provided"
-- 
-- 	VARIATION	ospfAreaRangeMask
-- 	ACCESS		read-only
-- 	DESCRIPTION	"Table will be obsoleted. Read access provided"
-- 
-- 	VARIATION	ospfAreaRangeStatus
-- 	ACCESS		read-only
-- 	DESCRIPTION	"Table will be obsoleted. Read access provided"
-- 
-- 
-- 
--      draft-ietf-ospf-mib-04.txt (OSPF version 2 MIB)
--      (A draft for evolution of RFC1253)
-- 
--   SUPPORTS OSPF-MIB
-- 
--   INCLUDES	  { ospfGeneralGroup 
-- 		    ospfAreaTable 
-- 		    ospfStubAreaTable
-- 		    ospfLsdbTable 
-- 		    ospfAreaRangeTable 
-- 		    ospfHostTable
-- 		    ospfIfTable 
-- 		    ospfIfMetricTable 
-- 		    ospfVirtIfTable
-- 		    ospfNbrTable 
-- 		    ospfVirtNbrTable 
-- 		    ospfExtLsdbTable
-- 		    ospfAreaAggregateTable }
-- 
-- 	   variations for ospfGeneralGroup group
-- 	
-- 	VARIATION	ospfTOSSupport
-- 	   WRITE-SYNTAX TruthValue { false(1) }
-- 	   DESCRIPTION	"Value limited to false(1)"
-- 
-- 	VARIATION       ospfMulticastExtensions
--  	   WRITE-SYNTAX INTEGER (0)
--  	   DESCRIPTION  "Value limited to 0"
--  
-- 	   Variations for ospfAreaTable group
-- 
-- 	VARIATION       ospfAuthType
--  	   WRITE-SYNTAX INTEGER { none (0), simplePassword (1) }
--   	   DESCRIPTION  "Value limited to none (0) and simplePassword (1)"
-- 
-- 	   Variations for the ospfIfTable
-- 
-- 	VARIATION       ospfIfMulticastForwarding
--   	   WRITE-SYNTAX INTEGER { blocked (1) }
--   	   DESCRIPTION  "Value limited to blocked (1)"
-- 
--         VARIATION       ospfIfType
--            WRITE-SYNTAX INTEGER { broadcast (1), nbma (2), pointToPoint (3) }
--            DESCRIPTION  "Value limited to broadcast (1), nbma (2) and 
--                          pointToPoint (3)"
-- 
--    rfc1724 (RIP Version2 MIB)
-- 
-- SUPPORTS RFC1724-MIB
-- INCLUDES { rip2Globals, rip2IfStatTable, rip2IfConfTable }                  
--              rip2PeerTable not supported
--           
-- 	   variations for the rip2IfStatTable
-- 	
-- 	VARIATION	rip2IfStatStatus
-- 	   ACCESS	read-only
-- 	   DESCRIPTION	"Set not allowed"
-- 	   
-- 	   variations for the rip2IfConfTable
-- 	
-- 	VARIATION	rip2IfConfDomain
-- 	   ACCESS	read-only
-- 	   DESCRIPTION	"Set not allowed"
-- 	   
-- 	VARIATION	rip2IfConfAuthType
-- 	   ACCESS	read-only
-- 	   DESCRIPTION	"Set not allowed"
-- 	   
-- 	VARIATION	rip2IfConfAuthKey
-- 	   ACCESS	read-only
-- 	   DESCRIPTION	"Set not allowed"
-- 	   
-- 	VARIATION	rip2IfConfSend
-- 	   ACCESS	read-only
-- 	   DESCRIPTION	"Set not allowed"
-- 	   
-- 	VARIATION	rip2IfConfRecveive
-- 	   ACCESS	read-only
-- 	   DESCRIPTION	"Set not allowed"
-- 	   
-- 	VARIATION	rip2IfConfDefaultMetric
-- 	   ACCESS	read-only
-- 	   DESCRIPTION	"Set not allowed"
-- 	   
-- 	VARIATION	rip2IfConfStatus
-- 	   ACCESS	read-only
-- 	   DESCRIPTION	"Set not allowed"
-- 	   
-- 	VARIATION	rip2IfConfSrcAddress
-- 	   ACCESS	read-only
-- 	   DESCRIPTION	"Set not allowed"
ipCapabilities OBJECT IDENTIFIER ::= { ipMIB 3 }
ipCapabilitiesBE OBJECT IDENTIFIER ::= { ipCapabilities 5 }
ipCapabilitiesBE01 OBJECT IDENTIFIER ::= { ipCapabilitiesBE 2 }
ipCapabilitiesBE01A OBJECT IDENTIFIER ::= { ipCapabilitiesBE01 2 }





END
