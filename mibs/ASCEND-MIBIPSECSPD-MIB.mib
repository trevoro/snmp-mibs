--			Ascend mibipsecspd MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBIPSECSPD-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibmibProfIpsecSpd  OBJECT IDENTIFIER ::= { configuration 168}

	-- The mibmibProfIpsecSpd table
	--
	-- This table contains parameters for the mibmibProfIpsecSpd profile
	--

    mibmibProfIpsecSpdTable	OBJECT-TYPE
	SYNTAX		SEQUENCE OF MibmibProfIpsecSpdEntry
	ACCESS		not-accessible
	STATUS		mandatory
	DESCRIPTION	"A list of mibmibProfIpsecSpd profile entries."
	::= { mibmibProfIpsecSpd 1 }

    mibmibProfIpsecSpdEntry	OBJECT-TYPE
	SYNTAX		MibmibProfIpsecSpdEntry
	ACCESS		not-accessible
	STATUS		mandatory
	DESCRIPTION	"A mibmibProfIpsecSpd entry containing objects that
			 maps to the parameters of mibmibProfIpsecSpd profile."
	INDEX		{ mibProfIpsecSpd-SpdName }
	::= { mibmibProfIpsecSpdTable 1 }

    MibmibProfIpsecSpdEntry ::=
	SEQUENCE {
	    mibProfIpsecSpd-SpdName
		DisplayString,
	    mibProfIpsecSpd-DefaultFilter
		DisplayString,
	    mibProfIpsecSpd-Action-o
		INTEGER
	}

    mibProfIpsecSpd-SpdName	OBJECT-TYPE
	SYNTAX	DisplayString
	ACCESS	read-only
	STATUS	mandatory
	DESCRIPTION	"The name of this IPSEC Security Policy Database."
	::= { mibmibProfIpsecSpdEntry 1 }

    mibProfIpsecSpd-DefaultFilter	OBJECT-TYPE
	SYNTAX	DisplayString
	ACCESS	read-write
	STATUS	mandatory
	DESCRIPTION	"The name of the default Filter. IP packets having matched no policy in the SPD will be processed through this filter and be either dropped or passed in clear. If no default-filter is defined, all this traffic will be dropped."
	::= { mibmibProfIpsecSpdEntry 2 }

    mibProfIpsecSpd-Action-o	OBJECT-TYPE
	SYNTAX	INTEGER {
		    noAction (1),
		    createProfile (2),
		    deleteProfile (3)
		}
	ACCESS	read-write
	STATUS	mandatory
	DESCRIPTION	""
	::= { mibmibProfIpsecSpdEntry 3 }


	-- The mibmibProfIpsecSpd__policy table
	--
	-- This table contains parameters for the mibmibProfIpsecSpd__policy profile
	--

    mibmibProfIpsecSpd-PolicyTable	OBJECT-TYPE
	SYNTAX		SEQUENCE OF MibmibProfIpsecSpd-PolicyEntry
	ACCESS		not-accessible
	STATUS		mandatory
	DESCRIPTION	"A list of mibmibProfIpsecSpd__policy profile entries."
	::= { mibmibProfIpsecSpd 2 }

    mibmibProfIpsecSpd-PolicyEntry	OBJECT-TYPE
	SYNTAX		MibmibProfIpsecSpd-PolicyEntry
	ACCESS		not-accessible
	STATUS		mandatory
	DESCRIPTION	"A mibmibProfIpsecSpd__policy entry containing objects that
			 maps to the parameters of mibmibProfIpsecSpd__policy profile."
	INDEX		{ mibProfIpsecSpd-Policy-SpdName, mibProfIpsecSpd-Policy-Index-o }
	::= { mibmibProfIpsecSpd-PolicyTable 1 }

    MibmibProfIpsecSpd-PolicyEntry ::=
	SEQUENCE {
	    mibProfIpsecSpd-Policy-SpdName
		DisplayString,
	    mibProfIpsecSpd-Policy-Index-o
		INTEGER,
	    mibProfIpsecSpd-Policy
		DisplayString
	}

    mibProfIpsecSpd-Policy-SpdName	OBJECT-TYPE
	SYNTAX	DisplayString
	ACCESS	read-only
	STATUS	mandatory
	DESCRIPTION	""
	::= { mibmibProfIpsecSpd-PolicyEntry 1 }

    mibProfIpsecSpd-Policy-Index-o	OBJECT-TYPE
	SYNTAX	INTEGER
	ACCESS	read-only
	STATUS	mandatory
	DESCRIPTION	""
	::= { mibmibProfIpsecSpd-PolicyEntry 2 }

    mibProfIpsecSpd-Policy	OBJECT-TYPE
	SYNTAX	DisplayString
	ACCESS	read-write
	STATUS	mandatory
	DESCRIPTION	"An ordered list of IPSec Policies."
	::= { mibmibProfIpsecSpd-PolicyEntry 3 }

END
