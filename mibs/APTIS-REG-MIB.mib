--	Aptis Enterprise MIB
--
--	Nortel Networks
--	11 Elizabeth Drive
--	Chelmsford, MA 01824
--
--	Copyright (c) 1997-2000 Nortel Networks
--	All Rights Reserved.
--

APTIS-REG-MIB DEFINITIONS ::= BEGIN

	IMPORTS
	    enterprises, MODULE-IDENTITY, OBJECT-IDENTITY
	        FROM SNMPv2-SMI
	    aptis-reg
		FROM APTIS-MIB;

	aptisRegModule MODULE-IDENTITY
        LAST-UPDATED "0004140000Z"
        ORGANIZATION "Nortel Networks"
        CONTACT-INFO
            "   Technical Support/Customer Service
                Nortel Networks

                Postal: 11 Elizabeth Drive
                        Chelmsford, MA 01824

                Tel:
                In the USA: Dial 1-800-758-4827 to contact a Technical Support engineer.
                Outside the USA:  Contact your Regional Nortel Networks Support Prime.

                For information about the Nortel Networks Network Access Division,
                go to the World Wide Web (WWW) site at http://www.nortelnetworks.com."

		DESCRIPTION
			"Registration subtree of 
			 Nortel Networks Aptis Enterprise MIB"

	::= { enterprises aptis(2637) aptis-reg(1) aptis-modules(1) 2 }

--
--	The registration subtree is broken up into modules,
--	systems, and cards.
--

	aptis-modules	OBJECT-IDENTITY
		STATUS	current
		DESCRIPTION
			"Subtree to register the values assigned
			to modules with the MODULE-IDENTITY construct."

		::= { aptis-reg 1 }

	aptis-systems	OBJECT-IDENTITY
		STATUS	current
		DESCRIPTION
			"Subtree to register the values assigned
			to complete systems.  These are registered in the 
			MIB-II systemGroup.sysObjectID."

		::= { aptis-reg 2 }

	aptis-cards	OBJECT-IDENTITY
		STATUS	deprecated
		DESCRIPTION
			"Subtree to register the values assigned
			to slot cards inside systems. These part numbers
			are no longer being used."

		::= { aptis-reg 3 }

	aptis-components	OBJECT-IDENTITY
		STATUS		current
		DESCRIPTION
			"Subtree to register the values assigned
			to managed objects for the system components 
			inside the software.

			These are referenced in 
			componenentTableEntry.componentType."

		::= { aptis-reg 4 }

--
--	Assigned module numbers
--

--	aptisRootModule		::= { aptis-modules 1 }
--	aptisRegModule		::= { aptis-modules 2 }	
--	aptisConfigModule	::= { aptis-modules 3 }	
--	aptisMonitorModule	::= { aptis-modules 4 }
--	aptisActionsModule	::= { aptis-modules 5 }
--	aptisExpModule		::= { aptis-modules 6 }

--
--	There is only one system subtree at this time.
--

	cvx	OBJECT-IDENTITY
		STATUS	current
		DESCRIPTION	"The CVX product line."

		::= { aptis-systems 1 }


	cvx-1800	OBJECT-IDENTITY
		STATUS	current
		DESCRIPTION	"The 18-slot CVX system."

		::= { cvx 1 }

	cvx-600		OBJECT-IDENTITY
		STATUS	current
		DESCRIPTION	"The 6-slot CVX system."

		::= { cvx 2 }

--
-- Deprecated items
--	

	assy-725	OBJECT-IDENTITY
		STATUS	deprecated
		DESCRIPTION	"725 Board-level assemblies."

		::= { aptis-cards 725 }

	assy-750	OBJECT-IDENTITY
		STATUS	deprecated
		DESCRIPTION	"750 Top-level assemblies."

		::= { aptis-cards 750 }

	mam-main-board	OBJECT-IDENTITY
		STATUS	deprecated
		DESCRIPTION	"725-0003 Modem Access Module main board"

		::= { assy-725 3 }

	dmm-board 	OBJECT-IDENTITY
		STATUS	deprecated
		DESCRIPTION	"725-0004 Digital Modem Module"

		::= { assy-725 4 }

	tsc-main-board	OBJECT-IDENTITY
		STATUS	deprecated
		DESCRIPTION	"725-0005 TSC main board"

		::= { assy-725 5 }

END
