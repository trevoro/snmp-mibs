HPOV-SNMPSEC-MIB DEFINITIONS ::= BEGIN

IMPORTS
    MODULE-IDENTITY, OBJECT-IDENTITY, OBJECT-TYPE, 
    NOTIFICATION-TYPE, enterprises
        FROM SNMPv2-SMI
    MODULE-COMPLIANCE, OBJECT-GROUP, NOTIFICATION-GROUP
        FROM SNMPv2-CONF;

hp		OBJECT IDENTIFIER ::= { enterprises 11 }
nm		OBJECT IDENTIFIER ::= { hp 2 }
openView	OBJECT IDENTIFIER ::= { nm 17 }

--
-- Textual Conventions
--

OVTDAddress ::= TEXTUAL-CONVENTION
    STATUS       current
    DESCRIPTION
          "Denotes a transport domain and address, much like the
          TDomain and TAddress textual convention pair defined in 
          RFC 1902, yet in a more compact representation.

	  The first octet identifies the transport domain.  This
          value directly corresponds to the value of the transport 
          domain object sub-identifier, as defined in RFC1906, that 
          is subordinate to iso.org.dod.internet.snmpV2.snmpDomains. 

          The remaining octets conform to the transport address 
          syntax associated with the specified transport domain.

          For example, a value of 1 in the first octet corresponds 
          to snmpUDPDomain, so the remaining octets conform to the 
          syntax of snmpUDPAddress.
	  
	  For convienence, the mappings are summarized as follows.
	  Note that UDP/IP and IPX are fixed length; CLNS, CONS and 
	  DDP are variable length.

		   OVTDAddress octets
	  Domain   1   2   3  4  5  6  7  8  9 10 11 12 13 14 15...
	  ======  ==  ==  == == == == == == == == == == == == ==
	  UDP/IP   1  <ip-address> <port>
          CLNS     2  <n> <nsap-address..n> <t-selector...m>
          CONS     3  <n> <nsap-address..n> <t-selector...m>
	  DDP      4  <n> <object...n><p><type..p><q><zone...q>
	  IPX      5  <net-number> <physical-addres> <sock>
	  "

    REFERENCE
          "RFC 1906, Transport Mappings for SNMP Version 2"

    SYNTAX       OCTET STRING (SIZE (1..255))


--
-- OpenView / SNMPv2 Security Group
--
-- This group provides protocol extensions for use in SNMPv2 
-- Secure environments.
-- 
hpOVSNMPSecurity OBJECT IDENTIFIER ::= { openView 5 }

hpOVSecureTarget OBJECT-TYPE
	SYNTAX	OVTDAddress
	ACCESS	not-accessible		-- or accessible-for-notify ?
	STATUS	current
	DESCRIPTION
		"The transport domain/address of the intended destination 
                 or original source of an SNMP message forwarded through
                 an OV/SNMPv2 Security Proxy.  

                 This object is not exposed to the OV application nor the
                 target SNMP agent.  It is used only within communication 
                 between the OpenView SNMP protocol engine and an SNMPv2 
                 Security Proxy, as follows:  

                   o  An instance of this object is appended to, 
                      and subsequently stripped from, all messages 
                      sent between the OV SNMP protocol engine and 
                      an SNMPv2 security proxy.  

                   o  An instance of this object in messages sent 
                      from the OVSNMP protocol engine to the SNMPv2 
                      security proxy identifies the intended 
                      destination of the SNMP message.

                   o  An instance of this object in messages received
                      by the OVSNMP protocol engine from the SNMPv2 
                      security proxy identifies the original source 
                      of the SNMP message."

	::= { hpOVSNMPSecurity 1 }

END
