--
--  SNMP-related managed objects.
--
--  Copyright(c) 1997,1998,1999 No Wires Needed BV
--
--  Version 2.0.0
--

WL400-SNMPGEN-MIB DEFINITIONS ::= BEGIN

IMPORTS
	MODULE-IDENTITY, OBJECT-TYPE, Integer32, IpAddress
		FROM SNMPv2-SMI
	RowStatus
		FROM SNMPv2-TC
	MODULE-COMPLIANCE, OBJECT-GROUP
		FROM SNMPv2-CONF
	wl400Generic, wl400Modules
		FROM WL400-GLOBAL-REG;
		

snmpGenMIBModule MODULE-IDENTITY
	LAST-UPDATED	"9905260000Z"
	ORGANIZATION	"Compaq Computer Corporation"
	CONTACT-INFO "
		 Name: 		Compaq Computer Corporation
		 Address:	20555 SH 249
		 Zip:		77070
		 City:		Houston
		 Country:	USA
		 Phone:		
		 Fax:		
		 e-mail:	
		 "
	DESCRIPTION
		"The Compaq WL400 SNMP General MIB Module."
	::= { wl400Modules 3 }


-- the group containing general SNMP objects
snmpGenMIB		OBJECT IDENTIFIER ::= { wl400Generic 1 }

-- conformance and compliance specifications
snmpGenConf		OBJECT IDENTIFIER ::= { snmpGenMIB 1 }
snmpGenGroups 	OBJECT IDENTIFIER ::= { snmpGenConf 1 }
snmpGenCompl	OBJECT IDENTIFIER ::= { snmpGenConf 2 }

-- the tree for managed objects
snmpGenObjs OBJECT IDENTIFIER ::= { snmpGenMIB 2 }


--
-- managed objects
--

snmpGenReadCommunityString OBJECT-TYPE
	SYNTAX		OCTET STRING (SIZE(0..64))
	MAX-ACCESS	read-write
	STATUS		current
	DESCRIPTION
		"The community string to use for SNMP communication with this
		 entity when the SNMP operation is a read operation."
	::= { snmpGenObjs 1 }

snmpGenWriteCommunityString OBJECT-TYPE
	SYNTAX 		OCTET STRING (SIZE(0..64))
	MAX-ACCESS	read-write
	STATUS		current
	DESCRIPTION
		"The community string to use for SNMP communication with this
		 entity when the SNMP operation is a SET Request. When read, 
		 this object has an undefined value. When written, subsequent 
		 SNMP SET operations must use the new community string to be 
		 accepted as authentic. 
		 
		 When the reset button is pressed on the Access Point, this
		 variable is reset to 'private'. This is also the default 
		 manufacturer value. "
	::= { snmpGenObjs 2 }

snmpGenTrapDstMaxTableLength OBJECT-TYPE
	SYNTAX		Integer32
	MAX-ACCESS	read-only
	STATUS		current
	DESCRIPTION
		"The maximum number of entries in the Trap Destination Table."
	::= { snmpGenObjs 3 }

snmpGenTrapDstTable OBJECT-TYPE
	SYNTAX		SEQUENCE OF SnmpGenTrapDstEntry
	MAX-ACCESS 	not-accessible
	STATUS		current
	DESCRIPTION
		"The table containing management targets where notifications
		 (SNMP traps) must be sent to. Syslog messages also use this 
		 table."
	::= { snmpGenObjs 4 }

snmpGenTrapDstEntry OBJECT-TYPE
	SYNTAX		SnmpGenTrapDstEntry
	MAX-ACCESS 	not-accessible
	STATUS		current
	DESCRIPTION
		"An entry in the Trap Destination table."
	INDEX { snmpGenTrapDstIndex }
	::= { snmpGenTrapDstTable 1 }

SnmpGenTrapDstEntry ::= SEQUENCE {
	snmpGenTrapDstIndex	   		Integer32,
    snmpGenTrapDstIpAddress    	IpAddress,
	snmpGenTrapDstType			INTEGER, 
    snmpGenTrapDstRowStatus   	RowStatus
   }

snmpGenTrapDstIndex OBJECT-TYPE
	SYNTAX 		Integer32 (1..256)
	MAX-ACCESS	not-accessible
	STATUS		current
	DESCRIPTION 
		"An index into the Trap Destination table."
	::= { snmpGenTrapDstEntry 1 }

snmpGenTrapDstIpAddress OBJECT-TYPE
	SYNTAX		IpAddress
	MAX-ACCESS 	read-create
	STATUS		current
	DESCRIPTION
		"The IP address of a management station to send traps to."
	::= { snmpGenTrapDstEntry 2 }

snmpGenTrapDstType OBJECT-TYPE
	SYNTAX		INTEGER { trapOnly(1), syslogOnly(2), 
					trapAndSyslog(3) }
	MAX-ACCESS 	read-create
	STATUS		current
	DESCRIPTION
		"The type indicates what kind of notification is sent.
		 When set to trapOnly(1), only SNMP traps are sent to the
		 IP address. When set to syslogOnly(2), only syslog messages
		 are sent and when set to trapAndSyslog(3), both a trap and
		 a syslog message will be sent."
	::= { snmpGenTrapDstEntry 3 }

snmpGenTrapDstRowStatus OBJECT-TYPE
	SYNTAX		RowStatus
	MAX-ACCESS	read-create
	STATUS		current
	DESCRIPTION
		"The status value for creating and deleting rows in this
		 table."
	::= { snmpGenTrapDstEntry 4 }

snmpGenLockStatus OBJECT-TYPE
	SYNTAX  	INTEGER { locked(1), unlocked(2) }
	MAX-ACCESS	read-write
	STATUS		current
	DESCRIPTION
		"This object can be used to lock the SNMP agent. When locked,
		 the agent becomes read-only, i.e. no objects can be written
		 any more. This is useful in a relatively insecure SNMPv1
		 environment when the network administrator has configured
		 the device and does not intend to change it.
		 
		 This variable can only be set to locked(1). When pressing the
		 reset button on the Access Point, this variable is reset to
		 unlocked(2) and the snmpGenWriteCommunityString is reset to
		 'private'."
	::= { snmpGenObjs 5 }
	
snmpGenChangeIPAddress OBJECT-TYPE
	SYNTAX		OCTET STRING (SIZE(18))
	MAX-ACCESS	read-write
	STATUS		current
	DESCRIPTION
		"This object is used to change the fixed or 'remembered' IP
		 address of an Access Point. When there is a DHCP/BOOTP server
		 on the network, this variable is not needed. When there is no 
		 DHCP/BOOTP server for the IP subnet, the Access Point will try 
		 to use the IP address gotten from a previous BOOTP reply (which 
		 gives an infinite lease) or an infinite DHCP lease. When there
		 was no previous BOOTP reply, the Access Point can be given an 
		 IP address using this variable.
		 
		 Also when the current IP address of the Access Point is invalid
		 for the current IP subnet, this variable can be set by sending 
		 an SNMP SET request to the multicast address 224.0.1.43.  The 
		 MAC address included here ensures that only the right Access 
		 Point will accept the SET Request. 
		 
		 The IP address given through this variable is considered an
		 infinite lease by the Access Point.
		 
		 The format of this variable is as follows:
		 
		 MAC Address: 6 octets
		 IP Address: 4 octets (network byte order)
		 IP Subnet Mask: 4 octets (network byte order)
		 IP Default Router: 4 octets (network byte order)"
	::= { snmpGenObjs 6 }
		 
snmpGenUseDHCP OBJECT-TYPE
	SYNTAX		INTEGER { always(1), smart(2), never(3) }
	MAX-ACCESS	read-write
	STATUS		current
	DESCRIPTION
		"This object controls DHCP operation. When set to always(1),
		 the Access Point will not assume an infinite lease it was
		 given but continue trying to obtain an IP address using DHCP.
		 
		 The Access Point can only see the difference between an infinite
		 lease and a finite lease because there is no clock running when
		 the device is shut down. When set to smart(2), the Access Point 
		 will use DHCP when it does not have an infinite lease. When it 
		 does have an infinite lease, it quickly tries to contact a DHCP
		 server (because it may now be in a new IP subnet) using one 
		 DHCPREQUEST and one DHCPDISCOVER. If no replies are received, it
		 will automatically assume its given (infinite) address within
		 a few seconds after reboot.
		 
		 When set to never(3), the Access Point will not use DHCP if it
		 has an infinite address. It will immediately assume that address
		 after a reboot. Note that the Access Point requires a valid
		 (not NULL) IP address for this object to be set to never(3)."
	::= { snmpGenObjs 7 }
	

--
--  Groups and compliances
--

snmpGenBasicGroup 	OBJECT-GROUP
	OBJECTS {
			snmpGenReadCommunityString,
			snmpGenWriteCommunityString,
			snmpGenTrapDstMaxTableLength,
			snmpGenTrapDstIpAddress,
			snmpGenTrapDstType,
			snmpGenTrapDstRowStatus,
			snmpGenLockStatus,
			snmpGenChangeIPAddress,
			snmpGenUseDHCP
			}
	STATUS		current
	DESCRIPTION	"The snmp general group."
	::= { snmpGenGroups 1 }


snmpGenBasicCompl MODULE-COMPLIANCE
	STATUS 		current	
	DESCRIPTION "The implementation requirements for an IEEE 802.11 Station."
	MODULE		-- this module
		MANDATORY-GROUPS {
			snmpGenBasicGroup
		}
	::= { snmpGenCompl 1 }

END
