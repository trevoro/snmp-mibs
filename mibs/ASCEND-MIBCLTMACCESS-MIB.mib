--			Ascend mibcltmaccess MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBCLTMACCESS-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibcltmAccess  OBJECT IDENTIFIER ::= { configuration 67}

	-- The mibcltmAccess table
	--
	-- This table contains parameters for the mibcltmAccess profile
	--

    mibcltmAccessTable	OBJECT-TYPE
	SYNTAX		SEQUENCE OF MibcltmAccessEntry
	ACCESS		not-accessible
	STATUS		mandatory
	DESCRIPTION	"A list of mibcltmAccess profile entries."
	::= { mibcltmAccess 1 }

    mibcltmAccessEntry	OBJECT-TYPE
	SYNTAX		MibcltmAccessEntry
	ACCESS		not-accessible
	STATUS		mandatory
	DESCRIPTION	"A mibcltmAccess entry containing objects that
			 maps to the parameters of mibcltmAccess profile."
	INDEX		{ cltmAccess-Index-o }
	::= { mibcltmAccessTable 1 }

    MibcltmAccessEntry ::=
	SEQUENCE {
	    cltmAccess-Index-o
		INTEGER,
	    cltmAccess-CltmSlot
		INTEGER,
	    cltmAccess-AccessSlot
		INTEGER,
	    cltmAccess-AccessPort
		INTEGER,
	    cltmAccess-AccessLoop
		INTEGER,
	    cltmAccess-AccessMode
		INTEGER,
	    cltmAccess-AccessTerminal
		INTEGER,
	    cltmAccess-ActivateAccess
		INTEGER,
	    cltmAccess-AccessResult
		INTEGER,
	    cltmAccess-Action-o
		INTEGER
	}

    cltmAccess-Index-o	OBJECT-TYPE
	SYNTAX	INTEGER
	ACCESS	read-only
	STATUS	mandatory
	DESCRIPTION	""
	::= { mibcltmAccessEntry 1 }

    cltmAccess-CltmSlot	OBJECT-TYPE
	SYNTAX	INTEGER {
		    anySlot (1),
		    slot1 (2),
		    slot2 (3),
		    slot3 (4),
		    slot4 (5),
		    slot5 (6),
		    slot6 (7),
		    slot7 (8),
		    slot10 (11),
		    slot11 (12),
		    slot12 (13),
		    slot13 (14),
		    slot14 (15),
		    slot15 (16),
		    slot16 (17)
		}
	ACCESS	read-write
	STATUS	mandatory
	DESCRIPTION	"Identify the CLTM slot within the system."
	::= { mibcltmAccessEntry 2 }

    cltmAccess-AccessSlot	OBJECT-TYPE
	SYNTAX	INTEGER {
		    anySlot (1),
		    slot1 (2),
		    slot2 (3),
		    slot3 (4),
		    slot4 (5),
		    slot5 (6),
		    slot6 (7),
		    slot7 (8),
		    slot10 (11),
		    slot11 (12),
		    slot12 (13),
		    slot13 (14),
		    slot14 (15),
		    slot15 (16),
		    slot16 (17)
		}
	ACCESS	read-write
	STATUS	mandatory
	DESCRIPTION	"Identify the slot of the copper loop to be accessed."
	::= { mibcltmAccessEntry 3 }

    cltmAccess-AccessPort	OBJECT-TYPE
	SYNTAX	INTEGER
	ACCESS	read-write
	STATUS	mandatory
	DESCRIPTION	"Identify the port of the copper loop to be accessed."
	::= { mibcltmAccessEntry 4 }

    cltmAccess-AccessLoop	OBJECT-TYPE
	SYNTAX	INTEGER
	ACCESS	read-write
	STATUS	mandatory
	DESCRIPTION	"Identify the the copper loop to be accessed."
	::= { mibcltmAccessEntry 10 }

    cltmAccess-AccessMode	OBJECT-TYPE
	SYNTAX	INTEGER {
		    lookingOut (1),
		    bridged (2)
		}
	ACCESS	read-write
	STATUS	mandatory
	DESCRIPTION	"The mode of the CLTM access."
	::= { mibcltmAccessEntry 5 }

    cltmAccess-AccessTerminal	OBJECT-TYPE
	SYNTAX	INTEGER {
		    internalTesterTerminal (1),
		    externalTesterTerminal (2),
		    auxiliaryTesterTerminal (3),
		    externalLoop (4)
		}
	ACCESS	read-write
	STATUS	mandatory
	DESCRIPTION	"The tester terminal to access the test copper loop."
	::= { mibcltmAccessEntry 6 }

    cltmAccess-ActivateAccess	OBJECT-TYPE
	SYNTAX	INTEGER {
		    no (1),
		    yes (2)
		}
	ACCESS	read-write
	STATUS	mandatory
	DESCRIPTION	"Activate/Deactivate access."
	::= { mibcltmAccessEntry 7 }

    cltmAccess-AccessResult	OBJECT-TYPE
	SYNTAX	INTEGER {
		    idle (1),
		    accessActivated (2),
		    resourceBusy (3)
		}
	ACCESS	read-only
	STATUS	mandatory
	DESCRIPTION	"The result of activating the copper loop access."
	::= { mibcltmAccessEntry 8 }

    cltmAccess-Action-o	OBJECT-TYPE
	SYNTAX	INTEGER {
		    noAction (1),
		    createProfile (2),
		    deleteProfile (3)
		}
	ACCESS	read-write
	STATUS	mandatory
	DESCRIPTION	""
	::= { mibcltmAccessEntry 9 }

END
