-- *****************************************************************************
-- Unisphere-Data-DS3-CONF
--
-- SNMP Agent Capabilities definitions for the DS3 MIBs.
--
-- Copyright (c) 2001 Unisphere Networks, Inc.
-- Copyright (c) 2002 Unisphere Networks, Inc.
--   All rights reserved.
-- *****************************************************************************

Unisphere-Data-DS3-CONF DEFINITIONS ::= BEGIN

IMPORTS
    MODULE-IDENTITY
        FROM SNMPv2-SMI
    AGENT-CAPABILITIES
        FROM SNMPv2-CONF
    usDataAgents
        FROM Unisphere-Data-Agents
    dsx3ConfigEntry, dsx3CurrentEntry, dsx3IntervalEntry, dsx3TotalEntry,
    dsx3FarEndConfigEntry, dsx3FarEndCurrentEntry, dsx3FarEndIntervalEntry,
    dsx3FarEndTotalEntry, dsx3FracEntry, dsx3SendCode
        FROM RFC1407-MIB
    usdDs3Group, usdDs3Group2, usdDs3Group3, usdDs3Group4, usdDs3Group5,
    usdDs3FarEndGroup
        FROM Unisphere-Data-DS3-MIB;

usdDs3Agent MODULE-IDENTITY
    LAST-UPDATED "200208271848Z"  -- 27-Aug-02 02:48 PM EDT
    ORGANIZATION "Unisphere Networks, Inc."
    CONTACT-INFO
        "       Unisphere Networks, Inc.
        Postal: 10 Technology Park Drive
                Westford, MA 01886
                USA
        Tel:    +1 978 589 5800
        E-mail: mib@UnisphereNetworks.com"
    DESCRIPTION
        "The agent capabilities definitions for the DS3 component of the SNMP
        agent in the Unisphere Data Routing Switch family of products."
    -- Revision History
    REVISION    "200208271848Z"  -- 27-Aug-02 02:48 PM EDT  - RX 4.0
    DESCRIPTION
        "Added far end support."
    REVISION    "200104181941Z"  -- 18-Apr-01 03:41 PM EDT  - RX 3.2
    DESCRIPTION
        "The initial release of this management information module."
    ::= { usDataAgents 11 }


usdDs3AgentV1 AGENT-CAPABILITIES
    PRODUCT-RELEASE
        "Version 1 of the DS3 component of the Unisphere Routing Switch SNMP
        agent.  This version of the DS3 component was supported in the Unisphere
        RX 1.0 system release."
    STATUS      obsolete
    DESCRIPTION
        "The MIBs supported by the SNMP agent for the DS3 application in the
        Unisphere Routing Switch.  These capabilities became obsolete when
        support was added for line type and cell scrambler objects."
    SUPPORTS    RFC1407-MIB
    --  The RFC1407-MIB is based on SMIv1 and has no conformance groups.
    --  Therefore, we list capabilities by OID subtree "groups".
        INCLUDES  {
            dsx3ConfigEntry,
            dsx3CurrentEntry,
            dsx3IntervalEntry,
            dsx3TotalEntry,
            dsx3FracEntry }
        VARIATION   dsx3SendCode
            ACCESS      not-implemented
            DESCRIPTION
                "Management of the type of code being sent across the DS3/E3
                interface is not implemented."
    SUPPORTS    Unisphere-Data-DS3-MIB
        INCLUDES  { usdDs3Group }
    ::= { usdDs3Agent 1 }

usdDs3AgentV2 AGENT-CAPABILITIES
    PRODUCT-RELEASE
        "Version 2 of the DS3 component of the Unisphere Routing Switch SNMP
        agent.  This version of the DS3 component was supported in the Unisphere
        RX 1.1 thru RX 2.5 system releases."
    STATUS      obsolete
    DESCRIPTION
        "The MIBs supported by the SNMP agent for the DS3 application in the
        Unisphere Routing Switch.  These capabilities became obsolete when
        support was added for DSU configuration objects."
    SUPPORTS    RFC1407-MIB
    --  The RFC1407-MIB is based on SMIv1 and has no conformance groups.
    --  Therefore, we list capabilities by OID subtree "groups".
        INCLUDES  {
            dsx3ConfigEntry,
            dsx3CurrentEntry,
            dsx3IntervalEntry,
            dsx3TotalEntry,
            dsx3FracEntry }
        VARIATION   dsx3SendCode
            ACCESS      not-implemented
            DESCRIPTION
                "Management of the type of code being sent across the DS3/E3
                interface is not implemented."
    SUPPORTS    Unisphere-Data-DS3-MIB
        INCLUDES  { usdDs3Group2 }
    ::= { usdDs3Agent 2 }

usdDs3AgentV3 AGENT-CAPABILITIES
    PRODUCT-RELEASE
        "Version 3 of the DS3 component of the Unisphere Routing Switch SNMP
        agent.  This version of the DS3 component was supported in the Unisphere
        RX 2.6 thru RX 2.9 system releases."
    STATUS      obsolete
    DESCRIPTION
        "The MIBs supported by the SNMP agent for the DS3 application in the
        Unisphere Routing Switch.  These capabilities became obsolete when
        support was added for dynamic DS3 interface objects."
    SUPPORTS    RFC1407-MIB
    --  The RFC1407-MIB is based on SMIv1 and has no conformance groups.
    --  Therefore, we list capabilities by OID subtree "groups".
        INCLUDES  {
            dsx3ConfigEntry,
            dsx3CurrentEntry,
            dsx3IntervalEntry,
            dsx3TotalEntry,
            dsx3FracEntry }
        VARIATION   dsx3SendCode
            ACCESS      not-implemented
            DESCRIPTION
                "Management of the type of code being sent across the DS3/E3
                interface is not implemented."
    SUPPORTS    Unisphere-Data-DS3-MIB
        INCLUDES  { usdDs3Group3 }
    ::= { usdDs3Agent 3 }

usdDs3AgentV4 AGENT-CAPABILITIES
    PRODUCT-RELEASE
        "Version 4 of the DS3 component of the Unisphere Routing Switch SNMP
        agent.  This version of the DS3 component was supported in the Unisphere
        RX 3.x system releases."
    STATUS      obsolete
    DESCRIPTION
        "The MIBs supported by the SNMP agent for the DS3 application in the
        Unisphere Routing Switch.  These capabilities became obsolete when far
        end support"
    SUPPORTS    RFC1407-MIB
    --  The RFC1407-MIB is based on SMIv1 and has no conformance groups.
    --  Therefore, we list capabilities by OID subtree "groups".
        INCLUDES  {
            dsx3ConfigEntry,
            dsx3CurrentEntry,
            dsx3IntervalEntry,
            dsx3TotalEntry,
            dsx3FracEntry }
        VARIATION   dsx3SendCode
            ACCESS      not-implemented
            DESCRIPTION
                "Management of the type of code being sent across the DS3/E3
                interface is not implemented."
    SUPPORTS    Unisphere-Data-DS3-MIB
        INCLUDES  { usdDs3Group4 }
    ::= { usdDs3Agent 4 }

usdDs3AgentV5 AGENT-CAPABILITIES
    PRODUCT-RELEASE
        "Version 5 of the DS3 component of the Unisphere Routing Switch SNMP
        agent.  This version of the DS3 component is supported in the Unisphere
        RX 4.0 and subsequent system releases."
    STATUS      current
    DESCRIPTION
        "The MIBs supported by the SNMP agent for the DS3 application in the
        Unisphere Routing Switch."
    SUPPORTS    RFC1407-MIB
    --  The RFC1407-MIB is based on SMIv1 and has no conformance groups.
    --  Therefore, we list capabilities by OID subtree "groups".
        INCLUDES  {
            dsx3ConfigEntry,
            dsx3CurrentEntry,
            dsx3IntervalEntry,
            dsx3TotalEntry,
            dsx3FarEndConfigEntry,
            dsx3FarEndCurrentEntry,
            dsx3FarEndIntervalEntry,
            dsx3FarEndTotalEntry,
            dsx3FracEntry }
        VARIATION   dsx3SendCode
            ACCESS      not-implemented
            DESCRIPTION
                "Management of the type of code being sent across the DS3/E3
                interface is not implemented."
    SUPPORTS    Unisphere-Data-DS3-MIB
        INCLUDES  {
            usdDs3Group5,
            usdDs3FarEndGroup }
    ::= { usdDs3Agent 5 }

END
