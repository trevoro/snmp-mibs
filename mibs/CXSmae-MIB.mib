-- Memotec Enterprise CX PRODUCT MIB
-- May 1994
-- Cheng Wu 

CXSmae-MIB DEFINITIONS ::= BEGIN

IMPORTS
  OBJECT-TYPE
    FROM RFC-1212
  cxSystemManagement
    FROM CXProduct-SMI;


cxSmRestart OBJECT-TYPE
   SYNTAX INTEGER
         {
		 system-idle(0),
         warm-start-save-end(1),
         cold-start (2),
         warm-start-without-save (3)
         }   
   ACCESS read-write
   STATUS mandatory
   DESCRIPTION
"Determines the reset method used throughout the system.

The setting of this object is dynamic. The system immediately implements 
the option you enter.

Options:
warm-start (0): system is idling no action is taken.

warm-start (1): this value is not taking effect immediatelly. When the user sets this object to 1
the system waits till it finishes saving the configuration before it tkes the value then it restarts.

cold-start (2): system reset to factory defaults

warm-start-without-save (3): system reset to previous configuration - no 
save

Default Value: none

Configuration Changed: operative"

   ::= { cxSystemManagement 1 }

cxSmConfig OBJECT-TYPE
   SYNTAX INTEGER
         {
         save (1)
         }   
   ACCESS write-only
   STATUS mandatory
   DESCRIPTION
"Determines the save method used throughout the system.

The setting of this object is dynamic. The system immediately implements 
the option you enter.

Options:

save (1): saves the current configuration into
flash memory. This configuraton will be used in
the next warm start.

Default Value: none

Configuration Changed: operative "

   ::= { cxSystemManagement 2 }


END
