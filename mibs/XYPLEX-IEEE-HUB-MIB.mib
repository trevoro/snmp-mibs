XYPLEX-IEEE-HUB-MIB DEFINITIONS ::= BEGIN
            
                    IMPORTS
                            NetworkAddress, Counter, TimeTicks, enterprises
                                    FROM RFC1155-SMI
                            DisplayString
                                    FROM SNMPv2-TC
                            OBJECT-TYPE
                                    FROM RFC-1212;
            
            xyplex          OBJECT IDENTIFIER ::= { enterprises 33 }
            ieeeHub         OBJECT IDENTIFIER ::= { xyplex 10001 }
            
            -- From this point on, all object descriptors and
            -- identifiers are as specified in [11] except for the
            -- reduction of certain tables to become scalars
            
            hmBasicCapability        OBJECT IDENTIFIER ::= { ieeeHub 1 }
            hmSelfTestCapability     OBJECT IDENTIFIER ::= { ieeeHub 2 }
            hmPerfMonCapability      OBJECT IDENTIFIER ::= { ieeeHub 3 }
            hmAddrTrackCapability    OBJECT IDENTIFIER ::= { ieeeHub 4 }
            hmBadBitClockCapability  OBJECT IDENTIFIER ::= { ieeeHub 5 }
            
            --  This MIB module uses the extended OBJECT-TYPE macro as
            --  defined in [9]
            
            --  this is the IEEE 802 model MIB module for Xyplex
            --  Ethernet hubs
















            
            

            
            
            
            
            -- the IEEE 802 Hub group
            
            -- Implementation of this group is mandatory for all Xyplex
            -- Ethernet hubs
            
            -- the basic group
            
            -- IEEE 802 specifies a hub table, Xyplex does not
            
            hmBasicHubTable          OBJECT IDENTIFIER ::=
                                              { hmBasicCapability 1 }
            hmBasicHubEntry          OBJECT IDENTIFIER ::=
                                              { hmBasicHubTable 1 }
            hubID OBJECT-TYPE
                SYNTAX OCTET STRING (SIZE (6))
                ACCESS read-only
                STATUS mandatory
                DESCRIPTION
                    "The hub's Ethernet address."
                ::= { hmBasicHubEntry 1 }
            
            hubGroupCapacity OBJECT-TYPE
                SYNTAX INTEGER (1..255)
                ACCESS read-only
                STATUS mandatory
                DESCRIPTION
                    "The maximum number of groups the hub can have; a 
                    constant 1."
                ::= { hmBasicHubEntry 2 }
            
            hubGroupMap OBJECT-TYPE
                SYNTAX OCTET STRING (SIZE (32))
                ACCESS read-only
                STATUS mandatory
                DESCRIPTION
                    "A bit map of defined groups."
                ::= { hmBasicHubEntry 3 }
            
            -- IEEE 802 specifies a group table, Xyplex does not
            
            hmBasicGroupTable        OBJECT IDENTIFIER ::=
                                              { hmBasicCapability 2 }
            hmBasicGroupEntry        OBJECT IDENTIFIER ::=
                                              { hmBasicGroupTable 1 }
            
            groupHubID OBJECT-TYPE

            
            

            
            
            
            
                SYNTAX OCTET STRING (SIZE (6))
                ACCESS read-only
                STATUS mandatory
                DESCRIPTION
                    "The hub's Ethernet address."
                ::= { hmBasicGroupEntry 1 }
            
            groupID OBJECT-TYPE
                SYNTAX INTEGER (1..255)
                ACCESS read-only
                STATUS mandatory
                DESCRIPTION
                    "The identification number of the hub's only group; 
                    a constant 1."
                ::= { hmBasicGroupEntry 2 }
            
            groupNumberOfPorts OBJECT-TYPE
                SYNTAX INTEGER (1..255)
                ACCESS read-only
                STATUS mandatory
                DESCRIPTION
                    "The number of physical Ethernet ports on the hub."
                ::= { hmBasicGroupEntry 3 }























            
            

            
            
            
            
            -- the basic port table
            
            hmBasicPortTable OBJECT-TYPE
                SYNTAX SEQUENCE OF HmBasicPortEntry
                ACCESS not-accessible
                STATUS mandatory
                DESCRIPTION
                    "A list of basic hub Ethernet port entries."
                ::= { hmBasicCapability 3 }
            
            hmBasicPortEntry OBJECT-TYPE
                SYNTAX HmBasicPortEntry
                ACCESS not-accessible
                STATUS mandatory
                DESCRIPTION
                    "Parameter values for a port."
                INDEX { portHubBasicID }
                ::= { hmBasicPortTable 1 }
            
            HmBasicPortEntry ::=
                SEQUENCE {
                    portHubBasicID
                        OCTET STRING,
                    portGroupBasicID 
                        INTEGER,
                    portBasicID
                        INTEGER,
                    portType
                        INTEGER,
                    portAdminState
                        INTEGER,
                    portAutoPartitionState
                        INTEGER
                }
            
            portHubBasicID OBJECT-TYPE
                SYNTAX OCTET STRING (SIZE (6))
                ACCESS read-only
                STATUS mandatory
                DESCRIPTION
                    "The hub's Ethernet address."
                ::= { hmBasicPortEntry 1 }
            
            portGroupBasicID OBJECT-TYPE
                SYNTAX INTEGER (1..255)
                ACCESS read-only

            
            

            
            
            
            
                STATUS mandatory
                DESCRIPTION
                    "Group number; a constant 1."
                ::= { hmBasicPortEntry 2 }
            
            portBasicID OBJECT-TYPE
                SYNTAX INTEGER (1..255)
                ACCESS read-only
                STATUS mandatory
                DESCRIPTION
                    "A unique value for each Ethernet port.  Its value 
                    ranges between 1 and the value of 
                    groupNumberOfPorts.  The value for each port must 
                    remain constant at least from one re-initialization 
                    of the network management agent to the next."
                ::= { hmBasicPortEntry 3 }
            
            portType OBJECT-TYPE
                SYNTAX INTEGER { other(1), repeater(2),
                                  tenBASE-FAsync(3), tenBASE-FSynch(4) }
                ACCESS read-only
                STATUS mandatory
                DESCRIPTION
                    "The port type, with the following meanings:
            
                    other               not listed here
                    repeater            802.3 sec. 9 rptr port
                    tenBASE-FAsync(3)   async port on 10BASE-FA
                    tenBASE-FSynch(4)   sync port on 10BASE-FA
                    "
                ::= { hmBasicPortEntry 4 }
            
            portAdminState OBJECT-TYPE
                SYNTAX INTEGER { other(1), disabled(2), enabled(3) }
                ACCESS read-write
                STATUS mandatory
                DESCRIPTION
                    "Control over the port's ability to transmit and 
                    receive.  Corresponds directly to PORT 
                    ENABLED/DISABLED and the value labeled 'State:' in 
                    the PORT display."
                ::= { hmBasicPortEntry 5 }
            
            portAutoPartitionState OBJECT-TYPE
                SYNTAX INTEGER { other(1), notAutoPartitioned(2),
                                 autoPartitioned(3) }

            
            

            
            
            
            
                ACCESS read-only
                STATUS mandatory
                DESCRIPTION
                    "The port's status with regard to automatic 
                    partitioning.  Corresponds directly to the value 
                    labeled 'Auto Partitioned:' in the PORT display."
                ::= { hmBasicPortEntry 6 }







































            
            

            
            
            
            
            -- the self test group
            
            -- IEEE 802 specifies a table, Xyplex does not
            
            hmSelfTestHubTable       OBJECT IDENTIFIER ::=
                                              { hmSelfTestCapability 1 }
            hmSelfTestHubEntry       OBJECT IDENTIFIER ::=
                                              { hmSelfTestHubTable 1 }
            
            hubSelfTestID OBJECT-TYPE
                SYNTAX OCTET STRING (SIZE (6))
                ACCESS read-only
                STATUS mandatory
                DESCRIPTION
                    "The hub's Ethernet address."
                ::= { hmSelfTestHubEntry 1 }
            
            hubResetTimeStamp OBJECT-TYPE
                SYNTAX TimeTicks
                ACCESS read-only
                STATUS mandatory
                DESCRIPTION
                    "The value of sysUpTime when the hub was last 
                    reset."
                ::= { hmSelfTestHubEntry 2 }
            
            hubHealthState OBJECT-TYPE
                SYNTAX  INTEGER { other(1), ok(2), failed(3) }
                ACCESS read-only
                STATUS mandatory
                DESCRIPTION
                    "Indication of hub operational failure."
                ::= { hmSelfTestHubEntry 3 }
            
            hubHealthText OBJECT-TYPE
                SYNTAX DisplayString (SIZE (0..255))
                ACCESS read-only
                STATUS mandatory
                DESCRIPTION
                    "Free form text description of hub operational 
                    state."
                ::= { hmSelfTestHubEntry 4 }
            
            hubHealthData OBJECT-TYPE
                SYNTAX OCTET STRING (SIZE (0..255))
                ACCESS read-only

            
            

            
            
            
            
                STATUS mandatory
                DESCRIPTION
                    "Free form binary data description of hub 
                    operational state."
                ::= { hmSelfTestHubEntry 5 }
            
            hubSystemResetting OBJECT-TYPE
                SYNTAX INTEGER { notResetting(1), resetting(2) }
                ACCESS read-write
                STATUS mandatory
                DESCRIPTION
                    "Control to cause initialization of hub, reset of 
                    management counters, ad reset of hub parameters to 
                    defaults."
                ::= { hmSelfTestHubEntry 6 }
            
            hubResetting OBJECT-TYPE
                SYNTAX INTEGER { notResetting(1), resetting(2) }
                ACCESS read-write
                STATUS mandatory
                DESCRIPTION
                    "Control to cause initialization of the relay and 
                    port counters and flags related to the 
                    auto-partition function.  This does not affect hub 
                    management counters."
                ::= { hmSelfTestHubEntry 7 }
            
            hubExecutingSelfTest OBJECT-TYPE
                SYNTAX INTEGER { notSelfTesting(1), selfTesting(2) }
                ACCESS read-write
                STATUS mandatory
                DESCRIPTION
                    "Control to cause execution of a non-disruptive self 
                    test."
                ::= { hmSelfTestHubEntry 8 }











            
            

            
            
            
            
            -- the performance monitor group
            
            -- IEEE 802 specifies a table, Xyplex does not
            
            hmPerfMonRelayTable      OBJECT IDENTIFIER ::=
                                              { hmPerfMonCapability 1 }
            hmPerfMonRelayEntry      OBJECT IDENTIFIER ::=
                                              { hmPerfMonRelayTable 1 }
            relayHubPerfID OBJECT-TYPE
                SYNTAX OCTET STRING (SIZE (6))
                ACCESS read-only
                STATUS mandatory
                DESCRIPTION
                    "The hub's Ethernet address."
                ::= { hmPerfMonRelayEntry 1 }
            
            relayPerfID OBJECT-TYPE
                SYNTAX INTEGER (1..4)
                ACCESS read-only
                STATUS mandatory
                DESCRIPTION
                    "Relay identification; a constant 1."
                ::= { hmPerfMonRelayEntry 2 }
            
            relayTotalCollisions OBJECT-TYPE
                SYNTAX Counter
                ACCESS read-only
                STATUS mandatory
                DESCRIPTION
                    "The number of times the hub transmitted and 
                    simultaneously detected external activity on one or 
                    more ports."
                ::= { hmPerfMonRelayEntry 3 }













            
            

            
            
            
            
            -- the performance monitoring port table
            
            hmPerfMonPortTable OBJECT-TYPE
                SYNTAX SEQUENCE OF HmPerfMonPortEntry
                ACCESS not-accessible
                STATUS mandatory
                ::= { hmPerfMonCapability 2 }
            
            hmPerfMonPortEntry OBJECT-TYPE
                SYNTAX HmPerfMonPortEntry
                ACCESS not-accessible
                STATUS mandatory
                ::= { hmPerfMonPortTable 1 }
            
            HmPerfMonPortEntry ::=
                SEQUENCE {
                    portHubPerfID
                        OCTET STRING,
                    portGroupPerfID 
                        INTEGER,
                    portPerfID
                        INTEGER,
                    portReadableFrames
                        Counter,
                    portReadableOctets
                        Counter,
                    portPygmys
                        Counter,
                    portRunts
                        Counter,
                    portFrameCheckSeqErrs
                        Counter,
                    portAlignmentErrors
                        Counter,
                    portFramesTooLong
                        Counter,
                    portAutoPartitionCount
                        Counter
                }
            
            portHubPerfID OBJECT-TYPE
                SYNTAX OCTET STRING (SIZE (6))
                ACCESS read-only
                STATUS mandatory
                DESCRIPTION
                    "The hub's Ethernet address."

            
            

            
            
            
            
                ::= { hmPerfMonPortEntry 1 }
            
            portGroupPerfID OBJECT-TYPE
                SYNTAX INTEGER (1..255)
                ACCESS read-only
                STATUS mandatory
                DESCRIPTION
                    "The group number; a constant 1."
                ::= { hmPerfMonPortEntry 2 }
            
            portPerfID OBJECT-TYPE
                SYNTAX INTEGER (1..255)
                ACCESS read-only
                STATUS mandatory
                DESCRIPTION
                    "A unique value for each Ethernet port, identifying 
                    the same port as the equivalent value of 
                    portBasicID."
                ::= { hmPerfMonPortEntry 3 }
            
            portReadableFrames OBJECT-TYPE
                SYNTAX Counter
                ACCESS read-only
                STATUS mandatory
                DESCRIPTION
                    "Number of frames received with legal length and no 
                    corruption in transmission.  Corresponds directly 
                    with the value labeled 'Received Frames:' in the 
                    PORT display."
                ::= { hmPerfMonPortEntry 4 }
            
            portReadableOctets OBJECT-TYPE
                SYNTAX Counter
                ACCESS read-only
                STATUS mandatory
                DESCRIPTION
                    "The number of data and padding bytes represented by 
                    portReadableFrames."
                ::= { hmPerfMonPortEntry 5 }
            
            portPygmys OBJECT-TYPE
                SYNTAX Counter
                ACCESS read-only
                STATUS mandatory
                DESCRIPTION
                    "Number of message fragments less than 64 +/- 10 

            
            

            
            
            
            
                            bits long, possibly indicating external noise 
                    problems.  Corresponds directly with the value 
                    labeled 'Fragments (Pygmy):' in the PORT display."
                ::= { hmPerfMonPortEntry 6 }
            
            portRunts OBJECT-TYPE
                SYNTAX Counter
                ACCESS read-only
                STATUS mandatory
                DESCRIPTION
                    "Number of collision fragments longer than a pygmy 
                    but shorter than a legal message.  These occur as a 
                    result of normal collision operation.  Corresponds 
                    directly with the value labeled 'Short Frames 
                    (Runt):' in the PORT display."
                ::= { hmPerfMonPortEntry 7 }
            
            portFrameCheckSeqErrs OBJECT-TYPE
                SYNTAX Counter
                ACCESS read-only
                STATUS mandatory
                DESCRIPTION
                    "Number of frames received with integral bytes but 
                    invalid FCS.  Corresponds directly with the value 
                    labeled 'Check Sequenct (CRC):' in the PORT 
                    display."
                ::= { hmPerfMonPortEntry 8 }
            
            portAlignmentErrors OBJECT-TYPE
                SYNTAX Counter
                ACCESS read-only
                STATUS mandatory
                DESCRIPTION
                    "Number of frames received with an incomplete 
                    bytes."
                ::= { hmPerfMonPortEntry 9 }
            
            portFramesTooLong OBJECT-TYPE
                SYNTAX Counter
                ACCESS read-only
                STATUS mandatory
                DESCRIPTION
                    "Number of frames received of length greater than 
                    1518 bytes.  Corresponds directly with the value 
                    labeled 'Long Frames (>1518):' in the PORT 
                    display."

            
            

            
            
            
            
                ::= { hmPerfMonPortEntry 10 }
            
            portAutoPartitionCount OBJECT-TYPE
                SYNTAX Counter
                ACCESS read-only
                STATUS mandatory
                DESCRIPTION
                    "Number of times the repeater has automatically 
                    partitioned the port.  Corresponds directly with the 
                    value labeled 'Auto Partitions:' in the PORT 
                    display."
                ::= { hmPerfMonPortEntry 11 }


































            
            

            
            
            
            
            -- the address tracking port table
            
            hmAddrTrackPortTable OBJECT-TYPE
                SYNTAX SEQUENCE OF HmAddrTrackPortEntry
                ACCESS not-accessible
                STATUS mandatory
                ::= { hmAddrTrackCapability 1 }
            
            hmAddrTrackPortEntry OBJECT-TYPE
                SYNTAX HmAddrTrackPortEntry
                ACCESS not-accessible
                STATUS mandatory
                ::= { hmAddrTrackPortTable 1 }
            
            HmAddrTrackPortEntry ::=
                SEQUENCE {
                    portHubAddrID
                        OCTET STRING,
                    portGroupAddrID 
                        INTEGER,
                    portAddrID
                        INTEGER,
                    portLastSourceAddress
                        NetworkAddress,
                    portSourceAddrChanges
                        Counter
                }
            
            portHubAddrID OBJECT-TYPE
                SYNTAX OCTET STRING (SIZE (6))
                ACCESS read-only
                STATUS mandatory
                DESCRIPTION
                    "The hub's Ethernet address."
                ::= { hmAddrTrackPortEntry 1 }
            
            portGroupAddrID OBJECT-TYPE
                SYNTAX INTEGER (1..255)
                ACCESS read-only
                STATUS mandatory
                DESCRIPTION
                    "The group number; a constant 1."
                ::= { hmAddrTrackPortEntry 2 }
            
            portAddrID OBJECT-TYPE
                SYNTAX INTEGER (1..255)

            
            

            
            
            
            
                ACCESS read-only
                STATUS mandatory
                DESCRIPTION
                    "A unique value for each Ethernet port, identifying 
                    the same port as the equivalent value of 
                    portBasicID."
                ::= { hmAddrTrackPortEntry 3 }
            
            portLastSourceAddress OBJECT-TYPE
                SYNTAX OCTET STRING (SIZE (6))
                ACCESS read-only
                STATUS mandatory
                DESCRIPTION
                    "Source address of the last readable frame received 
                    on the port.  Corresponds directly with the value 
                    labeled 'Last Address:' in the PORT display."
                ::= { hmAddrTrackPortEntry 4 }
            
            portSourceAddrChanges OBJECT-TYPE
                SYNTAX Counter
                ACCESS read-only
                STATUS mandatory
                DESCRIPTION
                    "Number of times portLastSourceAddress has changed.  
                    Corresponds directly with the value labeled 'Address 
                    Changes:' in the PORT display."
                ::= { hmAddrTrackPortEntry 5 }



















            
            

            
            
            
            
            -- bad bit clock port table
            
            hmBadBitClockPortTable OBJECT-TYPE
                SYNTAX SEQUENCE OF HmBadBitClockPortEntry
                ACCESS not-accessible
                STATUS mandatory
                ::= { hmBadBitClockCapability 1 }
            
            hmBadBitClockPortEntry OBJECT-TYPE
                SYNTAX HmBadBitClockPortEntry
                ACCESS not-accessible
                STATUS mandatory
                ::= { hmBadBitClockPortTable 1 }
            
            HmBadBitClockPortEntry ::=
                SEQUENCE {
                    portHubClockID
                        OCTET STRING,
                    portGroupClockID 
                        INTEGER,
                    portClockID
                        INTEGER,
                    portOutOfSpecBitRate
                        Counter
                }
            
            portHubClockID OBJECT-TYPE
                SYNTAX OCTET STRING (SIZE (6))
                ACCESS read-only
                STATUS mandatory
                DESCRIPTION
                    "The hub's Ethernet address."
                ::= { hmBadBitClockPortEntry 1 }
            
            portGroupClockID OBJECT-TYPE
                SYNTAX INTEGER (1..255)
                ACCESS read-only
                STATUS mandatory
                DESCRIPTION
                    "The group number; a constant 1."
                ::= { hmBadBitClockPortEntry 2 }
            
            portClockID OBJECT-TYPE
                SYNTAX INTEGER (1..255)
                ACCESS read-only
                STATUS mandatory

            
            

            
            
            
            
                DESCRIPTION
                    "A unique value for each Ethernet port, identifying 
                    the same port as the equivalent value of 
                    portBasicID."
                ::= { hmBadBitClockPortEntry 3 }
            
            portOutOfSpecBitRate OBJECT-TYPE
                SYNTAX Counter
                ACCESS read-only
                STATUS mandatory
                DESCRIPTION
                    "Number of received frames with the transmission 
                    frequency detectably out of specification.  
                    Corresponds directly with the value labeled 'Out of 
                    Spec. Bit Rate:' in the PORT display."
                ::= { hmBadBitClockPortEntry 4 }
            
END
