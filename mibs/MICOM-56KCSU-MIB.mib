-- Based on 56K CSU/DSU Functional Specification document (Rev 1.0, dated 8/6/97).
-- 
-- MIB Revision : 1.0 dated 8-6-97
-- Change Desc. : Initial submittal - R. Carmona. 
-- 
-- MIB Revision : 1.1 dated 8-15-97
-- Change Desc. : Replace mcm56KCsuStatusRcvrActive with
--		  mcm56KCsuStatusLineStatus. - R. Carmona.
-- 
-- MIB Revision : 1.2 dated 10-7-97
-- Change Desc. : Replaced MPA with 4400, and other minor changes - B. Jafari. 
-- 
-- ** RELEASE 3.0 **
-- MIB Revision : 1.3 dated 6-1-98
-- Change Desc. : Deprecated group mcm56kCsuCfgGroup and replaced it
--                   with table mcm56kCsuCfgTable.
--                Obsoleted group nvm56kCsuCfgGroup.
--                Deprecated group mcm56KCsuStatusGroup and replaced it with
--                   table mcm56kCsuStatusTable.
--                All 56K CSU replacement tables reside in MIB module: mcmcsu.mib.
--                Replaced '4400' with 'access device'.
--                - R. Carmona, S. Gaur, A. Llanes


MICOM-56KCSU-MIB DEFINITIONS ::= BEGIN
	
IMPORTS
	OBJECT-TYPE
		FROM RFC-1212
	micom-oscar 
		FROM MICOM-OSCAR-MIB;


-- group OBJECT IDENTIFIERs

	micom-56kcsu			OBJECT IDENTIFIER ::= {micom-oscar 28}
	csu56k-configuration		OBJECT IDENTIFIER ::= {micom-56kcsu 1}
	csu56k-status			OBJECT IDENTIFIER ::= {micom-56kcsu 2}


-- *** CONFIGURATION groups/tables ***

-- Note: The following groups contain 2 related groups/tables for all configuration
--       functionality. 
--	 1) The Standard or Operational Parameters (Operational) provide the
--	 SNMP management interface with the access device operational modules.
--	 Objects defined for this interface begin with the 'mcm' prefix.
--	 2) The Configuration Parameters (Configuration) provide the SNMP 
--	 management interface with a stored access device configuration. 
--	 Objects defined for this interface begin with the 'nvm' prefix.
--	


--  Operational Parameter ("mcm") Groups/Tables


--  the 56K CSU Configuration Group 
--  (Standard/Operational Parameters)

--  THE OBJECTS IN THE FOLLOWING GROUP (mcm56kCsuCfgGroup) 
--  HAVE BEEN DEPRECATED (beginning with Release 3.0) AND REPLACED
--  BY THE TABLE mcm56kCsuCfgTable (see mcmcsu.mib MIB module).

--  This group provides the 56K CSU configuration parameters.

mcm56kCsuCfgGroup  OBJECT IDENTIFIER ::= { csu56k-configuration 1 }

mcm56kCsuCfgOperatingMode OBJECT-TYPE
	SYNTAX	INTEGER {
		dds-pri-4Wire-56k (1),
		dds-sc-WithSecondaryChannel-72k (2),
		cc-64k-ClearChannel-64k (3),
		dds-pri-2Wire-56k (4)
		}
	ACCESS	read-write
	STATUS	deprecated	
	DESCRIPTION
	  "NAME = ;
	   DESC = The value of this object selects the 56K CSU \
		  operating mode. (Operational);
	   HELP = ;
	   CAPABILITIES = NET_CFG, VPN_CFG;"
	DEFVAL { dds-pri-4Wire-56k }
	::= { mcm56kCsuCfgGroup 1 }

mcm56kCsuCfgClockingSource OBJECT-TYPE
	SYNTAX	INTEGER {
		externalClock (1),
		internalClock (2)
		}
	ACCESS	read-write
	STATUS	deprecated	
	DESCRIPTION
	  "NAME = ;
	   DESC = The value of this object selects the 56K CSU \
		  clocking source. (Operational);
	   HELP = ;
	   CAPABILITIES = NET_CFG, VPN_CFG;"
	DEFVAL { externalClock }
	::= { mcm56kCsuCfgGroup 2 }

mcm56kCsuCfgTxOutOfFrame OBJECT-TYPE
	SYNTAX	INTEGER {
		normalTransmitCondition (1),
		transmitOutOfFrame (2)
		}
	ACCESS	read-write
	STATUS	deprecated	
	DESCRIPTION
	  "NAME = ;
	   DESC = This object selects transmission of the 56K CSU \
		  Out Of Frame sequence for DDS-PRI mode, or \
		  transmission of Multiplexer Out Of Sync \
		  sequence for DDS-SC mode. (Operational);
	   HELP = ;
	   CAPABILITIES = NET_CFG, VPN_CFG;"
	DEFVAL { normalTransmitCondition }
	::= { mcm56kCsuCfgGroup 3 }

mcm56kCsuCfgTxOutOfService OBJECT-TYPE
	SYNTAX	INTEGER {
		normalTransmitCondition (1),
		transmitOutOfService (2)
		}
	ACCESS	read-write
	STATUS	deprecated	
	DESCRIPTION
	  "NAME = ;
	   DESC = This object selects transmission of the 56K CSU \
		  Out Of Service sequence for DDS-PRI mode, or \
		  transmission of Abnormal Station Code \
		  sequence for DDS-SC mode. (Operational);
	   HELP = ;
	   CAPABILITIES = NET_CFG, VPN_CFG;"
	DEFVAL { normalTransmitCondition }
	::= { mcm56kCsuCfgGroup 4 }

mcm56kCsuCfgTxControlModeIdle OBJECT-TYPE
	SYNTAX	INTEGER {
		normalTransmitCondition (1),
		transmitControlModeIdle (2)
		}
	ACCESS	read-write
	STATUS	deprecated	
	DESCRIPTION
	  "NAME = ;
	   DESC = This object selects transmission of the 56K CSU \
		  Control Mode Idle sequence. (Operational);
	   HELP = ;
	   CAPABILITIES = NET_CFG, VPN_CFG;"
	DEFVAL { normalTransmitCondition }
	::= { mcm56kCsuCfgGroup 5 }

mcm56kCsuCfgZeroSuppressDisable OBJECT-TYPE
	SYNTAX	INTEGER {
		normalTransmitCondition (1),
		zeroSuppressionDisable (2)
		}
	ACCESS	read-write
	STATUS	deprecated	
	DESCRIPTION
	  "NAME = ;
	   DESC = This object selects the 56K CSU disable \
		  transmit Zero Suppression for DDS-PRI mode, \
		  or transmission of all zeros for DDS-SC mode. \
		  (Operational);
	   HELP = ;
	   CAPABILITIES = NET_CFG, VPN_CFG;"
	DEFVAL { normalTransmitCondition }
	::= { mcm56kCsuCfgGroup 6 }

mcm56kCsuCfgTxIdle OBJECT-TYPE
	SYNTAX	INTEGER {
		normalTransmitCondition (1),
		transmitIdle (2)
		}
	ACCESS	read-write
	STATUS	deprecated	
	DESCRIPTION
	  "NAME = ;
	   DESC = This object selects transmission of the 56K CSU \
		  All Marks (or 1s) of the Data Mode Idle sequence \
		  for all the modes. (Operational);
	   HELP = ;
	   CAPABILITIES = NET_CFG, VPN_CFG;"
	DEFVAL { normalTransmitCondition }
	::= { mcm56kCsuCfgGroup 7 }

mcm56kCsuCfgCSULoopback OBJECT-TYPE
	SYNTAX	INTEGER {
		normalReceiveCondition (1),
		forceCSUtoLoopback (2)
		}
	ACCESS	read-write
	STATUS	deprecated	
	DESCRIPTION
	  "NAME = ;
	   DESC = This object selects the 56K CSU to force the CSU \
		  to be in a loopback mode. (Operational);
	   HELP = ;
	   CAPABILITIES = NET_CFG, VPN_CFG;"
	DEFVAL { normalReceiveCondition }
	::= { mcm56kCsuCfgGroup 8 }

mcm56kCsuCfgFilterForceEnable OBJECT-TYPE
	SYNTAX	INTEGER {
		normalReceiveCondition (1),
		filterForceEnable (2)
		}
	ACCESS	read-write
	STATUS	deprecated	
	DESCRIPTION
	  "NAME = ;
	   DESC = This object selects the 56K CSU to have \
		  filter forcing enabled or not. (Operational);
	   HELP = ;
	   CAPABILITIES = NET_CFG, VPN_CFG;"
	DEFVAL { normalReceiveCondition }
	::= { mcm56kCsuCfgGroup 9 }

mcm56kCsuCfgFilterForcingCntl OBJECT-TYPE
	SYNTAX	INTEGER {
		filterGain-90db (1),
		filterGain-84db (2),
		filterGain-78db (3),
		filterGain-72db (4),
		filterGain-66db (5),
		filterGain-60db (6),
		filterGain-54db (7),
		filterGain-48db (8),
		filterGain-42db (9),
		filterGain-36db (10),
		filterGain-30db (11),
		filterGain-24db (12),
		filterGain-18db (13),
		filterGain-12db (14),
		filterGain-6db (15),
		filterGain-0db (16)
		}
	ACCESS	read-write
	STATUS	deprecated	
	DESCRIPTION
	  "NAME = ;
	   DESC = This object selects the 56K CSU filter \
		  gain if filter force is enabled. (Operational);
	   HELP = ;
	   CAPABILITIES = NET_CFG, VPN_CFG;"
	DEFVAL { filterGain-0db }
	::= { mcm56kCsuCfgGroup 10 }


--  "Parallel" Configuration Parameter ("nvm") Groups/Tables


--  the 56K CSU Configuration Group 
--  (Configuration Parameters)

--  THE OBJECTS IN THE FOLLOWING GROUP (nvm56kCsuCfgGroup) 
--  HAVE BEEN OBSOLETED (beginning with Release 3.0). 

nvm56kCsuCfgGroup  OBJECT IDENTIFIER ::= { csu56k-configuration 2 }

nvm56kCsuCfgOperatingMode OBJECT-TYPE
	SYNTAX	INTEGER {
		dds-pri-4Wire-56k (1),
		dds-sc-WithSecondaryChannel-72k (2),
		cc-64k-ClearChannel-64k (3),
		dds-pri-2Wire-56k (4)
		}
	ACCESS	read-only
	STATUS	obsolete	
	DESCRIPTION
	  "NAME = ;
	   DESC = The value of this object selects the 56K CSU \
		  operating mode. (Configuration);
	   HELP = ;
	   CAPABILITIES = NET_CFG, VPN_CFG;"
	DEFVAL { dds-pri-4Wire-56k }
	::= { nvm56kCsuCfgGroup 1 }

nvm56kCsuCfgClockingSource OBJECT-TYPE
	SYNTAX	INTEGER {
		externalClock (1),
		internalClock (2)
		}
	ACCESS	read-only
	STATUS	obsolete
	DESCRIPTION
	  "NAME = ;
	   DESC = The value of this object selects the 56K CSU \
		  clocking source. (Configuration);
	   HELP = ;
	   CAPABILITIES = NET_CFG, VPN_CFG;"
	DEFVAL { externalClock }
	::= { nvm56kCsuCfgGroup 2 }

nvm56kCsuCfgTxOutOfFrame OBJECT-TYPE
	SYNTAX	INTEGER {
		normalTransmitCondition (1),
		transmitOutOfFrame (2)
		}
	ACCESS	read-only
	STATUS	obsolete
	DESCRIPTION
	  "NAME = ;
	   DESC = This object selects transmission of the 56K CSU \
		  Out Of Frame sequence for DDS-PRI mode, or \
		  transmission of Multiplexer Out Of Sync \
		  sequence for DDS-SC mode. (Configuration);
	   HELP = ;
	   CAPABILITIES = NET_CFG, VPN_CFG;"
	DEFVAL { normalTransmitCondition }
	::= { nvm56kCsuCfgGroup 3 }

nvm56kCsuCfgTxOutOfService OBJECT-TYPE
	SYNTAX	INTEGER {
		normalTransmitCondition (1),
		transmitOutOfService (2)
		}
	ACCESS	read-only
	STATUS	obsolete
	DESCRIPTION
	  "NAME = ;
	   DESC = This object selects transmission of the 56K CSU \
		  Out Of Service sequence for DDS-PRI mode, or \
		  transmission of Abnormal Station Code \
		  sequence for DDS-SC mode. (Configuration);
	   HELP = ;
	   CAPABILITIES = NET_CFG, VPN_CFG;"
	DEFVAL { normalTransmitCondition }
	::= { nvm56kCsuCfgGroup 4 }

nvm56kCsuCfgTxControlModeIdle OBJECT-TYPE
	SYNTAX	INTEGER {
		normalTransmitCondition (1),
		transmitControlModeIdle (2)
		}
	ACCESS	read-only
	STATUS	obsolete
	DESCRIPTION
	  "NAME = ;
	   DESC = This object selects transmission of the 56K CSU \
		  Control Mode Idle sequence. (Configuration);
	   HELP = ;
	   CAPABILITIES = NET_CFG, VPN_CFG;"
	DEFVAL { normalTransmitCondition }
	::= { nvm56kCsuCfgGroup 5 }

nvm56kCsuCfgZeroSuppressDisable OBJECT-TYPE
	SYNTAX	INTEGER {
		normalTransmitCondition (1),
		zeroSuppressionDisable (2)
		}
	ACCESS	read-only
	STATUS	obsolete
	DESCRIPTION
	  "NAME = ;
	   DESC = This object selects the 56K CSU disable \
		  transmit Zero Suppression for DDS-PRI mode, \
		  or transmission of all zeros for DDS-SC mode. \
		  (Configuration);
	   HELP = ;
	   CAPABILITIES = NET_CFG, VPN_CFG;"
	DEFVAL { normalTransmitCondition }
	::= { nvm56kCsuCfgGroup 6 }

nvm56kCsuCfgTxIdle OBJECT-TYPE
	SYNTAX	INTEGER {
		normalTransmitCondition (1),
		transmitIdle (2)
		}
	ACCESS	read-only
	STATUS	obsolete
	DESCRIPTION
	  "NAME = ;
	   DESC = This object selects transmission of the 56K CSU \
		  All Marks (or 1s) of the Data Mode Idle sequence \
		  for all the modes. (Configuration);
	   HELP = ;
	   CAPABILITIES = NET_CFG, VPN_CFG;"
	DEFVAL { normalTransmitCondition }
	::= { nvm56kCsuCfgGroup 7 }

nvm56kCsuCfgCSULoopback OBJECT-TYPE
	SYNTAX	INTEGER {
		normalReceiveCondition (1),
		forceCSUtoLoopback (2)
		}
	ACCESS	read-only
	STATUS	obsolete
	DESCRIPTION
	  "NAME = ;
	   DESC = This object selects the 56K CSU to force the CSU \
		  to be in a loopback mode. (Configuration);
	   HELP = ;
	   CAPABILITIES = NET_CFG, VPN_CFG;"
	DEFVAL { normalReceiveCondition }
	::= { nvm56kCsuCfgGroup 8 }

nvm56kCsuCfgFilterForceEnable OBJECT-TYPE
	SYNTAX	INTEGER {
		normalReceiveCondition (1),
		filterForceEnable (2)
		}
	ACCESS	read-only
	STATUS	obsolete
	DESCRIPTION
	  "NAME = ;
	   DESC = This object selects the 56K CSU to have \
		  filter forcing enabled or not. (Configuration);
	   HELP = ;
	   CAPABILITIES = NET_CFG, VPN_CFG;"
	DEFVAL { normalReceiveCondition }
	::= { nvm56kCsuCfgGroup 9 }

nvm56kCsuCfgFilterForcingCntl OBJECT-TYPE
	SYNTAX	INTEGER {
		filterGain-90db (1),
		filterGain-84db (2),
		filterGain-78db (3),
		filterGain-72db (4),
		filterGain-66db (5),
		filterGain-60db (6),
		filterGain-54db (7),
		filterGain-48db (8),
		filterGain-42db (9),
		filterGain-36db (10),
		filterGain-30db (11),
		filterGain-24db (12),
		filterGain-18db (13),
		filterGain-12db (14),
		filterGain-6db (15),
		filterGain-0db (16)
		}
	ACCESS	read-only
	STATUS	obsolete
	DESCRIPTION
	  "NAME = ;
	   DESC = This object selects the 56K CSU filter \
		  gain if filter force is enabled. (Configuration);
	   HELP = ;
	   CAPABILITIES = NET_CFG, VPN_CFG;"
	DEFVAL { filterGain-0db }
	::= { nvm56kCsuCfgGroup 10 }


-- *** STATUS groups/tables ***

--  Operational Parameter ("mcm") Groups/Tables (note: no parallel "nvm" objects
--  are defined for STATUS parameters.)

--  THE OBJECTS IN THE FOLLOWING GROUP (mcm56KCsuStatusGroup) 
--  HAVE BEEN DEPRECATED (beginning with Release 3.0) AND REPLACED
--  BY THE TABLE mcm56kCsuStatusTable (see mcmcsu.mib MIB module).

--  the 56K CSU Status Group

--  This group provides the 56K CSU status objects.

mcm56KCsuStatusGroup  OBJECT IDENTIFIER ::= { csu56k-status 1 }

mcm56KCsuStatusLineStatus OBJECT-TYPE
	SYNTAX	INTEGER {
		operational (1),
		linkDown (2),
		testMode (3)
		}
	ACCESS	read-only
	STATUS	deprecated	
	DESCRIPTION
	  "NAME = ;
	   DESC = The value of this object indicates the 56K \
		  CSU line status.;
	   HELP = ;
	   CAPABILITIES = NET_CFG, VPN_CFG ;"
	::= { mcm56KCsuStatusGroup 1 }

mcm56KCsuStatusRxLossOfSignal OBJECT-TYPE
	SYNTAX	INTEGER {
		yes (1),
		no (2)
		}
	ACCESS	read-only
	STATUS	deprecated	
	DESCRIPTION
	  "NAME = ;
	   DESC = The value of this object indicates if the 56K \
		  CSU receiver has lost signal.;
	   HELP = ;
	   CAPABILITIES = NET_CFG, VPN_CFG ;"
	::= { mcm56KCsuStatusGroup 2 }

mcm56KCsuStatusFAWSync OBJECT-TYPE
	SYNTAX	INTEGER {
		yes (1),
		no (2)
		}
	ACCESS	read-only
	STATUS	deprecated	
	DESCRIPTION
	  "NAME = ;
	   DESC = The value of this object indicates the 56K \
		  CSU DDS FAW Sync in DDS-SC or CC-64K.;
	   HELP = ;
	   CAPABILITIES = NET_CFG, VPN_CFG ;"
	::= { mcm56KCsuStatusGroup 3 }

mcm56KCsuStatusLoopPresent OBJECT-TYPE
	SYNTAX	INTEGER {
		yes (1),
		no (2)
		}
	ACCESS	read-only
	STATUS	deprecated	
	DESCRIPTION
	  "NAME = ;
	   DESC = The value of this object indicates if the 56K \
		  CSU loop is currently present.;
	   HELP = ;
	   CAPABILITIES = NET_CFG, VPN_CFG ;"
	::= { mcm56KCsuStatusGroup 4 }

mcm56KCsuStatusInsertLossLineLength OBJECT-TYPE
	SYNTAX	INTEGER
	ACCESS	read-only
	STATUS	deprecated	
	DESCRIPTION
	  "NAME = ;
	   DESC = The value of this object indicates the 56K \
		  CSU receiver line length.;
	   HELP = ;
	   CAPABILITIES = NET_CFG, VPN_CFG ;"
	::= { mcm56KCsuStatusGroup 5 }

mcm56KCsuStatusRxSignalMag OBJECT-TYPE
	SYNTAX	INTEGER
	ACCESS	read-only
	STATUS	deprecated	
	DESCRIPTION
	  "NAME = ;
	   DESC = The value of this object indicates the 56K \
		  CSU receive signal magnitude.;
	   HELP = ;
	   CAPABILITIES = NET_CFG, VPN_CFG ;"
	::= { mcm56KCsuStatusGroup 6 }

mcm56KCsuStatusInvalidBPVcount OBJECT-TYPE
	SYNTAX	INTEGER
	ACCESS	read-only
	STATUS	deprecated	
	DESCRIPTION
	  "NAME = ;
	   DESC = The value of this object indicates the 56K \
		  CSU invalid Bipolar Violation (BPV) count.;
	   HELP = ;
	   CAPABILITIES = NET_CFG, VPN_CFG ;"
	::= { mcm56KCsuStatusGroup 7 }


END
