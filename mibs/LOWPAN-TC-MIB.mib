-- extracted from draft-daniel-lowpan-mib-00.txt
-- at Thu Mar  1 06:08:22 2007

LOWPAN-TC-MIB DEFINITIONS ::= BEGIN
       IMPORTS
              TEXTUAL-CONVENTION
                FROM SNMPv2-TC
              MODULE-IDENTITY, mib-2
                FROM SNMPv2-SMI;


        -- definition of textual conventions

    lowpanTCMIB    MODULE-IDENTITY
        LAST-UPDATED    "200701231307Z"
        ORGANIZATION    "IETF 6lowpan Working Group"
        CONTACT-INFO    "Ki-Hyung Kim, Editor
                        Ajou University
                        San 5 Wonchun-dong, Yeongtong-gu
                        Suwon-si, Gyeonggi-do  442-749
                        KOREA

                        Phone: +82 31 219 2433
                        Email: kkim86@ajou.ac.kr


                        Seung Wha Yoo
                        Ajou University
                        San 5 Wonchun-dong, Yeongtong-gu
                        Suwon-si, Gyeonggi-do  442-749
                        KOREA

                        Phone: +82 31 219 1603
                        Email: swyoo@ajou.ac.kr


                        Hamid Mukhtar
                        Ajou University
                        San 5 Wonchun-dong, Yeongtong-gu
                        Suwon-si, Gyeonggi-do  442-749
                        KOREA

                        Phone: +82 10 2892 2469
                        Email: hamid@ajou.ac.kr


                        Soohong Daniel Park, Editor
                        Mobile Platform Laboratory, SAMSUNG Electronics
                        416 Maetan-3dong, Yeongtong-gu
                        Suwon-si, Gyeonggi-do  442-742
                        KOREA

                        Phone: +82 31 200 4508
                        Email: soohong.park@samsung.com

                        Support Group E-mail: 6lowpan@ietf.org"

        DESCRIPTION     "A MIB module containing textual conventions
                        for 6lowpan data types. This module
                        addresses an immediate need for data types not
                        directly supported in the SMIv2.

                        Copyright (C) The Internet Society 2007.  This
                        version of this MIB module is part of RFC XXXX;
                        see the RFC itself for full legal notices."
      -- RFC Ed.: replace XXXX with actual RFC number & remove this note

        REVISION        "200701231307Z"
        DESCRIPTION        "Initial version, published as RFC XXXX."
    -- RFC Ed.: replace XXXX with actual RFC number & remove this note

        ::=  {  mib-2  1  } -- will be assigned by IANA

      -- IANA Reg.: Please assign a value for "XXX" under the 'mib-2'
      -- subtree and record the assignment in the SMI Numbers registry.

      -- RFC Ed.: When the above assignment has been made, please
      --     remove the above note
      --     replace "XXX" here with the assigned value and
      --     remove this note.

       LowpanIEEEEUI64Address ::= TEXTUAL-CONVENTION
              DISPLAY-HINT "1x:"
              STATUS        current
              DESCRIPTION
                      "The IEEE defined 64-bit extended unique
                      identifier (EUI-64) is a concatenation of the
                      24-bit company_id value by the IEEE Registration
                      Authority and a 40-bit extension identifier
                      assigned by the organization with that company_id
                      assignment."
              REFERENCE
                      "IEEE 64-BIT GLOBAL IDENTIFIER (EUI64)" 
              SYNTAX  OCTET STRING (SIZE (8))

        LowpanShortAddress ::= TEXTUAL-CONVENTION
             DISPLAY-HINT "1x:"
             STATUS       current
             DESCRIPTION
                      "The 16-bit Short Address used for 802.15.4
                      networks."
             REFERENCE
                      "IEEE Std 802.15.4 specifications"
             SYNTAX       OCTET STRING (SIZE (2))

       END

-- 
--    Copyright (C) The IETF Trust (2007).
-- 
--    This document is subject to the rights, licenses and restrictions
--    contained in BCP 78, and except as set forth therein, the authors
--    retain all their rights.
-- 
--    This document and the information contained herein are provided on an
--    "AS IS" basis and THE CONTRIBUTOR, THE ORGANIZATION HE/SHE REPRESENTS
--    OR IS SPONSORED BY (IF ANY), THE INTERNET SOCIETY, THE IETF TRUST AND
--    THE INTERNET ENGINEERING TASK FORCE DISCLAIM ALL WARRANTIES, EXPRESS
--    OR IMPLIED, INCLUDING BUT NOT LIMITED TO ANY WARRANTY THAT THE USE OF
--    THE INFORMATION HEREIN WILL NOT INFRINGE ANY RIGHTS OR ANY IMPLIED
--    WARRANTIES OF MERCHANTABILITY OR FITNESS FOR A PARTICULAR PURPOSE.
-- 
-- Intellectual Property
-- 
--    The IETF takes no position regarding the validity or scope of any
--    Intellectual Property Rights or other rights that might be claimed to
--    pertain to the implementation or use of the technology described in
--    this document or the extent to which any license under such rights
--    might or might not be available; nor does it represent that it has
--    made any independent effort to identify any such rights.  Information
--    on the procedures with respect to rights in RFC documents can be
--    found in BCP 78 and BCP 79.
-- 
--    Copies of IPR disclosures made to the IETF Secretariat and any
--    assurances of licenses to be made available, or the result of an
--    attempt made to obtain a general license or permission for the use of
--    such proprietary rights by implementers or users of this
--    specification can be obtained from the IETF on-line IPR repository at
--    http://www.ietf.org/ipr.
-- 
--    The IETF invites any interested party to bring to its attention any
--    copyrights, patents or patent applications, or other proprietary
--    rights that may cover technology that may be required to implement
--    this standard.  Please address the information to the IETF at
--    ietf-ipr@ietf.org.
--
