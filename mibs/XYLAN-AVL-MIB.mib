XYLAN-AVL-MIB DEFINITIONS ::= BEGIN

     --  xylan-avl.mib
     --  Revision: 2.10
     --  Date: July 10, 1997

     --  Alcatel Internetworking, Inc.
     --  26801 W. Agoura Road
     --  Calabasas, CA 91301
     --  (818) 880-3500
     --  support@ind.alcatel.com

     --  This module provides authoritative definitions for Alcatel Internetworking, Inc.
     --  enterprise-specific AVL(Authenticated VLAN) MIB.

     --  This module will be extended, as needed.


     --  Alcatel Internetworking, Inc. reserves the right to make changes in 
     --  specification and other information contained in this document 
     --  without prior notice.  The reader should consult Alcatel Internetworking,
     --  Inc. to determine whether any such changes have been made.
     --  Current MIBs are availible from the following URLs:
     --			ftp://ftp.ind.alcatel.com/pub/products/mibs
     --			http://www.ind.alcatel.com

     --  In no event shall Alcatel Internetworking, Inc. be liable for any incidental, 
     --  indirect, special, or consequential damages whatsoever (including 
     --  but not limited to lost profits) arising out of or related to this
     --  document or the information contained in it, even if Alcatel Internetworking,
     --  Inc. has been advised of, known, or should have known, the 
     --  possibility of such damages.
     --  Alcatel Internetworking, Inc. grants vendors, end-users, and other interested
     --  parties a non-exclusive license to use this Specification in connection
     --  with the management of Alcatel Internetworking, Inc. products.

     --  Copyright (C) 1997, Alcatel Internetworking, Inc. All Rights Reserved.

     
     	IMPORTS
		OBJECT-TYPE
			FROM RFC-1212
		DisplayString 
			FROM RFC1213-MIB
		IpAddress 
			FROM RFC1155-SMI
	        xylanAVLArch
			FROM XYLAN-BASE-MIB 
		MacAddress
			FROM BRIDGE-MIB
			;
-- Xylan Authenticated VLANs MIb *****************************

xylanAVLConfig  OBJECT IDENTIFIER ::= { xylanAVLArch 1 }

xylanAVLloginbanner OBJECT-TYPE
        SYNTAX        DisplayString 
        ACCESS        read-write
        STATUS        mandatory
        DESCRIPTION
            "The Authentication login banner"
        ::= { xylanAVLConfig 1 }

xylanAVLoptionprompt OBJECT-TYPE
        SYNTAX        DisplayString 
        ACCESS        read-write
        STATUS        mandatory
        DESCRIPTION
            "Radius/LDAP telnet authentication type prompt"
        ::= { xylanAVLConfig 4 }

xylanAVLgroupprompt OBJECT-TYPE
        SYNTAX        DisplayString 
        ACCESS        read-write
        STATUS        mandatory
        DESCRIPTION
            "Radius/LDAP authentication group prompt"
        ::= { xylanAVLConfig 5 }

xylanAVLuserprompt OBJECT-TYPE
        SYNTAX        DisplayString 
        ACCESS        read-write
        STATUS        mandatory
        DESCRIPTION
            "Radius/LDAP authentication username prompt"
        ::= { xylanAVLConfig 6 }

xylanAVLpassprompt OBJECT-TYPE
        SYNTAX        DisplayString 
        ACCESS        read-write
        STATUS        mandatory
        DESCRIPTION
            "Radius/LDAP authentication password prompt"
        ::= { xylanAVLConfig 7 }

xylanAVLchalprompt OBJECT-TYPE
        SYNTAX        DisplayString 
        ACCESS        read-write
        STATUS        mandatory
        DESCRIPTION
            "Radius/LDAP authentication challenge prompt"
        ::= { xylanAVLConfig 8 }

xylanAVLsucceedmsg OBJECT-TYPE
        SYNTAX        DisplayString 
        ACCESS        read-write
        STATUS        mandatory
        DESCRIPTION
            "Radius/LDAP successful authentication attempt message"
        ::= { xylanAVLConfig 9 }

xylanAVLfailmsg OBJECT-TYPE
        SYNTAX        DisplayString 
        ACCESS        read-write
        STATUS        mandatory
        DESCRIPTION
            "Radius/LDAP failed authentication attempt message"
        ::= { xylanAVLConfig 10 }

xylanAVLauthmode OBJECT-TYPE
        SYNTAX        INTEGER {
			single-authority (1),
			multiple-authority (2)
			      }	
        ACCESS        read-write
        STATUS        mandatory
        DESCRIPTION
            "Radius/LDAP authentication group mode:
		1 - single authority
		2 - multiple authority"
        ::= { xylanAVLConfig 11 }

xylanAVLtimeout OBJECT-TYPE
        SYNTAX        INTEGER
        ACCESS        read-write
        STATUS        mandatory
        DESCRIPTION
            "Radius/LDAP authentication client session timeout in seconds"
        ::= { xylanAVLConfig 12 }

xylanAVLlastuser OBJECT-TYPE
	SYNTAX	      DisplayString
	ACCESS	      read-only
	STATUS        mandatory
        DESCRIPTION 
	    "Radius/LDAP last user event information.  This is useful
	     in determining the last authentication attempt"
	::= { xylanAVLConfig 16 }

xylanAVLlastauthevent OBJECT-TYPE
	SYNTAX       INTEGER {
			success (1),
			failure (2),
			logout (3)
		             }
	ACCESS       read-only
        STATUS       mandatory
        DESCRIPTION
	    "Radius/LDAP last authorization event type.  The following 
             events are valid:

		1 - Successful Login 
		2 - Failed Login Attempt
	        3 - Logout/Drop

	     Note: The xylanAVLlastuser MIB entry is only valid on events
		   1 and 2.  Logouts and drops do NOT utilize this entry."
	::= { xylanAVLConfig 17 }

xylanAVLlastauthmac OBJECT-TYPE
	SYNTAX	MacAddress
	ACCESS  read-only
	STATUS  mandatory
	DESCRIPTION
	    "The last MAC Address to make an authentication attempt."
	::= { xylanAVLConfig 18 }

xylanAVLlastport OBJECT-TYPE
	SYNTAX  INTEGER
	ACCESS  read-only
	STATUS  mandatory
	DESCRIPTION
	    "The last port number from which the authentication attempt
	     originated."
	::= { xylanAVLConfig 19 }

xylanAVLlastslot OBJECT-TYPE
	SYNTAX  INTEGER
	ACCESS  read-only
	STATUS  mandatory
	DESCRIPTION
	    "The last slot number from which the authentication attempt
	     originated."
	::= { xylanAVLConfig 20}

xylanAVLversion OBJECT-TYPE
	SYNTAX DisplayString
	ACCESS read-only
	STATUS mandatory
	DESCRIPTION
	    "The Authenticated VLAN II module version information."
	::= { xylanAVLConfig 21 }

xylanAVLdropmac OBJECT-TYPE
	SYNTAX	MacAddress
	ACCESS  write-only
	STATUS  mandatory
	DESCRIPTION
	    "Drop the connection associated with this particular MAC
	     address."
	::= { xylanAVLConfig 22 }

xylanAVLradretries OBJECT-TYPE
	SYNTAX INTEGER
	ACCESS read-write
	STATUS mandatory
	DESCRIPTION
	    "The number of retries sent to the Radius server before
	     the request is timed out."
	::= { xylanAVLConfig 23 }

xylanAVLradtimeout OBJECT-TYPE
	SYNTAX INTEGER
	ACCESS read-write
	STATUS mandatory
	DESCRIPTION
	    "The number of seconds to wait before another request
	     is sent to the Radius server."
	::= { xylanAVLConfig 24 }

xylanAVLBootpIfAddr OBJECT-TYPE
	SYNTAX IpAddress
	ACCESS read-write
	STATUS mandatory
	DESCRIPTION
	    "The IP address of the interface on the switch through which
	     the DHCP requests are forwarded."
	::= { xylanAVLConfig 25 }

xylanAVLDNSName OBJECT-TYPE
	SYNTAX DisplayString
	ACCESS read-write
	STATUS mandatory
	DESCRIPTION
	    "The host name used to represent the authentication IP address 
	     configured on the switch."
	::= { xylanAVLConfig 26 }

xylanAVLPathRestriction OBJECT-TYPE
	SYNTAX DisplayString
	ACCESS read-write
	STATUS mandatory
	DESCRIPTION
	    "For security reasons it is necessary to limit a web
	     based user to a particular directory. This is the
	     path to which he is restricted . The Path must have the
	     form  /dir1name/dir2name/etc."
	::= { xylanAVLConfig 27 }

-- Telnet Authentication Proxy Port Address Table *********************

xylanAVLTproxyports OBJECT-TYPE
        SYNTAX  SEQUENCE OF XylanAVLTproxyEnt
        ACCESS  not-accessible
	STATUS	mandatory
        DESCRIPTION  "The Telnet Authentication proxy address list enumerates
	     the list of IP addresses that the switch recognizes as
	     authentication addresses."
        ::= { xylanAVLConfig 2 }

xylanAVLTproxyentry OBJECT-TYPE
	SYNTAX	 XylanAVLTproxyEnt
        ACCESS   not-accessible
	STATUS	 mandatory
        DESCRIPTION "The Telnet Authentication proxy address"
	INDEX {
		xylanAVLTproxyIntfAddr
	      }
        ::= { xylanAVLTproxyports 1 }

XylanAVLTproxyEnt ::=
	SEQUENCE {
		xylanAVLTproxyIntfAddr   IpAddress,
		xylanAVLTproxyProxyAddr  IpAddress
		 } 


xylanAVLTproxyIntfAddr OBJECT-TYPE
	        SYNTAX  IpAddress
		ACCESS  read-write
		STATUS	mandatory
        	DESCRIPTION
            	"This value gives the IP address of the router port to which
 		 the proxy address applies"
	        ::= { xylanAVLTproxyentry 1 }

xylanAVLTproxyProxyAddr OBJECT-TYPE
	        SYNTAX  IpAddress
		ACCESS  read-write
		STATUS	mandatory
        	DESCRIPTION
            	"This value gives the proxy IP address"
	        ::= { xylanAVLTproxyentry 2 }

-- Telnet Authentication Enabled ports table *********************


-- Telnet Radius Server Table *********************

xylanAVLRadiusServers OBJECT-TYPE
        SYNTAX  SEQUENCE OF XylanAVLRadiusEnt
        ACCESS  not-accessible
	STATUS	mandatory
        DESCRIPTION "Listing of Configured Radius Authentication Servers by group."
        ::= { xylanAVLConfig 13 }

xylanAVLradiusentry OBJECT-TYPE
	SYNTAX	 XylanAVLRadiusEnt
        ACCESS   not-accessible
	STATUS	 mandatory
        DESCRIPTION "Individual Radius Authentication Server Entry."
	INDEX {
		xylanAVLRadiusAddress,
		xylanAVLRadiusGroup
	      }
        ::= { xylanAVLRadiusServers 1 }

XylanAVLRadiusEnt ::=
	SEQUENCE {
		xylanAVLRadiusAddress  IpAddress,
		xylanAVLRadiusGroup   INTEGER,
		xylanAVLRadiusPriority INTEGER,
		xylanAVLRadiusPort     INTEGER,
		xylanAVLRadiusSecret   DisplayString,
		xylanAVLRadiusAdminState INTEGER
		 } 

xylanAVLRadiusGroup OBJECT-TYPE
	        SYNTAX  INTEGER
		ACCESS  read-write
		STATUS	mandatory
        	DESCRIPTION "The group number to which the Radius server is assigned."
	        ::= { xylanAVLradiusentry 1 }

xylanAVLRadiusAddress OBJECT-TYPE
	        SYNTAX  IpAddress
		ACCESS  read-write
		STATUS	mandatory
        	DESCRIPTION
            	"Radius Server IP address."
	        ::= { xylanAVLradiusentry 2 }

xylanAVLRadiusPriority OBJECT-TYPE
		SYNTAX INTEGER (1..255)
		ACCESS read-write
		STATUS mandatory
		DESCRIPTION "The radius servers priority in the list of
			     configured servers, 1 being the highest."
		::= { xylanAVLradiusentry 3 }

xylanAVLRadiusPort OBJECT-TYPE
		SYNTAX INTEGER
		ACCESS read-write
		STATUS mandatory	
		DESCRIPTION "The radius server remote UDP port number"
		::= { xylanAVLradiusentry 4 }

xylanAVLRadiusSecret OBJECT-TYPE
		SYNTAX DisplayString
		ACCESS write-only
		STATUS mandatory
		DESCRIPTION "The radius servers secret."
		::= { xylanAVLradiusentry 5 }
		
xylanAVLRadiusAdminState OBJECT-TYPE
		SYNTAX INTEGER {
				active (1),
				delete (2)
			       }
		ACCESS read-write
		STATUS mandatory
		DESCRIPTION "The current status of this server, active (1)
			     or delete(2) to tell SNMP to delete this entry"
		::= { xylanAVLradiusentry 6 }

-- Authentication Radius Server Table *********************

-- Radius Accounting Server Table *************************

xylanAVLRadiusAcctServers OBJECT-TYPE
        SYNTAX  SEQUENCE OF XylanAVLRadiusAcctEnt
        ACCESS  not-accessible
	STATUS	mandatory
        DESCRIPTION "Listing of Configured Radius Authentication Servers by group."
        ::= { xylanAVLConfig 14 }

xylanAVLradiusacctentry OBJECT-TYPE
	SYNTAX	 XylanAVLRadiusAcctEnt
        ACCESS   not-accessible
	STATUS	 mandatory
        DESCRIPTION "Individual Radius Authentication Server Entry."
	INDEX {
		xylanAVLRadiusAcctAddress,
		xylanAVLRadiusAcctGroup
	      }
        ::= { xylanAVLRadiusAcctServers 1 }

XylanAVLRadiusAcctEnt ::=
	SEQUENCE {
		xylanAVLRadiusAcctAddress  IpAddress,
		xylanAVLRadiusAcctGroup   INTEGER,
		xylanAVLRadiusAcctPri	  INTEGER,
		xylanAVLRadiusAcctPort	  INTEGER,
		xylanAVLRadiusAcctSecret DisplayString,
		xylanAVLRadiusAcctAdminState INTEGER
		 } 

xylanAVLRadiusAcctGroup OBJECT-TYPE
	        SYNTAX  INTEGER
		ACCESS  read-write
		STATUS	mandatory
        	DESCRIPTION "The group number to which the Radius server is assigned."
	        ::= { xylanAVLradiusacctentry 1 }

xylanAVLRadiusAcctAddress OBJECT-TYPE
	        SYNTAX  IpAddress
		ACCESS  read-write
		STATUS	mandatory
        	DESCRIPTION
            	"Radius Server IP address."
	        ::= { xylanAVLradiusacctentry 2 }

xylanAVLRadiusAcctPri OBJECT-TYPE
		SYNTAX INTEGER (1..255)
		ACCESS read-write
		STATUS mandatory
		DESCRIPTION "The server priority in the list, one being the
			     highest."
		::= { xylanAVLradiusacctentry 3 }

xylanAVLRadiusAcctPort OBJECT-TYPE
		SYNTAX INTEGER
		ACCESS read-write
		STATUS mandatory	
		DESCRIPTION "The radius server remote UDP port number"
		::= { xylanAVLradiusacctentry 4 }

xylanAVLRadiusAcctSecret OBJECT-TYPE
		SYNTAX DisplayString
		ACCESS write-only
		STATUS mandatory
		DESCRIPTION "The radius servers secret."
		::= { xylanAVLradiusacctentry 5 }
		
xylanAVLRadiusAcctAdminState OBJECT-TYPE
		SYNTAX INTEGER {
				active (1),
				delete (2)
			       }
		ACCESS read-write
		STATUS mandatory
		DESCRIPTION "The current status of this server, active (1)
			     or delete(2) to tell SNMP to delete this entry"
		::= { xylanAVLradiusacctentry 6 }

-- Radius Accounting Server Table *********************



XylanAVLtelportStatCodes ::= INTEGER {
		disable(1),
	    	enable(2)
	}

xylanAVLtelports OBJECT-TYPE
        SYNTAX  SEQUENCE OF XylanAVLtelportEnt
        ACCESS  not-accessible
	STATUS	mandatory
        DESCRIPTION
            "The Telnet Authentication enabled list enumerates
	     the list of Telnet authentication enabled ports"
        ::= { xylanAVLConfig 3 }
 
xylanAVLtelportentry OBJECT-TYPE
	SYNTAX	 XylanAVLtelportEnt
        ACCESS   not-accessible
	STATUS	 mandatory
        DESCRIPTION
            "The Telnet Authentication port description"
	INDEX {
		xylanAVLtelportslot,
		xylanAVLtelportport
	      }
        ::= { xylanAVLtelports 1 }

XylanAVLtelportEnt ::=
	SEQUENCE {
		xylanAVLtelportslot  INTEGER,
		xylanAVLtelportport  INTEGER,
	        xylanAVLtelportstat  XylanAVLtelportStatCodes
		 }

xylanAVLtelportslot OBJECT-TYPE
	        SYNTAX  INTEGER
		ACCESS  read-write
		STATUS	mandatory
        	DESCRIPTION
            	"This value gives the physical slot in the Switch"
	        ::= { xylanAVLtelportentry 1 }

xylanAVLtelportport OBJECT-TYPE
	        SYNTAX  INTEGER
		ACCESS  read-write
		STATUS	mandatory
        	DESCRIPTION
            	"This value gives the physical port within a slot in the Switch"
	        ::= { xylanAVLtelportentry 2 }

xylanAVLtelportstat  OBJECT-TYPE
	        SYNTAX  XylanAVLtelportStatCodes
		ACCESS  read-write
		STATUS	mandatory
        	DESCRIPTION
            	"This value gives status of the port. Used for deleting entries"
	        ::= { xylanAVLtelportentry 3 }


-- LDAP Server Table *************************

xylanAVLLdapServers OBJECT-TYPE
        SYNTAX  SEQUENCE OF XylanAVLLdapEnt
        ACCESS  not-accessible
        STATUS  mandatory
        DESCRIPTION "Listing of LDAP Authentication Servers by group."
        ::= { xylanAVLConfig 28 }

xylanAVLLdapentry OBJECT-TYPE
        SYNTAX   XylanAVLLdapEnt
        ACCESS   not-accessible
        STATUS   mandatory
        DESCRIPTION
            "Individual Authentication LDAP Server Entry"
        INDEX {
                xylanAVLLdapGroup
              }
        ::= { xylanAVLLdapServers 1 }

XylanAVLLdapEnt ::=
        SEQUENCE {
                xylanAVLLdapGroup        INTEGER,
                xylanAVLLdapUserId       DisplayString,
                xylanAVLLdapUserPassword DisplayString,
                xylanAVLLdapSearchBase   DisplayString,
                xylanAVLLdapChain        DisplayString,
                xylanAVLLdapType         INTEGER,
                xylanAVLLdapRetry        INTEGER,
                xylanAVLLdapResponseTime INTEGER,
                xylanAVLLdapAcctStatus   INTEGER,
                xylanAVLLdapLoginFailId  DisplayString,
                xylanAVLLdapMultiGroup   INTEGER,
                xylanAVLLdapAdminState   INTEGER
                 }

xylanAVLLdapGroup OBJECT-TYPE
                SYNTAX  INTEGER
                ACCESS  read-write
                STATUS  mandatory
                DESCRIPTION "The group number to which the LDAP server is assigned."
                ::= { xylanAVLLdapentry 1 }

xylanAVLLdapUserId OBJECT-TYPE
                SYNTAX  DisplayString
                ACCESS  read-write
                STATUS  mandatory
                DESCRIPTION
                "LDAP server super user id."
                ::= { xylanAVLLdapentry 2 }

xylanAVLLdapUserPassword OBJECT-TYPE
                SYNTAX  DisplayString
                ACCESS  write-only
                STATUS  mandatory
                DESCRIPTION
                "LDAP server super user password."
                ::= { xylanAVLLdapentry 3 }

xylanAVLLdapSearchBase OBJECT-TYPE
                SYNTAX  DisplayString
                ACCESS  read-write
                STATUS  mandatory
                DESCRIPTION
                "LDAP server search base."
                ::= { xylanAVLLdapentry 4 }

xylanAVLLdapChain OBJECT-TYPE
                SYNTAX  DisplayString
                ACCESS  read-write
                STATUS  mandatory
                DESCRIPTION
                "LDAP server chain."
                ::= { xylanAVLLdapentry 5 }

xylanAVLLdapType OBJECT-TYPE
                SYNTAX  INTEGER {
                                generic-schema (1),
                                netscape-directory-server (2),
                                novell-NDS (3),
                                sun-directory-services(4)
                                }
                ACCESS  read-write
                STATUS  mandatory
                DESCRIPTION
                "LDAP server type.
                        1 - Generic Schema
                        2 - Netscape Directory Server
                        3 - Novell NDS
                        4 - Sun Directory Services"
                ::= { xylanAVLLdapentry 6 }

xylanAVLLdapRetry OBJECT-TYPE
                SYNTAX  INTEGER (1..100)
                ACCESS  read-write
                STATUS  mandatory
                DESCRIPTION
                "LDAP server retry times."
                ::= { xylanAVLLdapentry 7 }

xylanAVLLdapResponseTime OBJECT-TYPE
                SYNTAX  INTEGER (1..90)
                ACCESS  read-write
                STATUS  mandatory
                DESCRIPTION
                "LDAP server response time in seconds."
                ::= { xylanAVLLdapentry 8 }

xylanAVLLdapAcctStatus OBJECT-TYPE
                SYNTAX  INTEGER {
                                on (1),
                                off (2)
                                }
                ACCESS  read-write
                STATUS  mandatory
                DESCRIPTION
                "LDAP accounting status:
                        1 - on
                        2 - off"
                ::= { xylanAVLLdapentry 9 }

xylanAVLLdapLoginFailId OBJECT-TYPE
                SYNTAX  DisplayString
                ACCESS  read-write
                STATUS  mandatory
                DESCRIPTION
                "LDAP server login fail id."
                ::= { xylanAVLLdapentry 10 }

xylanAVLLdapMultiGroup OBJECT-TYPE
                SYNTAX  INTEGER {
                                yes (1),
                                no (2)
                                }
                ACCESS  read-write
                STATUS  mandatory
                DESCRIPTION
                "LDAP multiple mode has group data:
                        1 - yes
                        2 - no"
                ::= { xylanAVLLdapentry 11 }

xylanAVLLdapAdminState OBJECT-TYPE
                SYNTAX INTEGER {
                                active (1),
                                delete (2)
                               }
                ACCESS read-write
                STATUS mandatory
                DESCRIPTION
                "The current status of this server:
                        active (1): Server chain is active.
                        delete (2): tell SNMP to delete this entry."
                ::= { xylanAVLLdapentry 12 }

-- LDAP Server Table *************************

END
