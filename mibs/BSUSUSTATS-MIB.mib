BSUSUSTATS-MIB DEFINITIONS ::= BEGIN

	IMPORTS
		OBJECT-TYPE, MODULE-IDENTITY, Integer32, Counter32
			FROM SNMPv2-SMI
		aniBsuSuMacAddr
			FROM BSUSUINV-MIB
		aniBsuSuGroup
			FROM ANIROOT-MIB;

		-- the BSU-SU Statistics Group
			-- BSU SU Service Level Statistics 
			-- BSU SU Signal Quality Statistics 

aniBsuSuStatistics  MODULE-IDENTITY
	LAST-UPDATED "0105091130Z"      -- Wed May 9 11:30:00 PDT 2001
	ORGANIZATION "Aperto Networks"
	CONTACT-INFO
	  "       
	  Postal:  Aperto Networks Inc
		   1637 S Main Street 
		   Milpitas, California 95035
	  Tel:	   +1 408 719 9977
	  "       
	DESCRIPTION
	   "This group contains Statistical information for each SU 
	    connected to this BSU.
	    It displays statistics per SU per Service Flow ID when viewed 
	    from the BSU.
	   " 
	::= { aniBsuSuGroup 4 }


        -- Service Flow Statistics Group

aniBsuSuServStatsTable OBJECT-TYPE
	SYNTAX      SEQUENCE OF AniBsuSuServStatsEntry
	MAX-ACCESS  not-accessible
	STATUS      current
	DESCRIPTION
	   "This table provides the statistics information for each SU
	    for each Service Flow.
	   "
	::= { aniBsuSuStatistics 1 }

aniBsuSuServStatsEntry OBJECT-TYPE
	SYNTAX      AniBsuSuServStatsEntry
	MAX-ACCESS  not-accessible
	STATUS      current
	DESCRIPTION
	   "An entry with objects that provide statistics information 
	    for each Service Flow.
	   "
	INDEX { aniBsuSuMacAddr, aniBsuSuServStatsFlowId }
	::= { aniBsuSuServStatsTable 1 }

AniBsuSuServStatsEntry ::= SEQUENCE {
	aniBsuSuServStatsFlowId			Integer32,
	aniBsuSuServStatsDSEthernetPkts		Counter32,
	aniBsuSuServStatsDSDropEthernetPkts  	Counter32,
	aniBsuSuServStatsDSBytes  		Counter32,
	aniBsuSuServStatsDSWirelessPkts 	Counter32,
	aniBsuSuServStatsDSWirelessPktsRetrans 	Counter32,
	aniBsuSuServStatsUSEthernetPkts		Counter32,
	aniBsuSuServStatsUSDropEthernetPkts  	Counter32,
	aniBsuSuServStatsUSBytes  		Counter32,
	aniBsuSuServStatsUSWirelessPkts  	Counter32
	}

aniBsuSuServStatsFlowId OBJECT-TYPE
	SYNTAX      Integer32
	MAX-ACCESS  read-only
	STATUS      current
	DESCRIPTION
	   "The Service Flow Identifier.
	   "
	--DEFAULT next-function-async     aniBsuSuServStatsEntry_next
        ::= { aniBsuSuServStatsEntry 1 }

aniBsuSuServStatsDSEthernetPkts OBJECT-TYPE
	SYNTAX      Counter32
	MAX-ACCESS  read-only
	STATUS      current
	DESCRIPTION
	   "The total number of downstream Ethernet packets for this Service FlowId.
	   "
	--DEFAULT next-function-async     aniBsuSuServStatsEntry_next
        ::= { aniBsuSuServStatsEntry 2 }

aniBsuSuServStatsDSDropEthernetPkts OBJECT-TYPE
	SYNTAX      Counter32
	MAX-ACCESS  read-only
	STATUS      current
	DESCRIPTION
	   "The total number of downstream Ethernet packets that got dropped.
	    This is visible only when ARQ is enabled.
	   "
	--DEFAULT next-function-async     aniBsuSuServStatsEntry_next
        ::= { aniBsuSuServStatsEntry 3 }

aniBsuSuServStatsDSBytes OBJECT-TYPE
	SYNTAX      Counter32
	MAX-ACCESS  read-only
	STATUS      current
	DESCRIPTION
	   "The total number of downstream bytes successfully received.
	   "
	--DEFAULT next-function-async     aniBsuSuServStatsEntry_next
        ::= { aniBsuSuServStatsEntry 4 }

aniBsuSuServStatsDSWirelessPkts OBJECT-TYPE
	SYNTAX      Counter32
	MAX-ACCESS  read-only
	STATUS      current
	DESCRIPTION
	   "The total number of downstream Wireless packets for this Service FlowId.
	   "
	--DEFAULT next-function-async     aniBsuSuServStatsEntry_next
        ::= { aniBsuSuServStatsEntry 5 }

aniBsuSuServStatsDSWirelessPktsRetrans OBJECT-TYPE
	SYNTAX      Counter32
	MAX-ACCESS  read-only
	STATUS      current
	DESCRIPTION
	   "The number of times downstream Wireless packets are retransmitted.
	    This is visible only when ARQ is enabled.
	   "
	--DEFAULT next-function-async     aniBsuSuServStatsEntry_next
        ::= { aniBsuSuServStatsEntry 6 }

aniBsuSuServStatsUSEthernetPkts OBJECT-TYPE
	SYNTAX      Counter32
	MAX-ACCESS  read-only
	STATUS      current
	DESCRIPTION
	   "The total number of upstream Ethernet packets for this Service FlowId.
	   "
	--DEFAULT next-function-async     aniBsuSuServStatsEntry_next
        ::= { aniBsuSuServStatsEntry 7 }

aniBsuSuServStatsUSDropEthernetPkts OBJECT-TYPE
	SYNTAX      Counter32
	MAX-ACCESS  read-only
	STATUS      current
	DESCRIPTION
	   "The total number of upstream Ethernet packets that got dropped.
	    This is visible only when ARQ is enabled.
	   "
	--DEFAULT next-function-async     aniBsuSuServStatsEntry_next
        ::= { aniBsuSuServStatsEntry 8 }

aniBsuSuServStatsUSBytes OBJECT-TYPE
	SYNTAX      Counter32
	MAX-ACCESS  read-only
	STATUS      current
	DESCRIPTION
	   "The total number of upstream bytes successfully received.
	   "
	--DEFAULT next-function-async     aniBsuSuServStatsEntry_next
        ::= { aniBsuSuServStatsEntry 9 }

aniBsuSuServStatsUSWirelessPkts OBJECT-TYPE
	SYNTAX      Counter32
	MAX-ACCESS  read-only
	STATUS      current
	DESCRIPTION
	   "The total number of upstream Wireless packets for this Service FlowId.
	   "
	--DEFAULT next-function-async     aniBsuSuServStatsEntry_next
        ::= { aniBsuSuServStatsEntry 10 }


	-- the Signal Quality Group

aniBsuSuSignalQualityTable OBJECT-TYPE
	SYNTAX      SEQUENCE OF AniBsuSuSignalQualityEntry
	MAX-ACCESS  not-accessible
	STATUS      current
	DESCRIPTION
	   "A table with entries for describing the Signal Quality associated 
	    with the SU per Service Flow.
	   "
	::= { aniBsuSuStatistics 2 }

aniBsuSuSignalQualityEntry OBJECT-TYPE
	SYNTAX      AniBsuSuSignalQualityEntry
	MAX-ACCESS  not-accessible
	STATUS      current
	DESCRIPTION
	   "An entry with objects that describe the signal 
	    quality for a given SU Service Flow.
	   "
	INDEX { aniBsuSuMacAddr, aniBsuSuServStatsFlowId }
	::= { aniBsuSuSignalQualityTable 1 }

AniBsuSuSignalQualityEntry ::= SEQUENCE {
	aniBsuSuSigQCollidedBurstsCount		Counter32,
	aniBsuSuSigQCorrFecErrorCount		Counter32,
	aniBsuSuSigQUnCorrFecErrorCount		Counter32,
	aniBsuSuSigQNoFecErrorCount 		Counter32,
	aniBsuSuSigQNoUniqWordDetectedCount   Counter32,
	aniBsuSuSigQNoEnergyDetectedCount     Counter32
        }

aniBsuSuSigQCollidedBurstsCount OBJECT-TYPE
	SYNTAX      Counter32
	MAX-ACCESS  read-only
	STATUS      current
	DESCRIPTION
	   "The number of Wireless Packet collisions.
	   "
	--DEFAULT next-function-async     aniBsuSuSignalQualityEntry_next
	::= { aniBsuSuSignalQualityEntry 1 }

aniBsuSuSigQCorrFecErrorCount OBJECT-TYPE
	SYNTAX      Counter32
	MAX-ACCESS  read-only
	STATUS      current
	DESCRIPTION
	   "The number of FEC errors which were corrected.
	   "
	--DEFAULT next-function-async     aniBsuSuSignalQualityEntry_next
	::= { aniBsuSuSignalQualityEntry 2 }

aniBsuSuSigQUnCorrFecErrorCount OBJECT-TYPE
	SYNTAX      Counter32
	MAX-ACCESS  read-only
	STATUS      current
	DESCRIPTION
	   "The total number of FEC errors that are uncorrectable.
	   "
	--DEFAULT next-function-async     aniBsuSuSignalQualityEntry_next
	::= { aniBsuSuSignalQualityEntry 3 }

aniBsuSuSigQNoFecErrorCount OBJECT-TYPE
	SYNTAX      Counter32
	MAX-ACCESS  read-only
	STATUS      current
	DESCRIPTION
	   "The number of codewords detected without any errors.
	   "
	--DEFAULT next-function-async     aniBsuSuSignalQualityEntry_next
	::= { aniBsuSuSignalQualityEntry 4 }

aniBsuSuSigQNoUniqWordDetectedCount OBJECT-TYPE
	SYNTAX      Counter32
	MAX-ACCESS  read-only
	STATUS      current
	DESCRIPTION
	   "The No Unique Word Deteced count.
	   "
	--DEFAULT next-function-async     aniBsuSuSignalQualityEntry_next
	::= { aniBsuSuSignalQualityEntry 5 }

aniBsuSuSigQNoEnergyDetectedCount OBJECT-TYPE
	SYNTAX      Counter32
	MAX-ACCESS  read-only
	STATUS      current
	DESCRIPTION
	   "The total number of instances where no energy is
	    detected.
	   "
	--DEFAULT next-function-async     aniBsuSuSignalQualityEntry_next
	::= { aniBsuSuSignalQualityEntry 6 }

	END
