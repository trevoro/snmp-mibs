Chromatis-MIB
--FORCE-INCLUDE <mib.h>
--FORCE-INCLUDE <snmpdefs.h>
--FORCE-INCLUDE "mibhand.h"

  DEFINITIONS  ::=  BEGIN

IMPORTS
     MODULE-IDENTITY FROM SNMPv2-SMI
     enterprises     FROM RFC1155-SMI;

chromatis    MODULE-IDENTITY
             LAST-UPDATED "9905170000Z"
             ORGANIZATION "Chromatis Networks Inc."
             CONTACT-INFO "Chromatis Networks
						   21 c Yagea Kapaim , Kiryat Arye,
						   Petach Tikva, Israel       
						   Phone: 972-3-9231030
						   Fax:   972-3-9231050
						   emil@chromatis.com"
			 DESCRIPTION "This MIB module is the SNMP version of Chromatis Networks' Metrpolis"
			 REVISION "9905171830Z"             
			 DESCRIPTION "Compiled for the first time by Zvika"
             ::= { enterprises  3695 }


-- chromatis
chrCommon               OBJECT IDENTIFIER ::= { chromatis 1 }
chrProducts             OBJECT IDENTIFIER ::= { chromatis 2 }

-- chromatis Common
chrComHW                OBJECT IDENTIFIER ::= { chrCommon 1 }
chrComIf                OBJECT IDENTIFIER ::= { chrCommon 2 }
chrComConfigVersion     OBJECT IDENTIFIER ::= { chrCommon 3 }
chrComSwVersion         OBJECT IDENTIFIER ::= { chrCommon 4 }
chrComAccess            OBJECT IDENTIFIER ::= { chrCommon 5 }
chrComTrap              OBJECT IDENTIFIER ::= { chrCommon 6 }
chrComActions			OBJECT IDENTIFIER ::= { chrCommon 7 }
chrComCompressData		OBJECT IDENTIFIER ::= { chrCommon 8 }
chrComAtm				OBJECT IDENTIFIER ::= { chrCommon 9 }
chrComPM				OBJECT IDENTIFIER ::= { chrCommon 10 }
chrComFM				OBJECT IDENTIFIER ::= { chrCommon 11 }
chrComProtection		OBJECT IDENTIFIER ::= { chrCommon 12 }
chrComNetwork			OBJECT IDENTIFIER ::= { chrCommon 13 }


-- chromatis Common Hardware
chrComHwNe				OBJECT IDENTIFIER ::= { chrComHW 1 }
--chrComHwEquipment		OBJECT IDENTIFIER ::= { chrComHW 2 }

-- chromatis Common Interface
chrComIfSonet           OBJECT IDENTIFIER ::= { chrComIf 1 }
chrComIfAtm				OBJECT IDENTIFIER ::= { chrComIf 2 }
chrComIfOptics			OBJECT IDENTIFIER ::= { chrComIf 3 }
chrComIfDS3				OBJECT IDENTIFIER ::= { chrComIf 4 }
chrComIfEthernet		OBJECT IDENTIFIER ::= { chrComIf 5 }

-- chromatis Common ATM
chrComAtmVpl			OBJECT IDENTIFIER ::= { chrComAtm 1 }
chrComAtmVcl			OBJECT IDENTIFIER ::= { chrComAtm 2 }

-- chromatis Common PM
chrComPmOptics			OBJECT IDENTIFIER ::= { chrComPM 1 } 
chrComPmSonet			OBJECT IDENTIFIER ::= { chrComPM 2 } 
chrComPmDs3				OBJECT IDENTIFIER ::= { chrComPM 3 } 
chrComPmAtm				OBJECT IDENTIFIER ::= { chrComPM 4 } 
chrComPmEth				OBJECT IDENTIFIER ::= { chrComPM 5 } 

-- chromatis Common Protection	
chrComProtectionGroup	OBJECT IDENTIFIER ::= { chrComProtection 1 }
chrComProtectionVp		OBJECT IDENTIFIER ::= { chrComProtection 2 }
chrComProtectionVc		OBJECT IDENTIFIER ::= { chrComProtection 3 }
chrComProtectSinglePath		OBJECT IDENTIFIER ::= { chrComProtection 4 }
chrComProtectEquip			OBJECT IDENTIFIER ::= { chrComProtection 5 }


-- chromatis Common Network Control
chrComNetClockSync		OBJECT IDENTIFIER ::= { chrComNetwork 1 }



-- chromatis Products
chrProductsMetropolis2000       OBJECT IDENTIFIER ::= { chrProducts 1 }
chrProductsMetropolis2500       OBJECT IDENTIFIER ::= { chrProducts 2 }
chrProductsMetropolis4000       OBJECT IDENTIFIER ::= { chrProducts 3 }
chrProductsMetropolis4500       OBJECT IDENTIFIER ::= { chrProducts 4 }

END
