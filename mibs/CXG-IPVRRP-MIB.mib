CXG-IPVRRP-MIB DEFINITIONS ::= BEGIN


    IMPORTS
      IpAddress
    FROM RFC1155-SMI
      OBJECT-TYPE                     
    FROM RFC-1212
      cxCfgIp               
    FROM CXProduct-SMI;




     cxVrrpTable OBJECT-TYPE
      SYNTAX  SEQUENCE OF CxVrrpEntry
      ACCESS  not-accessible
      STATUS  mandatory
      DESCRIPTION
"Provides the configuration VRRP Layer."
   ::= { cxCfgIp 5 }


     cxVrrpEntry OBJECT-TYPE
    SYNTAX  CxVrrpEntry
    ACCESS  not-accessible
    STATUS  mandatory
    DESCRIPTION
"Identifies the configuration of VRRP table."
    INDEX   { cxVrrpIPPort, cxVrrpVrID }
    ::= { cxVrrpTable 1 }


     CxVrrpEntry ::=
    SEQUENCE {
-- Parameters
   cxVrrpIPPort
       INTEGER,        
   cxVrrpVrID
       INTEGER,        
   cxVrrpPriority
       INTEGER,        
   cxVrrpIPAddress
       IpAddress,
   cxVrrpAdvertiseInterval
       INTEGER,        
   cxVrrpPreemptiveMode
       INTEGER,        
-- Control
   cxVrrpRowStatus
       INTEGER
    }



     cxVrrpIPPort  OBJECT-TYPE
     SYNTAX  INTEGER (1..255)
     ACCESS  read-only
     STATUS  mandatory
     DESCRIPTION 
""
    ::= { cxVrrpEntry 1 }


     cxVrrpVrID  OBJECT-TYPE
     SYNTAX  INTEGER (1..255)
     ACCESS  read-only
     STATUS  mandatory
     DESCRIPTION 
""
    ::= { cxVrrpEntry 2 }


    cxVrrpPriority OBJECT-TYPE
    SYNTAX  INTEGER (1..255)
    ACCESS  read-write
    STATUS  mandatory
    DESCRIPTION
""
    DEFVAL { 100 }
    ::= { cxVrrpEntry 3 }


    cxVrrpIPAddress OBJECT-TYPE
    SYNTAX  IpAddress
    ACCESS  read-write
    STATUS  mandatory
    DESCRIPTION
""
    ::= { cxVrrpEntry 4 }


    cxVrrpAdvertiseInterval OBJECT-TYPE
    SYNTAX  INTEGER (100..65335)
    ACCESS  read-write
    STATUS  mandatory
    DESCRIPTION
""
    DEFVAL { 1000 }
    ::= { cxVrrpEntry 5 }

    cxVrrpPreemptiveMode OBJECT-TYPE
    SYNTAX  INTEGER { enabled (1),
                      disabled (2)
                    }
    ACCESS  read-write
    STATUS  mandatory
    DESCRIPTION
""
    DEFVAL { enabled }
    ::= { cxVrrpEntry 6 }

     cxVrrpRowStatus  OBJECT-TYPE
    SYNTAX  INTEGER { invalid (1),
                      valid (2)
                    }
    ACCESS  read-write
    STATUS  mandatory
    DESCRIPTION 
"Determines the status of the objects in a table row.

Options:
invalid (1): Row is flagged. After next reset the values will be disabled
and the row will be deleted from the table.

valid (2): Values are enabled.

Default Value: (2)

Configuration Changed: Administrative"
    ::= { cxVrrpEntry 10 }


END
