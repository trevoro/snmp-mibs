-- 
-- Copyright 1999 by Fore Systems, Inc. 
-- Converted to SMIv2 rfc 2578,2579,2580 - STD 58
--
-- This FORE proprietary MIB defines all parameters relevant to the
-- Frame Relay/ATM interworking function. It is based on the FRF.5
-- interworking agreement.


Fore-frf5-MIB DEFINITIONS ::= BEGIN

       IMPORTS
	         Integer32,Counter32, TimeTicks, Gauge32,
		 MODULE-IDENTITY,
		 OBJECT-TYPE                    FROM SNMPv2-SMI
		 RowStatus			FROM SNMPv2-TC
		 frameInternetworking,
		 AtmAddress			FROM Fore-Common-MIB
		 InterfaceIndex			FROM IF-MIB;


     frf5 MODULE-IDENTITY
     LAST-UPDATED    "9912090000Z"
     ORGANIZATION    "FORE"
     CONTACT-INFO    "
             Postal: FORE Systems, Inc.
			1000 FORE Drive
			Warrendale, PA 15086-7502
			USA
             Tel:    +1 724-742-4444
             Email:  info@fore.com
             Web:    http://www.fore.com"
     DESCRIPTION
             "This MIB module defines FR/ATM interworking
              tables. It gives the means to create/remove a FR/ATM
              interworking connection and provides statistics at the
              connection level."
	  ::= { frameInternetworking 7 }

------------------------------------------------------------------------

frf5ConnTable	OBJECT-TYPE
  SYNTAX	SEQUENCE OF Frf5ConnEntry
  MAX-ACCESS	not-accessible
  STATUS	current
  DESCRIPTION
    "Table of cross connections between the frame relay and ATM Fabric
     connections"
  ::= { frf5 1 }

frf5ConnEntry	OBJECT-TYPE
  SYNTAX	Frf5ConnEntry
  MAX-ACCESS	not-accessible
  STATUS	current
  DESCRIPTION
    "Entry in the frame relay/atm netmod crossconnect table"
  INDEX   { frf5ConnFrServiceIfIndex, frf5ConnDlci }
  ::= { frf5ConnTable 1 }

Frf5ConnEntry ::= SEQUENCE {
	frf5ConnFrServiceIfIndex	InterfaceIndex,
	frf5ConnDlci			Integer32,
	frf5ConnFrsscsDlci		Integer32,
	frf5ConnFabServiceIfIndex	Integer32,
	frf5ConnFabAtmIf		Integer32,
	frf5ConnFabVpi			Integer32,
	frf5ConnFabVci			Integer32,
	frf5ConnRowStatus		RowStatus,
	frf5ConnProfileEpdPpdIndex	Integer32,
	frf5ConnAtmAddrType		INTEGER,
	frf5ConnAtmAddress		AtmAddress,
	frf5ConnAtmSubAddrType		INTEGER,
	frf5ConnAtmSubAddress		AtmAddress,
	frf5ConnFrAddrType		INTEGER,
	frf5ConnFrAddress		AtmAddress,
	frf5ConnAdminStatus		INTEGER,
	frf5ConnOperStatus		INTEGER,
	frf5ConnCreationTime		TimeTicks,
	frf5ConnTimeChange		TimeTicks
}


frf5ConnFrServiceIfIndex	OBJECT-TYPE
	       SYNTAX    InterfaceIndex
	       MAX-ACCESS    read-only
	       STATUS    current
	       DESCRIPTION
	       "Interface index of the Frame Relay service this
	       connection exists on"
	       ::= { frf5ConnEntry 1 }

frf5ConnDlci	OBJECT-TYPE
	       SYNTAX    Integer32
	       MAX-ACCESS    read-only
	       STATUS    current
	       DESCRIPTION
	       "DLCI of this connection on the frame relay service"
	       ::= { frf5ConnEntry 2 }

frf5ConnFrsscsDlci	OBJECT-TYPE
	       SYNTAX    Integer32
	       MAX-ACCESS    read-create
	       STATUS    current
	       DESCRIPTION
	       "FR SSCS DLCI of this connection which will be
	       multiplexed on a ATM PVC"
     	       DEFVAL { 1022 }
	       ::= { frf5ConnEntry 3 }

frf5ConnFabServiceIfIndex	OBJECT-TYPE
	       SYNTAX    Integer32
	       MAX-ACCESS    read-only
	       STATUS    current
	       DESCRIPTION
	       "This is the IfIndex associated with the fabric pseudo
	       atm service this connection is mapped to by the agent
	       when this Frame Relay connection is created."
	       ::= { frf5ConnEntry 4 }

frf5ConnFabAtmIf	OBJECT-TYPE
	       SYNTAX    Integer32
	       MAX-ACCESS    read-create
	       STATUS    current
	       DESCRIPTION
	       "This is the fabric ATM interface of the ATM
	       connection this frame relay/ATM connection is mapped to
	       by the agent when this row is created.
               This variable can be set only for dangling connections."
	       ::= { frf5ConnEntry 5 }

frf5ConnFabVpi	OBJECT-TYPE
	       SYNTAX    Integer32
	       MAX-ACCESS    read-create
	       STATUS    current
	       DESCRIPTION
	       "This is the fabric VPI (equivalent to ivpi) of the ATM
	       connection this frame relay/ATM connection is mapped to
	       by the agent when this row is created. This VPI will be
	       used to establish a connection across the switching
	       fabric by means of the FORE-switch MIB.
               This variable can be set only for dangling connections."
	       ::= { frf5ConnEntry 6 }

frf5ConnFabVci	OBJECT-TYPE
	       SYNTAX    Integer32
	       MAX-ACCESS    read-create
	       STATUS    current
	       DESCRIPTION
	       "This is the fabric VCI (equivalent to ivci) of the ATM
	       connection this frame relay connection is mapped to by
	       the agent when this row is created. This VCI will be
	       used to establish a connection across the switching
	       fabric by means of the FORE-switch MIB.
               This variable can be set only for dangling connections."
	       ::= { frf5ConnEntry 7 }

frf5ConnRowStatus	 OBJECT-TYPE
	       SYNTAX    RowStatus
	       MAX-ACCESS    read-create
	       STATUS    current
	       DESCRIPTION
	       "This object is used for dynamic creation of
	       entries in this table and all frame relay
	       connection level tables. This object is also
	       used to delete existing connection rows."
	       ::= { frf5ConnEntry 8 }

frf5ConnProfileEpdPpdIndex OBJECT-TYPE
	       SYNTAX    Integer32
	       MAX-ACCESS    read-create
	       STATUS    current
	       DESCRIPTION
	       "The index of the EpdPpd Controller profile."
     	       DEFVAL { 0 }
	       ::= { frf5ConnEntry 9 }

frf5ConnAtmAddrType OBJECT-TYPE
	       SYNTAX    INTEGER {
			 null(1),
			 e164(2),
			 nsap(3)
			 }
	       MAX-ACCESS    read-create
	       STATUS    current
	       DESCRIPTION
	       "Defines the address format of the ATM
	       Service User end point"
	       ::= { frf5ConnEntry 10 }

frf5ConnAtmAddress OBJECT-TYPE
	       SYNTAX    AtmAddress
	       MAX-ACCESS    read-create
	       STATUS    current
	       DESCRIPTION
	       "The destination ATM address to which this Virtual
	       Circuit is connected."
	       ::= { frf5ConnEntry 11 }

frf5ConnAtmSubAddrType OBJECT-TYPE
	       SYNTAX     INTEGER{
			  null(1),
			  e164(2),
			  nsap(3)
			  }
	       MAX-ACCESS    read-create
	       STATUS    current
	       DESCRIPTION
	       "Defines the sub-address format of the ATM
	       Service User end point "
		::= { frf5ConnEntry 12 }

frf5ConnAtmSubAddress	OBJECT-TYPE
	       SYNTAX  AtmAddress
	       MAX-ACCESS  read-create
	       STATUS  current
	       DESCRIPTION
	       "The destination ATM subaddress to which this Virtual
	       Circuit is connected."
	       ::= { frf5ConnEntry 13 }

frf5ConnFrAddrType	OBJECT-TYPE
	       SYNTAX    INTEGER{
			 null(1),
			 e164(2)
			 }
	       MAX-ACCESS    read-create
	       STATUS    current
	       DESCRIPTION
	       "Defines the frame relay address format of the Frame
	       Relay Service User end point"
	       ::= { frf5ConnEntry 14 }

frf5ConnFrAddress	OBJECT-TYPE
	       SYNTAX    AtmAddress
	       MAX-ACCESS    read-create
	       STATUS    current
	       DESCRIPTION
	       "The address to which the Frame Relay DLCI is
	       connected."
	       ::= { frf5ConnEntry 15 }

frf5ConnAdminStatus	OBJECT-TYPE
	       SYNTAX    INTEGER {
			 up       (1),
			 down     (2),
			 testing  (3)
			 }
	       MAX-ACCESS    read-create
	       STATUS    current
	       DESCRIPTION
	       "Indicates whether the particular virtual circuit
	       is operational. "
	       DEFVAL { up }
	       ::= {frf5ConnEntry 16 }

frf5ConnOperStatus        OBJECT-TYPE
	       SYNTAX    INTEGER {
			 up(1),
			 down(2)
			}
	       MAX-ACCESS    read-only
	       STATUS    current
	       DESCRIPTION
	       " The current operational status of the interworking
	       connection"
	       ::= {frf5ConnEntry 17 }

frf5ConnCreationTime    OBJECT-TYPE
	       SYNTAX    TimeTicks
	       MAX-ACCESS    read-only
	       STATUS    current
	       DESCRIPTION
	       "The value of sysUpTime when the virtual circuit was
	       created"
	       ::= {frf5ConnEntry 18 }

frf5ConnTimeChange  OBJECT-TYPE
	       SYNTAX    TimeTicks
	       MAX-ACCESS    read-only
	       STATUS    current
	       DESCRIPTION
	       "The value of sysUpTime (MIB II) when last there was a
	       change in the virtual circuit state "
	       ::= { frf5ConnEntry 19 }

------------------------------------------------------------------------
-- This table defines entries containing configuration and statistics
-- objects at an ATM VCC level


frf5extDlcmiTable    OBJECT-TYPE
	SYNTAX  SEQUENCE OF Frf5extDlcmiEntry
	MAX-ACCESS  not-accessible
	STATUS  current
	DESCRIPTION
		"The Parameters for the Data Link Connection
		Management Interface corresponding to a given
		ifEntry. These parameters are logical
		extensions to those contained within the
		object frDlcmiTable in RFC1315."
	::= { frf5 2 }

frf5extDlcmiEntry    OBJECT-TYPE
	SYNTAX  Frf5extDlcmiEntry
	MAX-ACCESS  not-accessible
	STATUS  current
	DESCRIPTION
		"The Parameters for the Data Link Connection
		Management Interface."
	INDEX   { frf5extDlmciAtmIf, frf5extDlcmiAtmVpi,
		  frf5extDlcmiAtmVci }
	::= { frf5extDlcmiTable 1 }

Frf5extDlcmiEntry ::= SEQUENCE {
	frf5extDlmciAtmIf			Integer32,
	frf5extDlcmiAtmVpi			Integer32,
	frf5extDlcmiAtmVci			Integer32,
	frf5extDlcmiProfileLmiIndex		Integer32,
	frf5extDlcmiProfileFrf5Index		Integer32,
	frf5extDlcmiStatsMonitor		INTEGER,
	frf5extDlcmiStatsEnabledTimeStamp	TimeTicks,
	frf5extDlcmiLmiDlci			INTEGER,
	frf5extDlcmiLmiFlowControl		INTEGER,
	frf5extDlcmiLmiBandwidthControl		INTEGER,
	frf5extDlcmiRxAbortedFrames		Counter32,
	frf5extDlcmiRcvCrcErrors		Counter32,
	frf5extDlcmiRcvShortFrames		Counter32,
	frf5extDlcmiRcvLongFrames		Counter32,
	frf5extDlcmiRcvInvalidDLCI		Counter32,
	frf5extDlcmiRcvUnknownErrs		Counter32,
	frf5extDlcmiLmiTxStatusResponses	Counter32,
	frf5extDlcmiLmiTxFullStatusResponses	Counter32,
	frf5extDlcmiLmiTxStatusEnquiries	Counter32,
	frf5extDlcmiLmiTxFullStatusEnquiries	Counter32,
	frf5extDlcmiLmiRxStatusResponses	Counter32,
	frf5extDlcmiLmiRxFullStatusResponses	Counter32,
	frf5extDlcmiLmiRxStatusEnquiries	Counter32,
	frf5extDlcmiLmiRxFullStatusEnquiries	Counter32,
	frf5extDlcmiLmiUnknownMessagesRcvd	Counter32,
	frf5extDlcmiLmiStatusLostSequences	Counter32,
	frf5extDlcmiLmiStatusEnqLostSequences	Counter32,
	frf5extDlcmiLmiMissingStatEnquiries	Counter32,
	frf5extDlcmiLmiUnexpectedPVCStatMsg	Counter32,
	frf5extDlcmiLmiUnexpectedDLCI		Counter32,
	frf5extDlcmiLmiStatEnqRatePlus		Counter32,
	frf5extDlcmiLmiInvInfoFrame		Counter32,
	frf5extDlcmiLmiInvFrameHdr		Counter32,
	frf5extDlcmiLmiNoIERepType		Counter32,
	frf5extDlcmiLmiNoIEKeepAlive		Counter32,
	frf5extDlcmiLmiMissingResponses		Counter32,
	frf5extDlcmiLmiUnsuppIERcvd		Counter32,
	frf5extDlcmiDlcis			Counter32,
	frf5extDlcmiUserLinkRelErrors		Counter32,
	frf5extDlcmiUserProtErrors		Counter32,
	frf5extDlcmiUserChanInactive		Counter32,
	frf5extDlcmiNetLinkRelErrors		Counter32,
	frf5extDlcmiNetProtErrors		Counter32,
	frf5extDlcmiNetChanInactive		Counter32,
	frf5extDlcmiRootService			Integer32,
	frf5extDlcmiRootDlci			Integer32
}

frf5extDlmciAtmIf OBJECT-TYPE
		SYNTAX  Integer32
		MAX-ACCESS  read-only
		STATUS  current
		DESCRIPTION
		"The Atm interface index corresponds to the port.
		 This is also the index of the portTable."
		::= { frf5extDlcmiEntry 1 }

frf5extDlcmiAtmVpi  OBJECT-TYPE
		SYNTAX  Integer32
		MAX-ACCESS  read-only
		STATUS  current
		DESCRIPTION
		"VPI of the ATM VCC on which FR DLCIs are multiplexed"
		::= { frf5extDlcmiEntry 2 }

frf5extDlcmiAtmVci  OBJECT-TYPE
		SYNTAX  Integer32
		MAX-ACCESS  read-only
		STATUS  current
		DESCRIPTION
		"VCI of the ATM VCC on which FR DLCIs are multiplexed "
		::= { frf5extDlcmiEntry 3 }

frf5extDlcmiProfileLmiIndex   OBJECT-TYPE
		SYNTAX  Integer32
		MAX-ACCESS  read-write
		STATUS  current
		DESCRIPTION
		"Index for the LMI profile for this ATM VCC."
		DEFVAL { 0 }
		::= { frf5extDlcmiEntry 4 }

frf5extDlcmiProfileFrf5Index OBJECT-TYPE
	       SYNTAX    Integer32
	       MAX-ACCESS    read-write
	       STATUS    current
	       DESCRIPTION
	       "Index for the FRF5 profile, in the fore-profile.mib."
     	       DEFVAL { 0 }
	       ::= { frf5extDlcmiEntry 5 }

frf5extDlcmiStatsMonitor   OBJECT-TYPE
		SYNTAX  INTEGER {
				enabled (1),
				disabled (2)
				}
		MAX-ACCESS  read-write
		STATUS  current
		DESCRIPTION
		"This object specifies whether statistics (ATM VCC and
		 FR DLCI statistics) are to be counted at an ATM VCC
		 level. When the state changes from
		 enabled to disabled, all the related statistics will be
		 frozen at their current value. When the state changes
		 from disabled to enabled, all related statistics
		 will be reset (zeroed). Note that this Monitor is
		 overridden by the netmod level nmFramStatsMonitor.
		 Refer to fore-fram.mib for more details."
		DEFVAL { disabled }
		::= { frf5extDlcmiEntry 6 }

frf5extDlcmiStatsEnabledTimeStamp  OBJECT-TYPE
		SYNTAX  TimeTicks
		MAX-ACCESS  read-only
		STATUS  current
		DESCRIPTION
		"This object reflects the point in time, with reference
		to sysUpTime, either when frf5extDlcmiStatsMonitor is set
		to enabled or when nmFramStatsMonitor is set to
		enabled. The time will reflect the last StatsMonitor to
		be enabled. The timestamp provides a starting timestamp
		for the current statistics that are being counted."
		::=  { frf5extDlcmiEntry 7 }

frf5extDlcmiLmiDlci  OBJECT-TYPE
		SYNTAX  INTEGER {
				q933AnnexA(0),
				stratacom(1023)
				}
		MAX-ACCESS  read-only
		STATUS  current
		DESCRIPTION
		"The dlci upon which LMI traffic will be broadcast.
		If Q933-AnnexA=0, otherwise STRATACOM=1023."
		::= { frf5extDlcmiEntry  8 }


frf5extDlcmiLmiFlowControl   OBJECT-TYPE
		SYNTAX  INTEGER {
				enabled(1),
				disabled(2)
				}
		MAX-ACCESS  read-write
		STATUS  current
		DESCRIPTION
		"Specifies whether STRATACOM LMI based (R-bit)
		notification performs flow control for the
		Circuits on this interface."
		DEFVAL { disabled }
		::= { frf5extDlcmiEntry 9 }

frf5extDlcmiLmiBandwidthControl   OBJECT-TYPE
		SYNTAX  INTEGER {
				enabled(1),
				disabled(2)
				}
		MAX-ACCESS  read-write
		STATUS  current
		DESCRIPTION
		"Specifies whether STRATACOM LMI based CIR
		notification affects the CIR flow control
		parameters for the connections on this interface."
		DEFVAL{ disabled }
		::= { frf5extDlcmiEntry 10 }

frf5extDlcmiRxAbortedFrames  OBJECT-TYPE
		SYNTAX    Counter32
		MAX-ACCESS    read-only
		STATUS    current
		DESCRIPTION
		"The number of aborted frames received on this
		Frame Relay logical interface. A frame is considered
		aborted after receiving 7 or more continuous ones."
		::= {frf5extDlcmiEntry 11 }


frf5extDlcmiRcvCrcErrors   OBJECT-TYPE
		SYNTAX   Counter32
		MAX-ACCESS   read-only
		STATUS   current
		DESCRIPTION
		"Specifies the number of frames receive with CRC errors on
		this interface."
		::= { frf5extDlcmiEntry 12 }


frf5extDlcmiRcvShortFrames OBJECT-TYPE
		SYNTAX   Counter32
		MAX-ACCESS   read-only
		STATUS   current
		DESCRIPTION
		"The number of frames containing less than 5
		octets received on this interface."
		::= { frf5extDlcmiEntry  13 }

frf5extDlcmiRcvLongFrames OBJECT-TYPE
		SYNTAX   Counter32
		MAX-ACCESS   read-only
		STATUS   current
		DESCRIPTION
		"The number of frames containing greater than 8191
		octets received on this interface."
		::= { frf5extDlcmiEntry 14 }

frf5extDlcmiRcvInvalidDLCI OBJECT-TYPE
		SYNTAX   Counter32
		MAX-ACCESS   read-only
		STATUS   current
		DESCRIPTION
		"The number of frames with an invalid DLCI received
		on this interface."
		::= { frf5extDlcmiEntry 15 }


frf5extDlcmiRcvUnknownErrs OBJECT-TYPE
	       SYNTAX   Counter32
	       MAX-ACCESS   read-only
	       STATUS   current
	       DESCRIPTION
	       "The number of frames with other errors received
	       on this interface."
	       ::= { frf5extDlcmiEntry 16 }


frf5extDlcmiLmiTxStatusResponses OBJECT-TYPE
		SYNTAX  Counter32
		MAX-ACCESS  read-only
		STATUS  current
		DESCRIPTION
		"Number of STATUS messages transmitted on this
		interface."
		::= { frf5extDlcmiEntry  17 }

frf5extDlcmiLmiTxFullStatusResponses   OBJECT-TYPE
		SYNTAX  Counter32
		MAX-ACCESS  read-only
		STATUS  current
		DESCRIPTION
		"Number of  STATUS  messages with full status Information Element
		transmitted on this interface."
		::= { frf5extDlcmiEntry  18 }


frf5extDlcmiLmiTxStatusEnquiries OBJECT-TYPE
		SYNTAX  Counter32
		MAX-ACCESS  read-only
		STATUS  current
		DESCRIPTION
		"Number of STATUS ENQUIRY messages transmitted on this
		interface."
		::= { frf5extDlcmiEntry 19 }


frf5extDlcmiLmiTxFullStatusEnquiries     OBJECT-TYPE
		SYNTAX  Counter32
		MAX-ACCESS  read-only
		STATUS  current
		DESCRIPTION
		"Number of STATUS ENQUIRY  messages with full status Information Element
		transmitted on this interface."
		::= { frf5extDlcmiEntry 20 }

frf5extDlcmiLmiRxStatusResponses       OBJECT-TYPE
		SYNTAX  Counter32
		MAX-ACCESS  read-only
		STATUS  current
		DESCRIPTION
		"Number of STATUS messages received on this
		interface."
		::= { frf5extDlcmiEntry 21 }

frf5extDlcmiLmiRxFullStatusResponses        OBJECT-TYPE
		SYNTAX  Counter32
		MAX-ACCESS  read-only
		STATUS  current
		DESCRIPTION
		"Number of STATUS messages with full status Information Element
		received on this interface."
		::= { frf5extDlcmiEntry 22 }

frf5extDlcmiLmiRxStatusEnquiries   OBJECT-TYPE
		SYNTAX  Counter32
		MAX-ACCESS  read-only
		STATUS  current
		DESCRIPTION
		"Number of STATUS messages received on this interface."
		::= { frf5extDlcmiEntry 23 }

frf5extDlcmiLmiRxFullStatusEnquiries OBJECT-TYPE
		SYNTAX  Counter32
		MAX-ACCESS  read-only
		STATUS  current
		DESCRIPTION
		"Number of STATUS ENQUIRY messages with full status
		Information Element receive on this interface."
		::= { frf5extDlcmiEntry 24 }

frf5extDlcmiLmiUnknownMessagesRcvd  OBJECT-TYPE
	       SYNTAX  Counter32
	       MAX-ACCESS  read-only
	       STATUS  current
	       DESCRIPTION
	       "Number of Unknown LMI messages received on this
	       interface."
	       ::= { frf5extDlcmiEntry  25 }

frf5extDlcmiLmiStatusLostSequences OBJECT-TYPE
	      SYNTAX   Counter32
	      MAX-ACCESS   read-only
	      STATUS   current
	      DESCRIPTION
	      "The total number of times a loss of sequencing in
	      received STATUS  messages was detected on this
	      interface."
	      ::= { frf5extDlcmiEntry  26 }


frf5extDlcmiLmiStatusEnqLostSequences OBJECT-TYPE
	      SYNTAX   Counter32
	      MAX-ACCESS   read-only
	      STATUS   current
	      DESCRIPTION
	      "The total number of times a loss of sequencing in
	      received STATUS ENQUIRY  messages was detected on this
	      interface."
	      ::= { frf5extDlcmiEntry  27 }


frf5extDlcmiLmiMissingStatEnquiries  OBJECT-TYPE
	      SYNTAX   Counter32
	      MAX-ACCESS   read-only
	      STATUS   current
	      DESCRIPTION
	      "The number of times an expected STATUS ENQUIRY message
	      was not received within the expected time on this
	      interface."
	      ::= { frf5extDlcmiEntry 28 }


frf5extDlcmiLmiUnexpectedPVCStatMsg OBJECT-TYPE
	      SYNTAX   Counter32
	      MAX-ACCESS   read-only
	      STATUS   current
	      DESCRIPTION
	      "The number of LMI messages that were received with
	      unexpected PVC STATUS Information Element on this interface."
	      ::= { frf5extDlcmiEntry 29 }


frf5extDlcmiLmiUnexpectedDLCI  OBJECT-TYPE
	     SYNTAX   Counter32
	     MAX-ACCESS   read-only
	     STATUS   current
	     DESCRIPTION
	     "The number of STATUS messages received with unconfigured
	     DLCI"
	     ::= { frf5extDlcmiEntry 30 }

frf5extDlcmiLmiStatEnqRatePlus  OBJECT-TYPE
	     SYNTAX   Counter32
	     MAX-ACCESS   read-only
	     STATUS   current
	     DESCRIPTION
	     "The number of times the STATUS ENQUIRY message was
	     received more frequently than expected. For STRATACOM
	     only"
	    ::= { frf5extDlcmiEntry 31 }

frf5extDlcmiLmiInvInfoFrame OBJECT-TYPE
	     SYNTAX   Counter32
	     MAX-ACCESS   read-only
	     STATUS   current
	     DESCRIPTION
	     "The number of times an LMI message was received with
	     information type not equal to unnumbered information
	     type."
	     ::= { frf5extDlcmiEntry 32 }


frf5extDlcmiLmiInvFrameHdr  OBJECT-TYPE
	     SYNTAX   Counter32
	     MAX-ACCESS   read-only
	     STATUS   current
	     DESCRIPTION
	     "The number of LMI frames received with error in the
	     header bits."
	     ::= { frf5extDlcmiEntry 33 }


frf5extDlcmiLmiNoIERepType  OBJECT-TYPE
	     SYNTAX   Counter32
	     MAX-ACCESS   read-only
	     STATUS   current
	     DESCRIPTION
	     "The number of times an LMI frame was received with
	     missing Report Type Information Element"
	     ::= { frf5extDlcmiEntry 34 }


frf5extDlcmiLmiNoIEKeepAlive OBJECT-TYPE
	     SYNTAX   Counter32
	     MAX-ACCESS   read-only
	     STATUS   current
	     DESCRIPTION
	     "The number of times an LMI frame was received with
	     missing Link Integrity Verification Information Element."
	     ::= { frf5extDlcmiEntry 35 }


frf5extDlcmiLmiMissingResponses OBJECT-TYPE
	     SYNTAX   Counter32
	     MAX-ACCESS   read-only
	     STATUS   current
	     DESCRIPTION
	     "The total number of times a timeout occurred without
	     receiving a response to an LMI request by this interface."
	     ::= { frf5extDlcmiEntry 36 }

frf5extDlcmiLmiUnsuppIERcvd  OBJECT-TYPE
	     SYNTAX  Counter32
	     MAX-ACCESS  read-only
	     STATUS  current
	     DESCRIPTION
	     "The number of LMI messages received with unknown
	     Information Element."
	     ::= { frf5extDlcmiEntry 37 }

frf5extDlcmiDlcis  OBJECT-TYPE
	     SYNTAX  Counter32
	     MAX-ACCESS  read-only
	     STATUS  current
	     DESCRIPTION
	     "The number of permanent DLCIs established on this ATM
	     logical interface"
	     ::= { frf5extDlcmiEntry 38 }

frf5extDlcmiUserLinkRelErrors OBJECT-TYPE
     SYNTAX  Counter32
     MAX-ACCESS  read-only
     STATUS  current
     DESCRIPTION
	     "The number of user-side local in-channel
	     signalling link reliability errors (i.e., non-
	     receipt of Status/Status Enquiry messages or
	     invalid sequence numbers in a Link Integrity
	     Verification Information Element) for this UNI/NNI
	     logical port.  If the logical port is not
	     performing user-side procedures, then this value
	     is equal to noSuchName."
     ::= { frf5extDlcmiEntry 39 }

 frf5extDlcmiUserProtErrors OBJECT-TYPE
     SYNTAX  Counter32
     MAX-ACCESS  read-only
     STATUS  current
     DESCRIPTION
	     "The number of user-side local in-channel
	     signalling protocol errors (i.e., protocol
	     discriminator, message type, call reference, and
	     mandatory information element errors) for this
	     UNI/NNI logical port.  If the logical port is not
	     performing user-side procedures, then this value
	     is equal to noSuchName."
     ::= { frf5extDlcmiEntry 40 }

 frf5extDlcmiUserChanInactive OBJECT-TYPE
     SYNTAX  Counter32
     MAX-ACCESS  read-only
     STATUS  current
     DESCRIPTION
	     "The number of times the user-side channel was
	     declared inactive (i.e., N392 errors in N393
	     events) for this UNI/NNI logical port. If the
	     logical port is not performing user-side
	     procedures, then this value is equal to
	     noSuchName."
     ::= { frf5extDlcmiEntry 41 }

 frf5extDlcmiNetLinkRelErrors OBJECT-TYPE
     SYNTAX  Counter32
     MAX-ACCESS  read-only
     STATUS  current
     DESCRIPTION
	     "The number of network-side local in-channel
	     signalling link reliability errors (i.e., non-
	     receipt of Status/Status Enquiry messages or
	     invalid sequence numbers in a Link Integrity
	     Verification Information Element) for this UNI/NNI
	     logical port.  If the logical port is not
	     performing network-side procedures, then this
	     value is equal to noSuchName."
     ::= { frf5extDlcmiEntry 42 }

 frf5extDlcmiNetProtErrors OBJECT-TYPE
     SYNTAX  Counter32
     MAX-ACCESS  read-only
     STATUS  current
     DESCRIPTION
	     "The number of network-side local in-channel
	     signalling protocol errors (i.e., protocol
	     discriminator, message type, call reference, and
	     mandatory information element errors) for this
	     UNI/NNI logical port.  If the logical port is not
	     performing network-side procedures, then this
	     value is equal to noSuchName."
     ::= { frf5extDlcmiEntry 43 }

 frf5extDlcmiNetChanInactive OBJECT-TYPE
     SYNTAX  Counter32
     MAX-ACCESS  read-only
     STATUS  current
     DESCRIPTION
	     "The number of times the network-side channel was
	     declared inactive (i.e., N392 errors in N393
	     events) for this UNI/NNI logical port.  If the
	     logical port is not performing network-side
	     procedures, then this value is equal to
	     noSuchName."
     ::= { frf5extDlcmiEntry 44 }

 frf5extDlcmiRootService OBJECT-TYPE
     SYNTAX  Integer32
     MAX-ACCESS  read-only
     STATUS  current
     DESCRIPTION
	     "The service ifindex of the first connection belonging to
	      this VCC."
     ::= { frf5extDlcmiEntry 45 }

 frf5extDlcmiRootDlci OBJECT-TYPE
     SYNTAX  Integer32
     MAX-ACCESS  read-only
     STATUS  current
     DESCRIPTION
	     "The dlci of the first connection belonging to this VCC."
     ::= { frf5extDlcmiEntry 46 }

END

------------------------------------------------------------------------
