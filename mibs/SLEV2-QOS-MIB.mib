--
-- slev2-qos-mib.mib
-- MIB generated by MG-SOFT Visual MIB Builder Version 6.0  Build 88
-- Tuesday, July 28, 2015 at 15:13:50
--

	SLEV2-QOS-MIB DEFINITIONS ::= BEGIN
 
		IMPORTS
			sleV2Mgmt			
				FROM DASAN-SMI			
			InterfaceIndex			
				FROM IF-MIB			
			InetAddressType, InetAddress, InetAddressPrefixLength			
				FROM INET-ADDRESS-MIB			
			SleControlStatusType, SleControlRequestResultType			
				FROM SLE-TC-MIB			
			OBJECT-GROUP, NOTIFICATION-GROUP			
				FROM SNMPv2-CONF			
			TimeTicks, IpAddress, Integer32, Gauge32, Counter32, 
			Counter64, OBJECT-TYPE, MODULE-IDENTITY, NOTIFICATION-TYPE			
				FROM SNMPv2-SMI			
			MacAddress, TEXTUAL-CONVENTION			
				FROM SNMPv2-TC;
	
	
		-- 1.3.6.1.4.1.6296.102.10
		sleV2QoS MODULE-IDENTITY 
			LAST-UPDATED "200605051406Z"		-- May 05, 2006 at 14:06 GMT
			ORGANIZATION 
				"Organization."
			CONTACT-INFO 
				"Contact-info."
			DESCRIPTION 
				"sleV2QoS"
			::= { sleV2Mgmt 10 }

		
	
--
-- Type definitions
--
	
		IntFlowIndex ::= INTEGER (1..1024)

		IntClassIndex ::= INTEGER (1..1024)

		IntPolicerIndex ::= INTEGER (1..1024)

		IntPolicyIndex ::= INTEGER (1..1024)

		OctetName ::= OCTET STRING (SIZE (1..64))

		IntEthernetType ::= INTEGER (-1 | 0..65535)

		Int8021p ::= INTEGER (-1 | 0..7)

		IntIpAddrMask ::= INTEGER (0..32)

		IntToS ::= INTEGER (-1 | 0..255)

		IntPktLen ::= INTEGER (-1 | 21..65535)

		IntProtocolType ::= INTEGER (-1 | 0..255)

		IntL4Port ::= INTEGER (-1 | 0..65535)

		IntIcmpType ::= INTEGER (-1 | 0..255)

		IntIcmpCode ::= INTEGER (-1 | 0..255)

		IntInternetProtocolFlag ::= INTEGER
			{
			nothing(-1),
			tcp(1),
			ucp(2),
			icmp(3)
			}

		IntRulePriority ::= INTEGER
			{
			nothing(-1),
			low(1),
			medium(2),
			high(3),
			highest(4),
			lowest(5),
			highMiddle(6)
			}

		IntFlowClass ::= INTEGER
			{
			nothing(-1),
			flow(1),
			class(2),
			both(4)
			}

		IntVlanID ::= INTEGER (-1 | 1..4094)

		IntQueue ::= INTEGER (-1 | 0..7)

		IntDP ::= INTEGER (-1 | 0..2)

		IntCoS ::= INTEGER (-1 | 0..7)

		IntDscp ::= INTEGER (-1 | 0..63)

		IntIpPrecedence ::= INTEGER (-1 | 0..7)

		IntDstMacOrEgressPorts ::= INTEGER
			{
			nothing(-1),
			dstMac(1),
			egressPorts(2)
			}

		IntMarkMode ::= INTEGER
			{
			nothing(-1),
			markByEntry(1),
			dSCPAttribute(2),
			entryDSCP(3)
			}

		IntMeterMode ::= INTEGER
			{
			nothing(-1),
			rateLimit(1),
			color(2),
			minmaxbandwidth(3)
			}

		IntColorType ::= INTEGER
			{
			nothing(-1),
			srTCM(1),
			trTCM(2)
			}

		IntColorMode ::= INTEGER
			{
			nothing(-1),
			blind(1),
			aware(2)
			}

		IntColorAwareMode ::= INTEGER
			{
			nothing(-1),
			unprotected(1),
			protected(2)
			}

		IntColorCIR ::= INTEGER (-1 | 1..1000000)

		IntColorCBS ::= INTEGER (-1 | 1..4000)

		IntColorPIR ::= INTEGER (-1 | 1..1000000)

		IntColorPBS ::= INTEGER (-1 | 1..4000)

		IntColorEBS ::= INTEGER (-1 | 1..4000)

		IntColorAction ::= INTEGER
			{
			nothing(-1),
			drop(1),
			marking(2),
			dropPrecedence(3),
			dropPrecedenceRed(4),
			dropPrecedenceYellow(5),
			dropPrecedenceGreen(6)
			}

		IntCounterMode ::= INTEGER
			{
			nothing(-1),
			byte(1),
			packet(2)
			}

		IntInterfaceIndex ::= INTEGER (-1 | 1..512)

		IntFlowOrClass ::= INTEGER
			{
			flow(1),
			class(2)
			}

		IntL2BaseRemarkMode ::= INTEGER
			{
			remarkByQueue(1),
			remarkByPriority(2)
			}

		IntColorIndex ::= INTEGER
			{
			green(1),
			yellow(2),
			red(3)
			}

		IntDSCPIndex ::= INTEGER (1..64)

		IntQueueCoSIndex ::= INTEGER (1..8)

		IntIpPktPriorityType ::= INTEGER
			{
			nothing(-1),
			iPPrecedence(1),
			diffServ(2),
			ipToS(3)
			}

		IntEnableFlag ::= INTEGER
			{
			enable(1),
			disable(2)
			}

		IntAvrgCounterMode ::= INTEGER
			{
			nothing(-1),
			byte(1)
			}

	
--
-- Textual conventions
--
	
		MacAddressMask ::= TEXTUAL-CONVENTION
			STATUS current
			DESCRIPTION 
				"Represents Mac address Mask.
				"
			SYNTAX OCTET STRING (SIZE (6))

	
--
-- Node definitions
--
	
		-- 1.3.6.1.4.1.6296.102.10.1
		sleV2QoSBase OBJECT IDENTIFIER ::= { sleV2QoS 1 }

		
		-- 1.3.6.1.4.1.6296.102.10.2
		sleV2QoS4 OBJECT IDENTIFIER ::= { sleV2QoS 2 }

		
		-- 1.3.6.1.4.1.6296.102.10.2.1
		sleV2QoS4Base OBJECT IDENTIFIER ::= { sleV2QoS4 1 }

		
		-- 1.3.6.1.4.1.6296.102.10.2.1.1
		sleV2QoS4BaseInfo OBJECT IDENTIFIER ::= { sleV2QoS4Base 1 }

		
		-- 1.3.6.1.4.1.6296.102.10.2.1.1.1
		sleV2QoS4BaseFlowMode OBJECT-TYPE
			SYNTAX INTEGER
				{
				default(1),
				extension(2)
				}
			MAX-ACCESS read-only
			STATUS current
			DESCRIPTION
				"flow mode
				default : double mode, extension : triple mode"
			::= { sleV2QoS4BaseInfo 1 }

		
		-- 1.3.6.1.4.1.6296.102.10.2.1.2
		sleV2QoS4BaseControl OBJECT IDENTIFIER ::= { sleV2QoS4Base 2 }

		
		-- 1.3.6.1.4.1.6296.102.10.2.1.2.1
		sleV2QoS4BaseControlRequest OBJECT-TYPE
			SYNTAX INTEGER { setFlowMode(1) }
			MAX-ACCESS read-write
			STATUS current
			DESCRIPTION
				"The request of a user command"
			::= { sleV2QoS4BaseControl 1 }

		
		-- 1.3.6.1.4.1.6296.102.10.2.1.2.2
		sleV2QoS4BaseControlStatus OBJECT-TYPE
			SYNTAX SleControlStatusType
			MAX-ACCESS read-only
			STATUS current
			DESCRIPTION
				"The status of user command"
			::= { sleV2QoS4BaseControl 2 }

		
		-- 1.3.6.1.4.1.6296.102.10.2.1.2.3
		sleV2QoS4BaseControlTimer OBJECT-TYPE
			SYNTAX Gauge32
			MAX-ACCESS read-write
			STATUS current
			DESCRIPTION
				"The maximum time for the manager for a long running user command"
			::= { sleV2QoS4BaseControl 3 }

		
		-- 1.3.6.1.4.1.6296.102.10.2.1.2.4
		sleV2QoS4BaseControlTimeStamp OBJECT-TYPE
			SYNTAX TimeTicks
			MAX-ACCESS read-only
			STATUS current
			DESCRIPTION
				"The time stamp of the last command(end of command)"
			::= { sleV2QoS4BaseControl 4 }

		
		-- 1.3.6.1.4.1.6296.102.10.2.1.2.5
		sleV2QoS4BaseControlResult OBJECT-TYPE
			SYNTAX SleControlRequestResultType
			MAX-ACCESS read-only
			STATUS current
			DESCRIPTION
				"The result of the last user command"
			::= { sleV2QoS4BaseControl 5 }

		
		-- 1.3.6.1.4.1.6296.102.10.2.1.2.6
		sleV2QoS4BaseControlFlowMode OBJECT-TYPE
			SYNTAX INTEGER
				{
				default(1),
				extension(2)
				}
			MAX-ACCESS read-write
			STATUS current
			DESCRIPTION
				"flow mode
				default : double mode, extension : triple "
			::= { sleV2QoS4BaseControl 6 }

		
		-- 1.3.6.1.4.1.6296.102.10.2.1.3
		sleV2QoS4BaseNotification OBJECT IDENTIFIER ::= { sleV2QoS4Base 3 }

		
		-- 1.3.6.1.4.1.6296.102.10.2.1.3.1
		sleV2QoS4BaseFlowModeChanged NOTIFICATION-TYPE
			OBJECTS { sleV2QoS4BaseControlRequest, sleV2QoS4BaseControlTimeStamp, sleV2QoS4BaseControlResult, sleV2QoS4BaseControlFlowMode }
			STATUS current
			DESCRIPTION 
				"Description."
			::= { sleV2QoS4BaseNotification 1 }

		
		-- 1.3.6.1.4.1.6296.102.10.2.2
		sleV2QoS4Flow OBJECT IDENTIFIER ::= { sleV2QoS4 2 }

		
		-- 1.3.6.1.4.1.6296.102.10.2.2.1
		sleV2QoS4FlowInfo OBJECT IDENTIFIER ::= { sleV2QoS4Flow 1 }

		
		-- 1.3.6.1.4.1.6296.102.10.2.2.1.1
		sleV2QoS4FlowTable OBJECT-TYPE
			SYNTAX SEQUENCE OF SleV2QoS4FlowEntry
			MAX-ACCESS not-accessible
			STATUS current
			DESCRIPTION
				"flow table."
			::= { sleV2QoS4FlowInfo 1 }

		
		-- 1.3.6.1.4.1.6296.102.10.2.2.1.1.1
		sleV2QoS4FlowEntry OBJECT-TYPE
			SYNTAX SleV2QoS4FlowEntry
			MAX-ACCESS not-accessible
			STATUS current
			DESCRIPTION
				"key: sleV2QoS4FlowIndex"
			INDEX { sleV2QoS4FlowIndex }
			::= { sleV2QoS4FlowTable 1 }

		
		SleV2QoS4FlowEntry ::=
			SEQUENCE { 
				sleV2QoS4FlowIndex
					INTEGER,
				sleV2QoS4FlowName
					OctetName,
				sleV2QoS4FlowEthernetType
					IntEthernetType,
				sleV2QoS4FlowSrcMacAddr
					MacAddress,
				sleV2QoS4FlowSrcMacAddrMask
					MacAddressMask,
				sleV2QoS4FlowDstMacAddr
					MacAddress,
				sleV2QoS4FlowDstMacAddrMask
					MacAddressMask,
				sleV2QoS4Flow8021p
					Int8021p,
				sleV2QoS4FlowSrcIpAddr
					IpAddress,
				sleV2QoS4FlowSrcIpAddrMask
					IntIpAddrMask,
				sleV2QoS4FlowDstIpAddr
					IpAddress,
				sleV2QoS4FlowDstIpAddrMask
					IntIpAddrMask,
				sleV2QoS4FlowIpPktPriorityType
					IntIpPktPriorityType,
				sleV2QoS4FlowIpPktPriority
					Integer32,
				sleV2QoS4FlowPktLen
					IntPktLen,
				sleV2QoS4FlowProtocolType
					IntProtocolType,
				sleV2QoS4FlowTcpSrcStartPort
					IntL4Port,
				sleV2QoS4FlowTcpSrcEndPort
					IntL4Port,
				sleV2QoS4FlowTcpDstStartPort
					IntL4Port,
				sleV2QoS4FlowTcpDstEndPort
					IntL4Port,
				sleV2QoS4FlowTcpFlag
					BITS,
				sleV2QoS4FlowUdpSrcStartPort
					IntL4Port,
				sleV2QoS4FlowUdpSrcEndPort
					IntL4Port,
				sleV2QoS4FlowUdpDstStartPort
					IntL4Port,
				sleV2QoS4FlowUdpDstEndPort
					IntL4Port,
				sleV2QoS4FlowIcmpType
					IntIcmpType,
				sleV2QoS4FlowIcmpCode
					IntIcmpCode,
				sleV2QoS4FlowHdrlen
					INTEGER,
				sleV2QoS4FlowHdrError
					IntEnableFlag,
				sleV2QoS4FlowInnerVlan
					Integer32,
				sleV2QoS4FlowInner8021p
					Integer32,
				sleV2QoS4FlowMacFlag
					INTEGER,
				sleV2QoS4FlowIpFlag
					INTEGER,
				sleV2QoS4FlowMacDlf
					INTEGER,
				sleV2QoS4FlowTagType
					INTEGER,
				sleV2QoS4FlowInPktTagVid
					Integer32,
				sleV2QoS4FlowInPktTagCfi
					Integer32,
				sleV2QoS4FlowInPktTagCoS
					Integer32,
				sleV2QoS4FlowOutPktTagVid
					Integer32,
				sleV2QoS4FlowOutPktTagCfi
					Integer32,
				sleV2QoS4FlowOutPktTagCoS
					Integer32,
				sleV2QoS4FlowFlowAlias
					OCTET STRING,
				sleV2QoSFlowInetAddrType
					InetAddressType,
				sleV2QoSFlowSrcInetAddr
					InetAddress,
				sleV2QoSFlowDstInetAddr
					InetAddress,
				sleV2QoSFlowSrcInetAddrLen
					InetAddressPrefixLength,
				sleV2QoSFlowDstInetAddrLen
					InetAddressPrefixLength,
				sleV2QoSFlowTrafficClass
					INTEGER,
				sleV2QoSFlowFlowLabel
					INTEGER,
				sleV2QoS4FlowOuterVlan
					Integer32,
				sleV2QoS4FlowOuter8021p
					Integer32,
				sleV2QoS4FlowOnuCircuitId
					Integer32
			 }

		-- 1.3.6.1.4.1.6296.102.10.2.2.1.1.1.1
		sleV2QoS4FlowIndex OBJECT-TYPE
			SYNTAX INTEGER (1..1024)
			MAX-ACCESS read-only
			STATUS current
			DESCRIPTION
				"The index of flow"
			::= { sleV2QoS4FlowEntry 1 }

		
		-- 1.3.6.1.4.1.6296.102.10.2.2.1.1.1.2
		sleV2QoS4FlowName OBJECT-TYPE
			SYNTAX OctetName
			MAX-ACCESS read-only
			STATUS current
			DESCRIPTION
				"The name of flow"
			::= { sleV2QoS4FlowEntry 2 }

		
		-- 1.3.6.1.4.1.6296.102.10.2.2.1.1.1.3
		sleV2QoS4FlowEthernetType OBJECT-TYPE
			SYNTAX IntEthernetType
			MAX-ACCESS read-only
			STATUS current
			DESCRIPTION
				"The ethernet type value in incoming frames
				The value of -1 means any(not set).
				"
			::= { sleV2QoS4FlowEntry 3 }

		
		-- 1.3.6.1.4.1.6296.102.10.2.2.1.1.1.4
		sleV2QoS4FlowSrcMacAddr OBJECT-TYPE
			SYNTAX MacAddress
			MAX-ACCESS read-only
			STATUS current
			DESCRIPTION
				"The source mac address
				The value of 00:00:00:00:00:00 is any(not set)
				"
			::= { sleV2QoS4FlowEntry 4 }

		
		-- 1.3.6.1.4.1.6296.102.10.2.2.1.1.1.5
		sleV2QoS4FlowSrcMacAddrMask OBJECT-TYPE
			SYNTAX MacAddressMask
			MAX-ACCESS read-only
			STATUS current
			DESCRIPTION
				"The mask of the source mac address
				The value of 00:00:00:00:00:00 is any(not set)
				"
			::= { sleV2QoS4FlowEntry 5 }

		
		-- 1.3.6.1.4.1.6296.102.10.2.2.1.1.1.6
		sleV2QoS4FlowDstMacAddr OBJECT-TYPE
			SYNTAX MacAddress
			MAX-ACCESS read-only
			STATUS current
			DESCRIPTION
				"The destination mac address
				The value of 00:00:00:00:00:00 is any(not set)
				"
			::= { sleV2QoS4FlowEntry 6 }

		
		-- 1.3.6.1.4.1.6296.102.10.2.2.1.1.1.7
		sleV2QoS4FlowDstMacAddrMask OBJECT-TYPE
			SYNTAX MacAddressMask
			MAX-ACCESS read-only
			STATUS current
			DESCRIPTION
				"The mask of the destination mac address
				The value of 00:00:00:00:00:00 is any(not set)
				"
			::= { sleV2QoS4FlowEntry 7 }

		
		-- 1.3.6.1.4.1.6296.102.10.2.2.1.1.1.8
		sleV2QoS4Flow8021p OBJECT-TYPE
			SYNTAX Int8021p
			MAX-ACCESS read-only
			STATUS current
			DESCRIPTION
				"The value of the IEEE802.1p priority in the packet
				The value of -1 means any(not set)
				"
			::= { sleV2QoS4FlowEntry 8 }

		
		-- 1.3.6.1.4.1.6296.102.10.2.2.1.1.1.9
		sleV2QoS4FlowSrcIpAddr OBJECT-TYPE
			SYNTAX IpAddress
			MAX-ACCESS read-only
			STATUS current
			DESCRIPTION
				"The IP address to match against the packet's source IP address.
				The value of 0.0.0.0 means any(not set)
				"
			::= { sleV2QoS4FlowEntry 9 }

		
		-- 1.3.6.1.4.1.6296.102.10.2.2.1.1.1.10
		sleV2QoS4FlowSrcIpAddrMask OBJECT-TYPE
			SYNTAX IntIpAddrMask
			MAX-ACCESS read-only
			STATUS current
			DESCRIPTION
				"The mask of source IP address
				The value of -1 means any(not set)
				"
			::= { sleV2QoS4FlowEntry 10 }

		
		-- 1.3.6.1.4.1.6296.102.10.2.2.1.1.1.11
		sleV2QoS4FlowDstIpAddr OBJECT-TYPE
			SYNTAX IpAddress
			MAX-ACCESS read-only
			STATUS current
			DESCRIPTION
				"The IP address to match against the packet's destination IP address.
				The value of 0.0.0.0 means any(not set)
				"
			::= { sleV2QoS4FlowEntry 11 }

		
		-- 1.3.6.1.4.1.6296.102.10.2.2.1.1.1.12
		sleV2QoS4FlowDstIpAddrMask OBJECT-TYPE
			SYNTAX IntIpAddrMask
			MAX-ACCESS read-only
			STATUS current
			DESCRIPTION
				"The mask of destination IP address
				The value of -1 means any(not set)
				"
			::= { sleV2QoS4FlowEntry 12 }

		
		-- 1.3.6.1.4.1.6296.102.10.2.2.1.1.1.13
		sleV2QoS4FlowIpPktPriorityType OBJECT-TYPE
			SYNTAX IntIpPktPriorityType
			MAX-ACCESS read-only
			STATUS current
			DESCRIPTION
				"The Priority type of incoming IP packet
				(specify a type of sleUserFlowIpPktPriority)
				"
			::= { sleV2QoS4FlowEntry 13 }

		
		-- 1.3.6.1.4.1.6296.102.10.2.2.1.1.1.14
		sleV2QoS4FlowIpPktPriority OBJECT-TYPE
			SYNTAX Integer32
			MAX-ACCESS read-only
			STATUS current
			DESCRIPTION
				"The Priority value of incoming IP packet
				If type is 1, this value's range is 0-7.
				If type is 2, this value's range is 0-63.
				If type is 3, this value's range is 0-255.
				"
			::= { sleV2QoS4FlowEntry 14 }

		
		-- 1.3.6.1.4.1.6296.102.10.2.2.1.1.1.15
		sleV2QoS4FlowPktLen OBJECT-TYPE
			SYNTAX IntPktLen
			MAX-ACCESS read-only
			STATUS current
			DESCRIPTION
				"The packet length of the incoming packet
				The value of -1 means any(not set)
				"
			::= { sleV2QoS4FlowEntry 15 }

		
		-- 1.3.6.1.4.1.6296.102.10.2.2.1.1.1.16
		sleV2QoS4FlowProtocolType OBJECT-TYPE
			SYNTAX IntProtocolType
			MAX-ACCESS read-only
			STATUS current
			DESCRIPTION
				"The type of IP protocol
				The flat internet protocol is from sleV2QoS4FlowTcpSrcStartPort to sleV2QoS4FlowIcmpCode
				If the value is tcp(6),
				From sleV2QoS4FlowTcpSrcStartPort to sleV2QoS4FlowTcpFlag value is available
				If the value is u¿¡(17),
				From sleV2QoS4FlowUdpSrcStartPort to sleV2QoS4FlowUdpDstEndPort value is available
				If the value is icmp(1),
				The value of sleV2QoS4FlowIcmpType and sleV2QoS4FlowIcmpCode is available
				The value of -1 means any(not set)
				Otherwise, from sleV2QoS4FlowTcpSrcStartPort to sleV2QoS4FlowIcmpCode value is not available
				The value of -1 means any(not set)
				"
			::= { sleV2QoS4FlowEntry 16 }

		
		-- 1.3.6.1.4.1.6296.102.10.2.2.1.1.1.17
		sleV2QoS4FlowTcpSrcStartPort OBJECT-TYPE
			SYNTAX IntL4Port
			MAX-ACCESS read-only
			STATUS current
			DESCRIPTION
				"The start source port in range of source port in TCP packet
				The value of -1 means any(not set)
				"
			::= { sleV2QoS4FlowEntry 17 }

		
		-- 1.3.6.1.4.1.6296.102.10.2.2.1.1.1.18
		sleV2QoS4FlowTcpSrcEndPort OBJECT-TYPE
			SYNTAX IntL4Port
			MAX-ACCESS read-only
			STATUS current
			DESCRIPTION
				"The end source port in range of source port in TCP packet
				The value of -1 means any(not set)
				"
			::= { sleV2QoS4FlowEntry 18 }

		
		-- 1.3.6.1.4.1.6296.102.10.2.2.1.1.1.19
		sleV2QoS4FlowTcpDstStartPort OBJECT-TYPE
			SYNTAX IntL4Port
			MAX-ACCESS read-only
			STATUS current
			DESCRIPTION
				"The start destination port in range of source port in TCP packet. The value of -1 means any(not set)"
			::= { sleV2QoS4FlowEntry 19 }

		
		-- 1.3.6.1.4.1.6296.102.10.2.2.1.1.1.20
		sleV2QoS4FlowTcpDstEndPort OBJECT-TYPE
			SYNTAX IntL4Port
			MAX-ACCESS read-only
			STATUS current
			DESCRIPTION
				"The end destination port in range of destination port in TCP packet. The value of -1 means any(not set)"
			::= { sleV2QoS4FlowEntry 20 }

		
		-- 1.3.6.1.4.1.6296.102.10.2.2.1.1.1.21
		sleV2QoS4FlowTcpFlag OBJECT-TYPE
			SYNTAX BITS
				{
				reserv0(0),
				reserv1(1),
				urg(2),
				ack(3),
				psh(4),
				rst(5),
				syn(6),
				fin(7)
				}
			MAX-ACCESS read-only
			STATUS current
			DESCRIPTION
				"The flag in TCP packet"
			::= { sleV2QoS4FlowEntry 21 }

		
		-- 1.3.6.1.4.1.6296.102.10.2.2.1.1.1.22
		sleV2QoS4FlowUdpSrcStartPort OBJECT-TYPE
			SYNTAX IntL4Port
			MAX-ACCESS read-only
			STATUS current
			DESCRIPTION
				"The start source port in range of source port in UDP packet
				The value of -1 means any(not set)
				"
			::= { sleV2QoS4FlowEntry 22 }

		
		-- 1.3.6.1.4.1.6296.102.10.2.2.1.1.1.23
		sleV2QoS4FlowUdpSrcEndPort OBJECT-TYPE
			SYNTAX IntL4Port
			MAX-ACCESS read-only
			STATUS current
			DESCRIPTION
				"The end source port in range of source port in UDP packet
				The value of -1 means any(not set)
				"
			::= { sleV2QoS4FlowEntry 23 }

		
		-- 1.3.6.1.4.1.6296.102.10.2.2.1.1.1.24
		sleV2QoS4FlowUdpDstStartPort OBJECT-TYPE
			SYNTAX IntL4Port
			MAX-ACCESS read-only
			STATUS current
			DESCRIPTION
				"The start destination port in range of destination port in UDP packet. The value of -1 means any(not set)"
			::= { sleV2QoS4FlowEntry 24 }

		
		-- 1.3.6.1.4.1.6296.102.10.2.2.1.1.1.25
		sleV2QoS4FlowUdpDstEndPort OBJECT-TYPE
			SYNTAX IntL4Port
			MAX-ACCESS read-only
			STATUS current
			DESCRIPTION
				"The end destination port in range of destination port in UDP packet. The value of -1 means any(not set)"
			::= { sleV2QoS4FlowEntry 25 }

		
		-- 1.3.6.1.4.1.6296.102.10.2.2.1.1.1.26
		sleV2QoS4FlowIcmpType OBJECT-TYPE
			SYNTAX IntIcmpType
			MAX-ACCESS read-only
			STATUS current
			DESCRIPTION
				"The type of ICMP message
				The value of -1 means any(not set)
				"
			::= { sleV2QoS4FlowEntry 26 }

		
		-- 1.3.6.1.4.1.6296.102.10.2.2.1.1.1.27
		sleV2QoS4FlowIcmpCode OBJECT-TYPE
			SYNTAX IntIcmpCode
			MAX-ACCESS read-only
			STATUS current
			DESCRIPTION
				"The code of ICMP message
				The value of -1 means any(not set)
				"
			::= { sleV2QoS4FlowEntry 27 }

		
		-- 1.3.6.1.4.1.6296.102.10.2.2.1.1.1.28
		sleV2QoS4FlowHdrlen OBJECT-TYPE
			SYNTAX INTEGER (0 | 1..15)
			MAX-ACCESS read-only
			STATUS current
			DESCRIPTION
				"The IP header length.
				The value of 0 means any(not set)"
			::= { sleV2QoS4FlowEntry 28 }

		
		-- 1.3.6.1.4.1.6296.102.10.2.2.1.1.1.29
		sleV2QoS4FlowHdrError OBJECT-TYPE
			SYNTAX IntEnableFlag
			MAX-ACCESS read-only
			STATUS current
			DESCRIPTION
				"The IP header error check "
			::= { sleV2QoS4FlowEntry 29 }

		
		-- 1.3.6.1.4.1.6296.102.10.2.2.1.1.1.30
		sleV2QoS4FlowInnerVlan OBJECT-TYPE
			SYNTAX Integer32 (1..4094)
			MAX-ACCESS read-only
			STATUS current
			DESCRIPTION
				"The index of inner vlan.
				The value of -1 is nothing(not set)
				"
			::= { sleV2QoS4FlowEntry 30 }

		
		-- 1.3.6.1.4.1.6296.102.10.2.2.1.1.1.31
		sleV2QoS4FlowInner8021p OBJECT-TYPE
			SYNTAX Integer32 (0..7)
			MAX-ACCESS read-only
			STATUS current
			DESCRIPTION
				"The value of the Inner IEEE802.1p priority in the packet.
				The value of -1 means any(not set)
				"
			::= { sleV2QoS4FlowEntry 31 }

		
		-- 1.3.6.1.4.1.6296.102.10.2.2.1.1.1.32
		sleV2QoS4FlowMacFlag OBJECT-TYPE
			SYNTAX INTEGER
				{
				none(0),
				srcAny(1),
				dstAny(2),
				srcDstAny(3)
				}
			MAX-ACCESS read-only
			STATUS current
			DESCRIPTION
				"The any flag of mac address"
			::= { sleV2QoS4FlowEntry 32 }

		
		-- 1.3.6.1.4.1.6296.102.10.2.2.1.1.1.33
		sleV2QoS4FlowIpFlag OBJECT-TYPE
			SYNTAX INTEGER
				{
				none(0),
				srcAny(1),
				dstAny(2),
				srcDstAny(3)
				}
			MAX-ACCESS read-only
			STATUS current
			DESCRIPTION
				"The any flag of IP address."
			::= { sleV2QoS4FlowEntry 33 }

		
		-- 1.3.6.1.4.1.6296.102.10.2.2.1.1.1.34
		sleV2QoS4FlowMacDlf OBJECT-TYPE
			SYNTAX INTEGER
				{
				none(0),
				dstFound(1),
				dstNotFound(2)
				}
			MAX-ACCESS read-only
			STATUS current
			DESCRIPTION
				"The destination mac address is found or not."
			::= { sleV2QoS4FlowEntry 34 }

		
		-- 1.3.6.1.4.1.6296.102.10.2.2.1.1.1.35
		sleV2QoS4FlowTagType OBJECT-TYPE
			SYNTAX INTEGER
				{
				untag(1),
				custom(2),
				service(3),
				both(4)
				}
			MAX-ACCESS read-only
			STATUS current
			DESCRIPTION
				"The packet tag type"
			::= { sleV2QoS4FlowEntry 35 }

		
		-- 1.3.6.1.4.1.6296.102.10.2.2.1.1.1.36
		sleV2QoS4FlowInPktTagVid OBJECT-TYPE
			SYNTAX Integer32 (1..4094 | 4095)
			MAX-ACCESS read-only
			STATUS current
			DESCRIPTION
				"VID, 4095 : any"
			::= { sleV2QoS4FlowEntry 36 }

		
		-- 1.3.6.1.4.1.6296.102.10.2.2.1.1.1.37
		sleV2QoS4FlowInPktTagCfi OBJECT-TYPE
			SYNTAX Integer32 (0..1 | 255)
			MAX-ACCESS read-only
			STATUS current
			DESCRIPTION
				"CFI,  255:any"
			::= { sleV2QoS4FlowEntry 37 }

		
		-- 1.3.6.1.4.1.6296.102.10.2.2.1.1.1.38
		sleV2QoS4FlowInPktTagCoS OBJECT-TYPE
			SYNTAX Integer32 (0..7 | 255)
			MAX-ACCESS read-only
			STATUS current
			DESCRIPTION
				"802.1p, 255:any"
			::= { sleV2QoS4FlowEntry 38 }

		
		-- 1.3.6.1.4.1.6296.102.10.2.2.1.1.1.39
		sleV2QoS4FlowOutPktTagVid OBJECT-TYPE
			SYNTAX Integer32 (1..4094 | 4095)
			MAX-ACCESS read-only
			STATUS current
			DESCRIPTION
				"VID, 4095 : any"
			::= { sleV2QoS4FlowEntry 39 }

		
		-- 1.3.6.1.4.1.6296.102.10.2.2.1.1.1.40
		sleV2QoS4FlowOutPktTagCfi OBJECT-TYPE
			SYNTAX Integer32 (0..1 | 255)
			MAX-ACCESS read-only
			STATUS current
			DESCRIPTION
				"CFI,  255:any"
			::= { sleV2QoS4FlowEntry 40 }

		
		-- 1.3.6.1.4.1.6296.102.10.2.2.1.1.1.41
		sleV2QoS4FlowOutPktTagCoS OBJECT-TYPE
			SYNTAX Integer32 (0..7 | 255)
			MAX-ACCESS read-only
			STATUS current
			DESCRIPTION
				"802.1p, 255:any"
			::= { sleV2QoS4FlowEntry 41 }

		
		-- 1.3.6.1.4.1.6296.102.10.2.2.1.1.1.42
		sleV2QoS4FlowFlowAlias OBJECT-TYPE
			SYNTAX OCTET STRING
			MAX-ACCESS read-only
			STATUS current
			DESCRIPTION
				"flow alias"
			::= { sleV2QoS4FlowEntry 42 }

		
		-- 1.3.6.1.4.1.6296.102.10.2.2.1.1.1.43
		sleV2QoSFlowInetAddrType OBJECT-TYPE
			SYNTAX InetAddressType
			MAX-ACCESS read-only
			STATUS current
			DESCRIPTION
				"IP address type"
			::= { sleV2QoS4FlowEntry 43 }

		
		-- 1.3.6.1.4.1.6296.102.10.2.2.1.1.1.44
		sleV2QoSFlowSrcInetAddr OBJECT-TYPE
			SYNTAX InetAddress
			MAX-ACCESS read-only
			STATUS current
			DESCRIPTION
				"The IP address to match against the packet¡¯s source IP address."
			::= { sleV2QoS4FlowEntry 44 }

		
		-- 1.3.6.1.4.1.6296.102.10.2.2.1.1.1.45
		sleV2QoSFlowDstInetAddr OBJECT-TYPE
			SYNTAX InetAddress
			MAX-ACCESS read-only
			STATUS current
			DESCRIPTION
				"The IP address to match against the packet¡¯s destination IP address."
			::= { sleV2QoS4FlowEntry 45 }

		
		-- 1.3.6.1.4.1.6296.102.10.2.2.1.1.1.46
		sleV2QoSFlowSrcInetAddrLen OBJECT-TYPE
			SYNTAX InetAddressPrefixLength
			MAX-ACCESS read-only
			STATUS current
			DESCRIPTION
				"The prefix length of source IP address"
			::= { sleV2QoS4FlowEntry 46 }

		
		-- 1.3.6.1.4.1.6296.102.10.2.2.1.1.1.47
		sleV2QoSFlowDstInetAddrLen OBJECT-TYPE
			SYNTAX InetAddressPrefixLength
			MAX-ACCESS read-only
			STATUS current
			DESCRIPTION
				"The prefix length of destination IP address"
			::= { sleV2QoS4FlowEntry 47 }

		
		-- 1.3.6.1.4.1.6296.102.10.2.2.1.1.1.48
		sleV2QoSFlowTrafficClass OBJECT-TYPE
			SYNTAX INTEGER (-1 | 0..255)
			MAX-ACCESS read-only
			STATUS current
			DESCRIPTION
				"The traffic class of IPv6 header
				The value of -1 means any(not set)"
			::= { sleV2QoS4FlowEntry 48 }

		
		-- 1.3.6.1.4.1.6296.102.10.2.2.1.1.1.49
		sleV2QoSFlowFlowLabel OBJECT-TYPE
			SYNTAX INTEGER (-1 | 0..65535)
			MAX-ACCESS read-only
			STATUS current
			DESCRIPTION
				"The flow label of IPv6 header
				The value of -1 means any(not set)"
			::= { sleV2QoS4FlowEntry 49 }

		
		-- 1.3.6.1.4.1.6296.102.10.2.2.1.1.1.50
		sleV2QoS4FlowOuterVlan OBJECT-TYPE
			SYNTAX Integer32 (-1 | 0..4094)
			MAX-ACCESS read-only
			STATUS current
			DESCRIPTION
				"The index of outer vlan 
				The value of -1 is nothing(not set)
				"
			::= { sleV2QoS4FlowEntry 50 }

		
		-- 1.3.6.1.4.1.6296.102.10.2.2.1.1.1.51
		sleV2QoS4FlowOuter8021p OBJECT-TYPE
			SYNTAX Integer32 (-1 | 0..7)
			MAX-ACCESS read-only
			STATUS current
			DESCRIPTION
				"The value of the outer IEEE802.1p priority in the packet
				The value of -1 means any(not set)
				"
			::= { sleV2QoS4FlowEntry 51 }

		
		-- 1.3.6.1.4.1.6296.102.10.2.2.1.1.1.52
		sleV2QoS4FlowOnuCircuitId OBJECT-TYPE
			SYNTAX Integer32 (-1 | 1..50000 | 50002 | 50003 | 50004 | 51002)
			MAX-ACCESS read-only
			STATUS current
			DESCRIPTION
				"The value of the Onu Circuit-id
				The value of -1 means any(not set)
				"
			::= { sleV2QoS4FlowEntry 52 }

		
		-- 1.3.6.1.4.1.6296.102.10.2.2.1.2
		sleV2QoS4FlowControl OBJECT IDENTIFIER ::= { sleV2QoS4FlowInfo 2 }

		
		-- 1.3.6.1.4.1.6296.102.10.2.2.1.2.1
		sleV2QoS4FlowControlRequest OBJECT-TYPE
			SYNTAX INTEGER
				{
				createFlow(1),
				modifyFlow(2),
				destroyFlow(3),
				destroyAllFlow(4),
				setInPktTag(5),
				setOutPktTag(6),
				setFlowAlias(7),
				createFlowEx(8),
				setFlowEx(9)
				}
			MAX-ACCESS read-write
			STATUS current
			DESCRIPTION
				"The request of a user command"
			::= { sleV2QoS4FlowControl 1 }

		
		-- 1.3.6.1.4.1.6296.102.10.2.2.1.2.2
		sleV2QoS4FlowControlStatus OBJECT-TYPE
			SYNTAX SleControlStatusType
			MAX-ACCESS read-only
			STATUS current
			DESCRIPTION
				"The status of user command"
			::= { sleV2QoS4FlowControl 2 }

		
		-- 1.3.6.1.4.1.6296.102.10.2.2.1.2.3
		sleV2QoS4FlowControlTimer OBJECT-TYPE
			SYNTAX Gauge32
			MAX-ACCESS read-write
			STATUS current
			DESCRIPTION
				"The maximum time for the manager for a long running user command"
			::= { sleV2QoS4FlowControl 3 }

		
		-- 1.3.6.1.4.1.6296.102.10.2.2.1.2.4
		sleV2QoS4FlowControlTimeStamp OBJECT-TYPE
			SYNTAX TimeTicks
			MAX-ACCESS read-only
			STATUS current
			DESCRIPTION
				"The time stamp of the last command(end of command)"
			::= { sleV2QoS4FlowControl 4 }

		
		-- 1.3.6.1.4.1.6296.102.10.2.2.1.2.5
		sleV2QoS4FlowControlReqResult OBJECT-TYPE
			SYNTAX SleControlRequestResultType
			MAX-ACCESS read-only
			STATUS current
			DESCRIPTION
				"The result of the last user command"
			::= { sleV2QoS4FlowControl 5 }

		
		-- 1.3.6.1.4.1.6296.102.10.2.2.1.2.6
		sleV2QoS4FlowControlIndex OBJECT-TYPE
			SYNTAX IntFlowIndex
			MAX-ACCESS read-write
			STATUS current
			DESCRIPTION
				"The index of flow"
			::= { sleV2QoS4FlowControl 6 }

		
		-- 1.3.6.1.4.1.6296.102.10.2.2.1.2.7
		sleV2QoS4FlowControlName OBJECT-TYPE
			SYNTAX OctetName
			MAX-ACCESS read-write
			STATUS current
			DESCRIPTION
				"The name of flow"
			::= { sleV2QoS4FlowControl 7 }

		
		-- 1.3.6.1.4.1.6296.102.10.2.2.1.2.8
		sleV2QoS4FlowControlEthernetType OBJECT-TYPE
			SYNTAX IntEthernetType
			MAX-ACCESS read-write
			STATUS current
			DESCRIPTION
				"The ethernet type value in incoming frames
				The value of -1 means any(not set).
				"
			::= { sleV2QoS4FlowControl 8 }

		
		-- 1.3.6.1.4.1.6296.102.10.2.2.1.2.9
		sleV2QoS4FlowControlSrcMacAddr OBJECT-TYPE
			SYNTAX MacAddress
			MAX-ACCESS read-write
			STATUS current
			DESCRIPTION
				"The source mac address
				The value of 00:00:00:00:00:00 is any(not set)
				"
			::= { sleV2QoS4FlowControl 9 }

		
		-- 1.3.6.1.4.1.6296.102.10.2.2.1.2.10
		sleV2QoS4FlowControlSrcMacAddrMask OBJECT-TYPE
			SYNTAX MacAddressMask
			MAX-ACCESS read-write
			STATUS current
			DESCRIPTION
				"The mask of the source mac address
				The value of 00:00:00:00:00:00 is any(not set)
				"
			::= { sleV2QoS4FlowControl 10 }

		
		-- 1.3.6.1.4.1.6296.102.10.2.2.1.2.11
		sleV2QoS4FlowControlDstMacAddr OBJECT-TYPE
			SYNTAX MacAddress
			MAX-ACCESS read-write
			STATUS current
			DESCRIPTION
				"The destination mac address
				The value of 00:00:00:00:00:00 is any(not set)
				"
			::= { sleV2QoS4FlowControl 11 }

		
		-- 1.3.6.1.4.1.6296.102.10.2.2.1.2.12
		sleV2QoS4FlowControlDstMacAddrMask OBJECT-TYPE
			SYNTAX MacAddressMask
			MAX-ACCESS read-write
			STATUS current
			DESCRIPTION
				"The mask of the destination mac address
				The value of 00:00:00:00:00:00 is any(not set)
				"
			::= { sleV2QoS4FlowControl 12 }

		
		-- 1.3.6.1.4.1.6296.102.10.2.2.1.2.13
		sleV2QoS4FlowControl8021p OBJECT-TYPE
			SYNTAX Int8021p
			MAX-ACCESS read-write
			STATUS current
			DESCRIPTION
				"The value of the IEEE802.1p priority in the packet
				The value of -1 means any(not set)
				"
			::= { sleV2QoS4FlowControl 13 }

		
		-- 1.3.6.1.4.1.6296.102.10.2.2.1.2.14
		sleV2QoS4FlowControlSrcIpAddr OBJECT-TYPE
			SYNTAX IpAddress
			MAX-ACCESS read-write
			STATUS current
			DESCRIPTION
				"The IP address to match against the packet's source IP address.
				The value of 0.0.0.0 means any(not set)
				"
			::= { sleV2QoS4FlowControl 14 }

		
		-- 1.3.6.1.4.1.6296.102.10.2.2.1.2.15
		sleV2QoS4FlowControlSrcIpAddrMask OBJECT-TYPE
			SYNTAX IntIpAddrMask
			MAX-ACCESS read-write
			STATUS current
			DESCRIPTION
				"The mask of source IP address
				The value of -1 means any(not set)
				"
			::= { sleV2QoS4FlowControl 15 }

		
		-- 1.3.6.1.4.1.6296.102.10.2.2.1.2.16
		sleV2QoS4FlowControlDstIpAddr OBJECT-TYPE
			SYNTAX IpAddress
			MAX-ACCESS read-write
			STATUS current
			DESCRIPTION
				"The IP address to match against the packet's destination IP address.
				The value of 0.0.0.0 means any(not set)
				"
			::= { sleV2QoS4FlowControl 16 }

		
		-- 1.3.6.1.4.1.6296.102.10.2.2.1.2.17
		sleV2QoS4FlowControlDstIpAddrMask OBJECT-TYPE
			SYNTAX IntIpAddrMask
			MAX-ACCESS read-write
			STATUS current
			DESCRIPTION
				"The mask of destination IP address
				The value of -1 means any(not set)
				"
			::= { sleV2QoS4FlowControl 17 }

		
		-- 1.3.6.1.4.1.6296.102.10.2.2.1.2.18
		sleV2QoS4FlowControlIpPktPriorityType OBJECT-TYPE
			SYNTAX IntIpPktPriorityType
			MAX-ACCESS read-write
			STATUS current
			DESCRIPTION
				"The Priority type of incoming IP packet
				(specify a type of sleUserFlowIpPktPriority)
				The value of -1 means any(not set)
				"
			::= { sleV2QoS4FlowControl 18 }

		
		-- 1.3.6.1.4.1.6296.102.10.2.2.1.2.19
		sleV2QoS4FlowControlIpPktPriority OBJECT-TYPE
			SYNTAX Integer32
			MAX-ACCESS read-write
			STATUS current
			DESCRIPTION
				"The Priority value of incoming IP packet
				If type is 1, this value's range is 0-7.
				If type is 2, this value's range is 0-63.
				If type is 3, this value's range is 0-255.
				The value of -1 means any(not set)
				"
			::= { sleV2QoS4FlowControl 19 }

		
		-- 1.3.6.1.4.1.6296.102.10.2.2.1.2.20
		sleV2QoS4FlowControlPktLen OBJECT-TYPE
			SYNTAX IntPktLen
			MAX-ACCESS read-write
			STATUS current
			DESCRIPTION
				"The packet length of the incoming packet
				The value of -1 means any(not set)
				"
			::= { sleV2QoS4FlowControl 20 }

		
		-- 1.3.6.1.4.1.6296.102.10.2.2.1.2.21
		sleV2QoS4FlowControlProtocolType OBJECT-TYPE
			SYNTAX IntProtocolType
			MAX-ACCESS read-write
			STATUS current
			DESCRIPTION
				"The type of IP protocol
				The flat internet protocol is from sleV2QoS4FlowTcpSrcStartPort to sleV2QoS4FlowIcmpCode
				If the value is tcp(6),
				From sleV2QoS4FlowControlTcpSrcStartPort to sleV2QoS4FlowControlTcpFlag value is available
				If the value is u¿¡(17),
				From sleV2QoS4FlowControlUdpSrcStartPort to sleV2QoS4FlowControlUdpDstEndPort value is available
				If the value is icmp(1),
				The value of sleV2QoS4FlowControlIcmpType and sleV2QoS4FlowControlIcmpCode is available
				The value of -1 means any(not set)
				Otherwise, from sleV2QoS4FlowControlTcpSrcStartPort to sleV2QoS4FlowControlIcmpCode value is not available
				The value of -1 means any(not set)
				"
			::= { sleV2QoS4FlowControl 21 }

		
		-- 1.3.6.1.4.1.6296.102.10.2.2.1.2.22
		sleV2QoS4FlowControlTcpSrcStartPort OBJECT-TYPE
			SYNTAX IntL4Port
			MAX-ACCESS read-write
			STATUS current
			DESCRIPTION
				"The start source port in range of source port in TCP packet
				The value of -1 means any(not set)
				"
			::= { sleV2QoS4FlowControl 22 }

		
		-- 1.3.6.1.4.1.6296.102.10.2.2.1.2.23
		sleV2QoS4FlowControlTcpSrcEndPort OBJECT-TYPE
			SYNTAX IntL4Port
			MAX-ACCESS read-write
			STATUS current
			DESCRIPTION
				"The end source port in range of source port in TCP packet
				The value of -1 means any(not set)
				"
			::= { sleV2QoS4FlowControl 23 }

		
		-- 1.3.6.1.4.1.6296.102.10.2.2.1.2.24
		sleV2QoS4FlowControlTcpDstStartPort OBJECT-TYPE
			SYNTAX IntL4Port
			MAX-ACCESS read-write
			STATUS current
			DESCRIPTION
				"The start destination port in range of source port in TCP packet. The value of -1 means any(not set)"
			::= { sleV2QoS4FlowControl 24 }

		
		-- 1.3.6.1.4.1.6296.102.10.2.2.1.2.25
		sleV2QoS4FlowControlTcpDstEndPort OBJECT-TYPE
			SYNTAX IntL4Port
			MAX-ACCESS read-write
			STATUS current
			DESCRIPTION
				"The end destination port in range of destination port in TCP packet. The value of -1 means any(not set)"
			::= { sleV2QoS4FlowControl 25 }

		
		-- 1.3.6.1.4.1.6296.102.10.2.2.1.2.26
		sleV2QoS4FlowControlTcpFlag OBJECT-TYPE
			SYNTAX BITS
				{
				reserv0(0),
				reserv1(1),
				urg(2),
				ack(3),
				psh(4),
				rst(5),
				syn(6),
				fin(7)
				}
			MAX-ACCESS read-write
			STATUS current
			DESCRIPTION
				"The flag in TCP packet"
			::= { sleV2QoS4FlowControl 26 }

		
		-- 1.3.6.1.4.1.6296.102.10.2.2.1.2.27
		sleV2QoS4FlowControlUdpSrcStartPort OBJECT-TYPE
			SYNTAX IntL4Port
			MAX-ACCESS read-write
			STATUS current
			DESCRIPTION
				"The start source port in range of source port in UDP packet
				The value of -1 means any(not set)
				"
			::= { sleV2QoS4FlowControl 27 }

		
		-- 1.3.6.1.4.1.6296.102.10.2.2.1.2.28
		sleV2QoS4FlowControlUdpSrcEndPort OBJECT-TYPE
			SYNTAX IntL4Port
			MAX-ACCESS read-write
			STATUS current
			DESCRIPTION
				"The end source port in range of source port in UDP packet
				The value of -1 means any(not set)
				"
			::= { sleV2QoS4FlowControl 28 }

		
		-- 1.3.6.1.4.1.6296.102.10.2.2.1.2.29
		sleV2QoS4FlowControlUdpDstStartPort OBJECT-TYPE
			SYNTAX IntL4Port
			MAX-ACCESS read-write
			STATUS current
			DESCRIPTION
				"The start destination port in range of destination port in UDP packet. The value of -1 means any(not set)"
			::= { sleV2QoS4FlowControl 29 }

		
		-- 1.3.6.1.4.1.6296.102.10.2.2.1.2.30
		sleV2QoS4FlowControlUdpDstEndPort OBJECT-TYPE
			SYNTAX IntL4Port
			MAX-ACCESS read-write
			STATUS current
			DESCRIPTION
				"The end destination port in range of destination port in UDP packet. The value of -1 means any(not set)"
			::= { sleV2QoS4FlowControl 30 }

		
		-- 1.3.6.1.4.1.6296.102.10.2.2.1.2.31
		sleV2QoS4FlowControlIcmpType OBJECT-TYPE
			SYNTAX IntIcmpType
			MAX-ACCESS read-write
			STATUS current
			DESCRIPTION
				"The type of ICMP message
				The value of -1 means any(not set)
				"
			::= { sleV2QoS4FlowControl 31 }

		
		-- 1.3.6.1.4.1.6296.102.10.2.2.1.2.32
		sleV2QoS4FlowControlIcmpCode OBJECT-TYPE
			SYNTAX IntIcmpCode
			MAX-ACCESS read-write
			STATUS current
			DESCRIPTION
				"The code of ICMP message
				The value of -1 means any(not set)
				"
			::= { sleV2QoS4FlowControl 32 }

		
		-- 1.3.6.1.4.1.6296.102.10.2.2.1.2.33
		sleV2QoS4FlowControlHdrlen OBJECT-TYPE
			SYNTAX INTEGER (0 | 1..15)
			MAX-ACCESS read-write
			STATUS current
			DESCRIPTION
				"The IP header error check "
			::= { sleV2QoS4FlowControl 33 }

		
		-- 1.3.6.1.4.1.6296.102.10.2.2.1.2.34
		sleV2QoS4FlowControlHdrError OBJECT-TYPE
			SYNTAX IntEnableFlag
			MAX-ACCESS read-write
			STATUS current
			DESCRIPTION
				"The IP header error check "
			::= { sleV2QoS4FlowControl 34 }

		
		-- 1.3.6.1.4.1.6296.102.10.2.2.1.2.35
		sleV2QoS4FlowControlInnerVlan OBJECT-TYPE
			SYNTAX Integer32 (1..4094)
			MAX-ACCESS read-write
			STATUS current
			DESCRIPTION
				"The index of inner vlan.
				The value of -1 is nothing(not set)
				"
			::= { sleV2QoS4FlowControl 35 }

		
		-- 1.3.6.1.4.1.6296.102.10.2.2.1.2.36
		sleV2QoS4FlowControlInner8021p OBJECT-TYPE
			SYNTAX Integer32 (0..7)
			MAX-ACCESS read-write
			STATUS current
			DESCRIPTION
				"The value of the Inner IEEE802.1p priority in the packet.
				The value of -1 means any(not set)
				"
			::= { sleV2QoS4FlowControl 36 }

		
		-- 1.3.6.1.4.1.6296.102.10.2.2.1.2.37
		sleV2QoS4FlowControlMacFlag OBJECT-TYPE
			SYNTAX INTEGER
				{
				none(0),
				srcAny(1),
				dstAny(2),
				srcDstAny(3)
				}
			MAX-ACCESS read-write
			STATUS current
			DESCRIPTION
				"The any flag of mac address"
			::= { sleV2QoS4FlowControl 37 }

		
		-- 1.3.6.1.4.1.6296.102.10.2.2.1.2.38
		sleV2QoS4FlowControlIpFlag OBJECT-TYPE
			SYNTAX INTEGER
				{
				none(0),
				srcAny(1),
				dstAny(2),
				srcDstAny(3)
				}
			MAX-ACCESS read-write
			STATUS current
			DESCRIPTION
				"The any flag of IP address."
			::= { sleV2QoS4FlowControl 38 }

		
		-- 1.3.6.1.4.1.6296.102.10.2.2.1.2.39
		sleV2QoS4FlowControlMacDlf OBJECT-TYPE
			SYNTAX INTEGER
				{
				none(0),
				dstFound(1),
				dstNotFound(2)
				}
			MAX-ACCESS read-write
			STATUS current
			DESCRIPTION
				"The destination MAC address found or not"
			::= { sleV2QoS4FlowControl 39 }

		
		-- 1.3.6.1.4.1.6296.102.10.2.2.1.2.40
		sleV2QoS4FlowControlTagType OBJECT-TYPE
			SYNTAX INTEGER
				{
				untag(1),
				custom(2),
				service(3),
				both(4)
				}
			MAX-ACCESS read-write
			STATUS current
			DESCRIPTION
				"The packet tag type"
			::= { sleV2QoS4FlowControl 40 }

		
		-- 1.3.6.1.4.1.6296.102.10.2.2.1.2.41
		sleV2QoS4FlowControlPktTagVid OBJECT-TYPE
			SYNTAX Integer32 (-1 | 1..4094 | 4095)
			MAX-ACCESS read-only
			STATUS current
			DESCRIPTION
				"VID, 4095 : any
				All VID, CFI, CoS are -1 : clear command "
			::= { sleV2QoS4FlowControl 41 }

		
		-- 1.3.6.1.4.1.6296.102.10.2.2.1.2.42
		sleV2QoS4FlowControlPktTagCfi OBJECT-TYPE
			SYNTAX Integer32 (-1 | 0..1 | 255)
			MAX-ACCESS read-only
			STATUS current
			DESCRIPTION
				"CFI,  255:any
				All VID, CFI, CoS are -1 : clear command"
			::= { sleV2QoS4FlowControl 42 }

		
		-- 1.3.6.1.4.1.6296.102.10.2.2.1.2.43
		sleV2QoS4FlowControlPktTagCoS OBJECT-TYPE
			SYNTAX Integer32 (-1 | 0..7 | 255)
			MAX-ACCESS read-only
			STATUS current
			DESCRIPTION
				"802.1p, 255:any
				All VID, CFI, CoS are -1 : clear command"
			::= { sleV2QoS4FlowControl 43 }

		
		-- 1.3.6.1.4.1.6296.102.10.2.2.1.2.44
		sleV2QoS4FlowControlFlowAlias OBJECT-TYPE
			SYNTAX OCTET STRING
			MAX-ACCESS read-only
			STATUS current
			DESCRIPTION
				"flow alias"
			::= { sleV2QoS4FlowControl 44 }

		
		-- 1.3.6.1.4.1.6296.102.10.2.2.1.2.45
		sleV2QoSFlowControlInetAddrType OBJECT-TYPE
			SYNTAX InetAddressType
			MAX-ACCESS read-only
			STATUS current
			DESCRIPTION
				"IP address type"
			::= { sleV2QoS4FlowControl 45 }

		
		-- 1.3.6.1.4.1.6296.102.10.2.2.1.2.46
		sleV2QoSFlowControlSrcInetAddr OBJECT-TYPE
			SYNTAX InetAddress
			MAX-ACCESS read-only
			STATUS current
			DESCRIPTION
				"The IP address to match against the packet¡¯s source IP address."
			::= { sleV2QoS4FlowControl 46 }

		
		-- 1.3.6.1.4.1.6296.102.10.2.2.1.2.47
		sleV2QoSFlowControlDstInetAddr OBJECT-TYPE
			SYNTAX InetAddress
			MAX-ACCESS read-only
			STATUS current
			DESCRIPTION
				"The IP address to match against the packet¡¯s destination IP address."
			::= { sleV2QoS4FlowControl 47 }

		
		-- 1.3.6.1.4.1.6296.102.10.2.2.1.2.48
		sleV2QoSFlowControlSrcInetAddrLen OBJECT-TYPE
			SYNTAX InetAddressPrefixLength
			MAX-ACCESS read-only
			STATUS current
			DESCRIPTION
				"The prefix length of source IP address"
			::= { sleV2QoS4FlowControl 48 }

		
		-- 1.3.6.1.4.1.6296.102.10.2.2.1.2.49
		sleV2QoSFlowControlDstInetAddrLen OBJECT-TYPE
			SYNTAX InetAddressPrefixLength
			MAX-ACCESS read-only
			STATUS current
			DESCRIPTION
				"The prefix length of destination IP address"
			::= { sleV2QoS4FlowControl 49 }

		
		-- 1.3.6.1.4.1.6296.102.10.2.2.1.2.50
		sleV2QoSFlowControlTrafficClass OBJECT-TYPE
			SYNTAX INTEGER (-1 | 0..255)
			MAX-ACCESS read-write
			STATUS current
			DESCRIPTION
				"The traffic class of IPv6 header
				The value of -1 means any(not set)"
			::= { sleV2QoS4FlowControl 50 }

		
		-- 1.3.6.1.4.1.6296.102.10.2.2.1.2.51
		sleV2QoSFlowControlFlowLabel OBJECT-TYPE
			SYNTAX INTEGER (-1 | 0..65535)
			MAX-ACCESS read-write
			STATUS current
			DESCRIPTION
				"The flow label of IPv6 header
				The value of -1 means any(not set)"
			::= { sleV2QoS4FlowControl 51 }

		
		-- 1.3.6.1.4.1.6296.102.10.2.2.1.2.52
		sleV2QoS4FlowControlOuterVlan OBJECT-TYPE
			SYNTAX Integer32 (-1 | 1..4094)
			MAX-ACCESS read-write
			STATUS current
			DESCRIPTION
				"The index of outer vlan 
				The value of -1 is nothing(not set)
				"
			::= { sleV2QoS4FlowControl 52 }

		
		-- 1.3.6.1.4.1.6296.102.10.2.2.1.2.53
		sleV2QoS4FlowControlOuter8021p OBJECT-TYPE
			SYNTAX Integer32 (-1 | 0..7)
			MAX-ACCESS read-write
			STATUS current
			DESCRIPTION
				"The value of the outer IEEE802.1p priority in the packet
				The value of -1 means any(not set)
				"
			::= { sleV2QoS4FlowControl 53 }

		
		-- 1.3.6.1.4.1.6296.102.10.2.2.1.2.54
		sleV2QoS4FlowControlOnuCircuitId OBJECT-TYPE
			SYNTAX Integer32 (-1 | 1..5000 | 50002 | 50003 | 50004 | 51002)
			MAX-ACCESS read-write
			STATUS current
			DESCRIPTION
				"The value of the Onu Circuit-id
				The value of -1 means any(not set)
				"
			::= { sleV2QoS4FlowControl 54 }

		
		-- 1.3.6.1.4.1.6296.102.10.2.2.1.3
		sleV2QoS4FlowNotification OBJECT IDENTIFIER ::= { sleV2QoS4FlowInfo 3 }

		
		-- 1.3.6.1.4.1.6296.102.10.2.2.1.3.1
		sleFlowCreated NOTIFICATION-TYPE
			OBJECTS { sleV2QoS4FlowControlRequest, sleV2QoS4FlowControlTimeStamp, sleV2QoS4FlowControlReqResult, sleV2QoS4FlowHdrError, sleV2QoS4FlowInner8021p, 
				sleV2QoS4FlowInnerVlan, sleV2QoS4FlowMacDlf, sleV2QoS4FlowMacFlag, sleV2QoS4FlowIpFlag, sleV2QoS4FlowTagType, 
				sleV2QoS4FlowOuterVlan, sleV2QoS4FlowOuter8021p, sleV2QoS4FlowOnuCircuitId, sleV2QoS4FlowName, sleV2QoS4FlowEthernetType, 
				sleV2QoS4FlowSrcMacAddr, sleV2QoS4FlowSrcMacAddrMask, sleV2QoS4FlowDstMacAddr, sleV2QoS4FlowDstMacAddrMask, sleV2QoS4Flow8021p, 
				sleV2QoS4FlowSrcIpAddr, sleV2QoS4FlowSrcIpAddrMask, sleV2QoS4FlowDstIpAddr, sleV2QoS4FlowDstIpAddrMask, sleV2QoS4FlowIpPktPriorityType, 
				sleV2QoS4FlowIpPktPriority, sleV2QoS4FlowPktLen, sleV2QoS4FlowProtocolType, sleV2QoS4FlowTcpSrcStartPort, sleV2QoS4FlowTcpSrcEndPort, 
				sleV2QoS4FlowTcpDstStartPort, sleV2QoS4FlowTcpDstEndPort, sleV2QoS4FlowTcpFlag, sleV2QoS4FlowUdpSrcStartPort, sleV2QoS4FlowUdpSrcEndPort, 
				sleV2QoS4FlowUdpDstStartPort, sleV2QoS4FlowUdpDstEndPort, sleV2QoS4FlowIcmpType, sleV2QoS4FlowIcmpCode, sleV2QoS4FlowHdrlen
				 }
			STATUS current
			DESCRIPTION 
				"Description."
			::= { sleV2QoS4FlowNotification 1 }

		
		-- 1.3.6.1.4.1.6296.102.10.2.2.1.3.2
		sleFlowChanged NOTIFICATION-TYPE
			OBJECTS { sleV2QoS4FlowControlRequest, sleV2QoS4FlowControlTimeStamp, sleV2QoS4BaseControlFlowMode, sleV2QoS4FlowControlIndex, sleV2QoS4FlowControlEthernetType, 
				sleV2QoS4FlowControlSrcMacAddr, sleV2QoS4FlowControlSrcMacAddrMask, sleV2QoS4FlowControlDstMacAddr, sleV2QoS4FlowControlDstMacAddrMask, sleV2QoS4FlowControl8021p, 
				sleV2QoS4FlowControlSrcIpAddr, sleV2QoS4FlowControlSrcIpAddrMask, sleV2QoS4FlowControlDstIpAddr, sleV2QoS4FlowControlDstIpAddrMask, sleV2QoS4FlowControlIpPktPriorityType, 
				sleV2QoS4FlowControlIpPktPriority, sleV2QoS4FlowControlPktLen, sleV2QoS4FlowControlProtocolType, sleV2QoS4FlowControlTcpSrcStartPort, sleV2QoS4FlowControlTcpSrcEndPort, 
				sleV2QoS4FlowControlTcpDstStartPort, sleV2QoS4FlowControlTcpDstEndPort, sleV2QoS4FlowControlTcpFlag, sleV2QoS4FlowControlUdpSrcStartPort, sleV2QoS4FlowControlUdpSrcEndPort, 
				sleV2QoS4FlowControlUdpDstStartPort, sleV2QoS4FlowControlUdpDstEndPort, sleV2QoS4FlowControlIcmpType, sleV2QoS4FlowControlIcmpCode, sleV2QoS4FlowControlHdrlen, 
				sleV2QoS4FlowControlHdrError, sleV2QoS4FlowControlInnerVlan, sleV2QoS4FlowControlInner8021p, sleV2QoS4FlowControlMacFlag, sleV2QoS4FlowControlIpFlag, 
				sleV2QoS4FlowControlTagType, sleV2QoS4FlowControlOuterVlan, sleV2QoS4FlowControlOuter8021p, sleV2QoS4FlowControlOnuCircuitId, sleV2QoS4FlowControlMacDlf, 
				sleV2QoS4FlowControlReqResult }
			STATUS current
			DESCRIPTION 
				"Description."
			::= { sleV2QoS4FlowNotification 2 }

		
		-- 1.3.6.1.4.1.6296.102.10.2.2.1.3.3
		sleFlowDestroyed NOTIFICATION-TYPE
			OBJECTS { sleV2QoS4FlowControlRequest, sleV2QoS4FlowControlTimeStamp, sleV2QoS4FlowControlReqResult, sleV2QoS4FlowControlIndex }
			STATUS current
			DESCRIPTION 
				"Description."
			::= { sleV2QoS4FlowNotification 3 }

		
		-- 1.3.6.1.4.1.6296.102.10.2.2.1.3.4
		sleFlowAllDestroyed NOTIFICATION-TYPE
			OBJECTS { sleV2QoS4FlowControlRequest, sleV2QoS4FlowControlTimeStamp, sleV2QoS4FlowControlReqResult }
			STATUS current
			DESCRIPTION 
				"Description."
			::= { sleV2QoS4FlowNotification 4 }

		
		-- 1.3.6.1.4.1.6296.102.10.2.2.1.3.5
		sleFlowInPktTagChanged NOTIFICATION-TYPE
			OBJECTS { sleV2QoS4FlowControlRequest, sleV2QoS4FlowControlTimeStamp, sleV2QoS4FlowControlReqResult, sleV2QoS4FlowControlIndex, sleV2QoS4FlowControlPktTagVid, 
				sleV2QoS4FlowControlPktTagCfi, sleV2QoS4FlowControlPktTagCoS }
			STATUS current
			DESCRIPTION 
				"Description."
			::= { sleV2QoS4FlowNotification 5 }

		
		-- 1.3.6.1.4.1.6296.102.10.2.2.1.3.6
		sleFlowOutPktTagChanged NOTIFICATION-TYPE
			OBJECTS { sleV2QoS4FlowControlRequest, sleV2QoS4FlowControlTimeStamp, sleV2QoS4FlowControlReqResult, sleV2QoS4FlowControlIndex, sleV2QoS4FlowControlPktTagVid, 
				sleV2QoS4FlowControlPktTagCfi, sleV2QoS4FlowControlPktTagCoS }
			STATUS current
			DESCRIPTION 
				"setOutPktTag"
			::= { sleV2QoS4FlowNotification 6 }

		
		-- 1.3.6.1.4.1.6296.102.10.2.2.1.3.7
		sleFlowAliasChanged NOTIFICATION-TYPE
			OBJECTS { sleV2QoS4FlowControlRequest, sleV2QoS4FlowControlTimeStamp, sleV2QoS4FlowControlReqResult, sleV2QoS4FlowControlIndex, sleV2QoS4FlowControlFlowAlias
				 }
			STATUS current
			DESCRIPTION 
				"setFlowAlias"
			::= { sleV2QoS4FlowNotification 7 }

		
		-- 1.3.6.1.4.1.6296.102.10.2.2.1.3.8
		sleFlowExCreated NOTIFICATION-TYPE
			OBJECTS { sleV2QoS4FlowControlRequest, sleV2QoS4FlowControlTimeStamp, sleV2QoS4FlowControlReqResult, sleV2QoS4FlowName, sleV2QoS4FlowEthernetType, 
				sleV2QoSFlowInetAddrType, sleV2QoSFlowSrcInetAddr, sleV2QoSFlowDstInetAddr, sleV2QoSFlowSrcInetAddrLen, sleV2QoSFlowDstInetAddrLen, 
				sleV2QoS4Flow8021p, sleV2QoS4FlowSrcIpAddr, sleV2QoS4FlowSrcIpAddrMask, sleV2QoS4FlowDstIpAddr, sleV2QoS4FlowDstIpAddrMask, 
				sleV2QoS4FlowIpPktPriorityType, sleV2QoS4FlowIpPktPriority, sleV2QoS4FlowPktLen, sleV2QoS4FlowProtocolType, sleV2QoS4FlowTcpSrcStartPort, 
				sleV2QoS4FlowTcpSrcEndPort, sleV2QoS4FlowTcpDstStartPort, sleV2QoS4FlowTcpDstEndPort, sleV2QoS4FlowTcpFlag, sleV2QoS4FlowUdpSrcStartPort, 
				sleV2QoS4FlowUdpSrcEndPort, sleV2QoS4FlowUdpDstStartPort, sleV2QoS4FlowUdpDstEndPort, sleV2QoS4FlowIcmpType, sleV2QoS4FlowIcmpCode, 
				sleV2QoS4FlowHdrlen, sleV2QoS4FlowHdrError, sleV2QoS4FlowInnerVlan, sleV2QoS4FlowInner8021p, sleV2QoS4FlowMacFlag, 
				sleV2QoS4FlowIpFlag, sleV2QoS4FlowMacDlf, sleV2QoS4FlowTagType, sleV2QoSFlowTrafficClass, sleV2QoSFlowFlowLabel, 
				sleV2QoS4FlowOuterVlan, sleV2QoS4FlowOuter8021p, sleV2QoS4FlowOnuCircuitId }
			STATUS current
			DESCRIPTION 
				"createFlowEx"
			::= { sleV2QoS4FlowNotification 8 }

		
		-- 1.3.6.1.4.1.6296.102.10.2.2.1.3.9
		sleFlowExChanged NOTIFICATION-TYPE
			OBJECTS { sleV2QoS4FlowControlRequest, sleV2QoS4FlowControlTimeStamp, sleV2QoS4BaseControlFlowMode, sleV2QoS4FlowIndex, sleV2QoS4FlowEthernetType, 
				sleV2QoS4FlowSrcMacAddr, sleV2QoS4FlowSrcMacAddrMask, sleV2QoS4FlowDstMacAddr, sleV2QoS4FlowDstMacAddrMask, sleV2QoS4Flow8021p, 
				sleV2QoSFlowInetAddrType, sleV2QoSFlowSrcInetAddr, sleV2QoSFlowDstInetAddr, sleV2QoSFlowSrcInetAddrLen, sleV2QoSFlowDstInetAddrLen, 
				sleV2QoS4FlowIpPktPriorityType, sleV2QoS4FlowIpPktPriority, sleV2QoS4FlowPktLen, sleV2QoS4FlowProtocolType, sleV2QoS4FlowTcpSrcStartPort, 
				sleV2QoS4FlowTcpSrcEndPort, sleV2QoS4FlowTcpDstStartPort, sleV2QoS4FlowTcpDstEndPort, sleV2QoS4FlowTcpFlag, sleV2QoS4FlowUdpSrcStartPort, 
				sleV2QoS4FlowUdpSrcEndPort, sleV2QoS4FlowUdpDstStartPort, sleV2QoS4FlowUdpDstEndPort, sleV2QoS4FlowIcmpType, sleV2QoS4FlowIcmpCode, 
				sleV2QoS4FlowHdrlen, sleV2QoS4FlowHdrError, sleV2QoS4FlowInnerVlan, sleV2QoS4FlowInner8021p, sleV2QoS4FlowMacFlag, 
				sleV2QoS4FlowIpFlag, sleV2QoS4FlowTagType, sleV2QoS4FlowMacDlf, sleV2QoS4FlowOuterVlan, sleV2QoS4FlowOuter8021p, 
				sleV2QoS4FlowOnuCircuitId, sleV2QoS4FlowControlReqResult, sleV2QoSFlowTrafficClass, sleV2QoSFlowFlowLabel }
			STATUS current
			DESCRIPTION 
				"setFlowEx"
			::= { sleV2QoS4FlowNotification 9 }

		
		-- 1.3.6.1.4.1.6296.102.10.2.2.2
		sleV2QoS4FlowClass OBJECT IDENTIFIER ::= { sleV2QoS4Flow 2 }

		
		-- 1.3.6.1.4.1.6296.102.10.2.2.2.1
		sleV2QoS4FlowClassTable OBJECT-TYPE
			SYNTAX SEQUENCE OF SleV2QoS4FlowClassEntry
			MAX-ACCESS not-accessible
			STATUS current
			DESCRIPTION
				"flow class table."
			::= { sleV2QoS4FlowClass 1 }

		
		-- 1.3.6.1.4.1.6296.102.10.2.2.2.1.1
		sleV2QoS4FlowClassEntry OBJECT-TYPE
			SYNTAX SleV2QoS4FlowClassEntry
			MAX-ACCESS not-accessible
			STATUS current
			DESCRIPTION
				"key: sleV2QoS4FlowIndex, sleV2QoS4FlowClassIndex"
			INDEX { sleV2QoS4FlowIndex, sleV2QoS4FlowClassIndex }
			::= { sleV2QoS4FlowClassTable 1 }

		
		SleV2QoS4FlowClassEntry ::=
			SEQUENCE { 
				sleV2QoS4FlowClassIndex
					IntClassIndex,
				sleV2QoS4FlowClassID
					IntClassIndex,
				sleV2QoS4FlowClassName
					OctetName
			 }

		-- 1.3.6.1.4.1.6296.102.10.2.2.2.1.1.1
		sleV2QoS4FlowClassIndex OBJECT-TYPE
			SYNTAX IntClassIndex
			MAX-ACCESS read-only
			STATUS current
			DESCRIPTION
				"The index of the class for the flow"
			::= { sleV2QoS4FlowClassEntry 1 }

		
		-- 1.3.6.1.4.1.6296.102.10.2.2.2.1.1.2
		sleV2QoS4FlowClassID OBJECT-TYPE
			SYNTAX IntClassIndex
			MAX-ACCESS read-only
			STATUS current
			DESCRIPTION
				"The identifier of the class"
			::= { sleV2QoS4FlowClassEntry 2 }

		
		-- 1.3.6.1.4.1.6296.102.10.2.2.2.1.1.3
		sleV2QoS4FlowClassName OBJECT-TYPE
			SYNTAX OctetName
			MAX-ACCESS read-only
			STATUS current
			DESCRIPTION
				"The name of the class"
			::= { sleV2QoS4FlowClassEntry 3 }

		
		-- 1.3.6.1.4.1.6296.102.10.2.2.3
		sleV2QoS4FlowPolicy OBJECT IDENTIFIER ::= { sleV2QoS4Flow 3 }

		
		-- 1.3.6.1.4.1.6296.102.10.2.2.3.1
		sleV2QoS4FlowPolicyTable OBJECT-TYPE
			SYNTAX SEQUENCE OF SleV2QoS4FlowPolicyEntry
			MAX-ACCESS not-accessible
			STATUS current
			DESCRIPTION
				"flow policy table."
			::= { sleV2QoS4FlowPolicy 1 }

		
		-- 1.3.6.1.4.1.6296.102.10.2.2.3.1.1
		sleV2QoS4FlowPolicyEntry OBJECT-TYPE
			SYNTAX SleV2QoS4FlowPolicyEntry
			MAX-ACCESS not-accessible
			STATUS current
			DESCRIPTION
				"key: sleV2QoS4FlowIndex, sleV2QoS4FlowPolicyIndex"
			INDEX { sleV2QoS4FlowIndex, sleV2QoS4FlowPolicyIndex }
			::= { sleV2QoS4FlowPolicyTable 1 }

		
		SleV2QoS4FlowPolicyEntry ::=
			SEQUENCE { 
				sleV2QoS4FlowPolicyIndex
					IntPolicyIndex,
				sleV2QoS4FlowPolicyID
					IntPolicyIndex,
				sleV2QoS4FlowPolicyName
					OctetName
			 }

		-- 1.3.6.1.4.1.6296.102.10.2.2.3.1.1.1
		sleV2QoS4FlowPolicyIndex OBJECT-TYPE
			SYNTAX IntPolicyIndex
			MAX-ACCESS read-only
			STATUS current
			DESCRIPTION
				"The index of the policy for the flow"
			::= { sleV2QoS4FlowPolicyEntry 1 }

		
		-- 1.3.6.1.4.1.6296.102.10.2.2.3.1.1.2
		sleV2QoS4FlowPolicyID OBJECT-TYPE
			SYNTAX IntPolicyIndex
			MAX-ACCESS read-only
			STATUS current
			DESCRIPTION
				"The identifier of the policy"
			::= { sleV2QoS4FlowPolicyEntry 2 }

		
		-- 1.3.6.1.4.1.6296.102.10.2.2.3.1.1.3
		sleV2QoS4FlowPolicyName OBJECT-TYPE
			SYNTAX OctetName
			MAX-ACCESS read-only
			STATUS current
			DESCRIPTION
				"The name of the policy"
			::= { sleV2QoS4FlowPolicyEntry 3 }

		
		-- 1.3.6.1.4.1.6296.102.10.2.3
		sleV2QoS4Class OBJECT IDENTIFIER ::= { sleV2QoS4 3 }

		
		-- 1.3.6.1.4.1.6296.102.10.2.3.1
		sleV2QoS4ClassInfo OBJECT IDENTIFIER ::= { sleV2QoS4Class 1 }

		
		-- 1.3.6.1.4.1.6296.102.10.2.3.1.1
		sleV2QoS4ClassTable OBJECT-TYPE
			SYNTAX SEQUENCE OF SleV2QoS4ClassEntry
			MAX-ACCESS not-accessible
			STATUS current
			DESCRIPTION
				"class table."
			::= { sleV2QoS4ClassInfo 1 }

		
		-- 1.3.6.1.4.1.6296.102.10.2.4.1.1.1
		sleV2QoS4ClassEntry OBJECT-TYPE
			SYNTAX SleV2QoS4ClassEntry
			MAX-ACCESS not-accessible
			STATUS current
			DESCRIPTION
				"key: sleV2QoS4ClassIndex"
			INDEX { sleV2QoS4ClassIndex }
			::= { sleV2QoS4ClassTable 1 }

		
		SleV2QoS4ClassEntry ::=
			SEQUENCE { 
				sleV2QoS4ClassIndex
					IntClassIndex,
				sleV2QoS4ClassName
					OctetName,
				sleV2QoS4ClassFlowCnt
					Counter32
			 }

		-- 1.3.6.1.4.1.6296.102.10.2.4.1.1.1.1
		sleV2QoS4ClassIndex OBJECT-TYPE
			SYNTAX IntClassIndex
			MAX-ACCESS read-only
			STATUS current
			DESCRIPTION
				"The index of class"
			::= { sleV2QoS4ClassEntry 1 }

		
		-- 1.3.6.1.4.1.6296.102.10.2.4.1.1.1.2
		sleV2QoS4ClassName OBJECT-TYPE
			SYNTAX OctetName
			MAX-ACCESS read-only
			STATUS current
			DESCRIPTION
				"The name of class"
			::= { sleV2QoS4ClassEntry 2 }

		
		-- 1.3.6.1.4.1.6296.102.10.2.4.1.1.1.3
		sleV2QoS4ClassFlowCnt OBJECT-TYPE
			SYNTAX Counter32
			MAX-ACCESS read-only
			STATUS current
			DESCRIPTION
				"The counter of flow in class"
			::= { sleV2QoS4ClassEntry 3 }

		
		-- 1.3.6.1.4.1.6296.102.10.2.3.1.2
		sleV2QoS4ClassControl OBJECT IDENTIFIER ::= { sleV2QoS4ClassInfo 2 }

		
		-- 1.3.6.1.4.1.6296.102.10.2.3.1.2.1
		sleV2QoS4ClassControlRequest OBJECT-TYPE
			SYNTAX INTEGER
				{
				createClass(1),
				destroyClass(2),
				destroyAllClass(3)
				}
			MAX-ACCESS read-write
			STATUS current
			DESCRIPTION
				"The request of a user command"
			::= { sleV2QoS4ClassControl 1 }

		
		-- 1.3.6.1.4.1.6296.102.10.2.3.1.2.2
		sleV2QoS4ClassControlStatus OBJECT-TYPE
			SYNTAX SleControlStatusType
			MAX-ACCESS read-only
			STATUS current
			DESCRIPTION
				"The status of user command"
			::= { sleV2QoS4ClassControl 2 }

		
		-- 1.3.6.1.4.1.6296.102.10.2.3.1.2.3
		sleV2QoS4ClassControlTimer OBJECT-TYPE
			SYNTAX Gauge32
			MAX-ACCESS read-write
			STATUS current
			DESCRIPTION
				"The maximum time for the manager for a long running user command"
			::= { sleV2QoS4ClassControl 3 }

		
		-- 1.3.6.1.4.1.6296.102.10.2.3.1.2.4
		sleV2QoS4ClassControlTimeStamp OBJECT-TYPE
			SYNTAX TimeTicks
			MAX-ACCESS read-only
			STATUS current
			DESCRIPTION
				"The time stamp of the last command(end of command)"
			::= { sleV2QoS4ClassControl 4 }

		
		-- 1.3.6.1.4.1.6296.102.10.2.3.1.2.5
		sleV2QoS4ClassControlReqResult OBJECT-TYPE
			SYNTAX SleControlRequestResultType
			MAX-ACCESS read-only
			STATUS current
			DESCRIPTION
				"The result of the last user command"
			::= { sleV2QoS4ClassControl 5 }

		
		-- 1.3.6.1.4.1.6296.102.10.2.3.1.2.6
		sleV2QoS4ClassControlIndex OBJECT-TYPE
			SYNTAX IntClassIndex
			MAX-ACCESS read-write
			STATUS current
			DESCRIPTION
				"The index of class"
			::= { sleV2QoS4ClassControl 6 }

		
		-- 1.3.6.1.4.1.6296.102.10.2.3.1.2.7
		sleV2QoS4ClassControlName OBJECT-TYPE
			SYNTAX OctetName
			MAX-ACCESS read-write
			STATUS current
			DESCRIPTION
				"The name of class"
			::= { sleV2QoS4ClassControl 7 }

		
		-- 1.3.6.1.4.1.6296.102.10.2.3.1.3
		sleV2QoS4ClassNotification OBJECT IDENTIFIER ::= { sleV2QoS4ClassInfo 3 }

		
		-- 1.3.6.1.4.1.6296.102.10.2.3.1.3.1
		sleClassCreated NOTIFICATION-TYPE
			OBJECTS { sleV2QoS4ClassControlRequest, sleV2QoS4ClassControlTimeStamp, sleV2QoS4ClassControlReqResult }
			STATUS current
			DESCRIPTION 
				"Description."
			::= { sleV2QoS4ClassNotification 1 }

		
		-- 1.3.6.1.4.1.6296.102.10.2.3.1.3.2
		sleClassDestroyed NOTIFICATION-TYPE
			OBJECTS { sleV2QoS4ClassControlRequest, sleV2QoS4ClassControlTimeStamp, sleV2QoS4ClassControlReqResult, sleV2QoS4ClassControlIndex }
			STATUS current
			DESCRIPTION 
				"Description."
			::= { sleV2QoS4ClassNotification 2 }

		
		-- 1.3.6.1.4.1.6296.102.10.2.3.1.3.3
		sleClassAllDestroyed NOTIFICATION-TYPE
			OBJECTS { sleV2QoS4ClassControlRequest, sleV2QoS4ClassControlTimeStamp, sleV2QoS4ClassControlReqResult }
			STATUS current
			DESCRIPTION 
				"Description."
			::= { sleV2QoS4ClassNotification 3 }

		
		-- 1.3.6.1.4.1.6296.102.10.2.3.2
		sleV2QoS4ClassFlow OBJECT IDENTIFIER ::= { sleV2QoS4Class 2 }

		
		-- 1.3.6.1.4.1.6296.102.10.2.3.2.1
		sleV2QoS4ClassFlowTable OBJECT-TYPE
			SYNTAX SEQUENCE OF SleV2QoS4ClassFlowEntry
			MAX-ACCESS not-accessible
			STATUS current
			DESCRIPTION
				"class flow table."
			::= { sleV2QoS4ClassFlow 1 }

		
		-- 1.3.6.1.4.1.6296.102.10.2.4.2.1.1
		sleV2QoS4ClassFlowEntry OBJECT-TYPE
			SYNTAX SleV2QoS4ClassFlowEntry
			MAX-ACCESS not-accessible
			STATUS current
			DESCRIPTION
				"key: sleV2QoS4ClassIndex, sleV2QoS4ClassFlowIndex"
			INDEX { sleV2QoS4ClassIndex, sleV2QoS4ClassFlowIndex }
			::= { sleV2QoS4ClassFlowTable 1 }

		
		SleV2QoS4ClassFlowEntry ::=
			SEQUENCE { 
				sleV2QoS4ClassFlowIndex
					IntFlowIndex,
				sleV2QoS4ClassFlowID
					IntFlowIndex,
				sleV2QoS4ClassFlowName
					OctetName,
				sleV2QoS4ClassFlowClassName
					OctetName
			 }

		-- 1.3.6.1.4.1.6296.102.10.2.4.2.1.1.1
		sleV2QoS4ClassFlowIndex OBJECT-TYPE
			SYNTAX IntFlowIndex
			MAX-ACCESS read-only
			STATUS current
			DESCRIPTION
				"The index of flow in class"
			::= { sleV2QoS4ClassFlowEntry 1 }

		
		-- 1.3.6.1.4.1.6296.102.10.2.4.2.1.1.2
		sleV2QoS4ClassFlowID OBJECT-TYPE
			SYNTAX IntFlowIndex
			MAX-ACCESS read-only
			STATUS current
			DESCRIPTION
				"The identifier of flow"
			::= { sleV2QoS4ClassFlowEntry 2 }

		
		-- 1.3.6.1.4.1.6296.102.10.2.4.2.1.1.3
		sleV2QoS4ClassFlowName OBJECT-TYPE
			SYNTAX OctetName
			MAX-ACCESS read-only
			STATUS current
			DESCRIPTION
				"The name of the flow"
			::= { sleV2QoS4ClassFlowEntry 3 }

		
		-- 1.3.6.1.4.1.6296.102.10.2.4.2.1.1.4
		sleV2QoS4ClassFlowClassName OBJECT-TYPE
			SYNTAX OctetName
			MAX-ACCESS read-only
			STATUS current
			DESCRIPTION
				"The class name of the flow"
			::= { sleV2QoS4ClassFlowEntry 4 }

		
		-- 1.3.6.1.4.1.6296.102.10.2.3.2.2
		sleV2QoS4ClassFlowControl OBJECT IDENTIFIER ::= { sleV2QoS4ClassFlow 2 }

		
		-- 1.3.6.1.4.1.6296.102.10.2.3.2.2.1
		sleV2QoS4ClassFlowControlRequest OBJECT-TYPE
			SYNTAX INTEGER
				{
				addFlow(1),
				deleteFlow(2),
				deleteAllFlow(3)
				}
			MAX-ACCESS read-write
			STATUS current
			DESCRIPTION
				"The request of a user command"
			::= { sleV2QoS4ClassFlowControl 1 }

		
		-- 1.3.6.1.4.1.6296.102.10.2.3.2.2.2
		sleV2QoS4ClassFlowControlStatus OBJECT-TYPE
			SYNTAX SleControlStatusType
			MAX-ACCESS read-only
			STATUS current
			DESCRIPTION
				"The status of user command"
			::= { sleV2QoS4ClassFlowControl 2 }

		
		-- 1.3.6.1.4.1.6296.102.10.2.3.2.2.3
		sleV2QoS4ClassFlowControlTimer OBJECT-TYPE
			SYNTAX Gauge32
			MAX-ACCESS read-write
			STATUS current
			DESCRIPTION
				"The maximum time for the manager for a long running user command"
			::= { sleV2QoS4ClassFlowControl 3 }

		
		-- 1.3.6.1.4.1.6296.102.10.2.3.2.2.4
		sleV2QoS4ClassFlowControlTimeStamp OBJECT-TYPE
			SYNTAX TimeTicks
			MAX-ACCESS read-only
			STATUS current
			DESCRIPTION
				"The time stamp of the last command(end of command)"
			::= { sleV2QoS4ClassFlowControl 4 }

		
		-- 1.3.6.1.4.1.6296.102.10.2.3.2.2.5
		sleV2QoS4ClassFlowControlReqResult OBJECT-TYPE
			SYNTAX SleControlRequestResultType
			MAX-ACCESS read-only
			STATUS current
			DESCRIPTION
				"The result of the last user command"
			::= { sleV2QoS4ClassFlowControl 5 }

		
		-- 1.3.6.1.4.1.6296.102.10.2.3.2.2.6
		sleV2QoS4ClassFlowControlClassIndex OBJECT-TYPE
			SYNTAX IntClassIndex
			MAX-ACCESS read-write
			STATUS current
			DESCRIPTION
				"The index of class"
			::= { sleV2QoS4ClassFlowControl 6 }

		
		-- 1.3.6.1.4.1.6296.102.10.2.3.2.2.7
		sleV2QoS4ClassFlowControlFlowIndex OBJECT-TYPE
			SYNTAX IntFlowIndex
			MAX-ACCESS read-write
			STATUS current
			DESCRIPTION
				"The index of flow in this class"
			::= { sleV2QoS4ClassFlowControl 7 }

		
		-- 1.3.6.1.4.1.6296.102.10.2.3.2.2.8
		sleV2QoS4ClassFlowControlFlowID OBJECT-TYPE
			SYNTAX IntFlowIndex
			MAX-ACCESS read-write
			STATUS current
			DESCRIPTION
				"The index of flow
				Refer to sleV2QoS4FlowIndex
				"
			::= { sleV2QoS4ClassFlowControl 8 }

		
		-- 1.3.6.1.4.1.6296.102.10.2.3.2.2.9
		sleV2QoS4ClassFlowControlClassName OBJECT-TYPE
			SYNTAX OctetName
			MAX-ACCESS read-write
			STATUS current
			DESCRIPTION
				"The class name of class-flow
				"
			::= { sleV2QoS4ClassFlowControl 9 }

		
		-- 1.3.6.1.4.1.6296.102.10.2.3.2.3
		sleV2QoS4ClassFlowNotification OBJECT IDENTIFIER ::= { sleV2QoS4ClassFlow 3 }

		
		-- 1.3.6.1.4.1.6296.102.10.2.3.2.3.1
		sleClassFlowAdded NOTIFICATION-TYPE
			OBJECTS { sleV2QoS4ClassFlowControlRequest, sleV2QoS4ClassFlowControlTimeStamp, sleV2QoS4ClassFlowControlClassName, sleV2QoS4ClassFlowControlReqResult, sleV2QoS4ClassFlowID
				 }
			STATUS current
			DESCRIPTION 
				"Description."
			::= { sleV2QoS4ClassFlowNotification 1 }

		
		-- 1.3.6.1.4.1.6296.102.10.2.3.2.3.2
		sleClassFlowDeleted NOTIFICATION-TYPE
			OBJECTS { sleV2QoS4ClassFlowControlRequest, sleV2QoS4ClassFlowControlTimeStamp, sleV2QoS4ClassFlowControlReqResult, sleV2QoS4ClassFlowControlClassIndex, sleV2QoS4ClassFlowControlFlowIndex, 
				sleV2QoS4ClassFlowControlClassName }
			STATUS current
			DESCRIPTION 
				"Description."
			::= { sleV2QoS4ClassFlowNotification 2 }

		
		-- 1.3.6.1.4.1.6296.102.10.2.3.2.3.3
		sleClassFlowAllDeleted NOTIFICATION-TYPE
			OBJECTS { sleV2QoS4ClassFlowControlRequest, sleV2QoS4ClassFlowControlTimeStamp, sleV2QoS4ClassFlowControlReqResult, sleV2QoS4ClassFlowControlClassIndex }
			STATUS current
			DESCRIPTION 
				"Description."
			::= { sleV2QoS4ClassFlowNotification 3 }

		
		-- 1.3.6.1.4.1.6296.102.10.2.3.3
		sleV2QoS4ClassPolicy OBJECT IDENTIFIER ::= { sleV2QoS4Class 3 }

		
		-- 1.3.6.1.4.1.6296.102.10.2.3.3.1
		sleV2QoS4ClassPolicyTable OBJECT-TYPE
			SYNTAX SEQUENCE OF SleV2QoS4ClassPolicyEntry
			MAX-ACCESS not-accessible
			STATUS current
			DESCRIPTION
				"class policy table."
			::= { sleV2QoS4ClassPolicy 1 }

		
		-- 1.3.6.1.4.1.6296.102.10.2.4.3.1.1
		sleV2QoS4ClassPolicyEntry OBJECT-TYPE
			SYNTAX SleV2QoS4ClassPolicyEntry
			MAX-ACCESS not-accessible
			STATUS current
			DESCRIPTION
				"key: sleV2QoS4ClassIndex, sleV2QoS4ClassPolicyIndex"
			INDEX { sleV2QoS4ClassIndex, sleV2QoS4ClassPolicyIndex }
			::= { sleV2QoS4ClassPolicyTable 1 }

		
		SleV2QoS4ClassPolicyEntry ::=
			SEQUENCE { 
				sleV2QoS4ClassPolicyIndex
					IntPolicyIndex,
				sleV2QoS4ClassPolicyID
					IntPolicyIndex,
				sleV2QoS4ClassPolicyName
					OctetName
			 }

		-- 1.3.6.1.4.1.6296.102.10.2.4.3.1.1.1
		sleV2QoS4ClassPolicyIndex OBJECT-TYPE
			SYNTAX IntPolicyIndex
			MAX-ACCESS read-only
			STATUS current
			DESCRIPTION
				"The index of the policy for the class"
			::= { sleV2QoS4ClassPolicyEntry 1 }

		
		-- 1.3.6.1.4.1.6296.102.10.2.4.3.1.1.2
		sleV2QoS4ClassPolicyID OBJECT-TYPE
			SYNTAX IntPolicyIndex
			MAX-ACCESS read-only
			STATUS current
			DESCRIPTION
				"The identifier of the policy"
			::= { sleV2QoS4ClassPolicyEntry 2 }

		
		-- 1.3.6.1.4.1.6296.102.10.2.4.3.1.1.3
		sleV2QoS4ClassPolicyName OBJECT-TYPE
			SYNTAX OctetName
			MAX-ACCESS read-only
			STATUS current
			DESCRIPTION
				"The name of the policy"
			::= { sleV2QoS4ClassPolicyEntry 3 }

		
		-- 1.3.6.1.4.1.6296.102.10.2.4
		sleV2QoS4Policer OBJECT IDENTIFIER ::= { sleV2QoS4 4 }

		
		-- 1.3.6.1.4.1.6296.102.10.2.4.1
		sleV2QoS4PolicerInfo OBJECT IDENTIFIER ::= { sleV2QoS4Policer 1 }

		
		-- 1.3.6.1.4.1.6296.102.10.2.4.1.1
		sleV2QoS4PolicerTable OBJECT-TYPE
			SYNTAX SEQUENCE OF SleV2QoS4PolicerEntry
			MAX-ACCESS not-accessible
			STATUS current
			DESCRIPTION
				"policer table."
			::= { sleV2QoS4PolicerInfo 1 }

		
		-- 1.3.6.1.4.1.6296.102.10.2.4.1.1.1
		sleV2QoS4PolicerEntry OBJECT-TYPE
			SYNTAX SleV2QoS4PolicerEntry
			MAX-ACCESS not-accessible
			STATUS current
			DESCRIPTION
				"key: sleV2QoS4PolicerIndex"
			INDEX { sleV2QoS4PolicerIndex }
			::= { sleV2QoS4PolicerTable 1 }

		
		SleV2QoS4PolicerEntry ::=
			SEQUENCE { 
				sleV2QoS4PolicerIndex
					IntPolicerIndex,
				sleV2QoS4PolicerName
					OctetName,
				sleV2QoS4PolicerMeterMode
					IntMeterMode,
				sleV2QoS4PolicerRateLimit
					Integer32,
				sleV2QoS4PolicerColorType
					IntColorType,
				sleV2QoS4PolicerColorMode
					IntColorMode,
				sleV2QoS4PolicerColorAwareMode
					IntColorAwareMode,
				sleV2QoS4PolicerColorCIR
					IntColorCIR,
				sleV2QoS4PolicerColorCBS
					IntColorCBS,
				sleV2QoS4PolicerColorPIR
					IntColorPIR,
				sleV2QoS4PolicerColorPBS
					IntColorPBS,
				sleV2QoS4PolicerColorEBS
					IntColorEBS,
				sleV2QoS4PolicerColorRedAction
					IntColorAction,
				sleV2QoS4PolicerColorYellowAction
					IntColorAction,
				sleV2QoS4PolicerColorGreenAction
					IntColorAction,
				sleV2QoS4PolicerRemarkLayerMode
					BITS,
				sleV2QoS4PolicerRemarkMode
					BITS,
				sleV2QoS4PolicerCounterMode
					IntCounterMode,
				sleV2QoS4PolicerAvrgCounterMode
					IntAvrgCounterMode,
				sleV2QoS4PolicerMinBandwidth
					Integer32,
				sleV2QoS4PolicerMaxBandwidth
					Integer32,
				sleV2QoS4PolicerColorRedDscp
					IntDscp,
				sleV2QoS4PolicerColorYellowDscp
					IntDscp,
				sleV2QoS4PolicerColorGreenDscp
					IntDscp,
				sleV2QoS4PolicerColorRedCosType
					INTEGER,
				sleV2QoS4PolicerColorRedCos
					IntCoS,
				sleV2QoS4PolicerColorYellowCosType
					INTEGER,
				sleV2QoS4PolicerColorYellowCos
					IntToS,
				sleV2QoS4PolicerColorGreenCosType
					INTEGER,
				sleV2QoS4PolicerColorGreenCos
					IntToS
			 }

		-- 1.3.6.1.4.1.6296.102.10.2.4.1.1.1.1
		sleV2QoS4PolicerIndex OBJECT-TYPE
			SYNTAX IntPolicerIndex
			MAX-ACCESS read-only
			STATUS current
			DESCRIPTION
				"The index of policer"
			::= { sleV2QoS4PolicerEntry 1 }

		
		-- 1.3.6.1.4.1.6296.102.10.2.4.1.1.1.2
		sleV2QoS4PolicerName OBJECT-TYPE
			SYNTAX OctetName
			MAX-ACCESS read-only
			STATUS current
			DESCRIPTION
				"The name of policer"
			::= { sleV2QoS4PolicerEntry 2 }

		
		-- 1.3.6.1.4.1.6296.102.10.2.4.1.1.1.3
		sleV2QoS4PolicerMeterMode OBJECT-TYPE
			SYNTAX IntMeterMode
			MAX-ACCESS read-only
			STATUS current
			DESCRIPTION
				"The meter mode.
				*) According to this value, rate-limit, color-marking and min-max-bandwidth exclusively activated.
				The value of -1 means nothing(not set)
				"
			::= { sleV2QoS4PolicerEntry 3 }

		
		-- 1.3.6.1.4.1.6296.102.10.2.4.1.1.1.4
		sleV2QoS4PolicerRateLimit OBJECT-TYPE
			SYNTAX Integer32
			MAX-ACCESS read-write
			STATUS current
			DESCRIPTION
				"The packet rate limit
				The value of -1 unlimit(not set)
				"
			::= { sleV2QoS4PolicerEntry 4 }

		
		-- 1.3.6.1.4.1.6296.102.10.2.4.1.1.1.5
		sleV2QoS4PolicerColorType OBJECT-TYPE
			SYNTAX IntColorType
			MAX-ACCESS read-only
			STATUS current
			DESCRIPTION
				"Color marking type
				Available Value : srTCM or trTCM
				srTCM = Single Rate Three Color Marking
				trTCM = Two Rate Three Color Marking
				The value of -1 means nothing(not set)
				"
			::= { sleV2QoS4PolicerEntry 5 }

		
		-- 1.3.6.1.4.1.6296.102.10.2.4.1.1.1.6
		sleV2QoS4PolicerColorMode OBJECT-TYPE
			SYNTAX IntColorMode
			MAX-ACCESS read-only
			STATUS current
			DESCRIPTION
				"Color marking mode.
				The value of -1 means nothing(not set)
				"
			::= { sleV2QoS4PolicerEntry 6 }

		
		-- 1.3.6.1.4.1.6296.102.10.2.4.1.1.1.7
		sleV2QoS4PolicerColorAwareMode OBJECT-TYPE
			SYNTAX IntColorAwareMode
			MAX-ACCESS read-only
			STATUS current
			DESCRIPTION
				"Color marking aware mode
				*) Used only when sleV2QoS4PolicerColorMode is aware
				The value of -1 is nothing(not set)
				"
			::= { sleV2QoS4PolicerEntry 7 }

		
		-- 1.3.6.1.4.1.6296.102.10.2.4.1.1.1.8
		sleV2QoS4PolicerColorCIR OBJECT-TYPE
			SYNTAX IntColorCIR
			MAX-ACCESS read-only
			STATUS current
			DESCRIPTION
				"Committed Information Rate.
				The value is in unit for 64 kbps.
				The value of -1 is nothing(not set)
				"
			::= { sleV2QoS4PolicerEntry 8 }

		
		-- 1.3.6.1.4.1.6296.102.10.2.4.1.1.1.9
		sleV2QoS4PolicerColorCBS OBJECT-TYPE
			SYNTAX IntColorCBS
			MAX-ACCESS read-only
			STATUS current
			DESCRIPTION
				"Committed Burst Size.
				The value is in unit for square of 2 bits
				The value of -1 is nothing(not set)
				"
			::= { sleV2QoS4PolicerEntry 9 }

		
		-- 1.3.6.1.4.1.6296.102.10.2.4.1.1.1.10
		sleV2QoS4PolicerColorPIR OBJECT-TYPE
			SYNTAX IntColorPIR
			MAX-ACCESS read-only
			STATUS current
			DESCRIPTION
				"Peak Information Rate. 
				*) Used only when sleV2QoS4PolicerColorType is trTCM.
				The value is in unit for 64 kbps.
				The value of -1 is nothing(not set)
				"
			::= { sleV2QoS4PolicerEntry 10 }

		
		-- 1.3.6.1.4.1.6296.102.10.2.4.1.1.1.11
		sleV2QoS4PolicerColorPBS OBJECT-TYPE
			SYNTAX IntColorPBS
			MAX-ACCESS read-only
			STATUS current
			DESCRIPTION
				"Peak Burst Size. 
				*) Used only when sleV2QoS4PolicerColorType is trTCM.
				The value is in unit for square of 2 bits.
				The value of -1 is nothing(not set)
				"
			::= { sleV2QoS4PolicerEntry 11 }

		
		-- 1.3.6.1.4.1.6296.102.10.2.4.1.1.1.12
		sleV2QoS4PolicerColorEBS OBJECT-TYPE
			SYNTAX IntColorEBS
			MAX-ACCESS read-only
			STATUS current
			DESCRIPTION
				"Excess Burst Size. 
				*) Used only when sleV2QoS4PolicerColorType is srTCM.
				The value is in unit for square of 2 bits.
				The value of -1 is nothing(not set)
				"
			::= { sleV2QoS4PolicerEntry 12 }

		
		-- 1.3.6.1.4.1.6296.102.10.2.4.1.1.1.13
		sleV2QoS4PolicerColorRedAction OBJECT-TYPE
			SYNTAX IntColorAction
			MAX-ACCESS read-only
			STATUS current
			DESCRIPTION
				"The action to be apply when incoming packet is colored in red.
				The value of -1 is nothing(not set)
				"
			::= { sleV2QoS4PolicerEntry 13 }

		
		-- 1.3.6.1.4.1.6296.102.10.2.4.1.1.1.14
		sleV2QoS4PolicerColorYellowAction OBJECT-TYPE
			SYNTAX IntColorAction
			MAX-ACCESS read-only
			STATUS current
			DESCRIPTION
				"The action to be apply when incoming packet is colored in yellow.
				The value of -1 is nothing(not set)
				"
			::= { sleV2QoS4PolicerEntry 14 }

		
		-- 1.3.6.1.4.1.6296.102.10.2.4.1.1.1.15
		sleV2QoS4PolicerColorGreenAction OBJECT-TYPE
			SYNTAX IntColorAction
			MAX-ACCESS read-only
			STATUS current
			DESCRIPTION
				"The action to be apply when incoming packet is colored in green. (not supported)
				The value of -1 is nothing(not set)
				"
			::= { sleV2QoS4PolicerEntry 15 }

		
		-- 1.3.6.1.4.1.6296.102.10.2.4.1.1.1.16
		sleV2QoS4PolicerRemarkLayerMode OBJECT-TYPE
			SYNTAX BITS
				{
				remarkByDSCP(0),
				remarkByQueueOrCoS(1)
				}
			MAX-ACCESS read-only
			STATUS current
			DESCRIPTION
				"The remark mode
				0 : Layer3
				1 : Layer2
				"
			::= { sleV2QoS4PolicerEntry 16 }

		
		-- 1.3.6.1.4.1.6296.102.10.2.4.1.1.1.17
		sleV2QoS4PolicerRemarkMode OBJECT-TYPE
			SYNTAX BITS
				{
				remarkQueue(0),
				remarkExtCoS(1)
				}
			MAX-ACCESS read-only
			STATUS current
			DESCRIPTION
				"This value is available when sleV2QoS4PolicerRemarkLayerMode bit was checked(one or more)
				0 : remark Queue
				1 : remark External CoS
				"
			::= { sleV2QoS4PolicerEntry 17 }

		
		-- 1.3.6.1.4.1.6296.102.10.2.4.1.1.1.18
		sleV2QoS4PolicerCounterMode OBJECT-TYPE
			SYNTAX IntCounterMode
			MAX-ACCESS read-only
			STATUS current
			DESCRIPTION
				"The counter mode
				The value of -1 is nothing(not set)
				"
			::= { sleV2QoS4PolicerEntry 18 }

		
		-- 1.3.6.1.4.1.6296.102.10.2.4.1.1.1.19
		sleV2QoS4PolicerAvrgCounterMode OBJECT-TYPE
			SYNTAX IntAvrgCounterMode
			MAX-ACCESS read-only
			STATUS current
			DESCRIPTION
				"The average counter mode
				The value of -1 is nothing(not set)
				"
			::= { sleV2QoS4PolicerEntry 19 }

		
		-- 1.3.6.1.4.1.6296.102.10.2.4.1.1.1.20
		sleV2QoS4PolicerMinBandwidth OBJECT-TYPE
			SYNTAX Integer32
			MAX-ACCESS read-only
			STATUS current
			DESCRIPTION
				"The minium bandwidth"
			::= { sleV2QoS4PolicerEntry 20 }

		
		-- 1.3.6.1.4.1.6296.102.10.2.4.1.1.1.21
		sleV2QoS4PolicerMaxBandwidth OBJECT-TYPE
			SYNTAX Integer32
			MAX-ACCESS read-only
			STATUS current
			DESCRIPTION
				"The maximum bandwidth"
			::= { sleV2QoS4PolicerEntry 21 }

		
		-- 1.3.6.1.4.1.6296.102.10.2.4.1.1.1.22
		sleV2QoS4PolicerColorRedDscp OBJECT-TYPE
			SYNTAX IntDscp
			MAX-ACCESS read-only
			STATUS current
			DESCRIPTION
				"The desc value to be apply when incoming packet is colored in red.
				Default : 30(0x1e)
				"
			DEFVAL { 30 }
			::= { sleV2QoS4PolicerEntry 22 }

		
		-- 1.3.6.1.4.1.6296.102.10.2.4.1.1.1.23
		sleV2QoS4PolicerColorYellowDscp OBJECT-TYPE
			SYNTAX IntDscp
			MAX-ACCESS read-only
			STATUS current
			DESCRIPTION
				"The desc value to be apply when incoming packet is colored in yellow.
				Default : 28(0x1c)
				"
			DEFVAL { 28 }
			::= { sleV2QoS4PolicerEntry 23 }

		
		-- 1.3.6.1.4.1.6296.102.10.2.4.1.1.1.24
		sleV2QoS4PolicerColorGreenDscp OBJECT-TYPE
			SYNTAX IntDscp
			MAX-ACCESS read-only
			STATUS current
			DESCRIPTION
				"The desc value to be apply when incoming packet is colored in green.
				Default : 30(0x1a)
				"
			DEFVAL { 26 }
			::= { sleV2QoS4PolicerEntry 24 }

		
		-- 1.3.6.1.4.1.6296.102.10.2.4.1.1.1.25
		sleV2QoS4PolicerColorRedCosType OBJECT-TYPE
			SYNTAX INTEGER
				{
				none(0),
				mark(1),
				overwrite(2)
				}
			MAX-ACCESS read-only
			STATUS current
			DESCRIPTION
				"The CoS type colored in red."
			::= { sleV2QoS4PolicerEntry 25 }

		
		-- 1.3.6.1.4.1.6296.102.10.2.4.1.1.1.26
		sleV2QoS4PolicerColorRedCos OBJECT-TYPE
			SYNTAX IntCoS
			MAX-ACCESS read-only
			STATUS current
			DESCRIPTION
				"The CoS colored in red."
			::= { sleV2QoS4PolicerEntry 26 }

		
		-- 1.3.6.1.4.1.6296.102.10.2.4.1.1.1.27
		sleV2QoS4PolicerColorYellowCosType OBJECT-TYPE
			SYNTAX INTEGER
				{
				none(0),
				mark(1),
				overwrite(2)
				}
			MAX-ACCESS read-only
			STATUS current
			DESCRIPTION
				"The CoS type colored in yellow"
			::= { sleV2QoS4PolicerEntry 27 }

		
		-- 1.3.6.1.4.1.6296.102.10.2.4.1.1.1.28
		sleV2QoS4PolicerColorYellowCos OBJECT-TYPE
			SYNTAX IntToS
			MAX-ACCESS read-only
			STATUS current
			DESCRIPTION
				"The CoS colored in yellow."
			::= { sleV2QoS4PolicerEntry 28 }

		
		-- 1.3.6.1.4.1.6296.102.10.2.4.1.1.1.29
		sleV2QoS4PolicerColorGreenCosType OBJECT-TYPE
			SYNTAX INTEGER
				{
				none(0),
				mark(1),
				overwrite(2)
				}
			MAX-ACCESS read-only
			STATUS current
			DESCRIPTION
				"The CoS type colored in yellow"
			::= { sleV2QoS4PolicerEntry 29 }

		
		-- 1.3.6.1.4.1.6296.102.10.2.4.1.1.1.30
		sleV2QoS4PolicerColorGreenCos OBJECT-TYPE
			SYNTAX IntToS
			MAX-ACCESS read-only
			STATUS current
			DESCRIPTION
				"The CoS colored in green."
			::= { sleV2QoS4PolicerEntry 30 }

		
		-- 1.3.6.1.4.1.6296.102.10.2.4.1.2
		sleV2QoS4PolicerControl OBJECT IDENTIFIER ::= { sleV2QoS4PolicerInfo 2 }

		
		-- 1.3.6.1.4.1.6296.102.10.2.4.1.2.1
		sleV2QoS4PolicerControlRequest OBJECT-TYPE
			SYNTAX INTEGER
				{
				createPolicer(1),
				modifyPolicer(2),
				destroyPolicer(3)
				}
			MAX-ACCESS read-write
			STATUS current
			DESCRIPTION
				"The request of a user command"
			::= { sleV2QoS4PolicerControl 1 }

		
		-- 1.3.6.1.4.1.6296.102.10.2.4.1.2.2
		sleV2QoS4PolicerControlStatus OBJECT-TYPE
			SYNTAX SleControlStatusType
			MAX-ACCESS read-only
			STATUS current
			DESCRIPTION
				"The status of user command"
			::= { sleV2QoS4PolicerControl 2 }

		
		-- 1.3.6.1.4.1.6296.102.10.2.4.1.2.3
		sleV2QoS4PolicerControlTimer OBJECT-TYPE
			SYNTAX Gauge32
			MAX-ACCESS read-write
			STATUS current
			DESCRIPTION
				"The maximum time for the manager for a long running user command"
			::= { sleV2QoS4PolicerControl 3 }

		
		-- 1.3.6.1.4.1.6296.102.10.2.4.1.2.4
		sleV2QoS4PolicerControlTimeStamp OBJECT-TYPE
			SYNTAX TimeTicks
			MAX-ACCESS read-only
			STATUS current
			DESCRIPTION
				"The time stamp of the last command(end of command)"
			::= { sleV2QoS4PolicerControl 4 }

		
		-- 1.3.6.1.4.1.6296.102.10.2.4.1.2.5
		sleV2QoS4PolicerControlReqResult OBJECT-TYPE
			SYNTAX SleControlRequestResultType
			MAX-ACCESS read-only
			STATUS current
			DESCRIPTION
				"The result of the last user command"
			::= { sleV2QoS4PolicerControl 5 }

		
		-- 1.3.6.1.4.1.6296.102.10.2.4.1.2.6
		sleV2QoS4PolicerControlIndex OBJECT-TYPE
			SYNTAX IntPolicerIndex
			MAX-ACCESS read-write
			STATUS current
			DESCRIPTION
				"The index of policer"
			::= { sleV2QoS4PolicerControl 6 }

		
		-- 1.3.6.1.4.1.6296.102.10.2.4.1.2.7
		sleV2QoS4PolicerControlName OBJECT-TYPE
			SYNTAX OctetName
			MAX-ACCESS read-write
			STATUS current
			DESCRIPTION
				"The name of policer"
			::= { sleV2QoS4PolicerControl 7 }

		
		-- 1.3.6.1.4.1.6296.102.10.2.4.1.2.8
		sleV2QoS4PolicerControlMeterMode OBJECT-TYPE
			SYNTAX IntMeterMode
			MAX-ACCESS read-write
			STATUS current
			DESCRIPTION
				"The meter mode.
				*) According to this value, rate-limit and color-marking exclusively activated.
				The value of -1 means nothing(not set)
				"
			::= { sleV2QoS4PolicerControl 8 }

		
		-- 1.3.6.1.4.1.6296.102.10.2.4.1.2.9
		sleV2QoS4PolicerControlRateLimit OBJECT-TYPE
			SYNTAX Integer32
			MAX-ACCESS read-write
			STATUS current
			DESCRIPTION
				"The packet rate limit
				The value of -1 unlimit(not set)
				"
			::= { sleV2QoS4PolicerControl 9 }

		
		-- 1.3.6.1.4.1.6296.102.10.2.4.1.2.10
		sleV2QoS4PolicerControlColorType OBJECT-TYPE
			SYNTAX IntColorType
			MAX-ACCESS read-write
			STATUS current
			DESCRIPTION
				"Color marking type
				Available Value : srTCM or trTCM
				srTCM = Single Rate Three Color Marking
				trTCM = Two Rate Three Color Marking
				The value of -1 is nothing(not set)
				"
			::= { sleV2QoS4PolicerControl 10 }

		
		-- 1.3.6.1.4.1.6296.102.10.2.4.1.2.11
		sleV2QoS4PolicerControlColorMode OBJECT-TYPE
			SYNTAX IntColorMode
			MAX-ACCESS read-write
			STATUS current
			DESCRIPTION
				"Color marking mode.
				*) Used only when sleColorMarkingMode is aware
				The value of -1 means nothing(not set)
				"
			::= { sleV2QoS4PolicerControl 11 }

		
		-- 1.3.6.1.4.1.6296.102.10.2.4.1.2.12
		sleV2QoS4PolicerControlColorAwareMode OBJECT-TYPE
			SYNTAX IntColorAwareMode
			MAX-ACCESS read-write
			STATUS current
			DESCRIPTION
				"Color marking aware mode
				The value of -1 is nothing(not set)
				"
			::= { sleV2QoS4PolicerControl 12 }

		
		-- 1.3.6.1.4.1.6296.102.10.2.4.1.2.13
		sleV2QoS4PolicerControlColorCIR OBJECT-TYPE
			SYNTAX IntColorCIR
			MAX-ACCESS read-write
			STATUS current
			DESCRIPTION
				"Committed Information Rate.
				The value is in unit for 64 kbps.
				The value of -1 is nothing(not set)
				
				"
			::= { sleV2QoS4PolicerControl 13 }

		
		-- 1.3.6.1.4.1.6296.102.10.2.4.1.2.14
		sleV2QoS4PolicerControlColorCBS OBJECT-TYPE
			SYNTAX IntColorCBS
			MAX-ACCESS read-write
			STATUS current
			DESCRIPTION
				"Committed Burst Size.
				The value is in unit for square of 2 bits
				The value of -1 is nothing(not set)
				"
			::= { sleV2QoS4PolicerControl 14 }

		
		-- 1.3.6.1.4.1.6296.102.10.2.4.1.2.15
		sleV2QoS4PolicerControlColorPIR OBJECT-TYPE
			SYNTAX IntColorPIR
			MAX-ACCESS read-write
			STATUS current
			DESCRIPTION
				"Peak Information Rate. 
				*) Used only when sleV2QoS4PolicerColorMode is Aware.
				The value is in unit for 64 kbps.
				The value of -1 is nothing(not set)
				"
			::= { sleV2QoS4PolicerControl 15 }

		
		-- 1.3.6.1.4.1.6296.102.10.2.4.1.2.16
		sleV2QoS4PolicerControlColorPBS OBJECT-TYPE
			SYNTAX IntColorPBS
			MAX-ACCESS read-write
			STATUS current
			DESCRIPTION
				"Peak Burst Size. 
				*) Used only when sleV2QoS4PolicerColorMode is Aware.
				The value is in unit for square of 2 bits.
				The value of -1 is nothing(not set)
				"
			::= { sleV2QoS4PolicerControl 16 }

		
		-- 1.3.6.1.4.1.6296.102.10.2.4.1.2.17
		sleV2QoS4PolicerControlColorEBS OBJECT-TYPE
			SYNTAX IntColorEBS
			MAX-ACCESS read-write
			STATUS current
			DESCRIPTION
				"Excess Burst Size. 
				*) Used only when sleV2QoS4PolicerColorMode is Blind.
				The value is in unit for square of 2 bits.
				The value of -1 is nothing(not set)
				"
			::= { sleV2QoS4PolicerControl 17 }

		
		-- 1.3.6.1.4.1.6296.102.10.2.4.1.2.18
		sleV2QoS4PolicerControlColorRedAction OBJECT-TYPE
			SYNTAX IntColorAction
			MAX-ACCESS read-write
			STATUS current
			DESCRIPTION
				"The action to be apply when incoming packet is colored in red.
				The value of -1 is nothing(not set)
				"
			::= { sleV2QoS4PolicerControl 18 }

		
		-- 1.3.6.1.4.1.6296.102.10.2.4.1.2.19
		sleV2QoS4PolicerControlColorYellowAction OBJECT-TYPE
			SYNTAX IntColorAction
			MAX-ACCESS read-write
			STATUS current
			DESCRIPTION
				"The action to be apply when incoming packet is colored in yellow.
				The value of -1 is nothing(not set)
				"
			::= { sleV2QoS4PolicerControl 19 }

		
		-- 1.3.6.1.4.1.6296.102.10.2.4.1.2.20
		sleV2QoS4PolicerControlColorGreenAction OBJECT-TYPE
			SYNTAX IntColorAction
			MAX-ACCESS read-write
			STATUS current
			DESCRIPTION
				"The action to be apply when incoming packet is colored in green. (not supported)
				The value of -1 is nothing(not set)
				"
			::= { sleV2QoS4PolicerControl 20 }

		
		-- 1.3.6.1.4.1.6296.102.10.2.4.1.2.21
		sleV2QoS4PolicerControlRemarkLayerMode OBJECT-TYPE
			SYNTAX BITS
				{
				remarkByDSCP(0),
				remarkByQueueOrCoS(1)
				}
			MAX-ACCESS read-write
			STATUS current
			DESCRIPTION
				"The remark mode
				0 : Layer3
				1 : Layer2
				"
			::= { sleV2QoS4PolicerControl 21 }

		
		-- 1.3.6.1.4.1.6296.102.10.2.4.1.2.22
		sleV2QoS4PolicerControlRemarkMode OBJECT-TYPE
			SYNTAX BITS
				{
				remarkQueue(0),
				remarkExtCoS(1)
				}
			MAX-ACCESS read-only
			STATUS current
			DESCRIPTION
				"This value is available when sleV2QoS4PolicerControlRemarkLayerMode bit was checked(one or more)
				0 : remark to Queue
				1 : remark to External CoS
				"
			::= { sleV2QoS4PolicerControl 22 }

		
		-- 1.3.6.1.4.1.6296.102.10.2.4.1.2.23
		sleV2QoS4PolicerControlCounterMode OBJECT-TYPE
			SYNTAX IntCounterMode
			MAX-ACCESS read-write
			STATUS current
			DESCRIPTION
				"The counter mode
				The value of -1 is nothing(not set)
				"
			::= { sleV2QoS4PolicerControl 23 }

		
		-- 1.3.6.1.4.1.6296.102.10.2.4.1.2.24
		sleV2QoS4PolicerControlAvrgCounterMode OBJECT-TYPE
			SYNTAX IntAvrgCounterMode
			MAX-ACCESS read-write
			STATUS current
			DESCRIPTION
				"The average counter mode
				The value of -1 is nothing(not set)
				"
			::= { sleV2QoS4PolicerControl 24 }

		
		-- 1.3.6.1.4.1.6296.102.10.2.4.1.2.25
		sleV2QoS4PolicerControlMinBandwidth OBJECT-TYPE
			SYNTAX Integer32
			MAX-ACCESS read-write
			STATUS current
			DESCRIPTION
				"The minimum bandwidth"
			::= { sleV2QoS4PolicerControl 25 }

		
		-- 1.3.6.1.4.1.6296.102.10.2.4.1.2.26
		sleV2QoS4PolicerControlMaxBandwidth OBJECT-TYPE
			SYNTAX Integer32
			MAX-ACCESS read-write
			STATUS current
			DESCRIPTION
				"The maximum bandwidth"
			::= { sleV2QoS4PolicerControl 26 }

		
		-- 1.3.6.1.4.1.6296.102.10.2.4.1.2.27
		sleV2QoS4PolicerControlColorRedDscp OBJECT-TYPE
			SYNTAX IntDscp
			MAX-ACCESS read-write
			STATUS current
			DESCRIPTION
				"The dscp value to be apply when incoming packet is colored in red"
			::= { sleV2QoS4PolicerControl 27 }

		
		-- 1.3.6.1.4.1.6296.102.10.2.4.1.2.28
		sleV2QoS4PolicerControlColorYellowDscp OBJECT-TYPE
			SYNTAX IntDscp
			MAX-ACCESS read-write
			STATUS current
			DESCRIPTION
				"The dscp value to be apply when incoming packet is colored in yellow"
			::= { sleV2QoS4PolicerControl 28 }

		
		-- 1.3.6.1.4.1.6296.102.10.2.4.1.2.29
		sleV2QoS4PolicerControlColorGreenDscp OBJECT-TYPE
			SYNTAX IntDscp
			MAX-ACCESS read-write
			STATUS current
			DESCRIPTION
				"The dscp value to be apply when incoming packet is colored in green"
			::= { sleV2QoS4PolicerControl 29 }

		
		-- 1.3.6.1.4.1.6296.102.10.2.4.1.2.30
		sleV2QoS4PolicerControlColorRedCosType OBJECT-TYPE
			SYNTAX INTEGER
				{
				none(0),
				mark(1),
				overwrite(2)
				}
			MAX-ACCESS read-write
			STATUS current
			DESCRIPTION
				"The CoS type colored in red."
			::= { sleV2QoS4PolicerControl 30 }

		
		-- 1.3.6.1.4.1.6296.102.10.2.4.1.2.31
		sleV2QoS4PolicerControlColorRedCos OBJECT-TYPE
			SYNTAX IntCoS
			MAX-ACCESS read-write
			STATUS current
			DESCRIPTION
				"The CoS colored in red."
			::= { sleV2QoS4PolicerControl 31 }

		
		-- 1.3.6.1.4.1.6296.102.10.2.4.1.2.32
		sleV2QoS4PolicerControlColorYellowCosType OBJECT-TYPE
			SYNTAX INTEGER
				{
				none(0),
				mark(1),
				overwrite(2)
				}
			MAX-ACCESS read-write
			STATUS current
			DESCRIPTION
				"The CoS type colored in yellow"
			::= { sleV2QoS4PolicerControl 32 }

		
		-- 1.3.6.1.4.1.6296.102.10.2.4.1.2.33
		sleV2QoS4PolicerControlColorYellowCos OBJECT-TYPE
			SYNTAX IntToS
			MAX-ACCESS read-write
			STATUS current
			DESCRIPTION
				"The CoS colored in yellow."
			::= { sleV2QoS4PolicerControl 33 }

		
		-- 1.3.6.1.4.1.6296.102.10.2.4.1.2.34
		sleV2QoS4PolicerControlColorGreenCosType OBJECT-TYPE
			SYNTAX INTEGER
				{
				none(0),
				mark(1),
				overwrite(2)
				}
			MAX-ACCESS read-write
			STATUS current
			DESCRIPTION
				"The CoS type colored in yellow"
			::= { sleV2QoS4PolicerControl 34 }

		
		-- 1.3.6.1.4.1.6296.102.10.2.4.1.2.35
		sleV2QoS4PolicerControlColorGreenCos OBJECT-TYPE
			SYNTAX IntToS
			MAX-ACCESS read-write
			STATUS current
			DESCRIPTION
				"The CoS colored in green."
			::= { sleV2QoS4PolicerControl 35 }

		
		-- 1.3.6.1.4.1.6296.102.10.2.4.1.3
		sleV2QoS4PolicerNotification OBJECT IDENTIFIER ::= { sleV2QoS4PolicerInfo 3 }

		
		-- 1.3.6.1.4.1.6296.102.10.2.4.1.3.1
		slePolicerCreated NOTIFICATION-TYPE
			OBJECTS { sleV2QoS4PolicerControlRequest, sleV2QoS4PolicerControlTimeStamp, sleV2QoS4PolicerControlReqResult, sleV2QoS4PolicerColorGreenDscp, sleV2QoS4PolicerColorYellowDscp, 
				sleV2QoS4PolicerColorRedDscp, sleV2QoS4PolicerMaxBandwidth, sleV2QoS4PolicerMinBandwidth, sleV2QoS4PolicerAvrgCounterMode, sleV2QoS4PolicerName, 
				sleV2QoS4PolicerMeterMode, sleV2QoS4PolicerRateLimit, sleV2QoS4PolicerColorType, sleV2QoS4PolicerColorMode, sleV2QoS4PolicerColorAwareMode, 
				sleV2QoS4PolicerColorCIR, sleV2QoS4PolicerColorCBS, sleV2QoS4PolicerColorPIR, sleV2QoS4PolicerColorPBS, sleV2QoS4PolicerColorEBS, 
				sleV2QoS4PolicerColorRedAction, sleV2QoS4PolicerColorYellowAction, sleV2QoS4PolicerColorGreenAction, sleV2QoS4PolicerRemarkLayerMode, sleV2QoS4PolicerRemarkMode, 
				sleV2QoS4PolicerCounterMode }
			STATUS current
			DESCRIPTION 
				"Description."
			::= { sleV2QoS4PolicerNotification 1 }

		
		-- 1.3.6.1.4.1.6296.102.10.2.4.1.3.2
		slePolicerChanged NOTIFICATION-TYPE
			OBJECTS { sleV2QoS4PolicerControlRequest, sleV2QoS4PolicerControlTimeStamp, sleV2QoS4PolicerControlReqResult, sleV2QoS4PolicerAvrgCounterMode, sleV2QoS4PolicerMeterMode, 
				sleV2QoS4PolicerRateLimit, sleV2QoS4PolicerColorType, sleV2QoS4PolicerColorMode, sleV2QoS4PolicerColorAwareMode, sleV2QoS4PolicerColorCIR, 
				sleV2QoS4PolicerColorCBS, sleV2QoS4PolicerColorPIR, sleV2QoS4PolicerColorPBS, sleV2QoS4PolicerColorEBS, sleV2QoS4PolicerColorRedAction, 
				sleV2QoS4PolicerColorYellowAction, sleV2QoS4PolicerColorGreenAction, sleV2QoS4PolicerRemarkLayerMode, sleV2QoS4PolicerRemarkMode, sleV2QoS4PolicerCounterMode, 
				sleV2QoS4PolicerMinBandwidth, sleV2QoS4PolicerMaxBandwidth, sleV2QoS4PolicerColorRedDscp, sleV2QoS4PolicerColorYellowDscp, sleV2QoS4PolicerColorGreenDscp
				 }
			STATUS current
			DESCRIPTION 
				"Description."
			::= { sleV2QoS4PolicerNotification 2 }

		
		-- 1.3.6.1.4.1.6296.102.10.2.4.1.3.3
		slePolicerDestroyed NOTIFICATION-TYPE
			OBJECTS { sleV2QoS4PolicerControlRequest, sleV2QoS4PolicerControlTimeStamp, sleV2QoS4PolicerControlReqResult, sleV2QoS4PolicerControlIndex }
			STATUS current
			DESCRIPTION 
				"Description."
			::= { sleV2QoS4PolicerNotification 3 }

		
		-- 1.3.6.1.4.1.6296.102.10.2.4.2
		sleV2QoS4PolicerMatchCounter OBJECT IDENTIFIER ::= { sleV2QoS4Policer 2 }

		
		-- 1.3.6.1.4.1.6296.102.10.2.4.2.1
		sleV2QoS4PolicerMatchCounterTable OBJECT-TYPE
			SYNTAX SEQUENCE OF SleV2QoS4PolicerMatchCounterEntry
			MAX-ACCESS not-accessible
			STATUS current
			DESCRIPTION
				"policer match counter table."
			::= { sleV2QoS4PolicerMatchCounter 1 }

		
		-- 1.3.6.1.4.1.6296.102.10.2.4.2.1.1
		sleV2QoS4PolicerMatchCounterEntry OBJECT-TYPE
			SYNTAX SleV2QoS4PolicerMatchCounterEntry
			MAX-ACCESS not-accessible
			STATUS current
			DESCRIPTION
				"key: sleV2QoS4PolicerMatchCounterName"
			INDEX { sleV2QoS4PolicerMatchCounterName }
			::= { sleV2QoS4PolicerMatchCounterTable 1 }

		
		SleV2QoS4PolicerMatchCounterEntry ::=
			SEQUENCE { 
				sleV2QoS4PolicerMatchCounterName
					OCTET STRING,
				sleV2QoS4PolicerMatchCounterDesc
					OCTET STRING,
				sleV2QoS4PolicerMatchCounterValue
					Counter64
			 }

		-- 1.3.6.1.4.1.6296.102.10.2.4.2.1.1.1
		sleV2QoS4PolicerMatchCounterName OBJECT-TYPE
			SYNTAX OCTET STRING (SIZE (1..63))
			MAX-ACCESS read-only
			STATUS current
			DESCRIPTION
				"The rule-counter policer name"
			::= { sleV2QoS4PolicerMatchCounterEntry 1 }

		
		-- 1.3.6.1.4.1.6296.102.10.2.4.2.1.1.2
		sleV2QoS4PolicerMatchCounterDesc OBJECT-TYPE
			SYNTAX OCTET STRING (SIZE (1..63))
			MAX-ACCESS read-only
			STATUS current
			DESCRIPTION
				"The rule-counter policer description.
				"
			::= { sleV2QoS4PolicerMatchCounterEntry 2 }

		
		-- 1.3.6.1.4.1.6296.102.10.2.4.2.1.1.3
		sleV2QoS4PolicerMatchCounterValue OBJECT-TYPE
			SYNTAX Counter64
			MAX-ACCESS read-only
			STATUS current
			DESCRIPTION
				"The  counter-value of matched policer.
				"
			::= { sleV2QoS4PolicerMatchCounterEntry 3 }

		
		-- 1.3.6.1.4.1.6296.102.10.2.5
		sleV2QoS4Policy OBJECT IDENTIFIER ::= { sleV2QoS4 5 }

		
		-- 1.3.6.1.4.1.6296.102.10.2.5.1
		sleV2QoS4PolicyInfo OBJECT IDENTIFIER ::= { sleV2QoS4Policy 1 }

		
		-- 1.3.6.1.4.1.6296.102.10.2.5.1.1
		sleV2QoS4PolicyTable OBJECT-TYPE
			SYNTAX SEQUENCE OF SleV2QoS4PolicyEntry
			MAX-ACCESS not-accessible
			STATUS current
			DESCRIPTION
				"policy table."
			::= { sleV2QoS4PolicyInfo 1 }

		
		-- 1.3.6.1.4.1.6296.102.10.2.6.1.1.1
		sleV2QoS4PolicyEntry OBJECT-TYPE
			SYNTAX SleV2QoS4PolicyEntry
			MAX-ACCESS not-accessible
			STATUS current
			DESCRIPTION
				"key: sleV2QoS4PolicyIndex"
			INDEX { sleV2QoS4PolicyIndex }
			::= { sleV2QoS4PolicyTable 1 }

		
		SleV2QoS4PolicyEntry ::=
			SEQUENCE { 
				sleV2QoS4PolicyIndex
					IntPolicyIndex,
				sleV2QoS4PolicyName
					OctetName,
				sleV2QoS4PolicyFlowCnt
					Integer32,
				sleV2QoS4PolicyClassCnt
					Integer32,
				sleV2QoS4PolicyPolicerIndex
					INTEGER,
				sleV2QoS4PolicyPriority
					IntRulePriority,
				sleV2QoS4PolicyIngressPorts
					OCTET STRING,
				sleV2QoS4PolicyEgressPorts
					OCTET STRING,
				sleV2QoS4PolicyVlan
					IntVlanID,
				sleV2QoS4PolicyMatchFlag
					BITS,
				sleV2QoS4PolicyMatchVlan
					IntVlanID,
				sleV2QoS4PolicyMatchRedirectVlan
					IntVlanID,
				sleV2QoS4PolicyMatchRedirectPort
					IntInterfaceIndex,
				sleV2QoS4PolicyMatchMarkMode
					IntMarkMode,
				sleV2QoS4PolicyMatchQueue
					IntQueue,
				sleV2QoS4PolicyMatchDp
					IntDP,
				sleV2QoS4PolicyMatchCoS
					IntCoS,
				sleV2QoS4PolicyMatchDscp
					IntDscp,
				sleV2QoS4PolicyMatchIpPrecedence
					IntIpPrecedence,
				sleV2QoS4PolicyMatchDstMacOrEgressPorts
					IntDstMacOrEgressPorts,
				sleV2QoS4PolicyMatchDstMac
					MacAddress,
				sleV2QoS4PolicyMatchEgressPorts
					OCTET STRING,
				sleV2QoS4PolicyNomatchFlag
					BITS,
				sleV2QoS4PolicyNomatchRedirectPort
					IntInterfaceIndex,
				sleV2QoS4PolicyNomatchCoS
					IntCoS,
				sleV2QoS4PolicyNomatchDscp
					IntDscp,
				sleV2QoS4PolicyNomatchIpPrecedence
					IntIpPrecedence,
				sleV2QoS4PolicyCounterValue
					Counter64,
				sleV2QoS4PolicyCounterGreenBytes
					Counter64,
				sleV2QoS4PolicyCounterYellowBytes
					Counter64,
				sleV2QoS4PolicyCounterRedBytes
					Counter64,
				sleV2QoS4PolicyRedirBlackhole
					IntEnableFlag,
				sleV2QoS4PolicyAvrg5SecCounterValue
					Counter64,
				sleV2QoS4PolicyAvrg1minCounterValue
					Counter64,
				sleV2QoS4PolicyAvrg10minCounterValue
					Counter64,
				sleV2QoS4PolicyIngressTunnelIfIndex
					Integer32,
				sleV2QoS4PolicyEgressTunnelIfIndex
					Integer32,
				sleV2QoS4PolicyCounterElapsedTimeAfterClear
					TimeTicks,
				sleV2QoS4PolicyMatchPbrNextHop
					IpAddress,
				sleV2QoS4PolicyStage
					INTEGER,
				sleV2QoS4PolicyIngressPortsFlag
					INTEGER,
				sleV2QoS4PolicyEgressPortsFlag
					INTEGER,
				sleV2QoS4PolicyInnerVlanAction
					INTEGER,
				sleV2QoS4PolicyOuterVlanAction
					INTEGER,
				sleV2QoS4PolicyInnerVlan
					INTEGER,
				sleV2QoS4PolicyOuterVlan
					INTEGER,
				sleV2QoS4PolicyMatchPbrNextHopSecondary
					IpAddress,
				sleV2QoS4PolicyMatchPbrNextHopVerifyReach
					INTEGER,
				sleV2QoS4PolicyMatchFlowAlias
					OCTET STRING,
				sleV2QoS4PolicyMatchInnerVlanCosReplace
					Integer32,
				sleV2QoS4PolicyMatchInnerVlanCfiReplace
					Integer32,
				sleV2QoS4PolicyMatchOuterVlanCosReplace
					Integer32,
				sleV2QoS4PolicyMatchOuterVlanCfiReplace
					Integer32
			 }

		-- 1.3.6.1.4.1.6296.102.10.2.6.1.1.1.1
		sleV2QoS4PolicyIndex OBJECT-TYPE
			SYNTAX IntPolicyIndex
			MAX-ACCESS read-only
			STATUS current
			DESCRIPTION
				"The index of policy"
			::= { sleV2QoS4PolicyEntry 1 }

		
		-- 1.3.6.1.4.1.6296.102.10.2.6.1.1.1.2
		sleV2QoS4PolicyName OBJECT-TYPE
			SYNTAX OctetName
			MAX-ACCESS read-only
			STATUS current
			DESCRIPTION
				"The name of policy"
			::= { sleV2QoS4PolicyEntry 2 }

		
		-- 1.3.6.1.4.1.6296.102.10.2.6.1.1.1.3
		sleV2QoS4PolicyFlowCnt OBJECT-TYPE
			SYNTAX Integer32
			MAX-ACCESS read-only
			STATUS current
			DESCRIPTION
				"The counter of flow that was included to policy"
			::= { sleV2QoS4PolicyEntry 3 }

		
		-- 1.3.6.1.4.1.6296.102.10.2.6.1.1.1.4
		sleV2QoS4PolicyClassCnt OBJECT-TYPE
			SYNTAX Integer32
			MAX-ACCESS read-only
			STATUS current
			DESCRIPTION
				"The counter of class that was included to policy"
			::= { sleV2QoS4PolicyEntry 4 }

		
		-- 1.3.6.1.4.1.6296.102.10.2.6.1.1.1.5
		sleV2QoS4PolicyPolicerIndex OBJECT-TYPE
			SYNTAX INTEGER (0 | 1..1024)
			MAX-ACCESS read-only
			STATUS current
			DESCRIPTION
				"The index of policer
				0: no policer
				"
			::= { sleV2QoS4PolicyEntry 5 }

		
		-- 1.3.6.1.4.1.6296.102.10.2.6.1.1.1.6
		sleV2QoS4PolicyPriority OBJECT-TYPE
			SYNTAX IntRulePriority
			MAX-ACCESS read-only
			STATUS current
			DESCRIPTION
				"The priority of the policy
				
				low : default value
				"
			::= { sleV2QoS4PolicyEntry 6 }

		
		-- 1.3.6.1.4.1.6296.102.10.2.6.1.1.1.7
		sleV2QoS4PolicyIngressPorts OBJECT-TYPE
			SYNTAX OCTET STRING
			MAX-ACCESS read-only
			STATUS current
			DESCRIPTION
				"The ingress port map"
			::= { sleV2QoS4PolicyEntry 7 }

		
		-- 1.3.6.1.4.1.6296.102.10.2.6.1.1.1.8
		sleV2QoS4PolicyEgressPorts OBJECT-TYPE
			SYNTAX OCTET STRING
			MAX-ACCESS read-only
			STATUS current
			DESCRIPTION
				"The egress port map"
			::= { sleV2QoS4PolicyEntry 8 }

		
		-- 1.3.6.1.4.1.6296.102.10.2.6.1.1.1.9
		sleV2QoS4PolicyVlan OBJECT-TYPE
			SYNTAX IntVlanID
			MAX-ACCESS read-only
			STATUS current
			DESCRIPTION
				"The index of vlan 
				The value of -1 is nothing(not set)
				"
			::= { sleV2QoS4PolicyEntry 9 }

		
		-- 1.3.6.1.4.1.6296.102.10.2.6.1.1.1.10
		sleV2QoS4PolicyMatchFlag OBJECT-TYPE
			SYNTAX BITS
				{
				deny(0),
				mirror(1),
				copyToCPU(2),
				sameAsTos(3),
				sameAsCos(4),
				cos(5),
				tos(6),
				permit(7)
				}
			MAX-ACCESS read-write
			STATUS current
			DESCRIPTION
				"The action to be apply for matched packets.
				bit 0: deny the matched packets
				bit 1: mirror the matched packets
				bit 2: copy to CPU
				bit 3: set 802.1p value to ToS precedence 
				bit 4: set ToS precedence to 802.1p value
				bit 5 : set 802.1p value from flow
				bit 6 : set TaoS precedence from flow
				bit 7 : permit the matched packets
				bit 8 : set inner VLAN value
				bit 9 : set outer VLAN value"
			::= { sleV2QoS4PolicyEntry 10 }

		
		-- 1.3.6.1.4.1.6296.102.10.2.6.1.1.1.11
		sleV2QoS4PolicyMatchVlan OBJECT-TYPE
			SYNTAX IntVlanID
			MAX-ACCESS read-only
			STATUS current
			DESCRIPTION
				"The vlan id to be assigned for the matched packets
				The value of -1 is nothing(not set)
				"
			::= { sleV2QoS4PolicyEntry 11 }

		
		-- 1.3.6.1.4.1.6296.102.10.2.6.1.1.1.12
		sleV2QoS4PolicyMatchRedirectVlan OBJECT-TYPE
			SYNTAX IntVlanID
			MAX-ACCESS read-only
			STATUS current
			DESCRIPTION
				"If the value of sleV2QoS4PolicyMatchRedirectVlan is set
				the value of sleV2QoS4PolicyMatchRedirectPort must be set."
			::= { sleV2QoS4PolicyEntry 12 }

		
		-- 1.3.6.1.4.1.6296.102.10.2.6.1.1.1.13
		sleV2QoS4PolicyMatchRedirectPort OBJECT-TYPE
			SYNTAX IntInterfaceIndex
			MAX-ACCESS read-only
			STATUS current
			DESCRIPTION
				"If the value of sleV2QoS4PolicyMatchRedirectPort is set
				the value of sleV2QoS4PolicyMatchRedirectVlan must be set."
			::= { sleV2QoS4PolicyEntry 13 }

		
		-- 1.3.6.1.4.1.6296.102.10.2.6.1.1.1.14
		sleV2QoS4PolicyMatchMarkMode OBJECT-TYPE
			SYNTAX IntMarkMode
			MAX-ACCESS read-only
			STATUS current
			DESCRIPTION
				"The match mark mode
				The value of -1 is nothing(not set)
				"
			::= { sleV2QoS4PolicyEntry 14 }

		
		-- 1.3.6.1.4.1.6296.102.10.2.6.1.1.1.15
		sleV2QoS4PolicyMatchQueue OBJECT-TYPE
			SYNTAX IntQueue
			MAX-ACCESS read-only
			STATUS current
			DESCRIPTION
				"The queue value to be apply for the matched packets
				The value of -1 is nothing(not set)
				"
			::= { sleV2QoS4PolicyEntry 15 }

		
		-- 1.3.6.1.4.1.6296.102.10.2.6.1.1.1.16
		sleV2QoS4PolicyMatchDp OBJECT-TYPE
			SYNTAX IntDP
			MAX-ACCESS read-only
			STATUS current
			DESCRIPTION
				"The drop precedence
				The value of -1 is nothing(not set)
				"
			::= { sleV2QoS4PolicyEntry 16 }

		
		-- 1.3.6.1.4.1.6296.102.10.2.6.1.1.1.17
		sleV2QoS4PolicyMatchCoS OBJECT-TYPE
			SYNTAX IntCoS
			MAX-ACCESS read-only
			STATUS current
			DESCRIPTION
				"The Class of Service
				The value of -1 is nothing(not set)
				"
			::= { sleV2QoS4PolicyEntry 17 }

		
		-- 1.3.6.1.4.1.6296.102.10.2.6.1.1.1.18
		sleV2QoS4PolicyMatchDscp OBJECT-TYPE
			SYNTAX IntDscp
			MAX-ACCESS read-only
			STATUS current
			DESCRIPTION
				"The DSCP
				The value of -1 is nothing(not set)
				"
			::= { sleV2QoS4PolicyEntry 18 }

		
		-- 1.3.6.1.4.1.6296.102.10.2.6.1.1.1.19
		sleV2QoS4PolicyMatchIpPrecedence OBJECT-TYPE
			SYNTAX IntIpPrecedence
			MAX-ACCESS read-only
			STATUS current
			DESCRIPTION
				"The IP precedence
				The value of -1 is nothing(not set)
				"
			::= { sleV2QoS4PolicyEntry 19 }

		
		-- 1.3.6.1.4.1.6296.102.10.2.6.1.1.1.20
		sleV2QoS4PolicyMatchDstMacOrEgressPorts OBJECT-TYPE
			SYNTAX IntDstMacOrEgressPorts
			MAX-ACCESS read-only
			STATUS current
			DESCRIPTION
				"If the value is nothing, sleV2QoS4PolicyMatchDstMac and sleV2QoS4PolicyMatchEgressPorts value is not available
				If the value is dstMac, the value of sleV2QoS4PolicyMatchDstMac is available
				If the value is egressPorts, the value of sleV2QoS4PolicyMatchEgressPorts is avalible
				"
			::= { sleV2QoS4PolicyEntry 20 }

		
		-- 1.3.6.1.4.1.6296.102.10.2.6.1.1.1.21
		sleV2QoS4PolicyMatchDstMac OBJECT-TYPE
			SYNTAX MacAddress
			MAX-ACCESS read-only
			STATUS current
			DESCRIPTION
				"Destination MAC Address of the matched packets
				The value of 00:00:00:00:00:00 is nothing(not set)
				"
			::= { sleV2QoS4PolicyEntry 21 }

		
		-- 1.3.6.1.4.1.6296.102.10.2.6.1.1.1.22
		sleV2QoS4PolicyMatchEgressPorts OBJECT-TYPE
			SYNTAX OCTET STRING
			MAX-ACCESS read-only
			STATUS current
			DESCRIPTION
				"The egress port map of the matched packets"
			::= { sleV2QoS4PolicyEntry 22 }

		
		-- 1.3.6.1.4.1.6296.102.10.2.6.1.1.1.23
		sleV2QoS4PolicyNomatchFlag OBJECT-TYPE
			SYNTAX BITS
				{
				deny(0),
				mirror(1),
				copyToCPU(2),
				sameAsTos(3),
				sameAsCos(4),
				cos(5),
				tos(6),
				permit(7)
				}
			MAX-ACCESS read-only
			STATUS current
			DESCRIPTION
				"The action to be apply for matched packets.
				bit 0: deny the nomatched packets
				bit 1: mirror the nomatched packets
				bit 2: copy to CPU
				bit 3: set 802.1p value to ToS precedence 
				bit 4: set ToS precedence to 802.1p value
				bit 5 : set 802.1p value from flow
				bit 6 : set TaoS precedence from flow
				"
			::= { sleV2QoS4PolicyEntry 23 }

		
		-- 1.3.6.1.4.1.6296.102.10.2.6.1.1.1.24
		sleV2QoS4PolicyNomatchRedirectPort OBJECT-TYPE
			SYNTAX IntInterfaceIndex
			MAX-ACCESS read-only
			STATUS current
			DESCRIPTION
				"The port to redirect to a nomatched packet.
				The value of -1 is nothing(not set)
				
				"
			::= { sleV2QoS4PolicyEntry 24 }

		
		-- 1.3.6.1.4.1.6296.102.10.2.6.1.1.1.25
		sleV2QoS4PolicyNomatchCoS OBJECT-TYPE
			SYNTAX IntCoS
			MAX-ACCESS read-only
			STATUS current
			DESCRIPTION
				"The Class of Service
				The value of -1 is nothing(not set)
				
				"
			::= { sleV2QoS4PolicyEntry 25 }

		
		-- 1.3.6.1.4.1.6296.102.10.2.6.1.1.1.26
		sleV2QoS4PolicyNomatchDscp OBJECT-TYPE
			SYNTAX IntDscp
			MAX-ACCESS read-only
			STATUS current
			DESCRIPTION
				"The DSCP
				The value of -1 is nothing(not set)
				"
			::= { sleV2QoS4PolicyEntry 26 }

		
		-- 1.3.6.1.4.1.6296.102.10.2.6.1.1.1.27
		sleV2QoS4PolicyNomatchIpPrecedence OBJECT-TYPE
			SYNTAX IntIpPrecedence
			MAX-ACCESS read-write
			STATUS current
			DESCRIPTION
				"The IP precedence
				The value of -1 is nothing(not set)
				"
			::= { sleV2QoS4PolicyEntry 27 }

		
		-- 1.3.6.1.4.1.6296.102.10.2.6.1.1.1.28
		sleV2QoS4PolicyCounterValue OBJECT-TYPE
			SYNTAX Counter64
			MAX-ACCESS read-only
			STATUS current
			DESCRIPTION
				"The value of the counter
				Packet count or bytes according to policer's counter mode.
				The value of 0 is no matched count.
				"
			::= { sleV2QoS4PolicyEntry 28 }

		
		-- 1.3.6.1.4.1.6296.102.10.2.6.1.1.1.29
		sleV2QoS4PolicyCounterGreenBytes OBJECT-TYPE
			SYNTAX Counter64
			MAX-ACCESS read-only
			STATUS current
			DESCRIPTION
				"The value of the octet counter for green-marked packets.
				Available only when sleV2QoS4PolicerMeterMode's value is color.
				The value of 0 is no matched count.
				"
			::= { sleV2QoS4PolicyEntry 29 }

		
		-- 1.3.6.1.4.1.6296.102.10.2.6.1.1.1.30
		sleV2QoS4PolicyCounterYellowBytes OBJECT-TYPE
			SYNTAX Counter64
			MAX-ACCESS read-only
			STATUS current
			DESCRIPTION
				"The value of the octet counter for yellow-marked packets.
				Available only when sleV2QoS4PolicerMeterMode's value is color.
				The value of 0 is no matched count.
				"
			::= { sleV2QoS4PolicyEntry 30 }

		
		-- 1.3.6.1.4.1.6296.102.10.2.6.1.1.1.31
		sleV2QoS4PolicyCounterRedBytes OBJECT-TYPE
			SYNTAX Counter64
			MAX-ACCESS read-only
			STATUS current
			DESCRIPTION
				"The value of the octet counter for red-marked packets.
				Available only when sleV2QoS4PolicerMeterMode's value is color.
				The value of 0 is no matched count.
				"
			::= { sleV2QoS4PolicyEntry 31 }

		
		-- 1.3.6.1.4.1.6296.102.10.2.6.1.1.1.32
		sleV2QoS4PolicyRedirBlackhole OBJECT-TYPE
			SYNTAX IntEnableFlag
			MAX-ACCESS read-only
			STATUS current
			DESCRIPTION
				"The packet discard"
			::= { sleV2QoS4PolicyEntry 32 }

		
		-- 1.3.6.1.4.1.6296.102.10.2.6.1.1.1.33
		sleV2QoS4PolicyAvrg5SecCounterValue OBJECT-TYPE
			SYNTAX Counter64
			MAX-ACCESS read-only
			STATUS current
			DESCRIPTION
				"The value of the average counter of 5 second.
				The bytes according to policer¡¯s average counter mode.
				The value of 0 is no matched count.
				"
			::= { sleV2QoS4PolicyEntry 33 }

		
		-- 1.3.6.1.4.1.6296.102.10.2.6.1.1.1.34
		sleV2QoS4PolicyAvrg1minCounterValue OBJECT-TYPE
			SYNTAX Counter64
			MAX-ACCESS read-only
			STATUS current
			DESCRIPTION
				"The value of the average counter of 1 minute.
				The bytes according to policer¡¯s average counter mode.
				The value of 0 is no matched count.
				"
			::= { sleV2QoS4PolicyEntry 34 }

		
		-- 1.3.6.1.4.1.6296.102.10.2.6.1.1.1.35
		sleV2QoS4PolicyAvrg10minCounterValue OBJECT-TYPE
			SYNTAX Counter64
			MAX-ACCESS read-only
			STATUS current
			DESCRIPTION
				"The value of the average counter of 10 minute.
				The bytes according to policer¡¯s average counter mode.
				The value of 0 is no matched count.
				"
			::= { sleV2QoS4PolicyEntry 35 }

		
		-- 1.3.6.1.4.1.6296.102.10.2.6.1.1.1.36
		sleV2QoS4PolicyIngressTunnelIfIndex OBJECT-TYPE
			SYNTAX Integer32 (10000..11023)
			MAX-ACCESS read-only
			STATUS current
			DESCRIPTION
				"Ingress tunnel interface index."
			::= { sleV2QoS4PolicyEntry 36 }

		
		-- 1.3.6.1.4.1.6296.102.10.2.6.1.1.1.37
		sleV2QoS4PolicyEgressTunnelIfIndex OBJECT-TYPE
			SYNTAX Integer32 (10000..11023)
			MAX-ACCESS read-only
			STATUS current
			DESCRIPTION
				"Egress tunnel interface index."
			::= { sleV2QoS4PolicyEntry 37 }

		
		-- 1.3.6.1.4.1.6296.102.10.2.6.1.1.1.38
		sleV2QoS4PolicyCounterElapsedTimeAfterClear OBJECT-TYPE
			SYNTAX TimeTicks
			MAX-ACCESS read-only
			STATUS current
			DESCRIPTION
				"The elapsed time after clearing counter."
			::= { sleV2QoS4PolicyEntry 38 }

		
		-- 1.3.6.1.4.1.6296.102.10.2.6.1.1.1.39
		sleV2QoS4PolicyMatchPbrNextHop OBJECT-TYPE
			SYNTAX IpAddress
			MAX-ACCESS read-only
			STATUS current
			DESCRIPTION
				"The PBR(Policy-Based_routing) nexthop address."
			::= { sleV2QoS4PolicyEntry 39 }

		
		-- 1.3.6.1.4.1.6296.102.10.2.6.1.1.1.40
		sleV2QoS4PolicyStage OBJECT-TYPE
			SYNTAX INTEGER
				{
				ingress(1),
				prio(2),
				egress(3),
				external(4)
				}
			MAX-ACCESS read-only
			STATUS current
			DESCRIPTION
				"The rule-policy-stage."
			::= { sleV2QoS4PolicyEntry 40 }

		
		-- 1.3.6.1.4.1.6296.102.10.2.6.1.1.1.41
		sleV2QoS4PolicyIngressPortsFlag OBJECT-TYPE
			SYNTAX INTEGER
				{
				none(0),
				any(1),
				cpu(2)
				}
			MAX-ACCESS read-only
			STATUS current
			DESCRIPTION
				"The interface-binding ingress-port flag of policy."
			::= { sleV2QoS4PolicyEntry 41 }

		
		-- 1.3.6.1.4.1.6296.102.10.2.6.1.1.1.42
		sleV2QoS4PolicyEgressPortsFlag OBJECT-TYPE
			SYNTAX INTEGER
				{
				none(0),
				any(1),
				cpu(2)
				}
			MAX-ACCESS read-only
			STATUS current
			DESCRIPTION
				"The interface-binding egress-port flag of policy."
			::= { sleV2QoS4PolicyEntry 42 }

		
		-- 1.3.6.1.4.1.6296.102.10.2.6.1.1.1.43
		sleV2QoS4PolicyInnerVlanAction OBJECT-TYPE
			SYNTAX INTEGER
				{
				nothing(-1),
				add(1),
				replace(2),
				del(3)
				}
			MAX-ACCESS read-only
			STATUS current
			DESCRIPTION
				"The InnerVlan Action Mode
				The Value of -1 is nothing(not set)"
			::= { sleV2QoS4PolicyEntry 43 }

		
		-- 1.3.6.1.4.1.6296.102.10.2.6.1.1.1.44
		sleV2QoS4PolicyOuterVlanAction OBJECT-TYPE
			SYNTAX INTEGER
				{
				nothing(-1),
				add(1),
				replace(2)
				}
			MAX-ACCESS read-only
			STATUS current
			DESCRIPTION
				"The OuterVlan Action Mode
				The Value of -1 is nothing(not set)"
			::= { sleV2QoS4PolicyEntry 44 }

		
		-- 1.3.6.1.4.1.6296.102.10.2.6.1.1.1.45
		sleV2QoS4PolicyInnerVlan OBJECT-TYPE
			SYNTAX INTEGER (-1 | 1..4094)
			MAX-ACCESS read-only
			STATUS current
			DESCRIPTION
				"The inner vlan id to be assigned for the matched packets
				The value of -1 is nothing(not set)
				"
			::= { sleV2QoS4PolicyEntry 45 }

		
		-- 1.3.6.1.4.1.6296.102.10.2.6.1.1.1.46
		sleV2QoS4PolicyOuterVlan OBJECT-TYPE
			SYNTAX INTEGER (-1 | 1..4094)
			MAX-ACCESS read-only
			STATUS current
			DESCRIPTION
				"The outer vlan id to be assigned for the matched packets
				The value of -1 is nothing(not set)"
			::= { sleV2QoS4PolicyEntry 46 }

		
		-- 1.3.6.1.4.1.6296.102.10.2.6.1.1.1.47
		sleV2QoS4PolicyMatchPbrNextHopSecondary OBJECT-TYPE
			SYNTAX IpAddress
			MAX-ACCESS read-only
			STATUS current
			DESCRIPTION
				"The PBR(Policy-Based_routing) nexthop secondary address."
			::= { sleV2QoS4PolicyEntry 47 }

		
		-- 1.3.6.1.4.1.6296.102.10.2.6.1.1.1.48
		sleV2QoS4PolicyMatchPbrNextHopVerifyReach OBJECT-TYPE
			SYNTAX INTEGER
				{
				false(0),
				true(1)
				}
			MAX-ACCESS read-only
			STATUS current
			DESCRIPTION
				"The PBR(Policy-Based_routing) Verify-Reachability."
			::= { sleV2QoS4PolicyEntry 48 }

		
		-- 1.3.6.1.4.1.6296.102.10.2.6.1.1.1.49
		sleV2QoS4PolicyMatchFlowAlias OBJECT-TYPE
			SYNTAX OCTET STRING
			MAX-ACCESS read-only
			STATUS current
			DESCRIPTION
				"The action match flowAlias"
			::= { sleV2QoS4PolicyEntry 49 }

		
		-- 1.3.6.1.4.1.6296.102.10.2.6.1.1.1.50
		sleV2QoS4PolicyMatchInnerVlanCosReplace OBJECT-TYPE
			SYNTAX Integer32 (-1 | 0..7)
			MAX-ACCESS read-only
			STATUS current
			DESCRIPTION
				"The inner vlan COS replace (-1: delete)"
			::= { sleV2QoS4PolicyEntry 50 }

		
		-- 1.3.6.1.4.1.6296.102.10.2.6.1.1.1.51
		sleV2QoS4PolicyMatchInnerVlanCfiReplace OBJECT-TYPE
			SYNTAX Integer32 (-1 | 0..1)
			MAX-ACCESS read-only
			STATUS current
			DESCRIPTION
				"The inner vlan CFI replace (-1: delete)"
			::= { sleV2QoS4PolicyEntry 51 }

		
		-- 1.3.6.1.4.1.6296.102.10.2.6.1.1.1.52
		sleV2QoS4PolicyMatchOuterVlanCosReplace OBJECT-TYPE
			SYNTAX Integer32 (-1 | 0..7)
			MAX-ACCESS read-only
			STATUS current
			DESCRIPTION
				"The outer vlan COS replace (-1: delete)"
			::= { sleV2QoS4PolicyEntry 52 }

		
		-- 1.3.6.1.4.1.6296.102.10.2.6.1.1.1.53
		sleV2QoS4PolicyMatchOuterVlanCfiReplace OBJECT-TYPE
			SYNTAX Integer32 (-1 | 0..1)
			MAX-ACCESS read-only
			STATUS current
			DESCRIPTION
				"The outer vlan CFI replace (-1: delete)"
			::= { sleV2QoS4PolicyEntry 53 }

		
		-- 1.3.6.1.4.1.6296.102.10.2.5.1.2
		sleV2QoS4PolicyControl OBJECT IDENTIFIER ::= { sleV2QoS4PolicyInfo 2 }

		
		-- 1.3.6.1.4.1.6296.102.10.2.5.1.2.1
		sleV2QoS4PolicyControlRequest OBJECT-TYPE
			SYNTAX INTEGER
				{
				createPolicy(1),
				setPolicyInfo(2),
				setMatchAction(3),
				setNomatchAction(4),
				destroyPolicy(5),
				clearCounter(6),
				createEmptyPolicy(7),
				setPolicyIngressTunnel(8),
				unsetPolicyIngressTunnel(9),
				setPolicyEgressTunnel(10),
				unsetPolicyEgressTunnel(11),
				setMatchActionFlowAlias(12),
				setMatchInnerVlanCosReplace(13),
				setMatchInnerVlanCfiReplace(14),
				setMatchOuterVlanCosReplace(15),
				setMatchOuterVlanCfiReplace(16)
				}
			MAX-ACCESS read-write
			STATUS current
			DESCRIPTION
				"The request of a user command"
			::= { sleV2QoS4PolicyControl 1 }

		
		-- 1.3.6.1.4.1.6296.102.10.2.5.1.2.2
		sleV2QoS4PolicyControlStatus OBJECT-TYPE
			SYNTAX SleControlStatusType
			MAX-ACCESS read-only
			STATUS current
			DESCRIPTION
				"The status of user command"
			::= { sleV2QoS4PolicyControl 2 }

		
		-- 1.3.6.1.4.1.6296.102.10.2.5.1.2.3
		sleV2QoS4PolicyControlTimer OBJECT-TYPE
			SYNTAX Gauge32
			MAX-ACCESS read-write
			STATUS current
			DESCRIPTION
				"The maximum time for the manager for a long running user command"
			::= { sleV2QoS4PolicyControl 3 }

		
		-- 1.3.6.1.4.1.6296.102.10.2.5.1.2.4
		sleV2QoS4PolicyControlTimeStamp OBJECT-TYPE
			SYNTAX TimeTicks
			MAX-ACCESS read-only
			STATUS current
			DESCRIPTION
				"The time stamp of the last command(end of command)"
			::= { sleV2QoS4PolicyControl 4 }

		
		-- 1.3.6.1.4.1.6296.102.10.2.5.1.2.5
		sleV2QoS4PolicyControlReqResult OBJECT-TYPE
			SYNTAX SleControlRequestResultType
			MAX-ACCESS read-only
			STATUS current
			DESCRIPTION
				"The result of the last user command"
			::= { sleV2QoS4PolicyControl 5 }

		
		-- 1.3.6.1.4.1.6296.102.10.2.5.1.2.6
		sleV2QoS4PolicyControlIndex OBJECT-TYPE
			SYNTAX IntPolicyIndex
			MAX-ACCESS read-write
			STATUS current
			DESCRIPTION
				"The index of policy"
			::= { sleV2QoS4PolicyControl 6 }

		
		-- 1.3.6.1.4.1.6296.102.10.2.5.1.2.7
		sleV2QoS4PolicyControlName OBJECT-TYPE
			SYNTAX OctetName
			MAX-ACCESS read-write
			STATUS current
			DESCRIPTION
				"The name of policy"
			::= { sleV2QoS4PolicyControl 7 }

		
		-- 1.3.6.1.4.1.6296.102.10.2.5.1.2.8
		sleV2QoS4PolicyControlPolicerIndex OBJECT-TYPE
			SYNTAX INTEGER (0 | 1..1024)
			MAX-ACCESS read-write
			STATUS current
			DESCRIPTION
				"The index of policer
				0: no policer
				"
			::= { sleV2QoS4PolicyControl 8 }

		
		-- 1.3.6.1.4.1.6296.102.10.2.5.1.2.9
		sleV2QoS4PolicyControlPriority OBJECT-TYPE
			SYNTAX IntRulePriority
			MAX-ACCESS read-write
			STATUS current
			DESCRIPTION
				"The priority of the policy
				
				low : default
				"
			::= { sleV2QoS4PolicyControl 9 }

		
		-- 1.3.6.1.4.1.6296.102.10.2.5.1.2.10
		sleV2QoS4PolicyControlIngressPorts OBJECT-TYPE
			SYNTAX OCTET STRING
			MAX-ACCESS read-write
			STATUS current
			DESCRIPTION
				"The ingress port map"
			::= { sleV2QoS4PolicyControl 10 }

		
		-- 1.3.6.1.4.1.6296.102.10.2.5.1.2.11
		sleV2QoS4PolicyControlEgressPorts OBJECT-TYPE
			SYNTAX OCTET STRING
			MAX-ACCESS read-write
			STATUS current
			DESCRIPTION
				"The egress port map"
			::= { sleV2QoS4PolicyControl 11 }

		
		-- 1.3.6.1.4.1.6296.102.10.2.5.1.2.12
		sleV2QoS4PolicyControlVlan OBJECT-TYPE
			SYNTAX IntVlanID
			MAX-ACCESS read-write
			STATUS current
			DESCRIPTION
				"The index of vlan 
				The value of -1 is nothing(not set)
				"
			::= { sleV2QoS4PolicyControl 12 }

		
		-- 1.3.6.1.4.1.6296.102.10.2.5.1.2.13
		sleV2QoS4PolicyControlMatchFlag OBJECT-TYPE
			SYNTAX BITS
				{
				deny(0),
				mirror(1),
				copyToCPU(2),
				sameAsTos(3),
				sameAsCos(4),
				cos(5),
				tos(6),
				permit(7)
				}
			MAX-ACCESS read-write
			STATUS current
			DESCRIPTION
				"The action to be apply for matched packets.
				bit 0: deny the matched packets
				bit 1: mirror the matched packets
				bit 2: copy to CPU
				bit 3: set 802.1p value to ToS precedence 
				bit 4: set ToS precedence to 802.1p value
				bit 5 : set 802.1p value from flow
				bit 6 : set TaoS precedence from flow
				bit 7 : permit the matched packets
				bit 8 : set inner VLAN value
				bit 9 : set outer VLAN value
				"
			::= { sleV2QoS4PolicyControl 13 }

		
		-- 1.3.6.1.4.1.6296.102.10.2.5.1.2.14
		sleV2QoS4PolicyControlMatchVlan OBJECT-TYPE
			SYNTAX IntVlanID
			MAX-ACCESS read-write
			STATUS current
			DESCRIPTION
				"The vlan id to be assigned for the matched packets
				The value of -1 is nothing(not set)
				"
			::= { sleV2QoS4PolicyControl 14 }

		
		-- 1.3.6.1.4.1.6296.102.10.2.5.1.2.15
		sleV2QoS4PolicyControlMatchRedirectVlan OBJECT-TYPE
			SYNTAX IntVlanID
			MAX-ACCESS read-write
			STATUS current
			DESCRIPTION
				"The valn id to redirect to a matched packet
				If the value of sleV2QoS4PolicyMatchRedirectVlan is set
				the value of sleV2QoS4PolicyMatchRedirectPort must be set.
				The value of -1 is nothing(not set)
				"
			::= { sleV2QoS4PolicyControl 15 }

		
		-- 1.3.6.1.4.1.6296.102.10.2.5.1.2.16
		sleV2QoS4PolicyControlMatchRedirectPort OBJECT-TYPE
			SYNTAX IntInterfaceIndex
			MAX-ACCESS read-write
			STATUS current
			DESCRIPTION
				"The port to redirect to a matched packet.
				If the value of sleV2QoS4PolicyMatchRedirectPort is set
				the value of sleV2QoS4PolicyMatchRedirectVlan must be set.
				The value of -1 is nothing(not set)
				"
			::= { sleV2QoS4PolicyControl 16 }

		
		-- 1.3.6.1.4.1.6296.102.10.2.5.1.2.17
		sleV2QoS4PolicyControlMatchMarkMode OBJECT-TYPE
			SYNTAX IntMarkMode
			MAX-ACCESS read-write
			STATUS current
			DESCRIPTION
				"The match mark mode
				The value of -1 is nothing(not set)
				"
			::= { sleV2QoS4PolicyControl 17 }

		
		-- 1.3.6.1.4.1.6296.102.10.2.5.1.2.18
		sleV2QoS4PolicyControlMatchQueue OBJECT-TYPE
			SYNTAX IntQueue
			MAX-ACCESS read-write
			STATUS current
			DESCRIPTION
				"The queue value to be apply for the matched packets
				The value of -1 is nothing(not set)
				"
			::= { sleV2QoS4PolicyControl 18 }

		
		-- 1.3.6.1.4.1.6296.102.10.2.5.1.2.19
		sleV2QoS4PolicyControlMatchDp OBJECT-TYPE
			SYNTAX IntDP
			MAX-ACCESS read-write
			STATUS current
			DESCRIPTION
				"The drop precedence
				The value of -1 is nothing(not set)
				"
			::= { sleV2QoS4PolicyControl 19 }

		
		-- 1.3.6.1.4.1.6296.102.10.2.5.1.2.20
		sleV2QoS4PolicyControlMatchCoS OBJECT-TYPE
			SYNTAX Integer32
			MAX-ACCESS read-write
			STATUS current
			DESCRIPTION
				"The Class of Service
				The value of -1 is nothing(not set)
				"
			::= { sleV2QoS4PolicyControl 20 }

		
		-- 1.3.6.1.4.1.6296.102.10.2.5.1.2.21
		sleV2QoS4PolicyControlMatchDscp OBJECT-TYPE
			SYNTAX IntDscp
			MAX-ACCESS read-write
			STATUS current
			DESCRIPTION
				"The DSCP
				The value of -1 is nothing(not set)
				"
			::= { sleV2QoS4PolicyControl 21 }

		
		-- 1.3.6.1.4.1.6296.102.10.2.5.1.2.22
		sleV2QoS4PolicyControlMatchIpPrecedence OBJECT-TYPE
			SYNTAX IntIpPrecedence
			MAX-ACCESS read-write
			STATUS current
			DESCRIPTION
				"The IP precedence
				The value of -1 is nothing(not set)
				"
			::= { sleV2QoS4PolicyControl 22 }

		
		-- 1.3.6.1.4.1.6296.102.10.2.5.1.2.23
		sleV2QoS4PolicyControlMatchDstMacOrEgressPorts OBJECT-TYPE
			SYNTAX IntDstMacOrEgressPorts
			MAX-ACCESS read-write
			STATUS current
			DESCRIPTION
				"If the value is nothing, sleV2QoS4PolicyControlMatchDstMac and sleV2QoS4PolicyControlMatchEgressPorts value is not available
				If the value is dstMac, the value of sleV2QoS4PolicyControlMatchDstMac is available
				If the value is egressPorts, the value of sleV2QoS4PolicyControlMatchEgressPorts is avalible
				"
			::= { sleV2QoS4PolicyControl 23 }

		
		-- 1.3.6.1.4.1.6296.102.10.2.5.1.2.24
		sleV2QoS4PolicyControlMatchDstMac OBJECT-TYPE
			SYNTAX MacAddress
			MAX-ACCESS read-write
			STATUS current
			DESCRIPTION
				"Destination MAC Address of the matched packets
				The value of 00:00:00:00:00:00 is nothing(not set)
				"
			::= { sleV2QoS4PolicyControl 24 }

		
		-- 1.3.6.1.4.1.6296.102.10.2.5.1.2.25
		sleV2QoS4PolicyControlMatchEgressPorts OBJECT-TYPE
			SYNTAX OCTET STRING
			MAX-ACCESS read-write
			STATUS current
			DESCRIPTION
				"The egress port map of the matched packets"
			::= { sleV2QoS4PolicyControl 25 }

		
		-- 1.3.6.1.4.1.6296.102.10.2.5.1.2.26
		sleV2QoS4PolicyControlNomatchFlag OBJECT-TYPE
			SYNTAX BITS
				{
				deny(0),
				mirror(1),
				copyToCPU(2),
				sameAsTos(3),
				sameAsCos(4),
				cos(5),
				tos(6),
				permit(7)
				}
			MAX-ACCESS read-write
			STATUS current
			DESCRIPTION
				"The action to be apply for matched packets.
				bit 0: deny the nomatched packets
				bit 1: mirror the nomatched packets
				bit 2: copy to CPU
				bit 3: set 802.1p value to ToS precedence 
				bit 4: set ToS precedence to 802.1p value
				bit 5 : set 802.1p value from flow
				bit 6 : set TaoS precedence from flow
				"
			::= { sleV2QoS4PolicyControl 26 }

		
		-- 1.3.6.1.4.1.6296.102.10.2.5.1.2.27
		sleV2QoS4PolicyControlNomatchRedirectPort OBJECT-TYPE
			SYNTAX IntInterfaceIndex
			MAX-ACCESS read-write
			STATUS current
			DESCRIPTION
				"The port to redirect to a nomatched packet.
				The value of -1 is nothing(not set)
				"
			::= { sleV2QoS4PolicyControl 27 }

		
		-- 1.3.6.1.4.1.6296.102.10.2.5.1.2.28
		sleV2QoS4PolicyControlNomatchCoS OBJECT-TYPE
			SYNTAX IntCoS
			MAX-ACCESS read-write
			STATUS current
			DESCRIPTION
				"The Class of Service
				The value of -1 is nothing(not set)
				"
			::= { sleV2QoS4PolicyControl 28 }

		
		-- 1.3.6.1.4.1.6296.102.10.2.5.1.2.29
		sleV2QoS4PolicyControlNomatchDscp OBJECT-TYPE
			SYNTAX IntDscp
			MAX-ACCESS read-write
			STATUS current
			DESCRIPTION
				"The DSCP
				The value of -1 is nothing(not set)
				"
			::= { sleV2QoS4PolicyControl 29 }

		
		-- 1.3.6.1.4.1.6296.102.10.2.5.1.2.30
		sleV2QoS4PolicyControlNomatchIpPrecedence OBJECT-TYPE
			SYNTAX IntIpPrecedence
			MAX-ACCESS read-write
			STATUS current
			DESCRIPTION
				"The IP precedence
				The value of -1 is nothing(not set)
				"
			::= { sleV2QoS4PolicyControl 30 }

		
		-- 1.3.6.1.4.1.6296.102.10.2.5.1.2.31
		sleV2QoS4PolicyControlMatchRedirBlackhole OBJECT-TYPE
			SYNTAX IntEnableFlag
			MAX-ACCESS read-write
			STATUS current
			DESCRIPTION
				"The packet discard"
			::= { sleV2QoS4PolicyControl 31 }

		
		-- 1.3.6.1.4.1.6296.102.10.2.5.1.2.32
		sleV2QoS4PolicyControlIngressTunnelIfIndex OBJECT-TYPE
			SYNTAX Integer32 (10000..11023)
			MAX-ACCESS read-write
			STATUS current
			DESCRIPTION
				"Ingress tunnel interface index."
			::= { sleV2QoS4PolicyControl 32 }

		
		-- 1.3.6.1.4.1.6296.102.10.2.5.1.2.33
		sleV2Qo4SPolicyControlEgressTunnelIfIndex OBJECT-TYPE
			SYNTAX Integer32 (10000..11023)
			MAX-ACCESS read-write
			STATUS current
			DESCRIPTION
				"Egress tunnel interface index."
			::= { sleV2QoS4PolicyControl 33 }

		
		-- 1.3.6.1.4.1.6296.102.10.2.5.1.2.34
		sleV2QoS4PolicyControlMatchPbrNextHop OBJECT-TYPE
			SYNTAX IpAddress
			MAX-ACCESS read-write
			STATUS current
			DESCRIPTION
				"The PBR(Policy-Based_routing) nexthop address."
			::= { sleV2QoS4PolicyControl 34 }

		
		-- 1.3.6.1.4.1.6296.102.10.2.5.1.2.35
		sleV2QoS4PolicyControlStage OBJECT-TYPE
			SYNTAX INTEGER
				{
				ingress(1),
				prio(2),
				egress(3),
				external(4)
				}
			MAX-ACCESS read-write
			STATUS current
			DESCRIPTION
				"The rule-policy-stage."
			::= { sleV2QoS4PolicyControl 35 }

		
		-- 1.3.6.1.4.1.6296.102.10.2.5.1.2.36
		sleV2QoS4PolicyControlIngressPortsFlag OBJECT-TYPE
			SYNTAX INTEGER
				{
				none(0),
				any(1),
				cpu(2)
				}
			MAX-ACCESS read-write
			STATUS current
			DESCRIPTION
				"The interface-binding ingress-port flag of policy."
			::= { sleV2QoS4PolicyControl 36 }

		
		-- 1.3.6.1.4.1.6296.102.10.2.5.1.2.37
		sleV2QoS4PolicyControlEgressPortsFlag OBJECT-TYPE
			SYNTAX INTEGER
				{
				none(0),
				any(1),
				cpu(2)
				}
			MAX-ACCESS read-write
			STATUS current
			DESCRIPTION
				"The interface-binding egress-port flag of policy."
			::= { sleV2QoS4PolicyControl 37 }

		
		-- 1.3.6.1.4.1.6296.102.10.2.5.1.2.38
		sleV2QoS4PolicyControlInnerVlanAction OBJECT-TYPE
			SYNTAX INTEGER
				{
				nothing(-1),
				add(1),
				replace(2),
				del(3)
				}
			MAX-ACCESS read-write
			STATUS current
			DESCRIPTION
				"The InnerVlan Action Mode
				The Value of -1 is nothing(not set)"
			::= { sleV2QoS4PolicyControl 38 }

		
		-- 1.3.6.1.4.1.6296.102.10.2.5.1.2.39
		sleV2QoS4PolicyControlOuterVlanAction OBJECT-TYPE
			SYNTAX INTEGER
				{
				nothing(-1),
				add(1),
				replace(2)
				}
			MAX-ACCESS read-write
			STATUS current
			DESCRIPTION
				"The OuterVlan Action Mode
				The Value of -1 is nothing(not set)"
			::= { sleV2QoS4PolicyControl 39 }

		
		-- 1.3.6.1.4.1.6296.102.10.2.5.1.2.40
		sleV2QoS4PolicyControlInnerVlan OBJECT-TYPE
			SYNTAX INTEGER (-1 | 1..4094)
			MAX-ACCESS read-write
			STATUS current
			DESCRIPTION
				"The inner vlan id to be assigned for the matched packets
				The value of -1 is nothing(not set)
				"
			::= { sleV2QoS4PolicyControl 40 }

		
		-- 1.3.6.1.4.1.6296.102.10.2.5.1.2.41
		sleV2QoS4PolicyControlOuterVlan OBJECT-TYPE
			SYNTAX INTEGER (-1 | 1..4094)
			MAX-ACCESS read-write
			STATUS current
			DESCRIPTION
				"The outer vlan id to be assigned for the matched packets
				The value of -1 is nothing(not set)"
			::= { sleV2QoS4PolicyControl 41 }

		
		-- 1.3.6.1.4.1.6296.102.10.2.5.1.2.42
		sleV2QoS4PolicyControlMatchPbrNextHopSecondary OBJECT-TYPE
			SYNTAX IpAddress
			MAX-ACCESS read-write
			STATUS current
			DESCRIPTION
				"The PBR(Policy-Based_routing) nexthop secondary address."
			::= { sleV2QoS4PolicyControl 42 }

		
		-- 1.3.6.1.4.1.6296.102.10.2.5.1.2.43
		sleV2QoS4PolicyControlMatchPbrNextHopVerifyReach OBJECT-TYPE
			SYNTAX INTEGER
				{
				false(0),
				true(1)
				}
			MAX-ACCESS read-write
			STATUS current
			DESCRIPTION
				"The PBR(Policy-Based_routing) Verify-Reachability."
			::= { sleV2QoS4PolicyControl 43 }

		
		-- 1.3.6.1.4.1.6296.102.10.2.5.1.2.44
		sleV2QoS4PolicyControlMatchFlowAlias OBJECT-TYPE
			SYNTAX OCTET STRING
			MAX-ACCESS read-only
			STATUS current
			DESCRIPTION
				"The action match flowAlias"
			::= { sleV2QoS4PolicyControl 44 }

		
		-- 1.3.6.1.4.1.6296.102.10.2.5.1.2.45
		sleV2QoS4PolicyControlMatchInnerVlanCosReplace OBJECT-TYPE
			SYNTAX Integer32 (-1 | 0..7)
			MAX-ACCESS read-write
			STATUS current
			DESCRIPTION
				"The inner vlan COS replace (-1: delete)"
			::= { sleV2QoS4PolicyControl 45 }

		
		-- 1.3.6.1.4.1.6296.102.10.2.5.1.2.46
		sleV2QoS4PolicyControlMatchInnerVlanCfiReplace OBJECT-TYPE
			SYNTAX Integer32 (-1 | 0..1)
			MAX-ACCESS read-write
			STATUS current
			DESCRIPTION
				"The inner vlan CFI replace (-1: delete)"
			::= { sleV2QoS4PolicyControl 46 }

		
		-- 1.3.6.1.4.1.6296.102.10.2.5.1.2.47
		sleV2QoS4PolicyControlMatchOuterVlanCosReplace OBJECT-TYPE
			SYNTAX Integer32 (-1 | 0..7)
			MAX-ACCESS read-write
			STATUS current
			DESCRIPTION
				"The outer vlan COS replace (-1: delete)"
			::= { sleV2QoS4PolicyControl 47 }

		
		-- 1.3.6.1.4.1.6296.102.10.2.5.1.2.48
		sleV2QoS4PolicyControlMatchOuterVlanCfiReplace OBJECT-TYPE
			SYNTAX Integer32 (-1 | 0..1)
			MAX-ACCESS read-write
			STATUS current
			DESCRIPTION
				"The outer vlan CFI replace (-1: delete)"
			::= { sleV2QoS4PolicyControl 48 }

		
		-- 1.3.6.1.4.1.6296.102.10.2.5.1.3
		sleV2QoSPolicyNotification OBJECT IDENTIFIER ::= { sleV2QoS4PolicyInfo 3 }

		
		-- 1.3.6.1.4.1.6296.102.10.2.5.1.3.1
		slePolicyCreated NOTIFICATION-TYPE
			OBJECTS { sleV2QoS4PolicyControlRequest, sleV2QoS4PolicyControlTimeStamp, sleV2QoS4PolicyRedirBlackhole, sleV2QoS4PolicyMatchPbrNextHop, sleV2QoS4PolicyStage, 
				sleV2QoS4PolicyIngressPortsFlag, sleV2QoS4PolicyEgressPortsFlag, sleV2QoS4PolicyInnerVlanAction, sleV2QoS4PolicyOuterVlanAction, sleV2QoS4PolicyInnerVlan, 
				sleV2QoS4PolicyOuterVlan, sleV2QoS4PolicyControlReqResult, sleV2QoS4PolicyName, sleV2QoS4PolicyFlowCnt, sleV2QoS4PolicyClassCnt, 
				sleV2QoS4PolicyPolicerIndex, sleV2QoS4PolicyPriority, sleV2QoS4PolicyIngressPorts, sleV2QoS4PolicyEgressPorts, sleV2QoS4PolicyVlan, 
				sleV2QoS4PolicyMatchFlag, sleV2QoS4PolicyMatchVlan, sleV2QoS4PolicyMatchRedirectVlan, sleV2QoS4PolicyMatchRedirectPort, sleV2QoS4PolicyMatchMarkMode, 
				sleV2QoS4PolicyMatchQueue, sleV2QoS4PolicyMatchDp, sleV2QoS4PolicyMatchCoS, sleV2QoS4PolicyMatchDscp, sleV2QoS4PolicyMatchIpPrecedence, 
				sleV2QoS4PolicyMatchDstMacOrEgressPorts, sleV2QoS4PolicyMatchDstMac, sleV2QoS4PolicyMatchEgressPorts, sleV2QoS4PolicyNomatchFlag, sleV2QoS4PolicyNomatchRedirectPort, 
				sleV2QoS4PolicyNomatchCoS, sleV2QoS4PolicyNomatchDscp, sleV2QoS4PolicyNomatchIpPrecedence, sleV2QoS4PolicyCounterValue, sleV2QoS4PolicyCounterGreenBytes, 
				sleV2QoS4PolicyCounterYellowBytes, sleV2QoS4PolicyCounterRedBytes, sleV2QoS4PolicyMatchPbrNextHopSecondary, sleV2QoS4PolicyMatchPbrNextHopVerifyReach }
			STATUS current
			DESCRIPTION 
				"Description."
			::= { sleV2QoSPolicyNotification 1 }

		
		-- 1.3.6.1.4.1.6296.102.10.2.5.1.3.2
		slePolicyInfoChanged NOTIFICATION-TYPE
			OBJECTS { sleV2QoS4PolicyControlRequest, sleV2QoS4PolicyControlTimeStamp, sleV2QoS4PolicyStage, sleV2QoS4PolicyControlReqResult, sleV2QoS4PolicyPolicerIndex, 
				sleV2QoS4PolicyIngressPorts, sleV2QoS4PolicyEgressPorts, sleV2QoS4PolicyIngressPortsFlag, sleV2QoS4PolicyEgressPortsFlag, sleV2QoS4PolicyVlan, 
				sleV2QoS4PolicyPriority }
			STATUS current
			DESCRIPTION 
				"Description."
			::= { sleV2QoSPolicyNotification 2 }

		
		-- 1.3.6.1.4.1.6296.102.10.2.5.1.3.3
		slePolicyMatchActionChanged NOTIFICATION-TYPE
			OBJECTS { sleV2QoS4PolicyControlRequest, sleV2QoS4PolicyControlTimeStamp, sleV2QoS4PolicyRedirBlackhole, sleV2QoS4PolicyInnerVlanAction, sleV2QoS4PolicyOuterVlanAction, 
				sleV2QoS4PolicyInnerVlan, sleV2QoS4PolicyOuterVlan, sleV2QoS4PolicyControlReqResult, sleV2QoS4PolicyMatchFlag, sleV2QoS4PolicyMatchVlan, 
				sleV2QoS4PolicyMatchRedirectVlan, sleV2QoS4PolicyMatchRedirectPort, sleV2QoS4PolicyMatchMarkMode, sleV2QoS4PolicyMatchQueue, sleV2QoS4PolicyMatchDp, 
				sleV2QoS4PolicyMatchCoS, sleV2QoS4PolicyMatchDscp, sleV2QoS4PolicyMatchIpPrecedence, sleV2QoS4PolicyMatchDstMacOrEgressPorts, sleV2QoS4PolicyMatchDstMac, 
				sleV2QoS4PolicyMatchEgressPorts, sleV2QoS4PolicyMatchPbrNextHop, sleV2QoS4PolicyMatchPbrNextHopSecondary, sleV2QoS4PolicyMatchPbrNextHopVerifyReach }
			STATUS current
			DESCRIPTION 
				"Description."
			::= { sleV2QoSPolicyNotification 3 }

		
		-- 1.3.6.1.4.1.6296.102.10.2.5.1.3.4
		slePolicyNomatchActionChanged NOTIFICATION-TYPE
			OBJECTS { sleV2QoS4PolicyControlRequest, sleV2QoS4PolicyControlTimeStamp, sleV2QoS4PolicyControlReqResult, sleV2QoS4PolicyNomatchFlag, sleV2QoS4PolicyNomatchRedirectPort, 
				sleV2QoS4PolicyNomatchCoS, sleV2QoS4PolicyNomatchDscp, sleV2QoS4PolicyNomatchIpPrecedence }
			STATUS current
			DESCRIPTION 
				"Description."
			::= { sleV2QoSPolicyNotification 4 }

		
		-- 1.3.6.1.4.1.6296.102.10.2.5.1.3.5
		slePolicyDestroyed NOTIFICATION-TYPE
			OBJECTS { sleV2QoS4PolicyControlRequest, sleV2QoS4PolicyControlTimeStamp, sleV2QoS4PolicyControlReqResult, sleV2QoS4PolicyControlIndex }
			STATUS current
			DESCRIPTION 
				"Description."
			::= { sleV2QoSPolicyNotification 5 }

		
		-- 1.3.6.1.4.1.6296.102.10.2.5.1.3.6
		slePolicyCounterCleared NOTIFICATION-TYPE
			OBJECTS { sleV2QoS4PolicyControlRequest, sleV2QoS4PolicyControlTimeStamp, sleV2QoS4PolicyControlReqResult, sleV2QoS4PolicyControlIndex, sleV2QoS4PolicyCounterValue, 
				sleV2QoS4PolicyCounterGreenBytes, sleV2QoS4PolicyCounterYellowBytes, sleV2QoS4PolicyCounterRedBytes }
			STATUS current
			DESCRIPTION 
				"Description."
			::= { sleV2QoSPolicyNotification 6 }

		
		-- 1.3.6.1.4.1.6296.102.10.2.5.1.3.7
		slePolicyEmptyCreated NOTIFICATION-TYPE
			OBJECTS { sleV2QoS4PolicyControlRequest, sleV2QoS4PolicyControlTimeStamp, sleV2QoS4PolicyControlReqResult, sleV2QoS4PolicyName }
			STATUS current
			DESCRIPTION 
				"Description."
			::= { sleV2QoSPolicyNotification 7 }

		
		-- 1.3.6.1.4.1.6296.102.10.2.5.1.3.8
		slePolicyIngressTunnelSet NOTIFICATION-TYPE
			OBJECTS { sleV2QoS4PolicyControlRequest, sleV2QoS4PolicyControlTimeStamp, sleV2QoS4PolicyControlReqResult, sleV2QoS4PolicyControlIndex, sleV2QoS4PolicyControlIngressTunnelIfIndex
				 }
			STATUS current
			DESCRIPTION 
				"Description."
			::= { sleV2QoSPolicyNotification 8 }

		
		-- 1.3.6.1.4.1.6296.102.10.2.5.1.3.9
		slePolicyIngressTunnelUnset NOTIFICATION-TYPE
			OBJECTS { sleV2QoS4PolicyControlRequest, sleV2QoS4PolicyControlTimeStamp, sleV2QoS4PolicyControlReqResult, sleV2QoS4PolicyControlIndex, sleV2QoS4PolicyControlIngressTunnelIfIndex
				 }
			STATUS current
			DESCRIPTION 
				"Description."
			::= { sleV2QoSPolicyNotification 9 }

		
		-- 1.3.6.1.4.1.6296.102.10.2.5.1.3.10
		slePolicyEgressTunnelSet NOTIFICATION-TYPE
			OBJECTS { sleV2QoS4PolicyControlRequest, sleV2QoS4PolicyControlTimeStamp, sleV2QoS4PolicyControlReqResult, sleV2QoS4PolicyControlIndex, sleV2Qo4SPolicyControlEgressTunnelIfIndex
				 }
			STATUS current
			DESCRIPTION 
				"Description."
			::= { sleV2QoSPolicyNotification 10 }

		
		-- 1.3.6.1.4.1.6296.102.10.2.5.1.3.11
		slePolicyEgressTunnelUnset NOTIFICATION-TYPE
			OBJECTS { sleV2QoS4PolicyControlRequest, sleV2QoS4PolicyControlTimeStamp, sleV2QoS4PolicyControlReqResult, sleV2QoS4PolicyControlIndex, sleV2Qo4SPolicyControlEgressTunnelIfIndex
				 }
			STATUS current
			DESCRIPTION 
				"Description."
			::= { sleV2QoSPolicyNotification 11 }

		
		-- 1.3.6.1.4.1.6296.102.10.2.5.1.3.12
		slePolicyActionMatchFlowAliasChanged NOTIFICATION-TYPE
			OBJECTS { sleV2QoS4PolicyControlRequest, sleV2QoS4PolicyControlTimeStamp, sleV2QoS4PolicyControlReqResult, sleV2QoS4PolicyControlIndex, sleV2QoS4PolicyControlMatchFlowAlias
				 }
			STATUS current
			DESCRIPTION 
				"setMatchActionFlowAlias"
			::= { sleV2QoSPolicyNotification 12 }

		
		-- 1.3.6.1.4.1.6296.102.10.2.5.1.3.13
		slePolicyMatchInnerVlanCosReplaceChanged NOTIFICATION-TYPE
			OBJECTS { sleV2QoS4PolicyControlRequest, sleV2QoS4PolicyControlTimeStamp, sleV2QoS4PolicyControlReqResult, sleV2QoS4PolicyControlIndex, sleV2QoS4PolicyControlMatchInnerVlanCosReplace
				 }
			STATUS current
			DESCRIPTION 
				"setMatchInnerVlanCosReplace"
			::= { sleV2QoSPolicyNotification 13 }

		
		-- 1.3.6.1.4.1.6296.102.10.2.5.1.3.14
		slePolicyMatchInnerVlanCfiReplaceChanged NOTIFICATION-TYPE
			OBJECTS { sleV2QoS4PolicyControlRequest, sleV2QoS4PolicyControlTimeStamp, sleV2QoS4PolicyControlReqResult, sleV2QoS4PolicyControlIndex, sleV2QoS4PolicyControlMatchInnerVlanCfiReplace
				 }
			STATUS current
			DESCRIPTION 
				"setMatchInnerVlanCfiReplace"
			::= { sleV2QoSPolicyNotification 14 }

		
		-- 1.3.6.1.4.1.6296.102.10.2.5.1.3.15
		slePolicyMatchOuterVlanCosReplaceChanged NOTIFICATION-TYPE
			OBJECTS { sleV2QoS4PolicyControlRequest, sleV2QoS4PolicyControlTimeStamp, sleV2QoS4PolicyControlReqResult, sleV2QoS4PolicyControlIndex, sleV2QoS4PolicyControlMatchOuterVlanCosReplace
				 }
			STATUS current
			DESCRIPTION 
				"setMatchOuterVlanCosReplace"
			::= { sleV2QoSPolicyNotification 15 }

		
		-- 1.3.6.1.4.1.6296.102.10.2.5.1.3.16
		slePolicyMatchOuterVlanCfiReplaceChanged NOTIFICATION-TYPE
			OBJECTS { sleV2QoS4PolicyControlRequest, sleV2QoS4PolicyControlTimeStamp, sleV2QoS4PolicyControlReqResult, sleV2QoS4PolicyControlIndex, sleV2QoS4PolicyControlMatchOuterVlanCfiReplace
				 }
			STATUS current
			DESCRIPTION 
				"setMatchOuterVlanCfiReplace"
			::= { sleV2QoSPolicyNotification 16 }

		
		-- 1.3.6.1.4.1.6296.102.10.2.5.2
		sleV2QoS4PolicyFlowClass OBJECT IDENTIFIER ::= { sleV2QoS4Policy 2 }

		
		-- 1.3.6.1.4.1.6296.102.10.2.5.2.1
		sleV2QoS4PolicyFlowClassTable OBJECT-TYPE
			SYNTAX SEQUENCE OF SleV2QoS4PolicyFlowClassEntry
			MAX-ACCESS not-accessible
			STATUS current
			DESCRIPTION
				"flow class table."
			::= { sleV2QoS4PolicyFlowClass 1 }

		
		-- 1.3.6.1.4.1.6296.102.10.2.6.2.1.1
		sleV2QoS4PolicyFlowClassEntry OBJECT-TYPE
			SYNTAX SleV2QoS4PolicyFlowClassEntry
			MAX-ACCESS not-accessible
			STATUS current
			DESCRIPTION
				"key: sleV2QoS4PolicyIndex, sleV2QoS4PolicyFlowClassIndex"
			INDEX { sleV2QoS4PolicyIndex, sleV2QoS4PolicyFlowClassIndex }
			::= { sleV2QoS4PolicyFlowClassTable 1 }

		
		SleV2QoS4PolicyFlowClassEntry ::=
			SEQUENCE { 
				sleV2QoS4PolicyFlowClassIndex
					IntFlowIndex,
				sleV2QoS4PolicyFlowClassType
					IntFlowOrClass,
				sleV2QoS4PolicyFlowClassID
					IntFlowIndex,
				sleV2QoS4PolicyFlowClassName
					OctetName
			 }

		-- 1.3.6.1.4.1.6296.102.10.2.6.2.1.1.1
		sleV2QoS4PolicyFlowClassIndex OBJECT-TYPE
			SYNTAX IntFlowIndex
			MAX-ACCESS read-only
			STATUS current
			DESCRIPTION
				"The index of flow or class in policy"
			::= { sleV2QoS4PolicyFlowClassEntry 1 }

		
		-- 1.3.6.1.4.1.6296.102.10.2.6.2.1.1.2
		sleV2QoS4PolicyFlowClassType OBJECT-TYPE
			SYNTAX IntFlowOrClass
			MAX-ACCESS read-only
			STATUS current
			DESCRIPTION
				"The flag about flow or class"
			::= { sleV2QoS4PolicyFlowClassEntry 2 }

		
		-- 1.3.6.1.4.1.6296.102.10.2.6.2.1.1.3
		sleV2QoS4PolicyFlowClassID OBJECT-TYPE
			SYNTAX IntFlowIndex
			MAX-ACCESS read-only
			STATUS current
			DESCRIPTION
				"The identifier of class or flow"
			::= { sleV2QoS4PolicyFlowClassEntry 3 }

		
		-- 1.3.6.1.4.1.6296.102.10.2.6.2.1.1.4
		sleV2QoS4PolicyFlowClassName OBJECT-TYPE
			SYNTAX OctetName
			MAX-ACCESS read-only
			STATUS current
			DESCRIPTION
				"The name of class or flow"
			::= { sleV2QoS4PolicyFlowClassEntry 4 }

		
		-- 1.3.6.1.4.1.6296.102.10.2.5.2.2
		sleV2QoS4PolicyFlowClassControl OBJECT IDENTIFIER ::= { sleV2QoS4PolicyFlowClass 2 }

		
		-- 1.3.6.1.4.1.6296.102.10.2.5.2.2.1
		sleV2QoS4PolicyFlowClassControlRequest OBJECT-TYPE
			SYNTAX INTEGER
				{
				addFlowClass(1),
				deleteFlowClass(2),
				deleteAllFlow(3),
				deleteAllClass(4),
				deleteAllFlowClass(5)
				}
			MAX-ACCESS read-write
			STATUS current
			DESCRIPTION
				"The request of a user command"
			::= { sleV2QoS4PolicyFlowClassControl 1 }

		
		-- 1.3.6.1.4.1.6296.102.10.2.5.2.2.2
		sleV2QoS4PolicyFlowClassControlStatus OBJECT-TYPE
			SYNTAX SleControlStatusType
			MAX-ACCESS read-write
			STATUS current
			DESCRIPTION
				"The status of user command"
			::= { sleV2QoS4PolicyFlowClassControl 2 }

		
		-- 1.3.6.1.4.1.6296.102.10.2.5.2.2.3
		sleV2QoS4PolicyFlowClassControlTimer OBJECT-TYPE
			SYNTAX Gauge32
			MAX-ACCESS read-write
			STATUS current
			DESCRIPTION
				"The maximum time for the manager for a long running user command"
			::= { sleV2QoS4PolicyFlowClassControl 3 }

		
		-- 1.3.6.1.4.1.6296.102.10.2.5.2.2.4
		sleV2QoS4PolicyFlowClassControlTimeStamp OBJECT-TYPE
			SYNTAX TimeTicks
			MAX-ACCESS read-write
			STATUS current
			DESCRIPTION
				"The time stamp of the last command(end of command)"
			::= { sleV2QoS4PolicyFlowClassControl 4 }

		
		-- 1.3.6.1.4.1.6296.102.10.2.5.2.2.5
		sleV2QoS4PolicyFlowClassControlReqResult OBJECT-TYPE
			SYNTAX SleControlRequestResultType
			MAX-ACCESS read-write
			STATUS current
			DESCRIPTION
				"The result of the last user command"
			::= { sleV2QoS4PolicyFlowClassControl 5 }

		
		-- 1.3.6.1.4.1.6296.102.10.2.5.2.2.6
		sleV2QoS4PolicyFlowClassControlPolicyIndex OBJECT-TYPE
			SYNTAX IntPolicyIndex
			MAX-ACCESS read-write
			STATUS current
			DESCRIPTION
				"The index of Policy"
			::= { sleV2QoS4PolicyFlowClassControl 6 }

		
		-- 1.3.6.1.4.1.6296.102.10.2.5.2.2.7
		sleV2QoS4PolicyFlowClassControlIndex OBJECT-TYPE
			SYNTAX IntFlowIndex
			MAX-ACCESS read-write
			STATUS current
			DESCRIPTION
				"The index of flow or class in this policy"
			::= { sleV2QoS4PolicyFlowClassControl 7 }

		
		-- 1.3.6.1.4.1.6296.102.10.2.5.2.2.8
		sleV2QoS4PolicyFlowClassControlType OBJECT-TYPE
			SYNTAX IntFlowOrClass
			MAX-ACCESS read-write
			STATUS current
			DESCRIPTION
				"The type of flow or class"
			::= { sleV2QoS4PolicyFlowClassControl 8 }

		
		-- 1.3.6.1.4.1.6296.102.10.2.5.2.2.9
		sleV2QoS4PolicyFlowClassControlFlowID OBJECT-TYPE
			SYNTAX IntFlowIndex
			MAX-ACCESS read-write
			STATUS current
			DESCRIPTION
				"The index of flow
				Available according to sleV2QoS4PolicyFlowClassControlType.
				"
			::= { sleV2QoS4PolicyFlowClassControl 9 }

		
		-- 1.3.6.1.4.1.6296.102.10.2.5.2.2.10
		sleV2QoS4PolicyFlowClassControlClassID OBJECT-TYPE
			SYNTAX IntClassIndex
			MAX-ACCESS read-write
			STATUS current
			DESCRIPTION
				"The index of class
				Available according to sleV2QoS4PolicyFlowClassControlType.
				"
			::= { sleV2QoS4PolicyFlowClassControl 10 }

		
		-- 1.3.6.1.4.1.6296.102.10.2.5.2.3
		sleV2QoS4PolicyFlowClassNotification OBJECT IDENTIFIER ::= { sleV2QoS4PolicyFlowClass 3 }

		
		-- 1.3.6.1.4.1.6296.102.10.2.5.2.3.1
		slePolicyFlowAdded NOTIFICATION-TYPE
			OBJECTS { sleV2QoS4PolicyFlowClassControlRequest, sleV2QoS4PolicyFlowClassControlTimeStamp, sleV2QoS4PolicyFlowClassControlReqResult, sleV2QoS4PolicyFlowClassType, sleV2QoS4PolicyFlowClassID
				 }
			STATUS current
			DESCRIPTION 
				"Description."
			::= { sleV2QoS4PolicyFlowClassNotification 1 }

		
		-- 1.3.6.1.4.1.6296.102.10.2.5.2.3.2
		slePolicyFlowDeleted NOTIFICATION-TYPE
			OBJECTS { sleV2QoS4PolicyFlowClassControlRequest, sleV2QoS4PolicyFlowClassControlTimeStamp, sleV2QoS4PolicyFlowClassControlReqResult, sleV2QoS4PolicyFlowClassControlPolicyIndex, sleV2QoS4PolicyFlowClassControlIndex
				 }
			STATUS current
			DESCRIPTION 
				"Description."
			::= { sleV2QoS4PolicyFlowClassNotification 2 }

		
		-- 1.3.6.1.4.1.6296.102.10.2.5.2.3.3
		slePolicyAllFlowDeleted NOTIFICATION-TYPE
			OBJECTS { sleV2QoS4PolicyFlowClassControlRequest, sleV2QoS4PolicyFlowClassControlTimeStamp, sleV2QoS4PolicyFlowClassControlReqResult, sleV2QoS4PolicyFlowClassControlPolicyIndex }
			STATUS current
			DESCRIPTION 
				"Description."
			::= { sleV2QoS4PolicyFlowClassNotification 3 }

		
		-- 1.3.6.1.4.1.6296.102.10.2.5.2.3.4
		slePolicyAllClassDeleted NOTIFICATION-TYPE
			OBJECTS { sleV2QoS4PolicyFlowClassControlRequest, sleV2QoS4PolicyFlowClassControlTimeStamp, sleV2QoS4PolicyFlowClassControlReqResult, sleV2QoS4PolicyFlowClassControlPolicyIndex }
			STATUS current
			DESCRIPTION 
				"Description."
			::= { sleV2QoS4PolicyFlowClassNotification 4 }

		
		-- 1.3.6.1.4.1.6296.102.10.2.5.2.3.5
		slePolicyAllFlowClassDeleted NOTIFICATION-TYPE
			OBJECTS { sleV2QoS4PolicyFlowClassControlRequest, sleV2QoS4PolicyFlowClassControlTimeStamp, sleV2QoS4PolicyFlowClassControlReqResult, sleV2QoS4PolicyFlowClassControlPolicyIndex }
			STATUS current
			DESCRIPTION 
				"Description."
			::= { sleV2QoS4PolicyFlowClassNotification 5 }

		
		-- 1.3.6.1.4.1.6296.102.10.2.5.3
		sleV2QoS4PolicyIF OBJECT IDENTIFIER ::= { sleV2QoS4Policy 3 }

		
--  1.3.6.1.4.1.6296.102.10.2.5.3.1
		-- 1.3.6.1.4.1.6296.102.10.2.5.3.1
		sleV2QoS4PolicyIFTable OBJECT-TYPE
			SYNTAX SEQUENCE OF SleV2QoS4PolicyIFEntry
			MAX-ACCESS not-accessible
			STATUS current
			DESCRIPTION
				"Description."
			::= { sleV2QoS4PolicyIF 1 }

		
--  1.3.6.1.4.1.6296.102.10.2.5.3.1.1
		-- 1.3.6.1.4.1.6296.102.10.2.5.3.1.1
		sleV2QoS4PolicyIFEntry OBJECT-TYPE
			SYNTAX SleV2QoS4PolicyIFEntry
			MAX-ACCESS not-accessible
			STATUS current
			DESCRIPTION
				"Description."
			INDEX { ifindex, sleV2QoS4PolicyIndex, sleV2QoS4PolicyIFDirection }
			::= { sleV2QoS4PolicyIFTable 1 }

		
		SleV2QoS4PolicyIFEntry ::=
			SEQUENCE { 
				sleV2QoS4PolicyIFDirection
					INTEGER
			 }

--  1.3.6.1.4.1.6296.102.10.2.5.3.1.1.1
		-- 1.3.6.1.4.1.6296.102.10.2.5.3.1.1.1
		sleV2QoS4PolicyIFDirection OBJECT-TYPE
			SYNTAX INTEGER
				{
				input(1),
				output(2)
				}
			MAX-ACCESS read-only
			STATUS current
			DESCRIPTION
				"Packet input/output direction"
			::= { sleV2QoS4PolicyIFEntry 1 }

		
		-- 1.3.6.1.4.1.6296.102.10.2.5.3.2
		sleV2QoS4PolicyIFControl OBJECT IDENTIFIER ::= { sleV2QoS4PolicyIF 2 }

		
		-- 1.3.6.1.4.1.6296.102.10.2.5.3.2.1
		sleV2QoS4PolicyIFControlRequest OBJECT-TYPE
			SYNTAX INTEGER
				{
				setServicePolicy(1),
				clearServicePolicy(2)
				}
			MAX-ACCESS read-write
			STATUS current
			DESCRIPTION
				"The request of a user command"
			::= { sleV2QoS4PolicyIFControl 1 }

		
		-- 1.3.6.1.4.1.6296.102.10.2.5.3.2.2
		sleV2QoS4PolicyIFControlStatus OBJECT-TYPE
			SYNTAX SleControlStatusType
			MAX-ACCESS read-only
			STATUS current
			DESCRIPTION
				"The status of user command"
			::= { sleV2QoS4PolicyIFControl 2 }

		
		-- 1.3.6.1.4.1.6296.102.10.2.5.3.2.3
		sleV2QoS4PolicyIFControlTimer OBJECT-TYPE
			SYNTAX Gauge32
			MAX-ACCESS read-write
			STATUS current
			DESCRIPTION
				"The maximum time for the manager for a long running user command"
			::= { sleV2QoS4PolicyIFControl 3 }

		
		-- 1.3.6.1.4.1.6296.102.10.2.5.3.2.4
		sleV2QoS4PolicyIFControlTimeStamp OBJECT-TYPE
			SYNTAX TimeTicks
			MAX-ACCESS read-only
			STATUS current
			DESCRIPTION
				"The time stamp of the last command(end of command)"
			::= { sleV2QoS4PolicyIFControl 4 }

		
		-- 1.3.6.1.4.1.6296.102.10.2.5.3.2.5
		sleV2QoS4PolicyIFControlReqResult OBJECT-TYPE
			SYNTAX SleControlRequestResultType
			MAX-ACCESS read-only
			STATUS current
			DESCRIPTION
				"The result of the last user command"
			::= { sleV2QoS4PolicyIFControl 5 }

		
		-- 1.3.6.1.4.1.6296.102.10.2.5.3.2.6
		sleV2QoS4PolicyIFControlIfindex OBJECT-TYPE
			SYNTAX Integer32
			MAX-ACCESS read-write
			STATUS current
			DESCRIPTION
				"The interface index."
			::= { sleV2QoS4PolicyIFControl 6 }

		
		-- 1.3.6.1.4.1.6296.102.10.2.5.3.2.7
		sleV2QoS4PolicyIFControlPolicyIndex OBJECT-TYPE
			SYNTAX IntPolicerIndex
			MAX-ACCESS read-write
			STATUS current
			DESCRIPTION
				"The Policy index."
			::= { sleV2QoS4PolicyIFControl 7 }

		
		-- 1.3.6.1.4.1.6296.102.10.2.5.3.2.8
		sleV2QoS4PolicyIFControlDirection OBJECT-TYPE
			SYNTAX INTEGER
				{
				input(1),
				output(2)
				}
			MAX-ACCESS read-write
			STATUS current
			DESCRIPTION
				"Packet input/output direction"
			::= { sleV2QoS4PolicyIFControl 8 }

		
		-- 1.3.6.1.4.1.6296.102.10.2.5.3.3
		sleV2QoS4PolicyIFNotification OBJECT IDENTIFIER ::= { sleV2QoS4PolicyIF 3 }

		
		-- 1.3.6.1.4.1.6296.102.10.2.5.3.3.1
		sleV2QosPolicyIFServicePolicyChanged NOTIFICATION-TYPE
			OBJECTS { sleV2QoS4PolicyIFControlRequest, sleV2QoS4PolicyIFControlTimeStamp, sleV2QoS4PolicyIFControlReqResult, sleV2QoS4PolicyIFControlIfindex, sleV2QoS4PolicyIFControlPolicyIndex, 
				sleV2QoS4PolicyIFControlDirection }
			STATUS current
			DESCRIPTION 
				"setServicePolicy"
			::= { sleV2QoS4PolicyIFNotification 1 }

		
		-- 1.3.6.1.4.1.6296.102.10.2.5.3.3.2
		sleV2QosPolicyIFServicePolicyCleared NOTIFICATION-TYPE
			OBJECTS { sleV2QoS4PolicyIFControlRequest, sleV2QoS4PolicyIFControlTimeStamp, sleV2QoS4PolicyIFControlReqResult, sleV2QoS4PolicyIFControlIfindex, sleV2QoS4PolicyIFControlPolicyIndex, 
				sleV2QoS4PolicyIFControlDirection }
			STATUS current
			DESCRIPTION 
				"setServicePolicy"
			::= { sleV2QoS4PolicyIFNotification 2 }

		
		-- 1.3.6.1.4.1.6296.102.10.2.6
		sleV2QoS4Remark OBJECT IDENTIFIER ::= { sleV2QoS4 6 }

		
		-- 1.3.6.1.4.1.6296.102.10.2.6.1
		sleV2QoS4RemarkBase OBJECT IDENTIFIER ::= { sleV2QoS4Remark 1 }

		
		-- 1.3.6.1.4.1.6296.102.10.2.6.1.1
		sleV2QoS4RemarkInfo OBJECT IDENTIFIER ::= { sleV2QoS4RemarkBase 1 }

		
		-- 1.3.6.1.4.1.6296.102.10.2.6.1.1.1
		sleV2QoS4RemarkLayer2Mode OBJECT-TYPE
			SYNTAX IntL2BaseRemarkMode
			MAX-ACCESS read-only
			STATUS current
			DESCRIPTION
				"The layer2 remark mode
				1 : remark based on queue (default)
				2 : remark based on 802.1p priority
				"
			::= { sleV2QoS4RemarkInfo 1 }

		
		-- 1.3.6.1.4.1.6296.102.10.2.6.1.1.2
		sleV2QoS4RemarkMode OBJECT-TYPE
			SYNTAX BITS
				{
				remarkPriorityIP(0),
				remarkByQueueOrCoS(1)
				}
			MAX-ACCESS read-only
			STATUS current
			DESCRIPTION
				"The remark mode
				0 : enable 801.1p-remark for IP packets
				1 : enable 801.1p-remark for Non-IP packets
				"
			::= { sleV2QoS4RemarkInfo 2 }

		
		-- 1.3.6.1.4.1.6296.102.10.2.6.1.2
		sleV2QoS4RemarkControl OBJECT IDENTIFIER ::= { sleV2QoS4RemarkBase 2 }

		
		-- 1.3.6.1.4.1.6296.102.10.2.6.1.2.1
		sleV2QoS4RemarkControlRequest OBJECT-TYPE
			SYNTAX INTEGER { setRemarkMode(1) }
			MAX-ACCESS read-write
			STATUS current
			DESCRIPTION
				"The request of a user command"
			::= { sleV2QoS4RemarkControl 1 }

		
		-- 1.3.6.1.4.1.6296.102.10.2.6.1.2.2
		sleV2QoS4RemarkControlStatus OBJECT-TYPE
			SYNTAX SleControlStatusType
			MAX-ACCESS read-write
			STATUS current
			DESCRIPTION
				"The status of user command"
			::= { sleV2QoS4RemarkControl 2 }

		
		-- 1.3.6.1.4.1.6296.102.10.2.6.1.2.3
		sleV2QoS4RemarkControlTimer OBJECT-TYPE
			SYNTAX Gauge32
			MAX-ACCESS read-write
			STATUS current
			DESCRIPTION
				"The maximum time for the manager for a long running user command"
			::= { sleV2QoS4RemarkControl 3 }

		
		-- 1.3.6.1.4.1.6296.102.10.2.6.1.2.4
		sleV2QoS4RemarkControlTimStamp OBJECT-TYPE
			SYNTAX TimeTicks
			MAX-ACCESS read-write
			STATUS current
			DESCRIPTION
				"The time stamp of the last command(end of command)"
			::= { sleV2QoS4RemarkControl 4 }

		
		-- 1.3.6.1.4.1.6296.102.10.2.6.1.2.5
		sleV2QoS4RemarkControlReqResult OBJECT-TYPE
			SYNTAX SleControlRequestResultType
			MAX-ACCESS read-write
			STATUS current
			DESCRIPTION
				"The result of the last user command"
			::= { sleV2QoS4RemarkControl 5 }

		
		-- 1.3.6.1.4.1.6296.102.10.2.6.1.2.6
		sleV2QoS4RemarkControlLayer2Mode OBJECT-TYPE
			SYNTAX IntL2BaseRemarkMode
			MAX-ACCESS read-write
			STATUS current
			DESCRIPTION
				"The layer2 remark mode
				-1: default (remarkByQueue)
				1 : remark by queue
				2 : remark by priority
				"
			::= { sleV2QoS4RemarkControl 6 }

		
		-- 1.3.6.1.4.1.6296.102.10.2.6.1.2.7
		sleV2QoS4RemarkControlMode OBJECT-TYPE
			SYNTAX BITS
				{
				remarkByDSCP(0),
				remarkByQueueOrCoS(1)
				}
			MAX-ACCESS read-write
			STATUS current
			DESCRIPTION
				"The remark mode
				0 : enable 801.1p-remark for IP packets
				1 : enable 801.1p-remark for Non-IP packets
				"
			::= { sleV2QoS4RemarkControl 7 }

		
		-- 1.3.6.1.4.1.6296.102.10.2.6.1.3
		sleV2QoS4RemarkNotification OBJECT IDENTIFIER ::= { sleV2QoS4RemarkBase 3 }

		
		-- 1.3.6.1.4.1.6296.102.10.2.6.1.3.1
		sleRemarkChanged NOTIFICATION-TYPE
			OBJECTS { sleV2QoS4RemarkControlRequest, sleV2QoS4RemarkControlTimStamp, sleV2QoS4RemarkControlReqResult, sleV2QoS4RemarkLayer2Mode, sleV2QoS4RemarkMode
				 }
			STATUS current
			DESCRIPTION 
				"Description."
			::= { sleV2QoS4RemarkNotification 1 }

		
		-- 1.3.6.1.4.1.6296.102.10.2.6.2
		sleV2QoS4RemarkL3 OBJECT IDENTIFIER ::= { sleV2QoS4Remark 2 }

		
		-- 1.3.6.1.4.1.6296.102.10.2.6.2.1
		sleV2QoS4RemarkL3Table OBJECT-TYPE
			SYNTAX SEQUENCE OF SleV2QoS4RemarkL3Entry
			MAX-ACCESS not-accessible
			STATUS current
			DESCRIPTION
				"remark L3 table."
			::= { sleV2QoS4RemarkL3 1 }

		
		-- 1.3.6.1.4.1.6296.102.10.2.7.2.1.1
		sleV2QoS4RemarkL3Entry OBJECT-TYPE
			SYNTAX SleV2QoS4RemarkL3Entry
			MAX-ACCESS not-accessible
			STATUS current
			DESCRIPTION
				"key: sleV2QoS4RemarkL3ColorIndex, sleV2QoS4RemarkL3DSCPIndex"
			INDEX { sleV2QoS4RemarkL3ColorIndex, sleV2QoS4RemarkL3DSCPIndex }
			::= { sleV2QoS4RemarkL3Table 1 }

		
		SleV2QoS4RemarkL3Entry ::=
			SEQUENCE { 
				sleV2QoS4RemarkL3ColorIndex
					IntColorIndex,
				sleV2QoS4RemarkL3DSCPIndex
					IntDSCPIndex,
				sleV2QoS4RemarkL3Queue
					IntQueue,
				sleV2QoS4RemarkL3Dp
					IntDP,
				sleV2QoS4RemarkL3CoS
					IntCoS,
				sleV2QoS4RemarkL3Dscp
					IntDscp
			 }

		-- 1.3.6.1.4.1.6296.102.10.2.7.2.1.1.1
		sleV2QoS4RemarkL3ColorIndex OBJECT-TYPE
			SYNTAX IntColorIndex
			MAX-ACCESS read-only
			STATUS current
			DESCRIPTION
				"The index of color"
			::= { sleV2QoS4RemarkL3Entry 1 }

		
		-- 1.3.6.1.4.1.6296.102.10.2.7.2.1.1.2
		sleV2QoS4RemarkL3DSCPIndex OBJECT-TYPE
			SYNTAX IntDSCPIndex
			MAX-ACCESS read-only
			STATUS current
			DESCRIPTION
				"The index of DSCP
				The index value of 1~ 64 mean 0 ~ 63 of the DSCP
				"
			::= { sleV2QoS4RemarkL3Entry 2 }

		
		-- 1.3.6.1.4.1.6296.102.10.2.7.2.1.1.3
		sleV2QoS4RemarkL3Queue OBJECT-TYPE
			SYNTAX IntQueue
			MAX-ACCESS read-only
			STATUS current
			DESCRIPTION
				"This is remarking to queue by Color and DSCP
				0 : default
				"
			::= { sleV2QoS4RemarkL3Entry 3 }

		
		-- 1.3.6.1.4.1.6296.102.10.2.7.2.1.1.4
		sleV2QoS4RemarkL3Dp OBJECT-TYPE
			SYNTAX IntDP
			MAX-ACCESS read-only
			STATUS current
			DESCRIPTION
				"This is remarking to drop precednece by Color and DSCP
				0 : default
				"
			::= { sleV2QoS4RemarkL3Entry 4 }

		
		-- 1.3.6.1.4.1.6296.102.10.2.7.2.1.1.5
		sleV2QoS4RemarkL3CoS OBJECT-TYPE
			SYNTAX IntCoS
			MAX-ACCESS read-only
			STATUS current
			DESCRIPTION
				"This is remarking to CoS by Color and DSCP
				0 : default
				"
			::= { sleV2QoS4RemarkL3Entry 5 }

		
		-- 1.3.6.1.4.1.6296.102.10.2.7.2.1.1.6
		sleV2QoS4RemarkL3Dscp OBJECT-TYPE
			SYNTAX IntDscp
			MAX-ACCESS read-only
			STATUS current
			DESCRIPTION
				"This is remarking to DSCP by Color and DSCP
				0 : default
				"
			::= { sleV2QoS4RemarkL3Entry 6 }

		
		-- 1.3.6.1.4.1.6296.102.10.2.6.2.2
		sleV2QoS4RemarkL3Control OBJECT IDENTIFIER ::= { sleV2QoS4RemarkL3 2 }

		
		-- 1.3.6.1.4.1.6296.102.10.2.6.2.2.1
		sleV2QoS4RemarkL3ControlRequest OBJECT-TYPE
			SYNTAX INTEGER { setL3Remark(1) }
			MAX-ACCESS read-write
			STATUS current
			DESCRIPTION
				"The request of a user command"
			::= { sleV2QoS4RemarkL3Control 1 }

		
		-- 1.3.6.1.4.1.6296.102.10.2.6.2.2.2
		sleV2QoS4RemarkL3ControlStatus OBJECT-TYPE
			SYNTAX SleControlStatusType
			MAX-ACCESS read-write
			STATUS current
			DESCRIPTION
				"The status of user command"
			::= { sleV2QoS4RemarkL3Control 2 }

		
		-- 1.3.6.1.4.1.6296.102.10.2.6.2.2.3
		sleV2QoS4RemarkL3ControlTimer OBJECT-TYPE
			SYNTAX Gauge32
			MAX-ACCESS read-write
			STATUS current
			DESCRIPTION
				"The maximum time for the manager for a long running user command"
			::= { sleV2QoS4RemarkL3Control 3 }

		
		-- 1.3.6.1.4.1.6296.102.10.2.6.2.2.4
		sleV2QoS4RemarkL3ControlTimeStamp OBJECT-TYPE
			SYNTAX TimeTicks
			MAX-ACCESS read-write
			STATUS current
			DESCRIPTION
				"The time stamp of the last command(end of command)"
			::= { sleV2QoS4RemarkL3Control 4 }

		
		-- 1.3.6.1.4.1.6296.102.10.2.6.2.2.5
		sleV2QoS4RemarkL3ControlReqResult OBJECT-TYPE
			SYNTAX SleControlRequestResultType
			MAX-ACCESS read-write
			STATUS current
			DESCRIPTION
				"The result of the last user command"
			::= { sleV2QoS4RemarkL3Control 5 }

		
		-- 1.3.6.1.4.1.6296.102.10.2.6.2.2.6
		sleV2QoS4RemarkL3ControlColorIndex OBJECT-TYPE
			SYNTAX IntColorIndex
			MAX-ACCESS read-write
			STATUS current
			DESCRIPTION
				"The index of color marking"
			::= { sleV2QoS4RemarkL3Control 6 }

		
		-- 1.3.6.1.4.1.6296.102.10.2.6.2.2.7
		sleV2QoS4RemarkL3ControlDSCPIndex OBJECT-TYPE
			SYNTAX IntDSCPIndex
			MAX-ACCESS read-write
			STATUS current
			DESCRIPTION
				"The index of DSCP
				The index value of 1~ 64 mean 0 ~ 63 of the DSCP
				"
			::= { sleV2QoS4RemarkL3Control 7 }

		
		-- 1.3.6.1.4.1.6296.102.10.2.6.2.2.8
		sleV2QoS4RemarkL3ControlQueue OBJECT-TYPE
			SYNTAX IntQueue
			MAX-ACCESS read-write
			STATUS current
			DESCRIPTION
				"This is remarking to queue by Color and DSCP
				The value of -1 means nothing(not set)
				"
			::= { sleV2QoS4RemarkL3Control 8 }

		
		-- 1.3.6.1.4.1.6296.102.10.2.6.2.2.9
		sleV2QoS4RemarkL3ControlDp OBJECT-TYPE
			SYNTAX IntDP
			MAX-ACCESS read-write
			STATUS current
			DESCRIPTION
				"This is remarking to drop precednece by Color and DSCP
				The value of -1 means nothing(not set)
				"
			::= { sleV2QoS4RemarkL3Control 9 }

		
		-- 1.3.6.1.4.1.6296.102.10.2.6.2.2.10
		sleV2QoS4RemarkL3ControlCoS OBJECT-TYPE
			SYNTAX IntCoS
			MAX-ACCESS read-write
			STATUS current
			DESCRIPTION
				"This is remarking to CoS by Color and DSCP
				The value of -1 means nothing(not set)
				"
			::= { sleV2QoS4RemarkL3Control 10 }

		
		-- 1.3.6.1.4.1.6296.102.10.2.6.2.2.11
		sleV2QoS4RemarkL3ControlDscp OBJECT-TYPE
			SYNTAX IntDscp
			MAX-ACCESS read-write
			STATUS current
			DESCRIPTION
				"This is remarking to DSCP by Color and DSCP
				The value of -1 means nothing(not set)
				"
			::= { sleV2QoS4RemarkL3Control 11 }

		
		-- 1.3.6.1.4.1.6296.102.10.2.6.2.3
		sleV2QoS4RemarkL3Notification OBJECT IDENTIFIER ::= { sleV2QoS4RemarkL3 3 }

		
		-- 1.3.6.1.4.1.6296.102.10.2.6.2.3.1
		sleRemarkL3Changed NOTIFICATION-TYPE
			OBJECTS { sleV2QoS4RemarkL3ControlRequest, sleV2QoS4RemarkL3ControlTimeStamp, sleV2QoS4RemarkL3ControlReqResult, sleV2QoS4RemarkL3Queue, sleV2QoS4RemarkL3Dp, 
				sleV2QoS4RemarkL3CoS, sleV2QoS4RemarkL3Dscp }
			STATUS current
			DESCRIPTION 
				"Description."
			::= { sleV2QoS4RemarkL3Notification 1 }

		
		-- 1.3.6.1.4.1.6296.102.10.2.6.3
		sleV2QoS4RemarkL2 OBJECT IDENTIFIER ::= { sleV2QoS4Remark 3 }

		
		-- 1.3.6.1.4.1.6296.102.10.2.6.3.1
		sleV2QoS4RemarkL2Table OBJECT-TYPE
			SYNTAX SEQUENCE OF SleV2QoS4RemarkL2Entry
			MAX-ACCESS not-accessible
			STATUS current
			DESCRIPTION
				"remark L2 table."
			::= { sleV2QoS4RemarkL2 1 }

		
		-- 1.3.6.1.4.1.6296.102.10.2.7.3.1.1
		sleV2QoS4RemarkL2Entry OBJECT-TYPE
			SYNTAX SleV2QoS4RemarkL2Entry
			MAX-ACCESS not-accessible
			STATUS current
			DESCRIPTION
				"key: sleV2QoS4RemarkL2ColorIndex, sleV2QoS4RemarkL2QueueCoSIndex"
			INDEX { sleV2QoS4RemarkL2ColorIndex, sleV2QoS4RemarkL2QueueCoSIndex }
			::= { sleV2QoS4RemarkL2Table 1 }

		
		SleV2QoS4RemarkL2Entry ::=
			SEQUENCE { 
				sleV2QoS4RemarkL2ColorIndex
					IntColorIndex,
				sleV2QoS4RemarkL2QueueCoSIndex
					IntQueueCoSIndex,
				sleV2QoS4RemarkL2Queue
					IntQueue,
				sleV2QoS4RemarkL2Dp
					IntDP,
				sleV2QoS4RemarkL2CoS
					IntCoS,
				sleV2QoS4RemarkL2Dscp
					IntDscp
			 }

		-- 1.3.6.1.4.1.6296.102.10.2.7.3.1.1.1
		sleV2QoS4RemarkL2ColorIndex OBJECT-TYPE
			SYNTAX IntColorIndex
			MAX-ACCESS read-only
			STATUS current
			DESCRIPTION
				"The index of color marking"
			::= { sleV2QoS4RemarkL2Entry 1 }

		
		-- 1.3.6.1.4.1.6296.102.10.2.7.3.1.1.2
		sleV2QoS4RemarkL2QueueCoSIndex OBJECT-TYPE
			SYNTAX IntQueueCoSIndex
			MAX-ACCESS read-only
			STATUS current
			DESCRIPTION
				"The index of queue or CoS
				The index value of 1~ 8 mean 0 ~ 7 of the queue and CoS
				Refer to sleV2QoS4RemarkLayer2Mode
				"
			::= { sleV2QoS4RemarkL2Entry 2 }

		
		-- 1.3.6.1.4.1.6296.102.10.2.7.3.1.1.3
		sleV2QoS4RemarkL2Queue OBJECT-TYPE
			SYNTAX IntQueue
			MAX-ACCESS read-only
			STATUS current
			DESCRIPTION
				"This is remarking to queue by Color and L2(queue or CoS)
				0 : default
				"
			::= { sleV2QoS4RemarkL2Entry 3 }

		
		-- 1.3.6.1.4.1.6296.102.10.2.7.3.1.1.4
		sleV2QoS4RemarkL2Dp OBJECT-TYPE
			SYNTAX IntDP
			MAX-ACCESS read-only
			STATUS current
			DESCRIPTION
				"This is remarking to drop precednece by L2(queue or CoS)
				0 : default
				"
			::= { sleV2QoS4RemarkL2Entry 4 }

		
		-- 1.3.6.1.4.1.6296.102.10.2.7.3.1.1.5
		sleV2QoS4RemarkL2CoS OBJECT-TYPE
			SYNTAX IntCoS
			MAX-ACCESS read-only
			STATUS current
			DESCRIPTION
				"This is remarking to CoS by Color and L2(queue or CoS)
				0 : default
				"
			::= { sleV2QoS4RemarkL2Entry 5 }

		
		-- 1.3.6.1.4.1.6296.102.10.2.7.3.1.1.6
		sleV2QoS4RemarkL2Dscp OBJECT-TYPE
			SYNTAX IntDscp
			MAX-ACCESS read-only
			STATUS current
			DESCRIPTION
				"This is remarking to DSCP by Color and L2(queue or CoS)
				0 : default
				"
			::= { sleV2QoS4RemarkL2Entry 6 }

		
		-- 1.3.6.1.4.1.6296.102.10.2.6.3.2
		sleV2QoS4RemarkL2Control OBJECT IDENTIFIER ::= { sleV2QoS4RemarkL2 2 }

		
		-- 1.3.6.1.4.1.6296.102.10.2.6.3.2.1
		sleV2QoS4RemarkL2ControlRequest OBJECT-TYPE
			SYNTAX INTEGER { setL2Remark(1) }
			MAX-ACCESS read-write
			STATUS current
			DESCRIPTION
				"The request of a user command"
			::= { sleV2QoS4RemarkL2Control 1 }

		
		-- 1.3.6.1.4.1.6296.102.10.2.6.3.2.2
		sleV2QoS4RemarkL2ControlStatus OBJECT-TYPE
			SYNTAX SleControlStatusType
			MAX-ACCESS read-write
			STATUS current
			DESCRIPTION
				"The status of user command"
			::= { sleV2QoS4RemarkL2Control 2 }

		
		-- 1.3.6.1.4.1.6296.102.10.2.6.3.2.3
		sleV2QoS4RemarkL2ControlTimer OBJECT-TYPE
			SYNTAX Gauge32
			MAX-ACCESS read-write
			STATUS current
			DESCRIPTION
				"The maximum time for the manager for a long running user command"
			::= { sleV2QoS4RemarkL2Control 3 }

		
		-- 1.3.6.1.4.1.6296.102.10.2.6.3.2.4
		sleV2QoS4RemarkL2ControlTimeStamp OBJECT-TYPE
			SYNTAX TimeTicks
			MAX-ACCESS read-write
			STATUS current
			DESCRIPTION
				"The time stamp of the last command(end of command)"
			::= { sleV2QoS4RemarkL2Control 4 }

		
		-- 1.3.6.1.4.1.6296.102.10.2.6.3.2.5
		sleV2QoS4RemarkL2ControlReqResult OBJECT-TYPE
			SYNTAX SleControlRequestResultType
			MAX-ACCESS read-write
			STATUS current
			DESCRIPTION
				"The result of the last user command"
			::= { sleV2QoS4RemarkL2Control 5 }

		
		-- 1.3.6.1.4.1.6296.102.10.2.6.3.2.6
		sleV2QoS4RemarkL2ControlColorIndex OBJECT-TYPE
			SYNTAX IntColorIndex
			MAX-ACCESS read-write
			STATUS current
			DESCRIPTION
				"The index of color marking"
			::= { sleV2QoS4RemarkL2Control 6 }

		
		-- 1.3.6.1.4.1.6296.102.10.2.6.3.2.7
		sleV2QoS4RemarkL2ControlQueueCoSIndex OBJECT-TYPE
			SYNTAX IntQueueCoSIndex
			MAX-ACCESS read-write
			STATUS current
			DESCRIPTION
				"The index of queue or CoS
				The index value of 1~ 8 mean 0 ~ 7 of the queue and CoS
				Refer to sleV2QoS4RemarkLayer2Mod
				"
			::= { sleV2QoS4RemarkL2Control 7 }

		
		-- 1.3.6.1.4.1.6296.102.10.2.6.3.2.8
		sleV2QoS4RemarkL2ControlQueue OBJECT-TYPE
			SYNTAX IntQueue
			MAX-ACCESS read-write
			STATUS current
			DESCRIPTION
				"This is remarking to queue by Color and L2(queue or CoS)
				The value of -1 means nothing(not set)
				"
			::= { sleV2QoS4RemarkL2Control 8 }

		
		-- 1.3.6.1.4.1.6296.102.10.2.6.3.2.9
		sleV2QoS4RemarkL2ControlDp OBJECT-TYPE
			SYNTAX IntDP
			MAX-ACCESS read-write
			STATUS current
			DESCRIPTION
				"This is remarking to drop precednece by L2(queue or CoS)
				The value of -1 means nothing(not set)
				"
			::= { sleV2QoS4RemarkL2Control 9 }

		
		-- 1.3.6.1.4.1.6296.102.10.2.6.3.2.10
		sleV2QoS4RemarkL2ControlCoS OBJECT-TYPE
			SYNTAX IntCoS
			MAX-ACCESS read-write
			STATUS current
			DESCRIPTION
				"This is remarking to CoS by Color and L2(queue or CoS)
				The value of -1 means nothing(not set)
				"
			::= { sleV2QoS4RemarkL2Control 10 }

		
		-- 1.3.6.1.4.1.6296.102.10.2.6.3.2.11
		sleV2QoS4RemarkL2ControlDscp OBJECT-TYPE
			SYNTAX IntDscp
			MAX-ACCESS read-write
			STATUS current
			DESCRIPTION
				"This is remarking to DSCP by Color and L2(queue or CoS)
				The value of -1 means nothing(not set)
				"
			::= { sleV2QoS4RemarkL2Control 11 }

		
		-- 1.3.6.1.4.1.6296.102.10.2.6.3.3
		sleV2QoS4RemarkL2Notification OBJECT IDENTIFIER ::= { sleV2QoS4RemarkL2 3 }

		
		-- 1.3.6.1.4.1.6296.102.10.2.6.3.3.1
		sleRemarkL2Changed NOTIFICATION-TYPE
			OBJECTS { sleV2QoS4RemarkL2ControlRequest, sleV2QoS4RemarkL2ControlTimeStamp, sleV2QoS4RemarkL2ControlReqResult, sleV2QoS4RemarkL2Queue, sleV2QoS4RemarkL2Dp, 
				sleV2QoS4RemarkL2CoS, sleV2QoS4RemarkL2Dscp }
			STATUS current
			DESCRIPTION 
				"Description."
			::= { sleV2QoS4RemarkL2Notification 1 }

		
		-- 1.3.6.1.4.1.6296.102.10.2.7
		sleV2QoS4RED OBJECT IDENTIFIER ::= { sleV2QoS4 7 }

		
		-- 1.3.6.1.4.1.6296.102.10.2.7.1
		sleV2QoS4REDProfile OBJECT IDENTIFIER ::= { sleV2QoS4RED 1 }

		
		-- 1.3.6.1.4.1.6296.102.10.2.7.1.1
		sleV2QoS4REDProfileTable OBJECT-TYPE
			SYNTAX SEQUENCE OF SleV2QoS4REDProfileEntry
			MAX-ACCESS not-accessible
			STATUS current
			DESCRIPTION
				"redundancy profile table."
			::= { sleV2QoS4REDProfile 1 }

		
		-- 1.3.6.1.4.1.6296.102.10.2.8.1.1.1
		sleV2QoS4REDProfileEntry OBJECT-TYPE
			SYNTAX SleV2QoS4REDProfileEntry
			MAX-ACCESS not-accessible
			STATUS current
			DESCRIPTION
				"key: sleV2QoS4REDProfileId, sleV2QoS4REDProfileQueueId"
			INDEX { sleV2QoS4REDProfileId, sleV2QoS4REDProfileQueueId }
			::= { sleV2QoS4REDProfileTable 1 }

		
		SleV2QoS4REDProfileEntry ::=
			SEQUENCE { 
				sleV2QoS4REDProfileId
					INTEGER,
				sleV2QoS4REDProfileQueueId
					INTEGER,
				sleV2QoS4REDProfileDp0MinThres
					INTEGER,
				sleV2QoS4REDProfileDp0MaxThres
					INTEGER,
				sleV2QoS4REDProfileDp0Prob
					INTEGER,
				sleV2QoS4REDProfileDp1MinThres
					INTEGER,
				sleV2QoS4REDProfileDp1MaxThres
					INTEGER,
				sleV2QoS4REDProfileDp1Prob
					INTEGER,
				sleV2QoS4REDProfileDp2MinThres
					INTEGER,
				sleV2QoS4REDProfileDp2MaxThres
					INTEGER,
				sleV2QoS4REDProfileDp2Prob
					INTEGER,
				sleV2QoS4REDProfileWeight
					INTEGER
			 }

		-- 1.3.6.1.4.1.6296.102.10.2.8.1.1.1.1
		sleV2QoS4REDProfileId OBJECT-TYPE
			SYNTAX INTEGER (1..255)
			MAX-ACCESS read-only
			STATUS current
			DESCRIPTION
				"The index of RED profile.
				Marvell : (1..4), BCM : number of ports."
			::= { sleV2QoS4REDProfileEntry 1 }

		
		-- 1.3.6.1.4.1.6296.102.10.2.8.1.1.1.2
		sleV2QoS4REDProfileQueueId OBJECT-TYPE
			SYNTAX INTEGER (1..8)
			MAX-ACCESS read-only
			STATUS current
			DESCRIPTION
				"The index of queue."
			::= { sleV2QoS4REDProfileEntry 2 }

		
		-- 1.3.6.1.4.1.6296.102.10.2.8.1.1.1.3
		sleV2QoS4REDProfileDp0MinThres OBJECT-TYPE
			SYNTAX INTEGER (-1 | 0..65535)
			MAX-ACCESS read-only
			STATUS current
			DESCRIPTION
				"DP0 min threshold.
				In case RED, used as RED min threshold.
				Marvell : (1..65535), BCM : (0..127)"
			::= { sleV2QoS4REDProfileEntry 3 }

		
		-- 1.3.6.1.4.1.6296.102.10.2.8.1.1.1.4
		sleV2QoS4REDProfileDp0MaxThres OBJECT-TYPE
			SYNTAX INTEGER (-1 | 0..65535)
			MAX-ACCESS read-only
			STATUS current
			DESCRIPTION
				"DP0 max threshold.
				Used only in case WRED.
				Marvell : (1..65535), BCM : not supported."
			::= { sleV2QoS4REDProfileEntry 4 }

		
		-- 1.3.6.1.4.1.6296.102.10.2.8.1.1.1.5
		sleV2QoS4REDProfileDp0Prob OBJECT-TYPE
			SYNTAX INTEGER (-1 | 1..15)
			MAX-ACCESS read-only
			STATUS current
			DESCRIPTION
				"DP0 drop probability.
				In case RED, used as RED prob"
			::= { sleV2QoS4REDProfileEntry 5 }

		
		-- 1.3.6.1.4.1.6296.102.10.2.8.1.1.1.6
		sleV2QoS4REDProfileDp1MinThres OBJECT-TYPE
			SYNTAX INTEGER (-1 | 0..65535)
			MAX-ACCESS read-only
			STATUS current
			DESCRIPTION
				"DP1 min threshold. Used only in case WRED
				Marvell : (1..65535), BCM : not supported."
			::= { sleV2QoS4REDProfileEntry 6 }

		
		-- 1.3.6.1.4.1.6296.102.10.2.8.1.1.1.7
		sleV2QoS4REDProfileDp1MaxThres OBJECT-TYPE
			SYNTAX INTEGER (-1 | 0..65535)
			MAX-ACCESS read-only
			STATUS current
			DESCRIPTION
				"DP1 max threshold. Used only in case WRED
				Marvell : (1..65535), BCM : not supported."
			::= { sleV2QoS4REDProfileEntry 7 }

		
		-- 1.3.6.1.4.1.6296.102.10.2.8.1.1.1.8
		sleV2QoS4REDProfileDp1Prob OBJECT-TYPE
			SYNTAX INTEGER (-1 | 1..15)
			MAX-ACCESS read-only
			STATUS current
			DESCRIPTION
				"DP1 drop probability."
			::= { sleV2QoS4REDProfileEntry 8 }

		
		-- 1.3.6.1.4.1.6296.102.10.2.8.1.1.1.9
		sleV2QoS4REDProfileDp2MinThres OBJECT-TYPE
			SYNTAX INTEGER (-1 | 0..65535)
			MAX-ACCESS read-only
			STATUS current
			DESCRIPTION
				"DP2 min threshold. Used only in case WRED
				Marvell : (1..65535), BCM : not supported."
			::= { sleV2QoS4REDProfileEntry 9 }

		
		-- 1.3.6.1.4.1.6296.102.10.2.8.1.1.1.10
		sleV2QoS4REDProfileDp2MaxThres OBJECT-TYPE
			SYNTAX INTEGER (-1 | 0..65535)
			MAX-ACCESS read-only
			STATUS current
			DESCRIPTION
				"DP2 max threshold. Used only in case WRED
				Marvell : (1..65535), BCM : not supported."
			::= { sleV2QoS4REDProfileEntry 10 }

		
		-- 1.3.6.1.4.1.6296.102.10.2.8.1.1.1.11
		sleV2QoS4REDProfileDp2Prob OBJECT-TYPE
			SYNTAX INTEGER (-1 | 1..15)
			MAX-ACCESS read-only
			STATUS current
			DESCRIPTION
				"DP2 drop probability."
			::= { sleV2QoS4REDProfileEntry 11 }

		
		-- 1.3.6.1.4.1.6296.102.10.2.8.1.1.1.12
		sleV2QoS4REDProfileWeight OBJECT-TYPE
			SYNTAX INTEGER (-1 | 1..15)
			MAX-ACCESS read-only
			STATUS current
			DESCRIPTION
				"Drop weight, Used only in case WRED.
				BCM : not supported."
			::= { sleV2QoS4REDProfileEntry 12 }

		
		-- 1.3.6.1.4.1.6296.102.10.2.7.1.2
		sleV2QoS4REDProfileControl OBJECT IDENTIFIER ::= { sleV2QoS4REDProfile 2 }

		
		-- 1.3.6.1.4.1.6296.102.10.2.7.1.2.1
		sleV2QoS4REDProfileControlRequest OBJECT-TYPE
			SYNTAX INTEGER
				{
				setREDProfile(1),
				clearREDProfile(2)
				}
			MAX-ACCESS read-write
			STATUS current
			DESCRIPTION
				"The request of a user command"
			::= { sleV2QoS4REDProfileControl 1 }

		
		-- 1.3.6.1.4.1.6296.102.10.2.7.1.2.2
		sleV2QoS4REDProfileControlStatus OBJECT-TYPE
			SYNTAX SleControlStatusType
			MAX-ACCESS read-only
			STATUS current
			DESCRIPTION
				"The status of user command"
			::= { sleV2QoS4REDProfileControl 2 }

		
		-- 1.3.6.1.4.1.6296.102.10.2.7.1.2.3
		sleV2QoS4REDProfileControlTimer OBJECT-TYPE
			SYNTAX Gauge32
			MAX-ACCESS read-write
			STATUS current
			DESCRIPTION
				"The maximum time for the manager for a long running user command"
			::= { sleV2QoS4REDProfileControl 3 }

		
		-- 1.3.6.1.4.1.6296.102.10.2.7.1.2.4
		sleV2QoS4REDProfileControlTimeStamp OBJECT-TYPE
			SYNTAX TimeTicks
			MAX-ACCESS read-only
			STATUS current
			DESCRIPTION
				"The time stamp of the last command(end of command)"
			::= { sleV2QoS4REDProfileControl 4 }

		
		-- 1.3.6.1.4.1.6296.102.10.2.7.1.2.5
		sleV2QoS4REDProfileControlReqResult OBJECT-TYPE
			SYNTAX SleControlRequestResultType
			MAX-ACCESS read-only
			STATUS current
			DESCRIPTION
				"The result of the last user command"
			::= { sleV2QoS4REDProfileControl 5 }

		
		-- 1.3.6.1.4.1.6296.102.10.2.7.1.2.6
		sleV2QoS4REDProfileControlId OBJECT-TYPE
			SYNTAX INTEGER (1..255)
			MAX-ACCESS read-write
			STATUS current
			DESCRIPTION
				"The index of RED profile.
				Marvell (1..4), BCM : number of ports"
			::= { sleV2QoS4REDProfileControl 6 }

		
		-- 1.3.6.1.4.1.6296.102.10.2.7.1.2.7
		sleV2QoS4REDProfileControlQueueId OBJECT-TYPE
			SYNTAX INTEGER (1..8)
			MAX-ACCESS read-write
			STATUS current
			DESCRIPTION
				"The index of queues"
			::= { sleV2QoS4REDProfileControl 7 }

		
		-- 1.3.6.1.4.1.6296.102.10.2.7.1.2.8
		sleV2QoS4REDProfileControlDp0MinThres OBJECT-TYPE
			SYNTAX INTEGER (-1 | 0..65535)
			MAX-ACCESS read-write
			STATUS current
			DESCRIPTION
				"DP0 min threshold.
				In case RED, used as RED min threshold.
				Marvell (1..65535), BCM (0..127)"
			::= { sleV2QoS4REDProfileControl 8 }

		
		-- 1.3.6.1.4.1.6296.102.10.2.7.1.2.9
		sleV2QoS4REDProfileControlDp0MaxThres OBJECT-TYPE
			SYNTAX INTEGER (-1 | 0..65535)
			MAX-ACCESS read-write
			STATUS current
			DESCRIPTION
				"DP0 max threshold.
				Used only in case WRED.
				Marvell (1..65535), BCM: not supported"
			::= { sleV2QoS4REDProfileControl 9 }

		
		-- 1.3.6.1.4.1.6296.102.10.2.7.1.2.10
		sleV2QoS4REDProfileControlDp0Prob OBJECT-TYPE
			SYNTAX INTEGER (-1 | 1..15)
			MAX-ACCESS read-write
			STATUS current
			DESCRIPTION
				"DP0 Drop Probability
				In case RED, used as RED prob."
			::= { sleV2QoS4REDProfileControl 10 }

		
		-- 1.3.6.1.4.1.6296.102.10.2.7.1.2.11
		sleV2QoS4REDProfileControlDp1MinThres OBJECT-TYPE
			SYNTAX INTEGER (-1 | 0..65535)
			MAX-ACCESS read-write
			STATUS current
			DESCRIPTION
				"DP1 min threshold.
				Used only in case WRED.
				Marvell (1..65535), BCM: not supported"
			::= { sleV2QoS4REDProfileControl 11 }

		
		-- 1.3.6.1.4.1.6296.102.10.2.7.1.2.12
		sleV2QoS4REDProfileControlDp1MaxThres OBJECT-TYPE
			SYNTAX INTEGER (-1 | 0..65535)
			MAX-ACCESS read-write
			STATUS current
			DESCRIPTION
				"DP1 max threshold.
				Used only in case WRED
				Marvell (1..65535), BCM: not supported"
			::= { sleV2QoS4REDProfileControl 12 }

		
		-- 1.3.6.1.4.1.6296.102.10.2.7.1.2.13
		sleV2QoS4REDProfileControlDp1Prob OBJECT-TYPE
			SYNTAX INTEGER (-1 | 1..15)
			MAX-ACCESS read-write
			STATUS current
			DESCRIPTION
				"DP1 Drop Probability. Used only in case WRED.
				BCM: not supported"
			::= { sleV2QoS4REDProfileControl 13 }

		
		-- 1.3.6.1.4.1.6296.102.10.2.7.1.2.14
		sleV2QoS4REDProfileControlDp2MinThres OBJECT-TYPE
			SYNTAX INTEGER (-1 | 0..65535)
			MAX-ACCESS read-write
			STATUS current
			DESCRIPTION
				"DP2 min threshold. Used only in case WRED
				Marvell (1..65535), BCM: not supported"
			::= { sleV2QoS4REDProfileControl 14 }

		
		-- 1.3.6.1.4.1.6296.102.10.2.7.1.2.15
		sleV2QoS4REDProfileControlDp2MaxThres OBJECT-TYPE
			SYNTAX INTEGER (-1 | 0..65535)
			MAX-ACCESS read-write
			STATUS current
			DESCRIPTION
				"DP2 max threshold.
				Marvell (1..65535), BCM: not supported"
			::= { sleV2QoS4REDProfileControl 15 }

		
		-- 1.3.6.1.4.1.6296.102.10.2.7.1.2.16
		sleV2QoS4REDProfileControlDp2Prob OBJECT-TYPE
			SYNTAX INTEGER (-1 | 1..15)
			MAX-ACCESS read-write
			STATUS current
			DESCRIPTION
				"DP2 Drop Probability. Used only in case WRED.
				BCM: not supported"
			::= { sleV2QoS4REDProfileControl 16 }

		
		-- 1.3.6.1.4.1.6296.102.10.2.7.1.2.17
		sleV2QoS4REDProfileControlWeight OBJECT-TYPE
			SYNTAX INTEGER (-1 | 1..15)
			MAX-ACCESS read-write
			STATUS current
			DESCRIPTION
				"Drop weight. Used only in case WRED.
				BCM: not supported"
			::= { sleV2QoS4REDProfileControl 17 }

		
		-- 1.3.6.1.4.1.6296.102.10.2.7.1.3
		sleV2QoS4REDProfileNotification OBJECT IDENTIFIER ::= { sleV2QoS4REDProfile 3 }

		
		-- 1.3.6.1.4.1.6296.102.10.2.7.1.3.1
		sleV2QS4REDProfileChanged NOTIFICATION-TYPE
			OBJECTS { sleV2QoS4REDProfileControlRequest, sleV2QoS4REDProfileControlTimeStamp, sleV2QoS4REDProfileControlReqResult, sleV2QoS4REDProfileDp0MinThres, sleV2QoS4REDProfileDp0MaxThres, 
				sleV2QoS4REDProfileDp0Prob, sleV2QoS4REDProfileDp1MinThres, sleV2QoS4REDProfileDp1MaxThres, sleV2QoS4REDProfileDp1Prob, sleV2QoS4REDProfileDp2MinThres, 
				sleV2QoS4REDProfileDp2MaxThres, sleV2QoS4REDProfileDp2Prob, sleV2QoS4REDProfileWeight }
			STATUS current
			DESCRIPTION 
				"Description."
			::= { sleV2QoS4REDProfileNotification 1 }

		
		-- 1.3.6.1.4.1.6296.102.10.2.7.1.3.2
		sleV2QS4REDProfileCleared NOTIFICATION-TYPE
			OBJECTS { sleV2QoS4REDProfileControlRequest, sleV2QoS4REDProfileControlTimeStamp, sleV2QoS4REDProfileControlReqResult, sleV2QoS4REDProfileControlId }
			STATUS current
			DESCRIPTION 
				"Description."
			::= { sleV2QoS4REDProfileNotification 2 }

		
		-- 1.3.6.1.4.1.6296.102.10.2.7.2
		sleV2QoS4PortREDInfo OBJECT IDENTIFIER ::= { sleV2QoS4RED 2 }

		
		-- 1.3.6.1.4.1.6296.102.10.2.7.2.1
		sleV2QoS4PortREDInfoTable OBJECT-TYPE
			SYNTAX SEQUENCE OF SleV2QoS4PortREDInfoEntry
			MAX-ACCESS not-accessible
			STATUS current
			DESCRIPTION
				"port redundancy info table."
			::= { sleV2QoS4PortREDInfo 1 }

		
		-- 1.3.6.1.4.1.6296.102.10.2.8.2.1.1
		sleV2QoS4PortREDInfoEntry OBJECT-TYPE
			SYNTAX SleV2QoS4PortREDInfoEntry
			MAX-ACCESS not-accessible
			STATUS current
			DESCRIPTION
				"key: sleV2QoS4PortREDInfoInterfaceIndex"
			INDEX { sleV2QoS4PortREDInfoInterfaceIndex }
			::= { sleV2QoS4PortREDInfoTable 1 }

		
		SleV2QoS4PortREDInfoEntry ::=
			SEQUENCE { 
				sleV2QoS4PortREDInfoInterfaceIndex
					InterfaceIndex,
				sleV2QoS4PortREDInfoEnable
					INTEGER,
				sleV2QoS4PortREDInfoProfileId
					INTEGER
			 }

		-- 1.3.6.1.4.1.6296.102.10.2.8.2.1.1.1
		sleV2QoS4PortREDInfoInterfaceIndex OBJECT-TYPE
			SYNTAX InterfaceIndex
			MAX-ACCESS read-only
			STATUS current
			DESCRIPTION
				"Inrterface Index"
			::= { sleV2QoS4PortREDInfoEntry 1 }

		
		-- 1.3.6.1.4.1.6296.102.10.2.8.2.1.1.2
		sleV2QoS4PortREDInfoEnable OBJECT-TYPE
			SYNTAX INTEGER
				{
				disable(0),
				red(1),
				wred(2)
				}
			MAX-ACCESS read-only
			STATUS current
			DESCRIPTION
				"RED/WRED enable flag
				BCM: only available RED, Marvell: only available WRED"
			::= { sleV2QoS4PortREDInfoEntry 2 }

		
		-- 1.3.6.1.4.1.6296.102.10.2.8.2.1.1.3
		sleV2QoS4PortREDInfoProfileId OBJECT-TYPE
			SYNTAX INTEGER (-1 | 1..255)
			MAX-ACCESS read-only
			STATUS current
			DESCRIPTION
				"RED profile index.
				In case sleV2QoS4PortREDInfoEnable == disable, invalid
				Marvell : (1..4), BCM : number of ports
				In case BCM, this value is equal to port index. (read-only)"
			::= { sleV2QoS4PortREDInfoEntry 3 }

		
		-- 1.3.6.1.4.1.6296.102.10.2.7.2.2
		sleV2QoS4PortREDInfoControl OBJECT IDENTIFIER ::= { sleV2QoS4PortREDInfo 2 }

		
		-- 1.3.6.1.4.1.6296.102.10.2.7.2.2.1
		sleV2QoS4PortREDInfoControlRequest OBJECT-TYPE
			SYNTAX INTEGER { setPortREDInfo(1) }
			MAX-ACCESS read-write
			STATUS current
			DESCRIPTION
				"The request of a user command"
			::= { sleV2QoS4PortREDInfoControl 1 }

		
		-- 1.3.6.1.4.1.6296.102.10.2.7.2.2.2
		sleV2QoS4PortREDInfoControlStatus OBJECT-TYPE
			SYNTAX SleControlStatusType
			MAX-ACCESS read-only
			STATUS current
			DESCRIPTION
				"The status of user command"
			::= { sleV2QoS4PortREDInfoControl 2 }

		
		-- 1.3.6.1.4.1.6296.102.10.2.7.2.2.3
		sleV2QoS4PortREDInfoControlTimer OBJECT-TYPE
			SYNTAX Gauge32
			MAX-ACCESS read-write
			STATUS current
			DESCRIPTION
				"The maximum time for the manager for a long running user command"
			::= { sleV2QoS4PortREDInfoControl 3 }

		
		-- 1.3.6.1.4.1.6296.102.10.2.7.2.2.4
		sleV2QoS4PortREDInfoControlTimeStamp OBJECT-TYPE
			SYNTAX TimeTicks
			MAX-ACCESS read-only
			STATUS current
			DESCRIPTION
				"The time stamp of the last command(end of command)"
			::= { sleV2QoS4PortREDInfoControl 4 }

		
		-- 1.3.6.1.4.1.6296.102.10.2.7.2.2.5
		sleV2QoS4PortREDInfoControlReqResult OBJECT-TYPE
			SYNTAX SleControlRequestResultType
			MAX-ACCESS read-only
			STATUS current
			DESCRIPTION
				"The result of the last user command"
			::= { sleV2QoS4PortREDInfoControl 5 }

		
		-- 1.3.6.1.4.1.6296.102.10.2.7.2.2.6
		sleV2QoS4PortREDInfoControlInterfaceIndex OBJECT-TYPE
			SYNTAX InterfaceIndex
			MAX-ACCESS read-write
			STATUS current
			DESCRIPTION
				"Inrterface Index"
			::= { sleV2QoS4PortREDInfoControl 6 }

		
		-- 1.3.6.1.4.1.6296.102.10.2.7.2.2.7
		sleV2QoS4PortREDInfoControlEnable OBJECT-TYPE
			SYNTAX INTEGER
				{
				disable(0),
				red(1),
				wred(2)
				}
			MAX-ACCESS read-write
			STATUS current
			DESCRIPTION
				"RED/WRED enable flag"
			::= { sleV2QoS4PortREDInfoControl 7 }

		
		-- 1.3.6.1.4.1.6296.102.10.2.7.2.2.8
		sleV2QoS4PortREDInfoControlProfileId OBJECT-TYPE
			SYNTAX INTEGER (-1 | 1..255)
			MAX-ACCESS read-write
			STATUS current
			DESCRIPTION
				"RED profile index.
				This value is valid only when  sleV2QoS4PortREDInfoEnable is 
				equal to RED or WRED only, valid.
				Marvell : (1..4), BCM : number of ports
				In case BCM, this value is equal to port index. (read-only)"
			::= { sleV2QoS4PortREDInfoControl 8 }

		
		-- 1.3.6.1.4.1.6296.102.10.2.7.2.3
		sleV2QoS4PortREDInfoNotification OBJECT IDENTIFIER ::= { sleV2QoS4PortREDInfo 3 }

		
		-- 1.3.6.1.4.1.6296.102.10.2.7.2.3.1
		sleV2QoS4PortREDInfoChanged NOTIFICATION-TYPE
			OBJECTS { sleV2QoS4PortREDInfoControlRequest, sleV2QoS4PortREDInfoControlTimeStamp, sleV2QoS4PortREDInfoControlReqResult, sleV2QoS4PortREDInfoEnable, sleV2QoS4PortREDInfoProfileId
				 }
			STATUS current
			DESCRIPTION 
				"setPortREDInfo"
			::= { sleV2QoS4PortREDInfoNotification 1 }

		
		-- 1.3.6.1.4.1.6296.102.10.2.8
		sleV2QoS4Queue OBJECT IDENTIFIER ::= { sleV2QoS4 8 }

		
		-- 1.3.6.1.4.1.6296.102.10.2.8.1
		sleV2QoS4QueueInfo OBJECT IDENTIFIER ::= { sleV2QoS4Queue 1 }

		
		-- 1.3.6.1.4.1.6296.102.10.2.8.1.1
		sleV2QoS4QueueInfoTable OBJECT-TYPE
			SYNTAX SEQUENCE OF SleV2QoS4QueueInfoEntry
			MAX-ACCESS not-accessible
			STATUS current
			DESCRIPTION
				"queue info table."
			::= { sleV2QoS4QueueInfo 1 }

		
		-- 1.3.6.1.4.1.6296.102.10.2.9.1.1.1
		sleV2QoS4QueueInfoEntry OBJECT-TYPE
			SYNTAX SleV2QoS4QueueInfoEntry
			MAX-ACCESS not-accessible
			STATUS current
			DESCRIPTION
				"key: sleV2QoS4QueueInfoInterfaceIndex, sleV2QoS4QueueInfoId"
			INDEX { sleV2QoS4QueueInfoInterfaceIndex, sleV2QoS4QueueInfoId }
			::= { sleV2QoS4QueueInfoTable 1 }

		
		SleV2QoS4QueueInfoEntry ::=
			SEQUENCE { 
				sleV2QoS4QueueInfoInterfaceIndex
					InterfaceIndex,
				sleV2QoS4QueueInfoId
					INTEGER,
				sleV2QoS4QueueInfoScheduleMode
					INTEGER,
				sleV2QoS4QueueInfoDWRRGroup
					INTEGER,
				sleV2QoS4QueueInfoMinBandwidth
					Integer32,
				sleV2QoS4QueueInfoMaxBandwidth
					Integer32,
				sleV2QoS4QueueInfoWeight
					INTEGER,
				sleV2QoS4QueueMappedCoS
					INTEGER,
				sleV2QoS4QueueInfoBufferEgressMinLimitUnicast
					Integer32,
				sleV2QoS4QueueInfoBufferEgressMaxLimitPolicyUnicast
					INTEGER,
				sleV2QoS4QueueInfoBufferEgressMaxLimitUnicast
					Integer32,
				sleV2QoS4QueueInfoBufferEgressMinLimitNonUnicast
					Integer32,
				sleV2QoS4QueueInfoBufferEgressMaxLimitPolicyNonUnicast
					INTEGER,
				sleV2QoS4QueueInfoBufferEgressMaxLimitNonUnicast
					Integer32
			 }

		-- 1.3.6.1.4.1.6296.102.10.2.9.1.1.1.1
		sleV2QoS4QueueInfoInterfaceIndex OBJECT-TYPE
			SYNTAX InterfaceIndex
			MAX-ACCESS read-only
			STATUS current
			DESCRIPTION
				"Inrterface Index"
			::= { sleV2QoS4QueueInfoEntry 1 }

		
		-- 1.3.6.1.4.1.6296.102.10.2.9.1.1.1.2
		sleV2QoS4QueueInfoId OBJECT-TYPE
			SYNTAX INTEGER (1..8)
			MAX-ACCESS read-only
			STATUS current
			DESCRIPTION
				"The index of queue"
			::= { sleV2QoS4QueueInfoEntry 2 }

		
		-- 1.3.6.1.4.1.6296.102.10.2.9.1.1.1.3
		sleV2QoS4QueueInfoScheduleMode OBJECT-TYPE
			SYNTAX INTEGER
				{
				sp(1),
				rr(2),
				wrr(3),
				wfq(4),
				drr(5),
				bd(6)
				}
			MAX-ACCESS read-only
			STATUS current
			DESCRIPTION
				"Schedule mode of queue."
			::= { sleV2QoS4QueueInfoEntry 3 }

		
		-- 1.3.6.1.4.1.6296.102.10.2.9.1.1.1.4
		sleV2QoS4QueueInfoDWRRGroup OBJECT-TYPE
			SYNTAX INTEGER
				{
				undefined(0),
				group0(1),
				group1(2)
				}
			MAX-ACCESS read-only
			STATUS current
			DESCRIPTION
				"Queue dwrr group"
			::= { sleV2QoS4QueueInfoEntry 4 }

		
		-- 1.3.6.1.4.1.6296.102.10.2.9.1.1.1.5
		sleV2QoS4QueueInfoMinBandwidth OBJECT-TYPE
			SYNTAX Integer32
			MAX-ACCESS read-only
			STATUS current
			DESCRIPTION
				"Min bandwidth of queue"
			::= { sleV2QoS4QueueInfoEntry 5 }

		
		-- 1.3.6.1.4.1.6296.102.10.2.9.1.1.1.6
		sleV2QoS4QueueInfoMaxBandwidth OBJECT-TYPE
			SYNTAX Integer32
			MAX-ACCESS read-only
			STATUS current
			DESCRIPTION
				"Max bandwidth of queue"
			::= { sleV2QoS4QueueInfoEntry 6 }

		
		-- 1.3.6.1.4.1.6296.102.10.2.9.1.1.1.7
		sleV2QoS4QueueInfoWeight OBJECT-TYPE
			SYNTAX INTEGER (-1 | 1..255)
			MAX-ACCESS read-only
			STATUS current
			DESCRIPTION
				"Weight of queue
				BCM (1..15), Marvell (6..255)"
			::= { sleV2QoS4QueueInfoEntry 7 }

		
		-- 1.3.6.1.4.1.6296.102.10.2.9.1.1.1.8
		sleV2QoS4QueueMappedCoS OBJECT-TYPE
			SYNTAX INTEGER (0..7)
			MAX-ACCESS read-only
			STATUS current
			DESCRIPTION
				"Mapped cos"
			::= { sleV2QoS4QueueInfoEntry 8 }

		
		-- 1.3.6.1.4.1.6296.102.10.2.9.1.1.1.9
		sleV2QoS4QueueInfoBufferEgressMinLimitUnicast OBJECT-TYPE
			SYNTAX Integer32
			MAX-ACCESS read-only
			STATUS current
			DESCRIPTION
				"Buffer Egress Min Limit for unicast Queue."
			::= { sleV2QoS4QueueInfoEntry 9 }

		
		-- 1.3.6.1.4.1.6296.102.10.2.9.1.1.1.10
		sleV2QoS4QueueInfoBufferEgressMaxLimitPolicyUnicast OBJECT-TYPE
			SYNTAX INTEGER
				{
				static(1),
				dynamic(2)
				}
			MAX-ACCESS read-only
			STATUS current
			DESCRIPTION
				"Policy to Buffer Egress Max Limit for unicast Queue."
			::= { sleV2QoS4QueueInfoEntry 10 }

		
		-- 1.3.6.1.4.1.6296.102.10.2.9.1.1.1.11
		sleV2QoS4QueueInfoBufferEgressMaxLimitUnicast OBJECT-TYPE
			SYNTAX Integer32
			MAX-ACCESS read-only
			STATUS current
			DESCRIPTION
				"Buffer Egress Max Limit for unicast Queue."
			::= { sleV2QoS4QueueInfoEntry 11 }

		
		-- 1.3.6.1.4.1.6296.102.10.2.9.1.1.1.12
		sleV2QoS4QueueInfoBufferEgressMinLimitNonUnicast OBJECT-TYPE
			SYNTAX Integer32
			MAX-ACCESS read-only
			STATUS current
			DESCRIPTION
				"Buffer Egress Min Limit for non-unicast Queue."
			::= { sleV2QoS4QueueInfoEntry 12 }

		
		-- 1.3.6.1.4.1.6296.102.10.2.9.1.1.1.13
		sleV2QoS4QueueInfoBufferEgressMaxLimitPolicyNonUnicast OBJECT-TYPE
			SYNTAX INTEGER
				{
				static(1),
				dynamic(2)
				}
			MAX-ACCESS read-only
			STATUS current
			DESCRIPTION
				"Policy to Buffer Egress Max Limit for non-unicast Queue."
			::= { sleV2QoS4QueueInfoEntry 13 }

		
		-- 1.3.6.1.4.1.6296.102.10.2.9.1.1.1.14
		sleV2QoS4QueueInfoBufferEgressMaxLimitNonUnicast OBJECT-TYPE
			SYNTAX Integer32
			MAX-ACCESS read-only
			STATUS current
			DESCRIPTION
				"Buffer Egress Max Limit for non-unicast Queue."
			::= { sleV2QoS4QueueInfoEntry 14 }

		
		-- 1.3.6.1.4.1.6296.102.10.2.8.1.2
		sleV2QoS4QueueInfoControl OBJECT IDENTIFIER ::= { sleV2QoS4QueueInfo 2 }

		
		-- 1.3.6.1.4.1.6296.102.10.2.8.1.2.1
		sleV2QoS4QueueInfoControlRequest OBJECT-TYPE
			SYNTAX INTEGER
				{
				setQueueInfo(1),
				setScheduleMode(2),
				setMaxBandwidth(3),
				setMinBandwidth(4),
				setWeight(5),
				setBufferEgressMinLimitUnicast(6),
				clearBufferEgressMinLimitUnicast(7),
				setBufferEgressMaxLimitUnicast(8),
				clearBufferEgressMaxLimitUnicast(9),
				setBufferEgressMinLimitNonUnicast(10),
				clearBufferEgressMinLimitNonUnicast(11),
				setBufferEgressMaxLimitNonUnicast(12),
				clearBufferEgressMaxLimitNonUnicast(13)
				}
			MAX-ACCESS read-write
			STATUS current
			DESCRIPTION
				"The request of a user command"
			::= { sleV2QoS4QueueInfoControl 1 }

		
		-- 1.3.6.1.4.1.6296.102.10.2.8.1.2.2
		sleV2QoS4QueueInfoControlStatus OBJECT-TYPE
			SYNTAX SleControlStatusType
			MAX-ACCESS read-only
			STATUS current
			DESCRIPTION
				"The status of user command"
			::= { sleV2QoS4QueueInfoControl 2 }

		
		-- 1.3.6.1.4.1.6296.102.10.2.8.1.2.3
		sleV2QoS4QueueInfoControlTimer OBJECT-TYPE
			SYNTAX Gauge32
			MAX-ACCESS read-write
			STATUS current
			DESCRIPTION
				"The maximum time for the manager for a long running user command"
			::= { sleV2QoS4QueueInfoControl 3 }

		
		-- 1.3.6.1.4.1.6296.102.10.2.8.1.2.4
		sleV2QoS4QueueInfoControlTimeStamp OBJECT-TYPE
			SYNTAX TimeTicks
			MAX-ACCESS read-only
			STATUS current
			DESCRIPTION
				"The time stamp of the last command(end of command)"
			::= { sleV2QoS4QueueInfoControl 4 }

		
		-- 1.3.6.1.4.1.6296.102.10.2.8.1.2.5
		sleV2QoS4QueueInfoControlReqResult OBJECT-TYPE
			SYNTAX SleControlRequestResultType
			MAX-ACCESS read-only
			STATUS current
			DESCRIPTION
				"The result of the last user command"
			::= { sleV2QoS4QueueInfoControl 5 }

		
		-- 1.3.6.1.4.1.6296.102.10.2.8.1.2.6
		sleV2QoS4QueueInfoControlInterfaceIndex OBJECT-TYPE
			SYNTAX InterfaceIndex
			MAX-ACCESS read-write
			STATUS current
			DESCRIPTION
				"Inrterface Index"
			::= { sleV2QoS4QueueInfoControl 6 }

		
		-- 1.3.6.1.4.1.6296.102.10.2.8.1.2.7
		sleV2QoS4QueueInfoControlId OBJECT-TYPE
			SYNTAX INTEGER (1..8)
			MAX-ACCESS read-write
			STATUS current
			DESCRIPTION
				"The index of queue"
			::= { sleV2QoS4QueueInfoControl 7 }

		
		-- 1.3.6.1.4.1.6296.102.10.2.8.1.2.8
		sleV2QoS4QueueInfoControlScheduleMode OBJECT-TYPE
			SYNTAX INTEGER
				{
				sp(1),
				rr(2),
				wrr(3),
				wfq(4),
				drr(5),
				bd(6)
				}
			MAX-ACCESS read-write
			STATUS current
			DESCRIPTION
				"Schedule mode of queue.
				( V5524  : sp, wrr, wfq,
				 V5212G : sp, wrr,
				 V5424G : sp, wrr, drr
				 V6424  : sp, dwrr )
				"
			::= { sleV2QoS4QueueInfoControl 8 }

		
		-- 1.3.6.1.4.1.6296.102.10.2.8.1.2.9
		sleV2QoS4QueueInfoControlDWRRGroup OBJECT-TYPE
			SYNTAX INTEGER
				{
				undefined(0),
				group0(1),
				group1(2)
				}
			MAX-ACCESS read-write
			STATUS current
			DESCRIPTION
				"Queue dwrr group
				( V6424 )"
			::= { sleV2QoS4QueueInfoControl 9 }

		
		-- 1.3.6.1.4.1.6296.102.10.2.8.1.2.10
		sleV2QoS4QueueInfoControlMinBandwidth OBJECT-TYPE
			SYNTAX Integer32
			MAX-ACCESS read-write
			STATUS current
			DESCRIPTION
				"Min bandwidth of queue.
				( V5524  : wfq,
				 V5424G : drr,
				 V6424  : dwrr )"
			::= { sleV2QoS4QueueInfoControl 10 }

		
		-- 1.3.6.1.4.1.6296.102.10.2.8.1.2.11
		sleV2QoS4QueueInfoControlMaxBandwidth OBJECT-TYPE
			SYNTAX Integer32
			MAX-ACCESS read-write
			STATUS current
			DESCRIPTION
				"Max bandwidth of queue"
			::= { sleV2QoS4QueueInfoControl 11 }

		
		-- 1.3.6.1.4.1.6296.102.10.2.8.1.2.12
		sleV2QoS4QueueInfoControlWeight OBJECT-TYPE
			SYNTAX INTEGER (1..255)
			MAX-ACCESS read-write
			STATUS current
			DESCRIPTION
				"Weight of queue
				BCM (1..15), Marvell (6..255) 
				
				( V5524, V5212G, V5424G : wrr,
				 V6424 : dwrr )"
			::= { sleV2QoS4QueueInfoControl 12 }

		
		-- 1.3.6.1.4.1.6296.102.10.2.8.1.2.13
		sleV2QoS4QueueInfoControlMappedCoS OBJECT-TYPE
			SYNTAX INTEGER (0..7)
			MAX-ACCESS read-write
			STATUS current
			DESCRIPTION
				"Mapped cos"
			::= { sleV2QoS4QueueInfoControl 13 }

		
		-- 1.3.6.1.4.1.6296.102.10.2.8.1.2.14
		sleV2QoS4QueueInfoControlBufferEgressMinLimitUnicast OBJECT-TYPE
			SYNTAX Integer32
			MAX-ACCESS read-write
			STATUS current
			DESCRIPTION
				"Buffer Egress Min Limit for unicast Queue."
			::= { sleV2QoS4QueueInfoControl 14 }

		
		-- 1.3.6.1.4.1.6296.102.10.2.8.1.2.15
		sleV2QoS4QueueInfoControlBufferEgressMaxLimitPolicyUnicast OBJECT-TYPE
			SYNTAX INTEGER
				{
				static(1),
				dynamic(2)
				}
			MAX-ACCESS read-write
			STATUS current
			DESCRIPTION
				"Policy to Buffer Egress Max Limit for unicast Queue."
			::= { sleV2QoS4QueueInfoControl 15 }

		
		-- 1.3.6.1.4.1.6296.102.10.2.8.1.2.16
		sleV2QoS4QueueInfoControlBufferEgressMaxLimitUnicast OBJECT-TYPE
			SYNTAX Integer32
			MAX-ACCESS read-write
			STATUS current
			DESCRIPTION
				"Buffer Egress Max Limit for unicast Queue."
			::= { sleV2QoS4QueueInfoControl 16 }

		
		-- 1.3.6.1.4.1.6296.102.10.2.8.1.2.17
		sleV2QoS4QueueInfoControlBufferEgressMinLimitNonUnicast OBJECT-TYPE
			SYNTAX Integer32
			MAX-ACCESS read-write
			STATUS current
			DESCRIPTION
				"Buffer Egress Min Limit for non-unicast Queue."
			::= { sleV2QoS4QueueInfoControl 17 }

		
		-- 1.3.6.1.4.1.6296.102.10.2.8.1.2.18
		sleV2QoS4QueueInfoControlBufferEgressMaxLimitPolicyNonUnicast OBJECT-TYPE
			SYNTAX INTEGER
				{
				static(1),
				dynamic(2)
				}
			MAX-ACCESS read-write
			STATUS current
			DESCRIPTION
				"Policy to Buffer Egress Max Limit for non-unicast Queue."
			::= { sleV2QoS4QueueInfoControl 18 }

		
		-- 1.3.6.1.4.1.6296.102.10.2.8.1.2.19
		sleV2QoS4QueueInfoControlBufferEgressMaxLimitNonUnicast OBJECT-TYPE
			SYNTAX Integer32
			MAX-ACCESS read-write
			STATUS current
			DESCRIPTION
				"Buffer Egress Max Limit for non-unicast Queue."
			::= { sleV2QoS4QueueInfoControl 19 }

		
		-- 1.3.6.1.4.1.6296.102.10.2.8.1.3
		sleV2QoS4QueueInfoNotification OBJECT IDENTIFIER ::= { sleV2QoS4QueueInfo 3 }

		
		-- 1.3.6.1.4.1.6296.102.10.2.8.1.3.1
		sleV2QoS4QueueInfoChanged NOTIFICATION-TYPE
			OBJECTS { sleV2QoS4QueueInfoControlRequest, sleV2QoS4QueueInfoControlTimeStamp, sleV2QoS4QueueInfoControlReqResult, sleV2QoS4QueueInfoScheduleMode, sleV2QoS4QueueInfoDWRRGroup, 
				sleV2QoS4QueueInfoMinBandwidth, sleV2QoS4QueueInfoMaxBandwidth, sleV2QoS4QueueInfoWeight, sleV2QoS4QueueMappedCoS }
			STATUS current
			DESCRIPTION 
				"setQueueInfo"
			::= { sleV2QoS4QueueInfoNotification 1 }

		
		-- 1.3.6.1.4.1.6296.102.10.2.8.1.3.2
		sleV2QoS4QueueInfoScheduleModeChanged NOTIFICATION-TYPE
			OBJECTS { sleV2QoS4QueueInfoControlRequest, sleV2QoS4QueueInfoControlTimeStamp, sleV2QoS4QueueInfoControlReqResult, sleV2QoS4QueueInfoScheduleMode, sleV2QoS4QueueInfoDWRRGroup
				 }
			STATUS current
			DESCRIPTION 
				"setScheduleMode"
			::= { sleV2QoS4QueueInfoNotification 2 }

		
		-- 1.3.6.1.4.1.6296.102.10.2.8.1.3.3
		sleV2QoS4QueueInfoMaxBandwidthChanged NOTIFICATION-TYPE
			OBJECTS { sleV2QoS4QueueInfoControlRequest, sleV2QoS4QueueInfoControlTimeStamp, sleV2QoS4QueueInfoControlReqResult, sleV2QoS4QueueInfoControlMaxBandwidth }
			STATUS current
			DESCRIPTION 
				"setMaxBandwidth"
			::= { sleV2QoS4QueueInfoNotification 3 }

		
		-- 1.3.6.1.4.1.6296.102.10.2.8.1.3.4
		sleV2QoS4QueueInfoMinBandwidthChanged NOTIFICATION-TYPE
			OBJECTS { sleV2QoS4QueueInfoControlRequest, sleV2QoS4QueueInfoControlTimeStamp, sleV2QoS4QueueInfoControlReqResult, sleV2QoS4QueueInfoControlMinBandwidth }
			STATUS current
			DESCRIPTION 
				"setMinBandwidth"
			::= { sleV2QoS4QueueInfoNotification 4 }

		
		-- 1.3.6.1.4.1.6296.102.10.2.8.1.3.5
		sleV2QoS4QueueInfoWeightChanged NOTIFICATION-TYPE
			OBJECTS { sleV2QoS4QueueInfoControlRequest, sleV2QoS4QueueInfoControlTimeStamp, sleV2QoS4QueueInfoControlReqResult, sleV2QoS4QueueInfoWeight }
			STATUS current
			DESCRIPTION 
				"setWeight"
			::= { sleV2QoS4QueueInfoNotification 5 }

		
		-- 1.3.6.1.4.1.6296.102.10.2.8.1.3.6
		sleV2QoS4QueueInfoBufferEgressMinLimitUnicastChanged NOTIFICATION-TYPE
			OBJECTS { sleV2QoS4QueueInfoControlRequest, sleV2QoS4QueueInfoControlTimeStamp, sleV2QoS4QueueInfoControlReqResult, sleV2QoS4QueueInfoControlInterfaceIndex, sleV2QoS4QueueInfoControlId, 
				sleV2QoS4QueueInfoControlBufferEgressMinLimitUnicast }
			STATUS current
			DESCRIPTION 
				"setBufferEgressMinLimitUnicast"
			::= { sleV2QoS4QueueInfoNotification 6 }

		
		-- 1.3.6.1.4.1.6296.102.10.2.8.1.3.7
		sleV2QoS4QueueInfoBufferEgressMinLimitUnicastCleared NOTIFICATION-TYPE
			OBJECTS { sleV2QoS4QueueInfoControlRequest, sleV2QoS4QueueInfoControlTimeStamp, sleV2QoS4QueueInfoControlReqResult, sleV2QoS4QueueInfoControlInterfaceIndex, sleV2QoS4QueueInfoControlId
				 }
			STATUS current
			DESCRIPTION 
				"Description."
			::= { sleV2QoS4QueueInfoNotification 7 }

		
		-- 1.3.6.1.4.1.6296.102.10.2.8.1.3.8
		sleV2QoS4QueueInfoBufferEgressMaxLimitUnicastChanged NOTIFICATION-TYPE
			OBJECTS { sleV2QoS4QueueInfoControlRequest, sleV2QoS4QueueInfoControlTimeStamp, sleV2QoS4QueueInfoControlReqResult, sleV2QoS4QueueInfoControlInterfaceIndex, sleV2QoS4QueueInfoControlId, 
				sleV2QoS4QueueInfoControlBufferEgressMaxLimitPolicyUnicast, sleV2QoS4QueueInfoControlBufferEgressMaxLimitUnicast }
			STATUS current
			DESCRIPTION 
				"setBufferEgressMaxLimitUnicast"
			::= { sleV2QoS4QueueInfoNotification 8 }

		
		-- 1.3.6.1.4.1.6296.102.10.2.8.1.3.9
		sleV2QoS4QueueInfoBufferEgressMaxLimitUnicastCleared NOTIFICATION-TYPE
			OBJECTS { sleV2QoS4QueueInfoControlRequest, sleV2QoS4QueueInfoControlTimeStamp, sleV2QoS4QueueInfoControlReqResult, sleV2QoS4QueueInfoControlInterfaceIndex, sleV2QoS4QueueInfoControlId
				 }
			STATUS current
			DESCRIPTION 
				"clearBufferEgressMaxLimitUnicast"
			::= { sleV2QoS4QueueInfoNotification 9 }

		
		-- 1.3.6.1.4.1.6296.102.10.2.8.1.3.10
		sleV2QoS4QueueInfoBufferEgressMinLimitNonUnicastChanged NOTIFICATION-TYPE
			OBJECTS { sleV2QoS4QueueInfoControlRequest, sleV2QoS4QueueInfoControlTimeStamp, sleV2QoS4QueueInfoControlReqResult, sleV2QoS4QueueInfoControlInterfaceIndex, sleV2QoS4QueueInfoControlId, 
				sleV2QoS4QueueInfoControlBufferEgressMinLimitNonUnicast }
			STATUS current
			DESCRIPTION 
				"setBufferEgressMinLimitNonUnicast "
			::= { sleV2QoS4QueueInfoNotification 10 }

		
		-- 1.3.6.1.4.1.6296.102.10.2.8.1.3.11
		sleV2QoS4QueueInfoBufferEgressMinLimitNonUnicastCleared NOTIFICATION-TYPE
			OBJECTS { sleV2QoS4QueueInfoControlRequest, sleV2QoS4QueueInfoControlTimeStamp, sleV2QoS4QueueInfoControlReqResult, sleV2QoS4QueueInfoControlInterfaceIndex, sleV2QoS4QueueInfoControlId
				 }
			STATUS current
			DESCRIPTION 
				"clearBufferEgressMinLimitNonUnicast"
			::= { sleV2QoS4QueueInfoNotification 11 }

		
		-- 1.3.6.1.4.1.6296.102.10.2.8.1.3.12
		sleV2QoS4QueueInfoBufferEgressMaxLimitNonUnicastChanged NOTIFICATION-TYPE
			OBJECTS { sleV2QoS4QueueInfoControlRequest, sleV2QoS4QueueInfoControlTimeStamp, sleV2QoS4QueueInfoControlReqResult, sleV2QoS4QueueInfoControlInterfaceIndex, sleV2QoS4QueueInfoControlId, 
				sleV2QoS4QueueInfoControlBufferEgressMaxLimitPolicyNonUnicast, sleV2QoS4QueueInfoControlBufferEgressMaxLimitNonUnicast }
			STATUS current
			DESCRIPTION 
				"setBufferEgressMaxLimitNonUnicast"
			::= { sleV2QoS4QueueInfoNotification 12 }

		
		-- 1.3.6.1.4.1.6296.102.10.2.8.1.3.13
		sleV2QoS4QueueInfoBufferEgressMaxLimitNonUnicastCleared NOTIFICATION-TYPE
			OBJECTS { sleV2QoS4QueueInfoControlRequest, sleV2QoS4QueueInfoControlTimeStamp, sleV2QoS4QueueInfoControlReqResult, sleV2QoS4QueueInfoControlInterfaceIndex, sleV2QoS4QueueInfoControlId
				 }
			STATUS current
			DESCRIPTION 
				"clearBufferEgressMaxLimitNonUnicast"
			::= { sleV2QoS4QueueInfoNotification 13 }

		
		-- 1.3.6.1.4.1.6296.102.10.2.9
		sleV2QoS4DscpMap OBJECT IDENTIFIER ::= { sleV2QoS4 9 }

		
		-- 1.3.6.1.4.1.6296.102.10.2.9.1
		sleV2QoS4DscpMapIngress OBJECT IDENTIFIER ::= { sleV2QoS4DscpMap 1 }

		
		-- 1.3.6.1.4.1.6296.102.10.2.9.1.1
		sleV2QoS4DscpMapIngressTable OBJECT-TYPE
			SYNTAX SEQUENCE OF SleV2QoS4DscpMapIngressEntry
			MAX-ACCESS not-accessible
			STATUS current
			DESCRIPTION
				"DSCP map ingress table."
			::= { sleV2QoS4DscpMapIngress 1 }

		
		-- 1.3.6.1.4.1.6296.102.10.2.9.1.1.1
		sleV2QoS4DscpMapIngressEntry OBJECT-TYPE
			SYNTAX SleV2QoS4DscpMapIngressEntry
			MAX-ACCESS not-accessible
			STATUS current
			DESCRIPTION
				"key: sleV2QoS4DscpMapIngressDscpIndex"
			INDEX { sleV2QoS4DscpMapIngressDscpIndex }
			::= { sleV2QoS4DscpMapIngressTable 1 }

		
		SleV2QoS4DscpMapIngressEntry ::=
			SEQUENCE { 
				sleV2QoS4DscpMapIngressDscpIndex
					INTEGER,
				sleV2QoS4DscpMapIngressDscp
					OCTET STRING,
				sleV2QoS4DscpMapIngressCos
					INTEGER,
				sleV2QoS4DscpMapIngressColor
					INTEGER
			 }

		-- 1.3.6.1.4.1.6296.102.10.2.9.1.1.1.1
		sleV2QoS4DscpMapIngressDscpIndex OBJECT-TYPE
			SYNTAX INTEGER (1..64)
			MAX-ACCESS read-only
			STATUS current
			DESCRIPTION
				"Ingress DSCP mapping index.
				The index value of 1~ 64 mean 0 ~ 63 of the DSCP."
			::= { sleV2QoS4DscpMapIngressEntry 1 }

		
		-- 1.3.6.1.4.1.6296.102.10.2.9.1.1.1.2
		sleV2QoS4DscpMapIngressDscp OBJECT-TYPE
			SYNTAX OCTET STRING (SIZE (0..63))
			MAX-ACCESS read-only
			STATUS current
			DESCRIPTION
				"DSCP value."
			::= { sleV2QoS4DscpMapIngressEntry 2 }

		
		-- 1.3.6.1.4.1.6296.102.10.2.9.1.1.1.3
		sleV2QoS4DscpMapIngressCos OBJECT-TYPE
			SYNTAX INTEGER (0..7)
			MAX-ACCESS read-only
			STATUS current
			DESCRIPTION
				"The Class of Service."
			::= { sleV2QoS4DscpMapIngressEntry 3 }

		
		-- 1.3.6.1.4.1.6296.102.10.2.9.1.1.1.4
		sleV2QoS4DscpMapIngressColor OBJECT-TYPE
			SYNTAX INTEGER
				{
				green(1),
				yellow(2),
				red(3)
				}
			MAX-ACCESS read-only
			STATUS current
			DESCRIPTION
				"Specify color by Internal DP."
			::= { sleV2QoS4DscpMapIngressEntry 4 }

		
		-- 1.3.6.1.4.1.6296.102.10.2.9.1.2
		sleV2QoS4DscpMapIngressControl OBJECT IDENTIFIER ::= { sleV2QoS4DscpMapIngress 2 }

		
		-- 1.3.6.1.4.1.6296.102.10.2.9.1.2.1
		sleV2QoS4DscpMapIngressControlRequest OBJECT-TYPE
			SYNTAX INTEGER { setDscpMapIngress(1) }
			MAX-ACCESS read-write
			STATUS current
			DESCRIPTION
				"The request of a user command"
			::= { sleV2QoS4DscpMapIngressControl 1 }

		
		-- 1.3.6.1.4.1.6296.102.10.2.9.1.2.2
		sleV2QoS4DscpMapIngressControlStatus OBJECT-TYPE
			SYNTAX SleControlStatusType
			MAX-ACCESS read-only
			STATUS current
			DESCRIPTION
				"The status of user command"
			::= { sleV2QoS4DscpMapIngressControl 2 }

		
		-- 1.3.6.1.4.1.6296.102.10.2.9.1.2.3
		sleV2QoS4DscpMapIngressControlTimer OBJECT-TYPE
			SYNTAX Gauge32
			MAX-ACCESS read-write
			STATUS current
			DESCRIPTION
				"The maximum time for the manager for a long running user command"
			::= { sleV2QoS4DscpMapIngressControl 3 }

		
		-- 1.3.6.1.4.1.6296.102.10.2.9.1.2.4
		sleV2QoS4DscpMapIngressControlTimeStamp OBJECT-TYPE
			SYNTAX TimeTicks
			MAX-ACCESS read-only
			STATUS current
			DESCRIPTION
				"The time stamp of the last command(end of command)"
			::= { sleV2QoS4DscpMapIngressControl 4 }

		
		-- 1.3.6.1.4.1.6296.102.10.2.9.1.2.5
		sleV2QoS4DscpMapIngressControlReqResult OBJECT-TYPE
			SYNTAX SleControlRequestResultType
			MAX-ACCESS read-only
			STATUS current
			DESCRIPTION
				"The result of the last user command"
			::= { sleV2QoS4DscpMapIngressControl 5 }

		
		-- 1.3.6.1.4.1.6296.102.10.2.9.1.2.6
		sleV2QoS4DscpMapIngressControlDscpIndex OBJECT-TYPE
			SYNTAX INTEGER (1..64)
			MAX-ACCESS read-write
			STATUS current
			DESCRIPTION
				"Ingress DSCP mapping index.
				The index value of 1~ 64 mean 0 ~ 63 of the DSCP."
			::= { sleV2QoS4DscpMapIngressControl 6 }

		
		-- 1.3.6.1.4.1.6296.102.10.2.9.1.2.7
		sleV2QoS4DscpMapIngressControlDscp OBJECT-TYPE
			SYNTAX INTEGER (0..63)
			MAX-ACCESS read-write
			STATUS current
			DESCRIPTION
				"DSCP value."
			::= { sleV2QoS4DscpMapIngressControl 7 }

		
		-- 1.3.6.1.4.1.6296.102.10.2.9.1.2.8
		sleV2QoS4DscpMapIngressControlCos OBJECT-TYPE
			SYNTAX INTEGER (0..7)
			MAX-ACCESS read-write
			STATUS current
			DESCRIPTION
				"The Class of Service."
			::= { sleV2QoS4DscpMapIngressControl 8 }

		
		-- 1.3.6.1.4.1.6296.102.10.2.9.1.2.9
		sleV2QoS4DscpMapIngressControlColor OBJECT-TYPE
			SYNTAX INTEGER
				{
				green(1),
				yellow(2),
				red(3)
				}
			MAX-ACCESS read-write
			STATUS current
			DESCRIPTION
				"Specify color by Internal DP."
			::= { sleV2QoS4DscpMapIngressControl 9 }

		
		-- 1.3.6.1.4.1.6296.102.10.2.9.1.3
		sleV2QoS4DscpMapIngressNotification OBJECT IDENTIFIER ::= { sleV2QoS4DscpMapIngress 3 }

		
		-- 1.3.6.1.4.1.6296.102.10.2.9.1.3.1
		sleV2QoS4DscpMapIngressChanged NOTIFICATION-TYPE
			OBJECTS { sleV2QoS4DscpMapIngressControlRequest, sleV2QoS4DscpMapIngressControlTimeStamp, sleV2QoS4DscpMapIngressControlReqResult, sleV2QoS4DscpMapIngressControlDscpIndex, sleV2QoS4DscpMapIngressControlDscp, 
				sleV2QoS4DscpMapIngressControlCos, sleV2QoS4DscpMapIngressControlColor }
			STATUS current
			DESCRIPTION 
				"Description."
			::= { sleV2QoS4DscpMapIngressNotification 1 }

		
		-- 1.3.6.1.4.1.6296.102.10.2.9.2
		sleV2QoS4DscpMapTunnel OBJECT IDENTIFIER ::= { sleV2QoS4DscpMap 2 }

		
		-- 1.3.6.1.4.1.6296.102.10.2.9.2.1
		sleV2QoS4DscpMapTunnelTable OBJECT-TYPE
			SYNTAX SEQUENCE OF SleV2QoS4DscpMapTunnelEntry
			MAX-ACCESS not-accessible
			STATUS current
			DESCRIPTION
				"DSCP map tunnel table."
			::= { sleV2QoS4DscpMapTunnel 1 }

		
		-- 1.3.6.1.4.1.6296.102.10.2.9.2.1.1
		sleV2QoS4DscpMapTunnelEntry OBJECT-TYPE
			SYNTAX SleV2QoS4DscpMapTunnelEntry
			MAX-ACCESS not-accessible
			STATUS current
			DESCRIPTION
				"key: sleV2QoS4DscpMapTunnelPriority, sleV2QoS4DscpMapTunnelColor"
			INDEX { sleV2QoS4DscpMapTunnelPriority, sleV2QoS4DscpMapTunnelColor }
			::= { sleV2QoS4DscpMapTunnelTable 1 }

		
		SleV2QoS4DscpMapTunnelEntry ::=
			SEQUENCE { 
				sleV2QoS4DscpMapTunnelPriority
					INTEGER,
				sleV2QoS4DscpMapTunnelColor
					INTEGER,
				sleV2QoS4DscpMapTunnelDscp
					INTEGER
			 }

		-- 1.3.6.1.4.1.6296.102.10.2.9.2.1.1.1
		sleV2QoS4DscpMapTunnelPriority OBJECT-TYPE
			SYNTAX INTEGER (1..8)
			MAX-ACCESS read-only
			STATUS current
			DESCRIPTION
				"Internal packet priority.
				The index value of 1 ~ 8 mean 0 ~ 7 of the priority."
			::= { sleV2QoS4DscpMapTunnelEntry 1 }

		
		-- 1.3.6.1.4.1.6296.102.10.2.9.2.1.1.2
		sleV2QoS4DscpMapTunnelColor OBJECT-TYPE
			SYNTAX INTEGER
				{
				green(1),
				yellow(2),
				red(3)
				}
			MAX-ACCESS read-only
			STATUS current
			DESCRIPTION
				"Specify color by Internal DP."
			::= { sleV2QoS4DscpMapTunnelEntry 2 }

		
		-- 1.3.6.1.4.1.6296.102.10.2.9.2.1.1.3
		sleV2QoS4DscpMapTunnelDscp OBJECT-TYPE
			SYNTAX INTEGER (0..63)
			MAX-ACCESS read-only
			STATUS current
			DESCRIPTION
				"DSCP value."
			::= { sleV2QoS4DscpMapTunnelEntry 3 }

		
		-- 1.3.6.1.4.1.6296.102.10.2.9.2.2
		sleV2QoS4DscpMapTunnelControl OBJECT IDENTIFIER ::= { sleV2QoS4DscpMapTunnel 2 }

		
		-- 1.3.6.1.4.1.6296.102.10.2.9.2.2.1
		sleV2QoS4DscpMapTunnelControlRequest OBJECT-TYPE
			SYNTAX INTEGER { setDscpMapTunnel(1) }
			MAX-ACCESS read-write
			STATUS current
			DESCRIPTION
				"The request of a user command"
			::= { sleV2QoS4DscpMapTunnelControl 1 }

		
		-- 1.3.6.1.4.1.6296.102.10.2.9.2.2.2
		sleV2QoS4DscpMapTunnelControlStatus OBJECT-TYPE
			SYNTAX SleControlStatusType
			MAX-ACCESS read-only
			STATUS current
			DESCRIPTION
				"The status of user command"
			::= { sleV2QoS4DscpMapTunnelControl 2 }

		
		-- 1.3.6.1.4.1.6296.102.10.2.9.2.2.3
		sleV2QoS4DscpMapTunnelControlTimer OBJECT-TYPE
			SYNTAX Gauge32
			MAX-ACCESS read-write
			STATUS current
			DESCRIPTION
				"The maximum time for the manager for a long running user command"
			::= { sleV2QoS4DscpMapTunnelControl 3 }

		
		-- 1.3.6.1.4.1.6296.102.10.2.9.2.2.4
		sleV2QoS4DscpMapTunnelControlTimeStamp OBJECT-TYPE
			SYNTAX TimeTicks
			MAX-ACCESS read-only
			STATUS current
			DESCRIPTION
				"The time stamp of the last command(end of command)"
			::= { sleV2QoS4DscpMapTunnelControl 4 }

		
		-- 1.3.6.1.4.1.6296.102.10.2.9.2.2.5
		sleV2QoS4DscpMapTunnelControlReqResult OBJECT-TYPE
			SYNTAX SleControlRequestResultType
			MAX-ACCESS read-only
			STATUS current
			DESCRIPTION
				"The result of the last user command"
			::= { sleV2QoS4DscpMapTunnelControl 5 }

		
		-- 1.3.6.1.4.1.6296.102.10.2.9.2.2.6
		sleV2QoS4DscpMapTunnelControlPriority OBJECT-TYPE
			SYNTAX INTEGER (1..8)
			MAX-ACCESS read-write
			STATUS current
			DESCRIPTION
				"Internal packet priority.
				The index value of 1 ~ 8 mean 0 ~ 7 of the priority."
			::= { sleV2QoS4DscpMapTunnelControl 6 }

		
		-- 1.3.6.1.4.1.6296.102.10.2.9.2.2.7
		sleV2QoS4DscpMapTunnelControlColor OBJECT-TYPE
			SYNTAX INTEGER
				{
				green(1),
				yellow(2),
				red(3)
				}
			MAX-ACCESS read-write
			STATUS current
			DESCRIPTION
				"Specify color by Internal DP."
			::= { sleV2QoS4DscpMapTunnelControl 7 }

		
		-- 1.3.6.1.4.1.6296.102.10.2.9.2.2.8
		sleV2QoS4DscpMapTunnelControlDscp OBJECT-TYPE
			SYNTAX INTEGER (0..63)
			MAX-ACCESS read-write
			STATUS current
			DESCRIPTION
				"DSCP value."
			::= { sleV2QoS4DscpMapTunnelControl 8 }

		
		-- 1.3.6.1.4.1.6296.102.10.2.9.2.3
		sleV2QoS4DscpMapTunnelNotification OBJECT IDENTIFIER ::= { sleV2QoS4DscpMapTunnel 3 }

		
		-- 1.3.6.1.4.1.6296.102.10.2.9.2.3.1
		sleV2QoS4DscpMapTunnelChanged NOTIFICATION-TYPE
			OBJECTS { sleV2QoS4DscpMapTunnelControlRequest, sleV2QoS4DscpMapTunnelControlTimeStamp, sleV2QoS4DscpMapTunnelControlReqResult, sleV2QoS4DscpMapTunnelControlPriority, sleV2QoS4DscpMapTunnelControlColor, 
				sleV2QoS4DscpMapTunnelControlDscp }
			STATUS current
			DESCRIPTION 
				"Description."
			::= { sleV2QoS4DscpMapTunnelNotification 1 }

		
		-- 1.3.6.1.4.1.6296.102.10.3
		sleV2QoS6 OBJECT IDENTIFIER ::= { sleV2QoS 3 }

		
		-- 1.3.6.1.4.1.6296.102.10.4
		sleV2QoSGroup OBJECT-GROUP
			OBJECTS { sleV2QoS4FlowIndex, sleV2QoS4FlowName, sleV2QoS4FlowEthernetType, sleV2QoS4FlowDstMacAddr, sleV2QoS4FlowDstMacAddrMask, 
				sleV2QoS4FlowSrcMacAddr, sleV2QoS4FlowSrcMacAddrMask, sleV2QoS4Flow8021p, sleV2QoS4FlowSrcIpAddr, sleV2QoS4FlowSrcIpAddrMask, 
				sleV2QoS4FlowDstIpAddr, sleV2QoS4FlowDstIpAddrMask, sleV2QoS4FlowPktLen, sleV2QoS4FlowProtocolType, sleV2QoS4FlowTcpFlag, 
				sleV2QoS4FlowIcmpType, sleV2QoS4FlowIcmpCode, sleV2QoS4ClassIndex, sleV2QoS4ClassName, sleV2QoS4ClassFlowCnt, 
				sleV2QoS4ClassFlowIndex, sleV2QoS4PolicerIndex, sleV2QoS4PolicerName, sleV2QoS4PolicerRateLimit, sleV2QoS4PolicerColorMode, 
				sleV2QoS4PolicerColorAwareMode, sleV2QoS4PolicerColorCIR, sleV2QoS4PolicerColorCBS, sleV2QoS4PolicerColorPIR, sleV2QoS4PolicerColorPBS, 
				sleV2QoS4PolicerColorEBS, sleV2QoS4PolicerColorRedAction, sleV2QoS4PolicerColorYellowAction, sleV2QoS4PolicerColorGreenAction, sleV2QoS4PolicerCounterMode, 
				sleV2QoS4PolicyIndex, sleV2QoS4PolicyName, sleV2QoS4PolicyPriority, sleV2QoS4PolicyIngressPorts, sleV2QoS4PolicyEgressPorts, 
				sleV2QoS4PolicyVlan, sleV2QoS4PolicyMatchFlag, sleV2QoS4PolicyMatchVlan, sleV2QoS4PolicyMatchRedirectVlan, sleV2QoS4PolicyMatchRedirectPort, 
				sleV2QoS4PolicyMatchMarkMode, sleV2QoS4PolicyMatchQueue, sleV2QoS4PolicyMatchDp, sleV2QoS4PolicyMatchCoS, sleV2QoS4PolicyMatchDscp, 
				sleV2QoS4PolicyMatchIpPrecedence, sleV2QoS4PolicyMatchDstMacOrEgressPorts, sleV2QoS4PolicyMatchDstMac, sleV2QoS4PolicyMatchEgressPorts, sleV2QoS4PolicyNomatchFlag, 
				sleV2QoS4PolicyNomatchRedirectPort, sleV2QoS4PolicyNomatchCoS, sleV2QoS4PolicyNomatchDscp, sleV2QoS4PolicyNomatchIpPrecedence, sleV2QoS4FlowTcpSrcStartPort, 
				sleV2QoS4FlowTcpSrcEndPort, sleV2QoS4FlowTcpDstStartPort, sleV2QoS4PolicyFlowCnt, sleV2QoS4PolicerColorType, sleV2QoS4ClassFlowID, 
				sleV2QoS4PolicyClassCnt, sleV2QoS4FlowTcpDstEndPort, sleV2QoS4FlowUdpSrcStartPort, sleV2QoS4FlowUdpSrcEndPort, sleV2QoS4FlowUdpDstStartPort, 
				sleV2QoS4FlowUdpDstEndPort, sleV2QoS4PolicyPolicerIndex, sleV2QoS4PolicyFlowClassID, sleV2QoS4RemarkL2ColorIndex, sleV2QoS4RemarkL2QueueCoSIndex, 
				sleV2QoS4RemarkL2Queue, sleV2QoS4RemarkL2Dp, sleV2QoS4RemarkL2CoS, sleV2QoS4RemarkL2Dscp, sleV2QoS4RemarkL3ColorIndex, 
				sleV2QoS4RemarkL3DSCPIndex, sleV2QoS4RemarkL3Queue, sleV2QoS4RemarkL3Dp, sleV2QoS4RemarkL3CoS, sleV2QoS4RemarkL3Dscp, 
				sleV2QoS4PolicyFlowClassType, sleV2QoS4PolicerMeterMode, sleV2QoS4PolicyCounterRedBytes, sleV2QoS4PolicyCounterYellowBytes, sleV2QoS4PolicyCounterGreenBytes, 
				sleV2QoS4PolicyCounterValue, sleV2QoS4ClassFlowControlFlowIndex, sleV2QoS4PolicyFlowClassName, sleV2QoS4ClassFlowName, sleV2QoS4ClassPolicyIndex, 
				sleV2QoS4ClassPolicyID, sleV2QoS4ClassPolicyName, sleV2QoS4FlowPolicyName, sleV2QoS4FlowPolicyID, sleV2QoS4FlowPolicyIndex, 
				sleV2QoS4FlowClassName, sleV2QoS4FlowClassID, sleV2QoS4FlowClassIndex, sleV2QoS4REDProfileDp1MinThres, sleV2QoS4REDProfileDp1MaxThres, 
				sleV2QoS4REDProfileDp1Prob, sleV2QoS4REDProfileDp2MinThres, sleV2QoS4REDProfileDp2MaxThres, sleV2QoS4REDProfileDp2Prob, sleV2QoS4REDProfileWeight, 
				sleV2QoS4REDProfileDp0Prob, sleV2QoS4REDProfileDp0MaxThres, sleV2QoS4REDProfileDp0MinThres, sleV2QoS4REDProfileQueueId, sleV2QoS4REDProfileId, 
				sleV2QoS4PortREDInfoInterfaceIndex, sleV2QoS4PortREDInfoEnable, sleV2QoS4PortREDInfoProfileId, sleV2QoS4QueueInfoInterfaceIndex, sleV2QoS4QueueInfoId, 
				sleV2QoS4QueueInfoScheduleMode, sleV2QoS4QueueInfoDWRRGroup, sleV2QoS4QueueInfoMinBandwidth, sleV2QoS4QueueInfoMaxBandwidth, sleV2QoS4QueueInfoWeight, 
				sleV2QoS4QueueMappedCoS, sleV2QoS4FlowHdrlen, sleV2QoS4PolicyRedirBlackhole, sleV2QoS4FlowHdrError, sleV2QoS4PolicerAvrgCounterMode, 
				sleV2QoS4PolicyAvrg5SecCounterValue, sleV2QoS4PolicyAvrg1minCounterValue, sleV2QoS4PolicyAvrg10minCounterValue, sleV2QoS4PolicerMaxBandwidth, sleV2QoS4PolicerMinBandwidth, 
				sleV2QoS4FlowInnerVlan, sleV2QoS4FlowInner8021p, sleV2QoS4FlowControlRequest, sleV2QoS4FlowControlStatus, sleV2QoS4FlowControlTimer, 
				sleV2QoS4FlowControlTimeStamp, sleV2QoS4FlowControlReqResult, sleV2QoS4FlowControlIndex, sleV2QoS4FlowControlName, sleV2QoS4FlowControlEthernetType, 
				sleV2QoS4FlowControlSrcMacAddr, sleV2QoS4FlowControlSrcMacAddrMask, sleV2QoS4FlowControlDstMacAddr, sleV2QoS4FlowControlDstMacAddrMask, sleV2QoS4FlowControl8021p, 
				sleV2QoS4FlowControlSrcIpAddr, sleV2QoS4FlowControlSrcIpAddrMask, sleV2QoS4FlowControlDstIpAddr, sleV2QoS4FlowControlDstIpAddrMask, sleV2QoS4FlowControlIpPktPriorityType, 
				sleV2QoS4FlowControlIpPktPriority, sleV2QoS4FlowControlPktLen, sleV2QoS4FlowControlProtocolType, sleV2QoS4FlowControlTcpSrcStartPort, sleV2QoS4FlowControlTcpSrcEndPort, 
				sleV2QoS4FlowControlTcpDstStartPort, sleV2QoS4FlowControlTcpDstEndPort, sleV2QoS4FlowControlTcpFlag, sleV2QoS4FlowControlUdpSrcStartPort, sleV2QoS4FlowControlUdpSrcEndPort, 
				sleV2QoS4FlowControlUdpDstStartPort, sleV2QoS4FlowControlUdpDstEndPort, sleV2QoS4FlowControlIcmpType, sleV2QoS4FlowControlIcmpCode, sleV2QoS4FlowControlHdrlen, 
				sleV2QoS4FlowControlHdrError, sleV2QoS4FlowControlInnerVlan, sleV2QoS4FlowControlInner8021p, sleV2QoS4ClassControlRequest, sleV2QoS4ClassControlStatus, 
				sleV2QoS4ClassControlTimer, sleV2QoS4ClassControlTimeStamp, sleV2QoS4ClassControlReqResult, sleV2QoS4ClassControlIndex, sleV2QoS4ClassControlName, 
				sleV2QoS4ClassFlowControlRequest, sleV2QoS4ClassFlowControlStatus, sleV2QoS4ClassFlowControlTimer, sleV2QoS4ClassFlowControlTimeStamp, sleV2QoS4ClassFlowControlReqResult, 
				sleV2QoS4ClassFlowControlClassIndex, sleV2QoS4ClassFlowControlFlowID, sleV2QoS4PolicerColorRedDscp, sleV2QoS4PolicerColorYellowDscp, sleV2QoS4PolicerColorGreenDscp, 
				sleV2QoS4PolicerControlRequest, sleV2QoS4PolicerControlStatus, sleV2QoS4PolicerControlTimer, sleV2QoS4PolicerControlTimeStamp, sleV2QoS4PolicerControlReqResult, 
				sleV2QoS4PolicerControlIndex, sleV2QoS4PolicerControlName, sleV2QoS4PolicerControlMeterMode, sleV2QoS4PolicerControlRateLimit, sleV2QoS4PolicerControlColorType, 
				sleV2QoS4PolicerControlColorMode, sleV2QoS4PolicerControlColorAwareMode, sleV2QoS4PolicerControlColorCIR, sleV2QoS4PolicerControlColorCBS, sleV2QoS4PolicerControlColorPIR, 
				sleV2QoS4PolicerControlColorPBS, sleV2QoS4PolicerControlColorEBS, sleV2QoS4PolicerControlColorRedAction, sleV2QoS4PolicerControlColorYellowAction, sleV2QoS4PolicerControlColorGreenAction, 
				sleV2QoS4PolicerControlRemarkLayerMode, sleV2QoS4PolicerControlRemarkMode, sleV2QoS4PolicerControlCounterMode, sleV2QoS4PolicerControlAvrgCounterMode, sleV2QoS4PolicerControlMinBandwidth, 
				sleV2QoS4PolicerControlMaxBandwidth, sleV2QoS4PolicerControlColorRedDscp, sleV2QoS4PolicerControlColorYellowDscp, sleV2QoS4PolicerControlColorGreenDscp, sleV2QoS4PolicyControlRequest, 
				sleV2QoS4PolicyControlStatus, sleV2QoS4PolicyControlTimer, sleV2QoS4PolicyControlTimeStamp, sleV2QoS4PolicyControlReqResult, sleV2QoS4PolicyControlIndex, 
				sleV2QoS4PolicyControlName, sleV2QoS4PolicyControlPolicerIndex, sleV2QoS4PolicyControlPriority, sleV2QoS4PolicyControlIngressPorts, sleV2QoS4PolicyControlEgressPorts, 
				sleV2QoS4PolicyControlVlan, sleV2QoS4PolicyControlMatchFlag, sleV2QoS4PolicyControlMatchVlan, sleV2QoS4PolicyControlMatchRedirectVlan, sleV2QoS4PolicyControlMatchRedirectPort, 
				sleV2QoS4PolicyControlMatchMarkMode, sleV2QoS4PolicyControlMatchQueue, sleV2QoS4PolicyControlMatchDp, sleV2QoS4PolicyControlMatchCoS, sleV2QoS4PolicyControlMatchDscp, 
				sleV2QoS4PolicyControlMatchIpPrecedence, sleV2QoS4PolicyControlMatchDstMacOrEgressPorts, sleV2QoS4PolicyControlMatchDstMac, sleV2QoS4PolicyControlMatchEgressPorts, sleV2QoS4PolicyControlNomatchFlag, 
				sleV2QoS4PolicyControlNomatchRedirectPort, sleV2QoS4PolicyControlNomatchCoS, sleV2QoS4PolicyControlNomatchDscp, sleV2QoS4PolicyControlNomatchIpPrecedence, sleV2QoS4PolicyControlMatchRedirBlackhole, 
				sleV2QoS4PolicyFlowClassControlRequest, sleV2QoS4PolicyFlowClassControlStatus, sleV2QoS4PolicyFlowClassControlTimer, sleV2QoS4PolicyFlowClassControlTimeStamp, sleV2QoS4PolicyFlowClassControlReqResult, 
				sleV2QoS4PolicyFlowClassControlPolicyIndex, sleV2QoS4PolicyFlowClassControlIndex, sleV2QoS4PolicyFlowClassControlType, sleV2QoS4PolicyFlowClassControlFlowID, sleV2QoS4PolicyFlowClassControlClassID, 
				sleV2QoS4RemarkLayer2Mode, sleV2QoS4RemarkMode, sleV2QoS4RemarkControlRequest, sleV2QoS4RemarkControlStatus, sleV2QoS4RemarkControlTimer, 
				sleV2QoS4RemarkControlTimStamp, sleV2QoS4RemarkControlReqResult, sleV2QoS4RemarkControlLayer2Mode, sleV2QoS4RemarkControlMode, sleV2QoS4RemarkL3ControlRequest, 
				sleV2QoS4RemarkL3ControlStatus, sleV2QoS4RemarkL3ControlTimer, sleV2QoS4RemarkL3ControlTimeStamp, sleV2QoS4RemarkL3ControlReqResult, sleV2QoS4RemarkL3ControlColorIndex, 
				sleV2QoS4RemarkL3ControlDSCPIndex, sleV2QoS4RemarkL3ControlQueue, sleV2QoS4RemarkL3ControlDp, sleV2QoS4RemarkL3ControlCoS, sleV2QoS4RemarkL3ControlDscp, 
				sleV2QoS4RemarkL2ControlRequest, sleV2QoS4RemarkL2ControlStatus, sleV2QoS4RemarkL2ControlTimer, sleV2QoS4RemarkL2ControlTimeStamp, sleV2QoS4RemarkL2ControlReqResult, 
				sleV2QoS4RemarkL2ControlColorIndex, sleV2QoS4RemarkL2ControlQueueCoSIndex, sleV2QoS4RemarkL2ControlQueue, sleV2QoS4RemarkL2ControlDp, sleV2QoS4RemarkL2ControlCoS, 
				sleV2QoS4RemarkL2ControlDscp, sleV2QoS4REDProfileControlRequest, sleV2QoS4REDProfileControlStatus, sleV2QoS4REDProfileControlTimer, sleV2QoS4REDProfileControlTimeStamp, 
				sleV2QoS4REDProfileControlReqResult, sleV2QoS4REDProfileControlId, sleV2QoS4REDProfileControlQueueId, sleV2QoS4REDProfileControlDp0MinThres, sleV2QoS4REDProfileControlDp0MaxThres, 
				sleV2QoS4REDProfileControlDp0Prob, sleV2QoS4REDProfileControlDp1MinThres, sleV2QoS4REDProfileControlDp1MaxThres, sleV2QoS4REDProfileControlDp1Prob, sleV2QoS4REDProfileControlDp2MinThres, 
				sleV2QoS4REDProfileControlDp2MaxThres, sleV2QoS4REDProfileControlDp2Prob, sleV2QoS4REDProfileControlWeight, sleV2QoS4PortREDInfoControlRequest, sleV2QoS4PortREDInfoControlStatus, 
				sleV2QoS4PortREDInfoControlTimer, sleV2QoS4PortREDInfoControlTimeStamp, sleV2QoS4PortREDInfoControlReqResult, sleV2QoS4PortREDInfoControlInterfaceIndex, sleV2QoS4PortREDInfoControlEnable, 
				sleV2QoS4PortREDInfoControlProfileId, sleV2QoS4QueueInfoControlRequest, sleV2QoS4QueueInfoControlStatus, sleV2QoS4QueueInfoControlTimer, sleV2QoS4QueueInfoControlTimeStamp, 
				sleV2QoS4QueueInfoControlReqResult, sleV2QoS4QueueInfoControlInterfaceIndex, sleV2QoS4QueueInfoControlId, sleV2QoS4QueueInfoControlScheduleMode, sleV2QoS4QueueInfoControlDWRRGroup, 
				sleV2QoS4QueueInfoControlMinBandwidth, sleV2QoS4QueueInfoControlMaxBandwidth, sleV2QoS4QueueInfoControlWeight, sleV2QoS4QueueInfoControlMappedCoS, sleV2QoS4PolicyIngressTunnelIfIndex, 
				sleV2QoS4PolicyEgressTunnelIfIndex, sleV2QoS4PolicyControlIngressTunnelIfIndex, sleV2Qo4SPolicyControlEgressTunnelIfIndex, sleV2QoS4DscpMapIngressDscpIndex, sleV2QoS4DscpMapIngressDscp, 
				sleV2QoS4DscpMapIngressCos, sleV2QoS4DscpMapIngressColor, sleV2QoS4DscpMapIngressControlRequest, sleV2QoS4DscpMapIngressControlStatus, sleV2QoS4DscpMapIngressControlTimer, 
				sleV2QoS4DscpMapIngressControlTimeStamp, sleV2QoS4DscpMapIngressControlReqResult, sleV2QoS4DscpMapIngressControlDscpIndex, sleV2QoS4DscpMapIngressControlDscp, sleV2QoS4DscpMapIngressControlCos, 
				sleV2QoS4DscpMapIngressControlColor, sleV2QoS4DscpMapTunnelPriority, sleV2QoS4DscpMapTunnelColor, sleV2QoS4DscpMapTunnelDscp, sleV2QoS4DscpMapTunnelControlRequest, 
				sleV2QoS4DscpMapTunnelControlStatus, sleV2QoS4DscpMapTunnelControlTimer, sleV2QoS4DscpMapTunnelControlTimeStamp, sleV2QoS4DscpMapTunnelControlReqResult, sleV2QoS4DscpMapTunnelControlPriority, 
				sleV2QoS4DscpMapTunnelControlColor, sleV2QoS4DscpMapTunnelControlDscp, sleV2QoS4BaseFlowMode, sleV2QoS4BaseControlRequest, sleV2QoS4BaseControlStatus, 
				sleV2QoS4BaseControlTimer, sleV2QoS4BaseControlTimeStamp, sleV2QoS4BaseControlResult, sleV2QoS4BaseControlFlowMode, sleV2QoS4PolicyCounterElapsedTimeAfterClear, 
				sleV2QoS4PolicerMatchCounterName, sleV2QoS4PolicerMatchCounterDesc, sleV2QoS4PolicerMatchCounterValue, sleV2QoS4FlowMacFlag, sleV2QoS4FlowIpFlag, 
				sleV2QoS4FlowControlMacFlag, sleV2QoS4FlowControlIpFlag, sleV2QoS4PolicerColorRedCos, sleV2QoS4PolicerColorYellowCos, sleV2QoS4PolicerColorGreenCos, 
				sleV2QoS4PolicerControlColorRedCos, sleV2QoS4PolicerControlColorYellowCos, sleV2QoS4PolicerControlColorGreenCos, sleV2QoS4PolicerColorRedCosType, sleV2QoS4PolicerColorYellowCosType, 
				sleV2QoS4PolicerControlColorRedCosType, sleV2QoS4PolicerControlColorYellowCosType, sleV2QoS4PolicerControlColorGreenCosType, sleV2QoS4FlowMacDlf, sleV2QoS4FlowControlMacDlf, 
				sleV2QoS4PolicyStage, sleV2QoS4PolicyControlStage, sleV2QoS4PolicyIngressPortsFlag, sleV2QoS4PolicyEgressPortsFlag, sleV2QoS4PolicyControlIngressPortsFlag, 
				sleV2QoS4PolicyControlEgressPortsFlag, sleV2QoS4PolicyInnerVlanAction, sleV2QoS4PolicyOuterVlanAction, sleV2QoS4PolicyInnerVlan, sleV2QoS4PolicyOuterVlan, 
				sleV2QoS4PolicyControlInnerVlanAction, sleV2QoS4PolicyControlOuterVlanAction, sleV2QoS4PolicyControlInnerVlan, sleV2QoS4PolicyControlOuterVlan, sleV2QoS4PolicyIFDirection, 
				sleV2QoS4PolicyIFControlRequest, sleV2QoS4PolicyIFControlStatus, sleV2QoS4PolicyIFControlTimer, sleV2QoS4PolicyIFControlTimeStamp, sleV2QoS4PolicyIFControlReqResult, 
				sleV2QoS4PolicyIFControlIfindex, sleV2QoS4PolicyIFControlPolicyIndex, sleV2QoS4PolicyIFControlDirection, sleV2QoS4PolicyMatchPbrNextHopSecondary, sleV2QoS4PolicyMatchPbrNextHopVerifyReach, 
				sleV2QoS4PolicyControlMatchPbrNextHopSecondary, sleV2QoS4PolicyControlMatchPbrNextHopVerifyReach, sleV2QoS4FlowTagType, sleV2QoS4FlowControlTagType, sleV2QoS4FlowInPktTagVid, 
				sleV2QoS4FlowInPktTagCfi, sleV2QoS4FlowInPktTagCoS, sleV2QoS4FlowOutPktTagVid, sleV2QoS4FlowOutPktTagCfi, sleV2QoS4FlowOutPktTagCoS, 
				sleV2QoS4FlowFlowAlias, sleV2QoS4FlowControlPktTagVid, sleV2QoS4FlowControlPktTagCfi, sleV2QoS4FlowControlPktTagCoS, sleV2QoS4FlowControlFlowAlias, 
				sleV2QoS4PolicyMatchFlowAlias, sleV2QoS4PolicyControlMatchFlowAlias, sleV2QoS4PolicyMatchInnerVlanCosReplace, sleV2QoS4PolicyMatchInnerVlanCfiReplace, sleV2QoS4PolicyMatchOuterVlanCosReplace, 
				sleV2QoS4PolicyMatchOuterVlanCfiReplace, sleV2QoS4PolicyControlMatchInnerVlanCosReplace, sleV2QoS4PolicyControlMatchInnerVlanCfiReplace, sleV2QoS4PolicyControlMatchOuterVlanCosReplace, sleV2QoS4PolicyControlMatchOuterVlanCfiReplace, 
				sleV2QoS4ClassFlowClassName, sleV2QoS4ClassFlowControlClassName, sleV2QoSFlowInetAddrType, sleV2QoSFlowSrcInetAddr, sleV2QoSFlowDstInetAddr, 
				sleV2QoSFlowSrcInetAddrLen, sleV2QoSFlowDstInetAddrLen, sleV2QoSFlowTrafficClass, sleV2QoSFlowFlowLabel, sleV2QoSFlowControlInetAddrType, 
				sleV2QoSFlowControlSrcInetAddr, sleV2QoSFlowControlDstInetAddr, sleV2QoSFlowControlSrcInetAddrLen, sleV2QoSFlowControlDstInetAddrLen, sleV2QoSFlowControlTrafficClass, 
				sleV2QoSFlowControlFlowLabel, sleV2QoS4FlowOuterVlan, sleV2QoS4FlowOuter8021p, sleV2QoS4FlowOnuCircuitId, sleV2QoS4FlowControlOuterVlan, 
				sleV2QoS4FlowControlOuter8021p, sleV2QoS4FlowControlOnuCircuitId, sleV2QoS4QueueInfoBufferEgressMinLimitUnicast, sleV2QoS4QueueInfoBufferEgressMaxLimitPolicyUnicast, sleV2QoS4QueueInfoBufferEgressMaxLimitUnicast, 
				sleV2QoS4QueueInfoBufferEgressMinLimitNonUnicast, sleV2QoS4QueueInfoBufferEgressMaxLimitPolicyNonUnicast, sleV2QoS4QueueInfoBufferEgressMaxLimitNonUnicast, sleV2QoS4QueueInfoControlBufferEgressMinLimitUnicast, sleV2QoS4QueueInfoControlBufferEgressMaxLimitPolicyUnicast, 
				sleV2QoS4QueueInfoControlBufferEgressMaxLimitUnicast, sleV2QoS4QueueInfoControlBufferEgressMinLimitNonUnicast, sleV2QoS4QueueInfoControlBufferEgressMaxLimitPolicyNonUnicast, sleV2QoS4QueueInfoControlBufferEgressMaxLimitNonUnicast, sleV2QoS4PolicyFlowClassIndex, 
				sleV2QoS4FlowIpPktPriorityType, sleV2QoS4FlowIpPktPriority, sleV2QoS4PolicerRemarkLayerMode, sleV2QoS4PolicerRemarkMode, sleV2QoS4PolicerColorGreenCosType, 
				sleV2QoS4PolicyMatchPbrNextHop, sleV2QoS4PolicyControlMatchPbrNextHop }
			STATUS current
			DESCRIPTION 
				"Description."
			::= { sleV2QoS 4 }

		
		-- 1.3.6.1.4.1.6296.102.10.5
		sleV2QoSNotificationGroup NOTIFICATION-GROUP
			NOTIFICATIONS { sleFlowCreated, sleFlowChanged, sleFlowDestroyed, sleFlowAllDestroyed, sleClassCreated, 
				sleClassDestroyed, sleClassAllDestroyed, sleClassFlowAdded, sleClassFlowDeleted, sleClassFlowAllDeleted, 
				slePolicerCreated, slePolicerChanged, slePolicerDestroyed, slePolicyCreated, slePolicyDestroyed, 
				sleRemarkChanged, sleRemarkL3Changed, sleV2QS4REDProfileChanged, sleV2QoS4PortREDInfoChanged, sleV2QoS4QueueInfoChanged, 
				sleV2QS4REDProfileCleared, slePolicyEmptyCreated, sleV2QoS4DscpMapIngressChanged, sleV2QoS4DscpMapTunnelChanged, sleV2QoS4BaseFlowModeChanged, 
				sleRemarkL2Changed, slePolicyInfoChanged, slePolicyMatchActionChanged, slePolicyNomatchActionChanged, slePolicyCounterCleared, 
				slePolicyFlowAdded, slePolicyFlowDeleted, slePolicyAllFlowDeleted, slePolicyAllClassDeleted, sleV2QoS4QueueInfoScheduleModeChanged, 
				sleV2QoS4QueueInfoWeightChanged, sleV2QosPolicyIFServicePolicyChanged, sleV2QosPolicyIFServicePolicyCleared, slePolicyAllFlowClassDeleted, slePolicyIngressTunnelSet, 
				slePolicyIngressTunnelUnset, slePolicyEgressTunnelSet, slePolicyEgressTunnelUnset, sleV2QoS4QueueInfoMaxBandwidthChanged, slePolicyMatchInnerVlanCosReplaceChanged, 
				slePolicyMatchInnerVlanCfiReplaceChanged, slePolicyMatchOuterVlanCosReplaceChanged, slePolicyMatchOuterVlanCfiReplaceChanged, sleFlowExCreated, sleFlowExChanged, 
				sleV2QoS4QueueInfoBufferEgressMinLimitUnicastChanged, sleV2QoS4QueueInfoBufferEgressMinLimitUnicastCleared, sleV2QoS4QueueInfoBufferEgressMaxLimitUnicastChanged, sleV2QoS4QueueInfoBufferEgressMaxLimitUnicastCleared, sleV2QoS4QueueInfoBufferEgressMinLimitNonUnicastChanged, 
				sleV2QoS4QueueInfoBufferEgressMinLimitNonUnicastCleared, sleV2QoS4QueueInfoBufferEgressMaxLimitNonUnicastChanged, sleV2QoS4QueueInfoBufferEgressMaxLimitNonUnicastCleared, sleV2QoS4QueueInfoMinBandwidthChanged, sleFlowInPktTagChanged, 
				sleFlowOutPktTagChanged, sleFlowAliasChanged, slePolicyActionMatchFlowAliasChanged }
			STATUS current
			DESCRIPTION 
				"Description."
			::= { sleV2QoS 5 }

		
	
	END

--
-- slev2-qos-mib.mib
--
