-- ZyXEL Communications Corporation
-- Private Enterprise MIB definition 
  
-- This file describes the ZyXEL Communications Corporation Enterprise MIB.
-- It contains ZyXEL products OIDs, and common managed objects.

-- $Log: ZYXEL-PROTOCOL-BASED-VLAN-MIB.mib $ 
-- Revision 1.3  2012/09/19 07:45:16  Kevin 
-- if it's leaf node, revise the vender name from zyxel to zy 
-- Revision 1.2  2012/07/05 06:24:26  Kevin 
-- 1. upgrade from SNMP to SNMPv2  
-- 2. clean warning 
-- Revision 1.1  2012/05/30 07:50:28  Kevin 
-- Initial revision 

ZYXEL-PROTOCOL-BASED-VLAN-MIB DEFINITIONS ::= BEGIN

    IMPORTS
	enterprises		FROM RFC1155-SMI                                
	
	OBJECT-TYPE
		FROM SNMPv2-SMI			-- RFC2578	
	RowStatus, DateAndTime, TruthValue, StorageType, MacAddress
		FROM SNMPv2-TC			-- RFC2579
	DisplayString                                          
	  	FROM RFC1213-MIB
	EnabledStatus
		FROM  P-BRIDGE-MIB
	PortList
		FROM  Q-BRIDGE-MIB
	dot1dBasePort
       	FROM BRIDGE-MIB
	InterfaceIndexOrZero			-- RFC2863
		FROM IF-MIB
	SnmpAdminString
		FROM SNMP-FRAMEWORK-MIB		-- RFC2571
	InetAddressType, InetAddress
		FROM INET-ADDRESS-MIB		-- RFC2851
	OperationResponseStatus
		FROM DISMAN-PING-MIB
    Counter, TimeTicks
        FROM RFC1155-SMI
    BridgeId, Timeout
        FROM BRIDGE-MIB  
    dot1agCfmMdIndex 
		FROM IEEE8021-CFM-MIB
	dot1agCfmMaIndex
		FROM IEEE8021-CFM-MIB	
	dot1agCfmMepIdentifier
		FROM IEEE8021-CFM-MIB   	
    IpAddress
        FROM SNMPv2-SMI
    ifIndex
    	FROM IF-MIB					-- RFC2863
    NOTIFICATION-TYPE
        FROM SNMPv2-SMI
    sysObjectID 
        FROM RFC1213-MIB 
	ospfIfIpAddress, ospfAddressLessIf, ospfAreaId, ospfNbrIpAddr, ospfNbrAddressLessIndex,
	ospfLsdbAreaId, ospfLsdbType, ospfLsdbLsid, ospfLsdbRouterId, ospfVirtIfAreaId, ospfVirtIfNeighbor
		FROM OSPF-MIB
	esMgmt			
		FROM ZYXEL-ES-SMI;

	zyxelProtocolBasedVlan MODULE-IDENTITY
		LAST-UPDATED	"201207010000Z"    
		ORGANIZATION "Enterprise Solution ZyXEL"     
		CONTACT-INFO
			""	   
		DESCRIPTION
			"The subtree for protocol-based VLAN"
		::= { esMgmt 69 }

	zyxelProtocolBasedVlanSetup     OBJECT IDENTIFIER ::= { zyxelProtocolBasedVlan 1 }
	
		
--  32.protocol-based VLAN
	 
	 	
        zyProtocolBasedVlanMaxNumberOfVlans OBJECT-TYPE
        SYNTAX  INTEGER
        MAX-ACCESS  read-only
        STATUS  current
        DESCRIPTION
                      	"The maximum number of protocol based VLANs that can be created"
        ::= { zyxelProtocolBasedVlanSetup 1 }
	
	    zyxelProtocolBasedVlanTable  OBJECT-TYPE
	    SYNTAX	SEQUENCE OF ZyxelProtocolBasedVlanEntry 
	    MAX-ACCESS  not-accessible
	    STATUS  current
	    DESCRIPTION
	             	"The table contains protocol based VLAN configuration. "
	    ::= { zyxelProtocolBasedVlanSetup 2 }	

		zyxelProtocolBasedVlanEntry  OBJECT-TYPE
        SYNTAX	ZyxelProtocolBasedVlanEntry 
        MAX-ACCESS	not-accessible
        STATUS	current
        DESCRIPTION    	
        			"An entry contains protocol based VLAN configuration."
        INDEX          	{ dot1dBasePort, zyProtocolBasedVlanPacketType, zyProtocolBasedVlanEthernetType }
        ::= { zyxelProtocolBasedVlanTable 1 }

        ZyxelProtocolBasedVlanEntry ::=
           SEQUENCE {
        	zyProtocolBasedVlanPacketType	INTEGER,
        	zyProtocolBasedVlanEthernetType	INTEGER,
        	zyProtocolBasedVlanName			DisplayString,
        	zyProtocolBasedVlanVid			INTEGER,
        	zyProtocolBasedVlanPriority		INTEGER,
        	zyProtocolBasedVlanRowStatus	RowStatus
           }

        zyProtocolBasedVlanPacketType OBJECT-TYPE
        SYNTAX  INTEGER {      
        	etherII(1),
        	snap(2),
        	llc(3)
        }
        MAX-ACCESS  not-accessible
        STATUS  current
        DESCRIPTION
                      	"There are several types of Ethernet frames. The different frame types have different 
                      	formats and MTU values, but can coexist on the same physical medium."
        ::= { zyxelProtocolBasedVlanEntry 1 }

        zyProtocolBasedVlanEthernetType OBJECT-TYPE
        SYNTAX  INTEGER
        MAX-ACCESS  not-accessible
        STATUS  current
        DESCRIPTION
                      	"The predefined protocol in this protocol based VLAN. For example, 
                      	the IP protocol in hexadecimal notation is 0800, and in decimal is 2048."
        ::= { zyxelProtocolBasedVlanEntry 2 }

        zyProtocolBasedVlanName OBJECT-TYPE
        SYNTAX  DisplayString (SIZE (0..32))
        MAX-ACCESS  read-write
        STATUS  current
        DESCRIPTION
                      	"Type a descriptive name that identifies this protocol based VLAN."
        ::= { zyxelProtocolBasedVlanEntry 3 }

        zyProtocolBasedVlanVid OBJECT-TYPE
        SYNTAX  INTEGER (1..4094)
        MAX-ACCESS  read-write
        STATUS  current
        DESCRIPTION
                      	"Enter the ID of a VLAN to which the port belongs. This must be an existing VLAN which you 
                      	defined on switch."
        ::= { zyxelProtocolBasedVlanEntry 4 }

        zyProtocolBasedVlanPriority OBJECT-TYPE
        SYNTAX  INTEGER (0..7)
        MAX-ACCESS  read-write
        STATUS  current
        DESCRIPTION
                      	"Enter the priority level that the Switch will assign to frames belonging to this VLAN."
        ::= { zyxelProtocolBasedVlanEntry 5 }

        zyProtocolBasedVlanRowStatus OBJECT-TYPE
        SYNTAX  RowStatus
        MAX-ACCESS  read-create
        STATUS  current
        DESCRIPTION
                      	"This object allows entries to be created and deleted from the protocol based VLAN table"
        ::= { zyxelProtocolBasedVlanEntry 6 } 
 END
