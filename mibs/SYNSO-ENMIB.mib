-- Synso Environment Measure Management Information Base
-- SYNSO-UPSMIB
-- {iso org(3) internet(1) private(4) enterprises(1) synso(9557)}

SYNSO-ENMIB DEFINITIONS ::= BEGIN

IMPORTS
	OBJECT-TYPE, enterprises, IpAddress
		FROM RFC1155-SMI
	DisplayString
		FROM SNMPv2-TC;


synso			OBJECT IDENTIFIER ::= {enterprises 9557}
synsoMeasure	OBJECT IDENTIFIER ::= {synso 2}

--
-- The Temperature Group
--

syupsEnvironTemperature		OBJECT IDENTIFIER ::= {synsoMeasure 1}

syupsEnvironTemperatureNumber OBJECT-TYPE
	SYNTAX      INTEGER
	ACCESS      read-only
	STATUS      mandatory
	DESCRIPTION
                "The number of temperature sensor."
	::= {syupsEnvironTemperature 1}


syupsEnvironTemperatureTable OBJECT-TYPE
	SYNTAX      SEQUENCE OF SyupsEnvironTemperatureEntry
	ACCESS      not-accessible
	STATUS      mandatory
	DESCRIPTION
                "A table containing the supported temperature entry."
	::= {syupsEnvironTemperature 2}

syupsEnvironTemperatureEntry OBJECT-TYPE
	SYNTAX      SyupsEnvironTemperatureEntry
	ACCESS      not-accessible
	STATUS      mandatory
	DESCRIPTION
                "An entry representing the information for a temperature port."
	INDEX {syupsEnvironTemperatureIndex}
	::= {syupsEnvironTemperatureTable 1}

SyupsEnvironTemperatureEntry ::= SEQUENCE {
	syupsEnvironTemperatureIndex INTEGER,
	syupsEnvironTemperatureDescription DisplayString,
	syupsEnvironTemperatureLow INTEGER,
	syupsEnvironTemperatureHigh INTEGER,
	syupsEnvironTemperatureCurrent INTEGER
}

syupsEnvironTemperatureIndex OBJECT-TYPE
	SYNTAX      INTEGER
	ACCESS      read-only
	STATUS      mandatory
	DESCRIPTION
                "An index identifying the temperature sensor."
	::= {syupsEnvironTemperatureEntry 1}

syupsEnvironTemperatureDescription OBJECT-TYPE
	SYNTAX      DisplayString
	ACCESS      read-write
	STATUS      mandatory
	DESCRIPTION
                "The string containing the description for the temperature sensor."
	::= {syupsEnvironTemperatureEntry 2}

syupsEnvironTemperatureLow OBJECT-TYPE
	SYNTAX      INTEGER
	ACCESS      read-write
	STATUS      mandatory
	DESCRIPTION
                "The low temperature to indicate abnormal status."
	::= {syupsEnvironTemperatureEntry 3}


syupsEnvironTemperatureHigh OBJECT-TYPE
	SYNTAX      INTEGER
	ACCESS      read-write
	STATUS      mandatory
	DESCRIPTION
                "The high temperature to indicate abnormal status."
	::= {syupsEnvironTemperatureEntry 4}

syupsEnvironTemperatureCurrent OBJECT-TYPE
	SYNTAX      INTEGER
	ACCESS      read-only
	STATUS      mandatory
	DESCRIPTION
                "The current temperature from the temperature sensor."
	::= {syupsEnvironTemperatureEntry 5}

--
-- The Humidity Group
--

syupsEnvironHumidity		OBJECT IDENTIFIER ::= {synsoMeasure 2}

syupsEnvironHumidityNumber OBJECT-TYPE
	SYNTAX      INTEGER
	ACCESS      read-only
	STATUS      mandatory
	DESCRIPTION
                "The number of Humidity sensor."
	::= {syupsEnvironHumidity 1}


syupsEnvironHumidityTable OBJECT-TYPE
	SYNTAX      SEQUENCE OF SyupsEnvironHumidityEntry
	ACCESS      not-accessible
	STATUS      mandatory
	DESCRIPTION
                "A table containing the supported Humidity entry."
	::= {syupsEnvironHumidity 2}

syupsEnvironHumidityEntry OBJECT-TYPE
	SYNTAX      SyupsEnvironHumidityEntry
	ACCESS      not-accessible
	STATUS      mandatory
	DESCRIPTION
                "An entry representing the information for a Humidity port."
	INDEX {syupsEnvironHumidityIndex}
	::= {syupsEnvironHumidityTable 1}

SyupsEnvironHumidityEntry ::= SEQUENCE {
	syupsEnvironHumidityIndex INTEGER,
	syupsEnvironHumidityDescription DisplayString,
	syupsEnvironHumidityLow INTEGER,
	syupsEnvironHumidityHigh INTEGER,
	syupsEnvironHumidityCurrent INTEGER
}

syupsEnvironHumidityIndex OBJECT-TYPE
	SYNTAX      INTEGER
	ACCESS      read-only
	STATUS      mandatory
	DESCRIPTION
                "An index identifying the Humidity sensor."
	::= {syupsEnvironHumidityEntry 1}

syupsEnvironHumidityDescription OBJECT-TYPE
	SYNTAX      DisplayString
	ACCESS      read-write
	STATUS      mandatory
	DESCRIPTION
                "The string containing the description for the Humidity sensor."
	::= {syupsEnvironHumidityEntry 2}

syupsEnvironHumidityLow OBJECT-TYPE
	SYNTAX      INTEGER
	ACCESS      read-write
	STATUS      mandatory
	DESCRIPTION
                "The low humidity to indicate abnormal status."
	::= {syupsEnvironHumidityEntry 3}


syupsEnvironHumidityHigh OBJECT-TYPE
	SYNTAX      INTEGER
	ACCESS      read-write
	STATUS      mandatory
	DESCRIPTION
                "The high Humidity to indicate abnormal status."
	::= {syupsEnvironHumidityEntry 4}

syupsEnvironHumidityCurrent OBJECT-TYPE
	SYNTAX      INTEGER
	ACCESS      read-only
	STATUS      mandatory
	DESCRIPTION
                "The current humidity from the humidity sensor."
	::= {syupsEnvironHumidityEntry 5}


--
-- The Contact Group
--

syupsContact		OBJECT IDENTIFIER ::= {synsoMeasure 3}

syupsContactNumber OBJECT-TYPE
	SYNTAX      INTEGER
	ACCESS      read-only
	STATUS      mandatory
	DESCRIPTION
                "The number of contacts supported by the measure unit."
	::= {syupsContact 1}


syupsContactTable OBJECT-TYPE
	SYNTAX      SEQUENCE OF SyupsContactEntry
	ACCESS      not-accessible
	STATUS      mandatory
	DESCRIPTION
                "A table containing the supported contacts."
	::= {syupsContact 2}

syupsContactEntry OBJECT-TYPE
	SYNTAX      SyupsContactEntry
	ACCESS      not-accessible
	STATUS      mandatory
	DESCRIPTION
                "An entry representing the information for a contact."
	INDEX {syupsContactIndex}
	::= {syupsContactTable 1}

SyupsContactEntry ::= SEQUENCE {
	syupsContactIndex INTEGER,
	syupsContactDescription DisplayString,
	syupsContactNormalState INTEGER,
	syupsContactMonitoringStatus INTEGER,
	syupsContactCurrentStatus INTEGER
}

syupsContactIndex OBJECT-TYPE
	SYNTAX      INTEGER
	ACCESS      read-only
	STATUS      mandatory
	DESCRIPTION
                "An index identifying the contact."
	::= {syupsContactEntry 1}

syupsContactDescription OBJECT-TYPE
	SYNTAX      DisplayString
	ACCESS      read-write
	STATUS      mandatory
	DESCRIPTION
                "The string containing the description for the contact."
	::= {syupsContactEntry 2}

syupsContactNormalState OBJECT-TYPE
    SYNTAX INTEGER {unknown(1),	open(2), closed(3) }
	ACCESS      read-write
	STATUS      mandatory
	DESCRIPTION
      			"The normal operating position of the contact."
	::= {syupsContactEntry 3}


syupsContactMonitoringStatus OBJECT-TYPE
	SYNTAX      INTEGER {unknown(1),  enabled(2), disabled(3) }
	ACCESS      read-write
	STATUS      mandatory
	DESCRIPTION
			   	"A flag indicating whether this contact is 
       			 monitored, or not."
	::= {syupsContactEntry 4}

syupsContactCurrentStatus OBJECT-TYPE
	SYNTAX      INTEGER { unknown(1),   noFault(2),  fault(3) }
	ACCESS      read-only
	STATUS      mandatory
	DESCRIPTION
      			"This value indicates the current state of the contact.
       			 If the contact is not in its normal state.  This value
       			 is set to fault(2)."
	::= {syupsContactEntry 5}


END
