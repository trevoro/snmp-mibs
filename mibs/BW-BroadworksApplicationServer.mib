-- File Name : BW-BroadworksApplicationServer.mib
-- Date      : Thu Oct 19 11:55:17 EDT 2000
-- Author    : AdventNet Agent Toolkit - MibEditor 4.0

BW-BroadworksApplicationServer DEFINITIONS ::= BEGIN
        IMPORTS
                DateAndTime, DisplayString
                        FROM SNMPv2-TC
                MODULE-COMPLIANCE, OBJECT-GROUP          
                        FROM SNMPv2-CONF
                enterprises, MODULE-IDENTITY, NOTIFICATION-TYPE, OBJECT-TYPE, Gauge32, Counter32, Counter64, Integer32, Unsigned32
                        FROM SNMPv2-SMI;

  broadsoft MODULE-IDENTITY
    LAST-UPDATED  "200508161000Z"
    ORGANIZATION  "Broadsoft, Inc"
    CONTACT-INFO  "Broadsoft, Inc
220 Perry Parkway
Gaithersburg, MD  20877

301-977-9440"
                DESCRIPTION
                                "This is the System Management Information structure for the
                                Broadsoft enterprise."
    REVISION    "200508161000Z"
    DESCRIPTION   
                                "Added MIB conformance section."
    REVISION    "200412200000Z"
                DESCRIPTION
                                "Adding release 12.0 counters."
    REVISION    "200406220000Z"
                DESCRIPTION
                                "Adding release 11.1 counters."
    REVISION    "200309200000Z"
                DESCRIPTION
                                "Adding release 10 counters."
    REVISION    "200206120000Z"
                DESCRIPTION
                                "Added new counters for Release 8. The BroadWorks counters were also changed from
                                read-only to read-write. Group based service counter tables were introduced."
    REVISION    "200201240000Z"
                DESCRIPTION
                                ""
    REVISION    "200107121159Z"
                DESCRIPTION
                                "Added POP3 and SMTP performance measurement .
                                Added  instantConferencing module and the following performance measurements:
                                bwICGroupPortLimitExceeded
                                bwICNumAttempts
                                bwICInvalidPasscode"
    REVISION    "200107261048Z"
                DESCRIPTION
                                "Reintroduce instant conferencing statistics as service performance measurements."
    REVISION    "200107121200Z"
                DESCRIPTION
                                "Added POP3 and SMTP performance measurement ."
                ::=  {  enterprises  6431  }

  broadworks  OBJECT IDENTIFIER
                ::=  {  broadsoft  1  }

  executionServer OBJECT IDENTIFIER
                ::=  {  broadworks  2  }

  provisioningServer  OBJECT IDENTIFIER
                ::=  {  broadworks  6  }

-- Application server modules  ...........................................


-- Execution server modules  ...........................................

  mgcpModule  OBJECT IDENTIFIER
                ::=  {  executionServer  1  }

  mcpModule OBJECT IDENTIFIER
                ::=  {  executionServer  3  }

  imsModule OBJECT IDENTIFIER
                ::=  {  executionServer  4  }

  databaseModule  OBJECT IDENTIFIER
                ::=  {  executionServer  5  }

  callpModule OBJECT IDENTIFIER
                ::=  {  executionServer  7  }

  smtpModule  OBJECT IDENTIFIER
                ::=  {  executionServer  8  }

  sipModule OBJECT IDENTIFIER
                ::=  {  executionServer  9  }

  services  OBJECT IDENTIFIER
                ::=  {  executionServer  11  }

  mssModule OBJECT IDENTIFIER
                ::=  {  executionServer  12  }

  nrsModule OBJECT IDENTIFIER
                ::=  {  executionServer  13  }

  pmtModule OBJECT IDENTIFIER
                ::=  {  executionServer  15  }

  systemModule  OBJECT IDENTIFIER
                ::=  {  executionServer  16  }

  management  OBJECT IDENTIFIER
                ::=  {  executionServer  17  }

  redundancyModule  OBJECT IDENTIFIER
                ::=  {  executionServer  18  }

  capModule OBJECT IDENTIFIER
                ::=  {  executionServer  19  }

  smdiModule  OBJECT IDENTIFIER
                ::=  {  executionServer  20  }

  mediaModule OBJECT IDENTIFIER
                ::=  {  executionServer  21  }

  wspModule OBJECT IDENTIFIER
                ::=  {  executionServer  22  }

  realtimeAccountingModule  OBJECT IDENTIFIER
                ::=  {  executionServer  23  }

  externalCallLogsModule  OBJECT IDENTIFIER
                ::=  {  executionServer  24  }

  commonCommModule  OBJECT IDENTIFIER
                ::=  {  executionServer  25  }

  tcpModule OBJECT IDENTIFIER
                ::=  {  executionServer  26  }

  concurrentModule  OBJECT IDENTIFIER
                ::=  {  executionServer  27  }

  soapModule  OBJECT IDENTIFIER
                ::=  {  executionServer  28  }

  smppModule  OBJECT IDENTIFIER
    ::=  {  executionServer  29  }

  dnsModule OBJECT IDENTIFIER
    ::=  {  executionServer  30  }

  bwAsMibConformance  OBJECT IDENTIFIER
                ::=  {  executionServer  1000  }

  mgcpStats OBJECT IDENTIFIER
                ::=  {  mgcpModule  1  }

  mcpStats  OBJECT IDENTIFIER
                ::=  {  mcpModule  1  }

  imsStats  OBJECT IDENTIFIER
                ::=  {  imsModule  1  }

  callpStats  OBJECT IDENTIFIER
                ::=  {  callpModule  1  }

  smtpStats OBJECT IDENTIFIER
                ::=  {  smtpModule  1  }

  sipStats  OBJECT IDENTIFIER
                ::=  {  sipModule  1  }

  congestionManagement  OBJECT IDENTIFIER
    ::=  {  sipModule  2  }

  capStats  OBJECT IDENTIFIER
                ::=  {  capModule 1 }

  smdiStats OBJECT IDENTIFIER
                ::=  {  smdiModule 1 }

  mediaStats  OBJECT IDENTIFIER
                ::=  {  mediaModule 1 }

  wspStats  OBJECT IDENTIFIER
                ::=  {  wspModule 1 }

  realtimeAccountingStats OBJECT IDENTIFIER
                ::=  {  realtimeAccountingModule 1 }

  externalCallLogsStats OBJECT IDENTIFIER
                ::=  {  externalCallLogsModule 1 }

  commonCommStats OBJECT IDENTIFIER
                ::=  {  commonCommModule 1 }

  tcpStats  OBJECT IDENTIFIER
                ::=  {  tcpModule 1 }
                
  concurrentStats OBJECT IDENTIFIER
                ::=  {  concurrentModule 1 }
                
  soapStats OBJECT IDENTIFIER
                ::=  {  soapModule 1 }

  smppStats OBJECT IDENTIFIER
          ::=  { smppModule 1 }

  dnsStats  OBJECT IDENTIFIER
          ::=  {  dnsModule 1 }

  accountCodes  OBJECT IDENTIFIER
                ::=  {  services  1  }

  anonymousCallRejection  OBJECT IDENTIFIER
                ::=  {  services  2  }

  authentication  OBJECT IDENTIFIER
                ::=  {  services  3  }

  autoAttendant OBJECT IDENTIFIER
                ::=  {  services  4  }

  callCapacity  OBJECT IDENTIFIER
                ::=  {  services  5  }

  callForwardingAlways  OBJECT IDENTIFIER
                ::=  {  services  6  }

  callForwardingBusy  OBJECT IDENTIFIER
                ::=  {  services  7  }

  callForwardingNoAnswer  OBJECT IDENTIFIER
                ::=  {  services  8  }

  callNotify  OBJECT IDENTIFIER
                ::=  {  services  9  }

  callPark  OBJECT IDENTIFIER
                ::=  {  services  10  }

  callPickup  OBJECT IDENTIFIER
                ::=  {  services  11  }

  callReturn  OBJECT IDENTIFIER
                ::=  {  services  12  }

  commPilotCallManager  OBJECT IDENTIFIER
                ::=  {  services  13  }

  doNotDisturb  OBJECT IDENTIFIER
                ::=  {  services  14  }

  flashCallTransfer OBJECT IDENTIFIER
                ::=  {  services  15  }

  flashCallWaiting  OBJECT IDENTIFIER
                ::=  {  services  16  }

  flashConsultation OBJECT IDENTIFIER
                ::=  {  services  17  }

  flashThreeWayCall OBJECT IDENTIFIER
                ::=  {  services  18  }

  huntGroups  OBJECT IDENTIFIER
                ::=  {  services  19  }

  incomingCallingPlan OBJECT IDENTIFIER
                ::=  {  services  20  }

  ipPhone OBJECT IDENTIFIER
                ::=  {  services  21  }

  lastNumberRedial  OBJECT IDENTIFIER
                ::=  {  services  22  }

  outgoingCallingPlan OBJECT IDENTIFIER
                ::=  {  services  23  }

  priorityAlert OBJECT IDENTIFIER
                ::=  {  services  24  }

  selectiveCallAcceptance OBJECT IDENTIFIER
                ::=  {  services  25  }

  selectiveCallForward  OBJECT IDENTIFIER
                ::=  {  services  26  }

  selectiveCallRejection  OBJECT IDENTIFIER
                ::=  {  services  27  }

  simRingPersonal OBJECT IDENTIFIER
                ::=  {  services  28  }

  voiceMessaging  OBJECT IDENTIFIER
                ::=  {  services  29  }

  seriesCompletion  OBJECT IDENTIFIER
                ::=  {  services  30  }

  intercept OBJECT IDENTIFIER
                ::=  {  services  31  }

  instantConferencing OBJECT IDENTIFIER
                ::=  {  services  32  }

  callingLineIDDeliveryBlock  OBJECT IDENTIFIER
                ::=  {  services  33  }

  sessionAudit  OBJECT IDENTIFIER
                ::=  {  services  34  }

        windowsMessaging      OBJECT IDENTIFIER
                ::=  {  services  35  }

        callWaiting      OBJECT IDENTIFIER
                ::=  {  services  36  }

        alternateNumbers      OBJECT IDENTIFIER
                ::=  {  services  37  }

        cot      OBJECT IDENTIFIER
                ::=  {  services  38  }

        sd8      OBJECT IDENTIFIER
                ::=  {  services  39  }

        musicOnHold      OBJECT IDENTIFIER
                ::=  {  services  40  }

        callingNameRetrieval      OBJECT IDENTIFIER
                ::=  {  services  41  }

        thirdPartyMWIControl      OBJECT IDENTIFIER
                ::=  {  services  42  }

        callCenter      OBJECT IDENTIFIER
                ::=  {  services  43  }

        callForwardGroupNoAnswer      OBJECT IDENTIFIER
                ::=  {  services  44  }

        sd100      OBJECT IDENTIFIER
                ::=  {  services  45  }

        thirdPartyVMail      OBJECT IDENTIFIER
                ::=  {  services  46  }

        directedCallPickup      OBJECT IDENTIFIER
                ::=  {  services  47  }

        flashCallHold      OBJECT IDENTIFIER
                ::=  {  services  48  }

        emergencyZones      OBJECT IDENTIFIER
                ::=  {  services  49  }

        dpubi      OBJECT IDENTIFIER
                ::=  {  services  50  }

        acb      OBJECT IDENTIFIER
                ::=  {  services  51  }

        sequentialRing      OBJECT IDENTIFIER
                ::=  {  services  52  }

        ringTimeout      OBJECT IDENTIFIER
                ::=  {  services  53  }

        videoAddOn      OBJECT IDENTIFIER
                ::=  {  services  54  }

        mct      OBJECT IDENTIFIER
                ::=  {  services  55  }

        pushToTalk      OBJECT IDENTIFIER
                ::=  {  services  56  }

        hoteling      OBJECT IDENTIFIER
                ::=  {  services  57  }

        preferredCarrier      OBJECT IDENTIFIER
                ::=  {  services  58  }
        
        familySimRing      OBJECT IDENTIFIER
                ::=  {  services  59  }

        diversionInhibitor      OBJECT IDENTIFIER
                ::=  {  services  60  }
  
        instantGroupCall      OBJECT IDENTIFIER
                ::=  {  services  61  }
                
        automaticHoldRetrieve      OBJECT IDENTIFIER
                ::=  {  services  62  }

        trunkGroup      OBJECT IDENTIFIER
                ::=  {  services  63  }

        customRingback      OBJECT IDENTIFIER
                ::=  {  services  64  }

        physicalLocation    OBJECT IDENTIFIER
                ::=  {  services  65  }

        faxMessaging    OBJECT IDENTIFIER
                ::=  {  services  66  }
                
        externalemergencyrouting      OBJECT IDENTIFIER
                ::=  {  services  67  }

        twoStageDialing      OBJECT IDENTIFIER
                ::=  {  services  68  }

  callForwardingNotReachable  OBJECT IDENTIFIER
                ::=  {  services  69  }

        mwiDeliveryToMobile OBJECT IDENTIFIER
                ::=  {  services  70  }

        sharedCallAppearance OBJECT IDENTIFIER
                ::=  {  services  71  }

        externalCustomRingback OBJECT IDENTIFIER
                ::=  {  services  72  }

        inCallServiceActivation         OBJECT IDENTIFIER
                ::=  {  services  73  }

        expensiveCallNotification         OBJECT IDENTIFIER
                ::=  {  services  74  }

        locationControl OBJECT IDENTIFIER
                ::= { services 75 }

        callRetrieve OBJECT IDENTIFIER
                ::= { services 76 }

        broadworksAnywhere OBJECT IDENTIFIER
                ::= { services 77 }

                
-- Other modules ...........................................

  mssStats  OBJECT IDENTIFIER
                ::=  {  mssModule  1  }

  nrsStats  OBJECT IDENTIFIER
                ::=  {  nrsModule  1  }

  databaseStats OBJECT IDENTIFIER
                ::=  {  databaseModule  1  }

  pmtStats  OBJECT IDENTIFIER
                ::=  {  pmtModule  1  }

  redundancyStats OBJECT IDENTIFIER
                ::=  {  redundancyModule  1  }

-- Provisioing server modules  ...........................................

  psDatabaseModule  OBJECT IDENTIFIER
                ::=  {  provisioningServer  1  }

  psOssModule OBJECT IDENTIFIER
                ::=  {  provisioningServer  2  }

  psNSSyncModule  OBJECT IDENTIFIER
                ::=  {  provisioningServer  3  }

  psOAMModule OBJECT IDENTIFIER
                ::=  {  provisioningServer  4  }

  ldapModule  OBJECT IDENTIFIER
                ::=  {  provisioningServer  5  }

  cpeDevicesModule  OBJECT IDENTIFIER
                ::=  {  provisioningServer  6  }

  psExternalCallLogsModule  OBJECT IDENTIFIER
                ::=  {  provisioningServer  7  }
                
  psOciModule OBJECT IDENTIFIER
                ::=  {  provisioningServer  8  }
                
  psSystemModule  OBJECT IDENTIFIER
                ::=  {  provisioningServer  9  }

  psCommonCommModule  OBJECT IDENTIFIER
                ::=  {  provisioningServer  10  }
                
  psTcpModule OBJECT IDENTIFIER
                ::=  {  provisioningServer  11  }

  psConcurrentModule  OBJECT IDENTIFIER
                ::=  {  provisioningServer  12  }

  psActivatableFeatureModule  OBJECT IDENTIFIER
                ::=  {  provisioningServer  13  }

  psShInterfaceModule     OBJECT IDENTIFIER
                ::=  {  provisioningServer  14  }

  psServices OBJECT IDENTIFIER
                ::= { provisioningServer 15 }

  psReservedModule  OBJECT IDENTIFIER
                ::=  {  provisioningServer 999  }

  psVoiceMessaging OBJECT IDENTIFIER
                ::= { psServices 1 }

  polycomPhoneServices OBJECT IDENTIFIER
                ::= { psServices 2 }
                
  psDatabaseStats OBJECT IDENTIFIER
                ::=  {  psDatabaseModule  1  }

  psOssStats  OBJECT IDENTIFIER
                ::=  {  psOssModule  1  }

  psNSSyncStats OBJECT IDENTIFIER
                ::=  {  psNSSyncModule  1  }

  psOAMStats  OBJECT IDENTIFIER
                ::=  {  psOAMModule  1  }

  cpeDevicesStats OBJECT IDENTIFIER
                ::=  {  cpeDevicesModule 1 }

  psExternalCallLogsStats OBJECT IDENTIFIER
                ::=  {  psExternalCallLogsModule 1 }

  psOciStats  OBJECT IDENTIFIER
                ::=  {  psOciModule 1 }

  psInternalStats OBJECT IDENTIFIER
                ::=  {  psSystemModule 1 }

  psCommonCommStats OBJECT IDENTIFIER
                ::=  {  psCommonCommModule 1 }

  psTcpStats  OBJECT IDENTIFIER
                ::=  {  psTcpModule 1 }

  psConcurrentStats OBJECT IDENTIFIER
                ::=  {  psConcurrentModule 1 }

  psActivatableFeatureStats OBJECT IDENTIFIER
                ::=  {  psActivatableFeatureModule 1 }

  psShInterfaceStats      OBJECT IDENTIFIER
               ::=  {  psShInterfaceModule 1 }

-- dnsModule modules

  bwDnsQueryTimeMax OBJECT-TYPE
    SYNTAX    Gauge32
    MAX-ACCESS  read-write
    STATUS    current
    DESCRIPTION
        "This gauge reports the maximum query time in milliseconds."
    ::=  {  dnsStats  1  }

  bwDnsQueryTimeMaxTimestampMSB OBJECT-TYPE
    SYNTAX    Gauge32
    MAX-ACCESS  read-write
    STATUS    current
    DESCRIPTION
        "The gauge reports the most significant part of the timestamp (4 most significant bytes) of when bwDnsQueryTimeMax was obtained."
    ::=  {  dnsStats  2  }

  bwDnsQueryTimeMaxTimestampLSB OBJECT-TYPE
    SYNTAX    Gauge32
    MAX-ACCESS  read-write
    STATUS    current
    DESCRIPTION
        "The gauge reports the least significant part of the timestamp (4 least significant bytes) of when bwDnsQueryTimeMax was obtained."
    ::=  {  dnsStats  3  }

  bwDnsQueryTimeAvg OBJECT-TYPE
    SYNTAX    Gauge32
    MAX-ACCESS  read-write
    STATUS    current
    DESCRIPTION
        "This gauge reports the average query time in milliseconds."
    ::=  {  dnsStats  4  }

  bwDnsStatsQueriesTable  OBJECT-TYPE
    SYNTAX    SEQUENCE  OF  BwDnsStatsQueriesEntry
    MAX-ACCESS  not-accessible
    STATUS    current
    DESCRIPTION
      "This table contains DNS statistics."
    ::=  { dnsStats  5 }

  bwDnsStatsQueriesEntry  OBJECT-TYPE
    SYNTAX    BwDnsStatsQueriesEntry
    MAX-ACCESS  not-accessible
    STATUS    current
    DESCRIPTION
      "This row contains information on a particular DNS query type."
    INDEX   {  bwDnsStatsQueryIndex  }
    ::=  { bwDnsStatsQueriesTable 1 }

  BwDnsStatsQueriesEntry  ::=  SEQUENCE {
    bwDnsStatsQueryIndex  Unsigned32,
    bwDnsStatsQueryType  DisplayString,
    bwDnsStatsQueries  Counter32,
    bwDnsStatsQueryTimeouts Counter32
    }

  bwDnsStatsQueryIndex  OBJECT-TYPE 
    SYNTAX      Unsigned32
    MAX-ACCESS    read-only
    STATUS      current
    DESCRIPTION   
        "This column is the index for the table."
    ::=  {  bwDnsStatsQueriesEntry  1  }


  bwDnsStatsQueryType OBJECT-TYPE 
    SYNTAX      DisplayString
    MAX-ACCESS    read-only
    STATUS      current
    DESCRIPTION   
        "This column represents the DNS query type."
    ::=  {  bwDnsStatsQueriesEntry  2  }

  bwDnsStatsQueries OBJECT-TYPE 
    SYNTAX      Counter32
    MAX-ACCESS    read-write
    STATUS      current
    DESCRIPTION   
        "This counter reflects the number of DNS queries for a given type."
    ::=  {  bwDnsStatsQueriesEntry  3  }

  bwDnsStatsQueryTimeouts OBJECT-TYPE 
    SYNTAX      Counter32
    MAX-ACCESS    read-write
    STATUS      current
    DESCRIPTION   
        "This counter reflects the number of DNS queries timeouts for a given type."
    ::=  {  bwDnsStatsQueriesEntry  4  }

-- Protocol :: MGCP ...........................................

  bwMGCPStatsMGCPCommandOuts  OBJECT-TYPE
    SYNTAX      Counter32
    MAX-ACCESS    read-write
    STATUS      current
                DESCRIPTION
                                "This counter reflects the number of MGCP commands sent out by BroadWorks"
                ::=  {  mgcpStats  1  }

  bwMGCPStatsMGCPCommandIns OBJECT-TYPE
    SYNTAX      Counter32
    MAX-ACCESS    read-write
    STATUS      current
                DESCRIPTION
                                "This counter reflects the total number of MGCP commands received by BroadWorks"
                ::=  {  mgcpStats  2  }

  bwMGCPStatsMGCPResponseOuts OBJECT-TYPE
    SYNTAX      Counter32
    MAX-ACCESS    read-write
    STATUS      current
                DESCRIPTION
                                "This counter reflects the total number of MGCP responses sent by BroadWorks"
                ::=  {  mgcpStats  3  }

  bwMGCPStatsMGCPResponseIns  OBJECT-TYPE
    SYNTAX      Counter32
    MAX-ACCESS    read-write
    STATUS      current
                DESCRIPTION
                                "This counter reflects the total number of MGCP responses recevied by BroadWorks"
                ::=  {  mgcpStats  4  }

  bwMGCPStatsAuditConnectionOuts  OBJECT-TYPE
    SYNTAX      Counter32
    MAX-ACCESS    read-write
    STATUS      current
                DESCRIPTION
                                "This counter reflects the number of Audit Connection commands sent by Broadworks"
                ::=  {  mgcpStats  5  }

        bwMGCPStatsAuditEndpointOuts OBJECT-TYPE
    SYNTAX      Counter32
    MAX-ACCESS    read-write
    STATUS      current
                DESCRIPTION
                                "This counter reflects the number of Audit Endpoint commands sent by BroadWorks"
                ::=  {  mgcpStats  6  }

  bwMGCPStatsCreateConnectionOuts OBJECT-TYPE
    SYNTAX      Counter32
    MAX-ACCESS    read-write
    STATUS      current
                DESCRIPTION
                                "This counter reflects the number of Create Connection commands sent by BroadWorks"
                ::=  {  mgcpStats  7  }

        bwMGCPStatsDeleteAgentConnectionOuts OBJECT-TYPE
    SYNTAX      Counter32
    MAX-ACCESS    read-write
    STATUS      current
                DESCRIPTION
                                "This counter reflects the number of Delete Agent Connections sent by BroadWorks"
                ::=  {  mgcpStats  8  }

  bwMGCPStatsDeleteConnectionOuts OBJECT-TYPE
    SYNTAX      Counter32
    MAX-ACCESS    read-write
    STATUS      current
                DESCRIPTION
                                "This counter reflects the number of Delete Connection commands sent by BroadWorks"
                ::=  {  mgcpStats  9  }

        bwMGCPStatsDeleteGatewayConnectionIns OBJECT-TYPE
    SYNTAX      Counter32
    MAX-ACCESS    read-write
    STATUS      current
                DESCRIPTION
                                "This counter reflects the number of Delete Gateway Connection commands received by BroadWorks"
                ::=  {  mgcpStats  10  }

  bwMGCPStatsEndpointConfigurationOuts  OBJECT-TYPE
    SYNTAX      Counter32
    MAX-ACCESS    read-write
    STATUS      current
                DESCRIPTION
                                "This counter reflects the number of Endpoint Configuration commands sent by Broadworks"
                ::=  {  mgcpStats  11  }

  bwMGCPStatsExtraCommandOuts OBJECT-TYPE
    SYNTAX      Counter32
    MAX-ACCESS    read-write
    STATUS      current
                DESCRIPTION
                                "This counter reflects the number of Extra Commands sent by BroadWorks"
                ::=  {  mgcpStats  12  }

  bwMGCPStatsModifyConnectionOuts OBJECT-TYPE
    SYNTAX      Counter32
    MAX-ACCESS    read-write
    STATUS      current
                DESCRIPTION
                                "This counter reflects the number of Modify Connection commands sent by BroadWorks"
                ::=  {  mgcpStats  13  }

  bwMGCPStatsNotificationRequestOuts  OBJECT-TYPE
    SYNTAX      Counter32
    MAX-ACCESS    read-write
    STATUS      current
                DESCRIPTION
                                "This counter reflects the number of Notification Request commands sent by BroadWorks"
                ::=  {  mgcpStats  14  }

  bwMGCPStatsNotifyIns  OBJECT-TYPE
    SYNTAX      Counter32
    MAX-ACCESS    read-write
    STATUS      current
                DESCRIPTION
                                "This counter reflects the number of Notify commands received by BroadWorks"
                ::=  {  mgcpStats  15  }

  bwMGCPStatsRestartInProgressIns OBJECT-TYPE
    SYNTAX      Counter32
    MAX-ACCESS    read-write
    STATUS      current
                DESCRIPTION
                                "This counter reflects the number of Restarts In Progress received by BroadWorks"
                ::=  {  mgcpStats  16  }

  bwMGCPStatsMGCPCommandResponseTable OBJECT-TYPE
    SYNTAX    SEQUENCE  OF  BwMGCPStatsMGCPCommandResponseEntry
    MAX-ACCESS  not-accessible
    STATUS    current
                DESCRIPTION
                        "This table contains the counters for all MGCP responses sent or received by BroadWorks.  Each counter is a 32-Bit counter. The response code is used to index into the table. Here are all the response codes:  100, 200, 250, 400, 401, 402, 403, 404, 500, 501, 502, 510, 511, 512, 513, 514, 515, 516, 517, 518, 519, 520, 521, 522, 523, 524, 525, 526, 527, 528, 529, 530, 531"
                ::=  { mgcpStats  17 }

  bwMGCPStatsMGCPCommandResponseEntry OBJECT-TYPE
    SYNTAX    BwMGCPStatsMGCPCommandResponseEntry
    MAX-ACCESS  not-accessible
    STATUS    current
                DESCRIPTION
                        "This row contains information on a particular MGCP status code received or sent in response to a MGCP command."
    INDEX   {  bwMGCPStatsMGCPCommandResponseCodeValue  }
                ::=  { bwMGCPStatsMGCPCommandResponseTable 1 }

        BwMGCPStatsMGCPCommandResponseEntry  ::=  SEQUENCE {
                bwMGCPStatsMGCPCommandResponseCodeValue  Integer32,
                bwMGCPStatsMGCPCommandResponseOuts  Counter32,
                bwMGCPStatsMGCPCommandResponseIns  Counter32
                }


  bwMGCPStatsMGCPCommandResponseCodeValue OBJECT-TYPE
    SYNTAX      Integer32  ( 100 .. 999  )
    MAX-ACCESS    not-accessible
    STATUS      current
                DESCRIPTION
                                "This integer represents an MGCP status code.  The rest of the information in this row is related to this value."
                ::=  {  bwMGCPStatsMGCPCommandResponseEntry  1  }


  bwMGCPStatsMGCPCommandResponseOuts  OBJECT-TYPE
    SYNTAX      Counter32
    MAX-ACCESS    read-write
    STATUS      current
                DESCRIPTION
                                "This counter represents the number of MGCP responses sent by BroadWorks in response to an MGCP command received."
                ::=  {  bwMGCPStatsMGCPCommandResponseEntry  2  }


  bwMGCPStatsMGCPCommandResponseIns OBJECT-TYPE
    SYNTAX      Counter32
    MAX-ACCESS    read-write
    STATUS      current
                DESCRIPTION
                                "This counter represents the number of MGCP responses received by BroadWorks in response to an MGCP command"
                ::=  {  bwMGCPStatsMGCPCommandResponseEntry  3  }

  bwMGCPStatsAuditConnectionResponseTable OBJECT-TYPE
    SYNTAX    SEQUENCE  OF  BwMGCPStatsAuditConnectionResponseEntry
    MAX-ACCESS  not-accessible
    STATUS    current
                DESCRIPTION
                        "This table contains the counters for MGCP responses received by BroadWorks to an Audit Connection command sent by BroadWorks..  Each counter is a 32-Bit counter. The response code is used to index into the table. Here are all the response codes:  100, 200, 250, 400, 401, 402, 403, 404, 500, 501, 502, 510, 511, 512, 513, 514, 515, 516, 517, 518, 519, 520, 521, 522, 523, 524, 525, 526, 527, 528, 529, 530, 531"
                ::=  { mgcpStats  18 }

  bwMGCPStatsAuditConnectionResponseEntry OBJECT-TYPE
    SYNTAX    BwMGCPStatsAuditConnectionResponseEntry
    MAX-ACCESS  not-accessible
    STATUS    current
                DESCRIPTION
                        "This row contains information on a particular MGCP status code received or sent in response to a MGCP command."
    INDEX   {  bwMGCPStatsAuditConnectionResponseCodeValue  }
                ::=  { bwMGCPStatsAuditConnectionResponseTable 1 }

        BwMGCPStatsAuditConnectionResponseEntry  ::=  SEQUENCE {
                bwMGCPStatsAuditConnectionResponseCodeValue  Integer32,
                bwMGCPStatsAuditConnectionResponseIns  Counter32
                }


  bwMGCPStatsAuditConnectionResponseCodeValue OBJECT-TYPE
    SYNTAX      Integer32  ( 100 .. 999  )
    MAX-ACCESS    not-accessible
    STATUS      current
                DESCRIPTION
                                "This integer represents an MGCP status code.  The rest of the information in this row is related to this value."
                ::=  {  bwMGCPStatsAuditConnectionResponseEntry  1  }


  bwMGCPStatsAuditConnectionResponseIns OBJECT-TYPE
    SYNTAX      Counter32
    MAX-ACCESS    read-write
    STATUS      current
                DESCRIPTION
                                "This counter represents the number of MGCP responses received by BroadWorks in response to an Audit Connection command sent."
                ::=  {  bwMGCPStatsAuditConnectionResponseEntry  2  }

  bwMGCPStatsAuditEndpointResponseTable OBJECT-TYPE
    SYNTAX    SEQUENCE  OF  BwMGCPStatsAuditEndpointResponseEntry
    MAX-ACCESS  not-accessible
    STATUS    current
                DESCRIPTION
                        "This table contains the counters for MGCP responses received by BroadWorks to an Audit Endpoint command sent by BroadWorks..  Each counter is a 32-Bit counter. The response code is used to index into the table. Here are all the response codes:  100, 200, 250, 400, 401, 402, 403, 404, 500, 501, 502, 510, 511, 512, 513, 514, 515, 516, 517, 518, 519, 520, 521, 522, 523, 524, 525, 526, 527, 528, 529, 530, 531"
                ::=  { mgcpStats  19 }

  bwMGCPStatsAuditEndpointResponseEntry OBJECT-TYPE
    SYNTAX    BwMGCPStatsAuditEndpointResponseEntry
    MAX-ACCESS  not-accessible
    STATUS    current
                DESCRIPTION
                        "This row contains information on a particular MGCP status code received or sent in response to an Audit Endpoint command."
    INDEX   {  bwMGCPStatsAuditEndpointResponseCodeValue  }
                ::=  { bwMGCPStatsAuditEndpointResponseTable 1 }

        BwMGCPStatsAuditEndpointResponseEntry  ::=  SEQUENCE {
                bwMGCPStatsAuditEndpointResponseCodeValue  Integer32,
                bwMGCPStatsAuditEndpointResponseIns  Counter32
                }


  bwMGCPStatsAuditEndpointResponseCodeValue OBJECT-TYPE
    SYNTAX      Integer32  ( 100 .. 999  )
    MAX-ACCESS    not-accessible
    STATUS      current
                DESCRIPTION
                                "This integer represents an MGCP status code.  The rest of the information in this row is related to this value."
                ::=  {  bwMGCPStatsAuditEndpointResponseEntry  1  }


  bwMGCPStatsAuditEndpointResponseIns OBJECT-TYPE
    SYNTAX      Counter32
    MAX-ACCESS    read-write
    STATUS      current
                DESCRIPTION
                                "This counter represents the number of MGCP responses received by BroadWorks in response to an Audit Endpoint command sent."
                ::=  {  bwMGCPStatsAuditEndpointResponseEntry  2  }

  bwMGCPStatsCreateConnectionResponseTable  OBJECT-TYPE
    SYNTAX    SEQUENCE  OF  BwMGCPStatsCreateConnectionResponseEntry
    MAX-ACCESS  not-accessible
    STATUS    current
                DESCRIPTION
                        "This table contains the counters for MGCP responses received by BroadWorks to an Create Connection command sent by BroadWorks..  Each counter is a 32-Bit counter. The response code is used to index into the table. Here are all the response codes:  100, 200, 250, 400, 401, 402, 403, 404, 500, 501, 502, 510, 511, 512, 513, 514, 515, 516, 517, 518, 519, 520, 521, 522, 523, 524, 525, 526, 527, 528, 529, 530, 531"
                ::=  { mgcpStats  20 }

  bwMGCPStatsCreateConnectionResponseEntry  OBJECT-TYPE
    SYNTAX    BwMGCPStatsCreateConnectionResponseEntry
    MAX-ACCESS  not-accessible
    STATUS    current
                DESCRIPTION
                        "This row contains information on a particular MGCP status code received or sent in response to an Create Connection command."
    INDEX   {  bwMGCPStatsCreateConnectionResponseCodeValue  }
                ::=  { bwMGCPStatsCreateConnectionResponseTable 1 }

        BwMGCPStatsCreateConnectionResponseEntry  ::=  SEQUENCE {
                bwMGCPStatsCreateConnectionResponseCodeValue  Integer32,
                bwMGCPStatsCreateConnectionResponseIns  Counter32
                }


  bwMGCPStatsCreateConnectionResponseCodeValue  OBJECT-TYPE
    SYNTAX      Integer32  ( 100 .. 999  )
    MAX-ACCESS    not-accessible
    STATUS      current
                DESCRIPTION
                                "This integer represents an MGCP status code.  The rest of the information in this row is related to this value."
                ::=  {  bwMGCPStatsCreateConnectionResponseEntry  1  }


  bwMGCPStatsCreateConnectionResponseIns  OBJECT-TYPE
    SYNTAX      Counter32
    MAX-ACCESS    read-write
    STATUS      current
                DESCRIPTION
                                "This counter represents the number of MGCP responses received by BroadWorks in response to an Create Connection command sent."
                ::=  {  bwMGCPStatsCreateConnectionResponseEntry  2  }

  bwMGCPStatsDeleteConnectionResponseTable  OBJECT-TYPE
    SYNTAX    SEQUENCE  OF  BwMGCPStatsDeleteConnectionResponseEntry
    MAX-ACCESS  not-accessible
    STATUS    current
                DESCRIPTION
                        "This table contains the counters for MGCP responses received by BroadWorks to an Create Connection command sent by BroadWorks..  Each counter is a 32-Bit counter. The response code is used to index into the table. Here are all the response codes:  100, 200, 250, 400, 401, 402, 403, 404, 500, 501, 502, 510, 511, 512, 513, 514, 515, 516, 517, 518, 519, 520, 521, 522, 523, 524, 525, 526, 527, 528, 529, 530, 531"
                ::=  { mgcpStats  21 }

  bwMGCPStatsDeleteConnectionResponseEntry  OBJECT-TYPE
    SYNTAX    BwMGCPStatsDeleteConnectionResponseEntry
    MAX-ACCESS  not-accessible
    STATUS    current
                DESCRIPTION
                        "This row contains information on a particular MGCP status code received or sent in response to an Create Connection command."
    INDEX   {  bwMGCPStatsDeleteConnectionResponseCodeValue  }
                ::=  { bwMGCPStatsDeleteConnectionResponseTable 1 }

        BwMGCPStatsDeleteConnectionResponseEntry  ::=  SEQUENCE {
                bwMGCPStatsDeleteConnectionResponseCodeValue  Integer32,
                bwMGCPStatsDeleteAgentConnectionResponseIns  Counter32,
                bwMGCPStatsDeleteConnectionResponseIns  Counter32,
                bwMGCPStatsDeleteGatewayConnectionResponseOuts  Counter32
                }


  bwMGCPStatsDeleteConnectionResponseCodeValue  OBJECT-TYPE
    SYNTAX      Integer32  ( 100 .. 999  )
    MAX-ACCESS    not-accessible
    STATUS      current
                DESCRIPTION
                                "This integer represents an MGCP status code.  The rest of the information in this row is related to this value."
                ::=  {  bwMGCPStatsDeleteConnectionResponseEntry  1  }


  bwMGCPStatsDeleteAgentConnectionResponseIns OBJECT-TYPE
    SYNTAX      Counter32
    MAX-ACCESS    read-write
    STATUS      current
                DESCRIPTION
                                "This counter represents the number of MGCP responses received by BroadWorks in response to a Delete Agent Connection command sent."
                ::=  {  bwMGCPStatsDeleteConnectionResponseEntry  2  }


  bwMGCPStatsDeleteConnectionResponseIns  OBJECT-TYPE
    SYNTAX      Counter32
    MAX-ACCESS    read-write
    STATUS      current
                DESCRIPTION
                                "This counter represents the number of MGCP responses received by BroadWorks in response to a Delete Connection command sent."
                ::=  {  bwMGCPStatsDeleteConnectionResponseEntry  3  }


  bwMGCPStatsDeleteGatewayConnectionResponseOuts  OBJECT-TYPE
    SYNTAX      Counter32
    MAX-ACCESS    read-write
    STATUS      current
                DESCRIPTION
                                "This counter represents the number of MGCP responses received by BroadWorks in response to a Delete Gateway Connection command sent."
                ::=  {  bwMGCPStatsDeleteConnectionResponseEntry  4  }

  bwMGCPStatsEndpointConfigurationResponseTable OBJECT-TYPE
    SYNTAX    SEQUENCE  OF  BwMGCPStatsEndpointConfigurationResponseEntry
    MAX-ACCESS  not-accessible
    STATUS    current
                DESCRIPTION
                        "This table contains the counters for MGCP responses received by BroadWorks to an Endpoint Configuration command sent by BroadWorks..  Each counter is a 32-Bit counter. The response code is used to index into the table. Here are all the response codes:  100, 200, 250, 400, 401, 402, 403, 404, 500, 501, 502, 510, 511, 512, 513, 514, 515, 516, 517, 518, 519, 520, 521, 522, 523, 524, 525, 526, 527, 528, 529, 530, 531"
                ::=  { mgcpStats  22 }

  bwMGCPStatsEndpointConfigurationResponseEntry OBJECT-TYPE
    SYNTAX    BwMGCPStatsEndpointConfigurationResponseEntry
    MAX-ACCESS  not-accessible
    STATUS    current
                DESCRIPTION
                        "This row contains information on a particular MGCP status code received or sent in response to an Endpoint Configuration command."
    INDEX   {  bwMGCPStatsEndpointConfigurationResponseCodeValue  }
                ::=  { bwMGCPStatsEndpointConfigurationResponseTable 1 }

        BwMGCPStatsEndpointConfigurationResponseEntry  ::=  SEQUENCE {
                bwMGCPStatsEndpointConfigurationResponseCodeValue  Integer32,
                bwMGCPStatsEndpointConfigurationResponseIns  Counter32
                }


  bwMGCPStatsEndpointConfigurationResponseCodeValue OBJECT-TYPE
    SYNTAX      Integer32  ( 100 .. 999  )
    MAX-ACCESS    not-accessible
    STATUS      current
                DESCRIPTION
                                "This integer represents an MGCP status code.  The rest of the information in this row is related to this value."
                ::=  {  bwMGCPStatsEndpointConfigurationResponseEntry  1  }


  bwMGCPStatsEndpointConfigurationResponseIns OBJECT-TYPE
    SYNTAX      Counter32
    MAX-ACCESS    read-write
    STATUS      current
                DESCRIPTION
                                "This counter represents the number of MGCP responses received by BroadWorks in response to an Endpoint Configuration command sent."
                ::=  {  bwMGCPStatsEndpointConfigurationResponseEntry  2  }

  bwMGCPStatsExtraCommandResponseTable  OBJECT-TYPE
    SYNTAX    SEQUENCE  OF  BwMGCPStatsExtraCommandResponseEntry
    MAX-ACCESS  not-accessible
    STATUS    current
                DESCRIPTION
                        "This table contains the counters for MGCP responses received by BroadWorks to an Extra Command command sent by BroadWorks..  Each counter is a 32-Bit counter. The response code is used to index into the table. Here are all the response codes:  100, 200, 250, 400, 401, 402, 403, 404, 500, 501, 502, 510, 511, 512, 513, 514, 515, 516, 517, 518, 519, 520, 521, 522, 523, 524, 525, 526, 527, 528, 529, 530, 531"
                ::=  { mgcpStats  23 }

  bwMGCPStatsExtraCommandResponseEntry  OBJECT-TYPE
    SYNTAX    BwMGCPStatsExtraCommandResponseEntry
    MAX-ACCESS  not-accessible
    STATUS    current
                DESCRIPTION
                        "This row contains information on a particular MGCP status code received or sent in response to an Extra Command command."
    INDEX   {  bwMGCPStatsExtraCommandResponseCodeValue  }
                ::=  { bwMGCPStatsExtraCommandResponseTable 1 }

        BwMGCPStatsExtraCommandResponseEntry  ::=  SEQUENCE {
                bwMGCPStatsExtraCommandResponseCodeValue  Integer32,
                bwMGCPStatsExtraCommandResponseIns  Counter32
                }


  bwMGCPStatsExtraCommandResponseCodeValue  OBJECT-TYPE
    SYNTAX      Integer32  ( 100 .. 999  )
    MAX-ACCESS    not-accessible
    STATUS      current
                DESCRIPTION
                                "This integer represents an MGCP status code.  The rest of the information in this row is related to this value."
                ::=  {  bwMGCPStatsExtraCommandResponseEntry  1  }


  bwMGCPStatsExtraCommandResponseIns  OBJECT-TYPE
    SYNTAX      Counter32
    MAX-ACCESS    read-write
    STATUS      current
                DESCRIPTION
                                "This counter represents the number of MGCP responses received by BroadWorks in response to an Extra Command command sent."
                ::=  {  bwMGCPStatsExtraCommandResponseEntry  2  }

  bwMGCPStatsModifyConnectionResponseTable  OBJECT-TYPE
    SYNTAX    SEQUENCE  OF  BwMGCPStatsModifyConnectionResponseEntry
    MAX-ACCESS  not-accessible
    STATUS    current
                DESCRIPTION
                        "This table contains the counters for MGCP responses received by BroadWorks to a Modify Connection command sent by BroadWorks..  Each counter is a 32-Bit counter. The response code is used to index into the table. Here are all the response codes:  100, 200, 250, 400, 401, 402, 403, 404, 500, 501, 502, 510, 511, 512, 513, 514, 515, 516, 517, 518, 519, 520, 521, 522, 523, 524, 525, 526, 527, 528, 529, 530, 531"
                ::=  { mgcpStats  24 }

  bwMGCPStatsModifyConnectionResponseEntry  OBJECT-TYPE
    SYNTAX    BwMGCPStatsModifyConnectionResponseEntry
    MAX-ACCESS  not-accessible
    STATUS    current
                DESCRIPTION
                        "This row contains information on a particular MGCP status code received or sent in response to a Modify Connection command."
    INDEX   {  bwMGCPStatsModifyConnectionResponseCodeValue  }
                ::=  { bwMGCPStatsModifyConnectionResponseTable 1 }

        BwMGCPStatsModifyConnectionResponseEntry  ::=  SEQUENCE {
                bwMGCPStatsModifyConnectionResponseCodeValue  Integer32,
                bwMGCPStatsModifyConnectionResponseIns  Counter32
                }


  bwMGCPStatsModifyConnectionResponseCodeValue  OBJECT-TYPE
    SYNTAX      Integer32  ( 100 .. 999  )
    MAX-ACCESS    not-accessible
    STATUS      current
                DESCRIPTION
                                "This integer represents an MGCP status code.  The rest of the information in this row is related to this value."
                ::=  {  bwMGCPStatsModifyConnectionResponseEntry  1  }


  bwMGCPStatsModifyConnectionResponseIns  OBJECT-TYPE
    SYNTAX      Counter32
    MAX-ACCESS    read-write
    STATUS      current
                DESCRIPTION
                                "This counter represents the number of MGCP responses received by BroadWorks in response to a Modify Connection command sent."
                ::=  {  bwMGCPStatsModifyConnectionResponseEntry  2  }

  bwMGCPStatsNotificationRequestResponseTable OBJECT-TYPE
    SYNTAX    SEQUENCE  OF  BwMGCPStatsNotificationRequestResponseEntry
    MAX-ACCESS  not-accessible
    STATUS    current
                DESCRIPTION
                        "This table contains the counters for MGCP responses received by BroadWorks to a Notification Request command sent by BroadWorks..  Each counter is a 32-Bit counter. The response code is used to index into the table. Here are all the response codes:  100, 200, 250, 400, 401, 402, 403, 404, 500, 501, 502, 510, 511, 512, 513, 514, 515, 516, 517, 518, 519, 520, 521, 522, 523, 524, 525, 526, 527, 528, 529, 530, 531"
                ::=  { mgcpStats  25 }

  bwMGCPStatsNotificationRequestResponseEntry OBJECT-TYPE
    SYNTAX    BwMGCPStatsNotificationRequestResponseEntry
    MAX-ACCESS  not-accessible
    STATUS    current
                DESCRIPTION
                        "This row contains information on a particular MGCP status code received or sent in response to a Notification Request command."
    INDEX   {  bwMGCPStatsNotificationRequestResponseCodeValue  }
                ::=  { bwMGCPStatsNotificationRequestResponseTable 1 }

        BwMGCPStatsNotificationRequestResponseEntry  ::=  SEQUENCE {
                bwMGCPStatsNotificationRequestResponseCodeValue  Integer32,
                bwMGCPStatsNotificationRequestResponseIns  Counter32
                }


  bwMGCPStatsNotificationRequestResponseCodeValue OBJECT-TYPE
    SYNTAX      Integer32  ( 100 .. 999  )
    MAX-ACCESS    not-accessible
    STATUS      current
                DESCRIPTION
                                "This integer represents an MGCP status code.  The rest of the information in this row is related to this value."
                ::=  {  bwMGCPStatsNotificationRequestResponseEntry  1  }


  bwMGCPStatsNotificationRequestResponseIns OBJECT-TYPE
    SYNTAX      Counter32
    MAX-ACCESS    read-write
    STATUS      current
                DESCRIPTION
                                "This counter represents the number of MGCP responses received by BroadWorks in response to a Notification Request command sent."
                ::=  {  bwMGCPStatsNotificationRequestResponseEntry  2  }

  bwMGCPStatsNotifyResponseTable  OBJECT-TYPE
    SYNTAX    SEQUENCE  OF  BwMGCPStatsNotifyResponseEntry
    MAX-ACCESS  not-accessible
    STATUS    current
                DESCRIPTION
                        "This table contains the counters for MGCP responses sent by BroadWorks to a Notify command received by BroadWorks..  Each counter is a 32-Bit counter. The response code is used to index into the table. Here are all the response codes:  100, 200, 250, 400, 401, 402, 403, 404, 500, 501, 502, 510, 511, 512, 513, 514, 515, 516, 517, 518, 519, 520, 521, 522, 523, 524, 525, 526, 527, 528, 529, 530, 531"
                ::=  { mgcpStats  26 }

  bwMGCPStatsNotifyResponseEntry  OBJECT-TYPE
    SYNTAX    BwMGCPStatsNotifyResponseEntry
    MAX-ACCESS  not-accessible
    STATUS    current
                DESCRIPTION
                        "This row contains information on a particular MGCP status code sent in response to a Notify command."
    INDEX   {  bwMGCPStatsNotifyResponseCodeValue  }
                ::=  { bwMGCPStatsNotifyResponseTable 1 }

        BwMGCPStatsNotifyResponseEntry  ::=  SEQUENCE {
                bwMGCPStatsNotifyResponseCodeValue  Integer32,
                bwMGCPStatsNotifyResponseOuts  Counter32
                }


  bwMGCPStatsNotifyResponseCodeValue  OBJECT-TYPE
    SYNTAX      Integer32  ( 100 .. 999  )
    MAX-ACCESS    not-accessible
    STATUS      current
                DESCRIPTION
                                "This integer represents an MGCP status code.  The rest of the information in this row is related to this value."
                ::=  {  bwMGCPStatsNotifyResponseEntry  1  }


  bwMGCPStatsNotifyResponseOuts OBJECT-TYPE
    SYNTAX      Counter32
    MAX-ACCESS    read-write
    STATUS      current
                DESCRIPTION
                                "This counter represents the number of MGCP responses sent by BroadWorks in response to a Notify command received."
                ::=  {  bwMGCPStatsNotifyResponseEntry  2  }

  bwMGCPStatsRestartInProgressResponseTable OBJECT-TYPE
    SYNTAX    SEQUENCE  OF  BwMGCPStatsRestartInProgressResponseEntry
    MAX-ACCESS  not-accessible
    STATUS    current
                DESCRIPTION
                        "This table contains the counters for MGCP responses sent by BroadWorks to a Restart In Progress command received by BroadWorks..  Each counter is a 32-Bit counter. The response code is used to index into the table. Here are all the response codes:  100, 200, 250, 400, 401, 402, 403, 404, 500, 501, 502, 510, 511, 512, 513, 514, 515, 516, 517, 518, 519, 520, 521, 522, 523, 524, 525, 526, 527, 528, 529, 530, 531"
                ::=  { mgcpStats  27 }

  bwMGCPStatsRestartInProgressResponseEntry OBJECT-TYPE
    SYNTAX    BwMGCPStatsRestartInProgressResponseEntry
    MAX-ACCESS  not-accessible
    STATUS    current
                DESCRIPTION
                        "This row contains information on a particular MGCP status code sent in response to a Restart In Progress command."
    INDEX   {  bwMGCPStatsRestartInProgressResponseCodeValue  }
                ::=  { bwMGCPStatsRestartInProgressResponseTable 1 }

        BwMGCPStatsRestartInProgressResponseEntry  ::=  SEQUENCE {
                bwMGCPStatsRestartInProgressResponseCodeValue  Integer32,
                bwMGCPStatsRestartInProgressResponseOuts  Counter32
                }


  bwMGCPStatsRestartInProgressResponseCodeValue OBJECT-TYPE
    SYNTAX      Integer32  ( 100 .. 999  )
    MAX-ACCESS    not-accessible
    STATUS      current
                DESCRIPTION
                                "This integer represents an MGCP status code.  The rest of the information in this row is related to this value."
                ::=  {  bwMGCPStatsRestartInProgressResponseEntry  1  }


  bwMGCPStatsRestartInProgressResponseOuts  OBJECT-TYPE
    SYNTAX      Counter32
    MAX-ACCESS    read-write
    STATUS      current
                DESCRIPTION
                                "This counter represents the number of MGCP responses sent by BroadWorks in response to a Restart In Progress command received."
                ::=  {  bwMGCPStatsRestartInProgressResponseEntry  2  }

  bwMGCPStatsDialToneDelay  OBJECT-TYPE
    SYNTAX      Gauge32
    MAX-ACCESS    read-write
    STATUS      current
                DESCRIPTION
                                "This gauge measures the average time (in milliseconds) between receipt of NTFY indicating off-hook and transmission of RQNT indicating dial-tone and request for digits"
                ::=  {  mgcpStats  28  }

  bwMGCPStatsMinDialToneDelay OBJECT-TYPE
    SYNTAX      Gauge32
    MAX-ACCESS    read-write
    STATUS      current
                DESCRIPTION
                                "This measures the shortest MGCP dial-tone delay sampled since the system was started or since this measurement was cleared"
                ::=  {  mgcpStats  29  }

  bwMGCPStatsMaxDialToneDelay OBJECT-TYPE
    SYNTAX      Gauge32
    MAX-ACCESS    read-write
    STATUS      current
                DESCRIPTION
                                "This measures the longest MGCP dial-tone delay sampled since the system was started or since this measurement was cleared"
                ::=  {  mgcpStats  30  }

  bwMGCPStatsSetupSignalDelay OBJECT-TYPE
    SYNTAX      Gauge32
    MAX-ACCESS    read-write
    STATUS      current
                DESCRIPTION
                                "This gauge is applicable to MGCP originated calls.  It measures the average time (in milliseconds) it takes between the receipt of a NTFY message with digits dialed for the origination of a new call and the transmission of an INVITE (Sip terminator), RQNT (MGCP terminator with in-band ringback), or CRCX (MGCP terminator without in-band ringback) to the primary device of the original called party (in the case of intra-group call) or to the network element of the original called party (in the case of a call to the PSTN).  Delays incurred by a dip to the Network Server are removed from the measurement.  This measurement is intended to reflect internal queuing, scheduling, and processing delays.
The same clarifications as for bwSipStatsSetupSignalDelay apply to bwMGCPStatsSetupSignalDelay"
                ::=  {  mgcpStats  31  }

  bwMGCPStatsMinSetupSignalDelay  OBJECT-TYPE
    SYNTAX      Gauge32
    MAX-ACCESS    read-write
    STATUS      current
                DESCRIPTION
                                "This measures the shortest MGCP setup-signal delay sampled since the system was started or since this measurement was cleared"
                ::=  {  mgcpStats  32  }

  bwMGCPStatsMaxSetupSignalDelay  OBJECT-TYPE
    SYNTAX      Gauge32
    MAX-ACCESS    read-write
    STATUS      current
                DESCRIPTION
                                "This measures the shortest MGCP setup-signal delay sampled since the system was started or since this measurement was cleared"
                ::=  {  mgcpStats  33  }

  bwMGCPStatsAnswerSignalDelay  OBJECT-TYPE
    SYNTAX      Gauge32
    MAX-ACCESS    read-write
    STATUS      current
                DESCRIPTION
                                "This gauge measures the average time (in milliseconds) between the receipt of a 200 OK message indicating answer or a NTFY off-hook indicating answer and the transmission of a MDCX indicating answer to the originator.   This measurement is intended to reflect internal queuing, scheduling, and processing delays.
This gauge is applicable to only the MGCP originated calls for which the setup-signal delay is measured.  Answer signal delay is not measured when the call has been forwarded, redirected, or when the call has encountered route advancing."
                ::=  {  mgcpStats  34  }

  bwMGCPStatsMinAnswerSignalDelay OBJECT-TYPE
    SYNTAX      Gauge32
    MAX-ACCESS    read-write
    STATUS      current
                DESCRIPTION
                                "This measures the shortest MGCP answer-signal delay sampled since the system was started or since this measurement was cleared."
                ::=  {  mgcpStats  35  }

  bwMGCPStatsMaxAnswerSignalDelay OBJECT-TYPE
    SYNTAX      Gauge32
    MAX-ACCESS    read-write
    STATUS      current
                DESCRIPTION
                                "This measures the longest MGCP answer-signal delay sampled since the system was started or since this measurement was cleared."
                ::=  {  mgcpStats  36  }

  bwMGCPStatsMessageRetryPercentage OBJECT-TYPE
    SYNTAX      Gauge32
    MAX-ACCESS    read-only
    STATUS      current
                DESCRIPTION
                                "This gauge measures the percentage of MGCP requests sent due to retry.  Of up to the last 100 requests sent, this gauge calculates the percentage sent due to retransmission (i.e. - gauge = MGCP request retransmissions  / (MGCP request initial transmissions + MGCP request retransmissions)."
                ::=  {  mgcpStats  37  }


-- Protocol :: MCP ...........................................

  bwMCPCommandsTransmitted  OBJECT-TYPE
    SYNTAX      Counter32
    MAX-ACCESS    read-write
    STATUS      obsolete
                DESCRIPTION
                                "Incremented each time an MCP command is transmitted.

This object is obsolete. The MCP interface is no longer used by the Application Server."

                ::=  {  mcpStats  1  }

  bwMCPCommandsRetransmitted  OBJECT-TYPE
    SYNTAX      Counter32
    MAX-ACCESS    read-write
    STATUS      obsolete
                DESCRIPTION
                                "Incremented each time an MCP command is re-transmitted.

This object is obsolete. The MCP interface is no longer used by the Application Server."

                ::=  {  mcpStats  2  }

  bwMCPNotificationsReceived  OBJECT-TYPE
    SYNTAX      Counter32
    MAX-ACCESS    read-write
    STATUS      obsolete
                DESCRIPTION
                                "Incremented each time an MCP notification is received

This object is obsolete. The MCP interface is no longer used by the Application Server."

                ::=  {  mcpStats  3  }

  bwMCPResourceAllocAttempts  OBJECT-TYPE
    SYNTAX      Counter32
    MAX-ACCESS    read-write
    STATUS      obsolete
                DESCRIPTION
                                "A resource allocation request is defined as an application layer request for a Media Server resource request (i.e.  IVR connection, bridge).  This counter is incremented by the MCP protocol layer upon receipt of the resource allocation request from the application layer (i.e.  prior transmission of any MCP resource allocation Command)

This object is obsolete. The MCP interface is no longer used by the Application Server."

                ::=  {  mcpStats  4  }

  bwMCPResourceAllocFailures  OBJECT-TYPE
    SYNTAX      Counter32
    MAX-ACCESS    read-write
    STATUS      obsolete
                DESCRIPTION
                                "A resource allocation request is defined as an application layer request for a Media Server resource request (i.e.  IVR connection, bridge).  This counter is incremented by the MCP protocol layer when resource allocation Commands have been transmitted toward all available Media Servers and no resource on any Media Server was allocated.

This object is obsolete. The MCP interface is no longer used by the Application Server."

                ::=  {  mcpStats  5  }

-- Protocol :: Incoming Mail Server ...........................................

  bwIMSSuccessfulConnectionAttempts OBJECT-TYPE
    SYNTAX      Counter32
    MAX-ACCESS    read-write
    STATUS      current
                DESCRIPTION
                                "This counter reflects the number of successful connection to incoming mail server."
                ::=  {  imsStats  1  }

  bwIMSUnsuccessfulConnectionAttempts OBJECT-TYPE
    SYNTAX      Counter32
    MAX-ACCESS    read-write
    STATUS      current
                DESCRIPTION
                                "This counter reflects the total number of unsuccessful connection to incoming mail server."
                ::=  {  imsStats  2  }

  bwIMSSuccessfulDownLoadAttempts OBJECT-TYPE
    SYNTAX      Counter32
    MAX-ACCESS    read-write
    STATUS      current
                DESCRIPTION
                                "This counter reflects the number of messages downloaded  from incoming mail server."
                ::=  {  imsStats  3  }

  bwIMSUnsuccessfulDownLoadAttempts OBJECT-TYPE
    SYNTAX      Counter32
    MAX-ACCESS    read-write
    STATUS      current
                DESCRIPTION
                                "This counter reflects the number of unsuccessful   message download attempted on incoming mail server."
                ::=  {  imsStats  4  }

  bwIMSMaxSessions  OBJECT-TYPE
    SYNTAX      Gauge32
    MAX-ACCESS    read-only
    STATUS      current
                DESCRIPTION
                                "Maximum number of incoming mail server sessions simultaneously active since the system was started. A session is defined as a complete dialog between the execution server and the incoming mail server, and includes elements such as mailbox information requests, message download requests, and idle time."
                ::=  {  imsStats  5  }

  bwIMSAvgSessions  OBJECT-TYPE
    SYNTAX      Gauge32
    MAX-ACCESS    read-only
    STATUS      current
                DESCRIPTION
                                "Average number of incoming mail server sessions simultaneously active, based on a rolling average over the last 100 sessions.  Each data point is computed right after the creation of a session. A session is defined as a complete dialog between the execution server and the incoming mail server, and includes elements such as mailbox information requests, message download requests, and idle time."
                ::=  {  imsStats  6  }

  bwIMSMaxThreads OBJECT-TYPE
    SYNTAX      Gauge32
    MAX-ACCESS    read-only
    STATUS      current
                DESCRIPTION
                                "Maximum number of incoming mail server threads simultaneously active since the system was started.  IMS threads are used when a session actively communicates with an IMS, and waits for a response.  A session does not use an IMS thread while it is idle, e.g. prompting or waiting for user input."
                ::=  {  imsStats  7  }

  bwIMSAvgThreads OBJECT-TYPE
    SYNTAX      Gauge32
    MAX-ACCESS    read-only
    STATUS      current
                DESCRIPTION
                                "Average number of incoming mail server threads simultaneously active, based on a rolling average over the last 100 sessions. Each data point is computed right after the creation of a session. IMS threads are used when a session actively communicates with an IMS, and waits for a response.  A session does not use an IMS thread while it is idle, e.g. prompting or waiting for user input."
                ::=  {  imsStats  8  }

  bwIMSMaxServiceTime OBJECT-TYPE
    SYNTAX      Gauge32
    MAX-ACCESS    read-only
    STATUS      current
                DESCRIPTION
                                "Maximum time in milliseconds required to process an incoming mail server request, since the system was started.  This service time includes any queuing time if applicable.  This time also includes the time required by the IMS to respond to a request such as a mailbox information request, or a message download request."
                ::=  {  imsStats  9  }

  bwIMSAvgServiceTime OBJECT-TYPE
    SYNTAX      Gauge32
    MAX-ACCESS    read-only
    STATUS      current
                DESCRIPTION
                                "Average time in milliseconds required to process an incoming mail server request, based on a rolling average over the last 100 requests.  This service time includes any queuing time if applicable.  This time also includes the time required by the IMS to respond to a request such as a mailbox information request, or a message download request."
                ::=  {  imsStats  10 }

  bwIMSNumKeepAlive OBJECT-TYPE
    SYNTAX      Counter32
    MAX-ACCESS    read-write
    STATUS      current
                DESCRIPTION
                                "Number of times a keep-alive message was sent to an incoming mail server.  Such a keep-alive message is sent when an IMS session lasts several minutes."
                ::=  {  imsStats  11 }

  bwIMSNumDroppedRequests OBJECT-TYPE
    SYNTAX      Counter32
    MAX-ACCESS    read-write
    STATUS      current
                DESCRIPTION
                                "Number of incoming mail server requests dropped because the number of IMS threads was too low, and the queue was full.  Note that a single session can make several requests to the IMS."
                ::=  {  imsStats  12 }

-- Protocol :: CAP ...........................................

  bwCAPStatsRegisterRequests  OBJECT-TYPE
    SYNTAX      Counter32
    MAX-ACCESS    read-write
    STATUS      current
                DESCRIPTION
                                "This counter reflects the number of CAP registerRequest messages that have been received by the system."
                ::=  {  capStats  1  }

  bwCAPStatsUnRegistersIn OBJECT-TYPE
    SYNTAX      Counter32
    MAX-ACCESS    read-write
    STATUS      current
                DESCRIPTION
                                "This counter reflects the number of CAP unRegister messages that have been received by the system."
                ::=  {  capStats  2  }

  bwCAPStatsUnRegistersOut  OBJECT-TYPE
    SYNTAX      Counter32
    MAX-ACCESS    read-write
    STATUS      current
                DESCRIPTION
                                "This counter reflects the number of CAP unRegister messages that have been sent out by the system."
                ::=  {  capStats  3  }

  bwCAPStatsSessionUpdatesOut OBJECT-TYPE
    SYNTAX      Counter32
    MAX-ACCESS    read-write
    STATUS      current
                DESCRIPTION
                                "This counter reflects the number of CAP sessionUpdate messages that have been sent out by the system."
                ::=  {  capStats  4  }

  bwCAPStatsProfileUpdatesOut OBJECT-TYPE
    SYNTAX      Counter32
    MAX-ACCESS    read-write
    STATUS      current
                DESCRIPTION
                                "This counter reflects the number of CAP profileUpdate messages that have been sent out by the system."
                ::=  {  capStats  5  }

  bwCAPStatsCallUpdatesOut  OBJECT-TYPE
    SYNTAX      Counter32
    MAX-ACCESS    read-write
    STATUS      current
                DESCRIPTION
                                "ThisThis counter reflects the number of CAP callUpdate messages that have been sent out by the system."
                ::=  {  capStats  6  }

  bwCAPStatsCallActionsIn OBJECT-TYPE
    SYNTAX      Counter32
    MAX-ACCESS    read-write
    STATUS      current
                DESCRIPTION
                                "This counter reflects the number of CAP callAction messages that have been received by the system."
                ::=  {  capStats  7  }

  bwCAPStatsAcknowledgementsIn  OBJECT-TYPE
    SYNTAX      Counter32
    MAX-ACCESS    read-write
    STATUS      current
                DESCRIPTION
                                "This counter reflects the number of CAP acknowledgement messages that have been received by the system."
                ::=  {  capStats  8  }


  bwCAPStatsAcknowledgementsOut OBJECT-TYPE
    SYNTAX      Counter32
    MAX-ACCESS    read-write
    STATUS      obsolete
                DESCRIPTION
                                "This counter could not be incremented anymore. It is now obsolete."
                ::=  {  capStats  9  }

  bwCAPStatsAclViolations OBJECT-TYPE
    SYNTAX      Counter32
    MAX-ACCESS    read-write
    STATUS      current
                DESCRIPTION
                                "This counter reflects the number of incoming CAP connections that have been rejected because the connecting machine is not in the CAP access control list.  This counter causes an alarm to be generated when its threshold value is reached."
                ::=  {  capStats  10  }

  bwCAPStatsUnsuccessfulRegisterResponses OBJECT-TYPE
    SYNTAX      Counter32
    MAX-ACCESS    read-write
    STATUS      current
                DESCRIPTION
                                "This counter reflects the number of unsuccessful CAP registerResponse messages that the system sends out.  This counter causes an alarm to be generated when its threshold value is reached."
                ::=  {  capStats  11  }

  bwCAPStatsRegisterResponsesTable  OBJECT-TYPE
    SYNTAX    SEQUENCE  OF  BwCAPStatsRegisterResponsesEntry
    MAX-ACCESS  not-accessible
    STATUS    current
                DESCRIPTION
                        "This table contains counters for the different types of CAP registerResponse messages sent by the system in response to a received CAP registerRequest message.  The following are the various types of registerResponse messages and an index value identifying each type: 1 - successful registerResponse, 2 - unsuccessful registerResponse (unknown user id), 3 - unsuccessful registerResponse (incorrect user credentials), 4 - unsuccessful registerResponse (feature unauthorized)."
                ::=  { capStats  12 }

  bwCAPStatsCallControlInfosOut OBJECT-TYPE
    SYNTAX      Counter32
    MAX-ACCESS    read-write
    STATUS      current
                DESCRIPTION
                                "This counter is incremented whenever a CAP callControlInfo message is sent out by the system"
                ::=  {  capStats  13  }

  bwCAPStatsRegisterAuthentications OBJECT-TYPE
    SYNTAX      Counter32
    MAX-ACCESS    read-write
    STATUS      current
                DESCRIPTION
                                "This counter is incremented whenever the Execution Server receives a registerAuthentication CAP message"
                ::=  {  capStats  14  }

  bwCAPStatsResponseAuthentications OBJECT-TYPE
    SYNTAX      Counter32
    MAX-ACCESS    read-write
    STATUS      current
                DESCRIPTION
                                "This counter is incremented whenever the Execution Server receives a responseAuthentication CAP message"
                ::=  {  capStats  15  }

  bwCAPStatsInfoRequests  OBJECT-TYPE
    SYNTAX      Counter32
    MAX-ACCESS    read-write
    STATUS      current
                DESCRIPTION
                                "This counter is incremented whenever the Execution Server receives a infoRequest CAP message"
                ::=  {  capStats  16  }

  bwCAPStatsInfoResponses OBJECT-TYPE
    SYNTAX      Counter32
    MAX-ACCESS    read-write
    STATUS      current
                DESCRIPTION
                                "This counter is incremented whenever the Execution Server receives a infoResponse CAP message"
                ::=  {  capStats  17  }

  bwCAPStatsExternalNotifies  OBJECT-TYPE
    SYNTAX      Counter32
    MAX-ACCESS    read-write
    STATUS      current
                DESCRIPTION
                                "This counter is incremented whenever the Execution Server receives a externalNotify CAP message"
                ::=  {  capStats  18  }

  bwCAPMonitoringUsersRequests  OBJECT-TYPE
    SYNTAX      Counter32
    MAX-ACCESS    read-write
    STATUS      current
                DESCRIPTION
                                "The number of monitoringUsersRequest CAP messages received."
                ::=  {  capStats  19  }

  bwCAPMonitoringUsersResponses OBJECT-TYPE
    SYNTAX      Counter32
    MAX-ACCESS    read-write
    STATUS      current
                DESCRIPTION
                                "The number of monitoringUsersResponse CAP messages sent."
                ::=  {  capStats  20  }

  bwCAPStatsQueueUpdatesOut OBJECT-TYPE
    SYNTAX      Counter32
    MAX-ACCESS    read-write
    STATUS      current
                DESCRIPTION
                                "This counter reflects the number of CAP queueUpdate messages that have been sent out by the system."
                ::=  {  capStats  21  }

  bwCAPStatsQueueActionsIn  OBJECT-TYPE
    SYNTAX      Counter32
    MAX-ACCESS    read-write
    STATUS      current
                DESCRIPTION
                                "This counter reflects the number of CAP queueAction messages that have been received by the system."
                ::=  {  capStats  22  }

  bwCAPStatsDatagramsIn OBJECT-TYPE
    SYNTAX      Counter32
    MAX-ACCESS    read-write
    STATUS      current
                DESCRIPTION
                                "This counter reflects the number of CAP datagram  commands  that have been received by the system."
                ::=  {  capStats  23  }

  bwCAPStatsDatagramsOut  OBJECT-TYPE
    SYNTAX      Counter32
    MAX-ACCESS    read-write
    STATUS      current
                DESCRIPTION
                                "This counter reflects the number of CAP datagram  commands  that have been sent by the system."
                ::=  {  capStats  24  }

        bwCAPStatsTotalMsgs OBJECT-TYPE
    SYNTAX      Counter32
    MAX-ACCESS    read-write
    STATUS      current
                DESCRIPTION
                                "This counter cumulates the total number of CAP messages that have been handled by the system."
                ::=  {  capStats  25  }

-- CAP :: Response TABLE ...........................................

  bwCAPStatsRegisterResponsesEntry  OBJECT-TYPE
    SYNTAX    BwCAPStatsRegisterResponsesEntry
    MAX-ACCESS  not-accessible
    STATUS    current
                DESCRIPTION
                        "This row contains information on a particular CAP registerResponse type sent out by the system."
    INDEX   {  bwCAPStatsRegisterResponsesType  }
                ::=  { bwCAPStatsRegisterResponsesTable 1 }

        BwCAPStatsRegisterResponsesEntry  ::=  SEQUENCE {
                bwCAPStatsRegisterResponsesType  Unsigned32,
                bwCAPStatsRegisterResponses  Counter32
                }


  bwCAPStatsRegisterResponsesType OBJECT-TYPE
    SYNTAX      Unsigned32
    MAX-ACCESS    read-only
    STATUS      current
                DESCRIPTION
                                "This integer represents a registerResponse type.  This is also the index into the table."
                ::=  {  bwCAPStatsRegisterResponsesEntry  1  }

  bwCAPStatsRegisterResponses OBJECT-TYPE
    SYNTAX      Counter32
    MAX-ACCESS    read-write
    STATUS      current
                DESCRIPTION
                                "This counter reflects the number of CAP registerResponse messages that have been sent out by the system."
                ::=  {  bwCAPStatsRegisterResponsesEntry  2  }

-- Protocol :: SMDI ...........................................

  bwSmdiNbOfActiveConnection  OBJECT-TYPE
    SYNTAX      Gauge32
    MAX-ACCESS    read-only
    STATUS      current
                DESCRIPTION
                                "Counts the total number of currently active Terminal Server SMDI connections."
                ::=  {  smdiStats  1  }

  bwSmdiNbOfOpenedConnection  OBJECT-TYPE
    SYNTAX      Counter32
    MAX-ACCESS    read-write
    STATUS      current
                DESCRIPTION
                                "This counter gives the total number of SMDI connections that were opened since the last reboot of the system or reset of the PMs."
                ::=  {  smdiStats  2  }

  bwSmdiIncomingMWIActivationRequests OBJECT-TYPE
    SYNTAX      Counter32
    MAX-ACCESS    read-write
    STATUS      current
                DESCRIPTION
                                "This counter reflects the number of SMDI MWI activation requests that were received and processed by the server."
                ::=  {  smdiStats  3  }

  bwSmdiIncomingMWIDesactivationRequests  OBJECT-TYPE
    SYNTAX      Counter32
    MAX-ACCESS    read-write
    STATUS      current
                DESCRIPTION
                                "This counter reflects the number of SMDI MWI desactivation requests that were received and processed by the server."
                ::=  {  smdiStats  4  }

  bwSmdiInvalidRequestsReceived OBJECT-TYPE
    SYNTAX      Counter32
    MAX-ACCESS    read-write
    STATUS      current
                DESCRIPTION
                                "This counter reflects the number of invalid SMDI requests."
                ::=  {  smdiStats  5  }

  bwSmdiBlockResponsesSent  OBJECT-TYPE
    SYNTAX      Counter32
    MAX-ACCESS    read-write
    STATUS      current
                DESCRIPTION
                                "This counter reflects the number of SMDI MWI negative acknowledgement with a cause set to BLK."
                ::=  {  smdiStats  6  }

  bwSmdiInvalidResponsesSent  OBJECT-TYPE
    SYNTAX      Counter32
    MAX-ACCESS    read-write
    STATUS      current
                DESCRIPTION
                                "This counter reflects the number of SMDI MWI negative acknowledgement with a cause set to INV."
                ::=  {  smdiStats  7  }

  bwSmdiOutgoingMWIActivationRequests OBJECT-TYPE
    SYNTAX      Counter32
    MAX-ACCESS    read-write
    STATUS      current
                DESCRIPTION
                                "This counter reflects the number of Number of outgoing SMDI MWI OP message."
                ::=  {  smdiStats  8  }

  bwSmdiOutgoingMWIDeactivationRequests OBJECT-TYPE
    SYNTAX      Counter32
    MAX-ACCESS    read-write
    STATUS      current
                DESCRIPTION
                                "This counter reflects the number of Number of outgoing SMDI MWI RMV message."
                ::=  {  smdiStats  9  }

  bwSmdiBlockResponsesReceived  OBJECT-TYPE
    SYNTAX      Counter32
    MAX-ACCESS    read-write
    STATUS      current
                DESCRIPTION
                                "This counter reflects the number of SMDI MWI negative acknowledgement with a cause set to BLK received from a station host, i.e. a Class 5 End Office."
                ::=  {  smdiStats  10  }

  bwSmdiInvalidResponsesReceived  OBJECT-TYPE
    SYNTAX      Counter32
    MAX-ACCESS    read-write
    STATUS      current
                DESCRIPTION
                                "This counter reflects the number of SMDI MWI negative acknowledgement with a cause set to INV."
                ::=  {  smdiStats  11  }

  bwSMDIMessageDeskMessageSent  OBJECT-TYPE
    SYNTAX      Counter32
    MAX-ACCESS    read-write
    STATUS      current
                DESCRIPTION
                                "This counter reflects the number of outgoing SMDI MD messages sent by BroadWorks."
                ::=  {  smdiStats  12  }

-- Media management ...........................................

  bwMediaCommandsTransmitted  OBJECT-TYPE
    SYNTAX      Counter32
    MAX-ACCESS    read-write
    STATUS      current
                DESCRIPTION
                                "Contains the number of times a media command was transmitted, for the entire Application Server."
                ::=  {  mediaStats  1  }

  bwMediaNotificationsReceived  OBJECT-TYPE
    SYNTAX      Counter32
    MAX-ACCESS    read-write
    STATUS      current
                DESCRIPTION
                                "Contains the number of times a media notification was received, for the entire Application Server."
                ::=  {  mediaStats  2  }

  bwMediaResourceAllocAttempts  OBJECT-TYPE
    SYNTAX      Counter32
    MAX-ACCESS    read-write
    STATUS      current
                DESCRIPTION
                                "Contains the number of media resource allocation attempts, for the entire Application Server."
                ::=  {  mediaStats  3  }

  bwMediaResourceAllocFailures  OBJECT-TYPE
    SYNTAX      Counter32
    MAX-ACCESS    read-write
    STATUS      current
                DESCRIPTION
                                "Contains the number of times a media command was transmitted, for the entire Application Server."
                ::=  {  mediaStats  4  }

-- WholeSale Protocol management ...........................................

  bwWSPStatsServiceRequestsIn OBJECT-TYPE
    SYNTAX      Counter32
    MAX-ACCESS    read-write
    STATUS      current
                DESCRIPTION
                                "This counter is incremented whenever a WSP ServiceRequest message is received."
                ::=  {  wspStats  1  }

  bwWSPStatsServiceActionsOut OBJECT-TYPE
    SYNTAX      Counter32
    MAX-ACCESS    read-write
    STATUS      current
                DESCRIPTION
                                "This counter is incremented whenever a WSP ServiceAction message is transmitted."
                ::=  {  wspStats  2  }

  bwWSPStatsServiceUpdatesIn  OBJECT-TYPE
    SYNTAX      Counter32
    MAX-ACCESS    read-write
    STATUS      current
                DESCRIPTION
                                "This counter is incremented whenever a WSP ServiceUpdate message is received."
                ::=  {  wspStats  3  }

  bwWSPStatsServiceAcknowledgementsOut  OBJECT-TYPE
    SYNTAX      Counter32
    MAX-ACCESS    read-write
    STATUS      current
                DESCRIPTION
                                "This counter is incremented whenever a WSP ServiceAcknowledgement message is transmitted."
                ::=  {  wspStats  4  }

-- Realtime Accounting management ...........................................

  bwRealtimeAccountingRequestsTransmitted OBJECT-TYPE
    SYNTAX      Counter32
    MAX-ACCESS    read-write
    STATUS      current
                DESCRIPTION
                                "Number of new Accounting Requests sent to a Radius Server. Incremented each time a new Accounting Request transmission is first attempted toward a Radius Server."
                ::=  {  realtimeAccountingStats  1  }

  bwRealtimeAccountingRequestsRetransmitted OBJECT-TYPE
    SYNTAX      Counter32
    MAX-ACCESS    read-write
    STATUS      current
                DESCRIPTION
                                "Number of Accounting Requests sent to Radius Server(s) due to retransmissions to the same server. Incremented each time an Accounting Request transmission is retransmitted toward an Accounting Radius Server (be it to the same server as the one where the original request was sent, or to the alternate server)."
                ::=  {  realtimeAccountingStats  2  }

  bwRealtimeAccountingRequestsDropped OBJECT-TYPE
    SYNTAX      Counter32
    MAX-ACCESS    read-write
    STATUS      current
                DESCRIPTION
                                "Number of Accounting Requests that were discarded due to the lack of a responsive Accounting Radius Server. Incremented each time an Accounting Request is dropped, after all transmissions attempts have failed."
                ::=  {  realtimeAccountingStats  3  }

-- External Call Logs management ...........................................

  bwExternalCallLogsTransmitted OBJECT-TYPE
    SYNTAX      Counter32
    MAX-ACCESS    read-write
    STATUS      current
                DESCRIPTION
                                "Incremented each time a new external call log transmission is first attempted toward a Call detail server."
                ::=  {  externalCallLogsStats  1  }

  bwExternalCallLogsRetransmitted OBJECT-TYPE
    SYNTAX      Counter32
    MAX-ACCESS    read-write
    STATUS      current
                DESCRIPTION
                                "Incremented each time a new external call log transmission is retransmitted towards a Call Detail Radius Server (be it to the same server as the one where the original call log was sent, or to the alternate server)."
                ::=  {  externalCallLogsStats  2  }

  bwExternalCallLogsDropped OBJECT-TYPE
    SYNTAX      Counter32
    MAX-ACCESS    read-write
    STATUS      current
                DESCRIPTION
                                "Incremented each time a call log is dropped, after all transmissions attempts have failed."
                ::=  {  externalCallLogsStats  3  }

  bwExternalCallLogsQueued  OBJECT-TYPE
    SYNTAX      Counter32
    MAX-ACCESS    read-write
    STATUS      current
                DESCRIPTION
                                "Incremented each time a call log is written to the AS file-based queue, after all transmissions attempts have failed."
                ::=  {  externalCallLogsStats  4  }

  bwExternalCallLogsTransmittedFromQueue  OBJECT-TYPE
    SYNTAX      Counter32
    MAX-ACCESS    read-write
    STATUS      current
                DESCRIPTION
                                "Incremented on the first attempt to send to the call detail server a call log read from the file based queue."
                ::=  {  externalCallLogsStats  5  }

  bwExternalCallLogsRetransmittedFromQueue  OBJECT-TYPE
    SYNTAX      Counter32
    MAX-ACCESS    read-write
    STATUS      current
                DESCRIPTION
                                "Incremented on all attempts but the first one to send to the Call Detail Server a call log read from the file based queue."
                ::=  {  externalCallLogsStats  6  }

-- XS - BroadWorks Common Communication Protocol ........................

  bwCommonCommXSStatsTable  OBJECT-TYPE
    SYNTAX    SEQUENCE  OF  BwCommonCommXSStatsEntry
    MAX-ACCESS  not-accessible
    STATUS    current
                DESCRIPTION
                        "This table contains counters for BCCT for the XS process."
                ::=  { commonCommStats  1 }

  bwCommonCommXSStatsEntry  OBJECT-TYPE
    SYNTAX    BwCommonCommXSStatsEntry
    MAX-ACCESS  not-accessible
    STATUS    current
                DESCRIPTION
                        "Definition of the entries for bwCommonCommXSStatsTable."
    INDEX   {  bwCommonCommXSStatsIndex  }
                ::=  { bwCommonCommXSStatsTable 1 }

        BwCommonCommXSStatsEntry  ::=  SEQUENCE {
                bwCommonCommXSStatsIndex  Unsigned32,
                bwCommonCommXSHost  DisplayString,
                bwCommonCommXSInterface  DisplayString,
                bwCommonCommXSProtocol  DisplayString,
                bwCommonCommXSAcceptedOutboundConnections  Counter32,
                bwCommonCommXSAcceptedInboundConnections  Counter32,
                bwCommonCommXSRejectedOutboundConnections  Counter32,
                bwCommonCommXSRejectedInboundConnections  Counter32,
                bwCommonCommXSOutputMessagesProcessed  Counter32,
                bwCommonCommXSInputMessagesProcessed  Counter32,
                bwCommonCommXSOutputCommunicationErrors  Counter32,
                bwCommonCommXSInputCommunicationErrors  Counter32
                }

  bwCommonCommXSStatsIndex  OBJECT-TYPE
    SYNTAX      Unsigned32
    MAX-ACCESS    read-only
    STATUS      current
                DESCRIPTION
                                "This integer represents an index in table bwCommonCommXSStatsTable. The index represents a connection for a specific Host-Interfacece-Protocol combination."
                ::=  {  bwCommonCommXSStatsEntry  1  }

  bwCommonCommXSHost  OBJECT-TYPE
    SYNTAX      DisplayString
    MAX-ACCESS    read-only
    STATUS      current
                DESCRIPTION
                                "The address of a host connected to the BroadWorks Common Communication Protocol."
                ::=  {  bwCommonCommXSStatsEntry  2  }


  bwCommonCommXSInterface OBJECT-TYPE
    SYNTAX      DisplayString
    MAX-ACCESS    read-only
    STATUS      current
                DESCRIPTION
                                "The IP address of a local interface that a protocol is bound to."
                ::=  {  bwCommonCommXSStatsEntry  3  }

  bwCommonCommXSProtocol  OBJECT-TYPE
    SYNTAX      DisplayString
    MAX-ACCESS    read-only
    STATUS      current
                DESCRIPTION
                                "The name of a BroadWorks Common Communication Protocol client protocol, e.g. OCI or SyncApi."
                ::=  {  bwCommonCommXSStatsEntry  4  }

  bwCommonCommXSAcceptedOutboundConnections OBJECT-TYPE
    SYNTAX      Counter32
    MAX-ACCESS    read-write
    STATUS      current
                DESCRIPTION
                                "This counter is incremented whenever a client in this process connects to the framework to a remote host, using the interface and protocol."
                ::=  {  bwCommonCommXSStatsEntry  5  }

  bwCommonCommXSAcceptedInboundConnections  OBJECT-TYPE
    SYNTAX      Counter32
    MAX-ACCESS    read-write
    STATUS      current
                DESCRIPTION
                                "This counter is incremented whenever a client in this process connects to the framework from a remote host, using the interface and protocol."
                ::=  {  bwCommonCommXSStatsEntry  6  }

  bwCommonCommXSRejectedOutboundConnections OBJECT-TYPE
    SYNTAX      Counter32
    MAX-ACCESS    read-write
    STATUS      current
                DESCRIPTION
                                "This counter is incremented whenever a client connection request going from this process to a remote host and going through this interface has been rejected for a particular protocol."
                ::=  {  bwCommonCommXSStatsEntry  7  }

  bwCommonCommXSRejectedInboundConnections  OBJECT-TYPE
    SYNTAX      Counter32
    MAX-ACCESS    read-write
    STATUS      current
                DESCRIPTION
                                "This counter is incremented whenever a client connection request coming to this host and going through this interface has been rejected by the framework for a particular protocol."
                ::=  {  bwCommonCommXSStatsEntry  8  }

  bwCommonCommXSOutputMessagesProcessed OBJECT-TYPE
    SYNTAX      Counter32
    MAX-ACCESS    read-write
    STATUS      current
                DESCRIPTION
                                "This counter is incremented whenever a message has been sent and processed for this host, interface and protocol."
                ::=  {  bwCommonCommXSStatsEntry  9  }

  bwCommonCommXSInputMessagesProcessed  OBJECT-TYPE
    SYNTAX      Counter32
    MAX-ACCESS    read-write
    STATUS      current
                DESCRIPTION
                                "This counter is incremented whenever a message has been received and processed for this host, interface and protocol."
                ::=  {  bwCommonCommXSStatsEntry  10  }

  bwCommonCommXSOutputCommunicationErrors OBJECT-TYPE
    SYNTAX      Counter32
    MAX-ACCESS    read-write
    STATUS      current
                DESCRIPTION
                                "This counter is incremented whenever a message could not be read because the TCP stack returned an error."
                ::=  {  bwCommonCommXSStatsEntry  11  }

  bwCommonCommXSInputCommunicationErrors  OBJECT-TYPE
    SYNTAX      Counter32
    MAX-ACCESS    read-write
    STATUS      current
                DESCRIPTION
                                "This counter is incremented whenever a message has been sent and processed for this host, interface and protocol."
                ::=  {  bwCommonCommXSStatsEntry  12  }

-- XS - Concurrent Framework ........................

  bwXSMonitoringExecutorTable OBJECT-TYPE
    SYNTAX    SEQUENCE  OF  BwXSMonitoringExecutorEntry
    MAX-ACCESS  not-accessible
    STATUS    current
                DESCRIPTION
                        "This table contains counters for the concurrent framework."
                ::=  { concurrentStats  1 }

  bwXSMonitoringExecutorEntry OBJECT-TYPE
    SYNTAX    BwXSMonitoringExecutorEntry
    MAX-ACCESS  not-accessible
    STATUS    current
                DESCRIPTION
                        "Definition of the entries for bwXSMonitoringExecutorTable."
    INDEX   {  bwXSMonitoringExecutorIndex  }
                ::=  { bwXSMonitoringExecutorTable 1 }

        BwXSMonitoringExecutorEntry  ::=  SEQUENCE {
                bwXSMonitoringExecutorIndex  Unsigned32,
                bwXSMonitoringExecutorName   DisplayString,
                bwXSMonitoringExecutorCurrentPoolSize  Gauge32,
                bwXSMonitoringExecutorMaxPoolSize      Gauge32,
                bwXSMonitoringExecutorAvgActiveThreads Gauge32,
                bwXSMonitoringExecutorTaskQueueSize     Gauge32,
                bwXSMonitoringExecutorNbTasksRun       Counter32,
                bwXSMonitoringExecutorNbWarnings       Counter32,
                bwXSMonitoringExecutorNbErrors         Counter32,
                bwXSMonitoringExecutorLongestTaskMs    Gauge32,
                bwXSMonitoringExecutorLongestTaskName  DisplayString
                }

  bwXSMonitoringExecutorIndex OBJECT-TYPE
    SYNTAX      Unsigned32
    MAX-ACCESS    read-only
    STATUS      current
                DESCRIPTION
                                "This integer represents an index in table bwXSMonitoringExecutorTable. This is the index to a specific Monitoring Executor name."
                ::=  {  bwXSMonitoringExecutorEntry  1  }

  bwXSMonitoringExecutorName  OBJECT-TYPE
    SYNTAX      DisplayString
    MAX-ACCESS    read-only
    STATUS      current
                DESCRIPTION
                                "The name of the Monitoring Executor - Names are internally defined at the application level."
                ::=  {  bwXSMonitoringExecutorEntry  2  }

  bwXSMonitoringExecutorCurrentPoolSize OBJECT-TYPE
    SYNTAX      Gauge32
    MAX-ACCESS    read-only
    STATUS      current
                DESCRIPTION
                                "The current thread pool size"
                ::=  {  bwXSMonitoringExecutorEntry  3  }

  bwXSMonitoringExecutorMaxPoolSize OBJECT-TYPE
    SYNTAX      Gauge32
    MAX-ACCESS    read-only
    STATUS      current
                DESCRIPTION
                                "The maximum thread pool size"
                ::=  {  bwXSMonitoringExecutorEntry  4  }

  bwXSMonitoringExecutorAvgActiveThreads  OBJECT-TYPE
    SYNTAX      Gauge32
    MAX-ACCESS    read-only
    STATUS      current
                DESCRIPTION
                                "The average number of active threads, rounded up"
                ::=  {  bwXSMonitoringExecutorEntry  5  }

  bwXSMonitoringExecutorTaskQueueSize OBJECT-TYPE
    SYNTAX      Gauge32
    MAX-ACCESS    read-only
    STATUS      current
                DESCRIPTION
                                "Number of tasks in the queue (includes scheduled and recurring tasks)"
                ::=  {  bwXSMonitoringExecutorEntry  6  }

  bwXSMonitoringExecutorNbTasksRun  OBJECT-TYPE
    SYNTAX      Counter32
    MAX-ACCESS    read-write
    STATUS      current
                DESCRIPTION
                                "Number of tasks run"
                ::=  {  bwXSMonitoringExecutorEntry  7  }

  bwXSMonitoringExecutorNbWarnings  OBJECT-TYPE
    SYNTAX      Counter32
    MAX-ACCESS    read-write
    STATUS      current
                DESCRIPTION
                                "Number of warnings that occured"
                ::=  {  bwXSMonitoringExecutorEntry  8  }

  bwXSMonitoringExecutorNbErrors  OBJECT-TYPE
    SYNTAX      Counter32
    MAX-ACCESS    read-write
    STATUS      current
                DESCRIPTION
                                "Number of errors that occured"
                ::=  {  bwXSMonitoringExecutorEntry  9  }

  bwXSMonitoringExecutorLongestTaskMs OBJECT-TYPE
    SYNTAX      Gauge32
    MAX-ACCESS    read-only
    STATUS      current
                DESCRIPTION
                                "Longest completed task execution time in milliseconds"
                ::=  {  bwXSMonitoringExecutorEntry  10  }

  bwXSMonitoringExecutorLongestTaskName OBJECT-TYPE
    SYNTAX      DisplayString
    MAX-ACCESS    read-only
    STATUS      current
                DESCRIPTION
                                "Longest completed task name"
                ::=  {  bwXSMonitoringExecutorEntry  11  }

-- XS - TCP Framework ........................

  bwXSTcpServersStatsTable  OBJECT-TYPE
    SYNTAX    SEQUENCE  OF  BwXSTcpServersStatsEntry
    MAX-ACCESS  not-accessible
    STATUS    current
                DESCRIPTION
                        "This table contains counters for TCP underlying framework for the XS process."
                ::=  { tcpStats  1 }

  bwXSTcpServersStatsEntry  OBJECT-TYPE
    SYNTAX    BwXSTcpServersStatsEntry
    MAX-ACCESS  not-accessible
    STATUS    current
                DESCRIPTION
                        "Definition of the entries for bwXSTcpServersStatsTable."
    INDEX   {  bwXSTcpServersStatsIndex  }
                ::=  { bwXSTcpServersStatsTable 1 }

        BwXSTcpServersStatsEntry  ::=  SEQUENCE {
                bwXSTcpServersStatsIndex  Unsigned32,
                bwXSTcpServersName  DisplayString,
                bwXSTcpServersNbConnectionsAccepted  Counter32,
                bwXSTcpServersNbConnectionsRefused  Counter32,
                bwXSTcpServersNbConnectionsInitiated  Counter32,
                bwXSTcpServersNbConnectionsClosed  Counter32,
                bwXSTcpServersNbBytesSent        Gauge32,
                bwXSTcpServersNbBytesReceived    Gauge32,
                bwXSTcpServersOutgoingQueueSize  Gauge32,
                bwXSTcpServersIncomingQueueSize  Gauge32,
                bwXSTcpServersNbBytesSentSecure Gauge32,
                bwXSTcpServersNbBytesReceivedSecure Gauge32
                }

  bwXSTcpServersStatsIndex  OBJECT-TYPE
    SYNTAX      Unsigned32
    MAX-ACCESS    read-only
    STATUS      current
                DESCRIPTION
                                "This integer represents an index in table bwXSTcpServersStatsTable. This is the index to a specific TCP server name."
                ::=  {  bwXSTcpServersStatsEntry  1  }

  bwXSTcpServersName  OBJECT-TYPE
    SYNTAX      DisplayString
    MAX-ACCESS    read-only
    STATUS      current
                DESCRIPTION
                                "The name of TCP server - Names are internally defined at at the application level."
                ::=  {  bwXSTcpServersStatsEntry  2  }

  bwXSTcpServersNbConnectionsAccepted OBJECT-TYPE
    SYNTAX      Counter32
    MAX-ACCESS    read-write
    STATUS      current
                DESCRIPTION
                                "This counter represents the number of connections accepted by the TCP server."
                ::=  {  bwXSTcpServersStatsEntry  3  }

  bwXSTcpServersNbConnectionsRefused  OBJECT-TYPE
    SYNTAX      Counter32
    MAX-ACCESS    read-write
    STATUS      current
                DESCRIPTION
                                "This counter represents the number of connections refused by the TCP server."
                ::=  {  bwXSTcpServersStatsEntry  4  }

  bwXSTcpServersNbConnectionsInitiated  OBJECT-TYPE
    SYNTAX      Counter32
    MAX-ACCESS    read-write
    STATUS      current
                DESCRIPTION
                                "This counter represents the number of connections initiated by the TCP server."
                ::=  {  bwXSTcpServersStatsEntry  5  }

  bwXSTcpServersNbConnectionsClosed OBJECT-TYPE
    SYNTAX      Counter32
    MAX-ACCESS    read-write
    STATUS      current
                DESCRIPTION
                                "This counter represents the number of connections closed by the TCP server or remote hosts."
                ::=  {  bwXSTcpServersStatsEntry  6  }

  bwXSTcpServersNbBytesSent OBJECT-TYPE
    SYNTAX      Gauge32
    MAX-ACCESS    read-write
    STATUS      current
                DESCRIPTION
                                "This counter represents the number of bytes sent by the TCP server."
                ::=  {  bwXSTcpServersStatsEntry  7  }

  bwXSTcpServersNbBytesReceived OBJECT-TYPE
    SYNTAX      Gauge32
    MAX-ACCESS    read-write
    STATUS      current
                DESCRIPTION
                                "This counter represents the number of bytes received by the TCP server."
                ::=  {  bwXSTcpServersStatsEntry  8  }

  bwXSTcpServersOutgoingQueueSize OBJECT-TYPE
    SYNTAX      Gauge32
    MAX-ACCESS    read-only
    STATUS      current
                DESCRIPTION
                                "This counter represents the number of bytes in the outgoing queue."
                ::=  {  bwXSTcpServersStatsEntry  9  }

  bwXSTcpServersIncomingQueueSize OBJECT-TYPE
    SYNTAX      Gauge32
    MAX-ACCESS    read-only
    STATUS      current
                DESCRIPTION
                                "This counter represents the number of bytes in the incoming queue."
                ::=  {  bwXSTcpServersStatsEntry  10  }

  bwXSTcpServersNbBytesSentSecure OBJECT-TYPE
    SYNTAX      Gauge32
    MAX-ACCESS  read-write
    STATUS      current
                DESCRIPTION
                                "This counter represents the number of bytes sent by the TCP server over secure connections."
                ::=  {  bwXSTcpServersStatsEntry  11  }

  bwXSTcpServersNbBytesReceivedSecure OBJECT-TYPE
    SYNTAX      Gauge32
    MAX-ACCESS   read-write
    STATUS      current
                DESCRIPTION
                                "This counter represents the number of bytes received by the TCP server over secure connections."
                ::=  {  bwXSTcpServersStatsEntry  12  }

-- XS - SOAP ........................

  bwSOAPMaxSessions OBJECT-TYPE
    SYNTAX      Gauge32
    MAX-ACCESS    read-only
    STATUS      current
                DESCRIPTION
                                "Maximum number of incoming SOAP sessions simultaneously active since the system was started."
                ::=  {  soapStats  1  }

  bwSOAPAvgSessions OBJECT-TYPE
    SYNTAX      Gauge32
    MAX-ACCESS    read-only
    STATUS      current
                DESCRIPTION
                                "Average number of incoming SOAP sessions simultaneously active, based on a rolling average over the last 100 sessions."
                ::=  {  soapStats  2  }

  bwSOAPMaxThreads  OBJECT-TYPE
    SYNTAX      Gauge32
    MAX-ACCESS    read-only
    STATUS      current
                DESCRIPTION
                                "This gauge measures the maximum percentage of SOAP processing threads simultaneously active since the system was started."
                ::=  {  soapStats  3  }

  bwSOAPAvgThreads  OBJECT-TYPE
    SYNTAX      Gauge32
    MAX-ACCESS    read-only
    STATUS      current
                DESCRIPTION
                                "Average percentage of SOAP threads simultaneously active, based on a rolling average over the last 100 sessions."
                ::=  {  soapStats  4  }

  bwSOAPMaxServiceTime  OBJECT-TYPE
    SYNTAX      Gauge32
    MAX-ACCESS    read-only
    STATUS      current
                DESCRIPTION
                                "Maximum time in milliseconds required to process an incoming SOAP request, since the system was started."
                ::=  {  soapStats  5  }

  bwSOAPAvgServiceTime  OBJECT-TYPE
    SYNTAX      Gauge32
    MAX-ACCESS    read-only
    STATUS      current
                DESCRIPTION
                                "Average time in milliseconds required to process an incoming SOAP request, based on a rolling average over the last 100 requests."
                ::=  {  soapStats  6  }

  bwSOAPNumDroppedRequests  OBJECT-TYPE
    SYNTAX      Counter32
    MAX-ACCESS    read-write
    STATUS      current
                DESCRIPTION
                                "Number of SOAP server requests dropped because the number of SOAP threads was too low."
                ::=  {  soapStats  7  }

-- XS - SMPP.................................................
  bwSmppSubmitSMRequestsSent  OBJECT-TYPE
    SYNTAX      Counter32
    MAX-ACCESS  read-write
    STATUS      current
    DESCRIPTION
      "Number of outgoing SMPP submit_sm requests sent."
    ::= { smppStats 1 }

  bwSmppInvalidSubmitSMResponsesReceived  OBJECT-TYPE
    SYNTAX      Counter32
    MAX-ACCESS  read-write
    STATUS      current
    DESCRIPTION
      "Count of invalid received submit_sm_resp"
    ::= { smppStats 2 }

  bwSmppSubmitSMResponseTimeout  OBJECT-TYPE
    SYNTAX      Counter32
    MAX-ACCESS  read-write
    STATUS      current
    DESCRIPTION
      "Number of submit_sm requests timeouts detected."
    ::= { smppStats 3 }

-- CPE devices management...........................................

  bwCPEDeviceStatsTable OBJECT-TYPE
    SYNTAX    SEQUENCE  OF  BwCPEDeviceStatsEntry
    MAX-ACCESS  not-accessible
    STATUS    current
                DESCRIPTION
                        "This table contains counters for the managed CPE devices management."
                ::=  { cpeDevicesStats  1 }

  bwCPEDeviceStatsEntry OBJECT-TYPE
    SYNTAX    BwCPEDeviceStatsEntry
    MAX-ACCESS  not-accessible
    STATUS    current
                DESCRIPTION
                        "Definition of the entries for bwCPEDeviceStatsTable."
    INDEX   {  bwCPEDeviceStatsIndex  }
                ::=  { bwCPEDeviceStatsTable 1 }

        BwCPEDeviceStatsEntry  ::=  SEQUENCE {
                bwCPEDeviceStatsIndex  Unsigned32,
                bwCPEDeviceName  DisplayString,
                bwCPEDeviceReset  Counter32,
                bwCPEDeviceFileRebuilt  Counter32            
                }

  bwCPEDeviceStatsIndex OBJECT-TYPE
    SYNTAX      Unsigned32
    MAX-ACCESS    read-only
    STATUS      current
                DESCRIPTION
                                "This integer represents a CPE device index in the table"
                ::=  {  bwCPEDeviceStatsEntry  1  }

  bwCPEDeviceName OBJECT-TYPE
    SYNTAX      DisplayString
    MAX-ACCESS    read-only
    STATUS      current
                DESCRIPTION
                                "This string represents CPE device name"
                ::=  {  bwCPEDeviceStatsEntry  2  }

  bwCPEDeviceReset  OBJECT-TYPE
    SYNTAX      Counter32
    MAX-ACCESS    read-write
    STATUS      current
                DESCRIPTION
                                "Number of time the Customer Premise Equipment has been reset. The CPE device is a subscriber IP Phone that can be reset/reloaded via the web portal or CLI. You must have administrative privileges to reset the phone."
                ::=  {  bwCPEDeviceStatsEntry  3  }

  bwCPEDeviceFileRebuilt  OBJECT-TYPE
    SYNTAX      Counter32
    MAX-ACCESS    read-write
    STATUS      current
                DESCRIPTION
                                "Number of time the Customer Premise Equipment has had its configuration file regenerated, the file can be regenerated in a number of ways, for example but not limited to - subscriber specific attribute has changed, a new line has been added to the device."
                ::=  {  bwCPEDeviceStatsEntry  4  }

  bwCPEDeviceFileGet  OBJECT-TYPE
    SYNTAX      Counter32
    MAX-ACCESS    read-write
    STATUS      current
                DESCRIPTION
                                "Number of time the Application Server retrieves a device file from the file repository, one counter per device."
                ::=  {  cpeDevicesStats  2  }

  bwCPEDeviceFileDelete  OBJECT-TYPE
    SYNTAX      Counter32
    MAX-ACCESS    read-write
    STATUS      current
                DESCRIPTION
                                "Number of time the Application Server deletes a device file from the file repository, one counter per device."
                ::=  {  cpeDevicesStats  3  }

  bwCPEDeviceFilePut  OBJECT-TYPE
    SYNTAX      Counter32
    MAX-ACCESS    read-write
    STATUS      current
                DESCRIPTION
                                "Number of time the Application Server saves a device file in the file repository, one counter per device."
                ::=  {  cpeDevicesStats  4  }


-- CallP ...........................................

  bwCallpNetworkOriginationAttempts OBJECT-TYPE
    SYNTAX      Counter32
    MAX-ACCESS    read-write
    STATUS      current
                DESCRIPTION
                                "This count indicates the total number of originations
                                from the network."
                ::=  {  callpStats  1  }

  bwCallpNetworkTerminationAttempts OBJECT-TYPE
    SYNTAX      Counter32
    MAX-ACCESS    read-write
    STATUS      current
                DESCRIPTION
                                "This count indicates the total number of termination
                                attempts to the network."
                ::=  {  callpStats  2  }

  bwCallpNetworkTerminationsAnswered  OBJECT-TYPE
    SYNTAX      Counter32
    MAX-ACCESS    read-write
    STATUS      current
                DESCRIPTION
                                "This count indicates the total number of termination
                                attempts to the network answered."
                ::=  {  callpStats  3  }

  bwCallpUserOriginationAttempts  OBJECT-TYPE
    SYNTAX      Counter32
    MAX-ACCESS    read-write
    STATUS      current
                DESCRIPTION
                                "This counts indicates the total number of origination
                                attempts from the access network(BroadWorks user/virtual user)."
                ::=  {  callpStats  4  }

  bwCallpUserTerminationAttempts  OBJECT-TYPE
    SYNTAX      Counter32
    MAX-ACCESS    read-write
    STATUS      current
                DESCRIPTION
                                "This counts indicates the total number of termination
                                attempts to the access network(BroadWorks user/virtual user)."
                ::=  {  callpStats  5  }

  bwCallpUserTerminationsAnswered OBJECT-TYPE
    SYNTAX      Counter32
    MAX-ACCESS    read-write
    STATUS      current
                DESCRIPTION
                                "This counts indicates the total number of termination
                                attempts to the access network answered."
                ::=  {  callpStats  6  }

  bwCallpEmergencyCallAttempts  OBJECT-TYPE
    SYNTAX      Counter32
    MAX-ACCESS    read-write
    STATUS      current
                DESCRIPTION
                                "This counter represents the number of Emergency call originations made by user's of the system"
                ::=  {  callpStats  7  }

  bwCallpEmergencyCallAlarms  OBJECT-TYPE
    SYNTAX      Counter32
    MAX-ACCESS    read-write
    STATUS      current
                DESCRIPTION
                                "The counter represents the number of times an alarm is generated for an emergency call routing failure"
                ::=  {  callpStats  8  }

  bwCallpSPTable  OBJECT-TYPE
    SYNTAX    SEQUENCE  OF  BwCallpSPEntry
    MAX-ACCESS  not-accessible
    STATUS    current
                DESCRIPTION
                        "This table contains the counters for CallP measurements for service providers"
                ::=  { callpStats  9 }

  bwCallpActiveCalls  OBJECT-TYPE
    SYNTAX      Gauge32
    MAX-ACCESS    read-only
    STATUS      current
                DESCRIPTION
                                "This counts indicates the total number of active session.
                                An active session is define as an active originating session.
                                Any call that needs to perform a lookup in a NetworkServer/LocationServer
                                will be counted as 2 calls, once for each call leg."
                ::=  {  callpStats  10  }

  bwCallpGroupTable OBJECT-TYPE
    SYNTAX    SEQUENCE  OF  BwCallpGroupEntry
    MAX-ACCESS  not-accessible
    STATUS    current
                DESCRIPTION
                        "This table contains the counters for CallP measurements for groups"
                ::=  { callpStats  11 }

  bwCallpCallsPerSecond OBJECT-TYPE
    SYNTAX      Gauge32
    MAX-ACCESS    read-only
    STATUS      current
                DESCRIPTION
                                "This gauge measures the rate at which network origination attempts and user origination attempts occur.  It uses the timestamps of up to the last 100 network origination attempts and user origination attempts in calculating the rate.  The criteria for capturing such attempts is the same as that for pegging the bwCallPNetworkOriginationAttempts and bwCallPUserOriginationAttempts PM's."
                ::=  {  callpStats  12  }

  bwCallpMaximumNumberofSimCallsExceeded  OBJECT-TYPE
    SYNTAX      Counter32
    MAX-ACCESS    read-write
    STATUS      current
                DESCRIPTION
                                "This counter reflects the number of times that the maximum number of simultaneous calls for a user is exceeded."
                ::=  {  callpStats  13  }

  bwCallpMaximumCallTimeforAnsweredCallsExceeded  OBJECT-TYPE
    SYNTAX      Counter32
    MAX-ACCESS    read-write
    STATUS      current
                DESCRIPTION
                                "This counter reflects the number of times that the maximum call time for answered calls is exceeded."
                ::=  {  callpStats  14  }

  bwCallpMaximumCallTimeforUnansweredCallsExceeded  OBJECT-TYPE
    SYNTAX      Counter32
    MAX-ACCESS    read-write
    STATUS      current
                DESCRIPTION
                                "This counter reflects the number of times that the maximum call time for unanswered calls is exceeded."
                ::=  {  callpStats  15  }

  bwCallpActiveCallsAsPercentOfLicense  OBJECT-TYPE
    SYNTAX      Gauge32
    MAX-ACCESS    read-only
    STATUS      current
                DESCRIPTION
                                "This gauge reports the number of active calls as a percentage of the maximum concurrent calls licensed value. If the concurrent calls licensed value is unlimited, the gauge is zero."
                ::=  {  callpStats  16  }

  bwCallpMaximumNumberofSimVideoCallsExceeded OBJECT-TYPE
    SYNTAX      Counter32
    MAX-ACCESS    read-write
    STATUS      current
                DESCRIPTION
                                "This counter reflects the number of times that the maximum number of simultaneous video calls for a user is exceeded."
                ::=  {  callpStats  17  }

  bwCallpMediaTypeNotSupported  OBJECT-TYPE
    SYNTAX      Counter32
    MAX-ACCESS    read-write
    STATUS      current
                DESCRIPTION
                                "This counter reflects the number of times that the media type (codec) has not been supported for a user."
                ::=  {  callpStats  18  }

  bwCallpRemoteOfficeEmergencyCallsBlocked	OBJECT-TYPE
    SYNTAX	Counter32
    MAX-ACCESS	read-write
    STATUS	current
                DESCRIPTION
                                "This is the number of times an emergency call origination attempt from a network location (i.e. remote office or BroadWorks anywhere) has been blocked."
		::=  {  callpStats  19  }

-- CallP :: SP TABLE ...........................................

  bwCallpSPEntry  OBJECT-TYPE
    SYNTAX    BwCallpSPEntry
    MAX-ACCESS  not-accessible
    STATUS    current
                DESCRIPTION
                        "This row contains the counters for CallP measurements for a service provider"
    INDEX   {  bwCallpSPIndex  }
                ::=  { bwCallpSPTable 1 }

        BwCallpSPEntry  ::=  SEQUENCE {
                bwCallpSPIndex  Unsigned32,
                bwCallpSPID  DisplayString,
                bwCallpSPUserOriginationAttempts  Counter32,
                bwCallpSPUserTerminationAttempts  Counter32,
                bwCallpSPUserTerminationsAnswered  Counter32,
                bwCallpSPEmergencyCallAttempts  Counter32,
                bwCallpSPMaximumNumberofSimCallsExceeded  Counter32,
                bwCallpSPMaximumCallTimeforAnsweredCallsExceeded  Counter32,
                bwCallpSPMaximumCallTimeforUnansweredCallsExceeded  Counter32,
                bwCallpSPMaximumNumberofSimVideoCallsExceeded Counter32,
                bwCallpSPMediaTypeNotSupported Counter32
                }

  bwCallpSPIndex  OBJECT-TYPE
    SYNTAX      Unsigned32
    MAX-ACCESS    read-only
    STATUS      current
                DESCRIPTION
                                "This integer represents the a service provider index in the system"
                ::=  {  bwCallpSPEntry  1  }


  bwCallpSPID OBJECT-TYPE
    SYNTAX      DisplayString
    MAX-ACCESS    read-only
    STATUS      current
                DESCRIPTION
                                "This string represents a service provider ID"
                ::=  {  bwCallpSPEntry  2  }


  bwCallpSPUserOriginationAttempts  OBJECT-TYPE
    SYNTAX      Counter32
    MAX-ACCESS    read-write
    STATUS      current
                DESCRIPTION
                                "This counts indicates the total number of origination attempts from the access network(BroadWorks user/virtual user) for a service provider"
                ::=  {  bwCallpSPEntry  3  }


  bwCallpSPUserTerminationAttempts  OBJECT-TYPE
    SYNTAX      Counter32
    MAX-ACCESS    read-write
    STATUS      current
                DESCRIPTION
                                "This counts indicates the total number of termination attempts to the access network(BroadWorks user/virtual user) for a service provider"
                ::=  {  bwCallpSPEntry  4  }


  bwCallpSPUserTerminationsAnswered OBJECT-TYPE
    SYNTAX      Counter32
    MAX-ACCESS    read-write
    STATUS      current
                DESCRIPTION
                                "This counts indicates the total number of termination attempts to the access network answered for a service provider"
                ::=  {  bwCallpSPEntry  5  }


  bwCallpSPEmergencyCallAttempts  OBJECT-TYPE
    SYNTAX      Counter32
    MAX-ACCESS    read-write
    STATUS      current
                DESCRIPTION
                                "This counter represents the number of Emergency call originations made by Broadworks users for a service provider"
                ::=  {  bwCallpSPEntry  6  }

  bwCallpSPMaximumNumberofSimCallsExceeded  OBJECT-TYPE
    SYNTAX      Counter32
    MAX-ACCESS    read-write
    STATUS      current
                DESCRIPTION
                                "This counter reflects the number of times that the maximum number of simultaneous calls for a user is exceeded for a service provider."
                ::=  {  bwCallpSPEntry  7  }

  bwCallpSPMaximumCallTimeforAnsweredCallsExceeded  OBJECT-TYPE
    SYNTAX      Counter32
    MAX-ACCESS    read-write
    STATUS      current
                DESCRIPTION
                                "This counter reflects the number of times that the maximum call time for answered calls is exceeded for a service provider."
                ::=  {  bwCallpSPEntry  8  }

  bwCallpSPMaximumCallTimeforUnansweredCallsExceeded  OBJECT-TYPE
    SYNTAX      Counter32
    MAX-ACCESS    read-write
    STATUS      current
                DESCRIPTION
                                "This counter reflects the number of times that the maximum call time for unanswered calls is exceeded for a service provider."
                ::=  {  bwCallpSPEntry  9  }

  bwCallpSPMaximumNumberofSimVideoCallsExceeded OBJECT-TYPE
    SYNTAX      Counter32
    MAX-ACCESS    read-write
    STATUS      current
                DESCRIPTION
                                "The counter reflects the number of times that the maximum number of simultaneous video calls for a user is exceeded."
                ::=  {  bwCallpSPEntry  10  }

  bwCallpSPMediaTypeNotSupported  OBJECT-TYPE
    SYNTAX      Counter32
    MAX-ACCESS    read-write
    STATUS      current
                DESCRIPTION
                                "The counter reflects the number of times that the media type (codec) within a service provider has not been supported for a user."
                ::=  {  bwCallpSPEntry  11  }

-- CallP :: GROUP TABLE ...........................................

  bwCallpGroupEntry OBJECT-TYPE
    SYNTAX    BwCallpGroupEntry
    MAX-ACCESS  not-accessible
    STATUS    current
                DESCRIPTION
                        "This row contains the counters for CallP measurements for a group"
    INDEX   {  bwCallpGroupIndex  }
                ::=  { bwCallpGroupTable 1 }

        BwCallpGroupEntry  ::=  SEQUENCE {
                bwCallpGroupIndex  Unsigned32,
                bwCallpGroupID  DisplayString,
                bwCallpGroupUserOriginationAttempts  Counter32,
                bwCallpGroupUserTerminationAttempts  Counter32,
                bwCallpGroupUserTerminationsAnswered  Counter32,
                bwCallpGroupEmergencyCallAttempts  Counter32,
                bwCallpGroupMaximumNumberofSimCallsExceeded  Counter32,
                bwCallpGroupMaximumCallTimeforAnsweredCallsExceeded  Counter32,
                bwCallpGroupMaximumCallTimeforUnansweredCallsExceeded  Counter32,
                bwCallpGroupMaximumNumberofSimVideoCallsExceeded  Counter32,
                bwCallpGroupMediaTypeNotSupported  Counter32
                }


  bwCallpGroupIndex OBJECT-TYPE
    SYNTAX      Unsigned32
    MAX-ACCESS    read-only
    STATUS      current
                DESCRIPTION
                                "This integer represents the a group index in the system"
                ::=  {  bwCallpGroupEntry  1  }


  bwCallpGroupID  OBJECT-TYPE
    SYNTAX      DisplayString
    MAX-ACCESS    read-only
    STATUS      current
                DESCRIPTION
                                "This string represents a group ID"
                ::=  {  bwCallpGroupEntry  2  }

  bwCallpGroupUserOriginationAttempts OBJECT-TYPE
    SYNTAX      Counter32
    MAX-ACCESS    read-write
    STATUS      current
                DESCRIPTION
                                "This counts indicates the total number of origination attempts from the access network(BroadWorks user/virtual user) for a group"
                ::=  {  bwCallpGroupEntry  3  }


  bwCallpGroupUserTerminationAttempts OBJECT-TYPE
    SYNTAX      Counter32
    MAX-ACCESS    read-write
    STATUS      current
                DESCRIPTION
                                "This counts indicates the total number of termination attempts to the access network(BroadWorks user/virtual user) for a group"
                ::=  {  bwCallpGroupEntry  4  }


  bwCallpGroupUserTerminationsAnswered  OBJECT-TYPE
    SYNTAX      Counter32
    MAX-ACCESS    read-write
    STATUS      current
                DESCRIPTION
                                "This counts indicates the total number of termination attempts to the access network answered for a group"
                ::=  {  bwCallpGroupEntry  5  }


  bwCallpGroupEmergencyCallAttempts OBJECT-TYPE
    SYNTAX      Counter32
    MAX-ACCESS    read-write
    STATUS      current
                DESCRIPTION
                                "This counter represents the number of Emergency call originations made by Broadworks users for a group"
                ::=  {  bwCallpGroupEntry  6  }

  bwCallpGroupMaximumNumberofSimCallsExceeded OBJECT-TYPE
    SYNTAX      Counter32
    MAX-ACCESS    read-write
    STATUS      current
                DESCRIPTION
                                "This counter reflects the number of times that the maximum number of simultaneous calls for a user is exceeded for a group."
                ::=  {  bwCallpGroupEntry  7  }

  bwCallpGroupMaximumCallTimeforAnsweredCallsExceeded OBJECT-TYPE
    SYNTAX      Counter32
    MAX-ACCESS    read-write
    STATUS      current
                DESCRIPTION
                                "This counter reflects the number of times that the maximum call time for answered calls is exceeded for a group."
                ::=  {  bwCallpGroupEntry  8  }

  bwCallpGroupMaximumCallTimeforUnansweredCallsExceeded OBJECT-TYPE
    SYNTAX      Counter32
    MAX-ACCESS    read-write
    STATUS      current
                DESCRIPTION
                                "This counter reflects the number of times that the maximum call time for unanswered calls is exceeded for a group."
                ::=  {  bwCallpGroupEntry  9  }

  bwCallpGroupMaximumNumberofSimVideoCallsExceeded  OBJECT-TYPE
    SYNTAX      Counter32
    MAX-ACCESS    read-write
    STATUS      current
                DESCRIPTION
                                "This counter reflects the number of times that the maximum number of simultaneous video calls for a user is exceeded."
                ::=  {  bwCallpGroupEntry  10  }

  bwCallpGroupMediaTypeNotSupported OBJECT-TYPE
    SYNTAX      Counter32
    MAX-ACCESS    read-write
    STATUS      current
                DESCRIPTION
                                "This counter reflects the number of times that a call is rejected because the media type was not valid for a user."
                ::=  {  bwCallpGroupEntry  11  }

-- Protocol :: SMTP ...........................................

  bwSMTPTotalPrimaryEmailSendAttempts OBJECT-TYPE
    SYNTAX      Counter32
    MAX-ACCESS    read-write
    STATUS      current
                DESCRIPTION
                                "This counter reflects the total number of message send attempted on the primary SMTP server."
                ::=  {  smtpStats  1  }

  bwSMTPTotalSecondaryEmailSendAttempts OBJECT-TYPE
    SYNTAX      Counter32
    MAX-ACCESS    read-write
    STATUS      current
                DESCRIPTION
                                "This counter reflects the total number of message send attempted on the secondary SMTP server."
                ::=  {  smtpStats  2  }

  bwSMTPPrimaryUnSuccessfulEmailSendAttempts  OBJECT-TYPE
    SYNTAX      Counter32
    MAX-ACCESS    read-write
    STATUS      current
                DESCRIPTION
                                "This counter reflects the total number of message deliveries that failed on the primary SMTP server."
                ::=  {  smtpStats  3  }

  bwSMTPSecondaryUnSuccessfulEmailSendAttempts  OBJECT-TYPE
    SYNTAX      Counter32
    MAX-ACCESS    read-write
    STATUS      current
                DESCRIPTION
                                "This counter reflects the total number of message deliveries that failed on the secondary SMTP server."
                ::=  {  smtpStats  4  }

-- Protocol :: SIP ...........................................

  bwSipSummaryTotalTransactions OBJECT-TYPE
    SYNTAX      Counter32
    MAX-ACCESS    read-write
    STATUS      current
                DESCRIPTION
                                "This counter contains a count of the number of transactions completed or in progress."
                ::=  {  sipStats  1  }

  bwSipStatsInviteIns OBJECT-TYPE
    SYNTAX      Counter32
    MAX-ACCESS    read-write
    STATUS      current
                DESCRIPTION
                                "This counter reflects the total number of INVITE requests received by BroadWorks."
                ::=  {  sipStats  2  }

  bwSipStatsInviteOuts  OBJECT-TYPE
    SYNTAX      Counter32
    MAX-ACCESS    read-write
    STATUS      current
                DESCRIPTION
                                "This counter reflects the total number of INVITE requests sent by BroadWorks."
                ::=  {  sipStats  3  }

  bwSipStatsAckIns  OBJECT-TYPE
    SYNTAX      Counter32
    MAX-ACCESS    read-write
    STATUS      current
                DESCRIPTION
                                "This counter reflects the total number of ACK requests received by BroadWorks."
                ::=  {  sipStats  4  }

  bwSipStatsAckOuts OBJECT-TYPE
    SYNTAX      Counter32
    MAX-ACCESS    read-write
    STATUS      current
                DESCRIPTION
                                "This counter reflects the total number of ACK requests sent by BroadWorks."
                ::=  {  sipStats  5  }

  bwSipStatsByeIns  OBJECT-TYPE
    SYNTAX      Counter32
    MAX-ACCESS    read-write
    STATUS      current
                DESCRIPTION
                                "This counter reflects the total number of BYE requests received by BroadWorks."
                ::=  {  sipStats  6  }

  bwSipStatsByeOuts OBJECT-TYPE
    SYNTAX      Counter32
    MAX-ACCESS    read-write
    STATUS      current
                DESCRIPTION
                                "This counter reflects the total number of BYE requests sent by BroadWorks."
                ::=  {  sipStats  7  }

  bwSipStatsCancelIns OBJECT-TYPE
    SYNTAX      Counter32
    MAX-ACCESS    read-write
    STATUS      current
                DESCRIPTION
                                "This counter reflects the total number of CANCEL requests received by BroadWorks."
                ::=  {  sipStats  8  }

  bwSipStatsCancelOuts  OBJECT-TYPE
    SYNTAX      Counter32
    MAX-ACCESS    read-write
    STATUS      current
                DESCRIPTION
                                "This counter reflects the total number of CANCEL requests sent by BroadWorks."
                ::=  {  sipStats  9  }

  bwSipStatsOptionsIns  OBJECT-TYPE
    SYNTAX      Counter32
    MAX-ACCESS    read-write
    STATUS      current
                DESCRIPTION
                                "This counter reflects the total number of OPTIONS requests received by BroadWorks."
                ::=  {  sipStats  10  }

  bwSipStatsOptionsOuts OBJECT-TYPE
    SYNTAX      Counter32
    MAX-ACCESS    read-write
    STATUS      current
                DESCRIPTION
                                "This counter reflects the total number of OPTIONS requests sent by BroadWorks."
                ::=  {  sipStats  11  }

  bwSipStatsRegisterIns OBJECT-TYPE
    SYNTAX      Counter32
    MAX-ACCESS    read-write
    STATUS      current
                DESCRIPTION
                                "This counter reflects the total number of REGISTER requests received by BroadWorks."
                ::=  {  sipStats  12  }

  bwSipStatsRegisterOuts  OBJECT-TYPE
    SYNTAX      Counter32
    MAX-ACCESS    read-write
    STATUS      current
                DESCRIPTION
                                "This counter reflects the total number of REGISTER requests sent by BroadWorks."
                ::=  {  sipStats  13  }

  bwSipStatsInfoIns OBJECT-TYPE
    SYNTAX      Counter32
    MAX-ACCESS    read-write
    STATUS      current
                DESCRIPTION
                                "This counter reflects the total number of INFO requests received by BroadWorks"
                ::=  {  sipStats  14  }

  bwSipStatsInfoOuts  OBJECT-TYPE
    SYNTAX      Counter32
    MAX-ACCESS    read-write
    STATUS      current
                DESCRIPTION
                                "This counter reflects the total number of INFO requests sent by BroadWorks"
                ::=  {  sipStats  15  }

  bwSipStatsNotifyIns OBJECT-TYPE
    SYNTAX      Counter32
    MAX-ACCESS    read-write
    STATUS      current
                DESCRIPTION
                                "This counter reflects the total number of NOTIFY requests received by BroadWorks"
                ::=  {  sipStats  16  }

  bwSipStatsNotifyOuts  OBJECT-TYPE
    SYNTAX      Counter32
    MAX-ACCESS    read-write
    STATUS      current
                DESCRIPTION
                                "This counter reflects the total number of NOTIFY requests sent by BroadWorks"
                ::=  {  sipStats  17  }

  bwSipStatsPrackIns  OBJECT-TYPE
    SYNTAX      Counter32
    MAX-ACCESS    read-write
    STATUS      current
                DESCRIPTION
                                "This counter reflects the total number of PRACK requests received by BroadWorks"
                ::=  {  sipStats  18  }

  bwSipStatsPrackOuts OBJECT-TYPE
    SYNTAX      Counter32
    MAX-ACCESS    read-write
    STATUS      current
                DESCRIPTION
                                "This counter reflects the total number of PRACK requests sent by BroadWorks"
                ::=  {  sipStats  19  }

  bwSipStatsOtherIns  OBJECT-TYPE
    SYNTAX      Counter32
    MAX-ACCESS    read-write
    STATUS      current
                DESCRIPTION
                                "This counter reflects the total number of unsupported requests (other than INFO and NOTIFY) received by BroadWorks"
                ::=  {  sipStats  20  }

  bwSipStatsOtherOuts OBJECT-TYPE
    SYNTAX      Counter32
    MAX-ACCESS    read-write
    STATUS      current
                DESCRIPTION
                                "This counter reflects the total number of UNKNOWN requests sent by BroadWorks"
                ::=  {  sipStats  21  }

  bwSipStatsInviteResponsesTable  OBJECT-TYPE
    SYNTAX    SEQUENCE  OF  BwSipStatsInviteResponsesEntry
    MAX-ACCESS  not-accessible
    STATUS    current
                DESCRIPTION
                        "This table contains the counters for all SIP responses to the Invite requests received or sent by BroadWorks. Each counter is a 32-Bit counter. The response code is used to index into the table. Here are all the response codes:  100, 180, 181, 182, 183, 200, 300, 301, 302, 305, 380, 400, 401, 402, 403, 404, 405, 406, 407, 408, 409, 410, 411, 413, 414, 415, 420, 480, 481, 482, 483, 484, 485, 486, 487, 500, 501, 502, 503, 504, 505, 600, 603, 604, 606"
                ::=  { sipStats  22 }

  bwSipStatsInviteResponsesEntry  OBJECT-TYPE
    SYNTAX    BwSipStatsInviteResponsesEntry
    MAX-ACCESS  not-accessible
    STATUS    current
                DESCRIPTION
                        "This row contains information on a particular SIP status code received or sent in response to an Invite"
    INDEX   {  bwSipStatsInviteResponseCodeValue  }
                ::=  { bwSipStatsInviteResponsesTable 1 }

        BwSipStatsInviteResponsesEntry  ::=  SEQUENCE {
                bwSipStatsInviteResponseCodeValue  Integer32,
                bwSipStatsInviteResponseIns  Counter32,
                bwSipStatsInviteResponseOuts  Counter32
                }


  bwSipStatsInviteResponseCodeValue OBJECT-TYPE
    SYNTAX      Integer32  ( 100 .. 999  )
    MAX-ACCESS    not-accessible
    STATUS      current
                DESCRIPTION
                                "This integer represents a SIP status code.  The rest of the information in this row is related to this value."
                ::=  {  bwSipStatsInviteResponsesEntry  1  }


  bwSipStatsInviteResponseIns OBJECT-TYPE
    SYNTAX      Counter32
    MAX-ACCESS    read-write
    STATUS      current
                DESCRIPTION
                                "This counter represents the number of SIP responses received in response to an Invite"
                ::=  {  bwSipStatsInviteResponsesEntry  2  }


  bwSipStatsInviteResponseOuts  OBJECT-TYPE
    SYNTAX      Counter32
    MAX-ACCESS    read-write
    STATUS      current
                DESCRIPTION
                                "This counter represents the number of SIP responses sent in response to an Invite"
                ::=  {  bwSipStatsInviteResponsesEntry  3  }

  bwSipStatsByeResponsesTable OBJECT-TYPE
    SYNTAX    SEQUENCE  OF  BwSipStatsByeResponsesEntry
    MAX-ACCESS  not-accessible
    STATUS    current
                DESCRIPTION
                        "This table contains the counters for all SIP responses to the BYE requests received or sent by BroadWorks. Each counter is a 32-Bit counter. The response code is used to index into the table. Here are all the response codes:  100, 180, 181, 182, 183, 200, 300, 301, 302, 305, 380, 400, 401, 402, 403, 404, 405, 406, 407, 408, 409, 410, 411, 413, 414, 415, 420, 480, 481, 482, 483, 484, 485, 486, 487, 500, 501, 502, 503, 504, 505, 600, 603, 604, 606"
                ::=  { sipStats  23 }

  bwSipStatsByeResponsesEntry OBJECT-TYPE
    SYNTAX    BwSipStatsByeResponsesEntry
    MAX-ACCESS  not-accessible
    STATUS    current
                DESCRIPTION
                        "This row contains information on a particular SIP status code received or sent in response to a Bye"
    INDEX   {  bwSipStatsByeResponseCodeValue  }
                ::=  { bwSipStatsByeResponsesTable 1 }

        BwSipStatsByeResponsesEntry  ::=  SEQUENCE {
                bwSipStatsByeResponseCodeValue  Integer32,
                bwSipStatsByeResponseIns  Counter32,
                bwSipStatsByeResponseOuts  Counter32
                }


  bwSipStatsByeResponseCodeValue  OBJECT-TYPE
    SYNTAX      Integer32  ( 100 .. 999  )
    MAX-ACCESS    not-accessible
    STATUS      current
                DESCRIPTION
                                "This integer represents a SIP status code.  The rest of the information in this row is related to this value."
                ::=  {  bwSipStatsByeResponsesEntry  1  }


  bwSipStatsByeResponseIns  OBJECT-TYPE
    SYNTAX      Counter32
    MAX-ACCESS    read-write
    STATUS      current
                DESCRIPTION
                                "This counter represents the number of SIP responses received in response to a Bye"
                ::=  {  bwSipStatsByeResponsesEntry  2  }


  bwSipStatsByeResponseOuts OBJECT-TYPE
    SYNTAX      Counter32
    MAX-ACCESS    read-write
    STATUS      current
                DESCRIPTION
                                "This counter represents the number of SIP responses sent in response to a Bye"
                ::=  {  bwSipStatsByeResponsesEntry  3  }

  bwSipStatsCancelResponsesTable  OBJECT-TYPE
    SYNTAX    SEQUENCE  OF  BwSipStatsCancelResponsesEntry
    MAX-ACCESS  not-accessible
    STATUS    current
                DESCRIPTION
                        "This table contains the counters for all SIP responses to the Cancel requests received or sent by BroadWorks. Each counter is a 32-Bit counter. The response code is used to index into the table. Here are all the response codes:  100, 180, 181, 182, 183, 200, 300, 301, 302, 305, 380, 400, 401, 402, 403, 404, 405, 406, 407, 408, 409, 410, 411, 413, 414, 415, 420, 480, 481, 482, 483, 484, 485, 486, 487, 500, 501, 502, 503, 504, 505, 600, 603, 604, 606"
                ::=  { sipStats  24 }

  bwSipStatsCancelResponsesEntry  OBJECT-TYPE
    SYNTAX    BwSipStatsCancelResponsesEntry
    MAX-ACCESS  not-accessible
    STATUS    current
                DESCRIPTION
                        "This row contains information on a particular SIP status code received or sent in response to a Cancel"
    INDEX   {  bwSipStatsCancelResponseCodeValue  }
                ::=  { bwSipStatsCancelResponsesTable 1 }

        BwSipStatsCancelResponsesEntry  ::=  SEQUENCE {
                bwSipStatsCancelResponseCodeValue  Integer32,
                bwSipStatsCancelResponseIns  Counter32,
                bwSipStatsCancelResponseOuts  Counter32
                }


  bwSipStatsCancelResponseCodeValue OBJECT-TYPE
    SYNTAX      Integer32  ( 100 .. 999  )
    MAX-ACCESS    not-accessible
    STATUS      current
                DESCRIPTION
                                "This integer represents a SIP status code.  The rest of the information in this row is related to this value."
                ::=  {  bwSipStatsCancelResponsesEntry  1  }


  bwSipStatsCancelResponseIns OBJECT-TYPE
    SYNTAX      Counter32
    MAX-ACCESS    read-write
    STATUS      current
                DESCRIPTION
                                "This counter represents the number of SIP responses received in response to a Cancel"
                ::=  {  bwSipStatsCancelResponsesEntry  2  }


  bwSipStatsCancelResponseOuts  OBJECT-TYPE
    SYNTAX      Counter32
    MAX-ACCESS    read-write
    STATUS      current
                DESCRIPTION
                                "This counter represents the number of SIP responses sent in response to a Cancel"
                ::=  {  bwSipStatsCancelResponsesEntry  3  }

  bwSipStatsOptionsResponsesTable OBJECT-TYPE
    SYNTAX    SEQUENCE  OF  BwSipStatsOptionsResponsesEntry
    MAX-ACCESS  not-accessible
    STATUS    current
                DESCRIPTION
                        "This table contains the counters for all SIP responses to the Options requests received or sent by BroadWorks. Each counter is a 32-Bit counter. The response code is used to index into the table. Here are all the response codes:  100, 180, 181, 182, 183, 200, 300, 301, 302, 305, 380, 400, 401, 402, 403, 404, 405, 406, 407, 408, 409, 410, 411, 413, 414, 415, 420, 480, 481, 482, 483, 484, 485, 486, 487, 500, 501, 502, 503, 504, 505, 600, 603, 604, 606"
                ::=  { sipStats  25 }

  bwSipStatsOptionsResponsesEntry OBJECT-TYPE
    SYNTAX    BwSipStatsOptionsResponsesEntry
    MAX-ACCESS  not-accessible
    STATUS    current
                DESCRIPTION
                        "This row contains information on a particular SIP status code received or sent in response to a Options"
    INDEX   {  bwSipStatsOptionsResponseCodeValue  }
                ::=  { bwSipStatsOptionsResponsesTable 1 }

        BwSipStatsOptionsResponsesEntry  ::=  SEQUENCE {
                bwSipStatsOptionsResponseCodeValue  Integer32,
                bwSipStatsOptionsResponseIns  Counter32,
                bwSipStatsOptionsResponseOuts  Counter32
                }


  bwSipStatsOptionsResponseCodeValue  OBJECT-TYPE
    SYNTAX      Integer32  ( 100 .. 999  )
    MAX-ACCESS    not-accessible
    STATUS      current
                DESCRIPTION
                                "This integer represents a SIP status code.  The rest of the information in this row is related to this value."
                ::=  {  bwSipStatsOptionsResponsesEntry  1  }


  bwSipStatsOptionsResponseIns  OBJECT-TYPE
    SYNTAX      Counter32
    MAX-ACCESS    read-write
    STATUS      current
                DESCRIPTION
                                "This counter represents the number of SIP responses received in response to an Options"
                ::=  {  bwSipStatsOptionsResponsesEntry  2  }


  bwSipStatsOptionsResponseOuts OBJECT-TYPE
    SYNTAX      Counter32
    MAX-ACCESS    read-write
    STATUS      current
                DESCRIPTION
                                "This counter represents the number of SIP responses sent in response to an Options"
                ::=  {  bwSipStatsOptionsResponsesEntry  3  }

  bwSipStatsRegisterResponsesTable  OBJECT-TYPE
    SYNTAX    SEQUENCE  OF  BwSipStatsRegisterResponsesEntry
    MAX-ACCESS  not-accessible
    STATUS    current
                DESCRIPTION
                        "This table contains the counters for all SIP responses to the Register requests received or sent by BroadWorks. Each counter is a 32-Bit counter. The response code is used to index into the table. Here are all the response codes:  100, 180, 181, 182, 183, 200, 300, 301, 302, 305, 380, 400, 401, 402, 403, 404, 405, 406, 407, 408, 409, 410, 411, 413, 414, 415, 420, 480, 481, 482, 483, 484, 485, 486, 487, 500, 501, 502, 503, 504, 505, 600, 603, 604, 606"
                ::=  { sipStats  26 }

  bwSipStatsRegisterResponsesEntry  OBJECT-TYPE
    SYNTAX    BwSipStatsRegisterResponsesEntry
    MAX-ACCESS  not-accessible
    STATUS    current
                DESCRIPTION
                        "This row contains information on a particular SIP status code received or sent in response to a Register"
    INDEX   {  bwSipStatsRegisterResponseCodeValue  }
                ::=  { bwSipStatsRegisterResponsesTable 1 }

        BwSipStatsRegisterResponsesEntry  ::=  SEQUENCE {
                bwSipStatsRegisterResponseCodeValue  Integer32,
                bwSipStatsRegisterResponseIns  Counter32,
                bwSipStatsRegisterResponseOuts  Counter32
                }


  bwSipStatsRegisterResponseCodeValue OBJECT-TYPE
    SYNTAX      Integer32  ( 100 .. 999  )
    MAX-ACCESS    not-accessible
    STATUS      current
                DESCRIPTION
                                "This integer represents a SIP status code.  The rest of the information in this row is related to this value."
                ::=  {  bwSipStatsRegisterResponsesEntry  1  }


  bwSipStatsRegisterResponseIns OBJECT-TYPE
    SYNTAX      Counter32
    MAX-ACCESS    read-write
    STATUS      current
                DESCRIPTION
                                "This counter represents the number of SIP responses received in response to a Register"
                ::=  {  bwSipStatsRegisterResponsesEntry  2  }


  bwSipStatsRegisterResponseOuts  OBJECT-TYPE
    SYNTAX      Counter32
    MAX-ACCESS    read-write
    STATUS      current
                DESCRIPTION
                                "This counter represents the number of SIP responses sent in response to a Register"
                ::=  {  bwSipStatsRegisterResponsesEntry  3  }

  bwSipStatsPrackResponsesTable OBJECT-TYPE
    SYNTAX    SEQUENCE  OF  BwSipStatsPrackResponsesEntry
    MAX-ACCESS  not-accessible
    STATUS    current
                DESCRIPTION
                        "This table contains the counters for all SIP responses to the Prack requests received or sent by BroadWorks. Each counter is a 32-Bit counter. The response code is used to index into the table. Here are all the response codes:  100, 180, 181, 182, 183, 200, 300, 301, 302, 305, 380, 400, 401, 402, 403, 404, 405, 406, 407, 408, 409, 410, 411, 413, 414, 415, 420, 480, 481, 482, 483, 484, 485, 486, 487, 500, 501, 502, 503, 504, 505, 600, 603, 604, 606"
                ::=  { sipStats  27 }

  bwSipStatsPrackResponsesEntry OBJECT-TYPE
    SYNTAX    BwSipStatsPrackResponsesEntry
    MAX-ACCESS  not-accessible
    STATUS    current
                DESCRIPTION
                        "This row contains information on a particular SIP status code received or sent in response to a Prack"
    INDEX   {  bwSipStatsPrackResponseCodeValue  }
                ::=  { bwSipStatsPrackResponsesTable 1 }

        BwSipStatsPrackResponsesEntry  ::=  SEQUENCE {
                bwSipStatsPrackResponseCodeValue  Integer32,
                bwSipStatsPrackResponseIns  Counter32,
                bwSipStatsPrackResponseOuts  Counter32
                }


  bwSipStatsPrackResponseCodeValue  OBJECT-TYPE
    SYNTAX      Integer32  ( 100 .. 999  )
    MAX-ACCESS    not-accessible
    STATUS      current
                DESCRIPTION
                                "This integer represents a SIP status code.  The rest of the information in this row is related to this value."
                ::=  {  bwSipStatsPrackResponsesEntry  1  }


  bwSipStatsPrackResponseIns  OBJECT-TYPE
    SYNTAX      Counter32
    MAX-ACCESS    read-write
    STATUS      current
                DESCRIPTION
                                "This counter represents the number of SIP responses received in response to a Prack"
                ::=  {  bwSipStatsPrackResponsesEntry  2  }


  bwSipStatsPrackResponseOuts OBJECT-TYPE
    SYNTAX      Counter32
    MAX-ACCESS    read-write
    STATUS      current
                DESCRIPTION
                                "This counter represents the number of SIP responses sent in response to a Prack"
                ::=  {  bwSipStatsPrackResponsesEntry  3  }

  bwSipStatsInfoResponsesTable  OBJECT-TYPE
    SYNTAX    SEQUENCE  OF  BwSipStatsInfoResponsesEntry
    MAX-ACCESS  not-accessible
    STATUS    current
                DESCRIPTION
                        "This table contains the counters for all SIP responses to the Info requests received or sent by BroadWorks. Each counter is a 32-Bit counter. The response code is used to index into the table. Here are all the response codes:  100, 180, 181, 182, 183, 200, 300, 301, 302, 305, 380, 400, 401, 402, 403, 404, 405, 406, 407, 408, 409, 410, 411, 413, 414, 415, 420, 480, 481, 482, 483, 484, 485, 486, 487, 500, 501, 502, 503, 504, 505, 600, 603, 604, 606"
                ::=  { sipStats  28 }

  bwSipStatsInfoResponsesEntry  OBJECT-TYPE
    SYNTAX    BwSipStatsInfoResponsesEntry
    MAX-ACCESS  not-accessible
    STATUS    current
                DESCRIPTION
                        "This row contains information on a particular SIP status code received or sent in response to an Info"
    INDEX   {  bwSipStatsInfoResponseCodeValue  }
                ::=  { bwSipStatsInfoResponsesTable 1 }

        BwSipStatsInfoResponsesEntry  ::=  SEQUENCE {
                bwSipStatsInfoResponseCodeValue  Integer32,
                bwSipStatsInfoResponseIns  Counter32,
                bwSipStatsInfoResponseOuts  Counter32
                }


  bwSipStatsInfoResponseCodeValue OBJECT-TYPE
    SYNTAX      Integer32  ( 100 .. 999  )
    MAX-ACCESS    not-accessible
    STATUS      current
                DESCRIPTION
                                "This integer represents a SIP status code.  The rest of the information in this row is related to this value."
                ::=  {  bwSipStatsInfoResponsesEntry  1  }


  bwSipStatsInfoResponseIns OBJECT-TYPE
    SYNTAX      Counter32
    MAX-ACCESS    read-write
    STATUS      current
                DESCRIPTION
                                "This counter represents the number of SIP responses received in response to an Info"
                ::=  {  bwSipStatsInfoResponsesEntry  2  }


  bwSipStatsInfoResponseOuts  OBJECT-TYPE
    SYNTAX      Counter32
    MAX-ACCESS    read-write
    STATUS      current
                DESCRIPTION
                                "This counter represents the number of SIP responses sent in response to an Info"
                ::=  {  bwSipStatsInfoResponsesEntry  3  }

  bwSipStatsNotifyResponsesTable  OBJECT-TYPE
    SYNTAX    SEQUENCE  OF  BwSipStatsNotifyResponsesEntry
    MAX-ACCESS  not-accessible
    STATUS    current
                DESCRIPTION
                        "This table contains the counters for all SIP responses to the Notify requests received or sent by BroadWorks. Each counter is a 32-Bit counter. The response code is used to index into the table. Here are all the response codes:  100, 180, 181, 182, 183, 200, 300, 301, 302, 305, 380, 400, 401, 402, 403, 404, 405, 406, 407, 408, 409, 410, 411, 413, 414, 415, 420, 480, 481, 482, 483, 484, 485, 486, 487, 500, 501, 502, 503, 504, 505, 600, 603, 604, 606"
                ::=  { sipStats  29 }

  bwSipStatsNotifyResponsesEntry  OBJECT-TYPE
    SYNTAX    BwSipStatsNotifyResponsesEntry
    MAX-ACCESS  not-accessible
    STATUS    current
                DESCRIPTION
                        "This row contains information on a particular SIP status code received or sent in response to an Notify"
    INDEX   {  bwSipStatsNotifyResponseCodeValue  }
                ::=  { bwSipStatsNotifyResponsesTable 1 }

        BwSipStatsNotifyResponsesEntry  ::=  SEQUENCE {
                bwSipStatsNotifyResponseCodeValue  Integer32,
                bwSipStatsNotifyResponseIns  Counter32,
                bwSipStatsNotifyResponseOuts  Counter32
                }


  bwSipStatsNotifyResponseCodeValue OBJECT-TYPE
    SYNTAX      Integer32  ( 100 .. 999  )
    MAX-ACCESS    not-accessible
    STATUS      current
                DESCRIPTION
                                "This integer represents a SIP status code.  The rest of the information in this row is related to this value."
                ::=  {  bwSipStatsNotifyResponsesEntry  1  }


  bwSipStatsNotifyResponseIns OBJECT-TYPE
    SYNTAX      Counter32
    MAX-ACCESS    read-write
    STATUS      current
                DESCRIPTION
                                "This counter represents the number of SIP responses received in response to a Notify"
                ::=  {  bwSipStatsNotifyResponsesEntry  2  }


  bwSipStatsNotifyResponseOuts  OBJECT-TYPE
    SYNTAX      Counter32
    MAX-ACCESS    read-write
    STATUS      current
                DESCRIPTION
                                "This counter represents the number of SIP responses sent in response to a Notify"
                ::=  {  bwSipStatsNotifyResponsesEntry  3  }

  bwSipStatsOtherResponsesTable OBJECT-TYPE
    SYNTAX    SEQUENCE  OF  BwSipStatsOtherResponsesEntry
    MAX-ACCESS  not-accessible
    STATUS    current
                DESCRIPTION
                        "This table contains the counters for all SIP responses to the Other requests received or sent by BroadWorks. Each counter is a 32-Bit counter. The response code is used to index into the table. Here are all the response codes:  100, 180, 181, 182, 183, 200, 300, 301, 302, 305, 380, 400, 401, 402, 403, 404, 405, 406, 407, 408, 409, 410, 411, 413, 414, 415, 420, 480, 481, 482, 483, 484, 485, 486, 487, 500, 501, 502, 503, 504, 505, 600, 603, 604, 606"
                ::=  { sipStats  30 }

  bwSipStatsOtherResponsesEntry OBJECT-TYPE
    SYNTAX    BwSipStatsOtherResponsesEntry
    MAX-ACCESS  not-accessible
    STATUS    current
                DESCRIPTION
                        "This row contains information on a particular SIP status code received or sent in response to an Other"
    INDEX   {  bwSipStatsOtherResponseCodeValue  }
                ::=  { bwSipStatsOtherResponsesTable 1 }

        BwSipStatsOtherResponsesEntry  ::=  SEQUENCE {
                bwSipStatsOtherResponseCodeValue  Integer32,
                bwSipStatsOtherResponseIns  Counter32,
                bwSipStatsOtherResponseOuts  Counter32
                }


  bwSipStatsOtherResponseCodeValue  OBJECT-TYPE
    SYNTAX      Integer32  ( 100 .. 999  )
    MAX-ACCESS    not-accessible
    STATUS      current
                DESCRIPTION
                                "This integer represents a SIP status code.  The rest of the information in this row is related to this value."
                ::=  {  bwSipStatsOtherResponsesEntry  1  }


  bwSipStatsOtherResponseIns  OBJECT-TYPE
    SYNTAX      Counter32
    MAX-ACCESS    read-write
    STATUS      current
                DESCRIPTION
                                "This counter represents the number of SIP responses received in response to an Other"
                ::=  {  bwSipStatsOtherResponsesEntry  2  }


  bwSipStatsOtherResponseOuts OBJECT-TYPE
    SYNTAX      Counter32
    MAX-ACCESS    read-write
    STATUS      current
                DESCRIPTION
                                "This counter represents the number of SIP responses sent in response to an Other"
                ::=  {  bwSipStatsOtherResponsesEntry  3  }

  bwSipStatsRetryInvites  OBJECT-TYPE
    SYNTAX      Counter32
    MAX-ACCESS    read-write
    STATUS      current
                DESCRIPTION
                                "This counter reflects the total number of INVITE retries that have been sent by the user agent."
                ::=  {  sipStats  31  }

  bwSipStatsRetryByes OBJECT-TYPE
    SYNTAX      Counter32
    MAX-ACCESS    read-write
    STATUS      current
                DESCRIPTION
                                "This counter reflects the total number of BYE retries that have been sent by the user agent."
                ::=  {  sipStats  32  }

  bwSipStatsRetryCancels  OBJECT-TYPE
    SYNTAX      Counter32
    MAX-ACCESS    read-write
    STATUS      current
                DESCRIPTION
                                "This counter reflects the total number of CANCEL retries that have been sent by the user agent."
                ::=  {  sipStats  33  }

  bwSipStatsRetryResponses  OBJECT-TYPE
    SYNTAX      Counter32
    MAX-ACCESS    read-write
    STATUS      current
                DESCRIPTION
                                "This counter reflects the total number of RESPONSES retries that have been sent by the user agent."
                ::=  {  sipStats  34  }

  bwSipStatsSubscribeIns    OBJECT-TYPE
    SYNTAX      Counter32
    MAX-ACCESS    read-write
    STATUS      current
                DESCRIPTION
                                "This counter reflects the total number of SUBSCRIBE message that have been received at the AS."
                ::=  {  sipStats  35  }

  bwSipStatsSubscribeOuts   OBJECT-TYPE
    SYNTAX      Counter32
    MAX-ACCESS    read-write
    STATUS      current
                DESCRIPTION
                                "This counter reflects the total number of SUBSCRIBE message that have been sent by the AS."
                ::=  {  sipStats  36  }

  bwSipStatsMessageIns    OBJECT-TYPE
    SYNTAX      Counter32
    MAX-ACCESS    read-write
    STATUS      current
                DESCRIPTION
                                "This counter reflects the total number of MESSAGE message that have been received at the AS."
                ::=  {  sipStats  37  }

  bwSipStatsMessageOuts   OBJECT-TYPE
    SYNTAX      Counter32
    MAX-ACCESS    read-write
    STATUS      current
                DESCRIPTION
                                "This counter reflects the total number of MESSAGE message that have been sent by the AS."
                ::=  {  sipStats  38  }

  bwSipStatsSubscribeResponsesTable OBJECT-TYPE
    SYNTAX    SEQUENCE  OF  BwSipStatsSubscribeResponsesEntry
    MAX-ACCESS  not-accessible
    STATUS    current
                DESCRIPTION
                        "This table contains the counters for all SIP responses to the Subscribe requests received or sent by BroadWorks. Each counter is a 32-Bit counter. The response code is used to index into the table. Here are all the response codes:  100, 180, 181, 182, 183, 200, 300, 301, 302, 305, 380, 400, 401, 402, 403, 404, 405, 406, 407, 408, 409, 410, 411, 413, 414, 415, 420, 480, 481, 482, 483, 484, 485, 486, 487, 500, 501, 502, 503, 504, 505, 600, 603, 604, 606"
                ::=  { sipStats  39 }

  bwSipStatsSubscribeResponsesEntry OBJECT-TYPE
    SYNTAX    BwSipStatsSubscribeResponsesEntry
    MAX-ACCESS  not-accessible
    STATUS    current
                DESCRIPTION
                        "This row contains information on a particular SIP status code received or sent in response to a Subscribe"
    INDEX   {  bwSipStatsSubscribeResponseCodeValue  }
                ::=  { bwSipStatsSubscribeResponsesTable 1 }

        BwSipStatsSubscribeResponsesEntry  ::=  SEQUENCE {
                bwSipStatsSubscribeResponseCodeValue  Integer32,
                bwSipStatsSubscribeResponseIns  Counter32,
                bwSipStatsSubscribeResponseOuts  Counter32
                }


  bwSipStatsSubscribeResponseCodeValue  OBJECT-TYPE
    SYNTAX      Integer32  ( 100 .. 999  )
    MAX-ACCESS    not-accessible
    STATUS      current
                DESCRIPTION
                                "This integer represents a SIP status code.  The rest of the information in this row is related to this value."
                ::=  {  bwSipStatsSubscribeResponsesEntry  1  }


  bwSipStatsSubscribeResponseIns  OBJECT-TYPE
    SYNTAX      Counter32
    MAX-ACCESS    read-write
    STATUS      current
                DESCRIPTION
                                "This counter represents the number of SIP responses received in response to a Subscribe"
                ::=  {  bwSipStatsSubscribeResponsesEntry  2  }


  bwSipStatsSubscribeResponseOuts OBJECT-TYPE
    SYNTAX      Counter32
    MAX-ACCESS    read-write
    STATUS      current
                DESCRIPTION
                                "This counter represents the number of SIP responses sent in response to a Subscribe"
                ::=  {  bwSipStatsSubscribeResponsesEntry  3  }


  bwSipStatsMessageResponsesTable OBJECT-TYPE
    SYNTAX    SEQUENCE  OF  BwSipStatsMessageResponsesEntry
    MAX-ACCESS  not-accessible
    STATUS    current
                DESCRIPTION
                        "This table contains the counters for all SIP responses to the Message requests received or sent by BroadWorks. Each counter is a 32-Bit counter. The response code is used to index into the table. Here are all the response codes:  100, 180, 181, 182, 183, 200, 300, 301, 302, 305, 380, 400, 401, 402, 403, 404, 405, 406, 407, 408, 409, 410, 411, 413, 414, 415, 420, 480, 481, 482, 483, 484, 485, 486, 487, 500, 501, 502, 503, 504, 505, 600, 603, 604, 606"
                ::=  { sipStats  40 }

  bwSipStatsMessageResponsesEntry OBJECT-TYPE
    SYNTAX    BwSipStatsMessageResponsesEntry
    MAX-ACCESS  not-accessible
    STATUS    current
                DESCRIPTION
                        "This row contains information on a particular SIP status code received or sent in response to a Message"
    INDEX   {  bwSipStatsMessageResponseCodeValue  }
                ::=  { bwSipStatsMessageResponsesTable 1 }

        BwSipStatsMessageResponsesEntry  ::=  SEQUENCE {
                bwSipStatsMessageResponseCodeValue  Integer32,
                bwSipStatsMessageResponseIns  Counter32,
                bwSipStatsMessageResponseOuts  Counter32
                }


  bwSipStatsMessageResponseCodeValue  OBJECT-TYPE
    SYNTAX      Integer32  ( 100 .. 999  )
    MAX-ACCESS    not-accessible
    STATUS      current
                DESCRIPTION
                                "This integer represents a SIP status code.  The rest of the information in this row is related to this value."
                ::=  {  bwSipStatsMessageResponsesEntry  1  }


  bwSipStatsMessageResponseIns  OBJECT-TYPE
    SYNTAX      Counter32
    MAX-ACCESS    read-write
    STATUS      current
                DESCRIPTION
                                "This counter represents the number of SIP responses received in response to a Message"
                ::=  {  bwSipStatsMessageResponsesEntry  2  }


  bwSipStatsMessageResponseOuts OBJECT-TYPE
    SYNTAX      Counter32
    MAX-ACCESS    read-write
    STATUS      current
                DESCRIPTION
                                "This counter represents the number of SIP responses sent in response to a Message"
                ::=  {  bwSipStatsMessageResponsesEntry  3  }

  bwSipStatsUpdateIns   OBJECT-TYPE
    SYNTAX      Counter32
    MAX-ACCESS    read-write
    STATUS      current
                DESCRIPTION
                                "This counter reflects the total number of UPDATE requests received by BroadWorks."
                ::=  {  sipStats  41  }

  bwSipStatsUpdateOuts    OBJECT-TYPE
    SYNTAX      Counter32
    MAX-ACCESS    read-write
    STATUS      current
                DESCRIPTION
                                "This counter reflects the total number of UPDATE requests sent by BroadWorks."
                ::=  {  sipStats  42  }

  bwSipStatsUpdateResponseTable OBJECT-TYPE
    SYNTAX    SEQUENCE  OF  BwSipStatsUpdateResponseEntry
    MAX-ACCESS  not-accessible
    STATUS    current
                DESCRIPTION
                        "This table contains the counters for all SIP responses to the Message requests received or sent by BroadWorks. Each counter is a 32-Bit counter. The response code is used to index into the table. Here are all the response codes:  100, 180, 181, 182, 183, 200, 300, 301, 302, 305, 380, 400, 401, 402, 403, 404, 405, 406, 407, 408, 409, 410, 411, 413, 414, 415, 420, 480, 481, 482, 483, 484, 485, 486, 487, 500, 501, 502, 503, 504, 505, 600, 603, 604, 606"
                ::=  { sipStats  43 }

  bwSipStatsUpdateResponseEntry OBJECT-TYPE
    SYNTAX    BwSipStatsUpdateResponseEntry
    MAX-ACCESS  not-accessible
    STATUS    current
                DESCRIPTION
                        "This row contains information on a particular SIP status code received or sent in response to an Update message"
    INDEX   {  bwSipStatsUpdateResponseCodeValue  }
                ::=  { bwSipStatsUpdateResponseTable 1 }

        BwSipStatsUpdateResponseEntry  ::=  SEQUENCE {
                bwSipStatsUpdateResponseCodeValue  Integer32,
                bwSipStatsUpdateResponseIns  Counter32,
                bwSipStatsUpdateResponseOuts  Counter32
                }


  bwSipStatsUpdateResponseCodeValue OBJECT-TYPE
    SYNTAX      Integer32  ( 100 .. 999  )
    MAX-ACCESS    not-accessible
    STATUS      current
                DESCRIPTION
                                "This integer represents a SIP status code.  The rest of the information in this row is related to this value."
                ::=  {  bwSipStatsUpdateResponseEntry  1  }


  bwSipStatsUpdateResponseIns OBJECT-TYPE
    SYNTAX      Counter32
    MAX-ACCESS    read-write
    STATUS      current
                DESCRIPTION
                                "This counter represents the number of SIP responses received in response to an Update message"
                ::=  {  bwSipStatsUpdateResponseEntry  2  }


  bwSipStatsUpdateResponseOuts  OBJECT-TYPE
    SYNTAX      Counter32
    MAX-ACCESS    read-write
    STATUS      current
                DESCRIPTION
                                "This counter represents the number of SIP responses sent in response to an Update message"
                ::=  {  bwSipStatsUpdateResponseEntry  3  }

  bwSipStatsSetupSignalDelay  OBJECT-TYPE
    SYNTAX      Gauge32
    MAX-ACCESS    read-write
    STATUS      current
                DESCRIPTION
                                "This gauge is applicable to SIP originated calls.  It measures the average time (in milliseconds) it takes between the receipt of an INVITE message for the origination of a new call and the transmission of an INVITE (Sip terminator), RQNT (MGCP terminator with in-band ringback), or CRCX (MGCP terminator without in-band ringback) to the primary device of the original called party (in the case of intra-group call) or to the network element of the original called party (in the case of a call to the PSTN).  Delays incurred by a query to an external element (e.g. - dip to the Network Server, CNAME query, any external database interaction incurred by CPL scripting) are part of the measurement.  This measurement is intended to reflect the elapsed delay between receipt of the call setup signal from the caller and transmission of the call setup signal to the called party"
                ::=  {  sipStats  44  }

  bwSipStatsMinSetupSignalDelay OBJECT-TYPE
    SYNTAX      Gauge32
    MAX-ACCESS    read-write
    STATUS      current
                DESCRIPTION
                                "This measures the shortest SIP setup-signal delay sampled since the system was started or since this measurement was cleared"
                ::=  {  sipStats  45  }

  bwSipStatsMaxSetupSignalDelay OBJECT-TYPE
    SYNTAX      Gauge32
    MAX-ACCESS    read-write
    STATUS      current
                DESCRIPTION
                                "This measures the longest SIP setup-signal delay sampled since the system was started or since this measurement was cleared"
                ::=  {  sipStats  46  }

  bwSipStatsAnswerSignalDelay OBJECT-TYPE
    SYNTAX      Gauge32
    MAX-ACCESS    read-write
    STATUS      current
                DESCRIPTION
                                "This gauge measures the average time (in milliseconds) between the receipt of a 200 OK message indicating answer or a NTFY off-hook indicating answer and the transmission of a 200 OK indicating answer to the originator.   This measurement is intended to reflect internal queuing, scheduling, and processing delays.
This gauge is applicable to only the SIP originated calls for which the setup-signal delay is measured.  Answer signal delay is not measured when the call has been forwarded, redirected, or when the call has encountered route advancing"
                ::=  {  sipStats  47  }

  bwSipStatsMinAnswerSignalDelay  OBJECT-TYPE
    SYNTAX      Gauge32
    MAX-ACCESS    read-write
    STATUS      current
                DESCRIPTION
                                "This measures the shortest SIP answer-signal delay sampled since the system was started or since this measurement was cleared"
                ::=  {  sipStats  49  }

  bwSipStatsMaxAnswerSignalDelay  OBJECT-TYPE
    SYNTAX      Gauge32
    MAX-ACCESS    read-write
    STATUS      current
                DESCRIPTION
                                "This measures the longest SIP answer-signal delay sampled since the system was started or since this measurement was cleared"
                ::=  {  sipStats  50  }

  bwSipStatsRegistrationsPerMinute  OBJECT-TYPE
    SYNTAX      Gauge32
    MAX-ACCESS    read-only
    STATUS      current
                DESCRIPTION
                                "This gauge measures the rate at which the Application Server receives SIP REGISTER messages.  It uses the timestamps of up to the last 100 registrations received in calculating the rate"
                ::=  {  sipStats  51  }

  bwSipStatsMsgRetryPercentageToOther OBJECT-TYPE
    SYNTAX      Gauge32
    MAX-ACCESS    read-only
    STATUS      current
                DESCRIPTION
                                "This gauge measures the percentage of SIP requests and reliable responses sent (to nodes other than those covered by bwSipStatsMsgRetryToNeTable) due to retry.  Of up to the last 100 requests and reliable responses sent, this gauge calculates the percentage sent due to retransmission (i.e. - gauge = (SIP request retransmissions + SIP reliable response retransmissions) / (SIP request initial transmissions + SIP request retransmissions + SIP reliable response initial transmissions + SIP reliable response retransmissions)"
                ::=  {  sipStats  52  }

  bwSipStatsMsgRetryToNeTable OBJECT-TYPE
    SYNTAX    SEQUENCE  OF  BwSipStatsMsgRetryToNeEntry
    MAX-ACCESS  not-accessible
    STATUS    current
                DESCRIPTION
                        "This gauge table consists of a bwSipStatsMsgRetryToNEEntry per Network Element address.  A Network Element can be a Network Server, Media Server, a Network Gateway, etc - anything but an access device."
                ::=  { sipStats   53 }

  bwSipStatsMsgRetryToNeEntry OBJECT-TYPE
    SYNTAX    BwSipStatsMsgRetryToNeEntry
    MAX-ACCESS  not-accessible
    STATUS    current
                DESCRIPTION
                        "This row contains information on a particular Network Element"
    INDEX   {  bwSipStatsMsgRetryToNeID  }
                ::=  { bwSipStatsMsgRetryToNeTable 1 }

        BwSipStatsMsgRetryToNeEntry  ::=  SEQUENCE {
                bwSipStatsMsgRetryToNeID  Unsigned32,
                bwSipStatsMsgRetryToNeAddr  DisplayString,
                bwSipStatsMsgRetryToNePercentage  Gauge32
                }

  bwSipStatsMsgRetryToNeID  OBJECT-TYPE
    SYNTAX      Unsigned32
    MAX-ACCESS    read-only
    STATUS      current
                DESCRIPTION
                                "This integer represents the unique index of a Network Element"
                ::=  {  bwSipStatsMsgRetryToNeEntry  1  }


  bwSipStatsMsgRetryToNeAddr  OBJECT-TYPE
    SYNTAX      DisplayString
    MAX-ACCESS    read-only
    STATUS      current
                DESCRIPTION
                                "This string represents a Network Element address"
                ::=  {  bwSipStatsMsgRetryToNeEntry  2  }


  bwSipStatsMsgRetryToNePercentage  OBJECT-TYPE
    SYNTAX      Gauge32
    MAX-ACCESS    read-only
    STATUS      current
                DESCRIPTION
                                "The gauge measures for that particular Network Element the percentage of SIP requests and reliable responses sent due to retry.  Of up to the last 100 requests and reliable responses sent to a particular NetworkElement address, this gauge calculates the percentage sent due to retransmission (i.e. - gauge = (SIP request retransmissions + SIP reliable response retransmissions) / (SIP request initial transmissions + SIP request retransmissions + SIP reliable response initial transmissions + SIP reliable response retransmissions)."
                ::=  {  bwSipStatsMsgRetryToNeEntry  3  }


  bwSipStatsActiveTcpConnections  OBJECT-TYPE
    SYNTAX      Gauge32
    MAX-ACCESS    read-only
    STATUS      current
                DESCRIPTION
                                "This gauge is incremented whenever a SIP TCP connection is established.   It decremented whenever a connection is closed."
                ::=  {  sipStats  54  }

  bwSipStatsTcpIns  OBJECT-TYPE
    SYNTAX      Counter32
    MAX-ACCESS    read-write
    STATUS      current
                DESCRIPTION
                                "This counter is incremented whenever a SIP message is received via TCP."
                ::=  {  sipStats  55  }

  bwSipStatsTcpOuts OBJECT-TYPE
    SYNTAX      Counter32
    MAX-ACCESS    read-write
    STATUS      current
                DESCRIPTION
                                "This counter is incremented whenever a SIP message is sent via TCP."
                ::=  {  sipStats  56  }

  bwSipStatsTcpFailures OBJECT-TYPE
    SYNTAX      Counter32
    MAX-ACCESS    read-write
    STATUS      current
                DESCRIPTION
                                "This counter is incremented whenever a SIP message was attempted to be sent via TCP but failed."
                ::=  {  sipStats  57  }

  bwSipStatsUdpIns  OBJECT-TYPE
    SYNTAX      Counter32
    MAX-ACCESS    read-write
    STATUS      current
                DESCRIPTION
                                "This counter is incremented whenever a SIP message is received via UDP."
                ::=  {  sipStats  58  }

  bwSipStatsUdpOuts OBJECT-TYPE
    SYNTAX      Counter32
    MAX-ACCESS    read-write
    STATUS      current
                DESCRIPTION
                                "This counter is incremented whenever a SIP message is sent via UDP."
                ::=  {  sipStats  59  }

  bwSIPReclaimedStaleTcpConnections OBJECT-TYPE
    SYNTAX      Counter32
    MAX-ACCESS    read-write
    STATUS      current
                DESCRIPTION
                                "This counter is incremented every time a SIP TCP connection is reclaimed because it is stale."
                ::=  {  sipStats  60  }

  bwSIPTcpTotalConnections  OBJECT-TYPE
    SYNTAX      Gauge32
    MAX-ACCESS    read-only
    STATUS      obsolete
                DESCRIPTION
                                "This counter is set with the current number of SIP TCP connections."
                ::=  {  sipStats  61  }

-- Protocol SIP :: Congestion Management  .............................

  bwCongestionManagementNeighborTable OBJECT-TYPE
    SYNTAX    SEQUENCE  OF  BwCongestionManagementNeighborEntry
    MAX-ACCESS  not-accessible
    STATUS    current
    DESCRIPTION
      "This table consists of bwCongestionManagementNeighborEntry. "
    ::=  { congestionManagement  1 }

  bwCongestionManagementNeighborEntry OBJECT-TYPE
    SYNTAX    BwCongestionManagementNeighborEntry
    MAX-ACCESS  not-accessible
    STATUS    current
    DESCRIPTION
      "This row contains information on a particular neighbor."
    INDEX   {  bwCongestionManagementNeighborIndex  }
    ::=  { bwCongestionManagementNeighborTable 1 }

  BwCongestionManagementNeighborEntry  ::=  SEQUENCE {
    bwCongestionManagementNeighborIndex  Unsigned32,
    bwCongestionManagementNeighborIpAddress  DisplayString,
    bwCongestionManagementNeighborInviteIn  Counter32,
    bwCongestionManagementNeighborInviteOut  Counter32,
    bwCongestionManagementNeighborRegisterIn  Counter32,
    bwCongestionManagementNeighborOptionsIn  Counter32,
    bwCongestionManagementNeighborOptionsOut  Counter32,
    bwCongestionManagementNeighborSubscribeNotifyIn  Counter32,
    bwCongestionManagementNeighborSubscribeNotifyOut  Counter32,
    bwCongestionManagementNeighbor5xxIn  Counter32,
    bwCongestionManagementNeighborCallpMessageInRate  Gauge32,
    bwCongestionManagementNeighborCallpMessageOutRate  Gauge32,
    bwCongestionManagementNeighborCallpRequestInRate  Gauge32,
    bwCongestionManagementNeighborNonCallpMessageInRate  Gauge32,
    bwCongestionManagementNeighborNonCallpMessageOutRate  Gauge32,
    bwCongestionManagementNeighborNonCallpRequestInRate  Gauge32,
    bwCongestionManagementNeighborState  DisplayString,
    bwCongestionManagementNeighborCapability  DisplayString
    }

  bwCongestionManagementNeighborIndex OBJECT-TYPE
    SYNTAX      Unsigned32
    MAX-ACCESS    read-only
    STATUS      current
    DESCRIPTION
        "This integer represents the neighbor index in the system"
    ::=  {  bwCongestionManagementNeighborEntry  1  }

  bwCongestionManagementNeighborIpAddress OBJECT-TYPE
    SYNTAX      DisplayString
    MAX-ACCESS    read-only
    STATUS      current
    DESCRIPTION
        "The IP address of the neighbor."
    ::=  {  bwCongestionManagementNeighborEntry  2  }

  bwCongestionManagementNeighborInviteIn  OBJECT-TYPE
    SYNTAX      Counter32
    MAX-ACCESS    read-write
    STATUS      current
    DESCRIPTION
        "This is the number of Invite requests that the neighbor sends to the AS."
    ::=  {  bwCongestionManagementNeighborEntry  3  }

  bwCongestionManagementNeighborInviteOut OBJECT-TYPE
    SYNTAX      Counter32
    MAX-ACCESS    read-write
    STATUS      current
    DESCRIPTION
        "This is the number of Invite requests that the AS sends to the neighbor."
    ::=  {  bwCongestionManagementNeighborEntry  4  }

  bwCongestionManagementNeighborRegisterIn  OBJECT-TYPE
    SYNTAX      Counter32
    MAX-ACCESS    read-write
    STATUS      current
    DESCRIPTION
        "This is the number of Register requests that the neighbor sends to the AS."
    ::=  {  bwCongestionManagementNeighborEntry  5  }

  bwCongestionManagementNeighborOptionsIn OBJECT-TYPE
    SYNTAX      Counter32
    MAX-ACCESS    read-write
    STATUS      current
    DESCRIPTION
        "This is the number of Options requests that the neighbor sends to the AS."
    ::=  {  bwCongestionManagementNeighborEntry  6  }

  bwCongestionManagementNeighborOptionsOut  OBJECT-TYPE
    SYNTAX      Counter32
    MAX-ACCESS    read-write
    STATUS      current
    DESCRIPTION
        "This is the number of Options requests that the AS sends to the neighbor."
    ::=  {  bwCongestionManagementNeighborEntry  7  }

  bwCongestionManagementNeighborSubscribeNotifyIn OBJECT-TYPE
    SYNTAX      Counter32
    MAX-ACCESS    read-write
    STATUS      current
    DESCRIPTION
        "This is the number of Subscribe and Notify requests that the neighbor sends to the AS."
    ::=  {  bwCongestionManagementNeighborEntry  8  }

  bwCongestionManagementNeighborSubscribeNotifyOut  OBJECT-TYPE
    SYNTAX      Counter32
    MAX-ACCESS    read-write
    STATUS      current
    DESCRIPTION
        "This is the number of Subscribe and Notify requests that the AS sends to the neighbor."
    ::=  {  bwCongestionManagementNeighborEntry  9  }

  bwCongestionManagementNeighbor5xxIn OBJECT-TYPE
    SYNTAX      Counter32
    MAX-ACCESS    read-write
    STATUS      current
    DESCRIPTION
        "This is the number of 5xx responses that the neighbor sends to the AS."
    ::=  {  bwCongestionManagementNeighborEntry  10  }

  bwCongestionManagementNeighborCallpMessageInRate  OBJECT-TYPE
    SYNTAX      Gauge32
    MAX-ACCESS    read-only
    STATUS      current
    DESCRIPTION
        "This is the incoming callp messages (requests and responses) rate."
    ::=  {  bwCongestionManagementNeighborEntry  11  }

  bwCongestionManagementNeighborCallpMessageOutRate OBJECT-TYPE
    SYNTAX      Gauge32
    MAX-ACCESS    read-only
    STATUS      current
    DESCRIPTION
        "This is the outgoing callp messages (requests and responses) rate."
    ::=  {  bwCongestionManagementNeighborEntry  12  }

  bwCongestionManagementNeighborCallpRequestInRate  OBJECT-TYPE
    SYNTAX      Gauge32
    MAX-ACCESS    read-only
    STATUS      current
    DESCRIPTION
        "This is the incoming callp requests rate."
    ::=  {  bwCongestionManagementNeighborEntry  13  }

  bwCongestionManagementNeighborNonCallpMessageInRate OBJECT-TYPE
    SYNTAX      Gauge32
    MAX-ACCESS    read-only
    STATUS      current
    DESCRIPTION
        "This is the incoming non-callp messages (requests and responses) rate."
    ::=  {  bwCongestionManagementNeighborEntry  14  }

  bwCongestionManagementNeighborNonCallpMessageOutRate  OBJECT-TYPE
    SYNTAX      Gauge32
    MAX-ACCESS    read-only
    STATUS      current
    DESCRIPTION
        "This is the outgoing non-callp messages (requests and responses) rate."
    ::=  {  bwCongestionManagementNeighborEntry  15  }

  bwCongestionManagementNeighborNonCallpRequestInRate OBJECT-TYPE
    SYNTAX      Gauge32
    MAX-ACCESS    read-only
    STATUS      current
    DESCRIPTION
        "This is the incoming non-callp requests rate."
    ::=  {  bwCongestionManagementNeighborEntry  16  }

  bwCongestionManagementNeighborState OBJECT-TYPE
    SYNTAX      DisplayString
    MAX-ACCESS    read-only
    STATUS      current
    DESCRIPTION
        "The current congestion management state of the neighbor."
    ::=  {  bwCongestionManagementNeighborEntry  17  }

  bwCongestionManagementNeighborCapability  OBJECT-TYPE
    SYNTAX      DisplayString
    MAX-ACCESS    read-only
    STATUS      current
    DESCRIPTION
        "The congestion management capability of the neighbor."
    ::=  {  bwCongestionManagementNeighborEntry  18  }

-- Service :: Account Code  ...........................................

  bwAuthCodeNumAttempts OBJECT-TYPE
    SYNTAX      Counter32
    MAX-ACCESS    read-write
    STATUS      current
                DESCRIPTION
                                "This counter reflects the number of authorization attempts"
                ::=  {  accountCodes  1  }

  bwAuthCodeNumValidations  OBJECT-TYPE
    SYNTAX      Counter32
    MAX-ACCESS    read-write
    STATUS      current
                DESCRIPTION
                                "This counter reflects the number of successful validations"
                ::=  {  accountCodes  2  }

  bwAccountCodeNumAttempts  OBJECT-TYPE
    SYNTAX      Counter32
    MAX-ACCESS    read-write
    STATUS      current
                DESCRIPTION
                                "This counter is incremented whenever the user is prompted for an account code in Automatic mode"
                ::=  {  accountCodes  3  }

  bwAccountCodesSPTable OBJECT-TYPE
    SYNTAX    SEQUENCE  OF  BwAccountCodesSPEntry
    MAX-ACCESS  not-accessible
    STATUS    current
                DESCRIPTION
                        "This table contains the counters for Account/Authorization Codes service measurements for service providers"
                ::=  { accountCodes  4 }

  bwAccountCodesGroupTable  OBJECT-TYPE
    SYNTAX    SEQUENCE  OF  BwAccountCodesGroupEntry
    MAX-ACCESS  not-accessible
    STATUS    current
                DESCRIPTION
                        "This table contains the counters for Account/Authorization Codes service measurements for groups"
                ::=  { accountCodes  5 }

  bwAccountCodeNumPerCallAttempts OBJECT-TYPE
    SYNTAX      Counter32
    MAX-ACCESS    read-write
    STATUS      current
                DESCRIPTION
                                "This counter is incremented whenever the user is prompted for an account code in FAC-based mode"
                ::=  {  accountCodes  6  }

-- Service :: Account Code  :: SP TABLE ...........................................

  bwAccountCodesSPEntry OBJECT-TYPE
    SYNTAX    BwAccountCodesSPEntry
    MAX-ACCESS  not-accessible
    STATUS    current
                DESCRIPTION
                        "This row contains the counters for Account/Authorization Codes service measurements for a service provider"
    INDEX   {  bwAccountCodesSPIndex  }
                ::=  { bwAccountCodesSPTable 1 }

        BwAccountCodesSPEntry  ::=  SEQUENCE {
                bwAccountCodesSPIndex  Unsigned32,
                bwAccountCodesSPID  DisplayString,
                bwAuthCodeSPNumAttempts  Counter32,
                bwAuthCodeSPNumValidations  Counter32,
                bwAccountCodeSPNumAttempts  Counter32,
                bwAccountCodeSPNumPerCallAttempts  Counter32
                }


  bwAccountCodesSPIndex OBJECT-TYPE
    SYNTAX      Unsigned32
    MAX-ACCESS    read-only
    STATUS      current
                DESCRIPTION
                                "This integer represents the a service provider index in the system"
                ::=  {  bwAccountCodesSPEntry  1  }


  bwAccountCodesSPID  OBJECT-TYPE
    SYNTAX      DisplayString
    MAX-ACCESS    read-only
    STATUS      current
                DESCRIPTION
                                "This string represents a service provider ID"
                ::=  {  bwAccountCodesSPEntry  2  }


  bwAuthCodeSPNumAttempts OBJECT-TYPE
    SYNTAX      Counter32
    MAX-ACCESS    read-write
    STATUS      current
                DESCRIPTION
                                "This counter reflects the number of authorization attempts for a service provider"
                ::=  {  bwAccountCodesSPEntry  3  }


  bwAuthCodeSPNumValidations  OBJECT-TYPE
    SYNTAX      Counter32
    MAX-ACCESS    read-write
    STATUS      current
                DESCRIPTION
                                "This counter reflects the number of successful validations for a service provider"
                ::=  {  bwAccountCodesSPEntry  4  }

  bwAccountCodeSPNumAttempts  OBJECT-TYPE
    SYNTAX      Counter32
    MAX-ACCESS    read-write
    STATUS      current
                DESCRIPTION
                                "Number of attempts to validate an Account Code (for a given service provider)."
                ::=  {  bwAccountCodesSPEntry  5  }


  bwAccountCodeSPNumPerCallAttempts OBJECT-TYPE
    SYNTAX      Counter32
    MAX-ACCESS    read-write
    STATUS      current
                DESCRIPTION
                                "Number of attempts to validate an Account Code (for a given service provider)."
                ::=  {  bwAccountCodesSPEntry  6  }

-- Service :: Account Code  :: Group TABLE ...........................................

  bwAccountCodesGroupEntry  OBJECT-TYPE
    SYNTAX    BwAccountCodesGroupEntry
    MAX-ACCESS  not-accessible
    STATUS    current
                DESCRIPTION
                        "This row contains the counters for Account/Authorization Codes service measurements for a group"
    INDEX   {  bwAccountCodesGroupIndex  }
                ::=  { bwAccountCodesGroupTable 1 }

        BwAccountCodesGroupEntry  ::=  SEQUENCE {
                bwAccountCodesGroupIndex  Unsigned32,
                bwAccountCodesGroupID  DisplayString,
                bwAuthCodeGroupNumAttempts  Counter32,
                bwAuthCodeGroupNumValidations  Counter32,
                bwAccountCodeGroupNumAttempts  Counter32,
                bwAccountCodeGroupNumPerCallAttempts Counter32
                }


  bwAccountCodesGroupIndex  OBJECT-TYPE
    SYNTAX      Unsigned32
    MAX-ACCESS    read-only
    STATUS      current
                DESCRIPTION
                                "This integer represents the a group index in the system"
                ::=  {  bwAccountCodesGroupEntry  1  }


  bwAccountCodesGroupID OBJECT-TYPE
    SYNTAX      DisplayString
    MAX-ACCESS    read-only
    STATUS      current
                DESCRIPTION
                                "This string represents a Group ID"
                ::=  {  bwAccountCodesGroupEntry  2  }


  bwAuthCodeGroupNumAttempts  OBJECT-TYPE
    SYNTAX      Counter32
    MAX-ACCESS    read-write
    STATUS      current
                DESCRIPTION
                                "This counter reflects the number of authorization attempts for a group"
                ::=  {  bwAccountCodesGroupEntry  3  }


  bwAuthCodeGroupNumValidations OBJECT-TYPE
    SYNTAX      Counter32
    MAX-ACCESS    read-write
    STATUS      current
                DESCRIPTION
                                "This counter reflects the number of successful validations for a group"
                ::=  {  bwAccountCodesGroupEntry  4  }


  bwAccountCodeGroupNumAttempts OBJECT-TYPE
    SYNTAX      Counter32
    MAX-ACCESS    read-write
    STATUS      current
                DESCRIPTION
                                "This counter reflects the number of Account code attempts for a group"
                ::=  {  bwAccountCodesGroupEntry  5  }

  bwAccountCodeGroupNumPerCallAttempts  OBJECT-TYPE
    SYNTAX      Counter32
    MAX-ACCESS    read-write
    STATUS      current
                DESCRIPTION
                                "Number of attempts to validate an Account Code (for a given group)."
                ::=  {  bwAccountCodesGroupEntry  6  }

-- Service :: Anonymous calls  ...........................................

  bwAnonymousCallsNumRejected OBJECT-TYPE
    SYNTAX      Counter32
    MAX-ACCESS    read-write
    STATUS      current
                DESCRIPTION
                                "This counter reflects the number of incoming anonymous calls rejected"
                ::=  {  anonymousCallRejection  1  }

  bwAnonymousCallRejectionSPTable OBJECT-TYPE
    SYNTAX    SEQUENCE  OF  BwAnonymousCallRejectionSPEntry
    MAX-ACCESS  not-accessible
    STATUS    current
                DESCRIPTION
                        "This table contains the counters for Anonymous Call Rejection service measurements for service providers"
                ::=  { anonymousCallRejection  2 }

  bwAnonymousCallRejectionGroupTable  OBJECT-TYPE
    SYNTAX    SEQUENCE  OF  BwAnonymousCallRejectionGroupEntry
    MAX-ACCESS  not-accessible
    STATUS    current
                DESCRIPTION
                        "This table contains the counters for Anonymous Call Rejection service measurements for group"
                ::=  { anonymousCallRejection  3 }

-- Service :: Anonymous calls  :: SP TABLE...........................................

  bwAnonymousCallRejectionSPEntry OBJECT-TYPE
    SYNTAX    BwAnonymousCallRejectionSPEntry
    MAX-ACCESS  not-accessible
    STATUS    current
                DESCRIPTION
                        "This row contains the counters for Anonymous Call Rejection service measurements for a service provider"
    INDEX   {  bwAnonymousCallRejectionSPIndex  }
                ::=  { bwAnonymousCallRejectionSPTable 1 }

        BwAnonymousCallRejectionSPEntry  ::=  SEQUENCE {
                bwAnonymousCallRejectionSPIndex  Unsigned32,
                bwAnonymousCallRejectionSPID  DisplayString,
                bwAnonymousCallsSPNumRejected  Counter32
                }


  bwAnonymousCallRejectionSPIndex OBJECT-TYPE
    SYNTAX      Unsigned32
    MAX-ACCESS    read-only
    STATUS      current
                DESCRIPTION
                                "This integer represents the a service provider index in the system"
                ::=  {  bwAnonymousCallRejectionSPEntry  1  }


  bwAnonymousCallRejectionSPID  OBJECT-TYPE
    SYNTAX      DisplayString
    MAX-ACCESS    read-only
    STATUS      current
                DESCRIPTION
                                "This string represents a service provider ID"
                ::=  {  bwAnonymousCallRejectionSPEntry  2  }


  bwAnonymousCallsSPNumRejected OBJECT-TYPE
    SYNTAX      Counter32
    MAX-ACCESS    read-write
    STATUS      current
                DESCRIPTION
                                "This counter reflects the number of incoming anonymous calls rejected by a service provider"
                ::=  {  bwAnonymousCallRejectionSPEntry  3  }

-- Service :: Anonymous calls  :: GROUP TABLE...........................................

  bwAnonymousCallRejectionGroupEntry  OBJECT-TYPE
    SYNTAX    BwAnonymousCallRejectionGroupEntry
    MAX-ACCESS  not-accessible
    STATUS    current
                DESCRIPTION
                        "This row contains the counters for Anonymous Call Rejection service measurements for a group"
    INDEX   {  bwAnonymousCallRejectionGroupIndex  }
                ::=  { bwAnonymousCallRejectionGroupTable 1 }

        BwAnonymousCallRejectionGroupEntry  ::=  SEQUENCE {
                bwAnonymousCallRejectionGroupIndex  Unsigned32,
                bwAnonymousCallRejectionGroupID  DisplayString,
                bwAnonymousCallsGroupNumRejected  Counter32
                }


  bwAnonymousCallRejectionGroupIndex  OBJECT-TYPE
    SYNTAX      Unsigned32
    MAX-ACCESS    read-only
    STATUS      current
                DESCRIPTION
                                "This integer represents the a group index in the system"
                ::=  {  bwAnonymousCallRejectionGroupEntry  1  }


  bwAnonymousCallRejectionGroupID OBJECT-TYPE
    SYNTAX      DisplayString
    MAX-ACCESS    read-only
    STATUS      current
                DESCRIPTION
                                "This string represents a group ID"
                ::=  {  bwAnonymousCallRejectionGroupEntry  2  }


  bwAnonymousCallsGroupNumRejected  OBJECT-TYPE
    SYNTAX      Counter32
    MAX-ACCESS    read-write
    STATUS      current
                DESCRIPTION
                                "This counter reflects the number of incoming anonymous calls rejected by a group"
                ::=  {  bwAnonymousCallRejectionGroupEntry  3  }

-- Service :: Authentication  ...........................................

  bwAuthenticationNumChallenges OBJECT-TYPE
    SYNTAX      Counter32
    MAX-ACCESS    read-write
    STATUS      current
                DESCRIPTION
                                "This counter reflects the number of authentication challenges"
                ::=  {  authentication  1  }

  bwAuthenticationNumValidResponses OBJECT-TYPE
    SYNTAX      Counter32
    MAX-ACCESS    read-write
    STATUS      current
                DESCRIPTION
                                "This counter reflects the number of valid client authentication responses"
                ::=  {  authentication  2  }

  bwAuthenticationSPTable OBJECT-TYPE
    SYNTAX    SEQUENCE  OF  BwAuthenticationSPEntry
    MAX-ACCESS  not-accessible
    STATUS    current
                DESCRIPTION
                        "This table contains the counters for Authentication service measurements for service providers"
                ::=  { authentication  3 }

  bwAuthenticationGroupTable  OBJECT-TYPE
    SYNTAX    SEQUENCE  OF  BwAuthenticationGroupEntry
    MAX-ACCESS  not-accessible
    STATUS    current
                DESCRIPTION
                        "This table contains the counters for Authentication service measurements for groups"
                ::=  { authentication  4 }

-- Service :: Authentication :: SP TABLE...........................................

  bwAuthenticationSPEntry OBJECT-TYPE
    SYNTAX    BwAuthenticationSPEntry
    MAX-ACCESS  not-accessible
    STATUS    current
                DESCRIPTION
                        "This row contains the counters for Authentication service measurements for a service provider"
    INDEX   {  bwAuthenticationSPIndex  }
                ::=  { bwAuthenticationSPTable 1 }

        BwAuthenticationSPEntry  ::=  SEQUENCE {
                bwAuthenticationSPIndex  Unsigned32,
                bwAuthenticationSPID  DisplayString,
                bwAuthenticationSPNumChallenges  Counter32,
                bwAuthenticationSPNumValidResponses  Counter32
                }


  bwAuthenticationSPIndex OBJECT-TYPE
    SYNTAX      Unsigned32
    MAX-ACCESS    read-only
    STATUS      current
                DESCRIPTION
                                "This integer represents the a service provider index in the system"
                ::=  {  bwAuthenticationSPEntry  1  }


  bwAuthenticationSPID  OBJECT-TYPE
    SYNTAX      DisplayString
    MAX-ACCESS    read-only
    STATUS      current
                DESCRIPTION
                                "This string represents a service provider ID"
                ::=  {  bwAuthenticationSPEntry  2  }


  bwAuthenticationSPNumChallenges OBJECT-TYPE
    SYNTAX      Counter32
    MAX-ACCESS    read-write
    STATUS      current
                DESCRIPTION
                                "This counter reflects the number of authentication challenges by a service provider"
                ::=  {  bwAuthenticationSPEntry  3  }


  bwAuthenticationSPNumValidResponses OBJECT-TYPE
    SYNTAX      Counter32
    MAX-ACCESS    read-write
    STATUS      current
                DESCRIPTION
                                "This counter reflects the number of valid client authentication responses by a service provider"
                ::=  {  bwAuthenticationSPEntry  4  }

-- Service :: Authentication :: GROUP TABLE...........................................

  bwAuthenticationGroupEntry  OBJECT-TYPE
    SYNTAX    BwAuthenticationGroupEntry
    MAX-ACCESS  not-accessible
    STATUS    current
                DESCRIPTION
                        "This row contains the counters for Authentication service measurements for a group"
    INDEX   {  bwAuthenticationGroupIndex  }
                ::=  { bwAuthenticationGroupTable 1 }

        BwAuthenticationGroupEntry  ::=  SEQUENCE {
                bwAuthenticationGroupIndex  Unsigned32,
                bwAuthenticationGroupID  DisplayString,
                bwAuthenticationGroupNumChallenges  Counter32,
                bwAuthenticationGroupNumValidResponses  Counter32
                }


  bwAuthenticationGroupIndex  OBJECT-TYPE
    SYNTAX      Unsigned32
    MAX-ACCESS    read-only
    STATUS      current
                DESCRIPTION
                                "This integer represents the a group index in the system"
                ::=  {  bwAuthenticationGroupEntry  1  }


  bwAuthenticationGroupID OBJECT-TYPE
    SYNTAX      DisplayString
    MAX-ACCESS    read-only
    STATUS      current
                DESCRIPTION
                                "This string represents a group ID"
                ::=  {  bwAuthenticationGroupEntry  2  }


  bwAuthenticationGroupNumChallenges  OBJECT-TYPE
    SYNTAX      Counter32
    MAX-ACCESS    read-write
    STATUS      current
                DESCRIPTION
                                "This counter reflects the number of authentication challenges by a group"
                ::=  {  bwAuthenticationGroupEntry  3  }


  bwAuthenticationGroupNumValidResponses  OBJECT-TYPE
    SYNTAX      Counter32
    MAX-ACCESS    read-write
    STATUS      current
                DESCRIPTION
                                "This counter reflects the number of valid client authentication responses by a group"
                ::=  {  bwAuthenticationGroupEntry  4  }

-- Service :: Auto Attendant  ...........................................

  bwAutoAttendantNumAnswers OBJECT-TYPE
    SYNTAX      Counter32
    MAX-ACCESS    read-write
    STATUS      current
                DESCRIPTION
                                "This counter reflects the number of times the Auto Attendant answers an incoming call"
                ::=  {  autoAttendant  1  }

  bwAutoAttendantNumTransfers OBJECT-TYPE
    SYNTAX      Counter32
    MAX-ACCESS    read-write
    STATUS      current
                DESCRIPTION
                                "This counter reflects the number times a call is transferred to another party
                                (name dialing, ext. dialing, etc.) by the Auto Attendant"
                ::=  {  autoAttendant  2  }

  bwAutoAttendantSPTable  OBJECT-TYPE
    SYNTAX    SEQUENCE  OF  BwAutoAttendantSPEntry
    MAX-ACCESS  not-accessible
    STATUS    current
                DESCRIPTION
                        "This table contains the counters for Auto Attendant service measurements for service providers"
                ::=  { autoAttendant  3 }

  bwAutoAttendantGroupTable OBJECT-TYPE
    SYNTAX    SEQUENCE  OF  BwAutoAttendantGroupEntry
    MAX-ACCESS  not-accessible
    STATUS    current
                DESCRIPTION
                        "This table contains the counters for Auto Attendant service measurements for Groups"
                ::=  { autoAttendant  4 }

-- Service :: Auto Attendant :: SP TABLE ...........................................

  bwAutoAttendantSPEntry  OBJECT-TYPE
    SYNTAX    BwAutoAttendantSPEntry
    MAX-ACCESS  not-accessible
    STATUS    current
                DESCRIPTION
                        "This row contains the counters for Auto Attendant Rejection service measurements for a service provider"
    INDEX   {  bwAutoAttendantSPIndex  }
                ::=  { bwAutoAttendantSPTable 1 }

        BwAutoAttendantSPEntry  ::=  SEQUENCE {
                bwAutoAttendantSPIndex  Unsigned32,
                bwAutoAttendantSPID  DisplayString,
                bwAutoAttendantSPNumAnswers  Counter32,
                bwAutoAttendantSPNumTransfers  Counter32
                }


  bwAutoAttendantSPIndex  OBJECT-TYPE
    SYNTAX      Unsigned32
    MAX-ACCESS    read-only
    STATUS      current
                DESCRIPTION
                                "This integer represents the a service provider index in the system"
                ::=  {  bwAutoAttendantSPEntry  1  }


  bwAutoAttendantSPID OBJECT-TYPE
    SYNTAX      DisplayString
    MAX-ACCESS    read-only
    STATUS      current
                DESCRIPTION
                                "This string represents a service provider ID"
                ::=  {  bwAutoAttendantSPEntry  2  }


  bwAutoAttendantSPNumAnswers OBJECT-TYPE
    SYNTAX      Counter32
    MAX-ACCESS    read-write
    STATUS      current
                DESCRIPTION
                                "This counter reflects the number of times the Auto Attendant answers an incoming call by a service provider"
                ::=  {  bwAutoAttendantSPEntry  3  }


  bwAutoAttendantSPNumTransfers OBJECT-TYPE
    SYNTAX      Counter32
    MAX-ACCESS    read-write
    STATUS      current
                DESCRIPTION
                                "This counter reflects the number times a call is transferred to another party (name dialing, ext. dialing, etc.) by the Auto Attendant by a service provider"
                ::=  {  bwAutoAttendantSPEntry  4  }

-- Service :: Auto Attendant :: GROUP TABLE ...........................................

  bwAutoAttendantGroupEntry OBJECT-TYPE
    SYNTAX    BwAutoAttendantGroupEntry
    MAX-ACCESS  not-accessible
    STATUS    current
                DESCRIPTION
                        "This row contains the counters for Auto Attendant Rejection service measurements for a group"
    INDEX   {  bwAutoAttendantGroupIndex  }
                ::=  { bwAutoAttendantGroupTable 1 }

        BwAutoAttendantGroupEntry  ::=  SEQUENCE {
                bwAutoAttendantGroupIndex  Unsigned32,
                bwAutoAttendantGroupID  DisplayString,
                bwAutoAttendantGroupNumAnswers  Counter32,
                bwAutoAttendantGroupNumTransfers  Counter32
                }


  bwAutoAttendantGroupIndex OBJECT-TYPE
    SYNTAX      Unsigned32
    MAX-ACCESS    read-only
    STATUS      current
                DESCRIPTION
                                "This integer represents the a group index in the system"
                ::=  {  bwAutoAttendantGroupEntry  1  }


  bwAutoAttendantGroupID  OBJECT-TYPE
    SYNTAX      DisplayString
    MAX-ACCESS    read-only
    STATUS      current
                DESCRIPTION
                                "This string represents a group ID"
                ::=  {  bwAutoAttendantGroupEntry  2  }


  bwAutoAttendantGroupNumAnswers  OBJECT-TYPE
    SYNTAX      Counter32
    MAX-ACCESS    read-write
    STATUS      current
                DESCRIPTION
                                "This counter reflects the number of times the Auto Attendant answers an incoming call by a group"
                ::=  {  bwAutoAttendantGroupEntry  3  }


  bwAutoAttendantGroupNumTransfers  OBJECT-TYPE
    SYNTAX      Counter32
    MAX-ACCESS    read-write
    STATUS      current
                DESCRIPTION
                                "This counter reflects the number times a call is transferred to another party (name dialing, ext. dialing, etc.) by the Auto Attendant by a group"
                ::=  {  bwAutoAttendantGroupEntry  4  }

-- Service :: Call Capacity  ...........................................

  bwCallCapacityNumCallsAttempted OBJECT-TYPE
    SYNTAX      Counter32
    MAX-ACCESS    read-write
    STATUS      current
                DESCRIPTION
                                "This counter reflects the number of calls attempted"
                ::=  {  callCapacity  1  }

  bwCallCapacityNumCallsBlocked OBJECT-TYPE
    SYNTAX      Counter32
    MAX-ACCESS    read-write
    STATUS      current
                DESCRIPTION
                                "This counter reflects the number of calls blocked by this service"
                ::=  {  callCapacity  2  }

  bwCallCapacitySPTable OBJECT-TYPE
    SYNTAX    SEQUENCE  OF  BwCallCapacitySPEntry
    MAX-ACCESS  not-accessible
    STATUS    current
                DESCRIPTION
                        "This table contains the counters for Call Capacity Management service measurements for service providers"
                ::=  { callCapacity  3 }

  bwCallCapacityGroupTable  OBJECT-TYPE
    SYNTAX    SEQUENCE  OF  BwCallCapacityGroupEntry
    MAX-ACCESS  not-accessible
    STATUS    current
                DESCRIPTION
                        "This table contains the counters for Call Capacity Management service measurements for groups"
                ::=  { callCapacity  4 }

-- Service :: Call Capacity :: SP TABLE ...........................................

  bwCallCapacitySPEntry OBJECT-TYPE
    SYNTAX    BwCallCapacitySPEntry
    MAX-ACCESS  not-accessible
    STATUS    current
                DESCRIPTION
                        "This row contains the counters for Call Capacity Management service measurements for a service provider"
    INDEX   {  bwCallCapacitySPIndex  }
                ::=  { bwCallCapacitySPTable 1 }

        BwCallCapacitySPEntry  ::=  SEQUENCE {
                bwCallCapacitySPIndex  Unsigned32,
                bwCallCapacitySPID  DisplayString,
                bwCallCapacitySPNumCallsAttempted  Counter32,
                bwCallCapacitySPNumCallsBlocked  Counter32
                }


  bwCallCapacitySPIndex OBJECT-TYPE
    SYNTAX      Unsigned32
    MAX-ACCESS    read-only
    STATUS      current
                DESCRIPTION
                                "This integer represents the a service provider index in the system"
                ::=  {  bwCallCapacitySPEntry  1  }


  bwCallCapacitySPID  OBJECT-TYPE
    SYNTAX      DisplayString
    MAX-ACCESS    read-only
    STATUS      current
                DESCRIPTION
                                "This string represents a service provider ID"
                ::=  {  bwCallCapacitySPEntry  2  }


  bwCallCapacitySPNumCallsAttempted OBJECT-TYPE
    SYNTAX      Counter32
    MAX-ACCESS    read-write
    STATUS      current
                DESCRIPTION
                                "This counter reflects the number of calls attempted by a service provider"
                ::=  {  bwCallCapacitySPEntry  3  }


  bwCallCapacitySPNumCallsBlocked OBJECT-TYPE
    SYNTAX      Counter32
    MAX-ACCESS    read-write
    STATUS      current
                DESCRIPTION
                                "This counter reflects the number of calls blocked by this service by a service provider"
                ::=  {  bwCallCapacitySPEntry  4  }

-- Service :: Call Capacity :: SP TABLE ...........................................

  bwCallCapacityGroupEntry  OBJECT-TYPE
    SYNTAX    BwCallCapacityGroupEntry
    MAX-ACCESS  not-accessible
    STATUS    current
                DESCRIPTION
                        "This row contains the counters for Call Capacity Management service measurements for a group"
    INDEX   {  bwCallCapacityGroupIndex  }
                ::=  { bwCallCapacityGroupTable 1 }

        BwCallCapacityGroupEntry  ::=  SEQUENCE {
                bwCallCapacityGroupIndex  Unsigned32,
                bwCallCapacityGroupID  DisplayString,
                bwCallCapacityGroupNumCallsAttempted  Counter32,
                bwCallCapacityGroupNumCallsBlocked  Counter32
                }


  bwCallCapacityGroupIndex  OBJECT-TYPE
    SYNTAX      Unsigned32
    MAX-ACCESS    read-only
    STATUS      current
                DESCRIPTION
                                "This integer represents the a group index in the system"
                ::=  {  bwCallCapacityGroupEntry  1  }


  bwCallCapacityGroupID OBJECT-TYPE
    SYNTAX      DisplayString
    MAX-ACCESS    read-only
    STATUS      current
                DESCRIPTION
                                "This string represents a group ID"
                ::=  {  bwCallCapacityGroupEntry  2  }


  bwCallCapacityGroupNumCallsAttempted  OBJECT-TYPE
    SYNTAX      Counter32
    MAX-ACCESS    read-write
    STATUS      current
                DESCRIPTION
                                "This counter reflects the number of calls attempted by a group"
                ::=  {  bwCallCapacityGroupEntry  3  }


  bwCallCapacityGroupNumCallsBlocked  OBJECT-TYPE
    SYNTAX      Counter32
    MAX-ACCESS    read-write
    STATUS      current
                DESCRIPTION
                                "This counter reflects the number of calls blocked by this service by a group"
                ::=  {  bwCallCapacityGroupEntry  4  }

-- Service :: Call Forward Always  ...........................................

  bwCFANumForwarded OBJECT-TYPE
    SYNTAX      Counter32
    MAX-ACCESS    read-write
    STATUS      current
                DESCRIPTION
                                "This counter reflects the number of calls forwarded"
                ::=  {  callForwardingAlways  1  }

  bwCFANumPhoneActivations  OBJECT-TYPE
    SYNTAX      Counter32
    MAX-ACCESS    read-write
    STATUS      current
                DESCRIPTION
                                "Incremented whenever a user activates CFA via FAC"
                ::=  {  callForwardingAlways  2  }

  bwCFANumPhoneDeactivations  OBJECT-TYPE
    SYNTAX      Counter32
    MAX-ACCESS    read-write
    STATUS      current
                DESCRIPTION
                                "Incremented whenever a user deactivates CFN via FAC"
                ::=  {  callForwardingAlways  3  }

  bwCallForwardingAlwaysSPTable OBJECT-TYPE
    SYNTAX    SEQUENCE  OF  BwCallForwardingAlwaysSPEntry
    MAX-ACCESS  not-accessible
    STATUS    current
                DESCRIPTION
                        "This table contains the counters for Call Forwarding Always service measurements for service providers"
                ::=  { callForwardingAlways  4 }

  bwCFADestinationChanged   OBJECT-TYPE
    SYNTAX      Counter32
    MAX-ACCESS    read-write
    STATUS      current
                DESCRIPTION
                                "Incremented whenever a user changes the CFA destination via FAC"
                ::=  {  callForwardingAlways  5  }

  bwCallForwardingAlwaysGroupTable  OBJECT-TYPE
    SYNTAX    SEQUENCE  OF  BwCallForwardingAlwaysGroupEntry
    MAX-ACCESS  not-accessible
    STATUS    current
                DESCRIPTION
                        "This table contains the counters for Call Forwarding Always service measurements for groups"
                ::=  { callForwardingAlways  6 }

-- Service :: Call Forward Always :: SP TABLE ...........................................

  bwCallForwardingAlwaysSPEntry OBJECT-TYPE
    SYNTAX    BwCallForwardingAlwaysSPEntry
    MAX-ACCESS  not-accessible
    STATUS    current
                DESCRIPTION
                        "This row contains the counters for Call Forwarding Always service measurements for a service provider"
    INDEX   {  bwCallForwardingAlwaysSPIndex  }
                ::=  { bwCallForwardingAlwaysSPTable 1 }

        BwCallForwardingAlwaysSPEntry  ::=  SEQUENCE {
    bwCallForwardingAlwaysSPIndex   Unsigned32,
    bwCallForwardingAlwaysSPID    DisplayString,
    bwCFASPNumForwarded     Counter32,
    bwCFASPNumPhoneActivations    Counter32,
    bwCFASPNumPhoneDeactivations    Counter32,
    bwCFASPDestinationChanged     Counter32
                }


  bwCallForwardingAlwaysSPIndex OBJECT-TYPE
    SYNTAX      Unsigned32
    MAX-ACCESS    read-only
    STATUS      current
                DESCRIPTION
                                "This integer represents the a service provider index in the system"
                ::=  {  bwCallForwardingAlwaysSPEntry  1  }


  bwCallForwardingAlwaysSPID  OBJECT-TYPE
    SYNTAX      DisplayString
    MAX-ACCESS    read-only
    STATUS      current
                DESCRIPTION
                                "This string represents a service provider ID"
                ::=  {  bwCallForwardingAlwaysSPEntry  2  }


  bwCFASPNumForwarded OBJECT-TYPE
    SYNTAX      Counter32
    MAX-ACCESS    read-write
    STATUS      current
                DESCRIPTION
                                "This counter reflects the number of calls forwarded for a given service provider"
                ::=  {  bwCallForwardingAlwaysSPEntry  3  }


  bwCFASPNumPhoneActivations  OBJECT-TYPE
    SYNTAX      Counter32
    MAX-ACCESS    read-write
    STATUS      current
                DESCRIPTION
                                "Number of times CFA has been activated via FAC for users in a given service provider"
                ::=  {  bwCallForwardingAlwaysSPEntry  4  }


  bwCFASPNumPhoneDeactivations  OBJECT-TYPE
    SYNTAX      Counter32
    MAX-ACCESS    read-write
    STATUS      current
                DESCRIPTION
                                "Number of times CFA has been deactivated via FAC for users in a given service provider"
                ::=  {  bwCallForwardingAlwaysSPEntry  5  }

  bwCFASPDestinationChanged OBJECT-TYPE
    SYNTAX      Counter32
    MAX-ACCESS    read-write
    STATUS      current
                DESCRIPTION
                                "Number of times CFA destination has been changed, by FAC only for a given service provider"
                ::=  {  bwCallForwardingAlwaysSPEntry  6  }

-- Service :: Call Forward Always :: GROUP TABLE ...........................................

  bwCallForwardingAlwaysGroupEntry  OBJECT-TYPE
    SYNTAX    BwCallForwardingAlwaysGroupEntry
    MAX-ACCESS  not-accessible
    STATUS    current
                DESCRIPTION
                        "This row contains the counters for Call Forwarding Always service measurements for a group"
    INDEX   {  bwCallForwardingAlwaysGroupIndex  }
                ::=  { bwCallForwardingAlwaysGroupTable 1 }

        BwCallForwardingAlwaysGroupEntry  ::=  SEQUENCE {
    bwCallForwardingAlwaysGroupIndex    Unsigned32,
    bwCallForwardingAlwaysGroupID   DisplayString,
    bwCFAGroupNumForwarded      Counter32,
    bwCFAGroupNumPhoneActivations   Counter32,
    bwCFAGroupNumPhoneDeactivations   Counter32,
    bwCFAGroupDestinationChanged      Counter32
                }


  bwCallForwardingAlwaysGroupIndex  OBJECT-TYPE
    SYNTAX      Unsigned32
    MAX-ACCESS    read-only
    STATUS      current
                DESCRIPTION
                                "This integer represents the a group index in the system"
                ::=  {  bwCallForwardingAlwaysGroupEntry  1  }


  bwCallForwardingAlwaysGroupID OBJECT-TYPE
    SYNTAX      DisplayString
    MAX-ACCESS    read-only
    STATUS      current
                DESCRIPTION
                                "This string represents a group ID"
                ::=  {  bwCallForwardingAlwaysGroupEntry  2  }


  bwCFAGroupNumForwarded  OBJECT-TYPE
    SYNTAX      Counter32
    MAX-ACCESS    read-write
    STATUS      current
                DESCRIPTION
                                "This counter reflects the number of calls forwarded for a given group"
                ::=  {  bwCallForwardingAlwaysGroupEntry  3  }


  bwCFAGroupNumPhoneActivations OBJECT-TYPE
    SYNTAX      Counter32
    MAX-ACCESS    read-write
    STATUS      current
                DESCRIPTION
                                "Number of times CFA has been activated via FAC for users in a given group"
                ::=  {  bwCallForwardingAlwaysGroupEntry  4  }


  bwCFAGroupNumPhoneDeactivations OBJECT-TYPE
    SYNTAX      Counter32
    MAX-ACCESS    read-write
    STATUS      current
                DESCRIPTION
                                "Number of times CFA has been deactivated via FAC for users in a given group"
                ::=  {  bwCallForwardingAlwaysGroupEntry  5  }

  bwCFAGroupDestinationChanged  OBJECT-TYPE
    SYNTAX      Counter32
    MAX-ACCESS    read-write
    STATUS      current
                DESCRIPTION
                                "Number of times CFA destination has been changed, by FAC only for a given group"
                ::=  {  bwCallForwardingAlwaysGroupEntry  6  }

-- Service :: Call Forward Busy  ...........................................

  bwCFBNumForwarded OBJECT-TYPE
    SYNTAX      Counter32
    MAX-ACCESS    read-write
    STATUS      current
                DESCRIPTION
                                "This counter reflects the number of times a call is forwarded by this service"
                ::=  {  callForwardingBusy  1  }

  bwCallForwardingBusySPTable OBJECT-TYPE
    SYNTAX    SEQUENCE  OF  BwCallForwardingBusySPEntry
    MAX-ACCESS  not-accessible
    STATUS    current
                DESCRIPTION
                        "This table contains the counters for Call Forwarding Busy service measurements for service providers"
                ::=  { callForwardingBusy  2 }

  bwCFBNumPhoneActivations  OBJECT-TYPE
    SYNTAX      Counter32
    MAX-ACCESS    read-write
    STATUS      current
                DESCRIPTION
                                "Total number of times CFB has been activated via FAC"
                ::=  {  callForwardingBusy  3  }

  bwCFBNumPhoneDeactivations  OBJECT-TYPE
    SYNTAX      Counter32
    MAX-ACCESS    read-write
    STATUS      current
                DESCRIPTION
                                "Total number of times CFB has been deactivated via FAC"
                ::=  {  callForwardingBusy  4  }

  bwCFBDestinationChanged   OBJECT-TYPE
    SYNTAX      Counter32
    MAX-ACCESS    read-write
    STATUS      current
                DESCRIPTION
                                "Incremented whenever a user changes the CFB destination via FAC"
                ::=  {  callForwardingBusy  5  }

  bwCallForwardingBusyGroupTable  OBJECT-TYPE
    SYNTAX    SEQUENCE  OF  BwCallForwardingBusyGroupEntry
    MAX-ACCESS  not-accessible
    STATUS    current
                DESCRIPTION
                        "This table contains the counters for Call Forwarding Busy service measurements for groups"
                ::=  { callForwardingBusy  6 }

-- Service :: Call Forward Busy :: SP TABLE ...........................................

  bwCallForwardingBusySPEntry OBJECT-TYPE
    SYNTAX    BwCallForwardingBusySPEntry
    MAX-ACCESS  not-accessible
    STATUS    current
                DESCRIPTION
                        "This row contains the counters for Call Forwarding Busy service measurements for a service provider"
    INDEX   {  bwCallForwardingBusySPIndex  }
                ::=  { bwCallForwardingBusySPTable 1 }

        BwCallForwardingBusySPEntry  ::=  SEQUENCE {
                bwCallForwardingBusySPIndex  Unsigned32,
                bwCallForwardingBusySPID  DisplayString,
                bwCFBSPNumForwarded  Counter32,
                bwCFBSPNumPhoneActivations  Counter32,
                bwCFBSPNumPhoneDeactivations  Counter32,
    bwCFBSPDestinationChanged   Counter32
                }


  bwCallForwardingBusySPIndex OBJECT-TYPE
    SYNTAX      Unsigned32
    MAX-ACCESS    read-only
    STATUS      current
                DESCRIPTION
                                "This integer represents the a service provider index in the system"
                ::=  {  bwCallForwardingBusySPEntry  1  }


  bwCallForwardingBusySPID  OBJECT-TYPE
    SYNTAX      DisplayString
    MAX-ACCESS    read-only
    STATUS      current
                DESCRIPTION
                                "This string represents a service provider ID"
                ::=  {  bwCallForwardingBusySPEntry  2  }


  bwCFBSPNumForwarded OBJECT-TYPE
    SYNTAX      Counter32
    MAX-ACCESS    read-write
    STATUS      current
                DESCRIPTION
                                "This counter reflects the number of times a call is forwarded by this service by a service provider"
                ::=  {  bwCallForwardingBusySPEntry  3  }

  bwCFBSPNumPhoneActivations  OBJECT-TYPE
    SYNTAX      Counter32
    MAX-ACCESS    read-write
    STATUS      current
                DESCRIPTION
                                "Number of times CFB has been activated via FAC for users in a given service provider"
                ::=  {  bwCallForwardingBusySPEntry  4  }

  bwCFBSPNumPhoneDeactivations  OBJECT-TYPE
    SYNTAX      Counter32
    MAX-ACCESS    read-write
    STATUS      current
                DESCRIPTION
                                "Number of times CFB has been deactivated via FAC for users in a given service provider"
                ::=  {  bwCallForwardingBusySPEntry  5  }

  bwCFBSPDestinationChanged OBJECT-TYPE
    SYNTAX      Counter32
    MAX-ACCESS    read-write
    STATUS      current
                DESCRIPTION
                                "Number of times CFB destination has been changed, by FAC only for a given service provider"
                ::=  {  bwCallForwardingBusySPEntry  6  }

-- Service :: Call Forward Busy :: GROUP TABLE ...........................................

  bwCallForwardingBusyGroupEntry  OBJECT-TYPE
    SYNTAX    BwCallForwardingBusyGroupEntry
    MAX-ACCESS  not-accessible
    STATUS    current
                DESCRIPTION
                        "This row contains the counters for Call Forwarding Busy service measurements for a group"
    INDEX   {  bwCallForwardingBusyGroupIndex  }
                ::=  { bwCallForwardingBusyGroupTable 1 }

        BwCallForwardingBusyGroupEntry  ::=  SEQUENCE {
                bwCallForwardingBusyGroupIndex  Unsigned32,
                bwCallForwardingBusyGroupID  DisplayString,
                bwCFBGroupNumForwarded  Counter32,
                bwCFBGroupNumPhoneActivations  Counter32,
                bwCFBGroupNumPhoneDeactivations  Counter32,
    bwCFBGroupDestinationChanged    Counter32
                }


  bwCallForwardingBusyGroupIndex  OBJECT-TYPE
    SYNTAX      Unsigned32
    MAX-ACCESS    read-only
    STATUS      current
                DESCRIPTION
                                "This integer represents the a group index in the system"
                ::=  {  bwCallForwardingBusyGroupEntry  1  }


  bwCallForwardingBusyGroupID OBJECT-TYPE
    SYNTAX      DisplayString
    MAX-ACCESS    read-only
    STATUS      current
                DESCRIPTION
                                "This string represents a group ID"
                ::=  {  bwCallForwardingBusyGroupEntry  2  }


  bwCFBGroupNumForwarded  OBJECT-TYPE
    SYNTAX      Counter32
    MAX-ACCESS    read-write
    STATUS      current
                DESCRIPTION
                                "This counter reflects the number of times a call is forwarded by this service by a group"
                ::=  {  bwCallForwardingBusyGroupEntry  3  }

  bwCFBGroupNumPhoneActivations OBJECT-TYPE
    SYNTAX      Counter32
    MAX-ACCESS    read-write
    STATUS      current
                DESCRIPTION
                                "Number of times CFB has been activated via FAC for users in a given group"
                ::=  {  bwCallForwardingBusyGroupEntry  4  }

  bwCFBGroupNumPhoneDeactivations OBJECT-TYPE
    SYNTAX      Counter32
    MAX-ACCESS    read-write
    STATUS      current
                DESCRIPTION
                                "Number of times CFB has been deactivated via FAC for users in a given group"
                ::=  {  bwCallForwardingBusyGroupEntry  5  }

  bwCFBGroupDestinationChanged  OBJECT-TYPE
    SYNTAX      Counter32
    MAX-ACCESS    read-write
    STATUS      current
                DESCRIPTION
                                "Number of times CFB destination has been changed, by FAC only for a given group"
                ::=  {  bwCallForwardingBusyGroupEntry  6  }

-- Service :: Call Forward No Answer  ...........................................

  bwCFNANumForwarded  OBJECT-TYPE
    SYNTAX      Counter32
    MAX-ACCESS    read-write
    STATUS      current
                DESCRIPTION
                                "This counter reflects the number of times a call is forwarded by this service"
                ::=  {  callForwardingNoAnswer  1  }

  bwCallForwardingNoAnswerSPTable OBJECT-TYPE
    SYNTAX    SEQUENCE  OF  BwCallForwardingNoAnswerSPEntry
    MAX-ACCESS  not-accessible
    STATUS    current
                DESCRIPTION
                        "This table contains the counters for Call Forwarding No Answer service measurements for service providers"
                ::=  { callForwardingNoAnswer  2 }

  bwCFNADestinationChanged  OBJECT-TYPE
    SYNTAX      Counter32
    MAX-ACCESS    read-write
    STATUS      current
                DESCRIPTION
                                "Incremented whenever a user changes the CFNA destination via FAC"
                ::=  {  callForwardingNoAnswer  3  }

  bwCFNANumPhoneActivations OBJECT-TYPE
    SYNTAX      Counter32
    MAX-ACCESS    read-write
    STATUS      current
                DESCRIPTION
                                "Total number of times CFNA has been activated via FAC"
                ::=  {  callForwardingNoAnswer  4  }

  bwCFNANumPhoneDeactivations OBJECT-TYPE
    SYNTAX      Counter32
    MAX-ACCESS    read-write
    STATUS      current
                DESCRIPTION
                                "Total number of times CFNA has been deactivated via FAC"
                ::=  {  callForwardingNoAnswer  5  }

  bwCallForwardingNoAnswerGroupTable  OBJECT-TYPE
    SYNTAX    SEQUENCE  OF  BwCallForwardingNoAnswerGroupEntry
    MAX-ACCESS  not-accessible
    STATUS    current
                DESCRIPTION
                        "This table contains the counters for Call Forwarding No Answer service measurements for groups"
                ::=  { callForwardingNoAnswer  6 }

-- Service :: Call Forward No Answer :: SP TABLE ...........................................

  bwCallForwardingNoAnswerSPEntry OBJECT-TYPE
    SYNTAX    BwCallForwardingNoAnswerSPEntry
    MAX-ACCESS  not-accessible
    STATUS    current
                DESCRIPTION
                        "This row contains the counters for Call Forwarding No Answer service measurements for a service provider"
    INDEX   {  bwCallForwardingNoAnswerSPIndex  }
                ::=  { bwCallForwardingNoAnswerSPTable 1 }

        BwCallForwardingNoAnswerSPEntry  ::=  SEQUENCE {
                bwCallForwardingNoAnswerSPIndex  Integer32,
                bwCallForwardingNoAnswerSPID  DisplayString,
                bwCFNASPNumForwarded  Counter32,
    bwCFNASPDestinationChanged  Counter32,
                bwCFNASPNumPhoneActivations  Counter32,
                bwCFNASPNumPhoneDeactivations  Counter32
                }


  bwCallForwardingNoAnswerSPIndex OBJECT-TYPE
    SYNTAX      Integer32  ( -2147483648 .. 2147483647  )
    MAX-ACCESS    read-only
    STATUS      current
                DESCRIPTION
                                "This integer represents the a service provider index in the system"
                ::=  {  bwCallForwardingNoAnswerSPEntry  1  }


  bwCallForwardingNoAnswerSPID  OBJECT-TYPE
    SYNTAX      DisplayString
    MAX-ACCESS    read-only
    STATUS      current
                DESCRIPTION
                                "This string represents a service provider ID"
                ::=  {  bwCallForwardingNoAnswerSPEntry  2  }


  bwCFNASPNumForwarded    OBJECT-TYPE
    SYNTAX      Counter32
    MAX-ACCESS    read-write
    STATUS      current
                DESCRIPTION
                                "This counter reflects the number of times a call is forwarded by this service by a service provider"
                ::=  {  bwCallForwardingNoAnswerSPEntry  3  }

  bwCFNASPDestinationChanged  OBJECT-TYPE
    SYNTAX      Counter32
    MAX-ACCESS    read-write
    STATUS      current
                DESCRIPTION
                                "Number of times CFNA destination has been changed, by FAC only for a given service provider"
                ::=  {  bwCallForwardingNoAnswerSPEntry  4  }

  bwCFNASPNumPhoneActivations OBJECT-TYPE
    SYNTAX      Counter32
    MAX-ACCESS    read-write
    STATUS      current
                DESCRIPTION
                                "Number of times CFNA has been activated via FAC for users in a given service provider"
                ::=  {  bwCallForwardingNoAnswerSPEntry  5  }

  bwCFNASPNumPhoneDeactivations OBJECT-TYPE
    SYNTAX      Counter32
    MAX-ACCESS    read-write
    STATUS      current
                DESCRIPTION
                                "Number of times CFNA has been deactivated via FAC for users in a given service provider"
                ::=  {  bwCallForwardingNoAnswerSPEntry  6  }

-- Service :: Call Forward No Answer :: GROUP TABLE ...........................................

  bwCallForwardingNoAnswerGroupEntry  OBJECT-TYPE
    SYNTAX    BwCallForwardingNoAnswerGroupEntry
    MAX-ACCESS  not-accessible
    STATUS    current
                DESCRIPTION
                        "This row contains the counters for Call Forwarding No Answer service measurements for a group"
    INDEX   {  bwCallForwardingNoAnswerGroupIndex  }
                ::=  { bwCallForwardingNoAnswerGroupTable 1 }

        BwCallForwardingNoAnswerGroupEntry  ::=  SEQUENCE {
                bwCallForwardingNoAnswerGroupIndex  Integer32,
                bwCallForwardingNoAnswerGroupID  DisplayString,
                bwCFNAGroupNumForwarded  Counter32,
    bwCFNAGroupDestinationChanged Counter32,
                bwCFNAGroupNumPhoneActivations  Counter32,
                bwCFNAGroupNumPhoneDeactivations  Counter32
                }


  bwCallForwardingNoAnswerGroupIndex  OBJECT-TYPE
    SYNTAX      Integer32  ( -2147483648 .. 2147483647  )
    MAX-ACCESS    read-only
    STATUS      current
                DESCRIPTION
                                "This integer represents the a group index in the system"
                ::=  {  bwCallForwardingNoAnswerGroupEntry  1  }


  bwCallForwardingNoAnswerGroupID OBJECT-TYPE
    SYNTAX      DisplayString
    MAX-ACCESS    read-only
    STATUS      current
                DESCRIPTION
                                "This string represents a group ID"
                ::=  {  bwCallForwardingNoAnswerGroupEntry  2  }


  bwCFNAGroupNumForwarded   OBJECT-TYPE
    SYNTAX      Counter32
    MAX-ACCESS    read-write
    STATUS      current
                DESCRIPTION
                                "This counter reflects the number of times a call is forwarded by this service by a group"
                ::=  {  bwCallForwardingNoAnswerGroupEntry  3  }

  bwCFNAGroupDestinationChanged OBJECT-TYPE
    SYNTAX      Counter32
    MAX-ACCESS    read-write
    STATUS      current
                DESCRIPTION
                                "Number of times CFNA destination has been changed, by FAC only for a given group"
                ::=  {  bwCallForwardingNoAnswerGroupEntry  4  }

  bwCFNAGroupNumPhoneActivations  OBJECT-TYPE
    SYNTAX      Counter32
    MAX-ACCESS    read-write
    STATUS      current
                DESCRIPTION
                                "Number of times CFNA has been activated via FAC for users in a given group"
                ::=  {  bwCallForwardingNoAnswerGroupEntry  5  }

  bwCFNAGroupNumPhoneDeactivations  OBJECT-TYPE
    SYNTAX      Counter32
    MAX-ACCESS    read-write
    STATUS      current
                DESCRIPTION
                                "Number of times CFNA has been deactivated via FAC for users in a given group"
                ::=  {  bwCallForwardingNoAnswerGroupEntry  6  }

-- Service :: Call Notify  ...........................................

  bwCallNotifyNumNotifications  OBJECT-TYPE
    SYNTAX      Counter32
    MAX-ACCESS    read-write
    STATUS      current
                DESCRIPTION
                                "This counter reflects the number of times a criteria evaluates successfully and the
                                service executes"
                ::=  {  callNotify  1  }

  bwCallNotifySPTable OBJECT-TYPE
    SYNTAX    SEQUENCE  OF  BwCallNotifySPEntry
    MAX-ACCESS  not-accessible
    STATUS    current
                DESCRIPTION
                        "This table contains the counters for Call Notify service measurements for service providers"
                ::=  { callNotify  2 }

  bwCallNotifyGroupTable  OBJECT-TYPE
    SYNTAX    SEQUENCE  OF  BwCallNotifyGroupEntry
    MAX-ACCESS  not-accessible
    STATUS    current
                DESCRIPTION
                        "This table contains the counters for Call Notify service measurements for groups"
                ::=  { callNotify  3 }

-- Service :: Call Notify :: SP TABLE ...........................................

  bwCallNotifySPEntry OBJECT-TYPE
    SYNTAX    BwCallNotifySPEntry
    MAX-ACCESS  not-accessible
    STATUS    current
                DESCRIPTION
                        "This row contains the counters for Call Notify service measurements for a service provider"
    INDEX   {  bwCallNotifySPIndex  }
                ::=  { bwCallNotifySPTable 1 }

        BwCallNotifySPEntry  ::=  SEQUENCE {
                bwCallNotifySPIndex  Unsigned32,
                bwCallNotifySPID  DisplayString,
                bwCallNotifySPNumNotifications  Counter32
                }


  bwCallNotifySPIndex OBJECT-TYPE
    SYNTAX      Unsigned32
    MAX-ACCESS    read-only
    STATUS      current
                DESCRIPTION
                                "This integer represents the a service provider index in the system"
                ::=  {  bwCallNotifySPEntry  1  }


  bwCallNotifySPID  OBJECT-TYPE
    SYNTAX      DisplayString
    MAX-ACCESS    read-only
    STATUS      current
                DESCRIPTION
                                "This string represents a service provider ID"
                ::=  {  bwCallNotifySPEntry  2  }


  bwCallNotifySPNumNotifications  OBJECT-TYPE
    SYNTAX      Counter32
    MAX-ACCESS    read-write
    STATUS      current
                DESCRIPTION
                                "This counter reflects the number of times a criteria evaluates successfully and the service executes by a service provider"
                ::=  {  bwCallNotifySPEntry  3  }

-- Service :: Call Notify :: GROUP TABLE ...........................................

  bwCallNotifyGroupEntry  OBJECT-TYPE
    SYNTAX    BwCallNotifyGroupEntry
    MAX-ACCESS  not-accessible
    STATUS    current
                DESCRIPTION
                        "This row contains the counters for Call Notify service measurements for a group"
    INDEX   {  bwCallNotifyGroupIndex  }
                ::=  { bwCallNotifyGroupTable 1 }

        BwCallNotifyGroupEntry  ::=  SEQUENCE {
                bwCallNotifyGroupIndex  Unsigned32,
                bwCallNotifyGroupID  DisplayString,
                bwCallNotifyGroupNumNotifications  Counter32
                }


  bwCallNotifyGroupIndex  OBJECT-TYPE
    SYNTAX      Unsigned32
    MAX-ACCESS    read-only
    STATUS      current
                DESCRIPTION
                                "This integer represents the a group index in the system"
                ::=  {  bwCallNotifyGroupEntry  1  }


  bwCallNotifyGroupID OBJECT-TYPE
    SYNTAX      DisplayString
    MAX-ACCESS    read-only
    STATUS      current
                DESCRIPTION
                                "This string represents a group ID"
                ::=  {  bwCallNotifyGroupEntry  2  }


  bwCallNotifyGroupNumNotifications OBJECT-TYPE
    SYNTAX      Counter32
    MAX-ACCESS    read-write
    STATUS      current
                DESCRIPTION
                                "This counter reflects the number of times a criteria evaluates successfully and the service executes by a group"
                ::=  {  bwCallNotifyGroupEntry  3  }

-- Service :: Call Park  ...........................................

  bwCallParkNumAttempts OBJECT-TYPE
    SYNTAX      Counter32
    MAX-ACCESS    read-write
    STATUS      current
                DESCRIPTION
                                "This counter reflects the number of times a user attempts to park a call"
                ::=  {  callPark  1  }

  bwCallParkNumFailures OBJECT-TYPE
    SYNTAX      Counter32
    MAX-ACCESS    read-write
    STATUS      current
                DESCRIPTION
                                "This counter reflects the number of failed attempts to park a call"
                ::=  {  callPark  2  }

  bwCallParkNumRetrieveAttempts OBJECT-TYPE
    SYNTAX      Counter32
    MAX-ACCESS    read-write
    STATUS      current
                DESCRIPTION
                                "This counter reflects the number of times a user attempts to retrieve a parked call"
                ::=  {  callPark  3  }

  bwCallParkNumRetrieveFailures OBJECT-TYPE
    SYNTAX      Counter32
    MAX-ACCESS    read-write
    STATUS      current
                DESCRIPTION
                                "This counter reflects the number of times an attempt to retrieve a parked call fails"
                ::=  {  callPark  4  }

  bwCallParkSPTable OBJECT-TYPE
    SYNTAX    SEQUENCE  OF  BwCallParkSPEntry
    MAX-ACCESS  not-accessible
    STATUS    current
                DESCRIPTION
                        "This table contains the counters for Call Park service measurements for service providers"
                ::=  { callPark  5 }

  bwCallParkGroupTable  OBJECT-TYPE
    SYNTAX    SEQUENCE  OF  BwCallParkGroupEntry
    MAX-ACCESS  not-accessible
    STATUS    current
                DESCRIPTION
                        "This table contains the counters for Call Park service measurements for groups"
                ::=  { callPark  6 }

-- Service :: Call Park :: SP TABLE ...........................................

  bwCallParkSPEntry OBJECT-TYPE
    SYNTAX    BwCallParkSPEntry
    MAX-ACCESS  not-accessible
    STATUS    current
                DESCRIPTION
                        "This row contains the counters for Call Park service measurements for a service provider"
    INDEX   {  bwCallParkSPIndex  }
                ::=  { bwCallParkSPTable 1 }

        BwCallParkSPEntry  ::=  SEQUENCE {
                bwCallParkSPIndex  Unsigned32,
                bwCallParkSPID  DisplayString,
                bwCallParkSPNumAttempts  Counter32,
                bwCallParkSPNumFailures  Counter32,
                bwCallParkSPNumRetrieveAttempts  Counter32,
                bwCallParkSPNumRetrieveFailures  Counter32
                }


  bwCallParkSPIndex OBJECT-TYPE
    SYNTAX      Unsigned32
    MAX-ACCESS    read-only
    STATUS      current
                DESCRIPTION
                                "This integer represents the a service provider index in the system"
                ::=  {  bwCallParkSPEntry  1  }


  bwCallParkSPID  OBJECT-TYPE
    SYNTAX      DisplayString
    MAX-ACCESS    read-only
    STATUS      current
                DESCRIPTION
                                "This string represents a service provider ID"
                ::=  {  bwCallParkSPEntry  2  }


  bwCallParkSPNumAttempts OBJECT-TYPE
    SYNTAX      Counter32
    MAX-ACCESS    read-write
    STATUS      current
                DESCRIPTION
                                "This counter reflects the number of times a user attempts to park a call by a service provider"
                ::=  {  bwCallParkSPEntry  3  }


  bwCallParkSPNumFailures OBJECT-TYPE
    SYNTAX      Counter32
    MAX-ACCESS    read-write
    STATUS      current
                DESCRIPTION
                                "This counter reflects the number of failed attempts to park a call by a service provider"
                ::=  {  bwCallParkSPEntry  4  }


  bwCallParkSPNumRetrieveAttempts OBJECT-TYPE
    SYNTAX      Counter32
    MAX-ACCESS    read-write
    STATUS      current
                DESCRIPTION
                                "This counter reflects the number of times a user attempts to retrieve a parked call by a service provider"
                ::=  {  bwCallParkSPEntry  5  }


  bwCallParkSPNumRetrieveFailures OBJECT-TYPE
    SYNTAX      Counter32
    MAX-ACCESS    read-write
    STATUS      current
                DESCRIPTION
                                "This counter reflects the number of times an attempt to retrieve a parked call fails by a service provider"
                ::=  {  bwCallParkSPEntry  6  }

-- Service :: Call Park :: GROUP TABLE ...........................................

  bwCallParkGroupEntry  OBJECT-TYPE
    SYNTAX    BwCallParkGroupEntry
    MAX-ACCESS  not-accessible
    STATUS    current
                DESCRIPTION
                        "This row contains the counters for Call Park service measurements for a group"
    INDEX   {  bwCallParkGroupIndex  }
                ::=  { bwCallParkGroupTable 1 }

        BwCallParkGroupEntry  ::=  SEQUENCE {
                bwCallParkGroupIndex  Unsigned32,
                bwCallParkGroupID  DisplayString,
                bwCallParkGroupNumAttempts  Counter32,
                bwCallParkGroupNumFailures  Counter32,
                bwCallParkGroupNumRetrieveAttempts  Counter32,
                bwCallParkGroupNumRetrieveFailures  Counter32
                }


  bwCallParkGroupIndex  OBJECT-TYPE
    SYNTAX      Unsigned32
    MAX-ACCESS    read-only
    STATUS      current
                DESCRIPTION
                                "This integer represents the a group index in the system"
                ::=  {  bwCallParkGroupEntry  1  }


  bwCallParkGroupID OBJECT-TYPE
    SYNTAX      DisplayString
    MAX-ACCESS    read-only
    STATUS      current
                DESCRIPTION
                                "This string represents a group ID"
                ::=  {  bwCallParkGroupEntry  2  }


  bwCallParkGroupNumAttempts  OBJECT-TYPE
    SYNTAX      Counter32
    MAX-ACCESS    read-write
    STATUS      current
                DESCRIPTION
                                "This counter reflects the number of times a user attempts to park a call by a group"
                ::=  {  bwCallParkGroupEntry  3  }


  bwCallParkGroupNumFailures  OBJECT-TYPE
    SYNTAX      Counter32
    MAX-ACCESS    read-write
    STATUS      current
                DESCRIPTION
                                "This counter reflects the number of failed attempts to park a call by a group"
                ::=  {  bwCallParkGroupEntry  4  }


  bwCallParkGroupNumRetrieveAttempts  OBJECT-TYPE
    SYNTAX      Counter32
    MAX-ACCESS    read-write
    STATUS      current
                DESCRIPTION
                                "This counter reflects the number of times a user attempts to retrieve a parked call by a group"
                ::=  {  bwCallParkGroupEntry  5  }


  bwCallParkGroupNumRetrieveFailures  OBJECT-TYPE
    SYNTAX      Counter32
    MAX-ACCESS    read-write
    STATUS      current
                DESCRIPTION
                                "This counter reflects the number of times an attempt to retrieve a parked call fails by a group"
                ::=  {  bwCallParkGroupEntry  6  }

-- Service :: Call PickUp  ...........................................

  bwCallPickupNumAttempts OBJECT-TYPE
    SYNTAX      Counter32
    MAX-ACCESS    read-write
    STATUS      current
                DESCRIPTION
                                "This counter reflects the number of user attempts to pick up an incoming call"
                ::=  {  callPickup  1  }

  bwCallPickupNumFailures OBJECT-TYPE
    SYNTAX      Counter32
    MAX-ACCESS    read-write
    STATUS      current
                DESCRIPTION
                                "This counter reflects the number of failed attempts to pick up an incoming call"
                ::=  {  callPickup  2  }

  bwCallPickupSPTable OBJECT-TYPE
    SYNTAX    SEQUENCE  OF  BwCallPickupSPEntry
    MAX-ACCESS  not-accessible
    STATUS    current
                DESCRIPTION
                        "This table contains the counters for Call Pickup service measurements for service providers"
                ::=  { callPickup  3 }

  bwCallPickupGroupTable  OBJECT-TYPE
    SYNTAX    SEQUENCE  OF  BwCallPickupGroupEntry
    MAX-ACCESS  not-accessible
    STATUS    current
                DESCRIPTION
                        "This table contains the counters for Call Pickup service measurements for groups"
                ::=  { callPickup  4 }

-- Service :: Call PickUp :: SP TABLE ...........................................

  bwCallPickupSPEntry OBJECT-TYPE
    SYNTAX    BwCallPickupSPEntry
    MAX-ACCESS  not-accessible
    STATUS    current
                DESCRIPTION
                        "This row contains the counters for Call Pickup service measurements for a service provider"
    INDEX   {  bwCallPickupSPIndex  }
                ::=  { bwCallPickupSPTable 1 }

        BwCallPickupSPEntry  ::=  SEQUENCE {
                bwCallPickupSPIndex  Unsigned32,
                bwCallPickupSPID  DisplayString,
                bwCallPickupSPNumAttempts  Counter32,
                bwCallPickupSPNumFailures  Counter32
                }


  bwCallPickupSPIndex OBJECT-TYPE
    SYNTAX      Unsigned32
    MAX-ACCESS    read-only
    STATUS      current
                DESCRIPTION
                                "This integer represents the a service provider index in the system"
                ::=  {  bwCallPickupSPEntry  1  }


  bwCallPickupSPID  OBJECT-TYPE
    SYNTAX      DisplayString
    MAX-ACCESS    read-only
    STATUS      current
                DESCRIPTION
                                "This string represents a service provider ID"
                ::=  {  bwCallPickupSPEntry  2  }


  bwCallPickupSPNumAttempts OBJECT-TYPE
    SYNTAX      Counter32
    MAX-ACCESS    read-write
    STATUS      current
                DESCRIPTION
                                "This counter reflects the number of user attempts to pick up an incoming call by a service provider"
                ::=  {  bwCallPickupSPEntry  3  }


  bwCallPickupSPNumFailures OBJECT-TYPE
    SYNTAX      Counter32
    MAX-ACCESS    read-write
    STATUS      current
                DESCRIPTION
                                "This counter reflects the number of failed attempts to pick up an incoming call by a service provider"
                ::=  {  bwCallPickupSPEntry  4  }

-- Service :: Call PickUp :: GROUP TABLE ...........................................

  bwCallPickupGroupEntry  OBJECT-TYPE
    SYNTAX    BwCallPickupGroupEntry
    MAX-ACCESS  not-accessible
    STATUS    current
                DESCRIPTION
                        "This row contains the counters for Call Pickup service measurements for a group"
    INDEX   {  bwCallPickupGroupIndex  }
                ::=  { bwCallPickupGroupTable 1 }

        BwCallPickupGroupEntry  ::=  SEQUENCE {
                bwCallPickupGroupIndex  Unsigned32,
                bwCallPickupGroupID  DisplayString,
                bwCallPickupGroupNumAttempts  Counter32,
                bwCallPickupGroupNumFailures  Counter32
                }


  bwCallPickupGroupIndex  OBJECT-TYPE
    SYNTAX      Unsigned32
    MAX-ACCESS    read-only
    STATUS      current
                DESCRIPTION
                                "This integer represents the a Group index in the system"
                ::=  {  bwCallPickupGroupEntry  1  }


  bwCallPickupGroupID OBJECT-TYPE
    SYNTAX      DisplayString
    MAX-ACCESS    read-only
    STATUS      current
                DESCRIPTION
                                "This string represents a Group ID"
                ::=  {  bwCallPickupGroupEntry  2  }


  bwCallPickupGroupNumAttempts  OBJECT-TYPE
    SYNTAX      Counter32
    MAX-ACCESS    read-write
    STATUS      current
                DESCRIPTION
                                "This counter reflects the number of user attempts to pick up an incoming call by a Group"
                ::=  {  bwCallPickupGroupEntry  3  }


  bwCallPickupGroupNumFailures  OBJECT-TYPE
    SYNTAX      Counter32
    MAX-ACCESS    read-write
    STATUS      current
                DESCRIPTION
                                "This counter reflects the number of failed attempts to pick up an incoming call by a Group"
                ::=  {  bwCallPickupGroupEntry  4  }

-- Service :: Call Return  ...........................................

  bwCallReturnNumReturns  OBJECT-TYPE
    SYNTAX      Counter32
    MAX-ACCESS    read-write
    STATUS      current
                DESCRIPTION
                                "This counter reflects the number of times this service is executed"
                ::=  {  callReturn  1  }

  bwCallReturnSPTable OBJECT-TYPE
    SYNTAX    SEQUENCE  OF  BwCallReturnSPEntry
    MAX-ACCESS  not-accessible
    STATUS    current
                DESCRIPTION
                        "This table contains the counters for Call Return service measurements for service providers"
                ::=  { callReturn  2 }

  bwCallReturnGroupTable  OBJECT-TYPE
    SYNTAX    SEQUENCE  OF  BwCallReturnGroupEntry
    MAX-ACCESS  not-accessible
    STATUS    current
                DESCRIPTION
                        "This table contains the counters for Call Return service measurements for groups"
                ::=  { callReturn  3 }

-- Service :: Call Return  :: SP TABLE ...........................................

  bwCallReturnSPEntry OBJECT-TYPE
    SYNTAX    BwCallReturnSPEntry
    MAX-ACCESS  not-accessible
    STATUS    current
                DESCRIPTION
                        "This row contains the counters for Call Return service measurements for a service provider"
    INDEX   {  bwCallReturnSPIndex  }
                ::=  { bwCallReturnSPTable 1 }

        BwCallReturnSPEntry  ::=  SEQUENCE {
                bwCallReturnSPIndex  Unsigned32,
                bwCallReturnSPID  DisplayString,
                bwCallReturnSPNumReturns  Counter32
                }


  bwCallReturnSPIndex OBJECT-TYPE
    SYNTAX      Unsigned32
    MAX-ACCESS    read-only
    STATUS      current
                DESCRIPTION
                                "This integer represents the a service provider index in the system"
                ::=  {  bwCallReturnSPEntry  1  }


  bwCallReturnSPID  OBJECT-TYPE
    SYNTAX      DisplayString
    MAX-ACCESS    read-only
    STATUS      current
                DESCRIPTION
                                "This string represents a service provider ID"
                ::=  {  bwCallReturnSPEntry  2  }


  bwCallReturnSPNumReturns  OBJECT-TYPE
    SYNTAX      Counter32
    MAX-ACCESS    read-write
    STATUS      current
                DESCRIPTION
                                "This counter reflects the number of times this service is executed by a service provider"
                ::=  {  bwCallReturnSPEntry  3  }

-- Service :: Call Return  :: GROUP TABLE ...........................................

  bwCallReturnGroupEntry  OBJECT-TYPE
    SYNTAX    BwCallReturnGroupEntry
    MAX-ACCESS  not-accessible
    STATUS    current
                DESCRIPTION
                        "This row contains the counters for Call Return service measurements for a group"
    INDEX   {  bwCallReturnGroupIndex  }
                ::=  { bwCallReturnGroupTable 1 }

        BwCallReturnGroupEntry  ::=  SEQUENCE {
                bwCallReturnGroupIndex  Unsigned32,
                bwCallReturnGroupID  DisplayString,
                bwCallReturnGroupNumReturns  Counter32
                }


  bwCallReturnGroupIndex  OBJECT-TYPE
    SYNTAX      Unsigned32
    MAX-ACCESS    read-only
    STATUS      current
                DESCRIPTION
                                "This integer represents the a group index in the system"
                ::=  {  bwCallReturnGroupEntry  1  }


  bwCallReturnGroupID OBJECT-TYPE
    SYNTAX      DisplayString
    MAX-ACCESS    read-only
    STATUS      current
                DESCRIPTION
                                "This string represents a group ID"
                ::=  {  bwCallReturnGroupEntry  2  }


  bwCallReturnGroupNumReturns OBJECT-TYPE
    SYNTAX      Counter32
    MAX-ACCESS    read-write
    STATUS      current
                DESCRIPTION
                                "This counter reflects the number of times this service is executed by a group"
                ::=  {  bwCallReturnGroupEntry  3  }

-- Service :: CommPilot  ...........................................

  bwCommPilotCallMgrNumDial OBJECT-TYPE
    SYNTAX      Counter32
    MAX-ACCESS    read-write
    STATUS      current
                DESCRIPTION
                                "This counter reflects the number of dial requests from a CommPilot Call Mgr that
                                results in an outgoing call"
                ::=  {  commPilotCallManager  1  }

  bwCommPilotCallMgrNumAnswer OBJECT-TYPE
    SYNTAX      Counter32
    MAX-ACCESS    read-write
    STATUS      current
                DESCRIPTION
                                "This counter reflects the number of times an incoming call being answered from the
                                CommPilot Call Mgr results in that call being answered"
                ::=  {  commPilotCallManager  2  }

  bwCommPilotCallMgrNumRelease  OBJECT-TYPE
    SYNTAX      Counter32
    MAX-ACCESS    read-write
    STATUS      current
                DESCRIPTION
                                "This counter reflects the number of times a Release request from the CommPilot Call
                                Mgr results in the call being released"
                ::=  {  commPilotCallManager  3  }

  bwCommPilotCallMgrNumHold OBJECT-TYPE
    SYNTAX      Counter32
    MAX-ACCESS    read-write
    STATUS      current
                DESCRIPTION
                                "This counter reflects the number of times a Hold request from the CommPilot Call Mgr
                                results in the call being held"
                ::=  {  commPilotCallManager  4  }

  bwCommPilotCallMgrNumTransfer OBJECT-TYPE
    SYNTAX      Counter32
    MAX-ACCESS    read-write
    STATUS      current
                DESCRIPTION
                                "This counter reflects the number of times a Transfer request from the CommPilot Call
                                Mgr results in the call being transferred"
                ::=  {  commPilotCallManager  5  }

  bwCommPilotCallMgrNumConference OBJECT-TYPE
    SYNTAX      Counter32
    MAX-ACCESS    read-write
    STATUS      current
                DESCRIPTION
                                "This counter reflects the number of times a Conference request from the CommPilot
                                Call Mgr results in two calls being conferenced"
                ::=  {  commPilotCallManager  6  }

  bwCommPilotCallMgrNumTransferVM OBJECT-TYPE
    SYNTAX      Counter32
    MAX-ACCESS    read-write
    STATUS      current
                DESCRIPTION
                                "This counter reflects the number of times a user attempts to send a call to voicemail"
                ::=  {  commPilotCallManager  7  }

  bwCommPilotCallManagerSPTable OBJECT-TYPE
    SYNTAX    SEQUENCE  OF  BwCommPilotCallManagerSPEntry
    MAX-ACCESS  not-accessible
    STATUS    current
                DESCRIPTION
                        "This table contains the counters for CommPilot Call Manager service measurements for service providers"
                ::=  { commPilotCallManager  8 }

  bwCommPilotCallMgrNumConferenceAnswer OBJECT-TYPE
    SYNTAX    Counter32
    MAX-ACCESS  read-write
    STATUS    current
                DESCRIPTION
                        "This counter reflects the number of times a held Conference has been answered/retrieved from the CommPilot Call Mgr"
                ::=  { commPilotCallManager  9 }

  bwCommPilotCallMgrNumConferenceHold OBJECT-TYPE
    SYNTAX    Counter32
    MAX-ACCESS  read-write
    STATUS    current
                DESCRIPTION
                        "This counter reflects the number of times a Conference has been held from the CommPilot Call Mgr"
                ::=  { commPilotCallManager  10 }

  bwCommPilotCallMgrNumConferenceRelease  OBJECT-TYPE
    SYNTAX    Counter32
    MAX-ACCESS  read-write
    STATUS    current
                DESCRIPTION
                        "This counter reflects the number of times a Conference has been released from the CommPilot Call Mgr"
                ::=  { commPilotCallManager  11 }

  bwCommPilotCallManagerGroupTable  OBJECT-TYPE
    SYNTAX    SEQUENCE  OF  BwCommPilotCallManagerGroupEntry
    MAX-ACCESS  not-accessible
    STATUS    current
                DESCRIPTION
                        "This table contains the counters for CommPilot Call Manager service measurements for service providers"
                ::=  { commPilotCallManager  12 }

  bwCommPilotCallMgrNumTransferCC OBJECT-TYPE
    SYNTAX    Counter32
    MAX-ACCESS  read-write
    STATUS    current
                DESCRIPTION
                        "This counter reflects the number of CAP callActions with actionType of xferCC which are received by the system"
                ::=  { commPilotCallManager  13 }

        bwCommPilotCallMgrNumConferenceAdd      OBJECT-TYPE
    SYNTAX    Counter32
    MAX-ACCESS  read-write
    STATUS    current
                DESCRIPTION
                        "This counter reflects the number of CAP callActions with actionType of ConfAdd which are received by the system"
                ::=  { commPilotCallManager  14 }

    bwCommPilotCallMgrNumCallPark OBJECT-TYPE
      SYNTAX  Counter32
      MAX-ACCESS read-write
      STATUS current
      DESCRIPTION
        "Number of CallPark call actions that have been received."
      ::= { commPilotCallManager 15 }

    bwCommPilotCallMgrNumGroupCallPark OBJECT-TYPE
      SYNTAX  Counter32
      MAX-ACCESS read-write
      STATUS current
      DESCRIPTION
        "Number of GroupCallPark call actions that have been received."
      ::= { commPilotCallManager 16 }

    bwCommPilotCallMgrNumCallParkRetrieve OBJECT-TYPE
      SYNTAX  Counter32
      MAX-ACCESS read-write
      STATUS current
      DESCRIPTION
        "Number of CallParkRetrieve call actions that have been received."
      ::= { commPilotCallManager 17 }

-- Service :: CommPilot :: SP TABLE ...........................................

  bwCommPilotCallManagerSPEntry OBJECT-TYPE
    SYNTAX    BwCommPilotCallManagerSPEntry
    MAX-ACCESS  not-accessible
    STATUS    current
                DESCRIPTION
                        "This row contains the counters for CommPilot Call Manager service measurements for a service provider"
    INDEX   {  bwCommPilotCallManagerSPIndex  }
                ::=  { bwCommPilotCallManagerSPTable 1 }

        BwCommPilotCallManagerSPEntry  ::=  SEQUENCE {
                bwCommPilotCallManagerSPIndex  Unsigned32,
                bwCommPilotCallManagerSPID  DisplayString,
                bwCommPilotCallMgrSPNumDial  Counter32,
                bwCommPilotCallMgrSPNumAnswer  Counter32,
                bwCommPilotCallMgrSPNumRelease  Counter32,
                bwCommPilotCallMgrSPNumHold  Counter32,
                bwCommPilotCallMgrSPNumTransfer  Counter32,
                bwCommPilotCallMgrSPNumConference  Counter32,
                bwCommPilotCallMgrSPNumTransferVM  Counter32,
                bwCommPilotCallMgrSPNumConferenceAnswer Counter32,
                bwCommPilotCallMgrSPNumConferenceHold   Counter32,
                bwCommPilotCallMgrSPNumConferenceRelease Counter32,
                bwCommPilotCallMgrSPNumTransferCC Counter32,
                bwCommPilotCallMgrSPNumConferenceAdd Counter32,
                bwCommPilotCallMgrSPNumCallPark Counter32,
                bwCommPilotCallMgrSPNumGroupCallPark Counter32,
                bwCommPilotCallMgrSPNumCallParkRetrieve Counter32
                }


  bwCommPilotCallManagerSPIndex OBJECT-TYPE
    SYNTAX      Unsigned32
    MAX-ACCESS    read-only
    STATUS      current
                DESCRIPTION
                                "This integer represents the a service provider index in the system"
                ::=  {  bwCommPilotCallManagerSPEntry  1  }


  bwCommPilotCallManagerSPID  OBJECT-TYPE
    SYNTAX      DisplayString
    MAX-ACCESS    read-only
    STATUS      current
                DESCRIPTION
                                "This string represents a service provider ID"
                ::=  {  bwCommPilotCallManagerSPEntry  2  }


  bwCommPilotCallMgrSPNumDial OBJECT-TYPE
    SYNTAX      Counter32
    MAX-ACCESS    read-write
    STATUS      current
                DESCRIPTION
                                "This counter reflects the number of dial requests from a CommPilot Call Mgr that results in an outgoing call by a service provider"
                ::=  {  bwCommPilotCallManagerSPEntry  3  }


  bwCommPilotCallMgrSPNumAnswer OBJECT-TYPE
    SYNTAX      Counter32
    MAX-ACCESS    read-write
    STATUS      current
                DESCRIPTION
                                "This counter reflects the number of times an incoming call being answered from the CommPilot Call Mgr results in that call being answered by a service provider"
                ::=  {  bwCommPilotCallManagerSPEntry  4  }


  bwCommPilotCallMgrSPNumRelease  OBJECT-TYPE
    SYNTAX      Counter32
    MAX-ACCESS    read-write
    STATUS      current
                DESCRIPTION
                                "This counter reflects the number of times a Release request from the CommPilot Call Mgr results in the call being released by a service provider"
                ::=  {  bwCommPilotCallManagerSPEntry  5  }


  bwCommPilotCallMgrSPNumHold OBJECT-TYPE
    SYNTAX      Counter32
    MAX-ACCESS    read-write
    STATUS      current
                DESCRIPTION
                                "This counter reflects the number of times a Hold request from the CommPilot Call Mgr results in the call being held by a service provider"
                ::=  {  bwCommPilotCallManagerSPEntry  6  }


  bwCommPilotCallMgrSPNumTransfer OBJECT-TYPE
    SYNTAX      Counter32
    MAX-ACCESS    read-write
    STATUS      current
                DESCRIPTION
                                "This counter reflects the number of times a Transfer request from the CommPilot Call Mgr results in the call being transferred by a service provider"
                ::=  {  bwCommPilotCallManagerSPEntry  7  }


  bwCommPilotCallMgrSPNumConference OBJECT-TYPE
    SYNTAX      Counter32
    MAX-ACCESS    read-write
    STATUS      current
                DESCRIPTION
                                "This counter reflects the number of times a Conference request from the CommPilot Call Mgr results in two calls being conferenced by a service provider"
                ::=  {  bwCommPilotCallManagerSPEntry  8  }


  bwCommPilotCallMgrSPNumTransferVM OBJECT-TYPE
    SYNTAX      Counter32
    MAX-ACCESS    read-write
    STATUS      current
                DESCRIPTION
                                "This counter reflects the number of times a user attempts to send a call to voicemail by a service provider"
                ::=  {  bwCommPilotCallManagerSPEntry  9  }

  bwCommPilotCallMgrSPNumConferenceAnswer OBJECT-TYPE
    SYNTAX      Counter32
    MAX-ACCESS    read-write
    STATUS      current
                DESCRIPTION
                                "This counter reflects the number of times a held conference has been answered/retrieved from the CommPilot Call Mgr by a service provider"
                ::=  {  bwCommPilotCallManagerSPEntry  10  }

  bwCommPilotCallMgrSPNumConferenceHold OBJECT-TYPE
    SYNTAX      Counter32
    MAX-ACCESS    read-write
    STATUS      current
                DESCRIPTION
                                "This counter reflects the number of times a Conference has been held from the CommPilot Call Mgr by a service provider by the service provider"
                ::=  {  bwCommPilotCallManagerSPEntry  11  }

  bwCommPilotCallMgrSPNumConferenceRelease  OBJECT-TYPE
    SYNTAX      Counter32
    MAX-ACCESS    read-write
    STATUS      current
                DESCRIPTION
                                "This counter reflects the number of times a Conference has been released from the CommPilot Call Mgr by a service provider by the service provider"
                ::=  {  bwCommPilotCallManagerSPEntry  12  }

  bwCommPilotCallMgrSPNumTransferCC OBJECT-TYPE
    SYNTAX      Counter32
    MAX-ACCESS    read-write
    STATUS      current
                DESCRIPTION
                                "This counter reflects the number of CAP callActions with actionType of xferCC which are received by the system per service provider"
                ::=  {  bwCommPilotCallManagerSPEntry  13  }

  bwCommPilotCallMgrSPNumConferenceAdd  OBJECT-TYPE
    SYNTAX      Counter32
    MAX-ACCESS    read-write
    STATUS      current
                DESCRIPTION
                                "This counter reflects the number of CAP callActions with actionType of ConfAdd which are received by the system per service provider"
                ::=  {  bwCommPilotCallManagerSPEntry  14  }

  bwCommPilotCallMgrSPNumCallPark  OBJECT-TYPE
    SYNTAX      Counter32
    MAX-ACCESS    read-write
    STATUS      current
                DESCRIPTION
                                "Number of CallPark call actions that have been received for a user under the service provider."
                ::=  {  bwCommPilotCallManagerSPEntry  15  }

  bwCommPilotCallMgrSPNumGroupCallPark  OBJECT-TYPE
    SYNTAX      Counter32
    MAX-ACCESS    read-write
    STATUS      current
                DESCRIPTION
                                "Number of GroupCallPark call actions that have been received for a user under the service provider."
                ::=  {  bwCommPilotCallManagerSPEntry  16  }

  bwCommPilotCallMgrSPNumCallParkRetrieve  OBJECT-TYPE
    SYNTAX      Counter32
    MAX-ACCESS    read-write
    STATUS      current
                DESCRIPTION
                                "Number of CallParkRetrieve call actions that have been received for a user under the service provider."
                ::=  {  bwCommPilotCallManagerSPEntry  17  }

-- Service :: CommPilot :: GROUP TABLE ...........................................

  bwCommPilotCallManagerGroupEntry  OBJECT-TYPE
    SYNTAX    BwCommPilotCallManagerGroupEntry
    MAX-ACCESS  not-accessible
    STATUS    current
                DESCRIPTION
                        "This row contains the counters for CommPilot Call Manager service measurements for a group"
    INDEX   {  bwCommPilotCallManagerGroupIndex  }
                ::=  { bwCommPilotCallManagerGroupTable 1 }

        BwCommPilotCallManagerGroupEntry  ::=  SEQUENCE {
                bwCommPilotCallManagerGroupIndex  Unsigned32,
                bwCommPilotCallManagerGroupID  DisplayString,
                bwCommPilotCallMgrGroupNumDial  Counter32,
                bwCommPilotCallMgrGroupNumAnswer  Counter32,
                bwCommPilotCallMgrGroupNumRelease  Counter32,
                bwCommPilotCallMgrGroupNumHold  Counter32,
                bwCommPilotCallMgrGroupNumTransfer  Counter32,
                bwCommPilotCallMgrGroupNumConference  Counter32,
                bwCommPilotCallMgrGroupNumTransferVM  Counter32,
                bwCommPilotCallMgrGroupNumConferenceAnswer Counter32,
                bwCommPilotCallMgrGroupNumConferenceHold   Counter32,
                bwCommPilotCallMgrGroupNumConferenceRelease Counter32,
                bwCommPilotCallMgrGroupNumTransferCC Counter32,
                bwCommPilotCallMgrGroupNumConferenceAdd Counter32,
                bwCommPilotCallMgrGroupNumCallPark Counter32,
                bwCommPilotCallMgrGroupNumGroupCallPark Counter32,
                bwCommPilotCallMgrGroupNumCallParkRetrieve Counter32
                }


  bwCommPilotCallManagerGroupIndex  OBJECT-TYPE
    SYNTAX      Unsigned32
    MAX-ACCESS    read-only
    STATUS      current
                DESCRIPTION
                                "This integer represents the a group index in the system"
                ::=  {  bwCommPilotCallManagerGroupEntry  1  }


  bwCommPilotCallManagerGroupID OBJECT-TYPE
    SYNTAX      DisplayString
    MAX-ACCESS    read-only
    STATUS      current
                DESCRIPTION
                                "This string represents a group ID"
                ::=  {  bwCommPilotCallManagerGroupEntry  2  }


  bwCommPilotCallMgrGroupNumDial  OBJECT-TYPE
    SYNTAX      Counter32
    MAX-ACCESS    read-write
    STATUS      current
                DESCRIPTION
                                "This counter reflects the number of dial requests from a CommPilot Call Mgr that results in an outgoing call by a group"
                ::=  {  bwCommPilotCallManagerGroupEntry  3  }


  bwCommPilotCallMgrGroupNumAnswer  OBJECT-TYPE
    SYNTAX      Counter32
    MAX-ACCESS    read-write
    STATUS      current
                DESCRIPTION
                                "This counter reflects the number of times an incoming call being answered from the CommPilot Call Mgr results in that call being answered by a group"
                ::=  {  bwCommPilotCallManagerGroupEntry  4  }


  bwCommPilotCallMgrGroupNumRelease OBJECT-TYPE
    SYNTAX      Counter32
    MAX-ACCESS    read-write
    STATUS      current
                DESCRIPTION
                                "This counter reflects the number of times a Release request from the CommPilot Call Mgr results in the call being released by a group"
                ::=  {  bwCommPilotCallManagerGroupEntry  5  }


  bwCommPilotCallMgrGroupNumHold  OBJECT-TYPE
    SYNTAX      Counter32
    MAX-ACCESS    read-write
    STATUS      current
                DESCRIPTION
                                "This counter reflects the number of times a Hold request from the CommPilot Call Mgr results in the call being held by a group"
                ::=  {  bwCommPilotCallManagerGroupEntry  6  }


  bwCommPilotCallMgrGroupNumTransfer  OBJECT-TYPE
    SYNTAX      Counter32
    MAX-ACCESS    read-write
    STATUS      current
                DESCRIPTION
                                "This counter reflects the number of times a Transfer request from the CommPilot Call Mgr results in the call being transferred by a group"
                ::=  {  bwCommPilotCallManagerGroupEntry  7  }


  bwCommPilotCallMgrGroupNumConference  OBJECT-TYPE
    SYNTAX      Counter32
    MAX-ACCESS    read-write
    STATUS      current
                DESCRIPTION
                                "This counter reflects the number of times a Conference request from the CommPilot Call Mgr results in two calls being conferenced by a group"
                ::=  {  bwCommPilotCallManagerGroupEntry  8  }


  bwCommPilotCallMgrGroupNumTransferVM  OBJECT-TYPE
    SYNTAX      Counter32
    MAX-ACCESS    read-write
    STATUS      current
                DESCRIPTION
                                "This counter reflects the number of times a user attempts to send a call to voicemail by a group"
                ::=  {  bwCommPilotCallManagerGroupEntry  9  }

  bwCommPilotCallMgrGroupNumConferenceAnswer  OBJECT-TYPE
    SYNTAX      Counter32
    MAX-ACCESS    read-write
    STATUS      current
                DESCRIPTION
                                "This counter reflects the number of times a held conference has been answered/retrieved from the CommPilot Call Mgr by a group"
                ::=  {  bwCommPilotCallManagerGroupEntry  10  }

  bwCommPilotCallMgrGroupNumConferenceHold  OBJECT-TYPE
    SYNTAX      Counter32
    MAX-ACCESS    read-write
    STATUS      current
                DESCRIPTION
                                "This counter reflects the number of times a Conference has been held from the CommPilot Call Mgr by a group"
                ::=  {  bwCommPilotCallManagerGroupEntry  11  }

  bwCommPilotCallMgrGroupNumConferenceRelease OBJECT-TYPE
    SYNTAX      Counter32
    MAX-ACCESS    read-write
    STATUS      current
                DESCRIPTION
                                "This counter reflects the number of times a Conference has been released from the CommPilot Call Mgr by a group"
                ::=  {  bwCommPilotCallManagerGroupEntry  12  }

  bwCommPilotCallMgrGroupNumTransferCC  OBJECT-TYPE
    SYNTAX      Counter32
    MAX-ACCESS    read-write
    STATUS      current
                DESCRIPTION
                                "This counter reflects the number of CAP callActions with actionType of xferCC which are received by the system per group"
                ::=  {  bwCommPilotCallManagerGroupEntry  13  }

  bwCommPilotCallMgrGroupNumConferenceAdd OBJECT-TYPE
    SYNTAX      Counter32
    MAX-ACCESS    read-write
    STATUS      current
                DESCRIPTION
                                "This counter reflects the number of CAP callActions with actionType of ConfAdd which are received by the system per group"
                ::=  {  bwCommPilotCallManagerGroupEntry  14  }

  bwCommPilotCallMgrGroupNumCallPark OBJECT-TYPE
    SYNTAX      Counter32
    MAX-ACCESS    read-write
    STATUS      current
                DESCRIPTION
                                "Number of CallPark call actions that have been received for a user in the group."
                ::=  {  bwCommPilotCallManagerGroupEntry  15  }

  bwCommPilotCallMgrGroupNumGroupCallPark OBJECT-TYPE
    SYNTAX      Counter32
    MAX-ACCESS    read-write
    STATUS      current
                DESCRIPTION
                                "Number of GroupCallPark call actions that have been received for a user in the group."
                ::=  {  bwCommPilotCallManagerGroupEntry  16  }

  bwCommPilotCallMgrGroupNumCallParkRetrieve OBJECT-TYPE
    SYNTAX      Counter32
    MAX-ACCESS    read-write
    STATUS      current
                DESCRIPTION
                                "Number of CallParkRetrieve call actions that have been received for a user in the group."
                ::=  {  bwCommPilotCallManagerGroupEntry  17  }

-- Service :: Do not disturb  ...........................................

  bwDoNotDisturbNumInvoked  OBJECT-TYPE
    SYNTAX      Counter32
    MAX-ACCESS    read-write
    STATUS      current
                DESCRIPTION
                                "This counter reflects the number of times this service is triggered"
                ::=  {  doNotDisturb  1  }

  bwDoNotDisturbSPTable OBJECT-TYPE
    SYNTAX    SEQUENCE  OF  BwDoNotDisturbSPEntry
    MAX-ACCESS  not-accessible
    STATUS    current
                DESCRIPTION
                        "This table contains the counters for Do Not Disturb service measurements for service providers"
                ::=  { doNotDisturb  2 }

  bwDndPhoneActivations OBJECT-TYPE
    SYNTAX    Counter32
    MAX-ACCESS  read-write
    STATUS    current
                DESCRIPTION
                        "Total number of times DND has been activated via FAC"
                ::=  { doNotDisturb  3 }

  bwDndPhoneDeactivations OBJECT-TYPE
    SYNTAX    Counter32
    MAX-ACCESS  read-write
    STATUS    current
                DESCRIPTION
                        "Total number of times DND has been deactivated via FAC"
                ::=  { doNotDisturb  4 }

  bwDoNotDisturbGroupTable  OBJECT-TYPE
    SYNTAX    SEQUENCE  OF  BwDoNotDisturbGroupEntry
    MAX-ACCESS  not-accessible
    STATUS    current
                DESCRIPTION
                        "This table contains the counters for Do Not Disturb service measurements for groups"
                ::=  { doNotDisturb  5 }

-- Service :: Do not disturb :: SP TABLE ...........................................

  bwDoNotDisturbSPEntry OBJECT-TYPE
    SYNTAX    BwDoNotDisturbSPEntry
    MAX-ACCESS  not-accessible
    STATUS    current
                DESCRIPTION
                        "This row contains the counters for Do Not Disturb service measurements for a service provider"
    INDEX   {  bwDoNotDisturbSPIndex  }
                ::=  { bwDoNotDisturbSPTable 1 }

        BwDoNotDisturbSPEntry  ::=  SEQUENCE {
                bwDoNotDisturbSPIndex  Unsigned32,
                bwDoNotDisturbSPID  DisplayString,
                bwDoNotDisturbSPNumInvoked  Counter32,
                bwDNDSPNumPhoneActivations  Counter32,
                bwDNDSPNumPhoneDeactivations  Counter32
                }


  bwDoNotDisturbSPIndex OBJECT-TYPE
    SYNTAX      Unsigned32
    MAX-ACCESS    read-only
    STATUS      current
                DESCRIPTION
                                "This integer represents the a service provider index in the system"
                ::=  {  bwDoNotDisturbSPEntry  1  }


  bwDoNotDisturbSPID  OBJECT-TYPE
    SYNTAX      DisplayString
    MAX-ACCESS    read-only
    STATUS      current
                DESCRIPTION
                                "This string represents a service provider ID"
                ::=  {  bwDoNotDisturbSPEntry  2  }


  bwDoNotDisturbSPNumInvoked  OBJECT-TYPE
    SYNTAX      Counter32
    MAX-ACCESS    read-write
    STATUS      current
                DESCRIPTION
                                "This counter reflects the number of times this service is triggered by a service provider"
                ::=  {  bwDoNotDisturbSPEntry  3  }

  bwDNDSPNumPhoneActivations  OBJECT-TYPE
    SYNTAX      Counter32
    MAX-ACCESS    read-write
    STATUS      current
                DESCRIPTION
                                "Number of times DND has been activated via FAC for users in a given service provider"
                ::=  {  bwDoNotDisturbSPEntry  4  }

  bwDNDSPNumPhoneDeactivations  OBJECT-TYPE
    SYNTAX      Counter32
    MAX-ACCESS    read-write
    STATUS      current
                DESCRIPTION
                                "Number of times DND has been deactivated via FAC for users in a given service provider"
                ::=  {  bwDoNotDisturbSPEntry  5  }

-- Service :: Do not disturb :: GROUP TABLE ...........................................

  bwDoNotDisturbGroupEntry  OBJECT-TYPE
    SYNTAX    BwDoNotDisturbGroupEntry
    MAX-ACCESS  not-accessible
    STATUS    current
                DESCRIPTION
                        "This row contains the counters for Do Not Disturb service measurements for a group"
    INDEX   {  bwDoNotDisturbGroupIndex  }
                ::=  { bwDoNotDisturbGroupTable 1 }

        BwDoNotDisturbGroupEntry  ::=  SEQUENCE {
                bwDoNotDisturbGroupIndex  Unsigned32,
                bwDoNotDisturbGroupID  DisplayString,
                bwDoNotDisturbGroupNumInvoked  Counter32,
                bwDNDGroupNumPhoneActivations  Counter32,
                bwDNDGroupNumPhoneDeactivations  Counter32
                }


  bwDoNotDisturbGroupIndex  OBJECT-TYPE
    SYNTAX      Unsigned32
    MAX-ACCESS    read-only
    STATUS      current
                DESCRIPTION
                                "This integer represents the a group index in the system"
                ::=  {  bwDoNotDisturbGroupEntry  1  }


  bwDoNotDisturbGroupID OBJECT-TYPE
    SYNTAX      DisplayString
    MAX-ACCESS    read-only
    STATUS      current
                DESCRIPTION
                                "This string represents a group ID"
                ::=  {  bwDoNotDisturbGroupEntry  2  }


  bwDoNotDisturbGroupNumInvoked OBJECT-TYPE
    SYNTAX      Counter32
    MAX-ACCESS    read-write
    STATUS      current
                DESCRIPTION
                                "This counter reflects the number of times this service is triggered by a group"
                ::=  {  bwDoNotDisturbGroupEntry  3  }

  bwDNDGroupNumPhoneActivations OBJECT-TYPE
    SYNTAX      Counter32
    MAX-ACCESS    read-write
    STATUS      current
                DESCRIPTION
                                "Number of times DND has been activated via FAC for users in a given group"
                ::=  {  bwDoNotDisturbGroupEntry  4  }

  bwDNDGroupNumPhoneDeactivations OBJECT-TYPE
    SYNTAX      Counter32
    MAX-ACCESS    read-write
    STATUS      current
                DESCRIPTION
                                "Number of times DND has been deactivated via FAC for users in a given group"
                ::=  {  bwDoNotDisturbGroupEntry  5  }

-- Service :: Expensive Call Notification  ...........................................

  bwECNWarningAnnouncementAttempts OBJECT-TYPE
    SYNTAX      Counter32
    MAX-ACCESS    read-write
    STATUS      current
                DESCRIPTION
                                "This is the number of times the Expensive Call Notification service attempted to play a warning announcement for a call identified as expensive."
                ::=  {  expensiveCallNotification  1  }

  bwECNExpensiveCallReleased  OBJECT-TYPE
    SYNTAX      Counter32
    MAX-ACCESS    read-write
    STATUS      current
                DESCRIPTION
                                "This is the number of times a user released an expensive call (identified as such by the Expensive Call Notification service) before it was answered."
                ::=  {  expensiveCallNotification  2  }


-- Service :: Flash Call Xfer  ...........................................

  bwFlashCallTransferNumTransfers OBJECT-TYPE
    SYNTAX      Counter32
    MAX-ACCESS    read-write
    STATUS      current
                DESCRIPTION
                                "This counter reflects the number of times the flash code and destination number
                                are used to effect a transfer"
                ::=  {  flashCallTransfer  1  }

  bwFlashCallTransferSPTable  OBJECT-TYPE
    SYNTAX    SEQUENCE  OF  BwFlashCallTransferSPEntry
    MAX-ACCESS  not-accessible
    STATUS    current
                DESCRIPTION
                        "This table contains the counters for Flash Call Transfer service measurements for service providers"
                ::=  { flashCallTransfer  2 }

  bwFlashCallTransferGroupTable OBJECT-TYPE
    SYNTAX    SEQUENCE  OF  BwFlashCallTransferGroupEntry
    MAX-ACCESS  not-accessible
    STATUS    current
                DESCRIPTION
                        "This table contains the counters for Flash Call Transfer service measurements for groups"
                ::=  { flashCallTransfer  3 }

-- Service :: Flash Call Xfer :: SP TABLE ...........................................

  bwFlashCallTransferSPEntry  OBJECT-TYPE
    SYNTAX    BwFlashCallTransferSPEntry
    MAX-ACCESS  not-accessible
    STATUS    current
                DESCRIPTION
                        "This row contains the counters for Flash Call Transfer service measurements for a service provider"
    INDEX   {  bwFlashCallTransferSPIndex  }
                ::=  { bwFlashCallTransferSPTable 1 }

        BwFlashCallTransferSPEntry  ::=  SEQUENCE {
                bwFlashCallTransferSPIndex  Unsigned32,
                bwFlashCallTransferSPID  DisplayString,
                bwFlashCallTransferSPNumTransfers  Counter32
                }


  bwFlashCallTransferSPIndex  OBJECT-TYPE
    SYNTAX      Unsigned32
    MAX-ACCESS    read-only
    STATUS      current
                DESCRIPTION
                                "This integer represents the a service provider index in the system"
                ::=  {  bwFlashCallTransferSPEntry  1  }


  bwFlashCallTransferSPID OBJECT-TYPE
    SYNTAX      DisplayString
    MAX-ACCESS    read-only
    STATUS      current
                DESCRIPTION
                                "This string represents a service provider ID"
                ::=  {  bwFlashCallTransferSPEntry  2  }


  bwFlashCallTransferSPNumTransfers OBJECT-TYPE
    SYNTAX      Counter32
    MAX-ACCESS    read-write
    STATUS      current
                DESCRIPTION
                                "This counter reflects the number of times the flash code and destination number are used to effect a transfer by a service provider"
                ::=  {  bwFlashCallTransferSPEntry  3  }

-- Service :: Flash Call Xfer :: GROUP TABLE ...........................................

  bwFlashCallTransferGroupEntry OBJECT-TYPE
    SYNTAX    BwFlashCallTransferGroupEntry
    MAX-ACCESS  not-accessible
    STATUS    current
                DESCRIPTION
                        "This row contains the counters for Flash Call Transfer service measurements for a group"
    INDEX   {  bwFlashCallTransferGroupIndex  }
                ::=  { bwFlashCallTransferGroupTable 1 }

        BwFlashCallTransferGroupEntry  ::=  SEQUENCE {
                bwFlashCallTransferGroupIndex  Unsigned32,
                bwFlashCallTransferGroupID  DisplayString,
                bwFlashCallTransferGroupNumTransfers  Counter32
                }


  bwFlashCallTransferGroupIndex OBJECT-TYPE
    SYNTAX      Unsigned32
    MAX-ACCESS    read-only
    STATUS      current
                DESCRIPTION
                                "This integer represents the a group index in the system"
                ::=  {  bwFlashCallTransferGroupEntry  1  }


  bwFlashCallTransferGroupID  OBJECT-TYPE
    SYNTAX      DisplayString
    MAX-ACCESS    read-only
    STATUS      current
                DESCRIPTION
                                "This string represents a group ID"
                ::=  {  bwFlashCallTransferGroupEntry  2  }


  bwFlashCallTransferGroupNumTransfers  OBJECT-TYPE
    SYNTAX      Counter32
    MAX-ACCESS    read-write
    STATUS      current
                DESCRIPTION
                                "This counter reflects the number of times the flash code and destination number are used to effect a transfer by a group"
                ::=  {  bwFlashCallTransferGroupEntry  3  }

-- Service :: Flash Call Waiting  ...........................................

  bwFlashCallWaitingNumAnswers  OBJECT-TYPE
    SYNTAX      Counter32
    MAX-ACCESS    read-write
    STATUS      current
                DESCRIPTION
                                "This counter reflects the number of times the flash code results in the waiting call
                                getting answered"
                ::=  {  flashCallWaiting  1  }

  bwFlashCallWaitingSPTable OBJECT-TYPE
    SYNTAX    SEQUENCE  OF  BwFlashCallWaitingSPEntry
    MAX-ACCESS  not-accessible
    STATUS    current
                DESCRIPTION
                        "This table contains the counters for Flash Call Waiting service measurements for service providers"
                ::=  { flashCallWaiting  2 }

  bwFlashCallWaitingGroupTable  OBJECT-TYPE
    SYNTAX    SEQUENCE  OF  BwFlashCallWaitingGroupEntry
    MAX-ACCESS  not-accessible
    STATUS    current
                DESCRIPTION
                        "This table contains the counters for Flash Call Waiting service measurements for groups"
                ::=  { flashCallWaiting  3 }

-- Service :: Flash Call Waiting :: SP TABLE ...........................................

  bwFlashCallWaitingSPEntry OBJECT-TYPE
    SYNTAX    BwFlashCallWaitingSPEntry
    MAX-ACCESS  not-accessible
    STATUS    current
                DESCRIPTION
                        "This row contains the counters for Flash Call Waiting service measurements for a service provider"
    INDEX   {  bwFlashCallWaitingSPIndex  }
                ::=  { bwFlashCallWaitingSPTable 1 }

        BwFlashCallWaitingSPEntry  ::=  SEQUENCE {
                bwFlashCallWaitingSPIndex  Unsigned32,
                bwFlashCallWaitingSPID  DisplayString,
                bwFlashCallWaitingSPNumAnswers  Counter32
                }


  bwFlashCallWaitingSPIndex OBJECT-TYPE
    SYNTAX      Unsigned32
    MAX-ACCESS    read-only
    STATUS      current
                DESCRIPTION
                                "This integer represents the a service provider index in the system"
                ::=  {  bwFlashCallWaitingSPEntry  1  }


  bwFlashCallWaitingSPID  OBJECT-TYPE
    SYNTAX      DisplayString
    MAX-ACCESS    read-only
    STATUS      current
                DESCRIPTION
                                "This string represents a service provider ID"
                ::=  {  bwFlashCallWaitingSPEntry  2  }


  bwFlashCallWaitingSPNumAnswers  OBJECT-TYPE
    SYNTAX      Counter32
    MAX-ACCESS    read-write
    STATUS      current
                DESCRIPTION
                                "This counter reflects the number of times the flash code results in the waiting call getting answered by a service provider"
                ::=  {  bwFlashCallWaitingSPEntry  3  }

-- Service :: Flash Call Waiting :: GROUP TABLE ...........................................

  bwFlashCallWaitingGroupEntry  OBJECT-TYPE
    SYNTAX    BwFlashCallWaitingGroupEntry
    MAX-ACCESS  not-accessible
    STATUS    current
                DESCRIPTION
                        "This row contains the counters for Flash Call Waiting service measurements for a group"
    INDEX   {  bwFlashCallWaitingGroupIndex  }
                ::=  { bwFlashCallWaitingGroupTable 1 }

        BwFlashCallWaitingGroupEntry  ::=  SEQUENCE {
                bwFlashCallWaitingGroupIndex  Unsigned32,
                bwFlashCallWaitingGroupID  DisplayString,
                bwFlashCallWaitingGroupNumAnswers  Counter32
                }


  bwFlashCallWaitingGroupIndex  OBJECT-TYPE
    SYNTAX      Unsigned32
    MAX-ACCESS    read-only
    STATUS      current
                DESCRIPTION
                                "This integer represents the a group index in the system"
                ::=  {  bwFlashCallWaitingGroupEntry  1  }


  bwFlashCallWaitingGroupID OBJECT-TYPE
    SYNTAX      DisplayString
    MAX-ACCESS    read-only
    STATUS      current
                DESCRIPTION
                                "This string represents a group ID"
                ::=  {  bwFlashCallWaitingGroupEntry  2  }


  bwFlashCallWaitingGroupNumAnswers OBJECT-TYPE
    SYNTAX      Counter32
    MAX-ACCESS    read-write
    STATUS      current
                DESCRIPTION
                                "This counter reflects the number of times the flash code results in the waiting call getting answered by a group"
                ::=  {  bwFlashCallWaitingGroupEntry  3  }

-- Service :: Flash Consultation  ...........................................

  bwFlashConsultationNumCalls OBJECT-TYPE
    SYNTAX      Counter32
    MAX-ACCESS    read-write
    STATUS      current
                DESCRIPTION
                                "This counter reflects the number of times a counsultation is attempted using the flash
                                code and destination number"
                ::=  {  flashConsultation  1  }

  bwFlashConsultationSPTable  OBJECT-TYPE
    SYNTAX    SEQUENCE  OF  BwFlashConsultationSPEntry
    MAX-ACCESS  not-accessible
    STATUS    current
                DESCRIPTION
                        "This table contains the counters for Flash Consultation service measurements for service providers"
                ::=  { flashConsultation  2 }

  bwFlashConsultationGroupTable OBJECT-TYPE
    SYNTAX    SEQUENCE  OF  BwFlashConsultationGroupEntry
    MAX-ACCESS  not-accessible
    STATUS    current
                DESCRIPTION
                        "This table contains the counters for Flash Consultation service measurements for groups"
                ::=  { flashConsultation  3 }

-- Service :: Flash Consultation :: SP TABLE ...........................................

  bwFlashConsultationSPEntry  OBJECT-TYPE
    SYNTAX    BwFlashConsultationSPEntry
    MAX-ACCESS  not-accessible
    STATUS    current
                DESCRIPTION
                        "This row contains the counters for Flash Consultation service measurements for a service provider"
    INDEX   {  bwFlashConsultationSPIndex  }
                ::=  { bwFlashConsultationSPTable 1 }

        BwFlashConsultationSPEntry  ::=  SEQUENCE {
                bwFlashConsultationSPIndex  Unsigned32,
                bwFlashConsultationSPID  DisplayString,
                bwFlashConsultationSPNumCalls  Counter32
                }


  bwFlashConsultationSPIndex  OBJECT-TYPE
    SYNTAX      Unsigned32
    MAX-ACCESS    read-only
    STATUS      current
                DESCRIPTION
                                "This integer represents the a service provider index in the system"
                ::=  {  bwFlashConsultationSPEntry  1  }


  bwFlashConsultationSPID OBJECT-TYPE
    SYNTAX      DisplayString
    MAX-ACCESS    read-only
    STATUS      current
                DESCRIPTION
                                "This string represents a service provider ID"
                ::=  {  bwFlashConsultationSPEntry  2  }


  bwFlashConsultationSPNumCalls OBJECT-TYPE
    SYNTAX      Counter32
    MAX-ACCESS    read-write
    STATUS      current
                DESCRIPTION
                                "This counter reflects the number of times a counsultation is attempted using the flash code and destination number by a service provider"
                ::=  {  bwFlashConsultationSPEntry  3  }

-- Service :: Flash Consultation :: GROUP TABLE ...........................................

  bwFlashConsultationGroupEntry OBJECT-TYPE
    SYNTAX    BwFlashConsultationGroupEntry
    MAX-ACCESS  not-accessible
    STATUS    current
                DESCRIPTION
                        "This row contains the counters for Flash Consultation service measurements for a group"
    INDEX   {  bwFlashConsultationGroupIndex  }
                ::=  { bwFlashConsultationGroupTable 1 }

        BwFlashConsultationGroupEntry  ::=  SEQUENCE {
                bwFlashConsultationGroupIndex  Unsigned32,
                bwFlashConsultationGroupID  DisplayString,
                bwFlashConsultationGroupNumCalls  Counter32
                }


  bwFlashConsultationGroupIndex OBJECT-TYPE
    SYNTAX      Unsigned32
    MAX-ACCESS    read-only
    STATUS      current
                DESCRIPTION
                                "This integer represents the a group index in the system"
                ::=  {  bwFlashConsultationGroupEntry  1  }


  bwFlashConsultationGroupID  OBJECT-TYPE
    SYNTAX      DisplayString
    MAX-ACCESS    read-only
    STATUS      current
                DESCRIPTION
                                "This string represents a group ID"
                ::=  {  bwFlashConsultationGroupEntry  2  }


  bwFlashConsultationGroupNumCalls  OBJECT-TYPE
    SYNTAX      Counter32
    MAX-ACCESS    read-write
    STATUS      current
                DESCRIPTION
                                "This counter reflects the number of times a counsultation is attempted using the flash code and destination number by a group"
                ::=  {  bwFlashConsultationGroupEntry  3  }

-- Service :: Flash 3WC  ...........................................

  bwFlashThreeWayCallNum3WC OBJECT-TYPE
    SYNTAX      Counter32
    MAX-ACCESS    read-write
    STATUS      current
                DESCRIPTION
                                "This counter reflects the number of times the flash results in two calls being joined
                                into a conference"
                ::=  {  flashThreeWayCall  1  }

  bwFlashThreeWayCallSPTable  OBJECT-TYPE
    SYNTAX    SEQUENCE  OF  BwFlashThreeWayCallSPEntry
    MAX-ACCESS  not-accessible
    STATUS    current
                DESCRIPTION
                        "This table contains the counters for Flash Three-Way Call service measurements for service providers"
                ::=  { flashThreeWayCall  2 }

  bwFlashThreeWayCallGroupTable OBJECT-TYPE
    SYNTAX    SEQUENCE  OF  BwFlashThreeWayCallGroupEntry
    MAX-ACCESS  not-accessible
    STATUS    current
                DESCRIPTION
                        "This table contains the counters for Flash Three-Way Call service measurements for groups"
                ::=  { flashThreeWayCall  3 }

-- Service :: Flash 3WC :: SP TABLE ...........................................

  bwFlashThreeWayCallSPEntry  OBJECT-TYPE
    SYNTAX    BwFlashThreeWayCallSPEntry
    MAX-ACCESS  not-accessible
    STATUS    current
                DESCRIPTION
                        "This row contains the counters for Flash Three-Way Call service measurements for a service provider"
    INDEX   {  bwFlashThreeWayCallSPIndex  }
                ::=  { bwFlashThreeWayCallSPTable 1 }

        BwFlashThreeWayCallSPEntry  ::=  SEQUENCE {
                bwFlashThreeWayCallSPIndex  Unsigned32,
                bwFlashThreeWayCallSPID  DisplayString,
                bwFlashThreeWayCallSPNum3WC  Counter32
                }


  bwFlashThreeWayCallSPIndex  OBJECT-TYPE
    SYNTAX      Unsigned32
    MAX-ACCESS    read-only
    STATUS      current
                DESCRIPTION
                                "This integer represents the a service provider index in the system"
                ::=  {  bwFlashThreeWayCallSPEntry  1  }


  bwFlashThreeWayCallSPID OBJECT-TYPE
    SYNTAX      DisplayString
    MAX-ACCESS    read-only
    STATUS      current
                DESCRIPTION
                                "This string represents a service provider ID"
                ::=  {  bwFlashThreeWayCallSPEntry  2  }


  bwFlashThreeWayCallSPNum3WC OBJECT-TYPE
    SYNTAX      Counter32
    MAX-ACCESS    read-write
    STATUS      current
                DESCRIPTION
                                "This counter reflects the number of times the flash results in two calls being joined into a conference by a service provider"
                ::=  {  bwFlashThreeWayCallSPEntry  3  }

-- Service :: Flash 3WC :: GROUP TABLE ...........................................

  bwFlashThreeWayCallGroupEntry OBJECT-TYPE
    SYNTAX    BwFlashThreeWayCallGroupEntry
    MAX-ACCESS  not-accessible
    STATUS    current
                DESCRIPTION
                        "This row contains the counters for Flash Three-Way Call service measurements for a group"
    INDEX   {  bwFlashThreeWayCallGroupIndex  }
                ::=  { bwFlashThreeWayCallGroupTable 1 }

        BwFlashThreeWayCallGroupEntry  ::=  SEQUENCE {
                bwFlashThreeWayCallGroupIndex  Unsigned32,
                bwFlashThreeWayCallGroupID  DisplayString,
                bwFlashThreeWayCallGroupNum3WC  Counter32
                }


  bwFlashThreeWayCallGroupIndex OBJECT-TYPE
    SYNTAX      Unsigned32
    MAX-ACCESS    read-only
    STATUS      current
                DESCRIPTION
                                "This integer represents the a group index in the system"
                ::=  {  bwFlashThreeWayCallGroupEntry  1  }


  bwFlashThreeWayCallGroupID  OBJECT-TYPE
    SYNTAX      DisplayString
    MAX-ACCESS    read-only
    STATUS      current
                DESCRIPTION
                                "This string represents a group ID"
                ::=  {  bwFlashThreeWayCallGroupEntry  2  }


  bwFlashThreeWayCallGroupNum3WC  OBJECT-TYPE
    SYNTAX      Counter32
    MAX-ACCESS    read-write
    STATUS      current
                DESCRIPTION
                                "This counter reflects the number of times the flash results in two calls being joined into a conference by a group"
                ::=  {  bwFlashThreeWayCallGroupEntry  3  }

-- Service :: Hunt Group  ...........................................

  bwHuntGroupNumAttempts  OBJECT-TYPE
    SYNTAX      Counter32
    MAX-ACCESS    read-write
    STATUS      current
                DESCRIPTION
                                "This counter reflects the number of times a Hunt Group virtual number receives an
                                incoming call attempt"
                ::=  {  huntGroups  1  }

  bwHuntGroupNumBusy  OBJECT-TYPE
    SYNTAX      Counter32
    MAX-ACCESS    read-write
    STATUS      current
                DESCRIPTION
                                "This counter reflects the number of times that all parties in a Hunt Group are busy"
                ::=  {  huntGroups  2  }

  bwHuntGroupsSPTable OBJECT-TYPE
    SYNTAX    SEQUENCE  OF  BwHuntGroupsSPEntry
    MAX-ACCESS  not-accessible
    STATUS    current
                DESCRIPTION
                        "This table contains the counters for Hunt Group service measurements for service providers"
                ::=  { huntGroups  3 }

  bwHuntGroupsGroupTable  OBJECT-TYPE
    SYNTAX    SEQUENCE  OF  BwHuntGroupsGroupEntry
    MAX-ACCESS  not-accessible
    STATUS    current
                DESCRIPTION
                        "This table contains the counters for Hunt Group service measurements for groups"
                ::=  { huntGroups  4 }

  bwHuntGroupsDNHIncomingCalls  OBJECT-TYPE
    SYNTAX      Counter32
    MAX-ACCESS    read-write
    STATUS      current
                DESCRIPTION
                                "This counter reflects the number of incoming calls to agents belonging to Directory Number Hunting groups"
                ::=  {  huntGroups  5  }

-- Service :: Hunt Group :: SP TABLE ...........................................

  bwHuntGroupsSPEntry OBJECT-TYPE
    SYNTAX    BwHuntGroupsSPEntry
    MAX-ACCESS  not-accessible
    STATUS    current
                DESCRIPTION
                        "This row contains the counters for Hunt Group service measurements for a service provider"
    INDEX   {  bwHuntGroupsSPIndex  }
                ::=  { bwHuntGroupsSPTable 1 }

        BwHuntGroupsSPEntry  ::=  SEQUENCE {
                bwHuntGroupsSPIndex  Unsigned32,
                bwHuntGroupsSPID  DisplayString,
                bwHuntGroupSPNumAttempts  Counter32,
                bwHuntGroupSPNumBusy  Counter32,
                bwHuntGroupsSPDNHIncomingCalls Counter32
                }


  bwHuntGroupsSPIndex OBJECT-TYPE
    SYNTAX      Unsigned32
    MAX-ACCESS    read-only
    STATUS      current
                DESCRIPTION
                                "This integer represents the a service provider index in the system"
                ::=  {  bwHuntGroupsSPEntry  1  }


  bwHuntGroupsSPID  OBJECT-TYPE
    SYNTAX      DisplayString
    MAX-ACCESS    read-only
    STATUS      current
                DESCRIPTION
                                "This string represents a service provider ID"
                ::=  {  bwHuntGroupsSPEntry  2  }


  bwHuntGroupSPNumAttempts  OBJECT-TYPE
    SYNTAX      Counter32
    MAX-ACCESS    read-write
    STATUS      current
                DESCRIPTION
                                "This counter reflects the number of times a Hunt Group virtual number receives an incoming call attempt by a service provider"
                ::=  {  bwHuntGroupsSPEntry  3  }

  bwHuntGroupSPNumBusy  OBJECT-TYPE
    SYNTAX      Counter32
    MAX-ACCESS    read-write
    STATUS      current
                DESCRIPTION
                                "This counter reflects the number of times that all parties in a Hunt Group are busy by a service provider"
                ::=  {  bwHuntGroupsSPEntry  4  }

  bwHuntGroupsSPDNHIncomingCalls  OBJECT-TYPE
    SYNTAX      Counter32
    MAX-ACCESS    read-write
    STATUS      current
                DESCRIPTION
                                "This counter reflects the number of incoming calls to agents belonging to Directory Number Hunting groups, per service provider"
                ::=  {  bwHuntGroupsSPEntry  5  }

-- Service :: Hunt Group :: GROUP TABLE ...........................................

  bwHuntGroupsGroupEntry  OBJECT-TYPE
    SYNTAX    BwHuntGroupsGroupEntry
    MAX-ACCESS  not-accessible
    STATUS    current
                DESCRIPTION
                        "This row contains the counters for Hunt Group service measurements for a group"
    INDEX   {  bwHuntGroupsGroupIndex  }
                ::=  { bwHuntGroupsGroupTable 1 }

        BwHuntGroupsGroupEntry  ::=  SEQUENCE {
                bwHuntGroupsGroupIndex  Unsigned32,
                bwHuntGroupsGroupID  DisplayString,
                bwHuntGroupsGroupNumAttempts  Counter32,
                bwHuntGroupsGroupNumBusy  Counter32,
                bwHuntGroupsGroupDNHIncomingCalls  Counter32
                }


  bwHuntGroupsGroupIndex  OBJECT-TYPE
    SYNTAX      Unsigned32
    MAX-ACCESS    read-only
    STATUS      current
                DESCRIPTION
                                "This integer represents the a Group index in the system"
                ::=  {  bwHuntGroupsGroupEntry  1  }


  bwHuntGroupsGroupID OBJECT-TYPE
    SYNTAX      DisplayString
    MAX-ACCESS    read-only
    STATUS      current
                DESCRIPTION
                                "This string represents a Group ID"
                ::=  {  bwHuntGroupsGroupEntry  2  }


  bwHuntGroupsGroupNumAttempts  OBJECT-TYPE
    SYNTAX      Counter32
    MAX-ACCESS    read-write
    STATUS      current
                DESCRIPTION
                                "This counter reflects the number of times a Hunt Group virtual number receives an incoming call attempt by a Group"
                ::=  {  bwHuntGroupsGroupEntry  3  }


  bwHuntGroupsGroupNumBusy  OBJECT-TYPE
    SYNTAX      Counter32
    MAX-ACCESS    read-write
    STATUS      current
                DESCRIPTION
                                "This counter reflects the number of times that all parties in a Hunt Group are busy by a Group"
                ::=  {  bwHuntGroupsGroupEntry  4  }

  bwHuntGroupsGroupDNHIncomingCalls OBJECT-TYPE
    SYNTAX      Counter32
    MAX-ACCESS    read-write
    STATUS      current
                DESCRIPTION
                                "This counter reflects the number of incoming calls to agents belonging to Directory Number Hunting groups, per group"
                ::=  {  bwHuntGroupsGroupEntry  5  }

-- Service :: Incoming Calling Plan  ...........................................

  bwICPNumInterGroupBlocks  OBJECT-TYPE
    SYNTAX      Counter32
    MAX-ACCESS    read-write
    STATUS      current
                DESCRIPTION
                                "This counter reflects the number of times this service denies a direct call from outside the group"
                ::=  {  incomingCallingPlan  1  }

  bwIncomingCallingPlanSPTable  OBJECT-TYPE
    SYNTAX    SEQUENCE  OF  BwIncomingCallingPlanSPEntry
    MAX-ACCESS  not-accessible
    STATUS    current
                DESCRIPTION
                        "This table contains the counters for Incoming Calling Plan service measurements for service providers"
                ::=  { incomingCallingPlan  2 }

  bwIncomingCallingPlanGroupTable OBJECT-TYPE
    SYNTAX    SEQUENCE  OF  BwIncomingCallingPlanGroupEntry
    MAX-ACCESS  not-accessible
    STATUS    current
                DESCRIPTION
                        "This table contains the counters for Incoming Calling Plan service measurements for groups"
                ::=  { incomingCallingPlan  3 }

  bwICPNumCollectCallBlocks OBJECT-TYPE
    SYNTAX      Counter32
    MAX-ACCESS    read-write
    STATUS      current
                DESCRIPTION
                                "This counter is incremented whenever the service denies a collect call"
                ::=  {  incomingCallingPlan  4  }

  bwICPNumIntraGroupBlocks  OBJECT-TYPE
    SYNTAX      Counter32
    MAX-ACCESS    read-write
    STATUS      current
                DESCRIPTION
                                "This counter is incremented whenever the service denies an intra-group call"
                ::=  {  incomingCallingPlan  5  }

  bwICPNumOutsideCallerBlocks OBJECT-TYPE
    SYNTAX      Counter32
    MAX-ACCESS    read-write
    STATUS      current
                DESCRIPTION
                                "This counter reflects the number of times this service denies a call forwarded/transferred by a group member where the other party is outside the group"
                ::=  {  incomingCallingPlan  6  }

-- Service :: Incoming Calling Plan :: SP TABLE ...........................................

  bwIncomingCallingPlanSPEntry  OBJECT-TYPE
    SYNTAX    BwIncomingCallingPlanSPEntry
    MAX-ACCESS  not-accessible
    STATUS    current
                DESCRIPTION
                        "This row contains the counters for Incoming Calling Plan service measurements for a service provider"
    INDEX   {  bwIncomingCallingPlanSPIndex  }
                ::=  { bwIncomingCallingPlanSPTable 1 }

        BwIncomingCallingPlanSPEntry  ::=  SEQUENCE {
                bwIncomingCallingPlanSPIndex  Unsigned32,
                bwIncomingCallingPlanSPID  DisplayString,
                bwICPSPNumInterGroupBlocks  Counter32,
                bwICPSPNumCollectCallBlocks  Counter32,
                bwICPSPNumIntraGroupBlocks  Counter32,
                bwICPSPNumOutsideCallerBlocks  Counter32
                }


  bwIncomingCallingPlanSPIndex  OBJECT-TYPE
    SYNTAX      Unsigned32
    MAX-ACCESS    read-only
    STATUS      current
                DESCRIPTION
                                "This integer represents the a service provider index in the system"
                ::=  {  bwIncomingCallingPlanSPEntry  1  }


  bwIncomingCallingPlanSPID OBJECT-TYPE
    SYNTAX      DisplayString
    MAX-ACCESS    read-only
    STATUS      current
                DESCRIPTION
                                "Column Description This string represents a service provider ID"
                ::=  {  bwIncomingCallingPlanSPEntry  2  }


  bwICPSPNumInterGroupBlocks  OBJECT-TYPE
    SYNTAX      Counter32
    MAX-ACCESS    read-write
    STATUS      current
                DESCRIPTION
                                "This counter reflects the number of times this service denies a direct call from outside the group for a service provider"
                ::=  {  bwIncomingCallingPlanSPEntry  3  }

  bwICPSPNumCollectCallBlocks OBJECT-TYPE
    SYNTAX      Counter32
    MAX-ACCESS    read-write
    STATUS      current
                DESCRIPTION
                                "This counter is incremented whenever the service denies a collect call for a service provider"
                ::=  {  bwIncomingCallingPlanSPEntry  4  }

  bwICPSPNumIntraGroupBlocks  OBJECT-TYPE
    SYNTAX      Counter32
    MAX-ACCESS    read-write
    STATUS      current
                DESCRIPTION
                                "This counter is incremented whenever the service denies an intra-group call for a service provider"
                ::=  {  bwIncomingCallingPlanSPEntry  5  }

  bwICPSPNumOutsideCallerBlocks OBJECT-TYPE
    SYNTAX      Counter32
    MAX-ACCESS    read-write
    STATUS      current
                DESCRIPTION
                                "This counter reflects the number of times this service denies a call forwarded/transferred by a group member where the other party is outside the group for a service provider"
                ::=  {  bwIncomingCallingPlanSPEntry  6  }

-- Service :: Incoming Calling Plan :: GROUP TABLE ...........................................

  bwIncomingCallingPlanGroupEntry OBJECT-TYPE
    SYNTAX    BwIncomingCallingPlanGroupEntry
    MAX-ACCESS  not-accessible
    STATUS    current
                DESCRIPTION
                        "This row contains the counters for Incoming Calling Plan service measurements for a group"
    INDEX   {  bwIncomingCallingPlanGroupIndex  }
                ::=  { bwIncomingCallingPlanGroupTable 1 }

        BwIncomingCallingPlanGroupEntry  ::=  SEQUENCE {
                bwIncomingCallingPlanGroupIndex  Unsigned32,
                bwIncomingCallingPlanGroupID  DisplayString,
                bwICPGroupNumInterGroupBlocks  Counter32,
                bwICPGroupNumCollectCallBlocks  Counter32,
                bwICPGroupNumIntraGroupBlocks  Counter32,
                bwICPGroupNumOutsideCallerBlocks  Counter32
                }


  bwIncomingCallingPlanGroupIndex OBJECT-TYPE
    SYNTAX      Unsigned32
    MAX-ACCESS    read-only
    STATUS      current
                DESCRIPTION
                                "This integer represents the a group index in the system"
                ::=  {  bwIncomingCallingPlanGroupEntry  1  }


  bwIncomingCallingPlanGroupID  OBJECT-TYPE
    SYNTAX      DisplayString
    MAX-ACCESS    read-only
    STATUS      current
                DESCRIPTION
                                "Column Description This string represents a group ID"
                ::=  {  bwIncomingCallingPlanGroupEntry  2  }


  bwICPGroupNumInterGroupBlocks OBJECT-TYPE
    SYNTAX      Counter32
    MAX-ACCESS    read-write
    STATUS      current
                DESCRIPTION
                                "This counter reflects the number of times this service denies a direct call from outside the group for a group"
                ::=  {  bwIncomingCallingPlanGroupEntry  3  }

  bwICPGroupNumCollectCallBlocks  OBJECT-TYPE
    SYNTAX      Counter32
    MAX-ACCESS    read-write
    STATUS      current
                DESCRIPTION
                                "This counter is incremented whenever the service denies a collect call for a group"
                ::=  {  bwIncomingCallingPlanGroupEntry  4  }

  bwICPGroupNumIntraGroupBlocks OBJECT-TYPE
    SYNTAX      Counter32
    MAX-ACCESS    read-write
    STATUS      current
                DESCRIPTION
                                "This counter is incremented whenever the service denies an intra-group call for a group"
                ::=  {  bwIncomingCallingPlanGroupEntry  5  }

  bwICPGroupNumOutsideCallerBlocks  OBJECT-TYPE
    SYNTAX      Counter32
    MAX-ACCESS    read-write
    STATUS      current
                DESCRIPTION
                                "This counter reflects the number of times this service denies a call forwarded/transferred by a group member where the other party is outside the group for a group"
                ::=  {  bwIncomingCallingPlanGroupEntry  6  }

-- Service :: IP Phones ...........................................

  bwIPPhoneNumForwards  OBJECT-TYPE
    SYNTAX      Counter32
    MAX-ACCESS    read-write
    STATUS      current
                DESCRIPTION
                                "This counter reflects the number of times this service redirects a call on a request from
                                an IP Phone"
                ::=  {  ipPhone  1  }

  bwIPPhoneSPTable  OBJECT-TYPE
    SYNTAX    SEQUENCE  OF  BwIPPhoneSPEntry
    MAX-ACCESS  not-accessible
    STATUS    current
                DESCRIPTION
                        "This table contains the counters for IP Phone service measurements for service providers"
                ::=  { ipPhone  2 }

  bwIPPhoneGroupTable OBJECT-TYPE
    SYNTAX    SEQUENCE  OF  BwIPPhoneGroupEntry
    MAX-ACCESS  not-accessible
    STATUS    current
                DESCRIPTION
                        "This table contains the counters for IP Phone service measurements for groups"
                ::=  { ipPhone  3 }

-- Service :: IP Phones :: SP TABLE ...........................................

  bwIPPhoneSPEntry  OBJECT-TYPE
    SYNTAX    BwIPPhoneSPEntry
    MAX-ACCESS  not-accessible
    STATUS    current
                DESCRIPTION
                        "This row contains the counters for IP Phone service measurements for a service provider"
    INDEX   {  bwIPPhoneSPIndex  }
                ::=  { bwIPPhoneSPTable 1 }

        BwIPPhoneSPEntry  ::=  SEQUENCE {
                bwIPPhoneSPIndex  Unsigned32,
                bwIPPhoneSPID  DisplayString,
                bwIPPhoneSPNumForwards  Counter32
                }


  bwIPPhoneSPIndex  OBJECT-TYPE
    SYNTAX      Unsigned32
    MAX-ACCESS    read-only
    STATUS      current
                DESCRIPTION
                                "This integer represents the a service provider index in the system"
                ::=  {  bwIPPhoneSPEntry  1  }


  bwIPPhoneSPID OBJECT-TYPE
    SYNTAX      DisplayString
    MAX-ACCESS    read-only
    STATUS      current
                DESCRIPTION
                                "This string represents a service provider ID"
                ::=  {  bwIPPhoneSPEntry  2  }


  bwIPPhoneSPNumForwards  OBJECT-TYPE
    SYNTAX      Counter32
    MAX-ACCESS    read-write
    STATUS      current
                DESCRIPTION
                                "This counter reflects the number of times this service redirects a call on a request from an IP Phone by a service provider"
                ::=  {  bwIPPhoneSPEntry  3  }

-- Service :: IP Phones :: GROUP TABLE ...........................................

  bwIPPhoneGroupEntry OBJECT-TYPE
    SYNTAX    BwIPPhoneGroupEntry
    MAX-ACCESS  not-accessible
    STATUS    current
                DESCRIPTION
                        "This row contains the counters for IP Phone service measurements for a group"
    INDEX   {  bwIPPhoneGroupIndex  }
                ::=  { bwIPPhoneGroupTable 1 }

        BwIPPhoneGroupEntry  ::=  SEQUENCE {
                bwIPPhoneGroupIndex  Unsigned32,
                bwIPPhoneGroupID  DisplayString,
                bwIPPhoneGroupNumForwards  Counter32
                }


  bwIPPhoneGroupIndex OBJECT-TYPE
    SYNTAX      Unsigned32
    MAX-ACCESS    read-only
    STATUS      current
                DESCRIPTION
                                "This integer represents the a group index in the system"
                ::=  {  bwIPPhoneGroupEntry  1  }


  bwIPPhoneGroupID  OBJECT-TYPE
    SYNTAX      DisplayString
    MAX-ACCESS    read-only
    STATUS      current
                DESCRIPTION
                                "This string represents a group ID"
                ::=  {  bwIPPhoneGroupEntry  2  }


  bwIPPhoneGroupNumForwards OBJECT-TYPE
    SYNTAX      Counter32
    MAX-ACCESS    read-write
    STATUS      current
                DESCRIPTION
                                "This counter reflects the number of times this service redirects a call on a request from an IP Phone by a group"
                ::=  {  bwIPPhoneGroupEntry  3  }

-- Service :: Last Number Redial  ...........................................

  bwLNRNumRedials OBJECT-TYPE
    SYNTAX      Counter32
    MAX-ACCESS    read-write
    STATUS      current
                DESCRIPTION
                                "This counter reflects the number of times the flash code results in this service
                                attempting to dial the last number called"
                ::=  {  lastNumberRedial  1  }

  bwLastNumberRedialSPTable OBJECT-TYPE
    SYNTAX    SEQUENCE  OF  BwLastNumberRedialSPEntry
    MAX-ACCESS  not-accessible
    STATUS    current
                DESCRIPTION
                        "This table contains the counters for Last Number Redial service measurements for service providers"
                ::=  { lastNumberRedial  2 }

  bwLastNumberRedialGroupTable  OBJECT-TYPE
    SYNTAX    SEQUENCE  OF  BwLastNumberRedialGroupEntry
    MAX-ACCESS  not-accessible
    STATUS    current
                DESCRIPTION
                        "This table contains the counters for Last Number Redial service measurements for groups"
                ::=  { lastNumberRedial  3 }

-- Service :: Last Number Redial :: SP TABLE ...........................................

  bwLastNumberRedialSPEntry OBJECT-TYPE
    SYNTAX    BwLastNumberRedialSPEntry
    MAX-ACCESS  not-accessible
    STATUS    current
                DESCRIPTION
                        "This row contains the counters for Last Number Redial service measurements for a service provider"
    INDEX   {  bwLastNumberRedialSPIndex  }
                ::=  { bwLastNumberRedialSPTable 1 }

        BwLastNumberRedialSPEntry  ::=  SEQUENCE {
                bwLastNumberRedialSPIndex  Unsigned32,
                bwLastNumberRedialSPID  DisplayString,
                bwLNRSPNumRedials  Counter32
                }


  bwLastNumberRedialSPIndex OBJECT-TYPE
    SYNTAX      Unsigned32
    MAX-ACCESS    read-only
    STATUS      current
                DESCRIPTION
                                "This integer represents the a service provider index in the system"
                ::=  {  bwLastNumberRedialSPEntry  1  }


  bwLastNumberRedialSPID  OBJECT-TYPE
    SYNTAX      DisplayString
    MAX-ACCESS    read-only
    STATUS      current
                DESCRIPTION
                                "This string represents a service provider ID"
                ::=  {  bwLastNumberRedialSPEntry  2  }


  bwLNRSPNumRedials OBJECT-TYPE
    SYNTAX      Counter32
    MAX-ACCESS    read-write
    STATUS      current
                DESCRIPTION
                                "This counter reflects the number of times the flash code results in this service attempting to dial the last number called by a service provider"
                ::=  {  bwLastNumberRedialSPEntry  3  }

-- Service :: Last Number Redial :: GROUP TABLE ...........................................

  bwLastNumberRedialGroupEntry  OBJECT-TYPE
    SYNTAX    BwLastNumberRedialGroupEntry
    MAX-ACCESS  not-accessible
    STATUS    current
                DESCRIPTION
                        "This row contains the counters for Last Number Redial service measurements for a group"
    INDEX   {  bwLastNumberRedialGroupIndex  }
                ::=  { bwLastNumberRedialGroupTable 1 }

        BwLastNumberRedialGroupEntry  ::=  SEQUENCE {
                bwLastNumberRedialGroupIndex  Unsigned32,
                bwLastNumberRedialGroupID  DisplayString,
                bwLNRGroupNumRedials  Counter32
                }


  bwLastNumberRedialGroupIndex  OBJECT-TYPE
    SYNTAX      Unsigned32
    MAX-ACCESS    read-only
    STATUS      current
                DESCRIPTION
                                "This integer represents the a group index in the system"
                ::=  {  bwLastNumberRedialGroupEntry  1  }


  bwLastNumberRedialGroupID OBJECT-TYPE
    SYNTAX      DisplayString
    MAX-ACCESS    read-only
    STATUS      current
                DESCRIPTION
                                "This string represents a group ID"
                ::=  {  bwLastNumberRedialGroupEntry  2  }


  bwLNRGroupNumRedials  OBJECT-TYPE
    SYNTAX      Counter32
    MAX-ACCESS    read-write
    STATUS      current
                DESCRIPTION
                                "This counter reflects the number of times the flash code results in this service attempting to dial the last number called by a group"
                ::=  {  bwLastNumberRedialGroupEntry  3  }

-- Service :: Outgoing Calling Plan  ...........................................

  bwOCPNumGroupCallsBlocked OBJECT-TYPE
    SYNTAX      Counter32
    MAX-ACCESS    read-write
    STATUS      current
                DESCRIPTION
                                "This counter reflects the number of times an intra-group call is blocked"
                ::=  {  outgoingCallingPlan  1  }

  bwOCPNumLocalCallsBlocked OBJECT-TYPE
    SYNTAX      Counter32
    MAX-ACCESS    read-write
    STATUS      current
                DESCRIPTION
                                "This counter reflects the number of times a local call is blocked"
                ::=  {  outgoingCallingPlan  2  }

  bwOCPNumTollFreeCallsBlocked  OBJECT-TYPE
    SYNTAX      Counter32
    MAX-ACCESS    read-write
    STATUS      current
                DESCRIPTION
                                "This counter reflects the number of times a toll free call is blocked"
                ::=  {  outgoingCallingPlan  3  }

  bwOCPNumTollCallsBlocked  OBJECT-TYPE
    SYNTAX      Counter32
    MAX-ACCESS    read-write
    STATUS      current
                DESCRIPTION
                                "This counter reflects the number of times a toll call is blocked"
                ::=  {  outgoingCallingPlan  4  }

  bwOCPNumIntlCallsBlocked  OBJECT-TYPE
    SYNTAX      Counter32
    MAX-ACCESS    read-write
    STATUS      current
                DESCRIPTION
                                "This counter reflects the number of times an international call is blocked"
                ::=  {  outgoingCallingPlan  5  }

  bwOCPNumOperatorAssistedCallsBlocked  OBJECT-TYPE
    SYNTAX      Counter32
    MAX-ACCESS    read-write
    STATUS      current
                DESCRIPTION
                                "This counter reflects the number of times an operator assisted call is blocked"
                ::=  {  outgoingCallingPlan  6  }

  bwOCPNumChargeableDirAssistCallsBlocked OBJECT-TYPE
    SYNTAX      Counter32
    MAX-ACCESS    read-write
    STATUS      current
                DESCRIPTION
                                "This counter reflects the number of times a chargeable directory assistance call is
                                blocked"
                ::=  {  outgoingCallingPlan  7  }

  bwOCPNumSpecialServices1CallsBlocked  OBJECT-TYPE
    SYNTAX      Counter32
    MAX-ACCESS    read-write
    STATUS      current
                DESCRIPTION
                                "This counter reflects the number of times a special services call is blocked"
                ::=  {  outgoingCallingPlan  8  }

  bwOCPNumSpecialServices2CallsBlocked  OBJECT-TYPE
    SYNTAX      Counter32
    MAX-ACCESS    read-write
    STATUS      current
                DESCRIPTION
                                "This counter reflects the number of times a special services call is blocked"
                ::=  {  outgoingCallingPlan  9  }

  bwOCPNumPremiumServices1CallsBlocked  OBJECT-TYPE
    SYNTAX      Counter32
    MAX-ACCESS    read-write
    STATUS      current
                DESCRIPTION
                                "This counter reflects the number of times a premium services call is blocked"
                ::=  {  outgoingCallingPlan  10  }

  bwOCPNumPremiumServices2CallsBlocked  OBJECT-TYPE
    SYNTAX      Counter32
    MAX-ACCESS    read-write
    STATUS      current
                DESCRIPTION
                                "This counter reflects the number of times a premium services call is blocked"
                ::=  {  outgoingCallingPlan  11  }

  bwOCPNumCasualCallsBlocked  OBJECT-TYPE
    SYNTAX      Counter32
    MAX-ACCESS    read-write
    STATUS      current
                DESCRIPTION
                                "This counter reflects the number of times a casual equal access call is blocked"
                ::=  {  outgoingCallingPlan  12  }

  bwOCPNumURLDialingCallsBlocked  OBJECT-TYPE
    SYNTAX      Counter32
    MAX-ACCESS    read-write
    STATUS      current
                DESCRIPTION
                                "This counter reflects the number of times a URL dialed call is blocked"
                ::=  {  outgoingCallingPlan  13  }

  bwOCPNumUnknownCallsBlocked OBJECT-TYPE
    SYNTAX      Counter32
    MAX-ACCESS    read-write
    STATUS      current
                DESCRIPTION
                                "This counter reflects the number of times an unknown call type is blocked"
                ::=  {  outgoingCallingPlan  14  }

  bwOutgoingCallingPlanSPTable  OBJECT-TYPE
    SYNTAX    SEQUENCE  OF  BwOutgoingCallingPlanSPEntry
    MAX-ACCESS  not-accessible
    STATUS    current
                DESCRIPTION
                        "This table contains the counters for Outgoing Calling Plan service measurements for service providers"
                ::=  { outgoingCallingPlan  15 }

  bwOutgoingCallingPlanGroupTable OBJECT-TYPE
    SYNTAX    SEQUENCE  OF  BwOutgoingCallingPlanGroupEntry
    MAX-ACCESS  not-accessible
    STATUS    current
                DESCRIPTION
                        "This table contains the counters for Outgoing Calling Plan service measurements for groups"
                ::=  { outgoingCallingPlan  16 }

  bwOCPNumSuccessfulAuthorizations  OBJECT-TYPE
    SYNTAX      Counter32
    MAX-ACCESS    read-write
    STATUS      current
                DESCRIPTION
                                "This counter reflects the number of times a caller enters a valid authorization code in order to establish a call."
                ::=  {  outgoingCallingPlan  17  }

  bwOCPNumUnsuccessfulAuthorizations  OBJECT-TYPE
    SYNTAX      Counter32
    MAX-ACCESS    read-write
    STATUS      current
                DESCRIPTION
                                "This counter reflects the number of times a caller enters an invalid authorization code in order to establish a call."
                ::=  {  outgoingCallingPlan  18  }

  bwOCPNumTransfers OBJECT-TYPE
    SYNTAX      Counter32
    MAX-ACCESS    read-write
    STATUS      current
                DESCRIPTION
                                "This counter reflects the number of times OCP transfers the caller to a number where the caller's request will be handled."
                ::=  {  outgoingCallingPlan  19  }

  bwOCPSACNumSuccessfulLock OBJECT-TYPE
    SYNTAX      Counter32
    MAX-ACCESS    read-write
    STATUS      current
                DESCRIPTION
                                "This counter reflects the number of times the SAC lock feature access code is used successfully in order to lock calls"
                ::=  {  outgoingCallingPlan  20  }

  bwOCPSACNumSuccessfulUnlock OBJECT-TYPE
    SYNTAX      Counter32
    MAX-ACCESS    read-write
    STATUS      current
                DESCRIPTION
                                "This counter reflects the number of times the SAC unlock feature access code is used successfully in order to unlock calls"
                ::=  {  outgoingCallingPlan  21  }

  bwOCPSACNumUnsuccessfulLock OBJECT-TYPE
    SYNTAX      Counter32
    MAX-ACCESS    read-write
    STATUS      current
                DESCRIPTION
                                "This counter reflects the number of times the SAC lock feature access code is used unsuccessfully"
                ::=  {  outgoingCallingPlan  22  }

  bwOCPSACNumUnsuccessfulUnlock OBJECT-TYPE
    SYNTAX      Counter32
    MAX-ACCESS    read-write
    STATUS      current
                DESCRIPTION
                                "This counter reflects the number of times the SAC unlock feature access code is used unsuccessfully"
                ::=  {  outgoingCallingPlan  23  }

  bwOCPSACNumUnsuccessfulCodeUsage  OBJECT-TYPE
    SYNTAX      Counter32
    MAX-ACCESS    read-write
    STATUS      current
                DESCRIPTION
                                "This counter reflects the number of times a stored SAC code is erased from the database because it fails to pass EOCP screening following a change in the EOCP plan that makes the stored SAC code obsolete"
                ::=  {  outgoingCallingPlan  24  }

  bwOCPNumOutsideGroupTransferBlocks  OBJECT-TYPE
    SYNTAX      Counter32
    MAX-ACCESS    read-write
    STATUS      current
                DESCRIPTION
                                "This counter reflects the number of times this service denies call forwarding or transfer to a party outside of the group."
                ::=  {  outgoingCallingPlan  25  }

-- Service :: Outgoing Calling Plan :: SP TABLE ...........................................

  bwOutgoingCallingPlanSPEntry  OBJECT-TYPE
    SYNTAX    BwOutgoingCallingPlanSPEntry
    MAX-ACCESS  not-accessible
    STATUS    current
                DESCRIPTION
                        "This row contains the counters for Outgoing Calling Plan service measurements for a service provider"
    INDEX   {  bwOutgoingCallingPlanSPIndex  }
                ::=  { bwOutgoingCallingPlanSPTable 1 }

        BwOutgoingCallingPlanSPEntry  ::=  SEQUENCE {
                bwOutgoingCallingPlanSPIndex  Unsigned32,
                bwOutgoingCallingPlanSPID  DisplayString,
                bwOCPSPNumGroupCallsBlocked  Counter32,
                bwOCPSPNumLocalCallsBlocked  Counter32,
                bwOCPSPNumTollFreeCallsBlocked  Counter32,
                bwOCPSPNumTollCallsBlocked  Counter32,
                bwOCPSPNumIntlCallsBlocked  Counter32,
                bwOCPSPNumOperatorAssistedCallsBlocked  Counter32,
                bwOCPSPNumChargeableDirAssistCallsBlocked  Counter32,
                bwOCPSPNumSpecialServices1CallsBlocked  Counter32,
                bwOCPSPNumSpecialServices2CallsBlocked  Counter32,
                bwOCPSPNumPremiumServices1CallsBlocked  Counter32,
                bwOCPSPNumPremiumServices2CallsBlocked  Counter32,
                bwOCPSPNumCasualCallsBlocked  Counter32,
                bwOCPSPNumURLDialingCallsBlocked  Counter32,
                bwOCPSPNumUnknownCallsBlocked  Counter32,
                bwOCPSPNumSuccessfulAuthorizations Counter32,
                bwOCPSPNumUnsuccessfulAuthorizations Counter32,
                bwOCPSPNumTransfers Counter32,
                bwOCPSACSPNumSuccessfulLock Counter32,
                bwOCPSACSPNumSuccessfulUnlock Counter32,
                bwOCPSACSPNumUnsuccessfulLock Counter32,
                bwOCPSACSPNumUnsuccessfulUnlock Counter32,
                bwOCPSACSPNumUnsuccessfulCodeUsage Counter32,
                bwOCPSPNumOutsideGroupTransferBlocks Counter32
                }


  bwOutgoingCallingPlanSPIndex  OBJECT-TYPE
    SYNTAX      Unsigned32
    MAX-ACCESS    read-only
    STATUS      current
                DESCRIPTION
                                "This integer represents the a service provider index in the system"
                ::=  {  bwOutgoingCallingPlanSPEntry  1  }


  bwOutgoingCallingPlanSPID OBJECT-TYPE
    SYNTAX      DisplayString
    MAX-ACCESS    read-only
    STATUS      current
                DESCRIPTION
                                "This string represents a service provider ID"
                ::=  {  bwOutgoingCallingPlanSPEntry  2  }


  bwOCPSPNumGroupCallsBlocked OBJECT-TYPE
    SYNTAX      Counter32
    MAX-ACCESS    read-write
    STATUS      current
                DESCRIPTION
                                "This counter reflects the number of times an intra-group call is blocked by a service provider"
                ::=  {  bwOutgoingCallingPlanSPEntry  3  }


  bwOCPSPNumLocalCallsBlocked OBJECT-TYPE
    SYNTAX      Counter32
    MAX-ACCESS    read-write
    STATUS      current
                DESCRIPTION
                                "This counter reflects the number of times a local call is blocked by a service provider"
                ::=  {  bwOutgoingCallingPlanSPEntry  4  }


  bwOCPSPNumTollFreeCallsBlocked  OBJECT-TYPE
    SYNTAX      Counter32
    MAX-ACCESS    read-write
    STATUS      current
                DESCRIPTION
                                "This counter reflects the number of times a toll free call is blocked by a service provider"
                ::=  {  bwOutgoingCallingPlanSPEntry  5  }


  bwOCPSPNumTollCallsBlocked  OBJECT-TYPE
    SYNTAX      Counter32
    MAX-ACCESS    read-write
    STATUS      current
                DESCRIPTION
                                "This counter reflects the number of times a toll call is blocked by a service provider"
                ::=  {  bwOutgoingCallingPlanSPEntry  6  }


  bwOCPSPNumIntlCallsBlocked  OBJECT-TYPE
    SYNTAX      Counter32
    MAX-ACCESS    read-write
    STATUS      current
                DESCRIPTION
                                "This counter reflects the number of times an international call is blocked by a service provider"
                ::=  {  bwOutgoingCallingPlanSPEntry  7  }


  bwOCPSPNumOperatorAssistedCallsBlocked  OBJECT-TYPE
    SYNTAX      Counter32
    MAX-ACCESS    read-write
    STATUS      current
                DESCRIPTION
                                "This counter reflects the number of times an operator assisted call is blocked by a service provider"
                ::=  {  bwOutgoingCallingPlanSPEntry  8  }


  bwOCPSPNumChargeableDirAssistCallsBlocked OBJECT-TYPE
    SYNTAX      Counter32
    MAX-ACCESS    read-write
    STATUS      current
                DESCRIPTION
                                "This counter reflects the number of times a chargeable directory assistance call is blocked by a service provider"
                ::=  {  bwOutgoingCallingPlanSPEntry  9  }


  bwOCPSPNumSpecialServices1CallsBlocked  OBJECT-TYPE
    SYNTAX      Counter32
    MAX-ACCESS    read-write
    STATUS      current
                DESCRIPTION
                                "This counter reflects the number of times a special services call is blocked by a service provider"
                ::=  {  bwOutgoingCallingPlanSPEntry  10  }


  bwOCPSPNumSpecialServices2CallsBlocked  OBJECT-TYPE
    SYNTAX      Counter32
    MAX-ACCESS    read-write
    STATUS      current
                DESCRIPTION
                                "This counter reflects the number of times a special services call is blocked by a service provider"
                ::=  {  bwOutgoingCallingPlanSPEntry  11  }


  bwOCPSPNumPremiumServices1CallsBlocked  OBJECT-TYPE
    SYNTAX      Counter32
    MAX-ACCESS    read-write
    STATUS      current
                DESCRIPTION
                                "This counter reflects the number of times a premium services call is blocked by a service provider"
                ::=  {  bwOutgoingCallingPlanSPEntry  12  }


  bwOCPSPNumPremiumServices2CallsBlocked  OBJECT-TYPE
    SYNTAX      Counter32
    MAX-ACCESS    read-write
    STATUS      current
                DESCRIPTION
                                "This counter reflects the number of times a premium services call is blocked by a service provider"
                ::=  {  bwOutgoingCallingPlanSPEntry  13  }


  bwOCPSPNumCasualCallsBlocked  OBJECT-TYPE
    SYNTAX      Counter32
    MAX-ACCESS    read-write
    STATUS      current
                DESCRIPTION
                                "This counter reflects the number of times a casual equal access call is blocked by a service provider"
                ::=  {  bwOutgoingCallingPlanSPEntry  14  }


  bwOCPSPNumURLDialingCallsBlocked  OBJECT-TYPE
    SYNTAX      Counter32
    MAX-ACCESS    read-write
    STATUS      current
                DESCRIPTION
                                "This counter reflects the number of times a URL dialed call is blocked by a service provider"
                ::=  {  bwOutgoingCallingPlanSPEntry  15  }


  bwOCPSPNumUnknownCallsBlocked OBJECT-TYPE
    SYNTAX      Counter32
    MAX-ACCESS    read-write
    STATUS      current
                DESCRIPTION
                                "This counter reflects the number of times an unknown call type is blocked by a service provider"
                ::=  {  bwOutgoingCallingPlanSPEntry  16  }

  bwOCPSPNumSuccessfulAuthorizations  OBJECT-TYPE
    SYNTAX      Counter32
    MAX-ACCESS    read-write
    STATUS      current
                DESCRIPTION
                                "This counter reflects the number of times a caller enters a valid authorization code in order to establish a call for a given service provider."
                ::=  {  bwOutgoingCallingPlanSPEntry  17  }

  bwOCPSPNumUnsuccessfulAuthorizations  OBJECT-TYPE
    SYNTAX      Counter32
    MAX-ACCESS    read-write
    STATUS      current
                DESCRIPTION
                                "This counter reflects the number of times a caller enters an invalid authorization code in order to establish a call for a given service provider."
                ::=  {  bwOutgoingCallingPlanSPEntry  18  }

  bwOCPSPNumTransfers OBJECT-TYPE
    SYNTAX      Counter32
    MAX-ACCESS    read-write
    STATUS      current
                DESCRIPTION
                                "This counter reflects the number of times OCP transfers the caller to a number where the caller's request will be handled for a given service provider."
                ::=  {  bwOutgoingCallingPlanSPEntry  19  }

  bwOCPSACSPNumSuccessfulLock OBJECT-TYPE
    SYNTAX      Counter32
    MAX-ACCESS    read-write
    STATUS      current
                DESCRIPTION
                                "This counter reflects the number of times the SAC lock feature access code is used successfully in order to lock calls for a given service provider"
                ::=  {  bwOutgoingCallingPlanSPEntry  20  }

  bwOCPSACSPNumSuccessfulUnlock OBJECT-TYPE
    SYNTAX      Counter32
    MAX-ACCESS    read-write
    STATUS      current
                DESCRIPTION
                                "This counter reflects the number of times the SAC unlock feature access code is used successfully in order to unlock calls for a given service provider"
                ::=  {  bwOutgoingCallingPlanSPEntry  21  }

  bwOCPSACSPNumUnsuccessfulLock OBJECT-TYPE
    SYNTAX      Counter32
    MAX-ACCESS    read-write
    STATUS      current
                DESCRIPTION
                                "This counter reflects the number of times the SAC lock feature access code is used unsuccessfully for a given service provider"
                ::=  {  bwOutgoingCallingPlanSPEntry  22  }

  bwOCPSACSPNumUnsuccessfulUnlock OBJECT-TYPE
    SYNTAX      Counter32
    MAX-ACCESS    read-write
    STATUS      current
                DESCRIPTION
                                "This counter reflects the number of times the SAC unlock feature access code is used unsuccessfully for a given service provider"
                ::=  {  bwOutgoingCallingPlanSPEntry  23  }

  bwOCPSACSPNumUnsuccessfulCodeUsage  OBJECT-TYPE
    SYNTAX      Counter32
    MAX-ACCESS    read-write
    STATUS      current
                DESCRIPTION
                                "This counter reflects the number of times a stored SAC code is erased from the database because it fails to pass EOCP screening following a change in the EOCP plan that makes the stored SAC code obsolete for a given service provider"
                ::=  {  bwOutgoingCallingPlanSPEntry  24  }

  bwOCPSPNumOutsideGroupTransferBlocks  OBJECT-TYPE
    SYNTAX      Counter32
    MAX-ACCESS    read-write
    STATUS      current
                DESCRIPTION
                                "This counter reflects the number of times this service denies call forwarding or transfer to a party outside of the group for a given service provider."
                ::=  {  bwOutgoingCallingPlanSPEntry  25  }

-- Service :: Outgoing Calling Plan :: GROUP TABLE ...........................................

  bwOutgoingCallingPlanGroupEntry OBJECT-TYPE
    SYNTAX    BwOutgoingCallingPlanGroupEntry
    MAX-ACCESS  not-accessible
    STATUS    current
                DESCRIPTION
                        "This row contains the counters for Outgoing Calling Plan service measurements for a group"
    INDEX   {  bwOutgoingCallingPlanGroupIndex  }
                ::=  { bwOutgoingCallingPlanGroupTable 1 }

        BwOutgoingCallingPlanGroupEntry  ::=  SEQUENCE {
                bwOutgoingCallingPlanGroupIndex  Unsigned32,
                bwOutgoingCallingPlanGroupID  DisplayString,
                bwOCPGroupNumGroupCallsBlocked  Counter32,
                bwOCPGroupNumLocalCallsBlocked  Counter32,
                bwOCPGroupNumTollFreeCallsBlocked  Counter32,
                bwOCPGroupNumTollCallsBlocked  Counter32,
                bwOCPGroupNumIntlCallsBlocked  Counter32,
                bwOCPGroupNumOperatorAssistedCallsBlocked  Counter32,
                bwOCPGroupNumChargeableDirAssistCallsBlocked  Counter32,
                bwOCPGroupNumSpecialServices1CallsBlocked  Counter32,
                bwOCPGroupNumSpecialServices2CallsBlocked  Counter32,
                bwOCPGroupNumPremiumServices1CallsBlocked  Counter32,
                bwOCPGroupNumPremiumServices2CallsBlocked  Counter32,
                bwOCPGroupNumCasualCallsBlocked  Counter32,
                bwOCPGroupNumURLDialingCallsBlocked  Counter32,
                bwOCPGroupNumUnknownCallsBlocked  Counter32,
                bwOCPGroupNumSuccessfulAuthorizations Counter32,
                bwOCPGroupNumUnsuccessfulAuthorizations Counter32,
                bwOCPGroupNumTransfers Counter32,
                bwOCPSACGroupNumSuccessfulLock Counter32,
                bwOCPSACGroupNumSuccessfulUnlock Counter32,
                bwOCPSACGroupNumUnsuccessfulLock Counter32,
                bwOCPSACGroupNumUnsuccessfulUnlock Counter32,
                bwOCPSACGroupNumUnsuccessfulCodeUsage Counter32,
                bwOCPGroupNumOutsideGroupTransferBlocks Counter32
                }


  bwOutgoingCallingPlanGroupIndex OBJECT-TYPE
    SYNTAX      Unsigned32
    MAX-ACCESS    read-only
    STATUS      current
                DESCRIPTION
                                "This integer represents the a group index in the system"
                ::=  {  bwOutgoingCallingPlanGroupEntry  1  }


  bwOutgoingCallingPlanGroupID  OBJECT-TYPE
    SYNTAX      DisplayString
    MAX-ACCESS    read-only
    STATUS      current
                DESCRIPTION
                                "This string represents a group ID"
                ::=  {  bwOutgoingCallingPlanGroupEntry  2  }


  bwOCPGroupNumGroupCallsBlocked  OBJECT-TYPE
    SYNTAX      Counter32
    MAX-ACCESS    read-write
    STATUS      current
                DESCRIPTION
                                "This counter reflects the number of times an intra-group call is blocked by a group"
                ::=  {  bwOutgoingCallingPlanGroupEntry  3  }


  bwOCPGroupNumLocalCallsBlocked  OBJECT-TYPE
    SYNTAX      Counter32
    MAX-ACCESS    read-write
    STATUS      current
                DESCRIPTION
                                "This counter reflects the number of times a local call is blocked by a group"
                ::=  {  bwOutgoingCallingPlanGroupEntry  4  }


  bwOCPGroupNumTollFreeCallsBlocked OBJECT-TYPE
    SYNTAX      Counter32
    MAX-ACCESS    read-write
    STATUS      current
                DESCRIPTION
                                "This counter reflects the number of times a toll free call is blocked by a group"
                ::=  {  bwOutgoingCallingPlanGroupEntry  5  }


  bwOCPGroupNumTollCallsBlocked OBJECT-TYPE
    SYNTAX      Counter32
    MAX-ACCESS    read-write
    STATUS      current
                DESCRIPTION
                                "This counter reflects the number of times a toll call is blocked by a group"
                ::=  {  bwOutgoingCallingPlanGroupEntry  6  }


  bwOCPGroupNumIntlCallsBlocked OBJECT-TYPE
    SYNTAX      Counter32
    MAX-ACCESS    read-write
    STATUS      current
                DESCRIPTION
                                "This counter reflects the number of times an international call is blocked by a group"
                ::=  {  bwOutgoingCallingPlanGroupEntry  7  }


  bwOCPGroupNumOperatorAssistedCallsBlocked OBJECT-TYPE
    SYNTAX      Counter32
    MAX-ACCESS    read-write
    STATUS      current
                DESCRIPTION
                                "This counter reflects the number of times an operator assisted call is blocked by a group"
                ::=  {  bwOutgoingCallingPlanGroupEntry  8  }


  bwOCPGroupNumChargeableDirAssistCallsBlocked  OBJECT-TYPE
    SYNTAX      Counter32
    MAX-ACCESS    read-write
    STATUS      current
                DESCRIPTION
                                "This counter reflects the number of times a chargeable directory assistance call is blocked by a group"
                ::=  {  bwOutgoingCallingPlanGroupEntry  9  }


  bwOCPGroupNumSpecialServices1CallsBlocked OBJECT-TYPE
    SYNTAX      Counter32
    MAX-ACCESS    read-write
    STATUS      current
                DESCRIPTION
                                "This counter reflects the number of times a special services call is blocked by a group"
                ::=  {  bwOutgoingCallingPlanGroupEntry  10  }


  bwOCPGroupNumSpecialServices2CallsBlocked OBJECT-TYPE
    SYNTAX      Counter32
    MAX-ACCESS    read-write
    STATUS      current
                DESCRIPTION
                                "This counter reflects the number of times a special services call is blocked by a group"
                ::=  {  bwOutgoingCallingPlanGroupEntry  11  }


  bwOCPGroupNumPremiumServices1CallsBlocked OBJECT-TYPE
    SYNTAX      Counter32
    MAX-ACCESS    read-write
    STATUS      current
                DESCRIPTION
                                "This counter reflects the number of times a premium services call is blocked by a group"
                ::=  {  bwOutgoingCallingPlanGroupEntry  12  }


  bwOCPGroupNumPremiumServices2CallsBlocked OBJECT-TYPE
    SYNTAX      Counter32
    MAX-ACCESS    read-write
    STATUS      current
                DESCRIPTION
                                "This counter reflects the number of times a premium services call is blocked by a group"
                ::=  {  bwOutgoingCallingPlanGroupEntry  13  }


  bwOCPGroupNumCasualCallsBlocked OBJECT-TYPE
    SYNTAX      Counter32
    MAX-ACCESS    read-write
    STATUS      current
                DESCRIPTION
                                "This counter reflects the number of times a casual equal access call is blocked by a group"
                ::=  {  bwOutgoingCallingPlanGroupEntry  14  }


  bwOCPGroupNumURLDialingCallsBlocked OBJECT-TYPE
    SYNTAX      Counter32
    MAX-ACCESS    read-write
    STATUS      current
                DESCRIPTION
                                "This counter reflects the number of times a URL dialed call is blocked by a group"
                ::=  {  bwOutgoingCallingPlanGroupEntry  15  }


  bwOCPGroupNumUnknownCallsBlocked  OBJECT-TYPE
    SYNTAX      Counter32
    MAX-ACCESS    read-write
    STATUS      current
                DESCRIPTION
                                "This counter reflects the number of times an unknown call type is blocked by a group"
                ::=  {  bwOutgoingCallingPlanGroupEntry  16  }

  bwOCPGroupNumSuccessfulAuthorizations OBJECT-TYPE
    SYNTAX      Counter32
    MAX-ACCESS    read-write
    STATUS      current
                DESCRIPTION
                                "This counter reflects the number of times a caller enters a valid authorization code in order to establish a call for a given group."
                ::=  {  bwOutgoingCallingPlanGroupEntry  17  }

  bwOCPGroupNumUnsuccessfulAuthorizations OBJECT-TYPE
    SYNTAX      Counter32
    MAX-ACCESS    read-write
    STATUS      current
                DESCRIPTION
                                "This counter reflects the number of times a caller enters an invalid authorization code in order to establish a call for a given group."
                ::=  {  bwOutgoingCallingPlanGroupEntry  18  }

  bwOCPGroupNumTransfers  OBJECT-TYPE
    SYNTAX      Counter32
    MAX-ACCESS    read-write
    STATUS      current
                DESCRIPTION
                                "This counter reflects the number of times OCP transfers the caller to a number where the caller's request will be handled for a given group."
                ::=  {  bwOutgoingCallingPlanGroupEntry  19  }

  bwOCPSACGroupNumSuccessfulLock  OBJECT-TYPE
    SYNTAX      Counter32
    MAX-ACCESS    read-write
    STATUS      current
                DESCRIPTION
                                "This counter reflects the number of times the SAC lock feature access code is used successfully in order to lock calls for a given group"
                ::=  {  bwOutgoingCallingPlanGroupEntry  20  }

  bwOCPSACGroupNumSuccessfulUnlock  OBJECT-TYPE
    SYNTAX      Counter32
    MAX-ACCESS    read-write
    STATUS      current
                DESCRIPTION
                                "This counter reflects the number of times the SAC unlock feature access code is used successfully in order to unlock calls for a given group"
                ::=  {  bwOutgoingCallingPlanGroupEntry  21  }

  bwOCPSACGroupNumUnsuccessfulLock  OBJECT-TYPE
    SYNTAX      Counter32
    MAX-ACCESS    read-write
    STATUS      current
                DESCRIPTION
                                "This counter reflects the number of times the SAC lock feature access code is used unsuccessfully for a given group"
                ::=  {  bwOutgoingCallingPlanGroupEntry  22  }

  bwOCPSACGroupNumUnsuccessfulUnlock  OBJECT-TYPE
    SYNTAX      Counter32
    MAX-ACCESS    read-write
    STATUS      current
                DESCRIPTION
                                "This counter reflects the number of times the SAC unlock feature access code is used unsuccessfully for a given group"
                ::=  {  bwOutgoingCallingPlanGroupEntry  23  }

  bwOCPSACGroupNumUnsuccessfulCodeUsage OBJECT-TYPE
    SYNTAX      Counter32
    MAX-ACCESS    read-write
    STATUS      current
                DESCRIPTION
                                "This counter reflects the number of times a stored SAC code is erased from the database because it fails to pass EOCP screening following a change in the EOCP plan that makes the stored SAC code obsolete for a given group"
                ::=  {  bwOutgoingCallingPlanGroupEntry  24  }

  bwOCPGroupNumOutsideGroupTransferBlocks OBJECT-TYPE
    SYNTAX      Counter32
    MAX-ACCESS    read-write
    STATUS      current
                DESCRIPTION
                                "This counter reflects the number of times this service denies call forwarding or transfer to a party outside of the group for a given group."
                ::=  {  bwOutgoingCallingPlanGroupEntry  25  }

-- Service :: Priority Alert  ...........................................

  bwPriorityAlertNumDistinctive OBJECT-TYPE
    SYNTAX      Counter32
    MAX-ACCESS    read-write
    STATUS      current
                DESCRIPTION
                                "This counter reflects the number of times an incoming or waiting call has a priority
                                tone applied"
                ::=  {  priorityAlert  1  }

  bwPriorityAlertSPTable  OBJECT-TYPE
    SYNTAX    SEQUENCE  OF  BwPriorityAlertSPEntry
    MAX-ACCESS  not-accessible
    STATUS    current
                DESCRIPTION
                        "This table contains the counters for Priority Alert service measurements for service providers"
                ::=  { priorityAlert  2 }

  bwPriorityAlertGroupTable OBJECT-TYPE
    SYNTAX    SEQUENCE  OF  BwPriorityAlertGroupEntry
    MAX-ACCESS  not-accessible
    STATUS    current
                DESCRIPTION
                        "This table contains the counters for Priority Alert service measurements for groups"
                ::=  { priorityAlert  3 }

-- Service :: Priority Alert :: SP TABLE ...........................................

  bwPriorityAlertSPEntry  OBJECT-TYPE
    SYNTAX    BwPriorityAlertSPEntry
    MAX-ACCESS  not-accessible
    STATUS    current
                DESCRIPTION
                        "This row contains the counters for Priority Alert service measurements for a service provider"
    INDEX   {  bwPriorityAlertSPIndex  }
                ::=  { bwPriorityAlertSPTable 1 }

        BwPriorityAlertSPEntry  ::=  SEQUENCE {
                bwPriorityAlertSPIndex  Unsigned32,
                bwPriorityAlertSPID  DisplayString,
                bwPriorityAlertSPNumDistinctive  Counter32
                }


  bwPriorityAlertSPIndex  OBJECT-TYPE
    SYNTAX      Unsigned32
    MAX-ACCESS    read-only
    STATUS      current
                DESCRIPTION
                                "This integer represents the a service provider index in the system"
                ::=  {  bwPriorityAlertSPEntry  1  }


  bwPriorityAlertSPID OBJECT-TYPE
    SYNTAX      DisplayString
    MAX-ACCESS    read-only
    STATUS      current
                DESCRIPTION
                                "This string represents a service provider ID"
                ::=  {  bwPriorityAlertSPEntry  2  }


  bwPriorityAlertSPNumDistinctive OBJECT-TYPE
    SYNTAX      Counter32
    MAX-ACCESS    read-write
    STATUS      current
                DESCRIPTION
                                "This counter reflects the number of times an incoming or waiting call has a priority tone applied by a service provider"
                ::=  {  bwPriorityAlertSPEntry  3  }

-- Service :: Priority Alert :: GROUP TABLE ...........................................

  bwPriorityAlertGroupEntry OBJECT-TYPE
    SYNTAX    BwPriorityAlertGroupEntry
    MAX-ACCESS  not-accessible
    STATUS    current
                DESCRIPTION
                        "This row contains the counters for Priority Alert service measurements for a group"
    INDEX   {  bwPriorityAlertGroupIndex  }
                ::=  { bwPriorityAlertGroupTable 1 }

        BwPriorityAlertGroupEntry  ::=  SEQUENCE {
                bwPriorityAlertGroupIndex  Unsigned32,
                bwPriorityAlertGroupID  DisplayString,
                bwPriorityAlertGroupNumDistinctive  Counter32
                }


  bwPriorityAlertGroupIndex OBJECT-TYPE
    SYNTAX      Unsigned32
    MAX-ACCESS    read-only
    STATUS      current
                DESCRIPTION
                                "This integer represents the a group index in the system"
                ::=  {  bwPriorityAlertGroupEntry  1  }


  bwPriorityAlertGroupID  OBJECT-TYPE
    SYNTAX      DisplayString
    MAX-ACCESS    read-only
    STATUS      current
                DESCRIPTION
                                "This string represents a group ID"
                ::=  {  bwPriorityAlertGroupEntry  2  }


  bwPriorityAlertGroupNumDistinctive  OBJECT-TYPE
    SYNTAX      Counter32
    MAX-ACCESS    read-write
    STATUS      current
                DESCRIPTION
                                "This counter reflects the number of times an incoming or waiting call has a priority tone applied by a group"
                ::=  {  bwPriorityAlertGroupEntry  3  }

-- Service :: Selective Call Acceptance  ...........................................

  bwSCANumAcceptances OBJECT-TYPE
    SYNTAX      Counter32
    MAX-ACCESS    read-write
    STATUS      current
                DESCRIPTION
                                "This counter reflects the number of times an incoming call meets a criteria for this
                                service"
                ::=  {  selectiveCallAcceptance  1  }

  bwSelectiveCallAcceptanceSPTable  OBJECT-TYPE
    SYNTAX    SEQUENCE  OF  BwSelectiveCallAcceptanceSPEntry
    MAX-ACCESS  not-accessible
    STATUS    current
                DESCRIPTION
                        "This table contains the counters for Selective Call Acceptance service measurements for service providers"
                ::=  { selectiveCallAcceptance  2 }

  bwSelectiveCallAcceptanceGroupTable OBJECT-TYPE
    SYNTAX    SEQUENCE  OF  BwSelectiveCallAcceptanceGroupEntry
    MAX-ACCESS  not-accessible
    STATUS    current
                DESCRIPTION
                        "This table contains the counters for Selective Call Acceptance service measurements for groups"
                ::=  { selectiveCallAcceptance  3 }

-- Service :: Selective Call Acceptance :: SP TABLE ...........................................

  bwSelectiveCallAcceptanceSPEntry  OBJECT-TYPE
    SYNTAX    BwSelectiveCallAcceptanceSPEntry
    MAX-ACCESS  not-accessible
    STATUS    current
                DESCRIPTION
                        "This row contains the counters for Selective Call Acceptance service measurements for a service provider"
    INDEX   {  bwSelectiveCallAcceptanceSPIndex  }
                ::=  { bwSelectiveCallAcceptanceSPTable 1 }

        BwSelectiveCallAcceptanceSPEntry  ::=  SEQUENCE {
                bwSelectiveCallAcceptanceSPIndex  Unsigned32,
                bwSelectiveCallAcceptanceSPID  DisplayString,
                bwSCASPNumAcceptances  Counter32
                }


  bwSelectiveCallAcceptanceSPIndex  OBJECT-TYPE
    SYNTAX      Unsigned32
    MAX-ACCESS    read-only
    STATUS      current
                DESCRIPTION
                                "This integer represents the a service provider index in the system"
                ::=  {  bwSelectiveCallAcceptanceSPEntry  1  }


  bwSelectiveCallAcceptanceSPID OBJECT-TYPE
    SYNTAX      DisplayString
    MAX-ACCESS    read-only
    STATUS      current
                DESCRIPTION
                                "This string represents a service provider ID"
                ::=  {  bwSelectiveCallAcceptanceSPEntry  2  }


  bwSCASPNumAcceptances OBJECT-TYPE
    SYNTAX      Counter32
    MAX-ACCESS    read-write
    STATUS      current
                DESCRIPTION
                                "This counter reflects the number of times an incoming call meets a criteria for this service by a service provider"
                ::=  {  bwSelectiveCallAcceptanceSPEntry  3  }

-- Service :: Selective Call Acceptance :: GROUP TABLE ...........................................

  bwSelectiveCallAcceptanceGroupEntry OBJECT-TYPE
    SYNTAX    BwSelectiveCallAcceptanceGroupEntry
    MAX-ACCESS  not-accessible
    STATUS    current
                DESCRIPTION
                        "This row contains the counters for Selective Call Acceptance service measurements for a group"
    INDEX   {  bwSelectiveCallAcceptanceGroupIndex  }
                ::=  { bwSelectiveCallAcceptanceGroupTable 1 }

        BwSelectiveCallAcceptanceGroupEntry  ::=  SEQUENCE {
                bwSelectiveCallAcceptanceGroupIndex  Unsigned32,
                bwSelectiveCallAcceptanceGroupID  DisplayString,
                bwSCAGroupNumAcceptances  Counter32
                }


  bwSelectiveCallAcceptanceGroupIndex OBJECT-TYPE
    SYNTAX      Unsigned32
    MAX-ACCESS    read-only
    STATUS      current
                DESCRIPTION
                                "This integer represents the a group index in the system"
                ::=  {  bwSelectiveCallAcceptanceGroupEntry  1  }


  bwSelectiveCallAcceptanceGroupID  OBJECT-TYPE
    SYNTAX      DisplayString
    MAX-ACCESS    read-only
    STATUS      current
                DESCRIPTION
                                "This string represents a group ID"
                ::=  {  bwSelectiveCallAcceptanceGroupEntry  2  }


  bwSCAGroupNumAcceptances  OBJECT-TYPE
    SYNTAX      Counter32
    MAX-ACCESS    read-write
    STATUS      current
                DESCRIPTION
                                "This counter reflects the number of times an incoming call meets a criteria for this service by a group"
                ::=  {  bwSelectiveCallAcceptanceGroupEntry  3  }

-- Service :: Selective Call Forward  ...........................................

  bwSCFNumForwards  OBJECT-TYPE
    SYNTAX      Counter32
    MAX-ACCESS    read-write
    STATUS      current
                DESCRIPTION
                                "This counter reflects the number of times a criteria is met for this service"
                ::=  {  selectiveCallForward  1  }

  bwSelectiveCallForwardSPTable OBJECT-TYPE
    SYNTAX    SEQUENCE  OF  BwSelectiveCallForwardSPEntry
    MAX-ACCESS  not-accessible
    STATUS    current
                DESCRIPTION
                        "This table contains the counters for Call Forwarding Selective service measurements for service providers"
                ::=  { selectiveCallForward  2 }

  bwSelectiveCallForwardGroupTable  OBJECT-TYPE
    SYNTAX    SEQUENCE  OF  BwSelectiveCallForwardGroupEntry
    MAX-ACCESS  not-accessible
    STATUS    current
                DESCRIPTION
                        "This table contains the counters for Call Forwarding Selective service measurements for groups"
                ::=  { selectiveCallForward  3 }

-- Service :: Selective Call Forward :: SP TABLE ...........................................

  bwSelectiveCallForwardSPEntry OBJECT-TYPE
    SYNTAX    BwSelectiveCallForwardSPEntry
    MAX-ACCESS  not-accessible
    STATUS    current
                DESCRIPTION
                        "This row contains the counters for Call Forwarding Selective service measurements for a service provider"
    INDEX   {  bwSelectiveCallForwardSPIndex  }
                ::=  { bwSelectiveCallForwardSPTable 1 }

        BwSelectiveCallForwardSPEntry  ::=  SEQUENCE {
                bwSelectiveCallForwardSPIndex  Unsigned32,
                bwSelectiveCallForwardSPID  DisplayString,
                bwSCFSPNumForwards  Counter32
                }


  bwSelectiveCallForwardSPIndex OBJECT-TYPE
    SYNTAX      Unsigned32
    MAX-ACCESS    read-only
    STATUS      current
                DESCRIPTION
                                "This integer represents the a service provider index in the system"
                ::=  {  bwSelectiveCallForwardSPEntry  1  }


  bwSelectiveCallForwardSPID  OBJECT-TYPE
    SYNTAX      DisplayString
    MAX-ACCESS    read-only
    STATUS      current
                DESCRIPTION
                                "This string represents a service provider ID"
                ::=  {  bwSelectiveCallForwardSPEntry  2  }


  bwSCFSPNumForwards  OBJECT-TYPE
    SYNTAX      Counter32
    MAX-ACCESS    read-write
    STATUS      current
                DESCRIPTION
                                "This counter reflects the number of times a criteria is met for this service by a service provider"
                ::=  {  bwSelectiveCallForwardSPEntry  3  }

-- Service :: Selective Call Forward :: GROUP TABLE ...........................................

  bwSelectiveCallForwardGroupEntry  OBJECT-TYPE
    SYNTAX    BwSelectiveCallForwardGroupEntry
    MAX-ACCESS  not-accessible
    STATUS    current
                DESCRIPTION
                        "This row contains the counters for Call Forwarding Selective service measurements for a group"
    INDEX   {  bwSelectiveCallForwardGroupIndex  }
                ::=  { bwSelectiveCallForwardGroupTable 1 }

        BwSelectiveCallForwardGroupEntry  ::=  SEQUENCE {
                bwSelectiveCallForwardGroupIndex  Unsigned32,
                bwSelectiveCallForwardGroupID  DisplayString,
                bwSCFGroupNumForwards  Counter32
                }


  bwSelectiveCallForwardGroupIndex  OBJECT-TYPE
    SYNTAX      Unsigned32
    MAX-ACCESS    read-only
    STATUS      current
                DESCRIPTION
                                "This integer represents the a group index in the system"
                ::=  {  bwSelectiveCallForwardGroupEntry  1  }


  bwSelectiveCallForwardGroupID OBJECT-TYPE
    SYNTAX      DisplayString
    MAX-ACCESS    read-only
    STATUS      current
                DESCRIPTION
                                "This string represents a group ID"
                ::=  {  bwSelectiveCallForwardGroupEntry  2  }


  bwSCFGroupNumForwards OBJECT-TYPE
    SYNTAX      Counter32
    MAX-ACCESS    read-write
    STATUS      current
                DESCRIPTION
                                "This counter reflects the number of times a criteria is met for this service by a group"
                ::=  {  bwSelectiveCallForwardGroupEntry  3  }

-- Service :: Selective Call Rejection  ...........................................

  bwSCRNumRejects OBJECT-TYPE
    SYNTAX      Counter32
    MAX-ACCESS    read-write
    STATUS      current
                DESCRIPTION
                                "This counter reflects the number of times an incoming call meets a criteria for this
                                service"
                ::=  {  selectiveCallRejection  1  }

  bwSelectiveCallRejectionSPTable OBJECT-TYPE
    SYNTAX    SEQUENCE  OF  BwSelectiveCallRejectionSPEntry
    MAX-ACCESS  not-accessible
    STATUS    current
                DESCRIPTION
                        "This table contains the counters for Selective Call Rejection service measurements for service providers"
                ::=  { selectiveCallRejection  2 }

  bwSelectiveCallRejectionGroupTable  OBJECT-TYPE
    SYNTAX    SEQUENCE  OF  BwSelectiveCallRejectionGroupEntry
    MAX-ACCESS  not-accessible
    STATUS    current
                DESCRIPTION
                        "This table contains the counters for Selective Call Rejection service measurements for groups"
                ::=  { selectiveCallRejection  3 }

-- Service :: Selective Call Rejection :: SP TABLE ...........................................

  bwSelectiveCallRejectionSPEntry OBJECT-TYPE
    SYNTAX    BwSelectiveCallRejectionSPEntry
    MAX-ACCESS  not-accessible
    STATUS    current
                DESCRIPTION
                        "This row contains the counters for Selective Call Rejection service measurements for a service provider"
    INDEX   {  bwSelectiveCallRejectionSPIndex  }
                ::=  { bwSelectiveCallRejectionSPTable 1 }

        BwSelectiveCallRejectionSPEntry  ::=  SEQUENCE {
                bwSelectiveCallRejectionSPIndex  Unsigned32,
                bwSelectiveCallRejectionSPID  DisplayString,
                bwSCRSPNumRejects  Counter32
                }


  bwSelectiveCallRejectionSPIndex OBJECT-TYPE
    SYNTAX      Unsigned32
    MAX-ACCESS    read-only
    STATUS      current
                DESCRIPTION
                                "This integer represents the a service provider index in the system"
                ::=  {  bwSelectiveCallRejectionSPEntry  1  }


  bwSelectiveCallRejectionSPID  OBJECT-TYPE
    SYNTAX      DisplayString
    MAX-ACCESS    read-only
    STATUS      current
                DESCRIPTION
                                "This string represents a service provider ID"
                ::=  {  bwSelectiveCallRejectionSPEntry  2  }


  bwSCRSPNumRejects OBJECT-TYPE
    SYNTAX      Counter32
    MAX-ACCESS    read-write
    STATUS      current
                DESCRIPTION
                                "This counter reflects the number of times an incoming call meets a criteria for this service by a service provider"
                ::=  {  bwSelectiveCallRejectionSPEntry  3  }

-- Service :: Selective Call Rejection :: GROUP TABLE ...........................................

  bwSelectiveCallRejectionGroupEntry  OBJECT-TYPE
    SYNTAX    BwSelectiveCallRejectionGroupEntry
    MAX-ACCESS  not-accessible
    STATUS    current
                DESCRIPTION
                        "This row contains the counters for Selective Call Rejection service measurements for a group"
    INDEX   {  bwSelectiveCallRejectionGroupIndex  }
                ::=  { bwSelectiveCallRejectionGroupTable 1 }

        BwSelectiveCallRejectionGroupEntry  ::=  SEQUENCE {
                bwSelectiveCallRejectionGroupIndex  Unsigned32,
                bwSelectiveCallRejectionGroupID  DisplayString,
                bwSCRGroupNumRejects  Counter32
                }


  bwSelectiveCallRejectionGroupIndex  OBJECT-TYPE
    SYNTAX      Unsigned32
    MAX-ACCESS    read-only
    STATUS      current
                DESCRIPTION
                                "This integer represents the a group index in the system"
                ::=  {  bwSelectiveCallRejectionGroupEntry  1  }


  bwSelectiveCallRejectionGroupID OBJECT-TYPE
    SYNTAX      DisplayString
    MAX-ACCESS    read-only
    STATUS      current
                DESCRIPTION
                                "This string represents a group ID"
                ::=  {  bwSelectiveCallRejectionGroupEntry  2  }


  bwSCRGroupNumRejects  OBJECT-TYPE
    SYNTAX      Counter32
    MAX-ACCESS    read-write
    STATUS      current
                DESCRIPTION
                                "This counter reflects the number of times an incoming call meets a criteria for this service by a group"
                ::=  {  bwSelectiveCallRejectionGroupEntry  3  }

-- Service :: SIMRING  ...........................................

  bwSimRingPersonalNumAttempts  OBJECT-TYPE
    SYNTAX      Counter32
    MAX-ACCESS    read-write
    STATUS      current
                DESCRIPTION
                                "This counter reflects the number of times an incoming call attempt is received"
                ::=  {  simRingPersonal  1  }

  bwSimRingPersonalNumBusy  OBJECT-TYPE
    SYNTAX      Counter32
    MAX-ACCESS    read-write
    STATUS      current
                DESCRIPTION
                                "This counter reflects the number of times that all parties to whom call delivery attempts
                                are made, are busy"
                ::=  {  simRingPersonal  2  }

  bwSimRingPersonalSPTable  OBJECT-TYPE
    SYNTAX    SEQUENCE  OF  BwSimRingPersonalSPEntry
    MAX-ACCESS  not-accessible
    STATUS    current
                DESCRIPTION
                        "This table contains the counters for Simultaneous Ring Personal service measurements for service providers"
                ::=  { simRingPersonal  3 }

  bwSimRingPersonalGroupTable OBJECT-TYPE
    SYNTAX    SEQUENCE  OF  BwSimRingPersonalGroupEntry
    MAX-ACCESS  not-accessible
    STATUS    current
                DESCRIPTION
                        "This table contains the counters for Simultaneous Ring Personal service measurements for groups"
                ::=  { simRingPersonal  4 }

-- Service :: SIMRING :: SP TABLE ...........................................

  bwSimRingPersonalSPEntry  OBJECT-TYPE
    SYNTAX    BwSimRingPersonalSPEntry
    MAX-ACCESS  not-accessible
    STATUS    current
                DESCRIPTION
                        "This row contains the counters for Simultaneous Ring Personal service measurements for a service provider"
    INDEX   {  bwSimRingPersonalSPIndex  }
                ::=  { bwSimRingPersonalSPTable 1 }

        BwSimRingPersonalSPEntry  ::=  SEQUENCE {
                bwSimRingPersonalSPIndex  Unsigned32,
                bwSimRingPersonalSPID  DisplayString,
                bwSimRingPersonalSPNumAttempts  Counter32,
                bwSimRingPersonalSPNumBusy  Counter32
                }


  bwSimRingPersonalSPIndex  OBJECT-TYPE
    SYNTAX      Unsigned32
    MAX-ACCESS    read-only
    STATUS      current
                DESCRIPTION
                                "This integer represents the a service provider index in the system"
                ::=  {  bwSimRingPersonalSPEntry  1  }


  bwSimRingPersonalSPID OBJECT-TYPE
    SYNTAX      DisplayString
    MAX-ACCESS    read-only
    STATUS      current
                DESCRIPTION
                                "This string represents a service provider ID"
                ::=  {  bwSimRingPersonalSPEntry  2  }


  bwSimRingPersonalSPNumAttempts  OBJECT-TYPE
    SYNTAX      Counter32
    MAX-ACCESS    read-write
    STATUS      current
                DESCRIPTION
                                "This counter reflects the number of times an incoming call attempt is received by a service provider"
                ::=  {  bwSimRingPersonalSPEntry  3  }


  bwSimRingPersonalSPNumBusy  OBJECT-TYPE
    SYNTAX      Counter32
    MAX-ACCESS    read-write
    STATUS      current
                DESCRIPTION
                                "This counter reflects the number of times that all parties to whom call delivery attempts are made by a service provider, are busy"
                ::=  {  bwSimRingPersonalSPEntry  4  }

-- Service :: SIMRING :: GROUP TABLE ...........................................

  bwSimRingPersonalGroupEntry OBJECT-TYPE
    SYNTAX    BwSimRingPersonalGroupEntry
    MAX-ACCESS  not-accessible
    STATUS    current
                DESCRIPTION
                        "This row contains the counters for Simultaneous Ring Personal service measurements for a group"
    INDEX   {  bwSimRingPersonalGroupIndex  }
                ::=  { bwSimRingPersonalGroupTable 1 }

        BwSimRingPersonalGroupEntry  ::=  SEQUENCE {
                bwSimRingPersonalGroupIndex  Unsigned32,
                bwSimRingPersonalGroupID  DisplayString,
                bwSimRingPersonalGroupNumAttempts  Counter32,
                bwSimRingPersonalGroupNumBusy  Counter32
                }


  bwSimRingPersonalGroupIndex OBJECT-TYPE
    SYNTAX      Unsigned32
    MAX-ACCESS    read-only
    STATUS      current
                DESCRIPTION
                                "This integer represents the a group index in the system"
                ::=  {  bwSimRingPersonalGroupEntry  1  }


  bwSimRingPersonalGroupID  OBJECT-TYPE
    SYNTAX      DisplayString
    MAX-ACCESS    read-only
    STATUS      current
                DESCRIPTION
                                "This string represents a group ID"
                ::=  {  bwSimRingPersonalGroupEntry  2  }


  bwSimRingPersonalGroupNumAttempts OBJECT-TYPE
    SYNTAX      Counter32
    MAX-ACCESS    read-write
    STATUS      current
                DESCRIPTION
                                "This counter reflects the number of times an incoming call attempt is received by a group"
                ::=  {  bwSimRingPersonalGroupEntry  3  }


  bwSimRingPersonalGroupNumBusy OBJECT-TYPE
    SYNTAX      Counter32
    MAX-ACCESS    read-write
    STATUS      current
                DESCRIPTION
                                "This counter reflects the number of times that all parties to whom call delivery attempts are made by a group, are busy"
                ::=  {  bwSimRingPersonalGroupEntry  4  }

-- Service :: Voice Messaging  ...........................................

  bwVMNumBusyGreetingsPlayed  OBJECT-TYPE
    SYNTAX      Counter32
    MAX-ACCESS    read-write
    STATUS      current
                DESCRIPTION
                                "This counter reflects the number of times a busy greeting is played to a caller"
                ::=  {  voiceMessaging  1  }

  bwVMNumNoAnswerGreetingsPlayed  OBJECT-TYPE
    SYNTAX      Counter32
    MAX-ACCESS    read-write
    STATUS      current
                DESCRIPTION
                                "This counter reflects the number of times a no answer greeting is played"
                ::=  {  voiceMessaging  2  }

  bwVMNumMessagesLeft OBJECT-TYPE
    SYNTAX      Counter32
    MAX-ACCESS    read-write
    STATUS      current
                DESCRIPTION
                                "This counter reflects the number of times a voice message is recorded"
                ::=  {  voiceMessaging  3  }

  bwVMRNumBusyGreetingsRecorded OBJECT-TYPE
    SYNTAX      Counter32
    MAX-ACCESS    read-write
    STATUS      current
                DESCRIPTION
                                "This counter reflects the number of times a busy greeting is recorded over the phone"
                ::=  {  voiceMessaging  4  }

  bwVMRNumNoAnswerGreetingsRecorded OBJECT-TYPE
    SYNTAX      Counter32
    MAX-ACCESS    read-write
    STATUS      current
                DESCRIPTION
                                "This counter reflects the number of times a no answer greeting is recorded over the
                                phone"
                ::=  {  voiceMessaging  5  }

  bwVMRNumPersonalizedNamesRecorded OBJECT-TYPE
    SYNTAX      Counter32
    MAX-ACCESS    read-write
    STATUS      current
                DESCRIPTION
                                "This counter reflects the number of times a personalized name greeting is recorded
                                over the phone"
                ::=  {  voiceMessaging  6  }

  bwVMRNumLoginAttempts OBJECT-TYPE
    SYNTAX      Counter32
    MAX-ACCESS    read-write
    STATUS      current
                DESCRIPTION
                                "This counter reflects the number of times a user attempts a login over the phone"
                ::=  {  voiceMessaging  7  }

  bwVMRNumLoginFailures OBJECT-TYPE
    SYNTAX      Counter32
    MAX-ACCESS    read-write
    STATUS      current
                DESCRIPTION
                                "This counter reflects the number of times a user login attempt fails"
                ::=  {  voiceMessaging  8  }

  bwVMRNumComposeSendAttempts OBJECT-TYPE
    SYNTAX      Counter32
    MAX-ACCESS    read-write
    STATUS      current
                DESCRIPTION
                                "This counter reflects the number of times a composed message is sent to a user"
                ::=  {  voiceMessaging  9  }

  bwVMRNumComposeSendGroupAttempts  OBJECT-TYPE
    SYNTAX      Counter32
    MAX-ACCESS    read-write
    STATUS      current
                DESCRIPTION
                                "This counter reflects the number of times a composed message is sent to a group"
                ::=  {  voiceMessaging  10  }

  bwVMRNumForwardSendAttempts OBJECT-TYPE
    SYNTAX      Counter32
    MAX-ACCESS    read-write
    STATUS      current
                DESCRIPTION
                                "This counter reflects the number of times a forwarded message is sent to a user"
                ::=  {  voiceMessaging  11  }

  bwVMRNumForwardSendGroupAttempts  OBJECT-TYPE
    SYNTAX      Counter32
    MAX-ACCESS    read-write
    STATUS      current
                DESCRIPTION
                                "This counter reflects the number of times a forwarded message is sent to a group"
                ::=  {  voiceMessaging  12  }

  bwVMRNumReplySendAttempts OBJECT-TYPE
    SYNTAX      Counter32
    MAX-ACCESS    read-write
    STATUS      current
                DESCRIPTION
                                "This counter reflects the number of times a message reply is sent"
                ::=  {  voiceMessaging  13  }

  bwVMRNumSendFailed  OBJECT-TYPE
    SYNTAX      Counter32
    MAX-ACCESS    read-write
    STATUS      current
                DESCRIPTION
                                "This counter reflects the number of times an attempt to send a message to a user failed"
                ::=  {  voiceMessaging  14  }

  bwVMRNumSendGroupFailed OBJECT-TYPE
    SYNTAX      Counter32
    MAX-ACCESS    read-write
    STATUS      current
                DESCRIPTION
                                "This counter reflects the number of times an attempt to send a message to a group failed"
                ::=  {  voiceMessaging  15  }

  bwVMRDeleteAllMsgsAttempts  OBJECT-TYPE
    SYNTAX      Counter32
    MAX-ACCESS    read-write
    STATUS      current
                DESCRIPTION
                                "This counter reflects the number of times a user attempts to delete all messages"
                ::=  {  voiceMessaging  16  }

  bwVMRCallBackAttempts OBJECT-TYPE
    SYNTAX      Counter32
    MAX-ACCESS    read-write
    STATUS      current
                DESCRIPTION
                                "This counter reflects the number of times a user attempts to callback the caller"
                ::=  {  voiceMessaging  17  }

  bwVMRCallBackFailures OBJECT-TYPE
    SYNTAX      Counter32
    MAX-ACCESS    read-write
    STATUS      obsolete
                DESCRIPTION
                                "This counter reflects the number of times an attempt to callback failed.

This object is obsolete. It could not be measure anymore."
                ::=  {  voiceMessaging  18  }

  bwVPNumAABusHoursGreetingRecorded OBJECT-TYPE
    SYNTAX      Counter32
    MAX-ACCESS    read-write
    STATUS      current
                DESCRIPTION
                                "This counter reflects the number of times an AA business hours greeting is recorded over the phone"
                ::=  {  voiceMessaging  19  }

  bwVPNumAAAfterHoursGreetingRecorded OBJECT-TYPE
    SYNTAX      Counter32
    MAX-ACCESS    read-write
    STATUS      current
                DESCRIPTION
                                "This counter reflects the number of times an AA after hours greeting is recorded over the phone"
                ::=  {  voiceMessaging  20  }

  bwVPNumCFADestinationChanged  OBJECT-TYPE
    SYNTAX      Counter32
    MAX-ACCESS    read-write
    STATUS      current
                DESCRIPTION
                                "This counter reflects the number of times a CFA destination is changed over the phone"
                ::=  {  voiceMessaging  21  }

  bwVPNumPasscodeChanged  OBJECT-TYPE
    SYNTAX      Counter32
    MAX-ACCESS    read-write
    STATUS      current
                DESCRIPTION
                                "This counter reflects the number of times a Voice Portal passcode is changed over the phone"
                ::=  {  voiceMessaging  22  }

  bwVoiceMessagingSPTable OBJECT-TYPE
    SYNTAX    SEQUENCE  OF  BwVoiceMessagingSPEntry
    MAX-ACCESS  not-accessible
    STATUS    current
                DESCRIPTION
                        "This table contains the counters for Voice Messaging service measurements for service providers"
                ::=  { voiceMessaging  23 }

  bwVMRNumComposeSendListAttempts OBJECT-TYPE
    SYNTAX      Counter32
    MAX-ACCESS    read-write
    STATUS      current
                DESCRIPTION
                                "This counter reflects the number of times a composed message is sent to a distribution list"
                ::=  {  voiceMessaging  24  }

  bwVMRNumForwardSendListAttempts OBJECT-TYPE
    SYNTAX      Counter32
    MAX-ACCESS    read-write
    STATUS      current
                DESCRIPTION
                                "This counter reflects the number of times a forwarded message is sent to a distribution list"
                ::=  {  voiceMessaging  25  }

  bwVMRNumSendListFailed  OBJECT-TYPE
    SYNTAX      Counter32
    MAX-ACCESS    read-write
    STATUS      current
                DESCRIPTION
                                "This counter reflects the number of times an attempt to send a message to a distribution list has failed (NOT incremented in case of partial failures)"
                ::=  {  voiceMessaging  26  }

  bwVPGreetingRecorded  OBJECT-TYPE
    SYNTAX      Counter32
    MAX-ACCESS    read-write
    STATUS      current
                DESCRIPTION
                                "Number of times a user recorded a branded Voice Portal greeting"
                ::=  {  voiceMessaging  27  }

  bwVMGreetingRecorded  OBJECT-TYPE
    SYNTAX      Counter32
    MAX-ACCESS    read-write
    STATUS      current
                DESCRIPTION
                                "Number of times a user recorded a branded Voice Messaging greeting"
                ::=  {  voiceMessaging  28  }

  bwVoiceMessagingGroupTable  OBJECT-TYPE
    SYNTAX    SEQUENCE  OF  BwVoiceMessagingGroupEntry
    MAX-ACCESS  not-accessible
    STATUS    current
                DESCRIPTION
                        "This table contains the counters for Voice Messaging service measurements for groups"
                ::=  { voiceMessaging  29 }

  bwVPCCall OBJECT-TYPE
    SYNTAX      Counter32
    MAX-ACCESS    read-write
    STATUS      current
                DESCRIPTION
                                "Number of times a user initiated a call with Voice Portal Calling"
                ::=  {  voiceMessaging  30  }

  bwMultiMediaMsgDeposit  OBJECT-TYPE
    SYNTAX      Counter32
    MAX-ACCESS    read-write
    STATUS      current
                DESCRIPTION
                                "Number of times a user has received a multimedia message"
                ::=  {  voiceMessaging  31  }

  bwVMMultiMediaGreetingRecorded  OBJECT-TYPE
    SYNTAX      Counter32
    MAX-ACCESS    read-write
    STATUS      current
                DESCRIPTION
                                "Number of time a user has recorded a multimedia message via the Voice Portal"
                ::=  {  voiceMessaging  32  }

  bwAutoAttendantMultiMediaPromptRecorded OBJECT-TYPE
    SYNTAX      Counter32
    MAX-ACCESS    read-write
    STATUS      current
                DESCRIPTION
                                "Number of times an administrator has recorded an AA prompt via the Voice Portal"
                ::=  {  voiceMessaging  33  }

  bwMessagingQuery  OBJECT-TYPE
    SYNTAX      Counter32
    MAX-ACCESS    read-write
    STATUS      current
                DESCRIPTION
                                "This counter is incremented whenever a request for remote user mailbox information is sent out."
                ::=  {  voiceMessaging  34  }

  bwMessagingQueryNoUser  OBJECT-TYPE
    SYNTAX      Counter32
    MAX-ACCESS    read-write
    STATUS      current
                DESCRIPTION
                                "This counter is incremented whenever a request for remote user mailbox information results in a user not found error."
                ::=  {  voiceMessaging  35  }

  bwMessagingQueryNoMailbox OBJECT-TYPE
    SYNTAX      Counter32
    MAX-ACCESS    read-write
    STATUS      current
                DESCRIPTION
                                "This counter is incremented whenever a request for remote user mailbox information results in an error because the remote mailbox is disabled, full, or not configured."
                ::=  {  voiceMessaging  36  }

-- Service :: Voice Messaging :: SP TABLE ...........................................

  bwVoiceMessagingSPEntry OBJECT-TYPE
    SYNTAX    BwVoiceMessagingSPEntry
    MAX-ACCESS  not-accessible
    STATUS    current
                DESCRIPTION
                        "This row contains the counters for Voice Messaging service measurements for a service provider"
    INDEX   {  bwVoiceMessagingSPIndex  }
                ::=  { bwVoiceMessagingSPTable 1 }

        BwVoiceMessagingSPEntry  ::=  SEQUENCE {
                bwVoiceMessagingSPIndex  Unsigned32,
                bwVoiceMessagingSPID  DisplayString,
                bwVMSPNumBusyGreetingsPlayed  Counter32,
                bwVMSPNumNoAnswerGreetingsPlayed  Counter32,
                bwVMSPNumMessagesLeft  Counter32,
                bwVMRSPNumBusyGreetingsRecorded  Counter32,
                bwVMRSPNumNoAnswerGreetingsRecorded  Counter32,
                bwVMRSPNumPersonalizedNamesRecorded  Counter32,
                bwVMRSPNumLoginAttempts  Counter32,
                bwVMRSPNumLoginFailures  Counter32,
                bwVMRSPNumComposeSendAttempts  Counter32,
                bwVMRSPNumComposeSendGroupAttempts  Counter32,
                bwVMRSPNumForwardSendAttempts  Counter32,
                bwVMRSPNumForwardSendGroupAttempts  Counter32,
                bwVMRSPNumReplySendAttempts  Counter32,
                bwVMRSPNumSendFailed  Counter32,
                bwVMRSPNumSendGroupFailed  Counter32,
                bwVMRSPDeleteAllMsgsAttempts  Counter32,
                bwVMRSPCallBackAttempts  Counter32,
                bwVPSPNumAABusHoursGreetingRecorded  Counter32,
                bwVPSPNumAAAfterHoursGreetingRecorded  Counter32,
                bwVPSPNumCFADestinationChanged  Counter32,
                bwVPSPNumPasscodeChanged  Counter32,
                bwVMRSPNumComposeSendListAttempts  Counter32,
                bwVMRSPNumForwardSendListAttempts  Counter32,
                bwVMRSPNumSendListFailed Counter32,
                bwVPSPGreetingRecorded  Counter32,
                bwVMSPGreetingRecorded  Counter32,
                bwVPCSPCall Counter32,
                bwSPMultiMediaMsgDeposit Counter32,
                bwVMSPMultiMediaGreetingRecorded Counter32,
                bwAutoAttendantSPMultiMediaPromptRecorded Counter32,
                bwMessagingSPQuery Counter32,
                bwMessagingSPQueryNoUser Counter32,
                bwMessagingSPQueryNoMailbox Counter32
                }


  bwVoiceMessagingSPIndex OBJECT-TYPE
    SYNTAX      Unsigned32
    MAX-ACCESS    read-only
    STATUS      current
                DESCRIPTION
                                "This integer represents the a service provider index in the system"
                ::=  {  bwVoiceMessagingSPEntry  1  }


  bwVoiceMessagingSPID  OBJECT-TYPE
    SYNTAX      DisplayString
    MAX-ACCESS    read-only
    STATUS      current
                DESCRIPTION
                                "This string represents a service provider ID"
                ::=  {  bwVoiceMessagingSPEntry  2  }


  bwVMSPNumBusyGreetingsPlayed  OBJECT-TYPE
    SYNTAX      Counter32
    MAX-ACCESS    read-write
    STATUS      current
                DESCRIPTION
                                "This counter reflects the number of times a busy greeting is played to a caller by a service provider"
                ::=  {  bwVoiceMessagingSPEntry  3  }


  bwVMSPNumNoAnswerGreetingsPlayed  OBJECT-TYPE
    SYNTAX      Counter32
    MAX-ACCESS    read-write
    STATUS      current
                DESCRIPTION
                                "This counter reflects the number of times a no answer greeting is played by a service provider"
                ::=  {  bwVoiceMessagingSPEntry  4  }


  bwVMSPNumMessagesLeft OBJECT-TYPE
    SYNTAX      Counter32
    MAX-ACCESS    read-write
    STATUS      current
                DESCRIPTION
                                "This counter reflects the number of times a voice message is recorded by a service provider"
                ::=  {  bwVoiceMessagingSPEntry  5  }


  bwVMRSPNumBusyGreetingsRecorded OBJECT-TYPE
    SYNTAX      Counter32
    MAX-ACCESS    read-write
    STATUS      current
                DESCRIPTION
                                "This counter reflects the number of times a busy greeting is recorded over the phone by a service provider"
                ::=  {  bwVoiceMessagingSPEntry  6  }


  bwVMRSPNumNoAnswerGreetingsRecorded OBJECT-TYPE
    SYNTAX      Counter32
    MAX-ACCESS    read-write
    STATUS      current
                DESCRIPTION
                                "This counter reflects the number of times a no answer greeting is recorded over the phone by a service provider"
                ::=  {  bwVoiceMessagingSPEntry  7  }


  bwVMRSPNumPersonalizedNamesRecorded OBJECT-TYPE
    SYNTAX      Counter32
    MAX-ACCESS    read-write
    STATUS      current
                DESCRIPTION
                                "This counter reflects the number of times a personalized name greeting is recorded over the phone by a service provider"
                ::=  {  bwVoiceMessagingSPEntry  8  }


  bwVMRSPNumLoginAttempts OBJECT-TYPE
    SYNTAX      Counter32
    MAX-ACCESS    read-write
    STATUS      current
                DESCRIPTION
                                "This counter reflects the number of times a user attempts a login over the phone by a service provider"
                ::=  {  bwVoiceMessagingSPEntry  9  }


  bwVMRSPNumLoginFailures OBJECT-TYPE
    SYNTAX      Counter32
    MAX-ACCESS    read-write
    STATUS      current
                DESCRIPTION
                                "This counter reflects the number of times a user login attempt fails by a service provider"
                ::=  {  bwVoiceMessagingSPEntry  10  }


  bwVMRSPNumComposeSendAttempts OBJECT-TYPE
    SYNTAX      Counter32
    MAX-ACCESS    read-write
    STATUS      current
                DESCRIPTION
                                "This counter reflects the number of times a composed message is sent to a user by a service provider"
                ::=  {  bwVoiceMessagingSPEntry  11  }


  bwVMRSPNumComposeSendGroupAttempts  OBJECT-TYPE
    SYNTAX      Counter32
    MAX-ACCESS    read-write
    STATUS      current
                DESCRIPTION
                                "This counter reflects the number of times a composed message is sent to a group by a service provider"
                ::=  {  bwVoiceMessagingSPEntry  12  }


  bwVMRSPNumForwardSendAttempts OBJECT-TYPE
    SYNTAX      Counter32
    MAX-ACCESS    read-write
    STATUS      current
                DESCRIPTION
                                "This counter reflects the number of times a forwarded message is sent to a user by a service provider"
                ::=  {  bwVoiceMessagingSPEntry  13  }


  bwVMRSPNumForwardSendGroupAttempts  OBJECT-TYPE
    SYNTAX      Counter32
    MAX-ACCESS    read-write
    STATUS      current
                DESCRIPTION
                                "This counter reflects the number of times a forwarded message is sent to a group by a service provider"
                ::=  {  bwVoiceMessagingSPEntry  14  }


  bwVMRSPNumReplySendAttempts OBJECT-TYPE
    SYNTAX      Counter32
    MAX-ACCESS    read-write
    STATUS      current
                DESCRIPTION
                                "This counter reflects the number of times a message reply is sent by a service provider"
                ::=  {  bwVoiceMessagingSPEntry  15  }


  bwVMRSPNumSendFailed  OBJECT-TYPE
    SYNTAX      Counter32
    MAX-ACCESS    read-write
    STATUS      current
                DESCRIPTION
                                "This counter reflects the number of times an attempt to send a message to a user failed by a service provider"
                ::=  {  bwVoiceMessagingSPEntry  16  }


  bwVMRSPNumSendGroupFailed OBJECT-TYPE
    SYNTAX      Counter32
    MAX-ACCESS    read-write
    STATUS      current
                DESCRIPTION
                                "This counter reflects the number of times an attempt to send a message to a group failed by a service provider"
                ::=  {  bwVoiceMessagingSPEntry  17  }


  bwVMRSPDeleteAllMsgsAttempts  OBJECT-TYPE
    SYNTAX      Counter32
    MAX-ACCESS    read-write
    STATUS      current
                DESCRIPTION
                                "This counter reflects the number of times a user attempts to delete all messages by a service provider"
                ::=  {  bwVoiceMessagingSPEntry  18  }


  bwVMRSPCallBackAttempts OBJECT-TYPE
    SYNTAX      Counter32
    MAX-ACCESS    read-write
    STATUS      current
                DESCRIPTION
                                "This counter reflects the number of times a user attempts to callback the caller by a service provider"
                ::=  {  bwVoiceMessagingSPEntry  19  }


  bwVMRSPCallBackFailures OBJECT-TYPE
    SYNTAX      Counter32
    MAX-ACCESS    read-write
    STATUS      obsolete
                DESCRIPTION
                                "This counter reflects the number of times an attempt to callback failed by a service provider.

This object is obsolete. It could not be measure anymore."
                ::=  {  bwVoiceMessagingSPEntry  20  }

  bwVPSPNumAABusHoursGreetingRecorded OBJECT-TYPE
    SYNTAX      Counter32
    MAX-ACCESS    read-write
    STATUS      current
                DESCRIPTION
                                "This counter reflects the number of times an AA business hours greeting is recorded over the phone by a service provider"
                ::=  {  bwVoiceMessagingSPEntry  21  }

  bwVPSPNumAAAfterHoursGreetingRecorded OBJECT-TYPE
    SYNTAX      Counter32
    MAX-ACCESS    read-write
    STATUS      current
                DESCRIPTION
                                "This counter reflects the number of times an AA after hours greeting is recorded over the phone by a service provider"
                ::=  {  bwVoiceMessagingSPEntry  22  }

  bwVPSPNumCFADestinationChanged  OBJECT-TYPE
    SYNTAX      Counter32
    MAX-ACCESS    read-write
    STATUS      current
                DESCRIPTION
                                "This counter reflects the number of times a CFA destination is changed over the phone by a service provider"
                ::=  {  bwVoiceMessagingSPEntry  23  }

  bwVPSPNumPasscodeChanged  OBJECT-TYPE
    SYNTAX      Counter32
    MAX-ACCESS    read-write
    STATUS      current
                DESCRIPTION
                                "This counter reflects the number of times a Voice Portal is changed over the phone by a service provider"
                ::=  {  bwVoiceMessagingSPEntry  24  }

  bwVMRSPNumComposeSendListAttempts OBJECT-TYPE
    SYNTAX      Counter32
    MAX-ACCESS    read-write
    STATUS      current
                DESCRIPTION
                                "This counter reflects the number of times a composed message is sent to a distribution list by a service provider"
                ::=  {  bwVoiceMessagingSPEntry  25  }

  bwVMRSPNumForwardSendListAttempts OBJECT-TYPE
    SYNTAX      Counter32
    MAX-ACCESS    read-write
    STATUS      current
                DESCRIPTION
                                "This counter reflects the number of times a forwarded message is sent to a distribution list by a service provider"
                ::=  {  bwVoiceMessagingSPEntry  26  }

  bwVMRSPNumSendListFailed  OBJECT-TYPE
    SYNTAX      Counter32
    MAX-ACCESS    read-write
    STATUS      current
                DESCRIPTION
                                "This counter reflects the number of times an attempt to send a message to a distribution list failed for a service provider (NOT incremented in case of partial failures)"
                ::=  {  bwVoiceMessagingSPEntry  27  }

  bwVPSPGreetingRecorded  OBJECT-TYPE
    SYNTAX      Counter32
    MAX-ACCESS    read-write
    STATUS      current
                DESCRIPTION
                                "Number of times a user recorded a branded Voice Messaging greeting for a given service provider"
                ::=  {  bwVoiceMessagingSPEntry  28  }

  bwVMSPGreetingRecorded  OBJECT-TYPE
    SYNTAX      Counter32
    MAX-ACCESS    read-write
    STATUS      current
                DESCRIPTION
                                "Number of times a user recorded a branded Voice Portal greeting for a given service provider"
                ::=  {  bwVoiceMessagingSPEntry  29  }

  bwVPCSPCall OBJECT-TYPE
    SYNTAX      Counter32
    MAX-ACCESS    read-write
    STATUS      current
                DESCRIPTION
                                "Number of times a user from a specific service provider initiated a call with Voice Portal Calling"
                ::=  {  bwVoiceMessagingSPEntry  30  }

  bwSPMultiMediaMsgDeposit  OBJECT-TYPE
    SYNTAX      Counter32
    MAX-ACCESS    read-write
    STATUS      current
                DESCRIPTION
                                "Number of times a user has received a multimedia message for a given service provider"
                ::=  {  bwVoiceMessagingSPEntry  31  }

  bwVMSPMultiMediaGreetingRecorded  OBJECT-TYPE
    SYNTAX      Counter32
    MAX-ACCESS    read-write
    STATUS      current
                DESCRIPTION
                                "Number of time a user has recorded a multimedia message via the Voice Portal for a given service provider"
                ::=  {  bwVoiceMessagingSPEntry  32  }

  bwAutoAttendantSPMultiMediaPromptRecorded OBJECT-TYPE
    SYNTAX      Counter32
    MAX-ACCESS    read-write
    STATUS      current
                DESCRIPTION
                                "Number of times an administrator has recorded an AA prompt via the Voice Portal for a given service provider"
                ::=  {  bwVoiceMessagingSPEntry  33  }

  bwMessagingSPQuery  OBJECT-TYPE
    SYNTAX      Counter32
    MAX-ACCESS    read-write
    STATUS      current
                DESCRIPTION
                                "This counter is incremented whenever a request for remote user mailbox information is sent out for a given service provider."
                ::=  {  bwVoiceMessagingSPEntry  34  }

  bwMessagingSPQueryNoUser  OBJECT-TYPE
    SYNTAX      Counter32
    MAX-ACCESS    read-write
    STATUS      current
                DESCRIPTION
                                "This counter is incremented whenever a request for remote user mailbox information results in a user not found error for a given service provider."
                ::=  {  bwVoiceMessagingSPEntry  35  }

  bwMessagingSPQueryNoMailbox OBJECT-TYPE
    SYNTAX      Counter32
    MAX-ACCESS    read-write
    STATUS      current
                DESCRIPTION
                                "This counter is incremented whenever a request for remote user mailbox information results in an error because the remote mailbox is disabled, full, or not configured for a given service provider."
                ::=  {  bwVoiceMessagingSPEntry  36  }

-- Service :: Voice Messaging :: GROUP TABLE ...........................................

  bwVoiceMessagingGroupEntry  OBJECT-TYPE
    SYNTAX    BwVoiceMessagingGroupEntry
    MAX-ACCESS  not-accessible
    STATUS    current
                DESCRIPTION
                        "This row contains the counters for Voice Messaging service measurements for a group"
    INDEX   {  bwVoiceMessagingGroupIndex  }
                ::=  { bwVoiceMessagingGroupTable 1 }

        BwVoiceMessagingGroupEntry  ::=  SEQUENCE {
                bwVoiceMessagingGroupIndex  Unsigned32,
                bwVoiceMessagingGroupID  DisplayString,
                bwVMGroupNumBusyGreetingsPlayed  Counter32,
                bwVMGroupNumNoAnswerGreetingsPlayed  Counter32,
                bwVMGroupNumMessagesLeft  Counter32,
                bwVMRGroupNumBusyGreetingsRecorded  Counter32,
                bwVMRGroupNumNoAnswerGreetingsRecorded  Counter32,
                bwVMRGroupNumPersonalizedNamesRecorded  Counter32,
                bwVMRGroupNumLoginAttempts  Counter32,
                bwVMRGroupNumLoginFailures  Counter32,
                bwVMRGroupNumComposeSendAttempts  Counter32,
                bwVMRGroupNumComposeSendGroupAttempts  Counter32,
                bwVMRGroupNumForwardSendAttempts  Counter32,
                bwVMRGroupNumForwardSendGroupAttempts  Counter32,
                bwVMRGroupNumReplySendAttempts  Counter32,
                bwVMRGroupNumSendFailed  Counter32,
                bwVMRGroupNumSendGroupFailed  Counter32,
                bwVMRGroupDeleteAllMsgsAttempts  Counter32,
                bwVMRGroupCallBackAttempts  Counter32,
                bwVMRGroupCallBackFailures  Counter32,
                bwVPGroupNumAABusHoursGreetingRecorded  Counter32,
                bwVPGroupNumAAAfterHoursGreetingRecorded  Counter32,
                bwVPGroupNumCFADestinationChanged  Counter32,
                bwVPGroupNumPasscodeChanged  Counter32,
                bwVMRGroupNumComposeSendListAttempts  Counter32,
                bwVMRGroupNumForwardSendListAttempts  Counter32,
                bwVMRGroupNumSendListFailed Counter32,
                bwVPGroupGreetingRecorded  Counter32,
                bwVMGroupGreetingRecorded  Counter32,
                bwVPCGroupCall Counter32,
                bwGroupMultiMediaMsgDeposit Counter32,
                bwVMGroupMultiMediaGreetingRecorded Counter32,
                bwAutoAttendantGroupMultiMediaPromptRecorded Counter32,
                bwMessagingGroupQuery Counter32,
                bwMessagingGroupQueryNoUser Counter32,
                bwMessagingGroupQueryNoMailbox Counter32
                }


  bwVoiceMessagingGroupIndex  OBJECT-TYPE
    SYNTAX      Unsigned32
    MAX-ACCESS    read-only
    STATUS      current
                DESCRIPTION
                                "This integer represents the a group index in the system"
                ::=  {  bwVoiceMessagingGroupEntry  1  }


  bwVoiceMessagingGroupID OBJECT-TYPE
    SYNTAX      DisplayString
    MAX-ACCESS    read-only
    STATUS      current
                DESCRIPTION
                                "This string represents a group ID"
                ::=  {  bwVoiceMessagingGroupEntry  2  }


  bwVMGroupNumBusyGreetingsPlayed OBJECT-TYPE
    SYNTAX      Counter32
    MAX-ACCESS    read-write
    STATUS      current
                DESCRIPTION
                                "This counter reflects the number of times a busy greeting is played to a caller by a group"
                ::=  {  bwVoiceMessagingGroupEntry  3  }


  bwVMGroupNumNoAnswerGreetingsPlayed OBJECT-TYPE
    SYNTAX      Counter32
    MAX-ACCESS    read-write
    STATUS      current
                DESCRIPTION
                                "This counter reflects the number of times a no answer greeting is played by a group"
                ::=  {  bwVoiceMessagingGroupEntry  4  }


  bwVMGroupNumMessagesLeft  OBJECT-TYPE
    SYNTAX      Counter32
    MAX-ACCESS    read-write
    STATUS      current
                DESCRIPTION
                                "This counter reflects the number of times a voice message is recorded by a group"
                ::=  {  bwVoiceMessagingGroupEntry  5  }


  bwVMRGroupNumBusyGreetingsRecorded  OBJECT-TYPE
    SYNTAX      Counter32
    MAX-ACCESS    read-write
    STATUS      current
                DESCRIPTION
                                "This counter reflects the number of times a busy greeting is recorded over the phone by a group"
                ::=  {  bwVoiceMessagingGroupEntry  6  }


  bwVMRGroupNumNoAnswerGreetingsRecorded  OBJECT-TYPE
    SYNTAX      Counter32
    MAX-ACCESS    read-write
    STATUS      current
                DESCRIPTION
                                "This counter reflects the number of times a no answer greeting is recorded over the phone by a group"
                ::=  {  bwVoiceMessagingGroupEntry  7  }


  bwVMRGroupNumPersonalizedNamesRecorded  OBJECT-TYPE
    SYNTAX      Counter32
    MAX-ACCESS    read-write
    STATUS      current
                DESCRIPTION
                                "This counter reflects the number of times a personalized name greeting is recorded over the phone by a group"
                ::=  {  bwVoiceMessagingGroupEntry  8  }


  bwVMRGroupNumLoginAttempts  OBJECT-TYPE
    SYNTAX      Counter32
    MAX-ACCESS    read-write
    STATUS      current
                DESCRIPTION
                                "This counter reflects the number of times a user attempts a login over the phone by a group"
                ::=  {  bwVoiceMessagingGroupEntry  9  }


  bwVMRGroupNumLoginFailures  OBJECT-TYPE
    SYNTAX      Counter32
    MAX-ACCESS    read-write
    STATUS      current
                DESCRIPTION
                                "This counter reflects the number of times a user login attempt fails by a group"
                ::=  {  bwVoiceMessagingGroupEntry  10  }


  bwVMRGroupNumComposeSendAttempts  OBJECT-TYPE
    SYNTAX      Counter32
    MAX-ACCESS    read-write
    STATUS      current
                DESCRIPTION
                                "This counter reflects the number of times a composed message is sent to a user by a group"
                ::=  {  bwVoiceMessagingGroupEntry  11  }


  bwVMRGroupNumComposeSendGroupAttempts OBJECT-TYPE
    SYNTAX      Counter32
    MAX-ACCESS    read-write
    STATUS      current
                DESCRIPTION
                                "This counter reflects the number of times a composed message is sent to a group by a group"
                ::=  {  bwVoiceMessagingGroupEntry  12  }


  bwVMRGroupNumForwardSendAttempts  OBJECT-TYPE
    SYNTAX      Counter32
    MAX-ACCESS    read-write
    STATUS      current
                DESCRIPTION
                                "This counter reflects the number of times a forwarded message is sent to a user by a group"
                ::=  {  bwVoiceMessagingGroupEntry  13  }


  bwVMRGroupNumForwardSendGroupAttempts OBJECT-TYPE
    SYNTAX      Counter32
    MAX-ACCESS    read-write
    STATUS      current
                DESCRIPTION
                                "This counter reflects the number of times a forwarded message is sent to a group by a group"
                ::=  {  bwVoiceMessagingGroupEntry  14  }


  bwVMRGroupNumReplySendAttempts  OBJECT-TYPE
    SYNTAX      Counter32
    MAX-ACCESS    read-write
    STATUS      current
                DESCRIPTION
                                "This counter reflects the number of times a message reply is sent by a group"
                ::=  {  bwVoiceMessagingGroupEntry  15  }


  bwVMRGroupNumSendFailed OBJECT-TYPE
    SYNTAX      Counter32
    MAX-ACCESS    read-write
    STATUS      current
                DESCRIPTION
                                "This counter reflects the number of times an attempt to send a message to a user failed by a group"
                ::=  {  bwVoiceMessagingGroupEntry  16  }


  bwVMRGroupNumSendGroupFailed  OBJECT-TYPE
    SYNTAX      Counter32
    MAX-ACCESS    read-write
    STATUS      current
                DESCRIPTION
                                "This counter reflects the number of times an attempt to send a message to a group failed by a group"
                ::=  {  bwVoiceMessagingGroupEntry  17  }


  bwVMRGroupDeleteAllMsgsAttempts OBJECT-TYPE
    SYNTAX      Counter32
    MAX-ACCESS    read-write
    STATUS      current
                DESCRIPTION
                                "This counter reflects the number of times a user attempts to delete all messages by a group"
                ::=  {  bwVoiceMessagingGroupEntry  18  }


  bwVMRGroupCallBackAttempts  OBJECT-TYPE
    SYNTAX      Counter32
    MAX-ACCESS    read-write
    STATUS      current
                DESCRIPTION
                                "This counter reflects the number of times a user attempts to callback the caller by a group"
                ::=  {  bwVoiceMessagingGroupEntry  19  }


  bwVMRGroupCallBackFailures  OBJECT-TYPE
    SYNTAX      Counter32
    MAX-ACCESS    read-write
    STATUS      obsolete
                DESCRIPTION
                                "This counter reflects the number of times an attempt to callback failed by a group.

This object is obsolete. It could not be measure anymore."
                ::=  {  bwVoiceMessagingGroupEntry  20  }

  bwVPGroupNumAABusHoursGreetingRecorded  OBJECT-TYPE
    SYNTAX      Counter32
    MAX-ACCESS    read-write
    STATUS      current
                DESCRIPTION
                                "This counter reflects the number of times an AA business hours greeting is recorded over the phone by a group"
                ::=  {  bwVoiceMessagingGroupEntry  21  }

  bwVPGroupNumAAAfterHoursGreetingRecorded  OBJECT-TYPE
    SYNTAX      Counter32
    MAX-ACCESS    read-write
    STATUS      current
                DESCRIPTION
                                "This counter reflects the number of times an AA after hours greeting is recorded over the phone by a group"
                ::=  {  bwVoiceMessagingGroupEntry  22  }

  bwVPGroupNumCFADestinationChanged OBJECT-TYPE
    SYNTAX      Counter32
    MAX-ACCESS    read-write
    STATUS      current
                DESCRIPTION
                                "This counter reflects the number of times a CFA destination is changed over the phone by a group"
                ::=  {  bwVoiceMessagingGroupEntry  23  }

  bwVPGroupNumPasscodeChanged OBJECT-TYPE
    SYNTAX      Counter32
    MAX-ACCESS    read-write
    STATUS      current
                DESCRIPTION
                                "This counter reflects the number of times a Voice Portal is changed over the phone by a group"
                ::=  {  bwVoiceMessagingGroupEntry  24  }

  bwVMRGroupNumComposeSendListAttempts  OBJECT-TYPE
    SYNTAX      Counter32
    MAX-ACCESS    read-write
    STATUS      current
                DESCRIPTION
                                "This counter reflects the number of times a composed message is sent to a distribution list by a group"
                ::=  {  bwVoiceMessagingGroupEntry  25  }

  bwVMRGroupNumForwardSendListAttempts  OBJECT-TYPE
    SYNTAX      Counter32
    MAX-ACCESS    read-write
    STATUS      current
                DESCRIPTION
                                "This counter reflects the number of times a forwarded message is sent to a distribution list by a group"
                ::=  {  bwVoiceMessagingGroupEntry  26  }

  bwVMRGroupNumSendListFailed OBJECT-TYPE
    SYNTAX      Counter32
    MAX-ACCESS    read-write
    STATUS      current
                DESCRIPTION
                                "This counter reflects the number of times an attempt to send a message to a distribution list failed for a group (NOT incremented in case of partial failures)"
                ::=  {  bwVoiceMessagingGroupEntry  27  }

  bwVPGroupGreetingRecorded OBJECT-TYPE
    SYNTAX      Counter32
    MAX-ACCESS    read-write
    STATUS      current
                DESCRIPTION
                                "Number of times a user recorded a branded Voice Messaging greeting for a given group"
                ::=  {  bwVoiceMessagingGroupEntry  28  }

  bwVMGroupGreetingRecorded OBJECT-TYPE
    SYNTAX      Counter32
    MAX-ACCESS    read-write
    STATUS      current
                DESCRIPTION
                                "Number of times a user recorded a branded Voice Portal greeting for a given group"
                ::=  {  bwVoiceMessagingGroupEntry  29  }

  bwVPCGroupCall  OBJECT-TYPE
    SYNTAX      Counter32
    MAX-ACCESS    read-write
    STATUS      current
                DESCRIPTION
                                "Number of times a user from a specific group initiated a call with Voice Portal Calling"
                ::=  {  bwVoiceMessagingGroupEntry  30  }

  bwGroupMultiMediaMsgDeposit OBJECT-TYPE
    SYNTAX      Counter32
    MAX-ACCESS    read-write
    STATUS      current
                DESCRIPTION
                                "Number of times a user has received a multimedia message for a given group"
                ::=  {  bwVoiceMessagingGroupEntry  31  }

  bwVMGroupMultiMediaGreetingRecorded OBJECT-TYPE
    SYNTAX      Counter32
    MAX-ACCESS    read-write
    STATUS      current
                DESCRIPTION
                                "Number of time a user has recorded a multimedia message via the Voice Portal for a given group"
                ::=  {  bwVoiceMessagingGroupEntry  32  }

  bwAutoAttendantGroupMultiMediaPromptRecorded  OBJECT-TYPE
    SYNTAX      Counter32
    MAX-ACCESS    read-write
    STATUS      current
                DESCRIPTION
                                "Number of times an administrator has recorded an AA prompt via the Voice Portal for a given group"
                ::=  {  bwVoiceMessagingGroupEntry  33  }

  bwMessagingGroupQuery OBJECT-TYPE
    SYNTAX      Counter32
    MAX-ACCESS    read-write
    STATUS      current
                DESCRIPTION
                                "This counter is incremented whenever a request for remote user mailbox information is sent out for a given service provider."
                ::=  {  bwVoiceMessagingGroupEntry  34  }

  bwMessagingGroupQueryNoUser OBJECT-TYPE
    SYNTAX      Counter32
    MAX-ACCESS    read-write
    STATUS      current
                DESCRIPTION
                                "This counter is incremented whenever a request for remote user mailbox information results in a user not found error for a given service provider."
                ::=  {  bwVoiceMessagingGroupEntry  35  }

  bwMessagingGroupQueryNoMailbox  OBJECT-TYPE
    SYNTAX      Counter32
    MAX-ACCESS    read-write
    STATUS      current
                DESCRIPTION
                                "This counter is incremented whenever a request for remote user mailbox information results in an error because the remote mailbox is disabled, full, or not configured for a given service provider."
                ::=  {  bwVoiceMessagingGroupEntry  36  }

-- Service :: Series Completion  ...........................................

  bwSeriesCompletionNumAttempts OBJECT-TYPE
    SYNTAX      Counter32
    MAX-ACCESS    read-write
    STATUS      current
                DESCRIPTION
                                "incremented whenever the series completion service forwards a call to the next user in the list"
                ::=  {  seriesCompletion  1  }

  bwSeriesCompletionNumBusy OBJECT-TYPE
    SYNTAX      Counter32
    MAX-ACCESS    read-write
    STATUS      current
                DESCRIPTION
                                "incremented whenever the series completion service reaches the end of the forwarding list, and no users are available"
                ::=  {  seriesCompletion  2  }

  bwSeriesCompletionSPTable OBJECT-TYPE
    SYNTAX    SEQUENCE  OF  BwSeriesCompletionSPEntry
    MAX-ACCESS  not-accessible
    STATUS    current
                DESCRIPTION
                        "This table contains the counters for Series Completion service measurements for service providers"
                ::=  { seriesCompletion  3 }

  bwSeriesCompletionGroupTable  OBJECT-TYPE
    SYNTAX    SEQUENCE  OF  BwSeriesCompletionGroupEntry
    MAX-ACCESS  not-accessible
    STATUS    current
                DESCRIPTION
                        "This table contains the counters for Series Completion service measurements for groups"
                ::=  { seriesCompletion  4 }

-- Service :: Series Completion :: SP TABLE ...........................................

  bwSeriesCompletionSPEntry OBJECT-TYPE
    SYNTAX    BwSeriesCompletionSPEntry
    MAX-ACCESS  not-accessible
    STATUS    current
                DESCRIPTION
                        "This row contains the counters for Series Completion service measurements for a service provider"
    INDEX   {  bwSeriesCompletionSPIndex  }
                ::=  { bwSeriesCompletionSPTable 1 }

        BwSeriesCompletionSPEntry  ::=  SEQUENCE {
                bwSeriesCompletionSPIndex  Unsigned32,
                bwSeriesCompletionSPID  DisplayString,
                bwSeriesCompletionSPNumAttempts  Counter32,
                bwSeriesCompletionSPNumBusy  Counter32
                }


  bwSeriesCompletionSPIndex OBJECT-TYPE
    SYNTAX      Unsigned32
    MAX-ACCESS    read-only
    STATUS      current
                DESCRIPTION
                                "This integer represents the a service provider index in the system"
                ::=  {  bwSeriesCompletionSPEntry  1  }


  bwSeriesCompletionSPID  OBJECT-TYPE
    SYNTAX      DisplayString
    MAX-ACCESS    read-only
    STATUS      current
                DESCRIPTION
                                "This string represents a service provider ID"
                ::=  {  bwSeriesCompletionSPEntry  2  }


  bwSeriesCompletionSPNumAttempts OBJECT-TYPE
    SYNTAX      Counter32
    MAX-ACCESS    read-write
    STATUS      current
                DESCRIPTION
                                "This counter reflects the number of times the series completion service forwards a call to the next user in the list by a service provider"
                ::=  {  bwSeriesCompletionSPEntry  3  }


  bwSeriesCompletionSPNumBusy OBJECT-TYPE
    SYNTAX      Counter32
    MAX-ACCESS    read-write
    STATUS      current
                DESCRIPTION
                                "This counter reflects the number of times the series completion service reaches the end of the forwarding list, and no users are available by a service provider"
                ::=  {  bwSeriesCompletionSPEntry  4  }

-- Service :: Series Completion :: GROUP TABLE ...........................................

  bwSeriesCompletionGroupEntry  OBJECT-TYPE
    SYNTAX    BwSeriesCompletionGroupEntry
    MAX-ACCESS  not-accessible
    STATUS    current
                DESCRIPTION
                        "This row contains the counters for Series Completion service measurements for a group"
    INDEX   {  bwSeriesCompletionGroupIndex  }
                ::=  { bwSeriesCompletionGroupTable 1 }

        BwSeriesCompletionGroupEntry  ::=  SEQUENCE {
                bwSeriesCompletionGroupIndex  Unsigned32,
                bwSeriesCompletionGroupID  DisplayString,
                bwSeriesCompletionGroupNumAttempts  Counter32,
                bwSeriesCompletionGroupNumBusy  Counter32
                }


  bwSeriesCompletionGroupIndex  OBJECT-TYPE
    SYNTAX      Unsigned32
    MAX-ACCESS    read-only
    STATUS      current
                DESCRIPTION
                                "This integer represents the a group index in the system"
                ::=  {  bwSeriesCompletionGroupEntry  1  }


  bwSeriesCompletionGroupID OBJECT-TYPE
    SYNTAX      DisplayString
    MAX-ACCESS    read-only
    STATUS      current
                DESCRIPTION
                                "This string represents a group ID"
                ::=  {  bwSeriesCompletionGroupEntry  2  }


  bwSeriesCompletionGroupNumAttempts  OBJECT-TYPE
    SYNTAX      Counter32
    MAX-ACCESS    read-write
    STATUS      current
                DESCRIPTION
                                "This counter reflects the number of times the series completion service forwards a call to the next user in the list by a group"
                ::=  {  bwSeriesCompletionGroupEntry  3  }


  bwSeriesCompletionGroupNumBusy  OBJECT-TYPE
    SYNTAX      Counter32
    MAX-ACCESS    read-write
    STATUS      current
                DESCRIPTION
                                "This counter reflects the number of times the series completion service reaches the end of the forwarding list, and no users are available by a group"
                ::=  {  bwSeriesCompletionGroupEntry  4  }

-- Service :: Intercept  ...........................................

  bwInterceptUserOriginationInvocations OBJECT-TYPE
    SYNTAX      Counter32
    MAX-ACCESS    read-write
    STATUS      current
                DESCRIPTION
                                "incremented whenever the intercept user service blocks an originating call"
                ::=  {  intercept  1  }

  bwInterceptGroupOriginationInvocations  OBJECT-TYPE
    SYNTAX      Counter32
    MAX-ACCESS    read-write
    STATUS      current
                DESCRIPTION
                                "incremented whenever the intercept group service blocks an originating call"
                ::=  {  intercept  2  }

  bwInterceptUserTerminationInvocations OBJECT-TYPE
    SYNTAX      Counter32
    MAX-ACCESS    read-write
    STATUS      current
                DESCRIPTION
                                "incremented whenever the intercept user service blocks a terminating call"
                ::=  {  intercept  3  }

  bwInterceptGroupTerminationInvocations  OBJECT-TYPE
    SYNTAX      Counter32
    MAX-ACCESS    read-write
    STATUS      current
                DESCRIPTION
                                "incremented whenever the intercept group service blocks a terminating call"
                ::=  {  intercept  4  }

  bwInterceptTransfers  OBJECT-TYPE
    SYNTAX      Counter32
    MAX-ACCESS    read-write
    STATUS      current
                DESCRIPTION
                                "incremented whenever the intercept service transfers a call"
                ::=  {  intercept  5  }

  bwInterceptSPTable  OBJECT-TYPE
    SYNTAX    SEQUENCE  OF  BwInterceptSPEntry
    MAX-ACCESS  not-accessible
    STATUS    current
                DESCRIPTION
                        "This table contains the counters for Intercept service measurements for service providers"
                ::=  { intercept  6 }

  bwInterceptGroupTable OBJECT-TYPE
    SYNTAX    SEQUENCE  OF  BwInterceptGroupEntry
    MAX-ACCESS  not-accessible
    STATUS    current
                DESCRIPTION
                        "This table contains the counters for Intercept service measurements for groups"
                ::=  { intercept  7 }

-- Service :: Intercept :: SP TABLE ...........................................

  bwInterceptSPEntry  OBJECT-TYPE
    SYNTAX    BwInterceptSPEntry
    MAX-ACCESS  not-accessible
    STATUS    current
                DESCRIPTION
                        "This row contains the counters for Intercept service measurements for a service provider"
    INDEX   {  bwInterceptSPIndex  }
                ::=  { bwInterceptSPTable 1 }

        BwInterceptSPEntry  ::=  SEQUENCE {
                bwInterceptSPIndex  Unsigned32,
                bwInterceptSPID  DisplayString,
                bwInterceptSPUserOriginationInvocations  Counter32,
                bwInterceptSPGroupOriginationInvocations  Counter32,
                bwInterceptSPUserTerminationInvocations  Counter32,
                bwInterceptSPGroupTerminationInvocations  Counter32,
                bwInterceptSPTransfers  Counter32
                }


  bwInterceptSPIndex  OBJECT-TYPE
    SYNTAX      Unsigned32
    MAX-ACCESS    read-only
    STATUS      current
                DESCRIPTION
                                "This integer represents the a service provider index in the system"
                ::=  {  bwInterceptSPEntry  1  }


  bwInterceptSPID OBJECT-TYPE
    SYNTAX      DisplayString
    MAX-ACCESS    read-only
    STATUS      current
                DESCRIPTION
                                "This string represents a service provider ID"
                ::=  {  bwInterceptSPEntry  2  }


  bwInterceptSPUserOriginationInvocations OBJECT-TYPE
    SYNTAX      Counter32
    MAX-ACCESS    read-write
    STATUS      current
                DESCRIPTION
                                "This counter reflects the number of times the intercept user service blocks an originating call by a service provider"
                ::=  {  bwInterceptSPEntry  3  }


  bwInterceptSPGroupOriginationInvocations  OBJECT-TYPE
    SYNTAX      Counter32
    MAX-ACCESS    read-write
    STATUS      current
                DESCRIPTION
                                "This counter reflects the number of times the intercept group service blocks an originating call by a service provider"
                ::=  {  bwInterceptSPEntry  4  }


  bwInterceptSPUserTerminationInvocations OBJECT-TYPE
    SYNTAX      Counter32
    MAX-ACCESS    read-write
    STATUS      current
                DESCRIPTION
                                "This counter reflects the number of times the intercept user service blocks a terminating call by a service provider"
                ::=  {  bwInterceptSPEntry  5  }


  bwInterceptSPGroupTerminationInvocations  OBJECT-TYPE
    SYNTAX      Counter32
    MAX-ACCESS    read-write
    STATUS      current
                DESCRIPTION
                                "This counter reflects the number of times the intercept group service blocks a terminating call by a service provider"
                ::=  {  bwInterceptSPEntry  6  }


  bwInterceptSPTransfers  OBJECT-TYPE
    SYNTAX      Counter32
    MAX-ACCESS    read-write
    STATUS      current
                DESCRIPTION
                                "This counter reflects the number of times the intercept service transfers a call by a service provider"
                ::=  {  bwInterceptSPEntry  7  }

-- Service :: Intercept :: GROUP TABLE ...........................................

  bwInterceptGroupEntry OBJECT-TYPE
    SYNTAX    BwInterceptGroupEntry
    MAX-ACCESS  not-accessible
    STATUS    current
                DESCRIPTION
                        "This row contains the counters for Intercept service measurements for a service provider"
    INDEX   {  bwInterceptGroupIndex  }
                ::=  { bwInterceptGroupTable 1 }

        BwInterceptGroupEntry  ::=  SEQUENCE {
                bwInterceptGroupIndex  Unsigned32,
                bwInterceptGroupID  DisplayString,
                bwInterceptGroupUserOriginationInvocations  Counter32,
                bwInterceptGroupGroupOriginationInvocations  Counter32,
                bwInterceptGroupUserTerminationInvocations  Counter32,
                bwInterceptGroupGroupTerminationInvocations  Counter32,
                bwInterceptGroupTransfers  Counter32
                }


  bwInterceptGroupIndex OBJECT-TYPE
    SYNTAX      Unsigned32
    MAX-ACCESS    read-only
    STATUS      current
                DESCRIPTION
                                "This integer represents the a service provider index in the system"
                ::=  {  bwInterceptGroupEntry  1  }


  bwInterceptGroupID  OBJECT-TYPE
    SYNTAX      DisplayString
    MAX-ACCESS    read-only
    STATUS      current
                DESCRIPTION
                                "This string represents a service provider ID"
                ::=  {  bwInterceptGroupEntry  2  }


  bwInterceptGroupUserOriginationInvocations  OBJECT-TYPE
    SYNTAX      Counter32
    MAX-ACCESS    read-write
    STATUS      current
                DESCRIPTION
                                "This counter reflects the number of times the intercept user service blocks an originating call by a service provider"
                ::=  {  bwInterceptGroupEntry  3  }


  bwInterceptGroupGroupOriginationInvocations OBJECT-TYPE
    SYNTAX      Counter32
    MAX-ACCESS    read-write
    STATUS      current
                DESCRIPTION
                                "This counter reflects the number of times the intercept group service blocks an originating call by a service provider"
                ::=  {  bwInterceptGroupEntry  4  }


  bwInterceptGroupUserTerminationInvocations  OBJECT-TYPE
    SYNTAX      Counter32
    MAX-ACCESS    read-write
    STATUS      current
                DESCRIPTION
                                "This counter reflects the number of times the intercept user service blocks a terminating call by a service provider"
                ::=  {  bwInterceptGroupEntry  5  }


  bwInterceptGroupGroupTerminationInvocations OBJECT-TYPE
    SYNTAX      Counter32
    MAX-ACCESS    read-write
    STATUS      current
                DESCRIPTION
                                "This counter reflects the number of times the intercept group service blocks a terminating call by a service provider"
                ::=  {  bwInterceptGroupEntry  6  }


  bwInterceptGroupTransfers OBJECT-TYPE
    SYNTAX      Counter32
    MAX-ACCESS    read-write
    STATUS      current
                DESCRIPTION
                                "This counter reflects the number of times the intercept service transfers a call by a service provider"
                ::=  {  bwInterceptGroupEntry  7  }

-- Service :: Instant Conferencing  ...........................................

  bwICGroupPortLimitExceeded  OBJECT-TYPE
    SYNTAX      Counter32
    MAX-ACCESS    read-write
    STATUS      current
                DESCRIPTION
                                "This statistics indicates that all instant conferencing ports allocated to a group are in use."
                ::=  {  instantConferencing  1  }

  bwICNumAttempts OBJECT-TYPE
    SYNTAX      Counter32
    MAX-ACCESS    read-write
    STATUS      current
                DESCRIPTION
                                "This statistics indicates the number of instant conferencing attempted"
                ::=  {  instantConferencing  2  }

  bwInstantConferencingSPTable  OBJECT-TYPE
    SYNTAX    SEQUENCE  OF  BwInstantConferencingSPEntry
    MAX-ACCESS  not-accessible
    STATUS    current
                DESCRIPTION
                        "This table contains the counters for Instant Conferencing service measurements for service providers"
                ::=  { instantConferencing  3 }

  bwInstantConferencingGroupTable OBJECT-TYPE
    SYNTAX    SEQUENCE  OF  BwInstantConferencingGroupEntry
    MAX-ACCESS  not-accessible
    STATUS    current
                DESCRIPTION
                        "This table contains the counters for Instant Conferencing service measurements for groups"
                ::=  { instantConferencing  4 }

  bwInstantConferencingBridgeTable  OBJECT-TYPE
    SYNTAX    SEQUENCE  OF  BwInstantConferencingBridgeEntry
    MAX-ACCESS  not-accessible
    STATUS    current
                DESCRIPTION
                        "This table is used to track the usage against all bridges defined in the system"
                ::=  { instantConferencing  5 }

  bwICOutdialNumAttempts  OBJECT-TYPE
    SYNTAX      Counter32
    MAX-ACCESS    read-write
    STATUS      current
                DESCRIPTION
                                "This counter is incremented each time an outcall attempt is processed by a conference bridge"
                ::=  {  instantConferencing  6  }

-- Service :: Instant Conferencing :: SP TABLE ...........................................

  bwInstantConferencingSPEntry  OBJECT-TYPE
    SYNTAX    BwInstantConferencingSPEntry
    MAX-ACCESS  not-accessible
    STATUS    current
                DESCRIPTION
                        "This row contains the counters for Instant Conferencing service measurements for a service provider"
    INDEX   {  bwInstantConferencingSPIndex  }
                ::=  { bwInstantConferencingSPTable 1 }

        BwInstantConferencingSPEntry  ::=  SEQUENCE {
                bwInstantConferencingSPIndex  Unsigned32,
                bwInstantConferencingSPID  DisplayString,
                bwICSPGroupPortLimitExceeded  Counter32,
                bwICSPNumAttempts  Counter32,
                bwICSPOutdialNumAttempts  Counter32
                }


  bwInstantConferencingSPIndex  OBJECT-TYPE
    SYNTAX      Unsigned32
    MAX-ACCESS    read-only
    STATUS      current
                DESCRIPTION
                                "This integer represents the a service provider index in the system"
                ::=  {  bwInstantConferencingSPEntry  1  }


  bwInstantConferencingSPID OBJECT-TYPE
    SYNTAX      DisplayString
    MAX-ACCESS    read-only
    STATUS      current
                DESCRIPTION
                                "This string represents a service provider ID"
                ::=  {  bwInstantConferencingSPEntry  2  }


  bwICSPGroupPortLimitExceeded  OBJECT-TYPE
    SYNTAX      Counter32
    MAX-ACCESS    read-write
    STATUS      current
                DESCRIPTION
                                "This statistics indicates that all instant conferencing ports allocated to a group are in use by a service provider"
                ::=  {  bwInstantConferencingSPEntry  3  }


  bwICSPNumAttempts OBJECT-TYPE
    SYNTAX      Counter32
    MAX-ACCESS    read-write
    STATUS      current
                DESCRIPTION
                                "This statistics indicates the number of instant conferencing attempted by a service provider"
                ::=  {  bwInstantConferencingSPEntry  4  }

  bwICSPOutdialNumAttempts  OBJECT-TYPE
    SYNTAX      Counter32
    MAX-ACCESS    read-write
    STATUS      current
                DESCRIPTION
                                "This counter is incremented each time an outcall attempt is processed by a conference bridge for a given service provider"
                ::=  {  bwInstantConferencingSPEntry  5  }

-- Service :: Instant Conferencing :: Group TABLE ...........................................

  bwInstantConferencingGroupEntry OBJECT-TYPE
    SYNTAX    BwInstantConferencingGroupEntry
    MAX-ACCESS  not-accessible
    STATUS    current
                DESCRIPTION
                        "This row contains the counters for Instant Conferencing service measurements for a group"
    INDEX   {  bwInstantConferencingGroupIndex  }
                ::=  { bwInstantConferencingGroupTable 1 }

        BwInstantConferencingGroupEntry  ::=  SEQUENCE {
                bwInstantConferencingGroupIndex  Unsigned32,
                bwInstantConferencingGroupID  DisplayString,
                bwICGroupGroupPortLimitExceeded  Counter32,
                bwICGroupNumAttempts  Counter32,
                bwICGroupOutdialNumAttempts  Counter32
                }


  bwInstantConferencingGroupIndex OBJECT-TYPE
    SYNTAX      Unsigned32
    MAX-ACCESS    read-only
    STATUS      current
                DESCRIPTION
                                "This integer represents the a group index in the system"
                ::=  {  bwInstantConferencingGroupEntry  1  }


  bwInstantConferencingGroupID  OBJECT-TYPE
    SYNTAX      DisplayString
    MAX-ACCESS    read-only
    STATUS      current
                DESCRIPTION
                                "This string represents a group ID"
                ::=  {  bwInstantConferencingGroupEntry  2  }


  bwICGroupGroupPortLimitExceeded OBJECT-TYPE
    SYNTAX      Counter32
    MAX-ACCESS    read-write
    STATUS      current
                DESCRIPTION
                                "This statistics indicates that all instant conferencing ports allocated to a group are in use by a group"
                ::=  {  bwInstantConferencingGroupEntry  3  }


  bwICGroupNumAttempts  OBJECT-TYPE
    SYNTAX      Counter32
    MAX-ACCESS    read-write
    STATUS      current
                DESCRIPTION
                                "This statistics indicates the number of instant conferencing attempted by a group"
                ::=  {  bwInstantConferencingGroupEntry  4  }

  bwICGroupOutdialNumAttempts OBJECT-TYPE
    SYNTAX      Counter32
    MAX-ACCESS    read-write
    STATUS      current
                DESCRIPTION
                                "This counter is incremented each time an outcall attempt is processed by a conference bridge for a given group"
                ::=  {  bwInstantConferencingGroupEntry  5  }

-- Service :: Instant Conferencing :: Bridge TABLE ...........................................

  bwInstantConferencingBridgeEntry  OBJECT-TYPE
    SYNTAX    BwInstantConferencingBridgeEntry
    MAX-ACCESS  not-accessible
    STATUS    current
                DESCRIPTION
                        "This row contains the counters for Instant Conferencing service measurements for a bridge"
    INDEX   {  bwInstantConferencingBridgeIndex  }
                ::=  { bwInstantConferencingBridgeTable 1 }

        BwInstantConferencingBridgeEntry  ::=  SEQUENCE {
                bwInstantConferencingBridgeIndex  Unsigned32,
                bwInstantConferencingBridgeName  DisplayString,
                bwInstantConferencingBridgeGroupName  DisplayString,
                bwInstantConferencingCurrentUsage  Gauge32,
                bwInstantConferencingTodaysPeakUsage  Gauge32,
                bwInstantConferencingYesterdaysPeakUsage  Gauge32
                }


  bwInstantConferencingBridgeIndex  OBJECT-TYPE
    SYNTAX      Unsigned32
    MAX-ACCESS    read-only
    STATUS      current
                DESCRIPTION
                                "This integer represents the a bridge index in the system"
                ::=  {  bwInstantConferencingBridgeEntry  1  }

  bwInstantConferencingBridgeName OBJECT-TYPE
    SYNTAX      DisplayString
    MAX-ACCESS    read-only
    STATUS      current
                DESCRIPTION
                                "The name of the conference bridge referenced by this index"
                ::=  {  bwInstantConferencingBridgeEntry  2  }

  bwInstantConferencingBridgeGroupName  OBJECT-TYPE
    SYNTAX      DisplayString
    MAX-ACCESS    read-only
    STATUS      current
                DESCRIPTION
                                "The name of the group that owns the conference bridge referenced by this index"
                ::=  {  bwInstantConferencingBridgeEntry  3  }

  bwInstantConferencingCurrentUsage OBJECT-TYPE
    SYNTAX      Gauge32
    MAX-ACCESS    read-only
    STATUS      current
                DESCRIPTION
                                "The number of ports currently in use in this bridge"
                ::=  {  bwInstantConferencingBridgeEntry  4  }

  bwInstantConferencingTodaysPeakUsage  OBJECT-TYPE
    SYNTAX      Gauge32
    MAX-ACCESS    read-only
    STATUS      current
                DESCRIPTION
                                "The maximum number of ports that were simultaneously in use for this bridge today"
                ::=  {  bwInstantConferencingBridgeEntry  5  }

  bwInstantConferencingYesterdaysPeakUsage  OBJECT-TYPE
    SYNTAX      Gauge32
    MAX-ACCESS    read-only
    STATUS      current
                DESCRIPTION
                                "The maximum number of ports that were simultaneously in use for this bridge yesterday"
                ::=  {  bwInstantConferencingBridgeEntry  6  }


-- Service :: Calling Line ID Blocking  ...........................................

  bwCallingLineIDDeliveryBlockPerCallBlocks OBJECT-TYPE
    SYNTAX      Counter32
    MAX-ACCESS    read-write
    STATUS      current
                DESCRIPTION
                                "This counter reflects the number of times the per call calling line ID delivery block service is invoked."
                ::=  {  callingLineIDDeliveryBlock  1  }

  bwCallingLineIDDeliveryBlockSPTable OBJECT-TYPE
    SYNTAX    SEQUENCE  OF  BwCallingLineIDDeliveryBlockSPEntry
    MAX-ACCESS  not-accessible
    STATUS    current
                DESCRIPTION
                        "Table used to report the calling line id blocking statistics per service providers"
                ::=  { callingLineIDDeliveryBlock  2 }

  bwCallingLineIDDeliveryBlockGroupTable  OBJECT-TYPE
    SYNTAX    SEQUENCE  OF  BwCallingLineIDDeliveryBlockGroupEntry
    MAX-ACCESS  not-accessible
    STATUS    current
                DESCRIPTION
                        "Table used to report the calling line id blocking statistics per groups"
                ::=  { callingLineIDDeliveryBlock  3 }

  bwCallingLineIDDeliveryPerCall  OBJECT-TYPE
    SYNTAX      Counter32
    MAX-ACCESS    read-write
    STATUS      current
                DESCRIPTION
                                "This counter reflects the number of times the per call calling line ID delivery service is invoked."
                ::=  {  callingLineIDDeliveryBlock  4  }


-- Service :: Calling Line ID Blocking :: SP TABLE ...........................................

  bwCallingLineIDDeliveryBlockSPEntry OBJECT-TYPE
    SYNTAX    BwCallingLineIDDeliveryBlockSPEntry
    MAX-ACCESS  not-accessible
    STATUS    current
                DESCRIPTION
                        "This row contains the counters for the per call calling line ID delivery block service measurements for a service provider."
    INDEX   {  bwCallingLineIDDeliveryBlockSPIndex  }
                ::=  { bwCallingLineIDDeliveryBlockSPTable 1 }

        BwCallingLineIDDeliveryBlockSPEntry  ::=  SEQUENCE {
                bwCallingLineIDDeliveryBlockSPIndex  Unsigned32,
                bwCallingLineIDDeliveryBlockSPID  DisplayString,
                bwCallingLineIDDeliveryBlockSPPerCallBlocks  Counter32,
                bwCallingLineIDDeliveryPerCallSP Counter32
                }


  bwCallingLineIDDeliveryBlockSPIndex OBJECT-TYPE
    SYNTAX      Unsigned32
    MAX-ACCESS    read-only
    STATUS      current
                DESCRIPTION
                                "This integer represents the service provider index in the system."
                ::=  {  bwCallingLineIDDeliveryBlockSPEntry  1  }


  bwCallingLineIDDeliveryBlockSPID  OBJECT-TYPE
    SYNTAX      DisplayString
    MAX-ACCESS    read-only
    STATUS      current
                DESCRIPTION
                                "This string represents a service provider ID"
                ::=  {  bwCallingLineIDDeliveryBlockSPEntry  2  }


  bwCallingLineIDDeliveryBlockSPPerCallBlocks OBJECT-TYPE
    SYNTAX      Counter32
    MAX-ACCESS    read-write
    STATUS      current
                DESCRIPTION
                                "This counter reflects the number of times the per call calling line ID delivery block service is invoked for this service provider."
                ::=  {  bwCallingLineIDDeliveryBlockSPEntry  3  }

  bwCallingLineIDDeliveryPerCallSP  OBJECT-TYPE
    SYNTAX      Counter32
    MAX-ACCESS    read-write
    STATUS      current
                DESCRIPTION
                                "This counter reflects the number of times the calling line ID delivery per call service is invoked for this service provider."
                ::=  {  bwCallingLineIDDeliveryBlockSPEntry  4  }

-- Service :: Calling Line ID Blocking :: GROUP TABLE ...........................................

  bwCallingLineIDDeliveryBlockGroupEntry  OBJECT-TYPE
    SYNTAX    BwCallingLineIDDeliveryBlockGroupEntry
    MAX-ACCESS  not-accessible
    STATUS    current
                DESCRIPTION
                        "This row contains the counters for the per call calling line ID delivery block service measurements for a group."
    INDEX   {  bwCallingLineIDDeliveryBlockGroupIndex  }
                ::=  { bwCallingLineIDDeliveryBlockGroupTable 1 }

        BwCallingLineIDDeliveryBlockGroupEntry  ::=  SEQUENCE {
                bwCallingLineIDDeliveryBlockGroupIndex  Unsigned32,
                bwCallingLineIDDeliveryBlockGroupID  DisplayString,
                bwCallingLineIDDeliveryBlockGroupPerCallBlocks  Counter32,
                bwCallingLineIDDeliveryPerCallGroup Counter32
                }


  bwCallingLineIDDeliveryBlockGroupIndex  OBJECT-TYPE
    SYNTAX      Unsigned32
    MAX-ACCESS    read-only
    STATUS      current
                DESCRIPTION
                                "This integer represents the group index in the system."
                ::=  {  bwCallingLineIDDeliveryBlockGroupEntry  1  }


  bwCallingLineIDDeliveryBlockGroupID OBJECT-TYPE
    SYNTAX      DisplayString
    MAX-ACCESS    read-only
    STATUS      current
                DESCRIPTION
                                "This string represents a group ID"
                ::=  {  bwCallingLineIDDeliveryBlockGroupEntry  2  }


  bwCallingLineIDDeliveryBlockGroupPerCallBlocks  OBJECT-TYPE
    SYNTAX      Counter32
    MAX-ACCESS    read-write
    STATUS      current
                DESCRIPTION
                                "This counter reflects the number of times the per call calling line ID delivery block service is invoked for this group."
                ::=  {  bwCallingLineIDDeliveryBlockGroupEntry  3  }

  bwCallingLineIDDeliveryPerCallGroup OBJECT-TYPE
    SYNTAX      Counter32
    MAX-ACCESS    read-write
    STATUS      current
                DESCRIPTION
                                "This counter reflects the number of times the calling line ID delivery per call service is invoked for this group."
                ::=  {  bwCallingLineIDDeliveryBlockGroupEntry  4  }


-- Service :: Session Audit  ...........................................

  bwSessionAuditNumCallsAudited OBJECT-TYPE
    SYNTAX      Counter32
    MAX-ACCESS    read-write
    STATUS      current
                DESCRIPTION
                                "Number of calls that are audited when a Session Audit is invoked."
                ::=  {  sessionAudit  1  }

  bwSessionAuditNumEndpointsAudited OBJECT-TYPE
    SYNTAX      Counter32
    MAX-ACCESS    read-write
    STATUS      current
                DESCRIPTION
                                "Number of endpoints that are audited when a Session Audit is invoked."
                ::=  {  sessionAudit  2  }

  bwSessionAuditNumCallsFailedAudit OBJECT-TYPE
    SYNTAX      Counter32
    MAX-ACCESS    read-write
    STATUS      current
                DESCRIPTION
                                "Number of times the SessionAudit service received a failure on a call being audited."
                ::=  {  sessionAudit  3  }

  bwSessionAuditNumEndpointsFailedAudit OBJECT-TYPE
    SYNTAX      Counter32
    MAX-ACCESS    read-write
    STATUS      current
                DESCRIPTION
                                "Number of times the SessionAudit service received a failure on an endpoint being audited."
                ::=  {  sessionAudit  4  }

  bwSessionAuditSPTable OBJECT-TYPE
    SYNTAX    SEQUENCE  OF  BwSessionAuditSPEntry
    MAX-ACCESS  not-accessible
    STATUS    current
                DESCRIPTION
                        "This table contains Session Audit service measurements at a service provider level."
                ::=  { sessionAudit  5 }

  bwSessionAuditGroupTable  OBJECT-TYPE
    SYNTAX    SEQUENCE  OF  BwSessionAuditGroupEntry
    MAX-ACCESS  not-accessible
    STATUS    current
                DESCRIPTION
                        "This table contains Session Audit service measurements at a group level."
                ::=  { sessionAudit  6 }

-- Service :: Session Audit :: SP TABLE ...........................................

  bwSessionAuditSPEntry OBJECT-TYPE
    SYNTAX    BwSessionAuditSPEntry
    MAX-ACCESS  not-accessible
    STATUS    current
                DESCRIPTION
                        "Each row contains the service counters for the SessionAudit service for each service provider in the system."
    INDEX   {  bwSessionAuditSPIndex  }
                ::=  { bwSessionAuditSPTable 1 }

        BwSessionAuditSPEntry  ::=  SEQUENCE {
                bwSessionAuditSPIndex  Unsigned32,
                bwSessionAuditSPID  DisplayString,
                bwSessionAuditSPNumCallsAudited  Counter32,
                bwSessionAuditSPNumEndpointsAudited  Counter32,
                bwSessionAuditSPNumCallsFailedAudit  Counter32,
                bwSessionAuditSPNumEndpointsFailedAudit  Counter32
                }

  bwSessionAuditSPIndex OBJECT-TYPE
    SYNTAX      Unsigned32
    MAX-ACCESS    read-only
    STATUS      current
                DESCRIPTION
                                "This column represents the index of the service provider in the system."
                ::=  {  bwSessionAuditSPEntry  1  }

  bwSessionAuditSPID  OBJECT-TYPE
    SYNTAX      DisplayString
    MAX-ACCESS    read-only
    STATUS      current
                DESCRIPTION
                                "This column represents a service provider ID."
                ::=  {  bwSessionAuditSPEntry  2  }

  bwSessionAuditSPNumCallsAudited OBJECT-TYPE
    SYNTAX      Counter32
    MAX-ACCESS    read-write
    STATUS      current
                DESCRIPTION
                                "Number of calls that are audited when a Session Audit is invoked, per service provider."
                ::=  {  bwSessionAuditSPEntry  3  }

  bwSessionAuditSPNumEndpointsAudited OBJECT-TYPE
    SYNTAX      Counter32
    MAX-ACCESS    read-write
    STATUS      current
                DESCRIPTION
                                "Number of endpoints that are audited when a Session Audit is invoked, per service provider."
                ::=  {  bwSessionAuditSPEntry  4  }

  bwSessionAuditSPNumCallsFailedAudit OBJECT-TYPE
    SYNTAX      Counter32
    MAX-ACCESS    read-write
    STATUS      current
                DESCRIPTION
                                "Number of times the SessionAudit service received a failure on a call being audited, per service provider."
                ::=  {  bwSessionAuditSPEntry  5  }

  bwSessionAuditSPNumEndpointsFailedAudit OBJECT-TYPE
    SYNTAX      Counter32
    MAX-ACCESS    read-write
    STATUS      current
                DESCRIPTION
                                "Number of times the SessionAudit service received a failure on an endpoint being audited, per service provider."
                ::=  {  bwSessionAuditSPEntry  6  }

-- Service :: Session Audit :: GROUP TABLE ...........................................

  bwSessionAuditGroupEntry  OBJECT-TYPE
    SYNTAX    BwSessionAuditGroupEntry
    MAX-ACCESS  not-accessible
    STATUS    current
                DESCRIPTION
                        "Each row contains the service counters for the SessionAudit service for each group in the system."
    INDEX   {  bwSessionAuditGroupIndex  }
                ::=  { bwSessionAuditGroupTable 1 }

        BwSessionAuditGroupEntry  ::=  SEQUENCE {
                bwSessionAuditGroupIndex  Unsigned32,
                bwSessionAuditGroupID  DisplayString,
                bwSessionAuditGroupNumCallsAudited  Counter32,
                bwSessionAuditGroupNumEndpointsAudited  Counter32,
                bwSessionAuditGroupNumCallsFailedAudit  Counter32,
                bwSessionAuditGroupNumEndpointsFailedAudit  Counter32
                }

  bwSessionAuditGroupIndex  OBJECT-TYPE
    SYNTAX      Unsigned32
    MAX-ACCESS    read-only
    STATUS      current
                DESCRIPTION
                                "This column represents the index of the group in the system."
                ::=  {  bwSessionAuditGroupEntry  1  }

  bwSessionAuditGroupID OBJECT-TYPE
    SYNTAX      DisplayString
    MAX-ACCESS    read-only
    STATUS      current
                DESCRIPTION
                                "This column represents a group ID."
                ::=  {  bwSessionAuditGroupEntry  2  }

  bwSessionAuditGroupNumCallsAudited  OBJECT-TYPE
    SYNTAX      Counter32
    MAX-ACCESS    read-write
    STATUS      current
                DESCRIPTION
                                "Number of calls that are audited when a Session Audit is invoked, per group."
                ::=  {  bwSessionAuditGroupEntry  3  }

  bwSessionAuditGroupNumEndpointsAudited  OBJECT-TYPE
    SYNTAX      Counter32
    MAX-ACCESS    read-write
    STATUS      current
                DESCRIPTION
                                "Number of endpoints that are audited when a Session Audit is invoked, per group."
                ::=  {  bwSessionAuditGroupEntry  4  }

  bwSessionAuditGroupNumCallsFailedAudit  OBJECT-TYPE
    SYNTAX      Counter32
    MAX-ACCESS    read-write
    STATUS      current
                DESCRIPTION
                                "Number of times the SessionAudit service received a failure on a call being audited, per group."
                ::=  {  bwSessionAuditGroupEntry  5  }

  bwSessionAuditGroupNumEndpointsFailedAudit  OBJECT-TYPE
    SYNTAX      Counter32
    MAX-ACCESS    read-write
    STATUS      current
                DESCRIPTION
                                "Number of times the SessionAudit service received a failure on an endpoint being audited, per group."
                ::=  {  bwSessionAuditGroupEntry  6  }

-- Service :: Windows Messaging  ...........................................

  bwWindowsMessagingIMSessionSuccessCounter OBJECT-TYPE
    SYNTAX      Counter32
    MAX-ACCESS    read-write
    STATUS      current
                DESCRIPTION
                                "The number of times we successfully initiate a windows messaging session of type IM"
                ::=  {  windowsMessaging  1  }


-- Service :: Call Waiting  ...........................................

  bwCallWaitingSPTable  OBJECT-TYPE
    SYNTAX    SEQUENCE  OF  BwCallWaitingSPEntry
    MAX-ACCESS  not-accessible
    STATUS    current
                DESCRIPTION
                        "This counter table will be indexed per service provider."
                ::=  { callWaiting  1 }

  bwCWNumPhoneCancellations OBJECT-TYPE
    SYNTAX      Counter32
    MAX-ACCESS    read-write
    STATUS      current
                DESCRIPTION
                                "Total number of times CW has been cancelled via FAC."
                ::=  {  callWaiting  2  }

  bwCallWaitingGroupTable OBJECT-TYPE
    SYNTAX    SEQUENCE  OF  BwCallWaitingGroupEntry
    MAX-ACCESS  not-accessible
    STATUS    current
                DESCRIPTION
                        "This counter table will be indexed per group."
                ::=  { callWaiting  3 }

-- Service :: Call Waiting :: SP TABLE ...........................................

  bwCallWaitingSPEntry  OBJECT-TYPE
    SYNTAX    BwCallWaitingSPEntry
    MAX-ACCESS  not-accessible
    STATUS    current
                DESCRIPTION
                        "Each row contains the service counters for the CallWaiting service for each service provider in the system."
    INDEX   {  bwCallWaitingSPIndex  }
                ::=  { bwCallWaitingSPTable 1 }

        BwCallWaitingSPEntry  ::=  SEQUENCE {
                bwCallWaitingSPIndex  Unsigned32,
    bwCallWaitingSPID     DisplayString,
                bwCWSPNumPhoneCancellations  Counter32
                }

  bwCallWaitingSPIndex    OBJECT-TYPE
    SYNTAX      Unsigned32
    MAX-ACCESS    read-only
    STATUS      current
                DESCRIPTION
                                "This column represents the index of the service provider in the system."
                ::=  {  bwCallWaitingSPEntry  1  }

  bwCallWaitingSPID   OBJECT-TYPE
    SYNTAX      DisplayString
    MAX-ACCESS    read-only
    STATUS      current
                DESCRIPTION
                                "This string represents a service provider ID"
                ::=  {  bwCallWaitingSPEntry  2  }

  bwCWSPNumPhoneCancellations OBJECT-TYPE
    SYNTAX      Counter32
    MAX-ACCESS    read-write
    STATUS      current
                DESCRIPTION
                                "Number of times CW has been cancelled via FAC for users in a given service provider."
                ::=  {  bwCallWaitingSPEntry  3  }

-- Service :: Call Waiting :: GROUP TABLE ...........................................

  bwCallWaitingGroupEntry OBJECT-TYPE
    SYNTAX    BwCallWaitingGroupEntry
    MAX-ACCESS  not-accessible
    STATUS    current
                DESCRIPTION
                        "Each row contains the service counters for the CallWaiting service for each group in the system."
    INDEX   {  bwCallWaitingGroupIndex  }
                ::=  { bwCallWaitingGroupTable 1 }

        BwCallWaitingGroupEntry  ::=  SEQUENCE {
                bwCallWaitingGroupIndex  Unsigned32,
    bwCallWaitingGroupID    DisplayString,
                bwCWGroupNumPhoneCancellations  Counter32
                }

  bwCallWaitingGroupIndex   OBJECT-TYPE
    SYNTAX      Unsigned32
    MAX-ACCESS    read-only
    STATUS      current
                DESCRIPTION
                                "This column represents the index of the group in the system."
                ::=  {  bwCallWaitingGroupEntry  1  }

  bwCallWaitingGroupID  OBJECT-TYPE
    SYNTAX      DisplayString
    MAX-ACCESS    read-only
    STATUS      current
                DESCRIPTION
                                "This string represents a group ID"
                ::=  {  bwCallWaitingGroupEntry  2  }

  bwCWGroupNumPhoneCancellations  OBJECT-TYPE
    SYNTAX      Counter32
    MAX-ACCESS    read-write
    STATUS      current
                DESCRIPTION
                                "Number of times CW has been cancelled via FAC for users in a given group."
                ::=  {  bwCallWaitingGroupEntry  3  }

-- Service :: Alternate Numbers  ...........................................

  bwAlternateNumbersSPTable OBJECT-TYPE
    SYNTAX    SEQUENCE  OF  BwAlternateNumbersSPEntry
    MAX-ACCESS  not-accessible
    STATUS    current
                DESCRIPTION
                        "This counter table will be indexed per service provider"
                ::=  { alternateNumbers  1 }

  bwAlternateNumbersUsage OBJECT-TYPE
    SYNTAX      Counter32
    MAX-ACCESS    read-write
    STATUS      current
                DESCRIPTION
                                "Counts all call made to a user's alternate number system"
                ::=  {  alternateNumbers  2  }

  bwAlternateNumbersGroupTable  OBJECT-TYPE
    SYNTAX    SEQUENCE  OF  BwAlternateNumbersGroupEntry
    MAX-ACCESS  not-accessible
    STATUS    current
                DESCRIPTION
                        "This counter table will be indexed per group"
                ::=  { alternateNumbers  3 }

-- Service :: Alternate Numbers :: SP TABLE ...........................................

  bwAlternateNumbersSPEntry OBJECT-TYPE
    SYNTAX    BwAlternateNumbersSPEntry
    MAX-ACCESS  not-accessible
    STATUS    current
                DESCRIPTION
                        "Each row contains the service counters for the Alternate Numbers service for each service provider in the system."
    INDEX   {  bwAlternateNumbersSPIndex  }
                ::=  { bwAlternateNumbersSPTable 1 }

        BwAlternateNumbersSPEntry  ::=  SEQUENCE {
                bwAlternateNumbersSPIndex  Unsigned32,
                bwAlternateNumbersSPID  DisplayString,
                bwAlternateNumbersSPUsage  Counter32
                }

  bwAlternateNumbersSPIndex   OBJECT-TYPE
    SYNTAX      Unsigned32
    MAX-ACCESS    read-only
    STATUS      current
                DESCRIPTION
                                "This column represents the index of the service provider in the system"
                ::=  {  bwAlternateNumbersSPEntry  1  }

  bwAlternateNumbersSPID  OBJECT-TYPE
    SYNTAX      DisplayString
    MAX-ACCESS    read-only
    STATUS      current
                DESCRIPTION
                                "This string represents a service provider ID"
                ::=  {  bwAlternateNumbersSPEntry  2  }

  bwAlternateNumbersSPUsage OBJECT-TYPE
    SYNTAX      Counter32
    MAX-ACCESS    read-write
    STATUS      current
                DESCRIPTION
                                "Counts all call made to a user's alternate number system per service provider"
                ::=  {  bwAlternateNumbersSPEntry  3  }

-- Service :: Alternate Numbers :: GROUP TABLE ...........................................

  bwAlternateNumbersGroupEntry  OBJECT-TYPE
    SYNTAX    BwAlternateNumbersGroupEntry
    MAX-ACCESS  not-accessible
    STATUS    current
                DESCRIPTION
                        "Each row contains the service counters for the Alternate Numbers service for each group in the system."
    INDEX   {  bwAlternateNumbersGroupIndex  }
                ::=  { bwAlternateNumbersGroupTable 1 }

        BwAlternateNumbersGroupEntry  ::=  SEQUENCE {
                bwAlternateNumbersGroupIndex  Unsigned32,
                bwAlternateNumbersGroupID  DisplayString,
                bwAlternateNumbersGroupUsage  Counter32
                }

  bwAlternateNumbersGroupIndex    OBJECT-TYPE
    SYNTAX      Unsigned32
    MAX-ACCESS    read-only
    STATUS      current
                DESCRIPTION
                                "This column represents the index of the group in the system"
                ::=  {  bwAlternateNumbersGroupEntry  1  }

  bwAlternateNumbersGroupID   OBJECT-TYPE
    SYNTAX      DisplayString
    MAX-ACCESS    read-only
    STATUS      current
                DESCRIPTION
                                "This string represents a group ID"
                ::=  {  bwAlternateNumbersGroupEntry  2  }

  bwAlternateNumbersGroupUsage  OBJECT-TYPE
    SYNTAX      Counter32
    MAX-ACCESS    read-write
    STATUS      current
                DESCRIPTION
                                "Counts all call made to a user's alternate number system per group"
                ::=  {  bwAlternateNumbersGroupEntry  3  }

-- Service :: COT  ...........................................

  bwCotActivation OBJECT-TYPE
    SYNTAX      Counter32
    MAX-ACCESS    read-write
    STATUS      current
                DESCRIPTION
                        "Total number of times that a user initiates a customer originated trace"
                ::=  { cot  1 }

  bwCotFailureNoId  OBJECT-TYPE
    SYNTAX      Counter32
    MAX-ACCESS    read-write
    STATUS      current
                DESCRIPTION
                                "Total number of times a user encounters a failure when initiating a customer originated trace due to the lack of information from the caller"
                ::=  {  cot  2  }

  bwCotSPTable  OBJECT-TYPE
    SYNTAX    SEQUENCE  OF  BwCotSPEntry
    MAX-ACCESS  not-accessible
    STATUS    current
                DESCRIPTION
                        "Counters for customer originated trace service measurements for service providers"
                ::=  { cot  3 }

  bwCotGroupTable OBJECT-TYPE
    SYNTAX    SEQUENCE  OF  BwCotGroupEntry
    MAX-ACCESS  not-accessible
    STATUS    current
                DESCRIPTION
                        "Counters for customer originated trace service measurements for groups"
                ::=  { cot  4 }

-- Service :: COT :: SP TABLE ...........................................

  bwCotSPEntry  OBJECT-TYPE
    SYNTAX    BwCotSPEntry
    MAX-ACCESS  not-accessible
    STATUS    current
                DESCRIPTION
                        "Each row contains the service counters for the COT service for each service provider in the system."
    INDEX   {  bwCotSPIndex  }
                ::=  { bwCotSPTable 1 }

        BwCotSPEntry  ::=  SEQUENCE {
                bwCotSPIndex  Unsigned32,
                bwCotSPID  DisplayString,
                bwCotSPActivation  Counter32,
                bwCotSPFailureNoId  Counter32
                }

  bwCotSPIndex    OBJECT-TYPE
    SYNTAX      Unsigned32
    MAX-ACCESS    read-only
    STATUS      current
                DESCRIPTION
                                "This column represents the index of the service provider in the system"
                ::=  {  bwCotSPEntry  1  }

  bwCotSPID   OBJECT-TYPE
    SYNTAX      DisplayString
    MAX-ACCESS    read-only
    STATUS      current
                DESCRIPTION
                                "This string represents a service provider ID"
                ::=  {  bwCotSPEntry  2  }


  bwCotSPActivation OBJECT-TYPE
    SYNTAX      Counter32
    MAX-ACCESS    read-write
    STATUS      current
                DESCRIPTION
                        "Total number of times that a user in a given service provider initiates a customer originated trace"
                ::=  {  bwCotSPEntry  3 }

  bwCotSPFailureNoId  OBJECT-TYPE
    SYNTAX      Counter32
    MAX-ACCESS    read-write
    STATUS      current
                DESCRIPTION
                                "Total number of times a user in a given service provider encounters a failure when initiating a customer originated trace due to the lack of information from the caller"
                ::=  {  bwCotSPEntry  4  }

-- Service :: COT :: GROUP TABLE ...........................................

  bwCotGroupEntry OBJECT-TYPE
    SYNTAX    BwCotGroupEntry
    MAX-ACCESS  not-accessible
    STATUS    current
                DESCRIPTION
                        "Each row contains the service counters for the COT service for each group in the system."
    INDEX   {  bwCotGroupIndex  }
                ::=  { bwCotGroupTable 1 }

        BwCotGroupEntry  ::=  SEQUENCE {
                bwCotGroupIndex  Unsigned32,
                bwCotGroupID  DisplayString,
                bwCotGroupActivation  Counter32,
                bwCotGroupFailureNoId  Counter32
                }

  bwCotGroupIndex   OBJECT-TYPE
    SYNTAX      Unsigned32
    MAX-ACCESS    read-only
    STATUS      current
                DESCRIPTION
                                "This column represents the index of the group in the system"
                ::=  {  bwCotGroupEntry  1  }

  bwCotGroupID  OBJECT-TYPE
    SYNTAX      DisplayString
    MAX-ACCESS    read-only
    STATUS      current
                DESCRIPTION
                                "This string represents a group ID"
                ::=  {  bwCotGroupEntry  2  }


  bwCotGroupActivation  OBJECT-TYPE
    SYNTAX      Counter32
    MAX-ACCESS    read-write
    STATUS      current
                DESCRIPTION
                        "Total number of times that a user in a given group initiates a customer originated trace"
                ::=  {  bwCotGroupEntry  3 }

  bwCotGroupFailureNoId OBJECT-TYPE
    SYNTAX      Counter32
    MAX-ACCESS    read-write
    STATUS      current
                DESCRIPTION
                                "Total number of times a user in a given group encounters a failure when initiating a customer originated trace due to the lack of information from the caller"
                ::=  {  bwCotGroupEntry  4  }

-- Service :: SD8  ...........................................

  bwSD8NumTimesDialed OBJECT-TYPE
    SYNTAX      Counter32
    MAX-ACCESS    read-write
    STATUS      current
                DESCRIPTION
                        "Total number of times a speed code has been dialed"
                ::=  { sd8  1 }

  bwSD8NumTimesProgrammed OBJECT-TYPE
    SYNTAX      Counter32
    MAX-ACCESS    read-write
    STATUS      current
                DESCRIPTION
                                "Total number of times a speed code has been defined by a user via FAC"
                ::=  {  sd8  2  }

  bwSD8SPTable  OBJECT-TYPE
    SYNTAX    SEQUENCE  OF  BwSD8SPEntry
    MAX-ACCESS  not-accessible
    STATUS    current
                DESCRIPTION
                        "Counters for SD8 service measurements for service providers"
                ::=  { sd8  3 }

  bwSD8GroupTable OBJECT-TYPE
    SYNTAX    SEQUENCE  OF  BwSD8GroupEntry
    MAX-ACCESS  not-accessible
    STATUS    current
                DESCRIPTION
                        "Counters for SD8 service measurements for groups"
                ::=  { sd8  4 }

-- Service :: SD8 :: SP TABLE ...........................................

  bwSD8SPEntry  OBJECT-TYPE
    SYNTAX    BwSD8SPEntry
    MAX-ACCESS  not-accessible
    STATUS    current
                DESCRIPTION
                        "Each row contains the service counters for the SD8 service for each service provider in the system."
    INDEX   {  bwSD8SPIndex  }
                ::=  { bwSD8SPTable 1 }

        BwSD8SPEntry  ::=  SEQUENCE {
                bwSD8SPIndex  Unsigned32,
                bwSD8SPID  DisplayString,
                bwSD8SPNumTimesDialed  Counter32,
                bwSD8SPNumTimesProgrammed  Counter32
                }

  bwSD8SPIndex    OBJECT-TYPE
    SYNTAX      Unsigned32
    MAX-ACCESS    read-only
    STATUS      current
                DESCRIPTION
                                "This column represents the index of the service provider in the system"
                ::=  {  bwSD8SPEntry  1  }

  bwSD8SPID   OBJECT-TYPE
    SYNTAX      DisplayString
    MAX-ACCESS    read-only
    STATUS      current
                DESCRIPTION
                                "This string represents a service provider ID"
                ::=  {  bwSD8SPEntry  2  }


  bwSD8SPNumTimesDialed OBJECT-TYPE
    SYNTAX      Counter32
    MAX-ACCESS    read-write
    STATUS      current
                DESCRIPTION
                        "Total Number of times a speed code has been dialed by users in a given service provider"
                ::=  {  bwSD8SPEntry  3 }

  bwSD8SPNumTimesProgrammed OBJECT-TYPE
    SYNTAX      Counter32
    MAX-ACCESS    read-write
    STATUS      current
                DESCRIPTION
                                "Total numberNumber of times a speed code has been defined via FAC by users in a given service provider"
                ::=  {  bwSD8SPEntry  4  }

-- Service :: SD8 :: GROUP TABLE ...........................................

  bwSD8GroupEntry OBJECT-TYPE
    SYNTAX    BwSD8GroupEntry
    MAX-ACCESS  not-accessible
    STATUS    current
                DESCRIPTION
                        "Each row contains the service counters for the SD8 service for each group in the system."
    INDEX   {  bwSD8GroupIndex  }
                ::=  { bwSD8GroupTable 1 }

        BwSD8GroupEntry  ::=  SEQUENCE {
                bwSD8GroupIndex  Unsigned32,
                bwSD8GroupID  DisplayString,
                bwSD8GroupNumTimesDialed  Counter32,
                bwSD8GroupNumTimesProgrammed  Counter32
                }

  bwSD8GroupIndex   OBJECT-TYPE
    SYNTAX      Unsigned32
    MAX-ACCESS    read-only
    STATUS      current
                DESCRIPTION
                                "This column represents the index of the group in the system"
                ::=  {  bwSD8GroupEntry  1  }

  bwSD8GroupID  OBJECT-TYPE
    SYNTAX      DisplayString
    MAX-ACCESS    read-only
    STATUS      current
                DESCRIPTION
                                "This string represents a group ID"
                ::=  {  bwSD8GroupEntry  2  }


  bwSD8GroupNumTimesDialed  OBJECT-TYPE
    SYNTAX      Counter32
    MAX-ACCESS    read-write
    STATUS      current
                DESCRIPTION
                        "Total Number of times a speed code has been dialed by users in a given group"
                ::=  {  bwSD8GroupEntry  3 }

  bwSD8GroupNumTimesProgrammed  OBJECT-TYPE
    SYNTAX      Counter32
    MAX-ACCESS    read-write
    STATUS      current
                DESCRIPTION
                                "Total numberNumber of times a speed code has been defined via FAC by users in a given group"
                ::=  {  bwSD8GroupEntry  4  }

-- Service :: Music on hold  ...........................................

  bwMusicOnHoldNumUses  OBJECT-TYPE
    SYNTAX      Counter32
    MAX-ACCESS    read-write
    STATUS      current
                DESCRIPTION
                                "Total number of times Music On Hold has been used"
                ::=  {  musicOnHold  1  }

  bwMusicOnHoldSPTable  OBJECT-TYPE
    SYNTAX    SEQUENCE  OF  BwMusicOnHoldSPEntry
    MAX-ACCESS  not-accessible
    STATUS    current
                DESCRIPTION
                        "Counters for Music On Hold service measurements for service providers"
                ::=  {  musicOnHold  2 }

  bwMusicOnHoldGroupTable OBJECT-TYPE
    SYNTAX    SEQUENCE  OF  BwMusicOnHoldGroupEntry
    MAX-ACCESS  not-accessible
    STATUS    current
                DESCRIPTION
                        "Counters for Music On Hold service measurements for groups"
                ::=  {  musicOnHold  3 }

  bwMusicOnHoldExternalSourceNumFailures  OBJECT-TYPE
    SYNTAX      Counter32
    MAX-ACCESS    read-write
    STATUS      current
                DESCRIPTION
                                "This counter is incremented whenever a caller is put on hold and that the music-on-hold source could not be connected to the caller"
                ::=  {  musicOnHold  4  }

-- Service :: Music on hold :: SP TABLE ...........................................

  bwMusicOnHoldSPEntry  OBJECT-TYPE
    SYNTAX    BwMusicOnHoldSPEntry
    MAX-ACCESS  not-accessible
    STATUS    current
                DESCRIPTION
                        "Each row contains the service counters for the Music On Hold service for each service provider in the system."
    INDEX   {  bwMusicOnHoldSPIndex  }
                ::=  { bwMusicOnHoldSPTable 1 }

        BwMusicOnHoldSPEntry  ::=  SEQUENCE {
                bwMusicOnHoldSPIndex  Unsigned32,
                bwMusicOnHoldSPID  DisplayString,
                bwMusicOnHoldSPNumUses  Counter32,
                bwMusicOnHoldSPExternalSourceNumFailures Counter32
                }

  bwMusicOnHoldSPIndex    OBJECT-TYPE
    SYNTAX      Unsigned32
    MAX-ACCESS    read-only
    STATUS      current
                DESCRIPTION
                                "This column represents the index of the service provider in the system"
                ::=  {  bwMusicOnHoldSPEntry  1  }

  bwMusicOnHoldSPID   OBJECT-TYPE
    SYNTAX      DisplayString
    MAX-ACCESS    read-only
    STATUS      current
                DESCRIPTION
                                "This string represents a service provider ID"
                ::=  {  bwMusicOnHoldSPEntry  2  }


  bwMusicOnHoldSPNumUses  OBJECT-TYPE
    SYNTAX      Counter32
    MAX-ACCESS    read-write
    STATUS      current
                DESCRIPTION
                        "The service provider counter is incremented every a user hears music on hold"
                ::=  {  bwMusicOnHoldSPEntry  3 }

  bwMusicOnHoldSPExternalSourceNumFailures  OBJECT-TYPE
    SYNTAX      Counter32
    MAX-ACCESS    read-write
    STATUS      current
                DESCRIPTION
                                "This counter is incremented whenever a caller, belonging to the indexed service provider, is put on hold and that the music-on-hold source could not be connected to the caller"
                ::=  {  bwMusicOnHoldSPEntry  4  }

-- Service :: Music on hold :: GROUP TABLE ...........................................

  bwMusicOnHoldGroupEntry OBJECT-TYPE
    SYNTAX    BwMusicOnHoldGroupEntry
    MAX-ACCESS  not-accessible
    STATUS    current
                DESCRIPTION
                        "Each row contains the service counters for the Music On Hold service for each group in the system."
    INDEX   {  bwMusicOnHoldGroupIndex  }
                ::=  { bwMusicOnHoldGroupTable 1 }

        BwMusicOnHoldGroupEntry  ::=  SEQUENCE {
                bwMusicOnHoldGroupIndex  Unsigned32,
                bwMusicOnHoldGroupID  DisplayString,
                bwMusicOnHoldGroupNumUses  Counter32,
                bwMusicOnHoldGroupExternalSourceNumFailures Counter32
                }

  bwMusicOnHoldGroupIndex   OBJECT-TYPE
    SYNTAX      Unsigned32
    MAX-ACCESS    read-only
    STATUS      current
                DESCRIPTION
                                "This column represents the index of the group in the system"
                ::=  {  bwMusicOnHoldGroupEntry  1  }

  bwMusicOnHoldGroupID  OBJECT-TYPE
    SYNTAX      DisplayString
    MAX-ACCESS    read-only
    STATUS      current
                DESCRIPTION
                                "This string represents a group ID"
                ::=  {  bwMusicOnHoldGroupEntry  2  }


  bwMusicOnHoldGroupNumUses OBJECT-TYPE
    SYNTAX      Counter32
    MAX-ACCESS    read-write
    STATUS      current
                DESCRIPTION
                        "The group counter is incremented every a user hears music on hold"
                ::=  {  bwMusicOnHoldGroupEntry  3 }

  bwMusicOnHoldGroupExternalSourceNumFailures OBJECT-TYPE
    SYNTAX      Counter32
    MAX-ACCESS    read-write
    STATUS      current
                DESCRIPTION
                                "This counter is incremented whenever a caller, belonging to the indexed group, is put on hold and that the music-on-hold source could not be connected to the caller"
                ::=  {  bwMusicOnHoldGroupEntry  4  }

-- Service :: callingNameRetrieval ...........................................

  bwCNAMQueriesSent OBJECT-TYPE
    SYNTAX      Counter32
    MAX-ACCESS    read-write
    STATUS      current
                DESCRIPTION
                                "Number of queries that have been sent to the external database inquiring the calling name information."
                ::=  {  callingNameRetrieval  1  }

  bwCNAMQueriesFailed OBJECT-TYPE
    SYNTAX      Counter32
    MAX-ACCESS    read-write
    STATUS      current
                DESCRIPTION
                                "Number of queries that have failed to the external database inquiring the calling name information."
                ::=  {  callingNameRetrieval  2  }

  bwCNAMQueriesTimeout  OBJECT-TYPE
    SYNTAX      Counter32
    MAX-ACCESS    read-write
    STATUS      current
                DESCRIPTION
                                "NumberNumber of queries that have timed out to the external database inquiring the calling name information."
                ::=  {  callingNameRetrieval  3  }


-- Service :: thirdPartyMWIControl ...........................................

  bwThirdPartyMWIControlNotifyIns OBJECT-TYPE
    SYNTAX      Counter32
    MAX-ACCESS    read-write
    STATUS      current
                DESCRIPTION
                                "Number of times a MWI NOTIFY is received."
                ::=  {  thirdPartyMWIControl  1  }

  bwThirdPartyMWIControlNotifyFailures  OBJECT-TYPE
    SYNTAX      Counter32
    MAX-ACCESS    read-write
    STATUS      current
                DESCRIPTION
                                "Number of times a MWI NOTIFY is received for an unknown user, or for a user who is not assigned the service."
                ::=  {  thirdPartyMWIControl  2  }

-- Service :: Call Center ...........................................

  bwCallCenterReportEmailed OBJECT-TYPE
    SYNTAX      Counter32
    MAX-ACCESS    read-write
    STATUS      current
                DESCRIPTION
                        "Number of call center statistics reports emailed."
                ::=  {  callCenter  1  }

  bwCallCenterSPTable OBJECT-TYPE
    SYNTAX    SEQUENCE  OF  BwCallCenterSPEntry
    MAX-ACCESS  not-accessible
    STATUS    current
                DESCRIPTION
                        "Counters for Call Center service measurements for service providers"
                ::=  {  callCenter  2 }

  bwCallCenterGroupTable  OBJECT-TYPE
    SYNTAX    SEQUENCE  OF  BwCallCenterGroupEntry
    MAX-ACCESS  not-accessible
    STATUS    current
                DESCRIPTION
                        "Counters for Call Center service measurements for groups"
                ::=  {  callCenter  3 }

-- Service :: Call Center :: SP TABLE ...........................................

  bwCallCenterSPEntry OBJECT-TYPE
    SYNTAX    BwCallCenterSPEntry
    MAX-ACCESS  not-accessible
    STATUS    current
                DESCRIPTION
                        "Each row contains the service counters for the Call Center service for each service provider in the system"
    INDEX   {  bwCallCenterSPIndex  }
                ::=  { bwCallCenterSPTable 1 }

        BwCallCenterSPEntry  ::=  SEQUENCE {
                bwCallCenterSPIndex  Unsigned32,
                bwCallCenterSPID  DisplayString,
                bwCallCenterSPReportEmailed  Counter32
                }

  bwCallCenterSPIndex   OBJECT-TYPE
    SYNTAX      Unsigned32
    MAX-ACCESS    read-only
    STATUS      current
                DESCRIPTION
                                "This column represents the index of the service provider in the system"
                ::=  {  bwCallCenterSPEntry  1  }

  bwCallCenterSPID  OBJECT-TYPE
    SYNTAX      DisplayString
    MAX-ACCESS    read-only
    STATUS      current
                DESCRIPTION
                                "This string represents a service provider ID"
                ::=  {  bwCallCenterSPEntry  2  }


  bwCallCenterSPReportEmailed OBJECT-TYPE
    SYNTAX      Counter32
    MAX-ACCESS    read-write
    STATUS      current
                DESCRIPTION
                        "Number of call center statistics reports emailed for a given service provider"
                ::=  {  bwCallCenterSPEntry  3 }

-- Service :: Call Center :: GROUP TABLE ...........................................

  bwCallCenterGroupEntry  OBJECT-TYPE
    SYNTAX    BwCallCenterGroupEntry
    MAX-ACCESS  not-accessible
    STATUS    current
                DESCRIPTION
                        "Each row contains the service counters for the Call Center service for each group in the system"
    INDEX   {  bwCallCenterGroupIndex  }
                ::=  { bwCallCenterGroupTable 1 }

        BwCallCenterGroupEntry  ::=  SEQUENCE {
                bwCallCenterGroupIndex  Unsigned32,
                bwCallCenterGroupID  DisplayString,
                bwCallCenterGroupReportEmailed  Counter32
                }

  bwCallCenterGroupIndex    OBJECT-TYPE
    SYNTAX      Unsigned32
    MAX-ACCESS    read-only
    STATUS      current
                DESCRIPTION
                                "This column represents the index of the group in the system"
                ::=  {  bwCallCenterGroupEntry  1  }

  bwCallCenterGroupID   OBJECT-TYPE
    SYNTAX      DisplayString
    MAX-ACCESS    read-only
    STATUS      current
                DESCRIPTION
                                "This string represents a group ID"
                ::=  {  bwCallCenterGroupEntry  2  }


  bwCallCenterGroupReportEmailed  OBJECT-TYPE
    SYNTAX      Counter32
    MAX-ACCESS    read-write
    STATUS      current
                DESCRIPTION
                        "Number of call center statistics reports emailed for a given Group"
                ::=  {  bwCallCenterGroupEntry  3 }

-- Service :: Call Forward Group No Answer ...........................................

  bwCFGNAForward  OBJECT-TYPE
    SYNTAX      Counter32
    MAX-ACCESS    read-write
    STATUS      current
                DESCRIPTION
                                "The number of times CFGNA has forwarded from one agent to another"
                ::=  {  callForwardGroupNoAnswer  1  }

  bwCFGNAOverflowForward  OBJECT-TYPE
    SYNTAX      Counter32
    MAX-ACCESS    read-write
    STATUS      current
                DESCRIPTION
                                "The number of times CGFNA rolls over to the first visited agent and the call forwards to the external destination"
                ::=  {  callForwardGroupNoAnswer  2  }

  bwCFGNAOverflowNoForward  OBJECT-TYPE
    SYNTAX      Counter32
    MAX-ACCESS    read-write
    STATUS      current
                DESCRIPTION
                                "The number of times CGFNA rolls over to the first visited agent and the call is either queued for call centers or given temporarily unavailable treatment for hunt groups"
                ::=  {  callForwardGroupNoAnswer  3  }

  bwCFGNASPTable  OBJECT-TYPE
    SYNTAX    SEQUENCE  OF  BwCFGNASPEntry
    MAX-ACCESS  not-accessible
    STATUS    current
                DESCRIPTION
                        "Counters for Call Center service measurements for service providers"
                ::=  {  callForwardGroupNoAnswer  4 }

  bwCFGNAGroupTable OBJECT-TYPE
    SYNTAX    SEQUENCE  OF  BwCFGNAGroupEntry
    MAX-ACCESS  not-accessible
    STATUS    current
                DESCRIPTION
                        "Counters for Call Center service measurements for groups"
                ::=  {  callForwardGroupNoAnswer  5 }

  bwCFGNAExternalForward  OBJECT-TYPE
    SYNTAX      Counter32
    MAX-ACCESS    read-write
    STATUS      current
                DESCRIPTION
                                "Number of times CFGNA External has forwarded a Hunt Group/Call Center call."
                ::=  {  callForwardGroupNoAnswer  6  }

  bwCFGNAExternalNoForward  OBJECT-TYPE
    SYNTAX      Counter32
    MAX-ACCESS    read-write
    STATUS      current
                DESCRIPTION
                                "Number of times CFGNA External has given Temporarily Unavailable treatment to a Hunt Group/Call Center call."
                ::=  {  callForwardGroupNoAnswer  7  }

-- Service :: Call Forward Group No Answer :: SP TABLE ...........................................

  bwCFGNASPEntry  OBJECT-TYPE
    SYNTAX    BwCFGNASPEntry
    MAX-ACCESS  not-accessible
    STATUS    current
                DESCRIPTION
                        "Each row contains the service counters for the Call Forward Group No Answer service for each service provider in the system"
    INDEX   {  bwCFGNASPIndex  }
                ::=  { bwCFGNASPTable 1 }

        BwCFGNASPEntry  ::=  SEQUENCE {
                bwCFGNASPIndex  Unsigned32,
                bwCFGNASPID  DisplayString,
                bwCFGNASPForward  Counter32,
                bwCFGNASPOverflowForward  Counter32,
                bwCFGNASPOverflowNoForward  Counter32,
                bwCFGNASPExternalForward  Counter32,
                bwCFGNASPExternalNoForward  Counter32
                }

  bwCFGNASPIndex    OBJECT-TYPE
    SYNTAX      Unsigned32
    MAX-ACCESS    read-only
    STATUS      current
                DESCRIPTION
                                "This column represents the index of the service provider in the system"
                ::=  {  bwCFGNASPEntry  1  }

  bwCFGNASPID   OBJECT-TYPE
    SYNTAX      DisplayString
    MAX-ACCESS    read-only
    STATUS      current
                DESCRIPTION
                                "This string represents a service provider ID"
                ::=  {  bwCFGNASPEntry  2  }

  bwCFGNASPForward  OBJECT-TYPE
    SYNTAX      Counter32
    MAX-ACCESS    read-write
    STATUS      current
                DESCRIPTION
                                "The number of times CGFNA rolls over to the first visited agent and the call forwards to the external destination for a given service provider"
                ::=  {  bwCFGNASPEntry  3  }

  bwCFGNASPOverflowForward  OBJECT-TYPE
    SYNTAX      Counter32
    MAX-ACCESS    read-write
    STATUS      current
                DESCRIPTION
                                "The number of times CGFNA rolls over to the first visited agent and the call forwards to the external destination for a given service provider"
                ::=  {  bwCFGNASPEntry  4  }

  bwCFGNASPOverflowNoForward  OBJECT-TYPE
    SYNTAX      Counter32
    MAX-ACCESS    read-write
    STATUS      current
                DESCRIPTION
                                "The number of times CGFNA rolls over to the first visited agent and the call is either queued for call centers or given temporarily unavailable treatment for hunt groups for a given service provider"
                ::=  {  bwCFGNASPEntry  5  }

  bwCFGNASPExternalForward  OBJECT-TYPE
    SYNTAX      Counter32
    MAX-ACCESS    read-write
    STATUS      current
                DESCRIPTION
                                "Number of times CFGNA External has forwarded a Hunt Group/Call Center call for a given service provider."
                ::=  {  bwCFGNASPEntry  6  }

  bwCFGNASPExternalNoForward  OBJECT-TYPE
    SYNTAX      Counter32
    MAX-ACCESS    read-write
    STATUS      current
                DESCRIPTION
                                "Number of times CFGNA External has given Temporarily Unavailable treatment to a Hunt Group/Call Center call for a given service provider."
                ::=  {  bwCFGNASPEntry  7  }

-- Service :: Call Forward Group No Answer :: GROUP TABLE ...........................................

  bwCFGNAGroupEntry OBJECT-TYPE
    SYNTAX    BwCFGNAGroupEntry
    MAX-ACCESS  not-accessible
    STATUS    current
                DESCRIPTION
                        "Each row contains the service counters for the Call Forward Group No Answer service for each group in the system"
    INDEX   {  bwCFGNAGroupIndex  }
                ::=  { bwCFGNAGroupTable 1 }

        BwCFGNAGroupEntry  ::=  SEQUENCE {
                bwCFGNAGroupIndex  Unsigned32,
                bwCFGNAGroupID  DisplayString,
                bwCFGNAGroupForward  Counter32,
                bwCFGNAGroupOverflowForward  Counter32,
                bwCFGNAGroupOverflowNoForward  Counter32,
                bwCFGNAGroupExternalForward  Counter32,
                bwCFGNAGroupExternalNoForward  Counter32
                }

  bwCFGNAGroupIndex   OBJECT-TYPE
    SYNTAX      Unsigned32
    MAX-ACCESS    read-only
    STATUS      current
                DESCRIPTION
                                "This column represents the index of the group in the system"
                ::=  {  bwCFGNAGroupEntry  1  }

  bwCFGNAGroupID  OBJECT-TYPE
    SYNTAX      DisplayString
    MAX-ACCESS    read-only
    STATUS      current
                DESCRIPTION
                                "This string represents a group ID"
                ::=  {  bwCFGNAGroupEntry  2  }

  bwCFGNAGroupForward OBJECT-TYPE
    SYNTAX      Counter32
    MAX-ACCESS    read-write
    STATUS      current
                DESCRIPTION
                                "The number of times CGFNA rolls over to the first visited agent and the call forwards to the external destination for a given group"
                ::=  {  bwCFGNAGroupEntry  3  }

  bwCFGNAGroupOverflowForward OBJECT-TYPE
    SYNTAX      Counter32
    MAX-ACCESS    read-write
    STATUS      current
                DESCRIPTION
                                "The number of times CGFNA rolls over to the first visited agent and the call forwards to the external destination for a given group"
                ::=  {  bwCFGNAGroupEntry  4  }

  bwCFGNAGroupOverflowNoForward OBJECT-TYPE
    SYNTAX      Counter32
    MAX-ACCESS    read-write
    STATUS      current
                DESCRIPTION
                                "The number of times CGFNA rolls over to the first visited agent and the call is either queued for call centers or given temporarily unavailable treatment for hunt groups for a given group"
                ::=  {  bwCFGNAGroupEntry  5  }

  bwCFGNAGroupExternalForward OBJECT-TYPE
    SYNTAX      Counter32
    MAX-ACCESS    read-write
    STATUS      current
                DESCRIPTION
                                "Number of times CFGNA External has forwarded a Hunt Group/Call Center call for a given group."
                ::=  {  bwCFGNAGroupEntry  6  }

  bwCFGNAGroupExternalNoForward OBJECT-TYPE
    SYNTAX      Counter32
    MAX-ACCESS    read-write
    STATUS      current
                DESCRIPTION
                                "Number of times CFGNA External has given Temporarily Unavailable treatment to a Hunt Group/Call Center call for a given group."
                ::=  {  bwCFGNAGroupEntry  7  }

-- Service :: SD100 ...........................................

  bwSD100Program  OBJECT-TYPE
    SYNTAX      Counter32
    MAX-ACCESS    read-write
    STATUS      current
                DESCRIPTION
                                "This counter is incremented each time a new SD100 call is programmed via FAC method on BroadWorks"
                ::=  {  sd100  1  }

  bwSD100Call OBJECT-TYPE
    SYNTAX      Counter32
    MAX-ACCESS    read-write
    STATUS      current
                DESCRIPTION
                                "This counter is incremented each time SD100 code is used to originate a call on BroadWorks"
                ::=  {  sd100  2  }

  bwSD100SPTable  OBJECT-TYPE
    SYNTAX    SEQUENCE  OF  BwSD100SPEntry
    MAX-ACCESS  not-accessible
    STATUS    current
                DESCRIPTION
                        "Counters for sd100 service measurements for service providers"
                ::=  {  sd100  3 }

  bwSD100GroupTable OBJECT-TYPE
    SYNTAX    SEQUENCE  OF  BwSD100GroupEntry
    MAX-ACCESS  not-accessible
    STATUS    current
                DESCRIPTION
                        "Counters for sd100 service measurements for groups"
                ::=  {  sd100  4 }

-- Service :: SD100 :: SP TABLE ...........................................

  bwSD100SPEntry  OBJECT-TYPE
    SYNTAX    BwSD100SPEntry
    MAX-ACCESS  not-accessible
    STATUS    current
                DESCRIPTION
                        "Each row contains the service counters for the sd100 service for each service provider in the system"
    INDEX   {  bwSD100SPIndex  }
                ::=  { bwSD100SPTable 1 }

        BwSD100SPEntry  ::=  SEQUENCE {
                bwSD100SPIndex  Unsigned32,
                bwSD100SPID  DisplayString,
                bwSD100SPProgram  Counter32,
                bwSD100SPCall  Counter32
                }

  bwSD100SPIndex    OBJECT-TYPE
    SYNTAX      Unsigned32
    MAX-ACCESS    read-only
    STATUS      current
                DESCRIPTION
                                "This column represents the index of the service provider in the system"
                ::=  {  bwSD100SPEntry  1  }

  bwSD100SPID   OBJECT-TYPE
    SYNTAX      DisplayString
    MAX-ACCESS    read-only
    STATUS      current
                DESCRIPTION
                                "This string represents a service provider ID"
                ::=  {  bwSD100SPEntry  2  }

  bwSD100SPProgram  OBJECT-TYPE
    SYNTAX      Counter32
    MAX-ACCESS    read-write
    STATUS      current
                DESCRIPTION
                                "This counter is incremented each time a new SD100 call is programmed via the FAC method for a particular service provider"
                ::=  {  bwSD100SPEntry  3  }

  bwSD100SPCall OBJECT-TYPE
    SYNTAX      Counter32
    MAX-ACCESS    read-write
    STATUS      current
                DESCRIPTION
                                "This counter is incremented each time SD100 code is used to originate a call for a particular service provider"
                ::=  {  bwSD100SPEntry  4  }

-- Service :: SD100 :: Group TABLE ...........................................

  bwSD100GroupEntry OBJECT-TYPE
    SYNTAX    BwSD100GroupEntry
    MAX-ACCESS  not-accessible
    STATUS    current
                DESCRIPTION
                        "Each row contains the service counters for the sd100 service for each group in the system"
    INDEX   {  bwSD100GroupIndex  }
                ::=  { bwSD100GroupTable 1 }

        BwSD100GroupEntry  ::=  SEQUENCE {
                bwSD100GroupIndex  Unsigned32,
                bwSD100GroupID  DisplayString,
                bwSD100GroupProgram  Counter32,
                bwSD100GroupCall  Counter32
                }

  bwSD100GroupIndex   OBJECT-TYPE
    SYNTAX      Unsigned32
    MAX-ACCESS    read-only
    STATUS      current
                DESCRIPTION
                                "This column represents the index of the group in the system"
                ::=  {  bwSD100GroupEntry  1  }

  bwSD100GroupID  OBJECT-TYPE
    SYNTAX      DisplayString
    MAX-ACCESS    read-only
    STATUS      current
                DESCRIPTION
                                "This string represents a group ID"
                ::=  {  bwSD100GroupEntry  2  }

  bwSD100GroupProgram OBJECT-TYPE
    SYNTAX      Counter32
    MAX-ACCESS    read-write
    STATUS      current
                DESCRIPTION
                                "This counter is incremented each time a new SD100 call is programmed via the FAC method for a particular group"
                ::=  {  bwSD100GroupEntry  3  }

  bwSD100GroupCall  OBJECT-TYPE
    SYNTAX      Counter32
    MAX-ACCESS    read-write
    STATUS      current
                DESCRIPTION
                                "This counter is incremented each time SD100 code is used to originate a call for a particular group"
                ::=  {  bwSD100GroupEntry  4  }

-- Service :: thirdPartyVMail ...........................................

  bwThirdPartyVoiceMailNbOfCFWBusy  OBJECT-TYPE
    SYNTAX      Counter32
    MAX-ACCESS    read-write
    STATUS      current
                DESCRIPTION
                                "Incremented each time a call is forwarded to an external VM (by the Third-Party Voice Mail Support User service) on busy condition"
                ::=  {  thirdPartyVMail  1  }

  bwThirdPartyVoiceMailNbOfCFWNoAnswer  OBJECT-TYPE
    SYNTAX      Counter32
    MAX-ACCESS    read-write
    STATUS      current
                DESCRIPTION
                                "Incremented each time a call is forwarded to an external VM (by the Third-Party Voice Mail Support User service) on no-answer condition, at the group level"
                ::=  {  thirdPartyVMail  2  }

  bwThirdPartyVMailSPTable  OBJECT-TYPE
    SYNTAX    SEQUENCE  OF  BwThirdPartyVMailSPEntry
    MAX-ACCESS  not-accessible
    STATUS    current
                DESCRIPTION
                        "Counters for the Third Party Voice Mail service measurements for service providers"
                ::=  {  thirdPartyVMail  3 }

  bwThirdPartyVMailGroupTable OBJECT-TYPE
    SYNTAX    SEQUENCE  OF  BwThirdPartyVMailGroupEntry
    MAX-ACCESS  not-accessible
    STATUS    current
                DESCRIPTION
                        "Counters for the Third Party Voice Mail service measurements for groups"
                ::=  {  thirdPartyVMail  4 }

-- Service :: thirdPartyVMail :: SP TABLE ...........................................

  bwThirdPartyVMailSPEntry  OBJECT-TYPE
    SYNTAX    BwThirdPartyVMailSPEntry
    MAX-ACCESS  not-accessible
    STATUS    current
                DESCRIPTION
                        "Each row contains the service counters for the sd100 service for each service provider in the system"
    INDEX   {  bwThirdPartyVMailSPIndex  }
                ::=  { bwThirdPartyVMailSPTable 1 }

        BwThirdPartyVMailSPEntry  ::=  SEQUENCE {
                bwThirdPartyVMailSPIndex  Unsigned32,
                bwThirdPartyVMailSPID  DisplayString,
                bwThirdPartyVoiceMailSPNbOfCFWBusy  Counter32,
                bwThirdPartyVoiceMailSPNbOfCFWNoAnswer  Counter32
                }

  bwThirdPartyVMailSPIndex    OBJECT-TYPE
    SYNTAX      Unsigned32
    MAX-ACCESS    read-only
    STATUS      current
                DESCRIPTION
                                "This column represents the index of the service provider in the system"
                ::=  {  bwThirdPartyVMailSPEntry  1  }

  bwThirdPartyVMailSPID   OBJECT-TYPE
    SYNTAX      DisplayString
    MAX-ACCESS    read-only
    STATUS      current
                DESCRIPTION
                                "This string represents a service provider ID"
                ::=  {  bwThirdPartyVMailSPEntry  2  }

  bwThirdPartyVoiceMailSPNbOfCFWBusy  OBJECT-TYPE
    SYNTAX      Counter32
    MAX-ACCESS    read-write
    STATUS      current
                DESCRIPTION
                                "Incremented each time a call is forwarded to an external VM (by the Third-Party Voice Mail Support User service) on busy condition for a particular service provider"
                ::=  {  bwThirdPartyVMailSPEntry  3  }

  bwThirdPartyVoiceMailSPNbOfCFWNoAnswer  OBJECT-TYPE
    SYNTAX      Counter32
    MAX-ACCESS    read-write
    STATUS      current
                DESCRIPTION
                                "Incremented each time a call is forwarded to an external VM (by the Third-Party Voice Mail Support User service) on no-answer condition, at the group level"
                ::=  {  bwThirdPartyVMailSPEntry  4  }

-- Service :: thirdPartyVMail :: Group TABLE ...........................................

  bwThirdPartyVMailGroupEntry OBJECT-TYPE
    SYNTAX    BwThirdPartyVMailGroupEntry
    MAX-ACCESS  not-accessible
    STATUS    current
                DESCRIPTION
                        "Each row contains the service counters for the sd100 service for each group in the system"
    INDEX   {  bwThirdPartyVMailGroupIndex  }
                ::=  { bwThirdPartyVMailGroupTable 1 }

        BwThirdPartyVMailGroupEntry  ::=  SEQUENCE {
                bwThirdPartyVMailGroupIndex  Unsigned32,
                bwThirdPartyVMailGroupID  DisplayString,
                bwThirdPartyVoiceMailGroupNbOfCFWBusy  Counter32,
                bwThirdPartyVoiceMailGroupNbOfCFWNoAnswer  Counter32
                }

  bwThirdPartyVMailGroupIndex   OBJECT-TYPE
    SYNTAX      Unsigned32
    MAX-ACCESS    read-only
    STATUS      current
                DESCRIPTION
                                "This column represents the index of the group in the system"
                ::=  {  bwThirdPartyVMailGroupEntry  1  }

  bwThirdPartyVMailGroupID  OBJECT-TYPE
    SYNTAX      DisplayString
    MAX-ACCESS    read-only
    STATUS      current
                DESCRIPTION
                                "This string represents a group ID"
                ::=  {  bwThirdPartyVMailGroupEntry  2  }

  bwThirdPartyVoiceMailGroupNbOfCFWBusy OBJECT-TYPE
    SYNTAX      Counter32
    MAX-ACCESS    read-write
    STATUS      current
                DESCRIPTION
                                "Incremented each time a call is forwarded to an external VM (by the Third-Party Voice Mail Support User service) on busy condition for a particular group"
                ::=  {  bwThirdPartyVMailGroupEntry  3  }

  bwThirdPartyVoiceMailGroupNbOfCFWNoAnswer OBJECT-TYPE
    SYNTAX      Counter32
    MAX-ACCESS    read-write
    STATUS      current
                DESCRIPTION
                                "Incremented each time a call is forwarded to an external VM (by the Third-Party Voice Mail Support User service) on no-answer condition, at the group level for a particular group"
                ::=  {  bwThirdPartyVMailGroupEntry  4  }

-- Service :: directedCallPickup ...........................................

  bwDirectedCallPickupNumAttempts OBJECT-TYPE
    SYNTAX      Counter32
    MAX-ACCESS    read-write
    STATUS      current
                DESCRIPTION
                                "This counter shall be incremented each time a user attempts to pick up a call using the Directed Call Pickup FAC"
                ::=  {  directedCallPickup  1  }

  bwDirectedCallPickupNumFailures OBJECT-TYPE
    SYNTAX      Counter32
    MAX-ACCESS    read-write
    STATUS      current
                DESCRIPTION
                                "This counter shall be incremented each time a user is unsuccessful at picking up a call using the Directed Call Pickup FAC"
                ::=  {  directedCallPickup  2  }

  bwDirectedCallPickupSPTable OBJECT-TYPE
    SYNTAX    SEQUENCE  OF  BwDirectedCallPickupSPEntry
    MAX-ACCESS  not-accessible
    STATUS    current
                DESCRIPTION
                        "Counters for the Directed Call Pick Up service measurements for service providers"
                ::=  {  directedCallPickup  3 }

  bwDirectedCallPickupGroupTable  OBJECT-TYPE
    SYNTAX    SEQUENCE  OF  BwDirectedCallPickupGroupEntry
    MAX-ACCESS  not-accessible
    STATUS    current
                DESCRIPTION
                        "Counters for the Directed Call Pick Up service measurements for groups"
                ::=  {  directedCallPickup  4 }

-- Service :: directedCallPickup :: SP TABLE ...........................................

  bwDirectedCallPickupSPEntry OBJECT-TYPE
    SYNTAX    BwDirectedCallPickupSPEntry
    MAX-ACCESS  not-accessible
    STATUS    current
                DESCRIPTION
                        "Each row contains the service counters for the directed call pick-up service for each service provider in the system"
    INDEX   {  bwDirectedCallPickupSPIndex  }
                ::=  { bwDirectedCallPickupSPTable 1 }

        BwDirectedCallPickupSPEntry  ::=  SEQUENCE {
                bwDirectedCallPickupSPIndex  Unsigned32,
                bwDirectedCallPickupSPID  DisplayString,
                bwDirectedCallPickupSPNumAttempts  Counter32,
                bwDirectedCallPickupSPNumFailures  Counter32
                }

  bwDirectedCallPickupSPIndex   OBJECT-TYPE
    SYNTAX      Unsigned32
    MAX-ACCESS    read-only
    STATUS      current
                DESCRIPTION
                                "This column represents the index of the service provider in the system"
                ::=  {  bwDirectedCallPickupSPEntry  1  }

  bwDirectedCallPickupSPID  OBJECT-TYPE
    SYNTAX      DisplayString
    MAX-ACCESS    read-only
    STATUS      current
                DESCRIPTION
                                "This string represents a service provider ID"
                ::=  {  bwDirectedCallPickupSPEntry  2  }

  bwDirectedCallPickupSPNumAttempts OBJECT-TYPE
    SYNTAX      Counter32
    MAX-ACCESS    read-write
    STATUS      current
                DESCRIPTION
                                "This counter shall be incremented each time a user attempts to pick up a call using the Directed Call Pickup FAC for a particular service provider"
                ::=  {  bwDirectedCallPickupSPEntry  3  }

  bwDirectedCallPickupSPNumFailures OBJECT-TYPE
    SYNTAX      Counter32
    MAX-ACCESS    read-write
    STATUS      current
                DESCRIPTION
                                "This counter shall be incremented each time a user is unsuccessful at picking up a call using the Directed Call Pickup FAC for a particular service provider"
                ::=  {  bwDirectedCallPickupSPEntry  4  }

-- Service :: directedCallPickup :: Group TABLE ...........................................

  bwDirectedCallPickupGroupEntry  OBJECT-TYPE
    SYNTAX    BwDirectedCallPickupGroupEntry
    MAX-ACCESS  not-accessible
    STATUS    current
                DESCRIPTION
                        "Each row contains the service counters for the directed call pick-up service for each service provider in the system"
    INDEX   {  bwDirectedCallPickupGroupIndex  }
                ::=  { bwDirectedCallPickupGroupTable 1 }

        BwDirectedCallPickupGroupEntry  ::=  SEQUENCE {
                bwDirectedCallPickupGroupIndex  Unsigned32,
                bwDirectedCallPickupGroupID  DisplayString,
                bwDirectedCallPickupGroupNumAttempts  Counter32,
                bwDirectedCallPickupGroupNumFailures  Counter32
                }

  bwDirectedCallPickupGroupIndex    OBJECT-TYPE
    SYNTAX      Unsigned32
    MAX-ACCESS    read-only
    STATUS      current
                DESCRIPTION
                                "This column represents the index of the service provider in the system"
                ::=  {  bwDirectedCallPickupGroupEntry  1  }

  bwDirectedCallPickupGroupID   OBJECT-TYPE
    SYNTAX      DisplayString
    MAX-ACCESS    read-only
    STATUS      current
                DESCRIPTION
                                "This string represents a service provider ID"
                ::=  {  bwDirectedCallPickupGroupEntry  2  }

  bwDirectedCallPickupGroupNumAttempts  OBJECT-TYPE
    SYNTAX      Counter32
    MAX-ACCESS    read-write
    STATUS      current
                DESCRIPTION
                                "This counter shall be incremented each time a user attempts to pick up a call using the Directed Call Pickup FAC for a particular group"
                ::=  {  bwDirectedCallPickupGroupEntry  3  }

  bwDirectedCallPickupGroupNumFailures  OBJECT-TYPE
    SYNTAX      Counter32
    MAX-ACCESS    read-write
    STATUS      current
                DESCRIPTION
                                "This counter shall be incremented each time a user is unsuccessful at picking up a call using the Directed Call Pickup FAC for a particular group"
                ::=  {  bwDirectedCallPickupGroupEntry  4  }

-- Service :: flashCallHold ...........................................

  bwFlashCallHoldNumActivations OBJECT-TYPE
    SYNTAX      Counter32
    MAX-ACCESS    read-write
    STATUS      current
                DESCRIPTION
                                "This counter shall be incremented each time a user successfully holds a call via the Flash Call Hold FAC"
                ::=  {  flashCallHold  1  }

  bwFlashCallHoldSPTable  OBJECT-TYPE
    SYNTAX    SEQUENCE  OF  BwFlashCallHoldSPEntry
    MAX-ACCESS  not-accessible
    STATUS    current
                DESCRIPTION
                        "Counters for the Flash Call Hold service measurements for service providers"
                ::=  {  flashCallHold  2 }

  bwFlashCallHoldGroupTable OBJECT-TYPE
    SYNTAX    SEQUENCE  OF  BwFlashCallHoldGroupEntry
    MAX-ACCESS  not-accessible
    STATUS    current
                DESCRIPTION
                        "Counters for the Flash Call Hold service measurements for groups"
                ::=  {  flashCallHold  3 }

-- Service :: flashCallHold :: SP TABLE ...........................................

  bwFlashCallHoldSPEntry  OBJECT-TYPE
    SYNTAX    BwFlashCallHoldSPEntry
    MAX-ACCESS  not-accessible
    STATUS    current
                DESCRIPTION
                        "Each row contains the service counters for the directed call pick-up service for each service provider in the system"
    INDEX   {  bwFlashCallHoldSPIndex  }
                ::=  { bwFlashCallHoldSPTable 1 }

        BwFlashCallHoldSPEntry  ::=  SEQUENCE {
                bwFlashCallHoldSPIndex  Unsigned32,
                bwFlashCallHoldSPID  DisplayString,
                bwFlashCallHoldSPNumActivations  Counter32
                }

  bwFlashCallHoldSPIndex    OBJECT-TYPE
    SYNTAX      Unsigned32
    MAX-ACCESS    read-only
    STATUS      current
                DESCRIPTION
                                "This column represents the index of the service provider in the system"
                ::=  {  bwFlashCallHoldSPEntry  1  }

  bwFlashCallHoldSPID   OBJECT-TYPE
    SYNTAX      DisplayString
    MAX-ACCESS    read-only
    STATUS      current
                DESCRIPTION
                                "This string represents a service provider ID"
                ::=  {  bwFlashCallHoldSPEntry  2  }

  bwFlashCallHoldSPNumActivations OBJECT-TYPE
    SYNTAX      Counter32
    MAX-ACCESS    read-write
    STATUS      current
                DESCRIPTION
                                "This counter shall be incremented each time a user successfully holds a call via the Flash Call Hold FAC for a specigic service provider"
                ::=  {  bwFlashCallHoldSPEntry  3  }

-- Service :: flashCallHold :: Group TABLE ...........................................

  bwFlashCallHoldGroupEntry OBJECT-TYPE
    SYNTAX    BwFlashCallHoldGroupEntry
    MAX-ACCESS  not-accessible
    STATUS    current
                DESCRIPTION
                        "Each row contains the service counters for the directed call pick-up service for each group in the system"
    INDEX   {  bwFlashCallHoldGroupIndex  }
                ::=  { bwFlashCallHoldGroupTable 1 }

        BwFlashCallHoldGroupEntry  ::=  SEQUENCE {
                bwFlashCallHoldGroupIndex  Unsigned32,
                bwFlashCallHoldGroupID  DisplayString,
                bwFlashCallHoldGroupNumActivations  Counter32
                }

  bwFlashCallHoldGroupIndex   OBJECT-TYPE
    SYNTAX      Unsigned32
    MAX-ACCESS    read-only
    STATUS      current
                DESCRIPTION
                                "This column represents the index of the service provider in the system"
                ::=  {  bwFlashCallHoldGroupEntry  1  }

  bwFlashCallHoldGroupID  OBJECT-TYPE
    SYNTAX      DisplayString
    MAX-ACCESS    read-only
    STATUS      current
                DESCRIPTION
                                "This string represents a service provider ID"
                ::=  {  bwFlashCallHoldGroupEntry  2  }

  bwFlashCallHoldGroupNumActivations  OBJECT-TYPE
    SYNTAX      Counter32
    MAX-ACCESS    read-write
    STATUS      current
                DESCRIPTION
                                "This counter shall be incremented each time a user successfully holds a call via the Flash Call Hold FAC for a specigic group"
                ::=  {  bwFlashCallHoldGroupEntry  3  }

-- Service :: emergencyZones ...........................................

  bwEZRegistrationsRejected OBJECT-TYPE
    SYNTAX      Counter32
    MAX-ACCESS    read-write
    STATUS      current
                DESCRIPTION
                                "This counter is incremented whenever a SIP device registration is rejected because of the Emergency Zone service setting for a group"
                ::=  {  emergencyZones  1  }

  bwEZEmergencyCallsRejected  OBJECT-TYPE
    SYNTAX      Counter32
    MAX-ACCESS    read-write
    STATUS      current
                DESCRIPTION
                                "This counter is incremented whenever an emergency call is rejected because of the emergency zone service setting for a group"
                ::=  {  emergencyZones  2  }

  bwEZNormalCallsRejected OBJECT-TYPE
    SYNTAX      Counter32
    MAX-ACCESS    read-write
    STATUS      current
                DESCRIPTION
                                "This counter is incremented whenever a non-emergency call is rejected because of the Emergency Zone serivce setting for a group"
                ::=  {  emergencyZones  3  }

  bwEZSPTable OBJECT-TYPE
    SYNTAX    SEQUENCE  OF  BwEZSPEntry
    MAX-ACCESS  not-accessible
    STATUS    current
                DESCRIPTION
                        "Counters for the Emergency Zones service measurements for service providers"
                ::=  {  emergencyZones  4 }

  bwEZGroupTable  OBJECT-TYPE
    SYNTAX    SEQUENCE  OF  BwEZGroupEntry
    MAX-ACCESS  not-accessible
    STATUS    current
                DESCRIPTION
                        "Counters for the Emergency Zones service measurements for groups"
                ::=  {  emergencyZones  5 }

-- Service :: emergencyZones :: SP TABLE ...........................................

  bwEZSPEntry OBJECT-TYPE
    SYNTAX    BwEZSPEntry
    MAX-ACCESS  not-accessible
    STATUS    current
                DESCRIPTION
                        "Each row contains the service counters for the emergency zone service for each service provider in the system"
    INDEX   {  bwEZSPIndex  }
                ::=  { bwEZSPTable 1 }

        BwEZSPEntry  ::=  SEQUENCE {
                bwEZSPIndex  Unsigned32,
                bwEZSPID  DisplayString,
                bwEZSPRegistrationsRejected  Counter32,
                bwEZSPEmergencyCallsRejected  Counter32,
                bwEZSPNormalCallsRejected  Counter32
                }

  bwEZSPIndex   OBJECT-TYPE
    SYNTAX      Unsigned32
    MAX-ACCESS    read-only
    STATUS      current
                DESCRIPTION
                                "This column represents the index of the service provider in the system"
                ::=  {  bwEZSPEntry  1  }

  bwEZSPID  OBJECT-TYPE
    SYNTAX      DisplayString
    MAX-ACCESS    read-only
    STATUS      current
                DESCRIPTION
                                "This string represents a service provider ID"
                ::=  {  bwEZSPEntry  2  }

  bwEZSPRegistrationsRejected OBJECT-TYPE
    SYNTAX      Counter32
    MAX-ACCESS    read-write
    STATUS      current
                DESCRIPTION
                                "This counter is incremented whenever a SIP device registration is rejected because of the Emergency Zone service setting for a group for a specific service provider"
                ::=  {  bwEZSPEntry  3  }

  bwEZSPEmergencyCallsRejected  OBJECT-TYPE
    SYNTAX      Counter32
    MAX-ACCESS    read-write
    STATUS      current
                DESCRIPTION
                                "This counter is incremented whenever an emergency call is rejected because of the emergency zone service setting for a group for a specific service provider"
                ::=  {  bwEZSPEntry  4  }

  bwEZSPNormalCallsRejected OBJECT-TYPE
    SYNTAX      Counter32
    MAX-ACCESS    read-write
    STATUS      current
                DESCRIPTION
                                "This counter is incremented whenever a non-emergency call is rejected because of the Emergency Zone serivce setting for a group for a specific service provider"
                ::=  {  bwEZSPEntry  5  }

-- Service :: emergencyZones :: Group TABLE ...........................................

  bwEZGroupEntry  OBJECT-TYPE
    SYNTAX    BwEZGroupEntry
    MAX-ACCESS  not-accessible
    STATUS    current
                DESCRIPTION
                        "Each row contains the service counters for the emergency zone service for each group in the system"
    INDEX   {  bwEZGroupIndex  }
                ::=  { bwEZGroupTable 1 }

        BwEZGroupEntry  ::=  SEQUENCE {
                bwEZGroupIndex  Unsigned32,
                bwEZGroupID  DisplayString,
                bwEZGroupRegistrationsRejected  Counter32,
                bwEZGroupEmergencyCallsRejected  Counter32,
                bwEZGroupNormalCallsRejected  Counter32
                }

  bwEZGroupIndex    OBJECT-TYPE
    SYNTAX      Unsigned32
    MAX-ACCESS    read-only
    STATUS      current
                DESCRIPTION
                                "This column represents the index of the service provider in the system"
                ::=  {  bwEZGroupEntry  1  }

  bwEZGroupID   OBJECT-TYPE
    SYNTAX      DisplayString
    MAX-ACCESS    read-only
    STATUS      current
                DESCRIPTION
                                "This string represents a service provider ID"
                ::=  {  bwEZGroupEntry  2  }

  bwEZGroupRegistrationsRejected  OBJECT-TYPE
    SYNTAX      Counter32
    MAX-ACCESS    read-write
    STATUS      current
                DESCRIPTION
                                "This counter is incremented whenever a SIP device registration is rejected because of the Emergency Zone service setting for a group for a specific group"
                ::=  {  bwEZGroupEntry  3  }

  bwEZGroupEmergencyCallsRejected OBJECT-TYPE
    SYNTAX      Counter32
    MAX-ACCESS    read-write
    STATUS      current
                DESCRIPTION
                                "This counter is incremented whenever an emergency call is rejected because of the emergency zone service setting for a group for a specific group"
                ::=  {  bwEZGroupEntry  4  }

  bwEZGroupNormalCallsRejected  OBJECT-TYPE
    SYNTAX      Counter32
    MAX-ACCESS    read-write
    STATUS      current
                DESCRIPTION
                                "This counter is incremented whenever a non-emergency call is rejected because of the Emergency Zone serivce setting for a group for a specific group"
                ::=  {  bwEZGroupEntry  5  }

-- Service :: Directed Call Pickup with Barge In ...........................................

  bwDPUBIAttempt  OBJECT-TYPE
    SYNTAX      Counter32
    MAX-ACCESS    read-write
    STATUS      current
                DESCRIPTION
                                "This counter is incremented each time a user attempts Directed Call Pickup with Barge-in"
                ::=  {  dpubi  1  }

  bwDPUBIFailure  OBJECT-TYPE
    SYNTAX      Counter32
    MAX-ACCESS    read-write
    STATUS      current
                DESCRIPTION
                                "This counter is incremented each time a user fails to pickup a call with Directed Call Pickup with Barge-in"
                ::=  {  dpubi  2  }

  bwDPUBIBargeIn  OBJECT-TYPE
    SYNTAX      Counter32
    MAX-ACCESS    read-write
    STATUS      current
                DESCRIPTION
                                "This counter is incremented each time a user successfully barges into a call with Directed Call Pickup with Barge-in"
                ::=  {  dpubi  3  }

  bwDPUBIBargeInFailure OBJECT-TYPE
    SYNTAX      Counter32
    MAX-ACCESS    read-write
    STATUS      current
                DESCRIPTION
                                "This counter is incremented each time a user fails to barge into a call with Directed Call Pickup with Barge-in"
                ::=  {  dpubi  4  }

  bwDPUBISPTable  OBJECT-TYPE
    SYNTAX    SEQUENCE  OF  BwDPUBISPEntry
    MAX-ACCESS  not-accessible
    STATUS    current
                DESCRIPTION
                        "Counters for the Directed Call Pickup with Barge In service measurements for service providers"
                ::=  {  dpubi  5 }

  bwDPUBIGroupTable OBJECT-TYPE
    SYNTAX    SEQUENCE  OF  BwDPUBIGroupEntry
    MAX-ACCESS  not-accessible
    STATUS    current
                DESCRIPTION
                        "Counters for the Directed Call Pickup with Barge In service measurements for groups"
                ::=  {  dpubi  6 }

  bwDPUBIExempt OBJECT-TYPE
    SYNTAX      Counter32
    MAX-ACCESS    read-write
    STATUS      current
                DESCRIPTION
                                "This counter is incremented each time a DPUBI attempt is blocked by the picked up user's Barge-in Exempt service."
                ::=  {  dpubi  7  }

-- Service :: Directed Call Pickup with Barge In :: SP TABLE ...........................................

  bwDPUBISPEntry  OBJECT-TYPE
    SYNTAX    BwDPUBISPEntry
    MAX-ACCESS  not-accessible
    STATUS    current
                DESCRIPTION
                        "Each row contains the service counters for the Directed Call Pickup with Barge In service for each service provider in the system"
    INDEX   {  bwDPUBISPIndex  }
                ::=  { bwDPUBISPTable 1 }

        BwDPUBISPEntry  ::=  SEQUENCE {
                bwDPUBISPIndex  Unsigned32,
                bwDPUBISPID  DisplayString,
                bwDPUBISPAttempt  Counter32,
                bwDPUBISPFailure  Counter32,
                bwDPUBISPBargeIn  Counter32,
                bwDPUBISPBargeInFailure  Counter32,
                bwDPUBISPExempt Counter32
                }

  bwDPUBISPIndex    OBJECT-TYPE
    SYNTAX      Unsigned32
    MAX-ACCESS    read-only
    STATUS      current
                DESCRIPTION
                                "This column represents the index of the service provider in the system"
                ::=  {  bwDPUBISPEntry  1  }

  bwDPUBISPID   OBJECT-TYPE
    SYNTAX      DisplayString
    MAX-ACCESS    read-only
    STATUS      current
                DESCRIPTION
                                "This string represents a service provider ID"
                ::=  {  bwDPUBISPEntry  2  }

  bwDPUBISPAttempt  OBJECT-TYPE
    SYNTAX      Counter32
    MAX-ACCESS    read-write
    STATUS      current
                DESCRIPTION
                                "This counter is incremented each time a user under the Service Provider attempts Directed Call Pickup with Barge-in"
                ::=  {  bwDPUBISPEntry  3  }

  bwDPUBISPFailure  OBJECT-TYPE
    SYNTAX      Counter32
    MAX-ACCESS    read-write
    STATUS      current
                DESCRIPTION
                                "This counter is incremented each time a user under the Service Provider fails to pickup a call with Directed Call Pickup with Barge-in"
                ::=  {  bwDPUBISPEntry  4  }

  bwDPUBISPBargeIn  OBJECT-TYPE
    SYNTAX      Counter32
    MAX-ACCESS    read-write
    STATUS      current
                DESCRIPTION
                                "This counter is incremented each time a user under the Service Provider successfully barges into a call with Directed Call Pickup with Barge-in"
                ::=  {  bwDPUBISPEntry  5  }

  bwDPUBISPBargeInFailure OBJECT-TYPE
    SYNTAX      Counter32
    MAX-ACCESS    read-write
    STATUS      current
                DESCRIPTION
                                "This counter is incremented each time a user under the Service Provider fails to barge into a call with Directed Call Pickup with Barge-in"
                ::=  {  bwDPUBISPEntry  6  }

  bwDPUBISPExempt OBJECT-TYPE
    SYNTAX      Counter32
    MAX-ACCESS    read-write
    STATUS      current
                DESCRIPTION
                                "This counter is incremented each time a DPUBI attempt is blocked by the picked up user's Barge-in Exempt service for a given service provider."
                ::=  {  bwDPUBISPEntry  7  }

-- Service :: Directed Call Pickup with Barge In :: GROUP TABLE ...........................................

  bwDPUBIGroupEntry OBJECT-TYPE
    SYNTAX    BwDPUBIGroupEntry
    MAX-ACCESS  not-accessible
    STATUS    current
                DESCRIPTION
                        "Each row contains the service counters for the Directed Call Pickup with Barge In service for each group in the system"
    INDEX   {  bwDPUBIGroupIndex  }
                ::=  { bwDPUBIGroupTable 1 }

        BwDPUBIGroupEntry  ::=  SEQUENCE {
                bwDPUBIGroupIndex  Unsigned32,
                bwDPUBIGroupID  DisplayString,
                bwDPUBIGroupAttempt  Counter32,
                bwDPUBIGroupFailure  Counter32,
                bwDPUBIGroupBargeIn  Counter32,
                bwDPUBIGroupBargeInFailure  Counter32,
                bwDPUBIGroupExempt Counter32
                }

  bwDPUBIGroupIndex   OBJECT-TYPE
    SYNTAX      Unsigned32
    MAX-ACCESS    read-only
    STATUS      current
                DESCRIPTION
                                "This column represents the index of the group in the system"
                ::=  {  bwDPUBIGroupEntry  1  }

  bwDPUBIGroupID  OBJECT-TYPE
    SYNTAX      DisplayString
    MAX-ACCESS    read-only
    STATUS      current
                DESCRIPTION
                                "This string represents a group ID"
                ::=  {  bwDPUBIGroupEntry  2  }

  bwDPUBIGroupAttempt OBJECT-TYPE
    SYNTAX      Counter32
    MAX-ACCESS    read-write
    STATUS      current
                DESCRIPTION
                                "This counter is incremented each time a user under the group attempts Directed Call Pickup with Barge-in"
                ::=  {  bwDPUBIGroupEntry  3  }

  bwDPUBIGroupFailure OBJECT-TYPE
    SYNTAX      Counter32
    MAX-ACCESS    read-write
    STATUS      current
                DESCRIPTION
                                "This counter is incremented each time a user under the group fails to pickup a call with Directed Call Pickup with Barge-in"
                ::=  {  bwDPUBIGroupEntry  4  }

  bwDPUBIGroupBargeIn OBJECT-TYPE
    SYNTAX      Counter32
    MAX-ACCESS    read-write
    STATUS      current
                DESCRIPTION
                                "This counter is incremented each time a user under the group successfully barges into a call with Directed Call Pickup with Barge-in"
                ::=  {  bwDPUBIGroupEntry  5  }

  bwDPUBIGroupBargeInFailure  OBJECT-TYPE
    SYNTAX      Counter32
    MAX-ACCESS    read-write
    STATUS      current
                DESCRIPTION
                                "This counter is incremented each time a user under the group fails to barge into a call with Directed Call Pickup with Barge-in"
                ::=  {  bwDPUBIGroupEntry  6  }

  bwDPUBIGroupExempt  OBJECT-TYPE
    SYNTAX      Counter32
    MAX-ACCESS    read-write
    STATUS      current
                DESCRIPTION
                                "This counter is incremented each time a DPUBI attempt is blocked by the picked up user's Barge-in Exempt service for a given group."
                ::=  {  bwDPUBIGroupEntry  7  }

-- Service :: Automatic Call Back ...........................................

  bwACBStarted  OBJECT-TYPE
    SYNTAX      Counter32
    MAX-ACCESS    read-write
    STATUS      current
                DESCRIPTION
                                "System wide, number of times Automatic Callback has been activated"
                ::=  {  acb  1  }


  bwACBExpired  OBJECT-TYPE
    SYNTAX      Counter32
    MAX-ACCESS    read-write
    STATUS      current
                DESCRIPTION
                                "System wide, number of times Automatic Callback's time to wait for an idle line has expired. The default time to wait is 30 minutes"
                ::=  {  acb  2  }

  bwACBMaxSession OBJECT-TYPE
    SYNTAX      Counter32
    MAX-ACCESS    read-write
    STATUS      current
                DESCRIPTION
                                "System wide, number of time the max number of outstanding Automatic Callback sessions has been reached"
                ::=  {  acb  3  }

  bwACBSPTable  OBJECT-TYPE
    SYNTAX    SEQUENCE  OF  BwACBSPEntry
    MAX-ACCESS  not-accessible
    STATUS    current
                DESCRIPTION
                        "Counters for the Automatic Call Back service measurements for service providers"
                ::=  {  acb  4 }

  bwACBGroupTable OBJECT-TYPE
    SYNTAX    SEQUENCE  OF  BwACBGroupEntry
    MAX-ACCESS  not-accessible
    STATUS    current
                DESCRIPTION
                        "Counters for the Automatic Call Back service measurements for groups"
                ::=  {  acb  5 }

-- Service :: Automatic Call Back :: SP TABLE ...........................................

  bwACBSPEntry  OBJECT-TYPE
    SYNTAX    BwACBSPEntry
    MAX-ACCESS  not-accessible
    STATUS    current
                DESCRIPTION
                        "Each row contains the service counters for the Automatic Call Back service for each service provider in the system"
    INDEX   {  bwACBSPIndex  }
                ::=  { bwACBSPTable 1 }

        BwACBSPEntry  ::=  SEQUENCE {
                bwACBSPIndex  Unsigned32,
                bwACBSPID  DisplayString,
                bwACBSPStarted  Counter32,
                bwACBSPExpired  Counter32,
                bwACBSPMaxSession  Counter32
                }

  bwACBSPIndex    OBJECT-TYPE
    SYNTAX      Unsigned32
    MAX-ACCESS    read-only
    STATUS      current
                DESCRIPTION
                                "This column represents the index of the service provider in the system"
                ::=  {  bwACBSPEntry  1  }

  bwACBSPID   OBJECT-TYPE
    SYNTAX      DisplayString
    MAX-ACCESS    read-only
    STATUS      current
                DESCRIPTION
                                "This string represents a service provider ID"
                ::=  {  bwACBSPEntry  2  }

  bwACBSPStarted  OBJECT-TYPE
    SYNTAX      Counter32
    MAX-ACCESS    read-write
    STATUS      current
                DESCRIPTION
                                "Number of times Automatic Callback has been activated for a given service provider"
                ::=  {  bwACBSPEntry  3  }

  bwACBSPExpired  OBJECT-TYPE
    SYNTAX      Counter32
    MAX-ACCESS    read-write
    STATUS      current
                DESCRIPTION
                                "Number of times Automatic Callback's time to wait for an idle line has expired for a given service provider. The default time to wait is 30 minutes."
                ::=  {  bwACBSPEntry  4  }

  bwACBSPMaxSession OBJECT-TYPE
    SYNTAX      Counter32
    MAX-ACCESS    read-write
    STATUS      current
                DESCRIPTION
                                "Number of time the max number of outstanding Automatic Callback sessions has been reached for a given service provider"
                ::=  {  bwACBSPEntry  5  }

-- Service :: Automatic Call Back :: Group TABLE ...........................................

  bwACBGroupEntry OBJECT-TYPE
    SYNTAX    BwACBGroupEntry
    MAX-ACCESS  not-accessible
    STATUS    current
                DESCRIPTION
                        "Each row contains the service counters for the Automatic Call Back service for each group in the system"
    INDEX   {  bwACBGroupIndex  }
                ::=  { bwACBGroupTable 1 }

        BwACBGroupEntry  ::=  SEQUENCE {
                bwACBGroupIndex  Unsigned32,
                bwACBGroupID  DisplayString,
                bwACBGroupStarted  Counter32,
                bwACBGroupExpired  Counter32,
                bwACBGroupMaxSession  Counter32
                }

  bwACBGroupIndex   OBJECT-TYPE
    SYNTAX      Unsigned32
    MAX-ACCESS    read-only
    STATUS      current
                DESCRIPTION
                                "This column represents the index of the group in the system"
                ::=  {  bwACBGroupEntry  1  }

  bwACBGroupID  OBJECT-TYPE
    SYNTAX      DisplayString
    MAX-ACCESS    read-only
    STATUS      current
                DESCRIPTION
                                "This string represents a group ID"
                ::=  {  bwACBGroupEntry  2  }

  bwACBGroupStarted OBJECT-TYPE
    SYNTAX      Counter32
    MAX-ACCESS    read-write
    STATUS      current
                DESCRIPTION
                                "Number of times Automatic Callback has been activated for a given group"
                ::=  {  bwACBGroupEntry  3  }

  bwACBGroupExpired OBJECT-TYPE
    SYNTAX      Counter32
    MAX-ACCESS    read-write
    STATUS      current
                DESCRIPTION
                                "Number of times Automatic Callback's time to wait for an idle line has expired for a given group. The default time to wait is 30 minutes."
                ::=  {  bwACBGroupEntry  4  }

  bwACBGroupMaxSession  OBJECT-TYPE
    SYNTAX      Counter32
    MAX-ACCESS    read-write
    STATUS      current
                DESCRIPTION
                                "Number of time the max number of outstanding Automatic Callback sessions has been reached for a given group"
                ::=  {  bwACBGroupEntry  5  }

-- Service :: Ring Timeout ...........................................

  bwRingTimeoutNumExpires OBJECT-TYPE
    SYNTAX      Counter32
    MAX-ACCESS    read-write
    STATUS      current
                DESCRIPTION
                                "Number of times the ring timeout timer expires for the entire system."
                ::=  {  ringTimeout  1  }

  bwRingTimeoutSPTable  OBJECT-TYPE
    SYNTAX    SEQUENCE  OF  BwRingTimeoutSPEntry
    MAX-ACCESS  not-accessible
    STATUS    current
                DESCRIPTION
                        "Counters for the Ring Timeout service measurements for service providers"
                ::=  {  ringTimeout  2 }

  bwRingTimeoutGroupTable OBJECT-TYPE
    SYNTAX    SEQUENCE  OF  BwRingTimeoutGroupEntry
    MAX-ACCESS  not-accessible
    STATUS    current
                DESCRIPTION
                        "Counters for the Ring Timeout service measurements for groups"
                ::=  {  ringTimeout  3 }


-- Service :: Ring Timeout :: SP TABLE ...........................................

  bwRingTimeoutSPEntry  OBJECT-TYPE
    SYNTAX    BwRingTimeoutSPEntry
    MAX-ACCESS  not-accessible
    STATUS    current
                DESCRIPTION
                        "Each row contains the service counters for the Ring Timeout service for each service provider in the system"
    INDEX   {  bwRingTimeoutSPIndex  }
                ::=  { bwRingTimeoutSPTable 1 }

        BwRingTimeoutSPEntry  ::=  SEQUENCE {
                bwRingTimeoutSPIndex  Unsigned32,
                bwRingTimeoutSPID  DisplayString,
                bwRingTimeoutSPNumExpires  Counter32
                }

  bwRingTimeoutSPIndex    OBJECT-TYPE
    SYNTAX      Unsigned32
    MAX-ACCESS    read-only
    STATUS      current
                DESCRIPTION
                                "This column represents the index of the service provider in the system"
                ::=  {  bwRingTimeoutSPEntry  1  }

  bwRingTimeoutSPID   OBJECT-TYPE
    SYNTAX      DisplayString
    MAX-ACCESS    read-only
    STATUS      current
                DESCRIPTION
                                "This string represents a service provider ID"
                ::=  {  bwRingTimeoutSPEntry  2  }

  bwRingTimeoutSPNumExpires OBJECT-TYPE
    SYNTAX      Counter32
    MAX-ACCESS    read-write
    STATUS      current
                DESCRIPTION
                                "Number of times the ring timeout timer expires for a given service provider"
                ::=  {  bwRingTimeoutSPEntry  3  }

-- Service :: Ring Timeout :: Group TABLE ...........................................

  bwRingTimeoutGroupEntry OBJECT-TYPE
    SYNTAX    BwRingTimeoutGroupEntry
    MAX-ACCESS  not-accessible
    STATUS    current
                DESCRIPTION
                        "Each row contains the service counters for the Ring Timeout service for each group in the system"
    INDEX   {  bwRingTimeoutGroupIndex  }
                ::=  { bwRingTimeoutGroupTable 1 }

        BwRingTimeoutGroupEntry  ::=  SEQUENCE {
                bwRingTimeoutGroupIndex  Unsigned32,
                bwRingTimeoutGroupID  DisplayString,
                bwRingTimeoutGroupNumExpires  Counter32
                }

  bwRingTimeoutGroupIndex   OBJECT-TYPE
    SYNTAX      Unsigned32
    MAX-ACCESS    read-only
    STATUS      current
                DESCRIPTION
                                "This column represents the index of the group in the system"
                ::=  {  bwRingTimeoutGroupEntry  1  }

  bwRingTimeoutGroupID  OBJECT-TYPE
    SYNTAX      DisplayString
    MAX-ACCESS    read-only
    STATUS      current
                DESCRIPTION
                                "This string represents a group ID"
                ::=  {  bwRingTimeoutGroupEntry  2  }

  bwRingTimeoutGroupNumExpires  OBJECT-TYPE
    SYNTAX      Counter32
    MAX-ACCESS    read-write
    STATUS      current
                DESCRIPTION
                                "Number of times the ring timeout timer expires for a given group"
                ::=  {  bwRingTimeoutGroupEntry  3  }

-- Service :: sequentialRing ...........................................

  bwSequentialRingNumAttempts OBJECT-TYPE
    SYNTAX      Counter32
    MAX-ACCESS    read-write
    STATUS      current
                DESCRIPTION
                                "This counter is incremented whenever the sequential ring service forwards a call to the next in the list. The counter is not incremented for an attempt to alert the base location, unless it appears in the sequential ring list."
                ::=  {  sequentialRing  1  }

  bwSequentialRingNumNoAnswer OBJECT-TYPE
    SYNTAX      Counter32
    MAX-ACCESS    read-write
    STATUS      current
                DESCRIPTION
                                "This counter is incremented whenever the sequential ring service reaches the end of the list, and no users are available"
                ::=  {  sequentialRing  2  }

  bwSequentialRingSPTable OBJECT-TYPE
    SYNTAX    SEQUENCE  OF  BwSequentialRingSPEntry
    MAX-ACCESS  not-accessible
    STATUS    current
                DESCRIPTION
                        "This table tracks sequential ring measurements per service provider"
                ::=  {  sequentialRing  3 }

  bwSequentialRingGroupTable  OBJECT-TYPE
    SYNTAX    SEQUENCE  OF  BwSequentialRingGroupEntry
    MAX-ACCESS  not-accessible
    STATUS    current
                DESCRIPTION
                        "This table tracks sequential ring measurements per groups"
                ::=  {  sequentialRing  4 }

  bwSequentialRingActivations OBJECT-TYPE
    SYNTAX      Counter32
    MAX-ACCESS    read-write
    STATUS      current
                DESCRIPTION
                                "This counter is incremented every time the Sequential Ring service is activated by an incoming call (service is active and screening is successful)."
                ::=  {  sequentialRing  5  }

  bwSequentialRingAnswered  OBJECT-TYPE
    SYNTAX      Counter32
    MAX-ACCESS    read-write
    STATUS      current
                DESCRIPTION
                                "This counter is incremented every time a caller gets connected to a location as a result of Sequential Ring"
                ::=  {  sequentialRing  6  }

  bwSequentialRingAbandoned OBJECT-TYPE
    SYNTAX      Counter32
    MAX-ACCESS    read-write
    STATUS      current
                DESCRIPTION
                                "This counter is incremented every time a caller hangs up before Sequential Ring completes"
                ::=  {  sequentialRing  7  }

-- Service :: sequentialRing :: SP TABLE ...........................................

  bwSequentialRingSPEntry OBJECT-TYPE
    SYNTAX    BwSequentialRingSPEntry
    MAX-ACCESS  not-accessible
    STATUS    current
                DESCRIPTION
                        "Each row contains the service counters for the sequentialRing service for each service provider in the system"
    INDEX   {  bwSequentialRingSPIndex  }
                ::=  { bwSequentialRingSPTable 1 }

        BwSequentialRingSPEntry  ::=  SEQUENCE {
                bwSequentialRingSPIndex  Unsigned32,
                bwSequentialRingSPID  DisplayString,
                bwSequentialRingSPNumAttempts  Counter32,
                bwSequentialRingSPNumNoAnswer  Counter32,
                bwSequentialRingSPActivations  Counter32,
                bwSequentialRingSPAnswered  Counter32,
                bwSequentialRingSPAbandoned  Counter32
                }

  bwSequentialRingSPIndex   OBJECT-TYPE
    SYNTAX      Unsigned32
    MAX-ACCESS    read-only
    STATUS      current
                DESCRIPTION
                                "This column represents the index of the service provider in the system"
                ::=  {  bwSequentialRingSPEntry  1  }

  bwSequentialRingSPID  OBJECT-TYPE
    SYNTAX      DisplayString
    MAX-ACCESS    read-only
    STATUS      current
                DESCRIPTION
                                "This string represents a service provider ID"
                ::=  {  bwSequentialRingSPEntry  2  }

  bwSequentialRingSPNumAttempts OBJECT-TYPE
    SYNTAX      Counter32
    MAX-ACCESS    read-write
    STATUS      current
                DESCRIPTION
                                "This counter is incremented whenever the sequential ring service forwards a call to the next user in the list for a given service provider. The counter is not incremented for an attempt to alert the base location, unless it appears in the sequential ring list."
                ::=  {  bwSequentialRingSPEntry  3  }

  bwSequentialRingSPNumNoAnswer OBJECT-TYPE
    SYNTAX      Counter32
    MAX-ACCESS    read-write
    STATUS      current
                DESCRIPTION
                                "This counter is incremented whenever the sequential ring service reaches the end of the list, and no users are available for a given service provider"
                ::=  {  bwSequentialRingSPEntry  4  }

  bwSequentialRingSPActivations OBJECT-TYPE
    SYNTAX      Counter32
    MAX-ACCESS    read-write
    STATUS      current
                DESCRIPTION
                                "This counter is incremented every time the Sequential Ring service is activated by an incoming call (service is active and screening is successful) for a given Service Provider."
                ::=  {  bwSequentialRingSPEntry  5  }

  bwSequentialRingSPAnswered  OBJECT-TYPE
    SYNTAX      Counter32
    MAX-ACCESS    read-write
    STATUS      current
                DESCRIPTION
                                "This counter is incremented every time a caller gets connected to a location as a result of Sequential Ring for a given Service Provider"
                ::=  {  bwSequentialRingSPEntry  6  }

  bwSequentialRingSPAbandoned OBJECT-TYPE
    SYNTAX      Counter32
    MAX-ACCESS    read-write
    STATUS      current
                DESCRIPTION
                                "This counter is incremented every time a caller hangs up before Sequential Ring completes for a given Service Provider"
                ::=  {  bwSequentialRingSPEntry  7  }

-- Service :: sequentialRing :: GROUP TABLE ...........................................

  bwSequentialRingGroupEntry  OBJECT-TYPE
    SYNTAX    BwSequentialRingGroupEntry
    MAX-ACCESS  not-accessible
    STATUS    current
                DESCRIPTION
                        "Each row contains the service counters for the sequentialRing service for each group in the system"
    INDEX   {  bwSequentialRingGroupIndex  }
                ::=  { bwSequentialRingGroupTable 1 }

        BwSequentialRingGroupEntry  ::=  SEQUENCE {
                bwSequentialRingGroupIndex  Unsigned32,
                bwSequentialRingGroupID  DisplayString,
                bwSequentialRingGroupNumAttempts  Counter32,
                bwSequentialRingGroupNumNoAnswer  Counter32,
                bwSequentialRingGroupActivations  Counter32,
                bwSequentialRingGroupAnswered  Counter32,
                bwSequentialRingGroupAbandoned  Counter32
                }

  bwSequentialRingGroupIndex    OBJECT-TYPE
    SYNTAX      Unsigned32
    MAX-ACCESS    read-only
    STATUS      current
                DESCRIPTION
                                "This column represents the index of the group in the system"
                ::=  {  bwSequentialRingGroupEntry  1  }

  bwSequentialRingGroupID   OBJECT-TYPE
    SYNTAX      DisplayString
    MAX-ACCESS    read-only
    STATUS      current
                DESCRIPTION
                                "This string represents a group ID"
                ::=  {  bwSequentialRingGroupEntry  2  }

  bwSequentialRingGroupNumAttempts  OBJECT-TYPE
    SYNTAX      Counter32
    MAX-ACCESS    read-write
    STATUS      current
                DESCRIPTION
                                "This counter is incremented whenever the sequential ring service forwards a call to the next user in the list for a given group. The counter is not incremented for an attempt to alert the base location, unless it appears in the sequential ring list."
                ::=  {  bwSequentialRingGroupEntry  3  }

  bwSequentialRingGroupNumNoAnswer  OBJECT-TYPE
    SYNTAX      Counter32
    MAX-ACCESS    read-write
    STATUS      current
                DESCRIPTION
                                "This counter is incremented whenever the sequential ring service reaches the end of the list, and no users are available for a given group"
                ::=  {  bwSequentialRingGroupEntry  4  }

  bwSequentialRingGroupActivations  OBJECT-TYPE
    SYNTAX      Counter32
    MAX-ACCESS    read-write
    STATUS      current
                DESCRIPTION
                                "This counter is incremented every time the Sequential Ring service is activated by an incoming call (service is active and screening is successful) for a given Group"
                ::=  {  bwSequentialRingGroupEntry  5  }

  bwSequentialRingGroupAnswered OBJECT-TYPE
    SYNTAX      Counter32
    MAX-ACCESS    read-write
    STATUS      current
                DESCRIPTION
                                "This counter is incremented every time a caller gets connected to a location as a result of Sequential Ring for a given Group"
                ::=  {  bwSequentialRingGroupEntry  6  }

  bwSequentialRingGroupAbandoned  OBJECT-TYPE
    SYNTAX      Counter32
    MAX-ACCESS    read-write
    STATUS      current
                DESCRIPTION
                                "This counter is incremented every time a caller hangs up before Sequential Ring completes for a given Group"
                ::=  {  bwSequentialRingGroupEntry  7  }

-- Service :: Video Add-On ...........................................

  bwVAOOutgoingAttempts OBJECT-TYPE
    SYNTAX      Counter32
    MAX-ACCESS    read-write
    STATUS      current
                DESCRIPTION
                                "This counter is incremented each time a video add on call is attempted for an outgoing call."
                ::=  {  videoAddOn  1  }

  bwVAOOutgoingSuccess  OBJECT-TYPE
    SYNTAX      Counter32
    MAX-ACCESS    read-write
    STATUS      current
                DESCRIPTION
                        "This counter is incremented each time a video add on call attempt is successful for an outgoing call."
                ::=  {  videoAddOn  2 }

  bwVAOIncomingAttempts OBJECT-TYPE
    SYNTAX      Counter32
    MAX-ACCESS    read-write
    STATUS      current
                DESCRIPTION
                        "This counter is incremented each time a video add on call is attempted for an incoming call."
                ::=  {  videoAddOn  3 }

  bwVAOIncomingSuccess  OBJECT-TYPE
    SYNTAX      Counter32
    MAX-ACCESS    read-write
    STATUS      current
                DESCRIPTION
                        "This counter is incremented each time a video add on call attempt is successful for an incoming call."
                ::=  {  videoAddOn  4 }

  bwVAOSPTable  OBJECT-TYPE
    SYNTAX    SEQUENCE  OF  BwVAOSPEntry
    MAX-ACCESS  not-accessible
    STATUS    current
                DESCRIPTION
                        "Counters for the Ring Timeout service measurements for service providers"
                ::=  {  videoAddOn  5 }

  bwVAOGroupTable OBJECT-TYPE
    SYNTAX    SEQUENCE  OF  BwVAOGroupEntry
    MAX-ACCESS  not-accessible
    STATUS    current
                DESCRIPTION
                        "Counters for the Ring Timeout service measurements for groups"
                ::=  {  videoAddOn  6 }

-- Service :: Video Add-On :: SP TABLE ...........................................

  bwVAOSPEntry  OBJECT-TYPE
    SYNTAX    BwVAOSPEntry
    MAX-ACCESS  not-accessible
    STATUS    current
                DESCRIPTION
                        "Each row contains the service counters for the Video Add-On service for each service provider in the system"
    INDEX   {  bwVAOSPIndex  }
                ::=  { bwVAOSPTable 1 }

        BwVAOSPEntry  ::=  SEQUENCE {
                bwVAOSPIndex  Unsigned32,
                bwVAOSPID  DisplayString,
                bwVAOSPOutgoingAttempts  Counter32,
                bwVAOSPOutgoingSuccess  Counter32,
                bwVAOSPIncomingAttempts  Counter32,
                bwVAOSPIncomingSuccess  Counter32
                }

  bwVAOSPIndex    OBJECT-TYPE
    SYNTAX      Unsigned32
    MAX-ACCESS    read-only
    STATUS      current
                DESCRIPTION
                                "This column represents the index of the service provider in the system"
                ::=  {  bwVAOSPEntry  1  }

  bwVAOSPID   OBJECT-TYPE
    SYNTAX      DisplayString
    MAX-ACCESS    read-only
    STATUS      current
                DESCRIPTION
                                "This string represents a service provider ID"
                ::=  {  bwVAOSPEntry  2  }

  bwVAOSPOutgoingAttempts OBJECT-TYPE
    SYNTAX      Counter32
    MAX-ACCESS    read-write
    STATUS      current
                DESCRIPTION
                                "This counter is incremented each time a video add on call is attempted for an outgoing call for the given service provider."
                ::=  {  bwVAOSPEntry  3  }

  bwVAOSPOutgoingSuccess  OBJECT-TYPE
    SYNTAX      Counter32
    MAX-ACCESS    read-write
    STATUS      current
                DESCRIPTION
                        "This counter is incremented each time a video add on call attempt is successful for an outgoing call for the given service provider."
                ::=  {  bwVAOSPEntry  4 }

  bwVAOSPIncomingAttempts OBJECT-TYPE
    SYNTAX      Counter32
    MAX-ACCESS    read-write
    STATUS      current
                DESCRIPTION
                        "This counter is incremented each time a video add on call is attempted for an incoming call for the given service provider."
                ::=  {  bwVAOSPEntry  5 }

  bwVAOSPIncomingSuccess  OBJECT-TYPE
    SYNTAX      Counter32
    MAX-ACCESS    read-write
    STATUS      current
                DESCRIPTION
                        "This counter is incremented each time a video add on call attempt is successful for an incoming call for the given service provider."
                ::=  {  bwVAOSPEntry  6 }

-- Service :: Video Add-On :: GROUP TABLE ...........................................

  bwVAOGroupEntry OBJECT-TYPE
    SYNTAX    BwVAOGroupEntry
    MAX-ACCESS  not-accessible
    STATUS    current
                DESCRIPTION
                        "Each row contains the service counters for the Video Add-On service for each group in the system"
    INDEX   {  bwVAOGroupIndex  }
                ::=  { bwVAOGroupTable 1 }

        BwVAOGroupEntry  ::=  SEQUENCE {
                bwVAOGroupIndex  Unsigned32,
                bwVAOGroupID  DisplayString,
                bwVAOGroupOutgoingAttempts  Counter32,
                bwVAOGroupOutgoingSuccess  Counter32,
                bwVAOGroupIncomingAttempts  Counter32,
                bwVAOGroupIncomingSuccess  Counter32
                }

  bwVAOGroupIndex   OBJECT-TYPE
    SYNTAX      Unsigned32
    MAX-ACCESS    read-only
    STATUS      current
                DESCRIPTION
                                "This column represents the index of the group in the system"
                ::=  {  bwVAOGroupEntry  1  }

  bwVAOGroupID  OBJECT-TYPE
    SYNTAX      DisplayString
    MAX-ACCESS    read-only
    STATUS      current
                DESCRIPTION
                                "This string represents a group ID"
                ::=  {  bwVAOGroupEntry  2  }

  bwVAOGroupOutgoingAttempts  OBJECT-TYPE
    SYNTAX      Counter32
    MAX-ACCESS    read-write
    STATUS      current
                DESCRIPTION
                                "This counter is incremented each time a video add on call is attempted for an outgoing call for the given group."
                ::=  {  bwVAOGroupEntry  3  }

  bwVAOGroupOutgoingSuccess   OBJECT-TYPE
    SYNTAX      Counter32
    MAX-ACCESS    read-write
    STATUS      current
                DESCRIPTION
                        "This counter is incremented each time a video add on call attempt is successful for an outgoing call for the given group."
                ::=  {  bwVAOGroupEntry  4 }

  bwVAOGroupIncomingAttempts  OBJECT-TYPE
    SYNTAX      Counter32
    MAX-ACCESS    read-write
    STATUS      current
                DESCRIPTION
                        "This counter is incremented each time a video add on call is attempted for an incoming call for the given group."
                ::=  {  bwVAOGroupEntry  5 }

  bwVAOGroupIncomingSuccess OBJECT-TYPE
    SYNTAX      Counter32
    MAX-ACCESS    read-write
    STATUS      current
                DESCRIPTION
                        "This counter is incremented each time a video add on call attempt is successful for an incoming call for the given group."
                ::=  {  bwVAOGroupEntry  6 }

-- Service :: Malicious Call Trace ...........................................

  bwMaliciousCallTraceApplied OBJECT-TYPE
    SYNTAX      Counter32
    MAX-ACCESS    read-write
    STATUS      current
                DESCRIPTION
                                "This counter is incremented each time a the Malicious Call Trace serevice is activated."
                ::=  {  mct  1  }

  bwMaliciousCallTraceSPTable   OBJECT-TYPE
    SYNTAX    SEQUENCE  OF  BwMaliciousCallTraceSPEntry
    MAX-ACCESS  not-accessible
    STATUS    current
                DESCRIPTION
                        "Counters for the Malicious Call Trace service measurements for service providers"
                ::=  {  mct  2 }

  bwMaliciousCallTraceGroupTable  OBJECT-TYPE
    SYNTAX    SEQUENCE  OF  BwMaliciousCallTraceGroupEntry
    MAX-ACCESS  not-accessible
    STATUS    current
                DESCRIPTION
                        "Counters for the Malicious Call Trace service measurements for groups"
                ::=  {  mct  3 }

-- Service :: Malicious Call Trace :: SP TABLE ...........................................

  bwMaliciousCallTraceSPEntry OBJECT-TYPE
    SYNTAX    BwMaliciousCallTraceSPEntry
    MAX-ACCESS  not-accessible
    STATUS    current
                DESCRIPTION
                        "Each row contains the service counters for the Malicious Call Trace service for each service provider in the system"
    INDEX   {  bwMaliciousCallTraceSPIndex  }
                ::=  { bwMaliciousCallTraceSPTable 1 }

        BwMaliciousCallTraceSPEntry  ::=  SEQUENCE {
                bwMaliciousCallTraceSPIndex  Unsigned32,
                bwMaliciousCallTraceSPID  DisplayString,
                bwMaliciousCallTraceSPApplied  Counter32
                }

  bwMaliciousCallTraceSPIndex   OBJECT-TYPE
    SYNTAX      Unsigned32
    MAX-ACCESS    read-only
    STATUS      current
                DESCRIPTION
                                "This column represents the index of the service provider in the system"
                ::=  {  bwMaliciousCallTraceSPEntry  1  }

  bwMaliciousCallTraceSPID  OBJECT-TYPE
    SYNTAX      DisplayString
    MAX-ACCESS    read-only
    STATUS      current
                DESCRIPTION
                                "This string represents a service provider ID"
                ::=  {  bwMaliciousCallTraceSPEntry  2  }

  bwMaliciousCallTraceSPApplied OBJECT-TYPE
    SYNTAX      Counter32
    MAX-ACCESS    read-write
    STATUS      current
                DESCRIPTION
                                "This counter is incremented each time a the Malicious Call Trace serevice is activated for the given service provider."
                ::=  {  bwMaliciousCallTraceSPEntry  3  }

-- Service :: Malicious Call Trace :: Group TABLE ...........................................

  bwMaliciousCallTraceGroupEntry  OBJECT-TYPE
    SYNTAX    BwMaliciousCallTraceGroupEntry
    MAX-ACCESS  not-accessible
    STATUS    current
                DESCRIPTION
                        "Each row contains the service counters for the Malicious Call Trace service for each group in the system"
    INDEX   {  bwMaliciousCallTraceGroupIndex  }
                ::=  { bwMaliciousCallTraceGroupTable 1 }

        BwMaliciousCallTraceGroupEntry  ::=  SEQUENCE {
                bwMaliciousCallTraceGroupIndex  Unsigned32,
                bwMaliciousCallTraceGroupID  DisplayString,
                bwMaliciousCallTraceGroupApplied  Counter32
                }

  bwMaliciousCallTraceGroupIndex    OBJECT-TYPE
    SYNTAX      Unsigned32
    MAX-ACCESS    read-only
    STATUS      current
                DESCRIPTION
                                "This column represents the index of the service provider in the system"
                ::=  {  bwMaliciousCallTraceGroupEntry  1  }

  bwMaliciousCallTraceGroupID   OBJECT-TYPE
    SYNTAX      DisplayString
    MAX-ACCESS    read-only
    STATUS      current
                DESCRIPTION
                                "This string represents a service provider ID"
                ::=  {  bwMaliciousCallTraceGroupEntry  2  }

  bwMaliciousCallTraceGroupApplied  OBJECT-TYPE
    SYNTAX      Counter32
    MAX-ACCESS    read-write
    STATUS      current
                DESCRIPTION
                                "This counter is incremented each time a the Malicious Call Trace serevice is activated for the given group."
                ::=  {  bwMaliciousCallTraceGroupEntry  3  }

-- Service :: Push To Talk ...........................................

  bwPTTInvoke OBJECT-TYPE
    SYNTAX      Counter32
    MAX-ACCESS    read-write
    STATUS      current
                DESCRIPTION
                                "Counts the number of times a user has originated a Push to Talk call."
                ::=  {  pushToTalk  1  }

  bwPTTReject OBJECT-TYPE
    SYNTAX      Counter32
    MAX-ACCESS    read-write
    STATUS      current
                DESCRIPTION
                                "Counts the number of times a user has rejected a Push to Talk call because of their access list."
                ::=  {  pushToTalk  2  }

  bwPTTSPTable  OBJECT-TYPE
    SYNTAX    SEQUENCE  OF  BwPTTSPEntry
    MAX-ACCESS  not-accessible
    STATUS    current
                DESCRIPTION
                        "Counters for the Push To Talk service measurements for service providers"
                ::=  {  pushToTalk  3 }

  bwPTTGroupTable OBJECT-TYPE
    SYNTAX    SEQUENCE  OF  BwPTTGroupEntry
    MAX-ACCESS  not-accessible
    STATUS    current
                DESCRIPTION
                        "Counters for the Push To Talk service measurements for groups"
                ::=  {  pushToTalk  4 }

-- Service :: Push To Talk :: SP TABLE ...........................................

  bwPTTSPEntry  OBJECT-TYPE
    SYNTAX    BwPTTSPEntry
    MAX-ACCESS  not-accessible
    STATUS    current
                DESCRIPTION
                        "Each row contains the service counters for the Push To Talk service for each service provider in the system"
    INDEX   {  bwPTTSPIndex  }
                ::=  { bwPTTSPTable 1 }

        BwPTTSPEntry  ::=  SEQUENCE {
                bwPTTSPIndex  Unsigned32,
                bwPTTSPID  DisplayString,
                bwPTTSPInvoke  Counter32,
                bwPTTSPReject  Counter32
                }

  bwPTTSPIndex    OBJECT-TYPE
    SYNTAX      Unsigned32
    MAX-ACCESS    read-only
    STATUS      current
                DESCRIPTION
                                "This column represents the index of the service provider in the system"
                ::=  {  bwPTTSPEntry  1  }

  bwPTTSPID   OBJECT-TYPE
    SYNTAX      DisplayString
    MAX-ACCESS    read-only
    STATUS      current
                DESCRIPTION
                                "This string represents a service provider ID"
                ::=  {  bwPTTSPEntry  2  }

  bwPTTSPInvoke OBJECT-TYPE
    SYNTAX      Counter32
    MAX-ACCESS    read-write
    STATUS      current
                DESCRIPTION
                                "Counts the number of times a user has originated a Push to Talk call for a given service provider."
                ::=  {  bwPTTSPEntry  3  }

  bwPTTSPReject OBJECT-TYPE
    SYNTAX      Counter32
    MAX-ACCESS    read-write
    STATUS      current
                DESCRIPTION
                                "Counts the number of times a user has rejected a Push to Talk call because of their access list for a given service provider."
                ::=  {  bwPTTSPEntry  4  }

-- Service :: Push To Talk :: Group TABLE ...........................................

  bwPTTGroupEntry OBJECT-TYPE
    SYNTAX    BwPTTGroupEntry
    MAX-ACCESS  not-accessible
    STATUS    current
                DESCRIPTION
                        "Each row contains the service counters for the Push To Talk service for each group in the system"
    INDEX   {  bwPTTGroupIndex  }
                ::=  { bwPTTGroupTable 1 }

        BwPTTGroupEntry  ::=  SEQUENCE {
                bwPTTGroupIndex  Unsigned32,
                bwPTTGroupID  DisplayString,
                bwPTTGroupInvoke  Counter32,
                bwPTTGroupReject  Counter32
                }

  bwPTTGroupIndex   OBJECT-TYPE
    SYNTAX      Unsigned32
    MAX-ACCESS    read-only
    STATUS      current
                DESCRIPTION
                                "This column represents the index of the group in the system"
                ::=  {  bwPTTGroupEntry  1  }

  bwPTTGroupID  OBJECT-TYPE
    SYNTAX      DisplayString
    MAX-ACCESS    read-only
    STATUS      current
                DESCRIPTION
                                "This string represents a group ID"
                ::=  {  bwPTTGroupEntry  2  }

  bwPTTGroupInvoke  OBJECT-TYPE
    SYNTAX      Counter32
    MAX-ACCESS    read-write
    STATUS      current
                DESCRIPTION
                                "Counts the number of times a user has originated a Push to Talk call for a given group."
                ::=  {  bwPTTGroupEntry  3  }

  bwPTTGroupReject  OBJECT-TYPE
    SYNTAX      Counter32
    MAX-ACCESS    read-write
    STATUS      current
                DESCRIPTION
                                "Counts the number of times a user has rejected a Push to Talk call because of their access list for agiven group."
                ::=  {  bwPTTGroupEntry  4  }

-- Service :: Hoteling ...........................................

  bwHotelingAssociate OBJECT-TYPE
    SYNTAX      Counter32
    MAX-ACCESS    read-write
    STATUS      current
                DESCRIPTION
                                "This counter is incremented each time a guest - host association is created."
                ::=  {  hoteling  1  }

  bwHotelingDisassociate  OBJECT-TYPE
    SYNTAX      Counter32
    MAX-ACCESS    read-write
    STATUS      current
                DESCRIPTION
                                "This counter is incremented each time a guest - host association is removed."
                ::=  {  hoteling  2  }

  bwHotelingTimeout OBJECT-TYPE
    SYNTAX      Counter32
    MAX-ACCESS    read-write
    STATUS      current
                DESCRIPTION
                                "This counter is incremented each time a guest - host association is removed due to a timeout."
                ::=  {  hoteling  3  }

  bwHotelingSPTable OBJECT-TYPE
    SYNTAX    SEQUENCE  OF  BwHotelingSPEntry
    MAX-ACCESS  not-accessible
    STATUS    current
                DESCRIPTION
                        "Counters for the Hoteling service measurements for service providers"
                ::=  {  hoteling  4 }

  bwHotelingGroupTable  OBJECT-TYPE
    SYNTAX    SEQUENCE  OF  BwHotelingGroupEntry
    MAX-ACCESS  not-accessible
    STATUS    current
                DESCRIPTION
                        "Counters for the Hoteling service measurements for groups"
                ::=  {  hoteling  5 }

-- Service :: Hoteling :: SP TABLE ...........................................

  bwHotelingSPEntry OBJECT-TYPE
    SYNTAX    BwHotelingSPEntry
    MAX-ACCESS  not-accessible
    STATUS    current
                DESCRIPTION
                        "Each row contains the service counters for the Hoteling service for each service provider in the system"
    INDEX   {  bwHotelingSPIndex  }
                ::=  { bwHotelingSPTable 1 }

        BwHotelingSPEntry  ::=  SEQUENCE {
                bwHotelingSPIndex  Unsigned32,
                bwHotelingSPID  DisplayString,
                bwHotelingSPAssociate  Counter32,
                bwHotelingSPDisassociate  Counter32,
                bwHotelingSPTimeout  Counter32
                }

  bwHotelingSPIndex   OBJECT-TYPE
    SYNTAX      Unsigned32
    MAX-ACCESS    read-only
    STATUS      current
                DESCRIPTION
                                "This column represents the index of the service provider in the system"
                ::=  {  bwHotelingSPEntry  1  }

  bwHotelingSPID  OBJECT-TYPE
    SYNTAX      DisplayString
    MAX-ACCESS    read-only
    STATUS      current
                DESCRIPTION
                                "This string represents a service provider ID"
                ::=  {  bwHotelingSPEntry  2  }

  bwHotelingSPAssociate OBJECT-TYPE
    SYNTAX      Counter32
    MAX-ACCESS    read-write
    STATUS      current
                DESCRIPTION
                                "This counter is incremented each time a guest - host association is created for a given service provider."
                ::=  {  bwHotelingSPEntry  3  }

  bwHotelingSPDisassociate  OBJECT-TYPE
    SYNTAX      Counter32
    MAX-ACCESS    read-write
    STATUS      current
                DESCRIPTION
                                "This counter is incremented each time a guest - host association is removed for a given service provider."
                ::=  {  bwHotelingSPEntry  4  }

  bwHotelingSPTimeout OBJECT-TYPE
    SYNTAX      Counter32
    MAX-ACCESS    read-write
    STATUS      current
                DESCRIPTION
                                "This counter is incremented each time a guest - host association is removed due to a timeout for a given service provider."
                ::=  {  bwHotelingSPEntry  5  }

-- Service :: Hoteling :: Group TABLE ...........................................

  bwHotelingGroupEntry  OBJECT-TYPE
    SYNTAX    BwHotelingGroupEntry
    MAX-ACCESS  not-accessible
    STATUS    current
                DESCRIPTION
                        "Each row contains the service counters for the Hoteling service for each group in the system"
    INDEX   {  bwHotelingGroupIndex  }
                ::=  { bwHotelingGroupTable 1 }

        BwHotelingGroupEntry  ::=  SEQUENCE {
                bwHotelingGroupIndex  Unsigned32,
                bwHotelingGroupID  DisplayString,
                bwHotelingGroupAssociate  Counter32,
                bwHotelingGroupDisassociate  Counter32,
                bwHotelingGroupTimeout  Counter32
                }

  bwHotelingGroupIndex    OBJECT-TYPE
    SYNTAX      Unsigned32
    MAX-ACCESS    read-only
    STATUS      current
                DESCRIPTION
                                "This column represents the index of the group in the system"
                ::=  {  bwHotelingGroupEntry  1  }

  bwHotelingGroupID   OBJECT-TYPE
    SYNTAX      DisplayString
    MAX-ACCESS    read-only
    STATUS      current
                DESCRIPTION
                                "This string represents a group ID"
                ::=  {  bwHotelingGroupEntry  2  }

  bwHotelingGroupAssociate  OBJECT-TYPE
    SYNTAX      Counter32
    MAX-ACCESS    read-write
    STATUS      current
                DESCRIPTION
                                "This counter is incremented each time a guest - host association is created for a given group."
                ::=  {  bwHotelingGroupEntry  3  }

  bwHotelingGroupDisassociate OBJECT-TYPE
    SYNTAX      Counter32
    MAX-ACCESS    read-write
    STATUS      current
                DESCRIPTION
                                "This counter is incremented each time a guest - host association is removed for a given group."
                ::=  {  bwHotelingGroupEntry  4  }

  bwHotelingGroupTimeout  OBJECT-TYPE
    SYNTAX      Counter32
    MAX-ACCESS    read-write
    STATUS      current
                DESCRIPTION
                                "This counter is incremented each time a guest - host association is removed due to a timeout for a given group."
                ::=  {  bwHotelingGroupEntry  5  }

-- Service :: preferredCarrier ...........................................

  bwSubscriptionUserPIC OBJECT-TYPE
    SYNTAX      Counter32
    MAX-ACCESS    read-write
    STATUS      current
                DESCRIPTION
                                "This counter shall be incremented each time the user PICs are used, but not explicitly dialed."
                ::=  {  preferredCarrier  1  }

  bwSubscriptionGroupPIC  OBJECT-TYPE
    SYNTAX      Counter32
    MAX-ACCESS    read-write
    STATUS      current
                DESCRIPTION
                                "This counter shall be incremented each time the group PICs are used, but not explicitly dialed."
                ::=  {  preferredCarrier  2  }

  bwSubscriptionServiceProviderPIC  OBJECT-TYPE
    SYNTAX      Counter32
    MAX-ACCESS    read-write
    STATUS      current
                DESCRIPTION
                                "This counter shall be incremented each time the service provider PICs are used, but not explicitly dialed."
                ::=  {  preferredCarrier  3  }

  bwSubscriptionDialedUserPIC OBJECT-TYPE
    SYNTAX      Counter32
    MAX-ACCESS    read-write
    STATUS      current
                DESCRIPTION
                                "This counter shall be incremented each time the user PICs are used and explicitly dialed."
                ::=  {  preferredCarrier  4  }


  bwSubscriptionDialedGroupPIC  OBJECT-TYPE
    SYNTAX      Counter32
    MAX-ACCESS    read-write
    STATUS      current
                DESCRIPTION
                                "This counter shall be incremented each time the group PICs are used and explicitly dialed."
                ::=  {  preferredCarrier  5  }

  bwSubscriptionDialedServiceProviderPIC  OBJECT-TYPE
    SYNTAX      Counter32
    MAX-ACCESS    read-write
    STATUS      current
                DESCRIPTION
                                "This counter shall be incremented each time the service provider PICs are used and explicitly dialed."
                ::=  {  preferredCarrier  6  }

  bwNonSubscriptionDialedUserPIC  OBJECT-TYPE
    SYNTAX      Counter32
    MAX-ACCESS    read-write
    STATUS      current
                DESCRIPTION
                                "This counter shall be incremented each time a casual dialed carrier is used instead of the user subscribed PIC."
                ::=  {  preferredCarrier  7  }

  bwNonSubscriptionDialedGroupPIC OBJECT-TYPE
    SYNTAX      Counter32
    MAX-ACCESS    read-write
    STATUS      current
                DESCRIPTION
                                "This counter shall be incremented each time a casual dialed carrier is used instead of the group subscribed PIC."
                ::=  {  preferredCarrier  8  }

  bwNonSubscriptionDialedServiceProviderPIC OBJECT-TYPE
    SYNTAX      Counter32
    MAX-ACCESS    read-write
    STATUS      current
                DESCRIPTION
                                "This counter shall be incremented each time a casual dialed carrier is used instead of the service provider subscribed PIC."
                ::=  {  preferredCarrier  9  }

  bwNoIndicationUserPIC OBJECT-TYPE
    SYNTAX      Counter32
    MAX-ACCESS    read-write
    STATUS      current
                DESCRIPTION
                                "This counter shall be incremented each time the user subscribed PIC is used, but with no indication on how this PIC was specified."
                ::=  {  preferredCarrier  10  }

  bwNoIndicationGroupPIC  OBJECT-TYPE
    SYNTAX      Counter32
    MAX-ACCESS    read-write
    STATUS      current
                DESCRIPTION
                                "This counter shall be incremented each time the group subscribed PIC is used, but with no indication on how this PIC was specified."
                ::=  {  preferredCarrier  11  }

  bwNoIndicationServiceProviderPIC  OBJECT-TYPE
    SYNTAX      Counter32
    MAX-ACCESS    read-write
    STATUS      current
                DESCRIPTION
                                "This counter shall be incremented each time the service provider subscribed PIC is used, but with no indication on how this PIC was specified."
                ::=  {  preferredCarrier  12  }

  bwPreferredCarrierSPTable OBJECT-TYPE
    SYNTAX    SEQUENCE  OF  BwPreferredCarrierSPEntry
    MAX-ACCESS  not-accessible
    STATUS    current
                DESCRIPTION
                        "Counters for the Preferred Carrier service measurements for service providers"
                ::=  {  preferredCarrier  13 }

  bwPreferredCarrierGroupTable  OBJECT-TYPE
    SYNTAX    SEQUENCE  OF  BwPreferredCarrierGroupEntry
    MAX-ACCESS  not-accessible
    STATUS    current
                DESCRIPTION
                        "Counters for the Preferred Carrier service measurements for groups"
                ::=  {  preferredCarrier  14 }

-- Service :: preferredCarrier :: SP TABLE ...........................................

  bwPreferredCarrierSPEntry OBJECT-TYPE
    SYNTAX    BwPreferredCarrierSPEntry
    MAX-ACCESS  not-accessible
    STATUS    current
                DESCRIPTION
                        "Each row contains the service counters for the Preferred Carrier service for each service provider in the system"
    INDEX   {  bwPreferredCarrierSPIndex  }
                ::=  { bwPreferredCarrierSPTable 1 }

        BwPreferredCarrierSPEntry  ::=  SEQUENCE {
                bwPreferredCarrierSPIndex  Unsigned32,
                bwPreferredCarrierSPID  DisplayString,
                bwSPSubscriptionUserPIC  Counter32,
                bwSPSubscriptionGroupPIC  Counter32,
                bwSPSubscriptionServiceProviderPIC  Counter32,
                bwSPSubscriptionDialedUserPIC  Counter32,
                bwSPSubscriptionDialedGroupPIC  Counter32,
                bwSPSubscriptionDialedServiceProviderPIC  Counter32,
                bwSPNonSubscriptionDialedUserPIC  Counter32,
                bwSPNonSubscriptionDialedGroupPIC  Counter32,
                bwSPNonSubscriptionDialedServiceProviderPIC  Counter32,
                bwSPNoIndicationUserPIC  Counter32,
                bwSPNoIndicationGroupPIC  Counter32,
                bwSPNoIndicationServiceProviderPIC  Counter32
                }

  bwPreferredCarrierSPIndex   OBJECT-TYPE
    SYNTAX      Unsigned32
    MAX-ACCESS    read-only
    STATUS      current
                DESCRIPTION
                                "This column represents the index of the service provider in the system"
                ::=  {  bwPreferredCarrierSPEntry  1  }

  bwPreferredCarrierSPID  OBJECT-TYPE
    SYNTAX      DisplayString
    MAX-ACCESS    read-only
    STATUS      current
                DESCRIPTION
                                "This string represents a service provider ID"
                ::=  {  bwPreferredCarrierSPEntry  2  }

  bwSPSubscriptionUserPIC OBJECT-TYPE
    SYNTAX      Counter32
    MAX-ACCESS    read-write
    STATUS      current
                DESCRIPTION
                                "This counter shall be incremented each time the user PICs are used, but not explicitly dialed, on a per-service provider basis.."
                ::=  {  bwPreferredCarrierSPEntry  3  }

  bwSPSubscriptionGroupPIC  OBJECT-TYPE
    SYNTAX      Counter32
    MAX-ACCESS    read-write
    STATUS      current
                DESCRIPTION
                                "This counter shall be incremented each time the group PICs are used, but not explicitly dialed, on a per-service provider basis.."
                ::=  {  bwPreferredCarrierSPEntry  4  }

  bwSPSubscriptionServiceProviderPIC  OBJECT-TYPE
    SYNTAX      Counter32
    MAX-ACCESS    read-write
    STATUS      current
                DESCRIPTION
                                "This counter shall be incremented each time the service provider PICs are used, but not explicitly dialed, on a per-service provider basis.."
                ::=  {  bwPreferredCarrierSPEntry  5  }

  bwSPSubscriptionDialedUserPIC OBJECT-TYPE
    SYNTAX      Counter32
    MAX-ACCESS    read-write
    STATUS      current
                DESCRIPTION
                                "This counter shall be incremented each time the user PICs are used and explicitly dialed, on a per-service provider basis.."
                ::=  {  bwPreferredCarrierSPEntry  6  }


  bwSPSubscriptionDialedGroupPIC  OBJECT-TYPE
    SYNTAX      Counter32
    MAX-ACCESS    read-write
    STATUS      current
                DESCRIPTION
                                "This counter shall be incremented each time the group PICs are used and explicitly dialed, on a per-service provider basis.."
                ::=  {  bwPreferredCarrierSPEntry  7  }

  bwSPSubscriptionDialedServiceProviderPIC  OBJECT-TYPE
    SYNTAX      Counter32
    MAX-ACCESS    read-write
    STATUS      current
                DESCRIPTION
                                "This counter shall be incremented each time the service provider PICs are used and explicitly dialed, on a per-service provider basis.."
                ::=  {  bwPreferredCarrierSPEntry  8  }

  bwSPNonSubscriptionDialedUserPIC  OBJECT-TYPE
    SYNTAX      Counter32
    MAX-ACCESS    read-write
    STATUS      current
                DESCRIPTION
                                "This counter shall be incremented each time a casual dialed carrier is used instead of the user subscribed PIC, on a per-service provider basis.."
                ::=  {  bwPreferredCarrierSPEntry  9  }

  bwSPNonSubscriptionDialedGroupPIC OBJECT-TYPE
    SYNTAX      Counter32
    MAX-ACCESS    read-write
    STATUS      current
                DESCRIPTION
                                "This counter shall be incremented each time a casual dialed carrier is used instead of the group subscribed PIC, on a per-service provider basis.."
                ::=  {  bwPreferredCarrierSPEntry  10  }

  bwSPNonSubscriptionDialedServiceProviderPIC OBJECT-TYPE
    SYNTAX      Counter32
    MAX-ACCESS    read-write
    STATUS      current
                DESCRIPTION
                                "This counter shall be incremented each time a casual dialed carrier is used instead of the service provider subscribed PIC, on a per-service provider basis.."
                ::=  {  bwPreferredCarrierSPEntry  11  }

  bwSPNoIndicationUserPIC OBJECT-TYPE
    SYNTAX      Counter32
    MAX-ACCESS    read-write
    STATUS      current
                DESCRIPTION
                                "This counter shall be incremented each time the user subscribed PIC is used, but with no indication on how this PIC was specified, on a per-service provider basis.."
                ::=  {  bwPreferredCarrierSPEntry  12  }

  bwSPNoIndicationGroupPIC  OBJECT-TYPE
    SYNTAX      Counter32
    MAX-ACCESS    read-write
    STATUS      current
                DESCRIPTION
                                "This counter shall be incremented each time the group subscribed PIC is used, but with no indication on how this PIC was specified, on a per-service provider basis.."
                ::=  {  bwPreferredCarrierSPEntry  13  }

  bwSPNoIndicationServiceProviderPIC  OBJECT-TYPE
    SYNTAX      Counter32
    MAX-ACCESS    read-write
    STATUS      current
                DESCRIPTION
                                "This counter shall be incremented each time the service provider subscribed PIC is used, but with no indication on how this PIC was specified, on a per-service provider basis.."
                ::=  {  bwPreferredCarrierSPEntry  14  }

-- Service :: preferredCarrier :: Group TABLE ...........................................

  bwPreferredCarrierGroupEntry  OBJECT-TYPE
    SYNTAX    BwPreferredCarrierGroupEntry
    MAX-ACCESS  not-accessible
    STATUS    current
                DESCRIPTION
                        "Each row contains the service counters for the Preferred Carrier service for each group in the system"
    INDEX   {  bwPreferredCarrierGroupIndex  }
                ::=  { bwPreferredCarrierGroupTable 1 }

        BwPreferredCarrierGroupEntry  ::=  SEQUENCE {
                bwPreferredCarrierGroupIndex  Unsigned32,
                bwPreferredCarrierGroupID  DisplayString,
                bwGroupSubscriptionUserPIC  Counter32,
                bwGroupSubscriptionGroupPIC  Counter32,
                bwGroupSubscriptionServiceProviderPIC  Counter32,
                bwGroupSubscriptionDialedUserPIC  Counter32,
                bwGroupSubscriptionDialedGroupPIC  Counter32,
                bwGroupSubscriptionDialedServiceProviderPIC  Counter32,
                bwGroupNonSubscriptionDialedUserPIC  Counter32,
                bwGroupNonSubscriptionDialedGroupPIC  Counter32,
                bwGroupNonSubscriptionDialedServiceProviderPIC  Counter32,
                bwGroupNoIndicationUserPIC  Counter32,
                bwGroupNoIndicationGroupPIC  Counter32,
                bwGroupNoIndicationServiceProviderPIC  Counter32
                }

  bwPreferredCarrierGroupIndex    OBJECT-TYPE
    SYNTAX      Unsigned32
    MAX-ACCESS    read-only
    STATUS      current
                DESCRIPTION
                                "This column represents the index of the group in the system"
                ::=  {  bwPreferredCarrierGroupEntry  1  }

  bwPreferredCarrierGroupID   OBJECT-TYPE
    SYNTAX      DisplayString
    MAX-ACCESS    read-only
    STATUS      current
                DESCRIPTION
                                "This string represents a group ID"
                ::=  {  bwPreferredCarrierGroupEntry  2  }

  bwGroupSubscriptionUserPIC  OBJECT-TYPE
    SYNTAX      Counter32
    MAX-ACCESS    read-write
    STATUS      current
                DESCRIPTION
                                "This counter shall be incremented each time the user PICs are used, but not explicitly dialed, on a per-group basis.."
                ::=  {  bwPreferredCarrierGroupEntry  3  }

  bwGroupSubscriptionGroupPIC OBJECT-TYPE
    SYNTAX      Counter32
    MAX-ACCESS    read-write
    STATUS      current
                DESCRIPTION
                                "This counter shall be incremented each time the group PICs are used, but not explicitly dialed, on a per-group basis.."
                ::=  {  bwPreferredCarrierGroupEntry  4  }

  bwGroupSubscriptionServiceProviderPIC OBJECT-TYPE
    SYNTAX      Counter32
    MAX-ACCESS    read-write
    STATUS      current
                DESCRIPTION
                                "This counter shall be incremented each time the service provider PICs are used, but not explicitly dialed, on a per-group basis.."
                ::=  {  bwPreferredCarrierGroupEntry  5  }

  bwGroupSubscriptionDialedUserPIC  OBJECT-TYPE
    SYNTAX      Counter32
    MAX-ACCESS    read-write
    STATUS      current
                DESCRIPTION
                                "This counter shall be incremented each time the user PICs are used and explicitly dialed, on a per-group basis.."
                ::=  {  bwPreferredCarrierGroupEntry  6  }


  bwGroupSubscriptionDialedGroupPIC OBJECT-TYPE
    SYNTAX      Counter32
    MAX-ACCESS    read-write
    STATUS      current
                DESCRIPTION
                                "This counter shall be incremented each time the group PICs are used and explicitly dialed, on a per-group basis.."
                ::=  {  bwPreferredCarrierGroupEntry  7  }

  bwGroupSubscriptionDialedServiceProviderPIC OBJECT-TYPE
    SYNTAX      Counter32
    MAX-ACCESS    read-write
    STATUS      current
                DESCRIPTION
                                "This counter shall be incremented each time the service provider PICs are used and explicitly dialed, on a per-group basis.."
                ::=  {  bwPreferredCarrierGroupEntry  8  }

  bwGroupNonSubscriptionDialedUserPIC OBJECT-TYPE
    SYNTAX      Counter32
    MAX-ACCESS    read-write
    STATUS      current
                DESCRIPTION
                                "This counter shall be incremented each time a casual dialed carrier is used instead of the user subscribed PIC, on a per-group basis.."
                ::=  {  bwPreferredCarrierGroupEntry  9  }

  bwGroupNonSubscriptionDialedGroupPIC  OBJECT-TYPE
    SYNTAX      Counter32
    MAX-ACCESS    read-write
    STATUS      current
                DESCRIPTION
                                "This counter shall be incremented each time a casual dialed carrier is used instead of the group subscribed PIC, on a per-group basis.."
                ::=  {  bwPreferredCarrierGroupEntry  10  }

  bwGroupNonSubscriptionDialedServiceProviderPIC  OBJECT-TYPE
    SYNTAX      Counter32
    MAX-ACCESS    read-write
    STATUS      current
                DESCRIPTION
                                "This counter shall be incremented each time a casual dialed carrier is used instead of the service provider subscribed PIC, on a per-group basis.."
                ::=  {  bwPreferredCarrierGroupEntry  11  }

  bwGroupNoIndicationUserPIC  OBJECT-TYPE
    SYNTAX      Counter32
    MAX-ACCESS    read-write
    STATUS      current
                DESCRIPTION
                                "This counter shall be incremented each time the user subscribed PIC is used, but with no indication on how this PIC was specified, on a per-group basis.."
                ::=  {  bwPreferredCarrierGroupEntry  12  }

  bwGroupNoIndicationGroupPIC OBJECT-TYPE
    SYNTAX      Counter32
    MAX-ACCESS    read-write
    STATUS      current
                DESCRIPTION
                                "This counter shall be incremented each time the group subscribed PIC is used, but with no indication on how this PIC was specified, on a per-group basis.."
                ::=  {  bwPreferredCarrierGroupEntry  13  }

  bwGroupNoIndicationServiceProviderPIC OBJECT-TYPE
    SYNTAX      Counter32
    MAX-ACCESS    read-write
    STATUS      current
                DESCRIPTION
                                "This counter shall be incremented each time the service provider subscribed PIC is used, but with no indication on how this PIC was specified, on a per-group basis.."
                ::=  {  bwPreferredCarrierGroupEntry  14  }

-- Service :: Family Simring ...........................................

  bwFamilySimRingNumAttempts  OBJECT-TYPE
    SYNTAX      Counter32
    MAX-ACCESS    read-write
    STATUS      current
                DESCRIPTION
                                "System wide counter for number of times family sim ring has been executed."
                ::=  {  familySimRing  1  }

  bwFamilySimRingNumBusy  OBJECT-TYPE
    SYNTAX      Counter32
    MAX-ACCESS    read-write
    STATUS      current
                DESCRIPTION
                                "System wide counter for number of times all sim ring numbers have failed."
                ::=  {  familySimRing  2  }

  bwFamilySimRingSPTable  OBJECT-TYPE
    SYNTAX    SEQUENCE  OF  BwFamilySimRingSPEntry
    MAX-ACCESS  not-accessible
    STATUS    current
                DESCRIPTION
                        "Counters for the Family Simring service measurements for service providers"
                ::=  {  familySimRing  3 }

  bwFamilySimRingGroupTable OBJECT-TYPE
    SYNTAX    SEQUENCE  OF  BwFamilySimRingGroupEntry
    MAX-ACCESS  not-accessible
    STATUS    current
                DESCRIPTION
                        "Counters for the Family Simring service measurements for groups"
                ::=  {  familySimRing  4 }

-- Service :: Family Simring :: SP TABLE ...........................................

  bwFamilySimRingSPEntry  OBJECT-TYPE
    SYNTAX    BwFamilySimRingSPEntry
    MAX-ACCESS  not-accessible
    STATUS    current
                DESCRIPTION
                        "Each row contains the service counters for the Family Simring service for each service provider in the system"
    INDEX   {  bwFamilySimRingSPIndex  }
                ::=  { bwFamilySimRingSPTable 1 }

        BwFamilySimRingSPEntry  ::=  SEQUENCE {
                bwFamilySimRingSPIndex  Unsigned32,
                bwFamilySimRingSPID  DisplayString,
                bwFamilySimRingSPNumAttempts  Counter32,
                bwFamilySimRingSPNumBusy  Counter32
                }

  bwFamilySimRingSPIndex    OBJECT-TYPE
    SYNTAX      Unsigned32
    MAX-ACCESS    read-only
    STATUS      current
                DESCRIPTION
                                "This column represents the index of the service provider in the system"
                ::=  {  bwFamilySimRingSPEntry  1  }

  bwFamilySimRingSPID   OBJECT-TYPE
    SYNTAX      DisplayString
    MAX-ACCESS    read-only
    STATUS      current
                DESCRIPTION
                                "This string represents a service provider ID"
                ::=  {  bwFamilySimRingSPEntry  2  }

  bwFamilySimRingSPNumAttempts  OBJECT-TYPE
    SYNTAX      Counter32
    MAX-ACCESS    read-write
    STATUS      current
                DESCRIPTION
                                "System wide counter for number of times family sim ring has been executed for a given service provider."
                ::=  {  bwFamilySimRingSPEntry  3  }

  bwFamilySimRingSPNumBusy  OBJECT-TYPE
    SYNTAX      Counter32
    MAX-ACCESS    read-write
    STATUS      current
                DESCRIPTION
                                "System wide counter for number of times all sim ring numbers have failed for a given service provider."
                ::=  {  bwFamilySimRingSPEntry  4  }

-- Service :: Family Simring :: Group TABLE ...........................................

  bwFamilySimRingGroupEntry OBJECT-TYPE
    SYNTAX    BwFamilySimRingGroupEntry
    MAX-ACCESS  not-accessible
    STATUS    current
                DESCRIPTION
                        "Each row contains the service counters for the Family Simring service for each group in the system"
    INDEX   {  bwFamilySimRingGroupIndex  }
                ::=  { bwFamilySimRingGroupTable 1 }

        BwFamilySimRingGroupEntry  ::=  SEQUENCE {
                bwFamilySimRingGroupIndex  Unsigned32,
                bwFamilySimRingGroupID  DisplayString,
                bwFamilySimRingGroupNumAttempts  Counter32,
                bwFamilySimRingGroupNumBusy  Counter32
                }

  bwFamilySimRingGroupIndex   OBJECT-TYPE
    SYNTAX      Unsigned32
    MAX-ACCESS    read-only
    STATUS      current
                DESCRIPTION
                                "This column represents the index of the group in the system"
                ::=  {  bwFamilySimRingGroupEntry  1  }

  bwFamilySimRingGroupID  OBJECT-TYPE
    SYNTAX      DisplayString
    MAX-ACCESS    read-only
    STATUS      current
                DESCRIPTION
                                "This string represents a group ID"
                ::=  {  bwFamilySimRingGroupEntry  2  }

  bwFamilySimRingGroupNumAttempts OBJECT-TYPE
    SYNTAX      Counter32
    MAX-ACCESS    read-write
    STATUS      current
                DESCRIPTION
                                "System wide counter for number of times family sim ring has been executed for a given group."
                ::=  {  bwFamilySimRingGroupEntry  3  }

  bwFamilySimRingGroupNumBusy OBJECT-TYPE
    SYNTAX      Counter32
    MAX-ACCESS    read-write
    STATUS      current
                DESCRIPTION
                                "System wide counter for number of times all sim ring numbers have failed for a given group."
                ::=  {  bwFamilySimRingGroupEntry  4  }

-- Service :: Diversion Inhibitor ...........................................

  bwDiversionInhibited  OBJECT-TYPE
    SYNTAX      Counter32
    MAX-ACCESS    read-write
    STATUS      current
                DESCRIPTION
                                "This counter is incremented each time Diversion Inhibitor FAC is invoked for a call, directly or via service configuration."
                ::=  {  diversionInhibitor  1  }

  bwDiversionInhibitorSPTable   OBJECT-TYPE
    SYNTAX    SEQUENCE  OF  BwDiversionInhibitorSPEntry
    MAX-ACCESS  not-accessible
    STATUS    current
                DESCRIPTION
                        "Counters for the Diversion Inhibitor service measurements for service providers"
                ::=  {  diversionInhibitor  2 }

  bwDiversionInhibitorGroupTable  OBJECT-TYPE
    SYNTAX    SEQUENCE  OF  BwDiversionInhibitorGroupEntry
    MAX-ACCESS  not-accessible
    STATUS    current
                DESCRIPTION
                        "Counters for the Diversion Inhibitor service measurements for groups"
                ::=  {  diversionInhibitor  3 }

-- Service :: Diversion Inhibitor :: SP TABLE ...........................................

  bwDiversionInhibitorSPEntry OBJECT-TYPE
    SYNTAX    BwDiversionInhibitorSPEntry
    MAX-ACCESS  not-accessible
    STATUS    current
                DESCRIPTION
                        "Each row contains the service counters for the Diversion Inhibitor service for each service provider in the system"
    INDEX   {  bwDiversionInhibitorSPIndex  }
                ::=  { bwDiversionInhibitorSPTable 1 }

        BwDiversionInhibitorSPEntry  ::=  SEQUENCE {
                bwDiversionInhibitorSPIndex  Unsigned32,
                bwDiversionInhibitorSPID  DisplayString,
                bwSPDiversionInhibited  Counter32
                }

  bwDiversionInhibitorSPIndex   OBJECT-TYPE
    SYNTAX      Unsigned32
    MAX-ACCESS    read-only
    STATUS      current
                DESCRIPTION
                                "This column represents the index of the service provider in the system"
                ::=  {  bwDiversionInhibitorSPEntry  1  }

  bwDiversionInhibitorSPID  OBJECT-TYPE
    SYNTAX      DisplayString
    MAX-ACCESS    read-only
    STATUS      current
                DESCRIPTION
                                "This string represents a service provider ID"
                ::=  {  bwDiversionInhibitorSPEntry  2  }

  bwSPDiversionInhibited  OBJECT-TYPE
    SYNTAX      Counter32
    MAX-ACCESS    read-write
    STATUS      current
                DESCRIPTION
                                "This counter is incremented each time Diversion Inhibitor FAC is invoked for a call, directly or via service configuration for a service provider."
                ::=  {  bwDiversionInhibitorSPEntry  3  }

-- Service :: Diversion Inhibitor :: Group TABLE ...........................................

  bwDiversionInhibitorGroupEntry  OBJECT-TYPE
    SYNTAX    BwDiversionInhibitorGroupEntry
    MAX-ACCESS  not-accessible
    STATUS    current
                DESCRIPTION
                        "Each row contains the service counters for the Diversion Inhibitor service for each group in the system"
    INDEX   {  bwDiversionInhibitorGroupIndex  }
                ::=  { bwDiversionInhibitorGroupTable 1 }

        BwDiversionInhibitorGroupEntry  ::=  SEQUENCE {
                bwDiversionInhibitorGroupIndex  Unsigned32,
                bwDiversionInhibitorGroupID  DisplayString,
                bwGroupDiversionInhibited  Counter32
                }

  bwDiversionInhibitorGroupIndex    OBJECT-TYPE
    SYNTAX      Unsigned32
    MAX-ACCESS    read-only
    STATUS      current
                DESCRIPTION
                                "This column represents the index of the group in the system"
                ::=  {  bwDiversionInhibitorGroupEntry  1  }

  bwDiversionInhibitorGroupID   OBJECT-TYPE
    SYNTAX      DisplayString
    MAX-ACCESS    read-only
    STATUS      current
                DESCRIPTION
                                "This string represents a group ID"
                ::=  {  bwDiversionInhibitorGroupEntry  2  }

  bwGroupDiversionInhibited OBJECT-TYPE
    SYNTAX      Counter32
    MAX-ACCESS    read-write
    STATUS      current
                DESCRIPTION
                                "This counter is incremented each time Diversion Inhibitor FAC is invoked for a call, directly or via service configuration for a group."
                ::=  {  bwDiversionInhibitorGroupEntry  3  }

-- Service :: Instant Group Call ...........................................

  bwIGCPushToTalkInvoke OBJECT-TYPE
    SYNTAX      Counter32
    MAX-ACCESS    read-write
    STATUS      current
                DESCRIPTION
                                "This counter is incremented each time a Instant Group Call virtual user is called and the Push-To-Talk feature access code was dialed."
                ::=  {  instantGroupCall  1  }

  bwIGCNormalInvoke OBJECT-TYPE
    SYNTAX      Counter32
    MAX-ACCESS    read-write
    STATUS      current
                DESCRIPTION
                                "This counter is incremented each time a Instant Group Call virtual user is called and the Push-To-Talk feature access code was not dialed."
                ::=  {  instantGroupCall  2  }

  bwIGCSPTable  OBJECT-TYPE
    SYNTAX    SEQUENCE  OF  BwIGCSPEntry
    MAX-ACCESS  not-accessible
    STATUS    current
                DESCRIPTION
                        "Counters for the Instant Group Call service measurements for service providers"
                ::=  {  instantGroupCall  3 }

  bwIGCGroupTable OBJECT-TYPE
    SYNTAX    SEQUENCE  OF  BwIGCGroupEntry
    MAX-ACCESS  not-accessible
    STATUS    current
                DESCRIPTION
                        "Counters for the Instant Group Call service measurements for groups"
                ::=  {  instantGroupCall  4 }

-- Service :: Instant Group Call :: SP TABLE ...........................................

  bwIGCSPEntry  OBJECT-TYPE
    SYNTAX    BwIGCSPEntry
    MAX-ACCESS  not-accessible
    STATUS    current
                DESCRIPTION
                        "Each row contains the service counters for the Instant Group Call service for each service provider in the system"
    INDEX   {  bwIGCSPIndex  }
                ::=  { bwIGCSPTable 1 }

        BwIGCSPEntry  ::=  SEQUENCE {
                bwIGCSPIndex  Unsigned32,
                bwIGCSPID  DisplayString,
                bwIGCSPPushToTalkInvoke  Counter32,
                bwIGCSPNormalInvoke  Counter32
                }

  bwIGCSPIndex    OBJECT-TYPE
    SYNTAX      Unsigned32
    MAX-ACCESS    read-only
    STATUS      current
                DESCRIPTION
                                "This column represents the index of the service provider in the system"
                ::=  {  bwIGCSPEntry  1  }

  bwIGCSPID   OBJECT-TYPE
    SYNTAX      DisplayString
    MAX-ACCESS    read-only
    STATUS      current
                DESCRIPTION
                                "This string represents a service provider ID"
                ::=  {  bwIGCSPEntry  2  }

  bwIGCSPPushToTalkInvoke OBJECT-TYPE
    SYNTAX      Counter32
    MAX-ACCESS    read-write
    STATUS      current
                DESCRIPTION
                                "This counter is incremented, per service provider ID, each time a Instant Group Call virtual user is called and the Push-To-Talk feature access code was dialed."
                ::=  {  bwIGCSPEntry  3  }

  bwIGCSPNormalInvoke OBJECT-TYPE
    SYNTAX      Counter32
    MAX-ACCESS    read-write
    STATUS      current
                DESCRIPTION
                                "This counter is incremented, per service provider ID, each time a Instant Group Call virtual user is called and the Push-To-Talk feature access code was not dialed."
                ::=  {  bwIGCSPEntry  4  }

-- Service :: Instant Group Call :: GROUP TABLE ...........................................

  bwIGCGroupEntry OBJECT-TYPE
    SYNTAX    BwIGCGroupEntry
    MAX-ACCESS  not-accessible
    STATUS    current
                DESCRIPTION
                        "Each row contains the service counters for the Instant Group Call service for each group in the system"
    INDEX   {  bwIGCGroupIndex  }
                ::=  { bwIGCGroupTable 1 }

        BwIGCGroupEntry  ::=  SEQUENCE {
                bwIGCGroupIndex  Unsigned32,
                bwIGCGroupID  DisplayString,
                bwIGCGroupPushToTalkInvoke  Counter32,
                bwIGCGroupNormalInvoke  Counter32
                }

  bwIGCGroupIndex   OBJECT-TYPE
    SYNTAX      Unsigned32
    MAX-ACCESS    read-only
    STATUS      current
                DESCRIPTION
                                "This column represents the index of the group in the system"
                ::=  {  bwIGCGroupEntry  1  }

  bwIGCGroupID  OBJECT-TYPE
    SYNTAX      DisplayString
    MAX-ACCESS    read-only
    STATUS      current
                DESCRIPTION
                                "This string represents a group ID"
                ::=  {  bwIGCGroupEntry  2  }

  bwIGCGroupPushToTalkInvoke  OBJECT-TYPE
    SYNTAX      Counter32
    MAX-ACCESS    read-write
    STATUS      current
                DESCRIPTION
                                "This counter is incremented, per group ID, each time a Instant Group Call virtual user is called and the Push-To-Talk feature access code was dialed."
                ::=  {  bwIGCGroupEntry  3  }

  bwIGCGroupNormalInvoke  OBJECT-TYPE
    SYNTAX      Counter32
    MAX-ACCESS    read-write
    STATUS      current
                DESCRIPTION
                                "This counter is incremented, per group ID, each time a Instant Group Call virtual user is called and the Push-To-Talk feature access code was not dialed."
                ::=  {  bwIGCGroupEntry  4  }

-- Service :: Automatic Hold Retrieve ...........................................

  bwAHRHold OBJECT-TYPE
    SYNTAX      Counter32
    MAX-ACCESS    read-write
    STATUS      current
                DESCRIPTION
                                "Number of times a call is put on hold via the AHR service."
                ::=  {  automaticHoldRetrieve  1  }

  bwAHRRetrieve OBJECT-TYPE
    SYNTAX      Counter32
    MAX-ACCESS    read-write
    STATUS      current
                DESCRIPTION
                                "Number of times a call is retrieved via the AHR service."
                ::=  {  automaticHoldRetrieve  2  }

  bwAHRSPTable  OBJECT-TYPE
    SYNTAX    SEQUENCE  OF  BwAHRSPEntry
    MAX-ACCESS  not-accessible
    STATUS    current
                DESCRIPTION
                        "Counters for the Automatic Hold Retrieve service measurements for service providers."
                ::=  {  automaticHoldRetrieve  3 }

  bwAHRGroupTable OBJECT-TYPE
    SYNTAX    SEQUENCE  OF  BwAHRGroupEntry
    MAX-ACCESS  not-accessible
    STATUS    current
                DESCRIPTION
                        "Counters for the Automatic Hold Retrieve service measurements for groups."
                ::=  {  automaticHoldRetrieve  4 }

-- Service :: Automatic Hold Retrieve :: SP TABLE ...........................................

  bwAHRSPEntry  OBJECT-TYPE
    SYNTAX    BwAHRSPEntry
    MAX-ACCESS  not-accessible
    STATUS    current
                DESCRIPTION
                        "Each row contains the service counters for the Automatic Hold Retrieve service for each service provider in the system"
    INDEX   {  bwAHRSPIndex  }
                ::=  { bwAHRSPTable 1 }

        BwAHRSPEntry  ::=  SEQUENCE {
                bwAHRSPIndex  Unsigned32,
                bwAHRSPID  DisplayString,
                bwAHRSPHold  Counter32,
                bwAHRSPRetrieve  Counter32
                }

  bwAHRSPIndex    OBJECT-TYPE
    SYNTAX      Unsigned32
    MAX-ACCESS    read-only
    STATUS      current
                DESCRIPTION
                                "This column represents the index of the service provider in the system."
                ::=  {  bwAHRSPEntry  1  }

  bwAHRSPID   OBJECT-TYPE
    SYNTAX      DisplayString
    MAX-ACCESS    read-only
    STATUS      current
                DESCRIPTION
                                "This string represents a service provider ID."
                ::=  {  bwAHRSPEntry  2  }

  bwAHRSPHold OBJECT-TYPE
    SYNTAX      Counter32
    MAX-ACCESS    read-write
    STATUS      current
                DESCRIPTION
                                "Number of calls within a service provider that are put on hold via the AHR service."
                ::=  {  bwAHRSPEntry  3  }

  bwAHRSPRetrieve OBJECT-TYPE
    SYNTAX      Counter32
    MAX-ACCESS    read-write
    STATUS      current
                DESCRIPTION
                                "Number of calls within a service provider that are retrieved via the AHR service."
                ::=  {  bwAHRSPEntry  4  }

-- Service :: Automatic Hold Retrieve :: GROUP TABLE ...........................................

  bwAHRGroupEntry OBJECT-TYPE
    SYNTAX    BwAHRGroupEntry
    MAX-ACCESS  not-accessible
    STATUS    current
                DESCRIPTION
                        "Each row contains the service counters for the Automatic Hold Retrieve service for each group in the system"
    INDEX   {  bwAHRGroupIndex  }
                ::=  { bwAHRGroupTable 1 }

        BwAHRGroupEntry  ::=  SEQUENCE {
                bwAHRGroupIndex  Unsigned32,
                bwAHRGroupID  DisplayString,
                bwAHRGroupHold  Counter32,
                bwAHRGroupRetrieve  Counter32
                }

  bwAHRGroupIndex   OBJECT-TYPE
    SYNTAX      Unsigned32
    MAX-ACCESS    read-only
    STATUS      current
                DESCRIPTION
                                "This column represents the index of the group in the system."
                ::=  {  bwAHRGroupEntry  1  }

  bwAHRGroupID  OBJECT-TYPE
    SYNTAX      DisplayString
    MAX-ACCESS    read-only
    STATUS      current
                DESCRIPTION
                                "This string represents a group ID."
                ::=  {  bwAHRGroupEntry  2  }

  bwAHRGroupHold  OBJECT-TYPE
    SYNTAX      Counter32
    MAX-ACCESS    read-write
    STATUS      current
                DESCRIPTION
                                "Number of calls within a group that are put on hold via the AHR service."
                ::=  {  bwAHRGroupEntry  3  }

  bwAHRGroupRetrieve  OBJECT-TYPE
    SYNTAX      Counter32
    MAX-ACCESS    read-write
    STATUS      current
                DESCRIPTION
                                "Number of calls within a group that are retrieved via the AHR service."
                ::=  {  bwAHRGroupEntry  4  }


-- Service :: Business Trunk Group ...........................................

  bwTrunkOriginationAttempt OBJECT-TYPE
    SYNTAX      Counter32
    MAX-ACCESS    read-write
    STATUS      current
                DESCRIPTION
                                "This counter is incremented when a call is originated by a trunk user, whether it goes through or not."
                ::=  {  trunkGroup  1  }

  bwTrunkOriginationBlocked OBJECT-TYPE
    SYNTAX      Counter32
    MAX-ACCESS    read-write
    STATUS      current
                DESCRIPTION
                                "This counter is incremented when a call originated by a trunk user is blocked because the trunk call capacity is reached."
                ::=  {  trunkGroup  2  }

  bwTrunkTerminationAttempt OBJECT-TYPE
    SYNTAX      Counter32
    MAX-ACCESS    read-write
    STATUS      current
                DESCRIPTION
                                "This counter is incremented when a call from an outside party attempts to terminate on a trunk user, whether it goes through or not."
                ::=  {  trunkGroup  3  }

  bwTrunkTerminationBlocked OBJECT-TYPE
    SYNTAX      Counter32
    MAX-ACCESS    read-write
    STATUS      current
                DESCRIPTION
                                "This counter is incremented when a call destined to a trunk user is blocked because the trunk call capacity is reached."
                ::=  {  trunkGroup  4  }

  bwTrunkSPTable  OBJECT-TYPE
    SYNTAX    SEQUENCE  OF  BwTrunkSPEntry
    MAX-ACCESS  not-accessible
    STATUS    current
                DESCRIPTION
                        "Counters for the Business Trunk Group service measurements for service providers."
                ::=  {  trunkGroup  5 }

  bwTrunkGroupTable OBJECT-TYPE
    SYNTAX    SEQUENCE  OF  BwTrunkGroupEntry
    MAX-ACCESS  not-accessible
    STATUS    current
                DESCRIPTION
                        "Counters for the Business Trunk Group service measurements for groups."
                ::=  {  trunkGroup  6 }

  bwTrunkGroupPerTGTable  OBJECT-TYPE
    SYNTAX    SEQUENCE  OF  BwTrunkGroupPerTGEntry
    MAX-ACCESS  not-accessible
    STATUS    current
                DESCRIPTION
                        "Counters for the Business Trunk Group service measurements on a per trunk group basis."
                ::=  {  trunkGroup  7 }

-- Service :: Business Trunk Group :: SP TABLE ...........................................

  bwTrunkSPEntry  OBJECT-TYPE
    SYNTAX    BwTrunkSPEntry
    MAX-ACCESS  not-accessible
    STATUS    current
                DESCRIPTION
                        "Each row contains the service counters for the Business Trunk Group service for each service provider in the system"
    INDEX   {  bwTrunkSPIndex  }
                ::=  { bwTrunkSPTable 1 }

        BwTrunkSPEntry  ::=  SEQUENCE {
                bwTrunkSPIndex  Unsigned32,
                bwTrunkSPID  DisplayString,
                bwTrunkSPOriginationAttempt  Counter32,
                bwTrunkSPOriginationBlocked  Counter32,
                bwTrunkSPTerminationAttempt  Counter32,
                bwTrunkSPTerminationBlocked  Counter32
                }

  bwTrunkSPIndex    OBJECT-TYPE
    SYNTAX      Unsigned32
    MAX-ACCESS    read-only
    STATUS      current
                DESCRIPTION
                                "This column represents the index of the service provider in the system."
                ::=  {  bwTrunkSPEntry  1  }

  bwTrunkSPID   OBJECT-TYPE
    SYNTAX      DisplayString
    MAX-ACCESS    read-only
    STATUS      current
                DESCRIPTION
                                "This string represents a service provider ID."
                ::=  {  bwTrunkSPEntry  2  }

  bwTrunkSPOriginationAttempt OBJECT-TYPE
    SYNTAX      Counter32
    MAX-ACCESS    read-write
    STATUS      current
                DESCRIPTION
                                "This counter is incremented when a call is originated by a trunk user in the service provider, whether it goes through or not."
                ::=  {  bwTrunkSPEntry  3  }

  bwTrunkSPOriginationBlocked OBJECT-TYPE
    SYNTAX      Counter32
    MAX-ACCESS    read-write
    STATUS      current
                DESCRIPTION
                                "This counter is incremented when a call originated by a trunk user within the service provider is blocked because the trunk call capacity is reached."
                ::=  {  bwTrunkSPEntry  4  }

  bwTrunkSPTerminationAttempt OBJECT-TYPE
    SYNTAX      Counter32
    MAX-ACCESS    read-write
    STATUS      current
                DESCRIPTION
                                "This counter is incremented when a call from an outside party attempts to terminate on a trunk user within the service provider, whether it goes through or not."
                ::=  {  bwTrunkSPEntry  5  }

  bwTrunkSPTerminationBlocked OBJECT-TYPE
    SYNTAX      Counter32
    MAX-ACCESS    read-write
    STATUS      current
                DESCRIPTION
                                "This counter is incremented when a call destined to a trunk user within the service provider is blocked because the trunk call capacity is reached."
                ::=  {  bwTrunkSPEntry  6  }

-- Service :: Business Trunk Group :: GROUP TABLE ...........................................

  bwTrunkGroupEntry OBJECT-TYPE
    SYNTAX    BwTrunkGroupEntry
    MAX-ACCESS  not-accessible
    STATUS    current
                DESCRIPTION
                        "Each row contains the service counters for the Business Trunk Group service for each group in the system"
    INDEX   {  bwTrunkGroupIndex  }
                ::=  { bwTrunkGroupTable 1 }

        BwTrunkGroupEntry  ::=  SEQUENCE {
                bwTrunkGroupIndex  Unsigned32,
                bwTrunkGroupID  DisplayString,
                bwTrunkGroupOriginationAttempt  Counter32,
                bwTrunkGroupOriginationBlocked  Counter32,
                bwTrunkGroupTerminationAttempt  Counter32,
                bwTrunkGroupTerminationBlocked  Counter32
                }

  bwTrunkGroupIndex   OBJECT-TYPE
    SYNTAX      Unsigned32
    MAX-ACCESS    read-only
    STATUS      current
                DESCRIPTION
                                "This column represents the index of the group in the system."
                ::=  {  bwTrunkGroupEntry  1  }

  bwTrunkGroupID  OBJECT-TYPE
    SYNTAX      DisplayString
    MAX-ACCESS    read-only
    STATUS      current
                DESCRIPTION
                                "This string represents a group ID."
                ::=  {  bwTrunkGroupEntry  2  }

  bwTrunkGroupOriginationAttempt  OBJECT-TYPE
    SYNTAX      Counter32
    MAX-ACCESS    read-write
    STATUS      current
                DESCRIPTION
                                "This counter is incremented when a call is originated by a trunk user in the group, whether it goes through or not."
                ::=  {  bwTrunkGroupEntry  3  }

  bwTrunkGroupOriginationBlocked  OBJECT-TYPE
    SYNTAX      Counter32
    MAX-ACCESS    read-write
    STATUS      current
                DESCRIPTION
                                "This counter is incremented when a call originated by a trunk user within the group is blocked because the trunk call capacity is reached."
                ::=  {  bwTrunkGroupEntry  4  }

  bwTrunkGroupTerminationAttempt  OBJECT-TYPE
    SYNTAX      Counter32
    MAX-ACCESS    read-write
    STATUS      current
                DESCRIPTION
                                "This counter is incremented when a call from an outside party attempts to terminate on a trunk user within the group, whether it goes through or not."
                ::=  {  bwTrunkGroupEntry  5  }

  bwTrunkGroupTerminationBlocked  OBJECT-TYPE
    SYNTAX      Counter32
    MAX-ACCESS    read-write
    STATUS      current
                DESCRIPTION
                                "This counter is incremented when a call destined to a trunk user within the group is blocked because the trunk call capacity is reached."
                ::=  {  bwTrunkGroupEntry  6  }

-- Service :: Business Trunk Group :: Per trunk group TABLE ...........................................

  bwTrunkGroupPerTGEntry  OBJECT-TYPE
    SYNTAX    BwTrunkGroupPerTGEntry
    MAX-ACCESS  not-accessible
    STATUS    current
                DESCRIPTION
                        "Each row contains the service counters for the Business Trunk Group service for each service provider in the system"
    INDEX   {  bwTrunkGroupPerTGIndex  }
                ::=  { bwTrunkGroupPerTGTable 1 }

        BwTrunkGroupPerTGEntry  ::=  SEQUENCE {
                bwTrunkGroupPerTGIndex  Unsigned32,
                bwTrunkGroupPerTGName  DisplayString,
                bwTrunkGroupPerTGCapacityExceeded  Counter32,
                bwTrunkGroupPerTGUnreachableDestination  Counter32,
                bwTrunkGroupPerTGMaxActiveCalls  Gauge32,
                bwTrunkGroupPerTGMaxOutgoingActiveCalls  Gauge32,
                bwTrunkGroupPerTGMaxIncomingActiveCalls Gauge32,
                bwTrunkGroupPerTGCapacityExceededInitialValue Gauge32,
                bwTrunkGroupPerTGCapacityExceededOffsetValue Gauge32,
                bwTrunkGroupPerTGUnreachableDestinationExceededInitialValue Gauge32,
                bwTrunkGroupPerTGUnreachableDestinationExceededOffsetValue Gauge32,
                bwTrunkGroupPerTGBursting DisplayString,
                bwTrunkGroupPerTGBurstingMaxActiveCalls Gauge32,
                bwTrunkGroupPerTGBurstingMaxOutgoingActiveCalls Gauge32,
                bwTrunkGroupPerTGBurstingMaxIncomingActiveCalls Gauge32,
                bwTrunkGroupPerTGGroupID DisplayString
                }

  bwTrunkGroupPerTGIndex    OBJECT-TYPE
    SYNTAX      Unsigned32
    MAX-ACCESS    read-only
    STATUS      current
                DESCRIPTION
                                "This column represents the index of the trunk group in the system."
                ::=  {  bwTrunkGroupPerTGEntry  1  }

  bwTrunkGroupPerTGName   OBJECT-TYPE
    SYNTAX      DisplayString
    MAX-ACCESS    read-only
    STATUS      current
                DESCRIPTION
                                "This string represents the name of a trunk group."
                ::=  {  bwTrunkGroupPerTGEntry  2  }

  bwTrunkGroupPerTGCapacityExceeded OBJECT-TYPE
    SYNTAX      Counter32
    MAX-ACCESS    read-write
    STATUS      current
                DESCRIPTION
                                "The counter is incremented each time a trunk group call capacity is exceeded."
                ::=  {  bwTrunkGroupPerTGEntry  3  }

  bwTrunkGroupPerTGUnreachableDestination OBJECT-TYPE
    SYNTAX      Counter32
    MAX-ACCESS    read-write
    STATUS      current
                DESCRIPTION
                                "The counter is incremented each time a trunk group is deemed unreachable."
                ::=  {  bwTrunkGroupPerTGEntry  4  }

  bwTrunkGroupPerTGMaxActiveCalls OBJECT-TYPE
    SYNTAX      Gauge32
    MAX-ACCESS    read-only
    STATUS      current
                DESCRIPTION
                                "Indicates the value of the Maximum Active Calls Allowed parameter for a trunk group."
                ::=  {  bwTrunkGroupPerTGEntry  5  }

  bwTrunkGroupPerTGMaxOutgoingActiveCalls OBJECT-TYPE
    SYNTAX      Gauge32
    MAX-ACCESS    read-only
    STATUS      current
                DESCRIPTION
                                "Indicates the value of the Maximum Outgoing Active Calls Allowed parameter a the trunk group."
                ::=  {  bwTrunkGroupPerTGEntry  6  }

  bwTrunkGroupPerTGMaxIncomingActiveCalls OBJECT-TYPE
    SYNTAX      Gauge32
    MAX-ACCESS    read-only
    STATUS      current
                DESCRIPTION
                                "Indicates the value of the Maximum Incoming Active Calls Allowed parameter a the trunk group."
                ::=  {  bwTrunkGroupPerTGEntry  7  }

  bwTrunkGroupPerTGCapacityExceededInitialValue OBJECT-TYPE
    SYNTAX      Gauge32
    MAX-ACCESS    read-only
    STATUS      current
                DESCRIPTION
                                "Indicates the value of the Capacity Exceeded Initial Value parameter for a trunk group."
                ::=  {  bwTrunkGroupPerTGEntry  8  }

  bwTrunkGroupPerTGCapacityExceededOffsetValue  OBJECT-TYPE
    SYNTAX      Gauge32
    MAX-ACCESS    read-only
    STATUS      current
                DESCRIPTION
                                "Indicates the value of the Capacity Exceeded Offset Value parameter for a trunk group."
                ::=  {  bwTrunkGroupPerTGEntry  9  }

  bwTrunkGroupPerTGUnreachableDestinationExceededInitialValue OBJECT-TYPE
    SYNTAX      Gauge32
    MAX-ACCESS    read-only
    STATUS      current
                DESCRIPTION
                                "Indicates the value of the Unreachable Destination Exceeded Initial Value parameter for a trunk group."
                ::=  {  bwTrunkGroupPerTGEntry 10   }

  bwTrunkGroupPerTGUnreachableDestinationExceededOffsetValue  OBJECT-TYPE
    SYNTAX      Gauge32
    MAX-ACCESS    read-only
    STATUS      current
                DESCRIPTION
                                "Indicates the value of the Unreachable Destination Exceeded Offset Value parameter for a trunk group."
                ::=  {  bwTrunkGroupPerTGEntry  11  }

  bwTrunkGroupPerTGBursting OBJECT-TYPE
    SYNTAX      DisplayString
    MAX-ACCESS    read-only
    STATUS      current
                DESCRIPTION
                                "Indicates the value bursting parameter for the trunk group."
                ::=  {  bwTrunkGroupPerTGEntry  12  }

  bwTrunkGroupPerTGBurstingMaxActiveCalls OBJECT-TYPE
    SYNTAX      Gauge32
    MAX-ACCESS    read-only
    STATUS      current
                DESCRIPTION
                                "Indicates the value of the Bursting Maximum Active Calls Allowed parameter for the trunk group."
                ::=  {  bwTrunkGroupPerTGEntry  13  }

  bwTrunkGroupPerTGBurstingMaxOutgoingActiveCalls OBJECT-TYPE
    SYNTAX      Gauge32
    MAX-ACCESS    read-only
    STATUS      current
                DESCRIPTION
                                "Indicates the value of the Bursting Maximum Outgoing Active Calls Allowed parameter for the trunk group."
                ::=  {  bwTrunkGroupPerTGEntry  14  }

  bwTrunkGroupPerTGBurstingMaxIncomingActiveCalls OBJECT-TYPE
    SYNTAX      Gauge32
    MAX-ACCESS    read-only
    STATUS      current
                DESCRIPTION
                                "Indicates the value of the Bursting Maximum Incoming Active Calls Allowed parameter for the trunk group."
                ::=  {  bwTrunkGroupPerTGEntry  15  }

  bwTrunkGroupPerTGGroupID OBJECT-TYPE
    SYNTAX      DisplayString
    MAX-ACCESS    read-only
    STATUS      current
                DESCRIPTION
                                "This string represents a group ID."
                ::=  {  bwTrunkGroupPerTGEntry  16  }

-- Service :: Custom Ringback ...........................................

  bwCustomRingbackUserAudioAttempts OBJECT-TYPE
    SYNTAX      Counter32
    MAX-ACCESS    read-write
    STATUS      current
                DESCRIPTION
                                "This counter is incremented each time a command is sent to the Media Server in an attempt to play a user custom audio ringback."
                ::=  {  customRingback  1  }

  bwCustomRingbackUserVideoAttempts OBJECT-TYPE
    SYNTAX      Counter32
    MAX-ACCESS    read-write
    STATUS      current
                DESCRIPTION
                                "This counter is incremented each time a command is sent to the Media Server in an attempt to play a user custom video ringback."
                ::=  {  customRingback  2  }

  bwCustomRingbackUserAudioFailures OBJECT-TYPE
    SYNTAX      Counter32
    MAX-ACCESS    read-write
    STATUS      current
                DESCRIPTION
                                "This counter is incremented each time where an attempt is made to play a user custom audio ringback, and that the Media Server reports any failure to play it."
                ::=  {  customRingback  3  }

  bwCustomRingbackUserVideoFailures OBJECT-TYPE
    SYNTAX      Counter32
    MAX-ACCESS    read-write
    STATUS      current
                DESCRIPTION
                                "This counter is incremented each time where an attempt is made to play a user custom video ringback, and that the Media Server reports any failure to play it."
                ::=  {  customRingback  4  }

  bwCustomRingbackGroupAudioAttempts  OBJECT-TYPE
    SYNTAX      Counter32
    MAX-ACCESS    read-write
    STATUS      current
                DESCRIPTION
                                "This counter is incremented each time a command is sent to the Media Server in an attempt to play a group custom audio ringback."
                ::=  {  customRingback  5  }

  bwCustomRingbackGroupVideoAttempts  OBJECT-TYPE
    SYNTAX      Counter32
    MAX-ACCESS    read-write
    STATUS      current
                DESCRIPTION
                                "This counter is incremented each time a command is sent to the Media Server in an attempt to play a group custom video ringback."
                ::=  {  customRingback  6  }

  bwCustomRingbackGroupAudioFailures  OBJECT-TYPE
    SYNTAX      Counter32
    MAX-ACCESS    read-write
    STATUS      current
                DESCRIPTION
                                "This counter is incremented each time where an attempt is made to play a group custom audio ringback, and that the Media Server reports any failure to play it."
                ::=  {  customRingback  7  }

  bwCustomRingbackGroupVideoFailures  OBJECT-TYPE
    SYNTAX      Counter32
    MAX-ACCESS    read-write
    STATUS      current
                DESCRIPTION
                                "This counter is incremented each time where an attempt is made to play a group custom video ringback, and that the Media Server reports any failure to play it."
                ::=  {  customRingback  8  }

  bwCustomRingbackSPTable   OBJECT-TYPE
    SYNTAX    SEQUENCE  OF  BwCustomRingbackSPEntry
    MAX-ACCESS  not-accessible
    STATUS    current
                DESCRIPTION
                        "Counters for the Custom Ringback service measurements for service providers."
                ::=  {  customRingback  9 }

  bwCustomRingbackGroupTable  OBJECT-TYPE
    SYNTAX    SEQUENCE  OF  BwCustomRingbackGroupEntry
    MAX-ACCESS  not-accessible
    STATUS    current
                DESCRIPTION
                        "Counters for the Custom Ringback service measurements for groups."
                ::=  {  customRingback  10 }

-- Service :: Custom Ringback :: SP TABLE ...........................................

  bwCustomRingbackSPEntry OBJECT-TYPE
    SYNTAX    BwCustomRingbackSPEntry
    MAX-ACCESS  not-accessible
    STATUS    current
                DESCRIPTION
                        "Each row contains the service counters for the Custom Ringback service for each service provider in the system."
    INDEX   {  bwCustomRingbackSPIndex  }
                ::=  { bwCustomRingbackSPTable 1 }

        BwCustomRingbackSPEntry  ::=  SEQUENCE {
                bwCustomRingbackSPIndex  Unsigned32,
                bwCustomRingbackSPID  DisplayString,
                bwCustomRingbackUserAudioSPAttempts  Counter32,
                bwCustomRingbackUserVideoSPAttempts  Counter32,
                bwCustomRingbackUserAudioSPFailures  Counter32,
                bwCustomRingbackUserVideoSPFailures  Counter32,
                bwCustomRingbackGroupAudioSPAttempts  Counter32,
                bwCustomRingbackGroupVideoSPAttempts  Counter32,
                bwCustomRingbackGroupAudioSPFailures  Counter32,
                bwCustomRingbackGroupVideoSPFailures  Counter32
                }

  bwCustomRingbackSPIndex   OBJECT-TYPE
    SYNTAX      Unsigned32
    MAX-ACCESS    read-only
    STATUS      current
                DESCRIPTION
                                "This column represents the index of the service provider in the system."
                ::=  {  bwCustomRingbackSPEntry  1  }

  bwCustomRingbackSPID  OBJECT-TYPE
    SYNTAX      DisplayString
    MAX-ACCESS    read-only
    STATUS      current
                DESCRIPTION
                                "This string represents a service provider ID."
                ::=  {  bwCustomRingbackSPEntry  2  }

  bwCustomRingbackUserAudioSPAttempts OBJECT-TYPE
    SYNTAX      Counter32
    MAX-ACCESS    read-write
    STATUS      current
                DESCRIPTION
                                "This counter is incremented each time a command is sent to the Media Server in an attempt to play a user custom audio ringback for a given service provider."
                ::=  {  bwCustomRingbackSPEntry  3  }

  bwCustomRingbackUserVideoSPAttempts OBJECT-TYPE
    SYNTAX      Counter32
    MAX-ACCESS    read-write
    STATUS      current
                DESCRIPTION
                                "This counter is incremented each time a command is sent to the Media Server in an attempt to play a user custom video ringback for a given service provider."
                ::=  {  bwCustomRingbackSPEntry  4  }

  bwCustomRingbackUserAudioSPFailures OBJECT-TYPE
    SYNTAX      Counter32
    MAX-ACCESS    read-write
    STATUS      current
                DESCRIPTION
                                "This counter is incremented each time where an attempt is made to play a user custom audio ringback, and that the Media Server reports any failure to play it for a given service provider."
                ::=  {  bwCustomRingbackSPEntry  5  }

  bwCustomRingbackUserVideoSPFailures OBJECT-TYPE
    SYNTAX      Counter32
    MAX-ACCESS    read-write
    STATUS      current
                DESCRIPTION
                                "This counter is incremented each time where an attempt is made to play a user custom video ringback, and that the Media Server reports any failure to play it for a given service provider."
                ::=  {  bwCustomRingbackSPEntry  6  }

  bwCustomRingbackGroupAudioSPAttempts  OBJECT-TYPE
    SYNTAX      Counter32
    MAX-ACCESS    read-write
    STATUS      current
                DESCRIPTION
                                "This counter is incremented each time a command is sent to the Media Server in an attempt to play a group custom audio ringback for a given service provider."
                ::=  {  bwCustomRingbackSPEntry  7  }

  bwCustomRingbackGroupVideoSPAttempts  OBJECT-TYPE
    SYNTAX      Counter32
    MAX-ACCESS    read-write
    STATUS      current
                DESCRIPTION
                                "This counter is incremented each time a command is sent to the Media Server in an attempt to play a group custom video ringback for a given service provider."
                ::=  {  bwCustomRingbackSPEntry  8  }

  bwCustomRingbackGroupAudioSPFailures  OBJECT-TYPE
    SYNTAX      Counter32
    MAX-ACCESS    read-write
    STATUS      current
                DESCRIPTION
                                "This counter is incremented each time where an attempt is made to play a group custom audio ringback, and that the Media Server reports any failure to play it for a given service provider."
                ::=  {  bwCustomRingbackSPEntry  9  }

  bwCustomRingbackGroupVideoSPFailures  OBJECT-TYPE
    SYNTAX      Counter32
    MAX-ACCESS    read-write
    STATUS      current
                DESCRIPTION
                                "This counter is incremented each time where an attempt is made to play a group custom video ringback, and that the Media Server reports any failure to play it for a given service provider."
                ::=  {  bwCustomRingbackSPEntry  10  }

-- Service :: Custom Ringback :: GROUP TABLE ...........................................

  bwCustomRingbackGroupEntry  OBJECT-TYPE
    SYNTAX    BwCustomRingbackGroupEntry
    MAX-ACCESS  not-accessible
    STATUS    current
                DESCRIPTION
                        "Each row contains the service counters for the Custom Ringback service for each group in the system."
    INDEX   {  bwCustomRingbackGroupIndex  }
                ::=  { bwCustomRingbackGroupTable 1 }

        BwCustomRingbackGroupEntry  ::=  SEQUENCE {
                bwCustomRingbackGroupIndex  Unsigned32,
                bwCustomRingbackGroupID  DisplayString,
                bwCustomRingbackUserAudioGroupAttempts  Counter32,
                bwCustomRingbackUserVideoGroupAttempts  Counter32,
                bwCustomRingbackUserAudioGroupFailures  Counter32,
                bwCustomRingbackUserVideoGroupFailures  Counter32,
                bwCustomRingbackGroupAudioGroupAttempts  Counter32,
                bwCustomRingbackGroupVideoGroupAttempts  Counter32,
                bwCustomRingbackGroupAudioGroupFailures  Counter32,
                bwCustomRingbackGroupVideoGroupFailures  Counter32
                }

  bwCustomRingbackGroupIndex    OBJECT-TYPE
    SYNTAX      Unsigned32
    MAX-ACCESS    read-only
    STATUS      current
                DESCRIPTION
                                "This column represents the index of the group in the system."
                ::=  {  bwCustomRingbackGroupEntry  1  }

  bwCustomRingbackGroupID   OBJECT-TYPE
    SYNTAX      DisplayString
    MAX-ACCESS    read-only
    STATUS      current
                DESCRIPTION
                                "This string represents a group ID."
                ::=  {  bwCustomRingbackGroupEntry  2  }

  bwCustomRingbackUserAudioGroupAttempts  OBJECT-TYPE
    SYNTAX      Counter32
    MAX-ACCESS    read-write
    STATUS      current
                DESCRIPTION
                                "This counter is incremented each time a command is sent to the Media Server in an attempt to play a user custom audio ringback for a given group."
                ::=  {  bwCustomRingbackGroupEntry  3  }

  bwCustomRingbackUserVideoGroupAttempts  OBJECT-TYPE
    SYNTAX      Counter32
    MAX-ACCESS    read-write
    STATUS      current
                DESCRIPTION
                                "This counter is incremented each time a command is sent to the Media Server in an attempt to play a user custom video ringback for a given group."
                ::=  {  bwCustomRingbackGroupEntry  4  }

  bwCustomRingbackUserAudioGroupFailures  OBJECT-TYPE
    SYNTAX      Counter32
    MAX-ACCESS    read-write
    STATUS      current
                DESCRIPTION
                                "This counter is incremented each time where an attempt is made to play a user custom audio ringback, and that the Media Server reports any failure to play it for a given group."
                ::=  {  bwCustomRingbackGroupEntry  5  }

  bwCustomRingbackUserVideoGroupFailures  OBJECT-TYPE
    SYNTAX      Counter32
    MAX-ACCESS    read-write
    STATUS      current
                DESCRIPTION
                                "This counter is incremented each time where an attempt is made to play a user custom video ringback, and that the Media Server reports any failure to play it for a given group."
                ::=  {  bwCustomRingbackGroupEntry  6  }

  bwCustomRingbackGroupAudioGroupAttempts OBJECT-TYPE
    SYNTAX      Counter32
    MAX-ACCESS    read-write
    STATUS      current
                DESCRIPTION
                                "This counter is incremented each time a command is sent to the Media Server in an attempt to play a group custom audio ringback for a given group."
                ::=  {  bwCustomRingbackGroupEntry  7  }

  bwCustomRingbackGroupVideoGroupAttempts OBJECT-TYPE
    SYNTAX      Counter32
    MAX-ACCESS    read-write
    STATUS      current
                DESCRIPTION
                                "This counter is incremented each time a command is sent to the Media Server in an attempt to play a group custom video ringback for a given group."
                ::=  {  bwCustomRingbackGroupEntry  8  }

  bwCustomRingbackGroupAudioGroupFailures OBJECT-TYPE
    SYNTAX      Counter32
    MAX-ACCESS    read-write
    STATUS      current
                DESCRIPTION
                                "This counter is incremented each time where an attempt is made to play a group custom audio ringback, and that the Media Server reports any failure to play it for a given group."
                ::=  {  bwCustomRingbackGroupEntry  9  }

  bwCustomRingbackGroupVideoGroupFailures OBJECT-TYPE
    SYNTAX      Counter32
    MAX-ACCESS    read-write
    STATUS      current
                DESCRIPTION
                                "This counter is incremented each time where an attempt is made to play a group custom video ringback, and that the Media Server reports any failure to play it for a given group."
                ::=  {  bwCustomRingbackGroupEntry  10  }

-- Service :: Physical Location ...........................................

  bwPhysicalLocationOriginationBlocked  OBJECT-TYPE
    SYNTAX      Counter32
    MAX-ACCESS    read-write
    STATUS      current
                DESCRIPTION
                                "Number of times a user has an origination blocked by the Physical Location service."
                ::=  {  physicalLocation  1  }

  bwPhysicalLocationSPTable   OBJECT-TYPE
    SYNTAX    SEQUENCE  OF  BwPhysicalLocationSPEntry
    MAX-ACCESS  not-accessible
    STATUS    current
                DESCRIPTION
                        "Counters for the Physical Location service measurements for service providers"
                ::=  {  physicalLocation  2 }

  bwPhysicalLocationGroupTable  OBJECT-TYPE
    SYNTAX    SEQUENCE  OF  BwPhysicalLocationGroupEntry
    MAX-ACCESS  not-accessible
    STATUS    current
                DESCRIPTION
                        "Counters for the Physical Location service measurements for groups"
                ::=  {  physicalLocation  3 }
 
-- Service :: Physical Location :: SP TABLE ...........................................

  bwPhysicalLocationSPEntry OBJECT-TYPE
    SYNTAX    BwPhysicalLocationSPEntry
    MAX-ACCESS  not-accessible
    STATUS    current
                DESCRIPTION
                        "Each row contains the service counters for the Physical Location service for each service provider in the system"
    INDEX   {  bwPhysicalLocationSPIndex  }
                ::=  { bwPhysicalLocationSPTable 1 }

        BwPhysicalLocationSPEntry  ::=  SEQUENCE {
                bwPhysicalLocationSPIndex  Unsigned32,
                bwPhysicalLocationSPID  DisplayString,
                bwPhysicalLocationSPOriginationBlocked  Counter32
                }

  bwPhysicalLocationSPIndex   OBJECT-TYPE
    SYNTAX      Unsigned32
    MAX-ACCESS    read-only
    STATUS      current
                DESCRIPTION
                                "This column represents the index of the service provider in the system"
                ::=  {  bwPhysicalLocationSPEntry  1  }

  bwPhysicalLocationSPID  OBJECT-TYPE
    SYNTAX      DisplayString
    MAX-ACCESS    read-only
    STATUS      current
                DESCRIPTION
                                "This string represents a service provider ID"
                ::=  {  bwPhysicalLocationSPEntry  2  }

  bwPhysicalLocationSPOriginationBlocked  OBJECT-TYPE
    SYNTAX      Counter32
    MAX-ACCESS    read-write
    STATUS      current
                DESCRIPTION
                                "Number of times a user under the Service Provider has an origination blocked by the Physical Location service."
                ::=  {  bwPhysicalLocationSPEntry  3  }

-- Service :: Physical Location :: GROUP TABLE ...........................................

  bwPhysicalLocationGroupEntry  OBJECT-TYPE
    SYNTAX    BwPhysicalLocationGroupEntry
    MAX-ACCESS  not-accessible
    STATUS    current
                DESCRIPTION
                        "Each row contains the service counters for the Physical Location service for each group in the system"
    INDEX   {  bwPhysicalLocationGroupIndex  }
                ::=  { bwPhysicalLocationGroupTable 1 }

        BwPhysicalLocationGroupEntry  ::=  SEQUENCE {
                bwPhysicalLocationGroupIndex  Unsigned32,
                bwPhysicalLocationGroupID  DisplayString,
                bwPhysicalLocationGroupOriginationBlocked  Counter32
                }

  bwPhysicalLocationGroupIndex    OBJECT-TYPE
    SYNTAX      Unsigned32
    MAX-ACCESS    read-only
    STATUS      current
                DESCRIPTION
                                "This column represents the index of the group in the system"
                ::=  {  bwPhysicalLocationGroupEntry  1  }

  bwPhysicalLocationGroupID   OBJECT-TYPE
    SYNTAX      DisplayString
    MAX-ACCESS    read-only
    STATUS      current
                DESCRIPTION
                                "This string represents a service provider ID"
                ::=  {  bwPhysicalLocationGroupEntry  2  }

  bwPhysicalLocationGroupOriginationBlocked OBJECT-TYPE
    SYNTAX      Counter32
    MAX-ACCESS    read-write
    STATUS      current
                DESCRIPTION
                                "Number of times a user under the group has an origination blocked by the Physical Location service."
                ::=  {  bwPhysicalLocationGroupEntry  3  }

-- Service :: Fax Messaging ...........................................

  bwFaxMessagingReceived  OBJECT-TYPE
    SYNTAX      Counter32
    MAX-ACCESS    read-write
    STATUS      current
                DESCRIPTION
                                "This counter is incremented each time a user receives a fax."
                ::=  {  faxMessaging  1  }

  bwFaxMessagingReceptionFailure  OBJECT-TYPE
    SYNTAX      Counter32
    MAX-ACCESS    read-write
    STATUS      current
                DESCRIPTION
                                "This counter is incremented whenever the reception of a fax fails."
                ::=  {  faxMessaging  2  }

  bwFaxMessagingPrinted OBJECT-TYPE
    SYNTAX      Counter32
    MAX-ACCESS    read-write
    STATUS      current
                DESCRIPTION
                                "This counter is incremented each time a user sends a fax."
                ::=  {  faxMessaging  3  }

  bwFaxMessagingPrintingFailure OBJECT-TYPE
    SYNTAX      Counter32
    MAX-ACCESS    read-write
    STATUS      current
                DESCRIPTION
                                "This counter is incremented each time the printing of a fax over a fax number fails."
                ::=  {  faxMessaging  4  }

  bwFaxMessagingSPTable   OBJECT-TYPE
    SYNTAX    SEQUENCE  OF  BwFaxMessagingSPEntry
    MAX-ACCESS  not-accessible
    STATUS    current
                DESCRIPTION
                        "Counters for the Fax Messaging service measurements for service providers"
                ::=  {  faxMessaging  5 }

  bwFaxMessagingGroupTable  OBJECT-TYPE
    SYNTAX    SEQUENCE  OF  BwFaxMessagingGroupEntry
    MAX-ACCESS  not-accessible
    STATUS    current
                DESCRIPTION
                        "Counters for the Fax Messaging service measurements for groups"
                ::=  {  faxMessaging  6 }
 
-- Service :: Fax Messaging :: SP TABLE ...........................................

  bwFaxMessagingSPEntry OBJECT-TYPE
    SYNTAX    BwFaxMessagingSPEntry
    MAX-ACCESS  not-accessible
    STATUS    current
                DESCRIPTION
                        "Each row contains the service counters for the Fax Messaging service for each service provider in the system"
    INDEX   {  bwFaxMessagingSPIndex  }
                ::=  { bwFaxMessagingSPTable 1 }

        BwFaxMessagingSPEntry  ::=  SEQUENCE {
                bwFaxMessagingSPIndex  Unsigned32,
                bwFaxMessagingSPID  DisplayString,
                bwFaxMessagingSPReceived  Counter32,
                bwFaxMessagingSPReceptionFailure  Counter32,
                bwFaxMessagingSPPrinted  Counter32,
                bwFaxMessagingSPPrintingFailure  Counter32
                }

  bwFaxMessagingSPIndex   OBJECT-TYPE
    SYNTAX      Unsigned32
    MAX-ACCESS    read-only
    STATUS      current
                DESCRIPTION
                                "This column represents the index of the service provider in the system"
                ::=  {  bwFaxMessagingSPEntry  1  }

  bwFaxMessagingSPID  OBJECT-TYPE
    SYNTAX      DisplayString
    MAX-ACCESS    read-only
    STATUS      current
                DESCRIPTION
                                "This string represents a service provider ID"
                ::=  {  bwFaxMessagingSPEntry  2  }

  bwFaxMessagingSPReceived  OBJECT-TYPE
    SYNTAX      Counter32
    MAX-ACCESS    read-write
    STATUS      current
                DESCRIPTION
                                "This counter is incremented each time a user for a given service provider receives a fax."
                ::=  {  bwFaxMessagingSPEntry  3  }

  bwFaxMessagingSPReceptionFailure  OBJECT-TYPE
    SYNTAX      Counter32
    MAX-ACCESS    read-write
    STATUS      current
                DESCRIPTION
                                "This counter is incremented whenever the reception of a fax fails for a user for a given service provider."
                ::=  {  bwFaxMessagingSPEntry  4  }

  bwFaxMessagingSPPrinted OBJECT-TYPE
    SYNTAX      Counter32
    MAX-ACCESS    read-write
    STATUS      current
                DESCRIPTION
                                "This counter is incremented each time a user for a given service provider sends a fax."
                ::=  {  bwFaxMessagingSPEntry  5  }

  bwFaxMessagingSPPrintingFailure OBJECT-TYPE
    SYNTAX      Counter32
    MAX-ACCESS    read-write
    STATUS      current
                DESCRIPTION
                                "This counter is incremented each time the printing of a fax over a fax number fails for a user for a given service provider."
                ::=  {  bwFaxMessagingSPEntry  6  }

-- Service :: Fax Messaging :: GROUP TABLE ...........................................

  bwFaxMessagingGroupEntry  OBJECT-TYPE
    SYNTAX    BwFaxMessagingGroupEntry
    MAX-ACCESS  not-accessible
    STATUS    current
                DESCRIPTION
                        "Each row contains the service counters for the Fax Messaging service for each group in the system"
    INDEX   {  bwFaxMessagingGroupIndex  }
                ::=  { bwFaxMessagingGroupTable 1 }

        BwFaxMessagingGroupEntry  ::=  SEQUENCE {
                bwFaxMessagingGroupIndex  Unsigned32,
                bwFaxMessagingGroupID  DisplayString,
                bwFaxMessagingGroupReceived  Counter32,
      bwFaxMessagingGroupReceptionFailure  Counter32,
      bwFaxMessagingGroupPrinted  Counter32,
      bwFaxMessagingGroupPrintingFailure  Counter32
                }

  bwFaxMessagingGroupIndex    OBJECT-TYPE
    SYNTAX      Unsigned32
    MAX-ACCESS    read-only
    STATUS      current
                DESCRIPTION
                                "This column represents the index of the group in the system"
                ::=  {  bwFaxMessagingGroupEntry  1  }

  bwFaxMessagingGroupID   OBJECT-TYPE
    SYNTAX      DisplayString
    MAX-ACCESS    read-only
    STATUS      current
                DESCRIPTION
                                "This string represents a group ID"
                ::=  {  bwFaxMessagingGroupEntry  2  }

  bwFaxMessagingGroupReceived OBJECT-TYPE
    SYNTAX      Counter32
    MAX-ACCESS    read-write
    STATUS      current
                DESCRIPTION
                                "This counter is incremented each time a user for a given group receives a fax."
                ::=  {  bwFaxMessagingGroupEntry  3  }

  bwFaxMessagingGroupReceptionFailure OBJECT-TYPE
    SYNTAX      Counter32
    MAX-ACCESS    read-write
    STATUS      current
                DESCRIPTION
                                "This counter is incremented whenever the reception of a fax fails for a user for a given group."
                ::=  {  bwFaxMessagingGroupEntry  4  }

  bwFaxMessagingGroupPrinted  OBJECT-TYPE
    SYNTAX      Counter32
    MAX-ACCESS    read-write
    STATUS      current
                DESCRIPTION
                                "This counter is incremented each time a user for a given group sends a fax."
                ::=  {  bwFaxMessagingGroupEntry  5  }

  bwFaxMessagingGroupPrintingFailure  OBJECT-TYPE
    SYNTAX      Counter32
    MAX-ACCESS    read-write
    STATUS      current
                DESCRIPTION
                                "This counter is incremented each time the printing of a fax over a fax number fails for a user for a given group."
                ::=  {  bwFaxMessagingGroupEntry  6  }

-- Service :: External Emergency Routing ...........................................

  bwExtEmergencyRtgQuerySent  OBJECT-TYPE
    SYNTAX      Counter32
    MAX-ACCESS    read-write
    STATUS      current
                DESCRIPTION
                                "The counter shall be incremented each time the service results in a query being sent to the EN Server."
                ::=  {  externalemergencyrouting  1  }

  bwExtEmergencyRtgQueryFailure OBJECT-TYPE
    SYNTAX      Counter32
    MAX-ACCESS    read-write
    STATUS      current
                DESCRIPTION
                                "The counter shall be incremented each time the query is not successful, either because the EN Server is unreachable, or because the routing number is invalid."
                ::=  {  externalemergencyrouting  2  }

  bwExtEmergencyRtgENServerTimeout  OBJECT-TYPE
    SYNTAX      Counter32
    MAX-ACCESS    read-write
    STATUS      current
                DESCRIPTION
                                "The counter shall be incremented each time an active connection to an EN Server times out."
                ::=  {  externalemergencyrouting  3  }

-- Service :: Two Stage Dialing ...........................................

  bwTwoStageDialingInvocation OBJECT-TYPE
    SYNTAX      Counter32
    MAX-ACCESS    read-write
    STATUS      current
                DESCRIPTION
                        "Number of times a user invokes the Two-Stage Dialing service."
                ::=  {  twoStageDialing  1  }

  bwTwoStageDialingSPTable  OBJECT-TYPE
    SYNTAX    SEQUENCE  OF  BwTwoStageDialingSPEntry
    MAX-ACCESS  not-accessible
    STATUS    current
                DESCRIPTION
                        "Counters for the Two Stage Dialing service measurements for service providers"
                ::=  {  twoStageDialing  2 }

  bwTwoStageDialingGroupTable OBJECT-TYPE
    SYNTAX    SEQUENCE  OF  BwTwoStageDialingGroupEntry
    MAX-ACCESS  not-accessible
    STATUS    current
                DESCRIPTION
                        "Counters for the Two Stage Dialing service measurements for groups"
                ::=  {  twoStageDialing  3 }
 
-- Service :: Two Stage Dialing :: SP TABLE ...........................................

  bwTwoStageDialingSPEntry  OBJECT-TYPE
    SYNTAX    BwTwoStageDialingSPEntry
    MAX-ACCESS  not-accessible
    STATUS    current
                DESCRIPTION
                        "Each row contains the service counters for the Fax Messaging service for each service provider in the system"
    INDEX   {  bwTwoStageDialingSPIndex  }
                ::=  { bwTwoStageDialingSPTable 1 }

        BwTwoStageDialingSPEntry  ::=  SEQUENCE {
                bwTwoStageDialingSPIndex  Unsigned32,
                bwTwoStageDialingSPID     DisplayString,
                bwTwoStageDialingSPInvocation  Counter32
                }

  bwTwoStageDialingSPIndex    OBJECT-TYPE
    SYNTAX      Unsigned32
    MAX-ACCESS    read-only
    STATUS      current
                DESCRIPTION
                                "This column represents the index of the Service Provider in the system"
                ::=  {  bwTwoStageDialingSPEntry  1  }

  bwTwoStageDialingSPID   OBJECT-TYPE
    SYNTAX      DisplayString
    MAX-ACCESS    read-only
    STATUS      current
                DESCRIPTION
                                "This string represents a Service Provider ID"
                ::=  {  bwTwoStageDialingSPEntry  2  }

  bwTwoStageDialingSPInvocation OBJECT-TYPE
    SYNTAX      Counter32
    MAX-ACCESS    read-write
    STATUS      current
                DESCRIPTION
                                "Number of times a user invokes the Two-Stage Dialing service.  There is one instance of this counter for each service provider defined in the system."
                ::=  {  bwTwoStageDialingSPEntry  3  }

-- Service :: Two Stage Dialing :: Group TABLE ...........................................

  bwTwoStageDialingGroupEntry OBJECT-TYPE
    SYNTAX    BwTwoStageDialingGroupEntry
    MAX-ACCESS  not-accessible
    STATUS    current
                DESCRIPTION
                        "Each row contains the service counters for the Fax Messaging service for each service provider in the system"
    INDEX   {  bwTwoStageDialingGroupIndex  }
                ::=  { bwTwoStageDialingGroupTable 1 }

        BwTwoStageDialingGroupEntry  ::=  SEQUENCE {
                bwTwoStageDialingGroupIndex Unsigned32,
                bwTwoStageDialingGroupID   DisplayString,
                bwTwoStageDialingGroupInvocation  Counter32
                }

  bwTwoStageDialingGroupIndex   OBJECT-TYPE
    SYNTAX      Unsigned32
    MAX-ACCESS    read-only
    STATUS      current
                DESCRIPTION
                                "This column represents the index of the Group in the system"
                ::=  {  bwTwoStageDialingGroupEntry  1  }

  bwTwoStageDialingGroupID  OBJECT-TYPE
    SYNTAX      DisplayString
    MAX-ACCESS    read-only
    STATUS      current
                DESCRIPTION
                                "This string represents a Group ID"
                ::=  {  bwTwoStageDialingGroupEntry  2  }

  bwTwoStageDialingGroupInvocation  OBJECT-TYPE
    SYNTAX      Counter32
    MAX-ACCESS    read-write
    STATUS      current
                DESCRIPTION
                        "Number of times a user invokes the Two-Stage Dialing service.  There is one instance of this counter for each group defined in the system."
                ::=  {  bwTwoStageDialingGroupEntry  3  }

-- Service :: Call Forwarding Not Reachable...........................................

  bwCFNRcNumForwarded         OBJECT-TYPE
    SYNTAX      Counter32
    MAX-ACCESS    read-write
    STATUS      current
                DESCRIPTION
                        "This is the number of times a call is redirected by the Call Forwarding Not Reachable service."
                ::=  {  callForwardingNotReachable  1  }

  bwCFNRcNumPhoneActivations  OBJECT-TYPE
    SYNTAX      Counter32
    MAX-ACCESS    read-write
    STATUS      current
                DESCRIPTION
                        "This is the number of times the Call Forwarding Not Reachable service is activated with a FAC."
                ::=  {  callForwardingNotReachable  2  }

  bwCFNRcNumPhoneDeactivations  OBJECT-TYPE
    SYNTAX      Counter32
    MAX-ACCESS    read-write
    STATUS      current
                DESCRIPTION
                        "This is the number of times the Call Forwarding Not Reachable service is deactivated with a FAC."
                ::=  {  callForwardingNotReachable  3  }

  bwCFNRcDestinationChanged OBJECT-TYPE
    SYNTAX      Counter32
    MAX-ACCESS    read-write
    STATUS      current
                DESCRIPTION
                        "This is the number of times the Call Forwarding Not Reachable service destination is modified with the activation FAC."
                ::=  {  callForwardingNotReachable  4  }

  bwCallForwardingNotReachableSPTable OBJECT-TYPE
    SYNTAX      SEQUENCE  OF  BwCallForwardingNotReachableSPEntry
    MAX-ACCESS    not-accessible
    STATUS      current
                DESCRIPTION
                        "This is the number of times a call is redirected by the Call Forwarding Not Reachable service.  There is one instance of this counter for each service provider or enterprise defined in the system."
                ::=  {  callForwardingNotReachable  5  }

  bwCallForwardingNotReachableGroupTable  OBJECT-TYPE
    SYNTAX      SEQUENCE  OF  BwCallForwardingNotReachableGroupEntry
    MAX-ACCESS    not-accessible
    STATUS      current
                DESCRIPTION
                        "This is the number of times a call is redirected by the Call Forwarding Not Reachable service.  There is one instance of this counter for each group defined in the system."
                ::=  {  callForwardingNotReachable  6  }


-- Service :: Call Forwarding Not Reachable :: SP TABLE ...........................................

  bwCallForwardingNotReachableSPEntry OBJECT-TYPE
    SYNTAX    BwCallForwardingNotReachableSPEntry
    MAX-ACCESS  not-accessible
    STATUS    current
                DESCRIPTION
                        "Each row contains the service counters for the Call Forwarding Not Reachable service for each service provider in the system"
    INDEX   {  bwCFNRcSPIndex  }
                ::=  { bwCallForwardingNotReachableSPTable 1 }

        BwCallForwardingNotReachableSPEntry  ::=  SEQUENCE {
                bwCFNRcSPIndex  Unsigned32,
                bwCFNRcSPID     DisplayString,
                bwCFNRcSPNumForwarded  Counter32,
                bwCFNRcSPNumPhoneActivations  Counter32,
                bwCFNRcSPNumPhoneDeactivations  Counter32,
                bwCFNRcSPDestinationChanged  Counter32
                }

  bwCFNRcSPIndex  OBJECT-TYPE
    SYNTAX      Unsigned32
    MAX-ACCESS    read-only
    STATUS      current
                DESCRIPTION
                                "This column represents the index of the Service Provider in the system."
                ::=  {  bwCallForwardingNotReachableSPEntry  1  }

  bwCFNRcSPID   OBJECT-TYPE
    SYNTAX      DisplayString
    MAX-ACCESS    read-only
    STATUS      current
                DESCRIPTION
                                "This string represents a Service Provider ID."
                ::=  {  bwCallForwardingNotReachableSPEntry  2  }

  bwCFNRcSPNumForwarded OBJECT-TYPE
    SYNTAX      Counter32
    MAX-ACCESS    read-write
    STATUS      current
                DESCRIPTION
                        "This is the number of times a call is redirected by the Call Forwarding Not Reachable service.  There is one instance of this counter for each service provider or enterprise defined in the system."
                ::=  {  bwCallForwardingNotReachableSPEntry  3  }

  bwCFNRcSPNumPhoneActivations  OBJECT-TYPE
    SYNTAX      Counter32
    MAX-ACCESS    read-write
    STATUS      current
                DESCRIPTION
                        "This is the number of times the Call Forwarding Not Reachable service is activated with a FAC.  There is one instance of this counter for each service provider or enterprise defined in the system."
                ::=  {  bwCallForwardingNotReachableSPEntry  4  }

  bwCFNRcSPNumPhoneDeactivations  OBJECT-TYPE
    SYNTAX      Counter32
    MAX-ACCESS    read-write
    STATUS      current
                DESCRIPTION
                        "This is the number of times the Call Forwarding Not Reachable service is deactivated with a FAC.  There is one instance of this counter for each service provider or enterprise defined in the system."
                ::=  {  bwCallForwardingNotReachableSPEntry  5  }

  bwCFNRcSPDestinationChanged OBJECT-TYPE
    SYNTAX      Counter32
    MAX-ACCESS    read-write
    STATUS      current
                DESCRIPTION
                        "This is the number of times the Call Forwarding Not Reachable service destination is modified with the activation FAC.  There is one instance of this counter for each service provider or enterprise defined in the system."
                ::=  {  bwCallForwardingNotReachableSPEntry  6  }

-- Service :: Call Forwarding Not Reachable :: Group TABLE ...........................................

  bwCallForwardingNotReachableGroupEntry  OBJECT-TYPE
    SYNTAX    BwCallForwardingNotReachableGroupEntry
    MAX-ACCESS  not-accessible
    STATUS    current
                DESCRIPTION
                        "Each row contains the service counters for the Call Forwarding Not Reachable service for each group in the system"
    INDEX   {  bwCFNRcGroupIndex  }
                ::=  { bwCallForwardingNotReachableGroupTable 1 }

        BwCallForwardingNotReachableGroupEntry  ::=  SEQUENCE {
                bwCFNRcGroupIndex Unsigned32,
                bwCFNRcGroupID   DisplayString,
                bwCFNRcGroupNumForwarded  Counter32,
                bwCFNRcGroupNumPhoneActivations  Counter32,
                bwCFNRcGroupNumPhoneDeactivations  Counter32,
                bwCFNRcGroupDestinationChanged  Counter32
                }

  bwCFNRcGroupIndex   OBJECT-TYPE
    SYNTAX      Unsigned32
    MAX-ACCESS    read-only
    STATUS      current
                DESCRIPTION
                                "This column represents the index of the Group in the system."
                ::=  {  bwCallForwardingNotReachableGroupEntry  1  }

  bwCFNRcGroupID  OBJECT-TYPE
    SYNTAX      DisplayString
    MAX-ACCESS    read-only
    STATUS      current
                DESCRIPTION
                                "This string represents a Group ID."
                ::=  {  bwCallForwardingNotReachableGroupEntry  2  }

  bwCFNRcGroupNumForwarded    OBJECT-TYPE
    SYNTAX      Counter32
    MAX-ACCESS    read-write
    STATUS      current
                DESCRIPTION
                        "This is the number of times a call is redirected by the Call Forwarding Not Reachable service.  There is one instance of this counter for each group defined in the system."
                ::=  {  bwCallForwardingNotReachableGroupEntry  3  }

  bwCFNRcGroupNumPhoneActivations   OBJECT-TYPE
    SYNTAX      Counter32
    MAX-ACCESS    read-write
    STATUS      current
                DESCRIPTION
                        "This is the number of times the Call Forwarding Not Reachable service is activated with a FAC.  There is one instance of this counter for each group defined in the system."
                ::=  {  bwCallForwardingNotReachableGroupEntry  4  }

  bwCFNRcGroupNumPhoneDeactivations   OBJECT-TYPE
    SYNTAX      Counter32
    MAX-ACCESS    read-write
    STATUS      current
                DESCRIPTION
                        "This is the number of times the Call Forwarding Not Reachable service is deactivated with a FAC.  There is one instance of this counter for each group defined in the system."
                ::=  {  bwCallForwardingNotReachableGroupEntry  5 }

  bwCFNRcGroupDestinationChanged    OBJECT-TYPE
    SYNTAX      Counter32
    MAX-ACCESS    read-write
    STATUS      current
                DESCRIPTION
                        "This is the number of times the Call Forwarding Not Reachable service destination is modified with the activation FAC.  There is one instance of this counter for each group defined in the system."
                ::=  {  bwCallForwardingNotReachableGroupEntry  6 }

-- Service :: MWI Delivery to Mobile...........................................

  bwMWISMSSent  OBJECT-TYPE
    SYNTAX      Counter32
    MAX-ACCESS  read-write
    STATUS      current
    DESCRIPTION
      "Number of SMS notifications sent for all users."
    ::= {  mwiDeliveryToMobile  1 }

  bwMWIDeliveryToMobileSPTable  OBJECT-TYPE
    SYNTAX      SEQUENCE  OF  BwMWIDeliveryToMobileSPEntry
    MAX-ACCESS    not-accessible
    STATUS      current
                DESCRIPTION
                        "This is the number of times a SMS is sent by the Message Waiting Indicator Delivery to Mobile service.  There is one instance of this counter for each service provider or enterprise defined in the system."
                ::=  {  mwiDeliveryToMobile  2  }

  bwMWIDeliveryToMobileGroupTable OBJECT-TYPE
    SYNTAX      SEQUENCE  OF  BwMWIDeliveryToMobileGroupEntry
    MAX-ACCESS    not-accessible
    STATUS      current
                DESCRIPTION
                        "This is the number of times a SMS is sent by the Message Waiting Indicator Delivery to Mobile service.  There is one instance of this counter for each group defined in the system."
                ::=  {  mwiDeliveryToMobile  3  }

-- Service :: MWI Delivery to Mobile :: SP TABLE ...........................................

  bwMWIDeliveryToMobileSPEntry  OBJECT-TYPE
    SYNTAX    BwMWIDeliveryToMobileSPEntry
    MAX-ACCESS  not-accessible
    STATUS    current
                DESCRIPTION
                        "Each row contains the service counters for the Message Waiting Indicator Delivery to Mobile service for each service provider in the system"
    INDEX   {  bwMWISPIndex  }
                ::=  { bwMWIDeliveryToMobileSPTable 1 }

        BwMWIDeliveryToMobileSPEntry  ::=  SEQUENCE {
    bwMWISPIndex    Unsigned32,
    bwMWISPID       DisplayString,
                bwSPMWISMSSent  Counter32
        }

  bwMWISPIndex  OBJECT-TYPE
    SYNTAX      Unsigned32
    MAX-ACCESS    read-only
    STATUS      current
                DESCRIPTION
                                "This column represents the index of the Service Provider in the system."
                ::=  {  bwMWIDeliveryToMobileSPEntry  1  }

  bwMWISPID   OBJECT-TYPE
    SYNTAX      DisplayString
    MAX-ACCESS    read-only
    STATUS      current
                DESCRIPTION
                                "This string represents a Service Provider ID."
                ::=  {  bwMWIDeliveryToMobileSPEntry  2  }

        bwSPMWISMSSent  OBJECT-TYPE
    SYNTAX      Counter32
    MAX-ACCESS  read-write
    STATUS      current
    DESCRIPTION
      "Same as bwMWISMSSent, per service provider."
    ::= {  bwMWIDeliveryToMobileSPEntry  3 }

-- Service :: MWI Delivery to Mobile :: Group TABLE ...........................................

  bwMWIDeliveryToMobileGroupEntry OBJECT-TYPE
    SYNTAX    BwMWIDeliveryToMobileGroupEntry
    MAX-ACCESS  not-accessible
    STATUS    current
                DESCRIPTION
                        "Each row contains the service counters for the Message Waiting Indicator Delivery to Mobile service for each service provider in the system"
    INDEX   {  bwMWIGroupIndex  }
                ::=  { bwMWIDeliveryToMobileGroupTable 1 }

        BwMWIDeliveryToMobileGroupEntry  ::=  SEQUENCE {
    bwMWIGroupIndex    Unsigned32,
    bwMWIGroupID       DisplayString,
                bwGroupMWISMSSent  Counter32
        }

  bwMWIGroupIndex OBJECT-TYPE
    SYNTAX      Unsigned32
    MAX-ACCESS    read-only
    STATUS      current
                DESCRIPTION
                                "This column represents the index of the Group in the system."
                ::=  {  bwMWIDeliveryToMobileGroupEntry  1  }

  bwMWIGroupID  OBJECT-TYPE
    SYNTAX      DisplayString
    MAX-ACCESS    read-only
    STATUS      current
                DESCRIPTION
                                "This string represents a Group ID."
                ::=  {  bwMWIDeliveryToMobileGroupEntry  2  }

        bwGroupMWISMSSent  OBJECT-TYPE
    SYNTAX      Counter32
    MAX-ACCESS  read-write
    STATUS      current
    DESCRIPTION
      "Same as bwMWISMSSent, per service provider."
    ::= {  bwMWIDeliveryToMobileGroupEntry  3 }

-- Service :: Shared Call Appearance ...........................................

  bwSCASPTable  OBJECT-TYPE
    SYNTAX      SEQUENCE  OF  BwSCASPEntry
    MAX-ACCESS    not-accessible
    STATUS      current
                DESCRIPTION
                        "This is the number of times a SMS is sent by the Message Waiting Indicator Delivery to Mobile service.  There is one instance of this counter for each service provider or enterprise defined in the system."
                ::=  {  sharedCallAppearance  1  }

  bwSCAGroupTable OBJECT-TYPE
    SYNTAX      SEQUENCE  OF  BwSCAGroupEntry
    MAX-ACCESS    not-accessible
    STATUS      current
                DESCRIPTION
                        "This is the number of times a SMS is sent by the Message Waiting Indicator Delivery to Mobile service.  There is one instance of this counter for each group defined in the system."
                ::=  {  sharedCallAppearance  2  }

  bwSCACallRetrieveSuccess  OBJECT-TYPE
    SYNTAX      Counter32
    MAX-ACCESS  read-write
    STATUS      current
    DESCRIPTION
      "This is the number of times a user successfully retrieves a call using the SCA Call Retrieve feature."
    ::= {  sharedCallAppearance  3 }

  bwSCALocationControlActivationSuccess  OBJECT-TYPE
    SYNTAX      Counter32
    MAX-ACCESS  read-write
    STATUS      current
    DESCRIPTION
      "This is the number of times a user activates an alternate location using the SCA Location Control feature."
    ::= {  sharedCallAppearance  4 }
  
  bwSCALocationControlDeactivationSuccess  OBJECT-TYPE
    SYNTAX      Counter32
    MAX-ACCESS  read-write
    STATUS      current
    DESCRIPTION
      "This is the number of times a user deactivates an alternate location using the SCA Location Control feature."
    ::= {  sharedCallAppearance  5 }

-- Service :: Shared Call Appearance :: SP TABLE ...........................................

  bwSCASPEntry  OBJECT-TYPE
    SYNTAX    BwSCASPEntry
    MAX-ACCESS  not-accessible
    STATUS    current
                DESCRIPTION
                        "Each row contains the service counters for the Shared Call Appearance service for each service provider in the system"
    INDEX   {  bwSCASPIndex  }
                ::=  { bwSCASPTable 1 }

        BwSCASPEntry  ::=  SEQUENCE {
    bwSCASPIndex    Unsigned32,
    bwSCASPID       DisplayString,
    bwSCASPCallRetrieveSuccess  Counter32,
    bwSCASPLocationControlActivationSuccess Counter32,
    bwSCASPLocationControlDeactivationSuccess Counter32
        }

    bwSCASPIndex  OBJECT-TYPE
    SYNTAX      Unsigned32
    MAX-ACCESS    read-only
    STATUS      current
                DESCRIPTION
                                "This column represents the index of the Service Provider in the system."
                ::=  {  bwSCASPEntry  1  }

  bwSCASPID   OBJECT-TYPE
    SYNTAX      DisplayString
    MAX-ACCESS    read-only
    STATUS      current
                DESCRIPTION
                                "This string represents a Service Provider ID."
                ::=  {  bwSCASPEntry  2  }

        bwSCASPCallRetrieveSuccess  OBJECT-TYPE
    SYNTAX      Counter32
    MAX-ACCESS  read-write
    STATUS      current
    DESCRIPTION
      "The number of times a user successfully retrieves a call using the SCA Call Retrieve feature.  There is one instance of this counter for each service provider defined in the system."
    ::= {  bwSCASPEntry  3 }

        bwSCASPLocationControlActivationSuccess  OBJECT-TYPE
    SYNTAX      Counter32
    MAX-ACCESS  read-write
    STATUS      current
    DESCRIPTION
      "The number of times a user activates an alternate location using the SCA Location Control feature.  There is one instance of this counter for each service provider defined in the system."
    ::= {  bwSCASPEntry  4 }

        bwSCASPLocationControlDeactivationSuccess  OBJECT-TYPE
    SYNTAX      Counter32
    MAX-ACCESS  read-write
    STATUS      current
    DESCRIPTION
      "The number of times a user deactivates an alternate location using the SCA Location Control feature.  There is one instance of this counter for each service provider defined in the system."
    ::= {  bwSCASPEntry  5 }

-- Service :: Shared Call Appearance :: GROUP TABLE ...........................................

  bwSCAGroupEntry OBJECT-TYPE
    SYNTAX    BwSCAGroupEntry
    MAX-ACCESS  not-accessible
    STATUS    current
                DESCRIPTION
                        "Each row contains the service counters for the Shared Call Appearance service for each group in the system"
    INDEX   {  bwSCAGroupIndex  }
                ::=  { bwSCAGroupTable 1 }

        BwSCAGroupEntry  ::=  SEQUENCE {
    bwSCAGroupIndex    Unsigned32,
    bwSCAGroupID       DisplayString,
    bwSCAGroupCallRetrieveSuccess  Counter32,
    bwSCAGroupLocationControlActivationSuccess Counter32,
    bwSCAGroupLocationControlDeactivationSuccess Counter32
        }

    bwSCAGroupIndex OBJECT-TYPE
    SYNTAX      Unsigned32
    MAX-ACCESS    read-only
    STATUS      current
                DESCRIPTION
                                "This column represents the index of the Group in the system."
                ::=  {  bwSCAGroupEntry  1  }

  bwSCAGroupID  OBJECT-TYPE
    SYNTAX      DisplayString
    MAX-ACCESS    read-only
    STATUS      current
                DESCRIPTION
                                "This string represents a Group ID."
                ::=  {  bwSCAGroupEntry  2  }

          bwSCAGroupCallRetrieveSuccess  OBJECT-TYPE
    SYNTAX      Counter32
    MAX-ACCESS  read-write
    STATUS      current
    DESCRIPTION
      "The number of times a user successfully retrieves a call using the SCA Call Retrieve feature.  There is one instance of this counter for each group defined in the system."
    ::= {  bwSCAGroupEntry  3 }

          bwSCAGroupLocationControlActivationSuccess  OBJECT-TYPE
    SYNTAX      Counter32
    MAX-ACCESS  read-write
    STATUS      current
    DESCRIPTION
      "The number of times a user activates an alternate location using the SCA Location Control feature.  There is one instance of this counter for each group defined in the system."
    ::= {  bwSCAGroupEntry  4 }

          bwSCAGroupLocationControlDeactivationSuccess  OBJECT-TYPE
    SYNTAX      Counter32
    MAX-ACCESS  read-write
    STATUS      current
    DESCRIPTION
      "The number of times a user deactivates an alternate location using the SCA Location Control feature.  There is one instance of this counter for each group defined in the system."
    ::= {  bwSCAGroupEntry  5 }

-- Service :: External Custom Ringback................................................

        bwExternalCustomRingbackAttempts  OBJECT-TYPE
                SYNTAX                  Counter32
                MAX-ACCESS              read-write
                STATUS                  current
                DESCRIPTION
                        "This is the number of attempts made to play ringback from an external custom ringback source."
                ::=  {  externalCustomRingback  1  }

        bwExternalCustomRingbackFailures        OBJECT-TYPE
                SYNTAX                  Counter32
                MAX-ACCESS              read-write
                STATUS                  current
                DESCRIPTION
                        "This is the number of times an attempt to play ringback from an external custom ringback source failed, due to timeout or error."
                ::=  {  externalCustomRingback  2  }

        bwExternalCustomRingbackSPTable OBJECT-TYPE
                SYNTAX                  SEQUENCE  OF  BwExternalCustomRingbackSPEntry
                MAX-ACCESS              not-accessible
                STATUS                  current
                DESCRIPTION
                        "This table contains the counters for External Custom Ringback service measurements for service providers."
                ::=  {  externalCustomRingback  3  }

        bwExternalCustomRingbackGroupTable      OBJECT-TYPE
                SYNTAX                  SEQUENCE  OF  BwExternalCustomRingbackGroupEntry
                MAX-ACCESS              not-accessible
                STATUS                  current
                DESCRIPTION
                        "This table contains the counters for External Custom Ringback service measurements for groups."
                ::=  {  externalCustomRingback  4  }


-- Service :: External Custom Ringback :: SP TABLE ................................................

        bwExternalCustomRingbackSPEntry OBJECT-TYPE
                SYNTAX          BwExternalCustomRingbackSPEntry
                MAX-ACCESS      not-accessible
                STATUS          current
                DESCRIPTION
                        "Each row contains the service counters for the External Custom Ringback service for each service provider in the system"
                INDEX           {  bwExternalCustomRingbackSPIndex  }
                ::=  { bwExternalCustomRingbackSPTable 1 }

        BwExternalCustomRingbackSPEntry  ::=  SEQUENCE {
    bwExternalCustomRingbackSPIndex  Unsigned32,
    bwExternalCustomRingbackSPID     DisplayString,
                bwExternalCustomRingbackSPAttempts  Counter32,
                bwExternalCustomRingbackSPFailures  Counter32
                }

        bwExternalCustomRingbackSPIndex OBJECT-TYPE
                SYNTAX                  Unsigned32
                MAX-ACCESS              read-only
                STATUS                  current
                DESCRIPTION
                                "This column represents the index of the Service Provider in the system."
                ::=  {  bwExternalCustomRingbackSPEntry  1  }

        bwExternalCustomRingbackSPID    OBJECT-TYPE
                SYNTAX                  DisplayString
                MAX-ACCESS              read-only
                STATUS                  current
                DESCRIPTION
                                "This string represents a Service Provider ID."
                ::=  {  bwExternalCustomRingbackSPEntry  2  }

        bwExternalCustomRingbackSPAttempts      OBJECT-TYPE
                SYNTAX                  Counter32
                MAX-ACCESS              read-write
                STATUS                  current
                DESCRIPTION
                        "This is the number of attempts made to play ringback from an external custom ringback source for a given service provider. There is one instance of this counter for each service provider or enterprise defined in the system."
                ::=  {  bwExternalCustomRingbackSPEntry  3  }

        bwExternalCustomRingbackSPFailures      OBJECT-TYPE
                SYNTAX                  Counter32
                MAX-ACCESS              read-write
                STATUS                  current
                DESCRIPTION
                        "This is the number of times an attempt to play ringback from an external custom ringback source failed, due to timeout or error, for a given service provider. There is one instance of this counter for each service provider or enterprise defined in the system."
                ::=  {  bwExternalCustomRingbackSPEntry  4  }

-- Service :: External Custom Ringback :: Group TABLE .............................................

        bwExternalCustomRingbackGroupEntry      OBJECT-TYPE
                SYNTAX          BwExternalCustomRingbackGroupEntry
                MAX-ACCESS      not-accessible
                STATUS          current
                DESCRIPTION
                        "Each row contains the service counters for the External Custom Ringback service for each group in the system"
                INDEX           {  bwExternalCustomRingbackGroupIndex  }
                ::=  { bwExternalCustomRingbackGroupTable 1 }

        BwExternalCustomRingbackGroupEntry  ::=  SEQUENCE {
    bwExternalCustomRingbackGroupIndex  Unsigned32,
    bwExternalCustomRingbackGroupID     DisplayString,
                bwExternalCustomRingbackGroupAttempts  Counter32,
                bwExternalCustomRingbackGroupFailures  Counter32
                }

        bwExternalCustomRingbackGroupIndex      OBJECT-TYPE
                SYNTAX                  Unsigned32
                MAX-ACCESS              read-only
                STATUS                  current
                DESCRIPTION
                                "This column represents the index of the Group in the system."
                ::=  {  bwExternalCustomRingbackGroupEntry  1  }

        bwExternalCustomRingbackGroupID         OBJECT-TYPE
                SYNTAX                  DisplayString
                MAX-ACCESS              read-only
                STATUS                  current
                DESCRIPTION
                                "This string represents a Group ID."
                ::=  {  bwExternalCustomRingbackGroupEntry  2  }

        bwExternalCustomRingbackGroupAttempts   OBJECT-TYPE
                SYNTAX                  Counter32
                MAX-ACCESS              read-write
                STATUS                  current
                DESCRIPTION
                        "This is the number of attempts made to play ringback from an external custom ringback source for a given group. There is one instance of this counter for each group defined in the system."
                ::=  {  bwExternalCustomRingbackGroupEntry  3  }

        bwExternalCustomRingbackGroupFailures   OBJECT-TYPE
                SYNTAX                  Counter32
                MAX-ACCESS              read-write
                STATUS                  current
                DESCRIPTION
                        "This is the number of times an attempt to play ringback from an external custom ringback source failed, due to timeout or error, for a given group. There is one instance of this counter for each group defined in the system."
                ::=  {  bwExternalCustomRingbackGroupEntry  4  }

-- Service :: In Call Service Activation ...........................................

  bwInCallServiceActivationSPTable      OBJECT-TYPE
                SYNTAX                  SEQUENCE  OF  BwInCallServiceActivationSPEntry
                MAX-ACCESS              not-accessible
                STATUS                  current
                DESCRIPTION
                        "Each row contains the service counters for the In Call Service Activation service for each service provider in the system"
                ::=  {  inCallServiceActivation  1  }

  bwInCallServiceActivationGroupTable   OBJECT-TYPE
                SYNTAX                  SEQUENCE  OF  BwInCallServiceActivationGroupEntry
                MAX-ACCESS              not-accessible
                STATUS                  current
                DESCRIPTION
                        "Each row contains the service counters for the In Call Service Activation service for each group in the system"
                ::=  {  inCallServiceActivation  2  }

  bwICSAMonitoringStarted  OBJECT-TYPE
                SYNTAX      Counter32
                MAX-ACCESS  read-write
                STATUS      current
                DESCRIPTION
                        "This is the number of times a media path is monitored for Flash Tone digits by the In Call Service Activation service."
                ::= {  inCallServiceActivation  3 }

  bwICSAMonitoringFailure  OBJECT-TYPE
                SYNTAX      Counter32
                MAX-ACCESS  read-write
                STATUS      current
                DESCRIPTION
                        "This is the number of times media path monitoring fails to be started by the In Call Service Activation service."
                ::= {  inCallServiceActivation  4 }

  bwICSAFlashDigitsDetected  OBJECT-TYPE
                SYNTAX      Counter32
                MAX-ACCESS  read-write
                STATUS      current
                DESCRIPTION
                        "This is the number of times the In Call Service Activation service detects the Flash digit string."
                ::= {  inCallServiceActivation  5 }

-- Service :: In Call Service Activation :: SP TABLE ...........................................

        bwInCallServiceActivationSPEntry        OBJECT-TYPE
                SYNTAX          BwInCallServiceActivationSPEntry
                MAX-ACCESS      not-accessible
                STATUS          current
                DESCRIPTION
                        "Each row contains the service counters for the In Call Service Activation service for each service provider in the system"
                INDEX           {  bwICSASPIndex  }
                ::=  { bwInCallServiceActivationSPTable 1 }

        BwInCallServiceActivationSPEntry  ::=  SEQUENCE {
                bwICSASPIndex  Unsigned32,
                bwICSASPID     DisplayString,
                bwICSASPMonitoringStarted  Counter32,
                bwICSASPMonitoringFailure  Counter32,
                bwICSASPFlashDigitsDetected  Counter32
                }

        bwICSASPIndex   OBJECT-TYPE
                SYNTAX                  Unsigned32
                MAX-ACCESS              read-only
                STATUS                  current
                DESCRIPTION
                                "This column represents the index of the Service Provider in the system."
                ::=  {  bwInCallServiceActivationSPEntry  1  }

        bwICSASPID      OBJECT-TYPE
                SYNTAX                  DisplayString
                MAX-ACCESS              read-only
                STATUS                  current
                DESCRIPTION
                                "This string represents a Service Provider ID."
                ::=  {  bwInCallServiceActivationSPEntry  2  }

        bwICSASPMonitoringStarted       OBJECT-TYPE
                SYNTAX                  Counter32
                MAX-ACCESS              read-write
                STATUS                  current
                DESCRIPTION
                        "This is the number of times a media path is monitored for Flash Tone digits by the In Call Service Activation service.  There is one instance of this counter for each service provider or enterprise defined in the system."
                ::=  {  bwInCallServiceActivationSPEntry  3  }

        bwICSASPMonitoringFailure       OBJECT-TYPE
                SYNTAX                  Counter32
                MAX-ACCESS              read-write
                STATUS                  current
                DESCRIPTION
                        "This is the number of times media path monitoring fails to be started by the In Call Service Activation service.  There is one instance of this counter for each service provider or enterprise defined in the system."
                ::=  {  bwInCallServiceActivationSPEntry  4  }

        bwICSASPFlashDigitsDetected     OBJECT-TYPE
                SYNTAX                  Counter32
                MAX-ACCESS              read-write
                STATUS                  current
                DESCRIPTION
                        "This is the number of times the In Call Service Activation service detects the Flash digit string.  There is one instance of this counter for each service provider or enterprise defined in the system."
                ::=  {  bwInCallServiceActivationSPEntry  5  }

-- Service :: In Call Service Activation :: Group TABLE ...........................................

        bwInCallServiceActivationGroupEntry     OBJECT-TYPE
                SYNTAX          BwInCallServiceActivationGroupEntry
                MAX-ACCESS      not-accessible
                STATUS          current
                DESCRIPTION
                        "Each row contains the service counters for the In Call Service Activation service for each group in the system"
                INDEX           {  bwICSAGroupIndex  }
                ::=  { bwInCallServiceActivationGroupTable 1 }

        BwInCallServiceActivationGroupEntry  ::=  SEQUENCE {
                bwICSAGroupIndex Unsigned32,
                bwICSAGroupID   DisplayString,
                bwICSAGroupMonitoringStarted  Counter32,
                bwICSAGroupMonitoringFailure  Counter32,
                bwICSAGroupFlashDigitsDetected  Counter32
                }

        bwICSAGroupIndex                OBJECT-TYPE
                SYNTAX                  Unsigned32
                MAX-ACCESS              read-only
                STATUS                  current
                DESCRIPTION
                                "This column represents the index of the Group in the system."
                ::=  {  bwInCallServiceActivationGroupEntry  1  }

        bwICSAGroupID   OBJECT-TYPE
                SYNTAX                  DisplayString
                MAX-ACCESS              read-only
                STATUS                  current
                DESCRIPTION
                                "This string represents a Group ID."
                ::=  {  bwInCallServiceActivationGroupEntry  2  }

        bwICSAGroupMonitoringStarted            OBJECT-TYPE
                SYNTAX                  Counter32
                MAX-ACCESS              read-write
                STATUS                  current
                DESCRIPTION
                        "This is the number of times a media path is monitored for Flash Tone digits by the In Call Service Activation service.  There is one instance of this counter for each service provider or enterprise defined in the system."
                ::=  {  bwInCallServiceActivationGroupEntry  3  }

        bwICSAGroupMonitoringFailure            OBJECT-TYPE
                SYNTAX                  Counter32
                MAX-ACCESS              read-write
                STATUS                  current
                DESCRIPTION
                        "This is the number of times media path monitoring fails to be started by the In Call Service Activation service.  There is one instance of this counter for each group defined in the system."
                ::=  {  bwInCallServiceActivationGroupEntry  4  }

        bwICSAGroupFlashDigitsDetected          OBJECT-TYPE
                SYNTAX                  Counter32
                MAX-ACCESS              read-write
                STATUS                  current
                DESCRIPTION
                        "This is the number of times the In Call Service Activation service detects the Flash digit string.  There is one instance of this counter for each group defined in the system."
                ::=  {  bwInCallServiceActivationGroupEntry  5  }

-- Service :: Location Control ...........................................
  
  bwLocationControlSPTable  OBJECT-TYPE
                SYNTAX                  SEQUENCE  OF  BwLocationControlSPEntry
                MAX-ACCESS              not-accessible
                STATUS                  current
                DESCRIPTION
                        "Each row contains the service counters for the Location Control service for each service provider in the system"
                ::=  {  locationControl  1  }

  bwLocationControlGroupTable   OBJECT-TYPE
                SYNTAX                  SEQUENCE  OF  BwLocationControlGroupEntry
                MAX-ACCESS              not-accessible
                STATUS                  current
                DESCRIPTION
                        "Each row contains the service counters for the Location Control service for each group in the system"
                ::=  {  locationControl  2  }

  bwLocationControlActivationSuccess  OBJECT-TYPE
                SYNTAX      Counter32
                MAX-ACCESS  read-write
                STATUS      current
                DESCRIPTION
                        "This is the number of times a user activates an alternate or BroadWorks Anywhere location using the Location Control feature."
                ::= {  locationControl  3 }

  bwLocationControlDeactivationSuccess  OBJECT-TYPE
                SYNTAX      Counter32
                MAX-ACCESS  read-write
                STATUS      current
                DESCRIPTION
                        "This is the number of times a user deactivates an alternate or BroadWorks Anywhere location using the Location Control feature."
                ::= {  locationControl  4 }

-- Service :: Location Control :: SP TABLE ...........................................

  bwLocationControlSPEntry  OBJECT-TYPE
                SYNTAX          BwLocationControlSPEntry
                MAX-ACCESS      not-accessible
                STATUS          current
                DESCRIPTION
                        "Each row contains the service counters for the Location Control service for each service provider in the system"
                INDEX           {  bwLocationControlSPIndex  }
                ::=  { bwLocationControlSPTable 1 }

  BwLocationControlSPEntry  ::=  SEQUENCE {
    bwLocationControlSPIndex    Unsigned32,
    bwLocationControlSPID       DisplayString,
    bwLocationControlSPActivationSuccess  Counter32,
    bwLocationControlSPDeactivationSuccess Counter32 }

  bwLocationControlSPIndex   OBJECT-TYPE
                SYNTAX                  Unsigned32
                MAX-ACCESS              read-only
                STATUS                  current
                DESCRIPTION
                                "This column represents the index of the Service Provider in the system."
                ::=  {  bwLocationControlSPEntry  1  }

  bwLocationControlSPID      OBJECT-TYPE
                SYNTAX                  DisplayString
                MAX-ACCESS              read-only
                STATUS                  current
                DESCRIPTION
                                "This string represents a Service Provider ID."
                ::=  {  bwLocationControlSPEntry  2  }

  bwLocationControlSPActivationSuccess       OBJECT-TYPE
                SYNTAX                  Counter32
                MAX-ACCESS              read-write
                STATUS                  current
                DESCRIPTION
                        "This is the number of times a user activates an alternate or BroadWorks Anywhere location using the Location Control feature.  There is one instance of this counter for each service provider defined in the system."
                ::=  {  bwLocationControlSPEntry  3  }

  bwLocationControlSPDeactivationSuccess  OBJECT-TYPE
                SYNTAX                  Counter32
                MAX-ACCESS              read-write
                STATUS                  current
                DESCRIPTION
                        "This is the number of times a user deactivates an alternate or BroadWorks Anywhere location using the Location Control feature.  There is one instance of this counter for each service provider defined in the system."
                ::=  {  bwLocationControlSPEntry  4  }

-- Service :: Location Control :: GROUP TABLE ...........................................

  bwLocationControlGroupEntry  OBJECT-TYPE
                SYNTAX          BwLocationControlGroupEntry
                MAX-ACCESS      not-accessible
                STATUS          current
                DESCRIPTION
                        "Each row contains the service counters for the Location Control service for each group in the system"
                INDEX           {  bwLocationControlGroupIndex  }
                ::=  { bwLocationControlGroupTable 1 }

  BwLocationControlGroupEntry  ::=  SEQUENCE {
    bwLocationControlGroupIndex    Unsigned32,
    bwLocationControlGroupID       DisplayString,
    bwLocationControlGroupActivationSuccess  Counter32,
    bwLocationControlGroupDeactivationSuccess Counter32 }

  bwLocationControlGroupIndex   OBJECT-TYPE
                SYNTAX                  Unsigned32
                MAX-ACCESS              read-only
                STATUS                  current
                DESCRIPTION
                                "This column represents the index of the Group in the system."
                ::=  {  bwLocationControlGroupEntry  1  }

  bwLocationControlGroupID      OBJECT-TYPE
                SYNTAX                  DisplayString
                MAX-ACCESS              read-only
                STATUS                  current
                DESCRIPTION
                                "This string represents a Group ID."
                ::=  {  bwLocationControlGroupEntry  2  }

  bwLocationControlGroupActivationSuccess   OBJECT-TYPE
                SYNTAX                  Counter32
                MAX-ACCESS              read-write
                STATUS                  current
                DESCRIPTION
                        "This is the number of times a user activates an alternate or BroadWorks Anywhere location using the Location Control feature.  There is one instance of this counter for each group defined in the system."
                ::=  {  bwLocationControlGroupEntry  3  }

  bwLocationControlGroupDeactivationSuccess  OBJECT-TYPE
                SYNTAX                  Counter32
                MAX-ACCESS              read-write
                STATUS                  current
                DESCRIPTION
                        "This is the number of times a user deactivates an alternate or BroadWorks Anywhere location using the Location Control feature.  There is one instance of this counter for each group defined in the system."
                ::=  {  bwLocationControlGroupEntry  4  }

-- Service :: Call Retrieve ...........................................

  bwCallRetrieveSPTable  OBJECT-TYPE
                SYNTAX                  SEQUENCE  OF  BwCallRetrieveSPEntry
                MAX-ACCESS              not-accessible
                STATUS                  current
                DESCRIPTION
                        "Each row contains the service counters for the Call Retrieve service for each service provider in the system"
                ::=  {  callRetrieve  1  }

  bwCallRetrieveGroupTable   OBJECT-TYPE
                SYNTAX                  SEQUENCE  OF  BwCallRetrieveGroupEntry
                MAX-ACCESS              not-accessible
                STATUS                  current
                DESCRIPTION
                        "Each row contains the service counters for the Call Retrieve service for each group in the system"
                ::=  {  callRetrieve  2  }

  bwCallRetrieveSuccess  OBJECT-TYPE
                SYNTAX      Counter32
                MAX-ACCESS  read-write
                STATUS      current
                DESCRIPTION
                        "This is the number of times a user successfully retrieves a call using the Call Retrieve feature."
                ::= {  callRetrieve  3 }

-- Service :: Call Retrieve :: SP TABLE ...........................................

  bwCallRetrieveSPEntry  OBJECT-TYPE
                SYNTAX          BwCallRetrieveSPEntry
                MAX-ACCESS      not-accessible
                STATUS          current
                DESCRIPTION
                        "Each row contains the service counters for the Call Retrieve service for each service provider in the system"
                INDEX           {  bwCallRetrieveSPIndex  }
                ::=  { bwCallRetrieveSPTable 1 }

  BwCallRetrieveSPEntry  ::=  SEQUENCE {
    bwCallRetrieveSPIndex    Unsigned32,
    bwCallRetrieveSPID       DisplayString,
    bwCallRetrieveSPSuccess  Counter32 }

  bwCallRetrieveSPIndex   OBJECT-TYPE
                SYNTAX                  Unsigned32
                MAX-ACCESS              read-only
                STATUS                  current
                DESCRIPTION
                                "This column represents the index of the Service Provider in the system."
                ::=  {  bwCallRetrieveSPEntry  1  }

  bwCallRetrieveSPID      OBJECT-TYPE
                SYNTAX                  DisplayString
                MAX-ACCESS              read-only
                STATUS                  current
                DESCRIPTION
                                "This string represents a Service Provider ID."
                ::=  {  bwCallRetrieveSPEntry  2  }

  bwCallRetrieveSPSuccess       OBJECT-TYPE
                SYNTAX                  Counter32
                MAX-ACCESS              read-write
                STATUS                  current
                DESCRIPTION
                        "The number of times a user successfully retrieves a call using the Call Retrieve feature.  There is one instance of this counter for each service provider defined in the system."
                ::=  {  bwCallRetrieveSPEntry  3  }

-- Service :: Call Retrieve :: GROUP TABLE ...........................................

  bwCallRetrieveGroupEntry  OBJECT-TYPE
                SYNTAX          BwCallRetrieveGroupEntry
                MAX-ACCESS      not-accessible
                STATUS          current
                DESCRIPTION
                        "Each row contains the service counters for the Call Retrieve service for each service provider in the system"
                INDEX           {  bwCallRetrieveGroupIndex  }
                ::=  { bwCallRetrieveGroupTable 1 }

  BwCallRetrieveGroupEntry  ::=  SEQUENCE {
    bwCallRetrieveGroupIndex    Unsigned32,
    bwCallRetrieveGroupID       DisplayString,
    bwCallRetrieveGroupSuccess  Counter32 }

  bwCallRetrieveGroupIndex   OBJECT-TYPE
                SYNTAX                  Unsigned32
                MAX-ACCESS              read-only
                STATUS                  current
                DESCRIPTION
                                "This column represents the index of the Group in the system."
                ::=  {  bwCallRetrieveGroupEntry  1  }

  bwCallRetrieveGroupID      OBJECT-TYPE
                SYNTAX                  DisplayString
                MAX-ACCESS              read-only
                STATUS                  current
                DESCRIPTION
                                "This string represents a Group ID."
                ::=  {  bwCallRetrieveGroupEntry  2  }

  bwCallRetrieveGroupSuccess   OBJECT-TYPE
                SYNTAX                  Counter32
                MAX-ACCESS              read-write
                STATUS                  current
                DESCRIPTION
                        "The number of times a user successfully retrieves a call using the Call Retrieve feature.  There is one instance of this counter for each group defined in the system."
                ::=  {  bwCallRetrieveGroupEntry  3  }

-- Service :: BroadWorks Anywhere ...........................................

  bwBroadWorksAnywhereSPTable  OBJECT-TYPE
                SYNTAX                  SEQUENCE  OF  BwBroadWorksAnywhereSPEntry
                MAX-ACCESS              not-accessible
                STATUS                  current
                DESCRIPTION
                        "Each row contains the service counters for the BroadWorks Anywhere service for each service provider in the system"
                ::=  {  broadworksAnywhere  1  }

  bwBroadWorksAnywhereGroupTable   OBJECT-TYPE
                SYNTAX                  SEQUENCE  OF  BwBroadWorksAnywhereGroupEntry
                MAX-ACCESS              not-accessible
                STATUS                  current
                DESCRIPTION
                        "Each row contains the service counters for the BroadWorks Anywhere service for each group in the system"
                ::=  {  broadworksAnywhere  2  }

  bwBACallOriginations  OBJECT-TYPE
                SYNTAX      Counter32
                MAX-ACCESS  read-write
                STATUS      current
                DESCRIPTION
                        "This is the number of times a user originates a call through the BroadWorks Anywhere Portal."
                ::= {  broadworksAnywhere  3 }

  bwBACallTerminations  OBJECT-TYPE
                SYNTAX      Counter32
                MAX-ACCESS  read-write
                STATUS      current
                DESCRIPTION
                        "This is the number of times a call leg is extended to a BroadWorks Anywhere location. "
                ::= {  broadworksAnywhere  4 }

-- Service :: BroadWorks Anywhere :: SP TABLE ...........................................

  bwBroadWorksAnywhereSPEntry  OBJECT-TYPE
                SYNTAX          BwBroadWorksAnywhereSPEntry
                MAX-ACCESS      not-accessible
                STATUS          current
                DESCRIPTION
                        "Each row contains the service counters for the BroadWorks Anywhere service for each service provider in the system"
                INDEX           {  bwBroadWorksAnywhereSPIndex  }
                ::=  { bwBroadWorksAnywhereSPTable 1 }

  BwBroadWorksAnywhereSPEntry  ::=  SEQUENCE {
    bwBroadWorksAnywhereSPIndex    Unsigned32,
    bwBroadWorksAnywhereSPID       DisplayString,
    bwBASPCallOriginations         Counter32,
    bwBASPCallTerminations         Counter32 }

  bwBroadWorksAnywhereSPIndex   OBJECT-TYPE
                SYNTAX                  Unsigned32
                MAX-ACCESS              read-only
                STATUS                  current
                DESCRIPTION
                                "This column represents the index of the Service Provider in the system."
                ::=  {  bwBroadWorksAnywhereSPEntry  1  }

  bwBroadWorksAnywhereSPID      OBJECT-TYPE
                SYNTAX                  DisplayString
                MAX-ACCESS              read-only
                STATUS                  current
                DESCRIPTION
                                "This string represents a Service Provider ID."
                ::=  {  bwBroadWorksAnywhereSPEntry  2  }

  bwBASPCallOriginations       OBJECT-TYPE
                SYNTAX                  Counter32
                MAX-ACCESS              read-write
                STATUS                  current
                DESCRIPTION
                        "This is the number of times a user originates a call through the BroadWorks Anywhere Portal. There is one instance of this counter for each service provider or enterprise defined in the system."
                ::=  {  bwBroadWorksAnywhereSPEntry  3  }

  bwBASPCallTerminations       OBJECT-TYPE
                SYNTAX                  Counter32
                MAX-ACCESS              read-write
                STATUS                  current
                DESCRIPTION
                        "This is the number of times a call leg is extended to a BroadWorks Anywhere location. There is one instance of this counter for each service provider or enterprise defined in the system."
                ::=  {  bwBroadWorksAnywhereSPEntry  4  }

-- Service :: BroadWorks Anywhere :: GROUP TABLE ...........................................

  bwBroadWorksAnywhereGroupEntry  OBJECT-TYPE
                SYNTAX          BwBroadWorksAnywhereGroupEntry
                MAX-ACCESS      not-accessible
                STATUS          current
                DESCRIPTION
                        "Each row contains the service counters for the BroadWorks Anywhere service for each service provider in the system"
                INDEX           {  bwBroadWorksAnywhereGroupIndex  }
                ::=  { bwBroadWorksAnywhereGroupTable 1 }

  BwBroadWorksAnywhereGroupEntry  ::=  SEQUENCE {
    bwBroadWorksAnywhereGroupIndex    Unsigned32,
    bwBroadWorksAnywhereGroupID       DisplayString,
    bwBAGroupCallOriginations         Counter32,
    bwBAGroupCallTerminations         Counter32 }

  bwBroadWorksAnywhereGroupIndex   OBJECT-TYPE
                SYNTAX                  Unsigned32
                MAX-ACCESS              read-only
                STATUS                  current
                DESCRIPTION
                                "This column represents the index of the Group in the system."
                ::=  {  bwBroadWorksAnywhereGroupEntry  1  }

  bwBroadWorksAnywhereGroupID      OBJECT-TYPE
                SYNTAX                  DisplayString
                MAX-ACCESS              read-only
                STATUS                  current
                DESCRIPTION
                                "This string represents a Group ID."
                ::=  {  bwBroadWorksAnywhereGroupEntry  2  }

  bwBAGroupCallOriginations   OBJECT-TYPE
                SYNTAX                  Counter32
                MAX-ACCESS              read-write
                STATUS                  current
                DESCRIPTION
                        "This is the number of times a user originates a call through the BroadWorks Anywhere Portal. There is one instance of this counter for each group defined in the system."
                ::=  {  bwBroadWorksAnywhereGroupEntry  3  }

  bwBAGroupCallTerminations   OBJECT-TYPE
                SYNTAX                  Counter32
                MAX-ACCESS              read-write
                STATUS                  current
                DESCRIPTION
                        "This is the number of times a call leg is extended to a BroadWorks Anywhere location. There is one instance of this counter for each group defined in the system."
                ::=  {  bwBroadWorksAnywhereGroupEntry  4  }

-- Protocol :: MSS  ...........................................

  bwNSqueryRequestsTransmitted  OBJECT-TYPE
    SYNTAX      Counter32
    MAX-ACCESS    read-write
    STATUS      current
                DESCRIPTION
                                "incremented each time a Media Server selection query transmission is attempted toward a Network Server"
                ::=  {  mssStats  1  }

  bwNSqueryRequestsRetransmitted  OBJECT-TYPE
    SYNTAX      Counter32
    MAX-ACCESS    read-write
    STATUS      obsolete
                DESCRIPTION
                                "incremented each time a Media Server selection query transmission is retransmitted toward a Network Server

This object is obsolete. Retransmission control through SIP, used to be controlled over MSS protocol."
                ::=  {  mssStats  2  }

  bwNSqueryCommFailures OBJECT-TYPE
    SYNTAX      Counter32
    MAX-ACCESS    read-write
    STATUS      current
                DESCRIPTION
                                "This counter is incremented when Media Server selection query has been transmitted toward all available Network Servers and no response has been received from any Network Server."
                ::=  {  mssStats  3  }

-- vvvvvvvvvvvvvvvvvv THESE COUNTERS ARE DEPRECATED vvvvvvvvvvvvvvvvvvvvv
--  nrsNbRequests OBJECT-TYPE
--    SYNTAX      Counter32
--    MAX-ACCESS    read-write
--    STATUS      current
--    DESCRIPTION
--        "This counter is incremented when an NRS request is received"
--    ::=  {  nrsStats  1  }
--
--  nrsNbRequestsResent OBJECT-TYPE
--    SYNTAX      Counter32
--    MAX-ACCESS    read-write
--    STATUS      current
--    DESCRIPTION
--        "This counter is incremented when an NRS request is resent"
--    ::=  {  nrsStats  2  }
--
--  nrsNbRequestsFailures OBJECT-TYPE
--    SYNTAX      Counter32
--    MAX-ACCESS    read-write
--    STATUS      current
--    DESCRIPTION
--        "This counter is incremented when an NRS request can't be decoded"
--    ::=  {  nrsStats  3  }
--
--  nrsInQueueSize  OBJECT-TYPE
--    SYNTAX      Gauge32
--    MAX-ACCESS    read-only
--    STATUS      current
--    DESCRIPTION
--        "The size of the NRS request in the incoming queue"
--    ::=  {  nrsStats  4  }
--
--  nrsOutQueueSize OBJECT-TYPE
--    SYNTAX      Gauge32
--    MAX-ACCESS    read-only
--    STATUS      current
--    DESCRIPTION
--        "The size of the NRS request in the outcoming queue"
--    ::=  {  nrsStats  5  }
-- ^^^^^^^^^^^^^^^^^^^^^^^ THESE COUNTERS ARE DEPRECATED ^^^^^^^^^^^^^^^^^^^^^^^^^

-- Protocol :: NRS  ...........................................

  bwNbInvalidMessagesReceived OBJECT-TYPE
    SYNTAX      Counter32
    MAX-ACCESS    read-write
    STATUS      current
                DESCRIPTION
                                "This counter is incremented when an invalid NRS message is received (either the header was valid but the body was not, or the message was pure junk)"
                ::=  {  nrsStats  6  }

  bwNbRequestsReceived  OBJECT-TYPE
    SYNTAX      Counter32
    MAX-ACCESS    read-write
    STATUS      current
                DESCRIPTION
                                "This counter is incremented when a NRS request is received"
                ::=  {  nrsStats  7  }

  bwNbResponsesReceived OBJECT-TYPE
    SYNTAX      Counter32
    MAX-ACCESS    read-write
    STATUS      current
                DESCRIPTION
                                "This counter is incremented when a NRS response is received"
                ::=  {  nrsStats  8  }

  bwNbErrorsReceived  OBJECT-TYPE
    SYNTAX      Counter32
    MAX-ACCESS    read-write
    STATUS      current
                DESCRIPTION
                                "This counter is incremented when a NRS error is received"
                ::=  {  nrsStats  9  }

  bwNbRequestsSent  OBJECT-TYPE
    SYNTAX      Counter32
    MAX-ACCESS    read-write
    STATUS      current
                DESCRIPTION
                                "This counter is incremented when a NRS request is sent"
                ::=  {  nrsStats  10  }

  bwNbResponsesSent OBJECT-TYPE
    SYNTAX      Counter32
    MAX-ACCESS    read-write
    STATUS      current
                DESCRIPTION
                                "This counter is incremented when a NRS response is sent"
                ::=  {  nrsStats  11  }

  bwNbErrorsSent  OBJECT-TYPE
    SYNTAX      Counter32
    MAX-ACCESS    read-write
    STATUS      current
                DESCRIPTION
                                "This counter is incremented when a NRS error is sent"
                ::=  {  nrsStats  12  }

  bwNbRequestsResent  OBJECT-TYPE
    SYNTAX      Counter32
    MAX-ACCESS    read-write
    STATUS      current
                DESCRIPTION
                                "This counter is incremented when a NRS request is re-sent"
                ::=  {  nrsStats  13  }

  bwNbResponsesResent OBJECT-TYPE
    SYNTAX      Counter32
    MAX-ACCESS    read-write
    STATUS      current
                DESCRIPTION
                                "This counter is incremented when a NRS response is re-sent"
                ::=  {  nrsStats  14  }

  bwNbRequestsUnanswered  OBJECT-TYPE
    SYNTAX      Counter32
    MAX-ACCESS    read-write
    STATUS      current
                DESCRIPTION
                                "This counter is incremented when a NRS request remains unanswered after a series of retries"
                ::=  {  nrsStats  15  }


  bwNRSStatsTable OBJECT-TYPE
    SYNTAX    SEQUENCE  OF  BwNRSStatsEntry
    MAX-ACCESS  not-accessible
    STATUS    current
                DESCRIPTION
                        "This table contains the counters for all NRS protocols"
                ::=  { nrsStats  16 }

  bwNRSStatsEntry OBJECT-TYPE
    SYNTAX    BwNRSStatsEntry
    MAX-ACCESS  not-accessible
    STATUS    current
                DESCRIPTION
                        "This row contains information on a particular NRS protocol"
    INDEX   {  bwNRSStatsTableIndex  }
                ::=  { bwNRSStatsTable 1 }

        BwNRSStatsEntry  ::=  SEQUENCE {
                bwNRSStatsTableIndex  Unsigned32,
                bwNRSStatsTableProtocolName  DisplayString,
                bwNRSStatsTableNbRequestsReceived  Counter32,
                bwNRSStatsTableNbResponsesReceived  Counter32,
                bwNRSStatsTableNbErrorsReceived  Counter32,
                bwNRSStatsTableNbRequestsSent  Counter32,
                bwNRSStatsTableNbResponsesSent  Counter32,
                bwNRSStatsTableNbErrorsSent  Counter32,
                bwNRSStatsTableNbRequestsResent  Counter32,
                bwNRSStatsTableNbResponsesResent  Counter32,
                bwNRSStatsTableNbRequestsUnanswered  Counter32
                }


  bwNRSStatsTableIndex  OBJECT-TYPE
    SYNTAX      Unsigned32
    MAX-ACCESS    not-accessible
    STATUS      current
                DESCRIPTION
                                "This integer represents a NRS protocol status code.  The rest of the information in this row is related to this value."
                ::=  {  bwNRSStatsEntry  1  }


  bwNRSStatsTableProtocolName OBJECT-TYPE
    SYNTAX      DisplayString
    MAX-ACCESS    read-only
    STATUS      current
                DESCRIPTION
                                "This string represents the NRS protocol name"
                ::=  {  bwNRSStatsEntry  2  }

  bwNRSStatsTableNbRequestsReceived OBJECT-TYPE
    SYNTAX      Counter32
    MAX-ACCESS    read-write
    STATUS      current
                DESCRIPTION
                                "This counter is incremented when a request is received"
                ::=  {  bwNRSStatsEntry  3  }

  bwNRSStatsTableNbResponsesReceived  OBJECT-TYPE
    SYNTAX      Counter32
    MAX-ACCESS    read-write
    STATUS      current
                DESCRIPTION
                                "This counter is incremented when a response is received"
                ::=  {  bwNRSStatsEntry  4  }

  bwNRSStatsTableNbErrorsReceived OBJECT-TYPE
    SYNTAX      Counter32
    MAX-ACCESS    read-write
    STATUS      current
                DESCRIPTION
                                "This counter is incremented when an error is received"
                ::=  {  bwNRSStatsEntry  5  }

  bwNRSStatsTableNbRequestsSent OBJECT-TYPE
    SYNTAX      Counter32
    MAX-ACCESS    read-write
    STATUS      current
                DESCRIPTION
                                "This counter is incremented when a request is sent"
                ::=  {  bwNRSStatsEntry  6  }

  bwNRSStatsTableNbResponsesSent  OBJECT-TYPE
    SYNTAX      Counter32
    MAX-ACCESS    read-write
    STATUS      current
                DESCRIPTION
                                "This counter is incremented when a response is sent"
                ::=  {  bwNRSStatsEntry  7  }

  bwNRSStatsTableNbErrorsSent OBJECT-TYPE
    SYNTAX      Counter32
    MAX-ACCESS    read-write
    STATUS      current
                DESCRIPTION
                                "This counter is incremented when an error is sent"
                ::=  {  bwNRSStatsEntry  8  }

  bwNRSStatsTableNbRequestsResent OBJECT-TYPE
    SYNTAX      Counter32
    MAX-ACCESS    read-write
    STATUS      current
                DESCRIPTION
                                "This counter is incremented when a request is re-sent"
                ::=  {  bwNRSStatsEntry  9  }

  bwNRSStatsTableNbResponsesResent  OBJECT-TYPE
    SYNTAX      Counter32
    MAX-ACCESS    read-write
    STATUS      current
                DESCRIPTION
                                "This counter is incremented when a response is re-sent"
                ::=  {  bwNRSStatsEntry  10  }

  bwNRSStatsTableNbRequestsUnanswered OBJECT-TYPE
    SYNTAX      Counter32
    MAX-ACCESS    read-write
    STATUS      current
                DESCRIPTION
                                "This counter is incremented when a request remains unanswered after a series of retries"
                ::=  {  bwNRSStatsEntry  11  }



-- Persistence :: TimesTen  ...........................................

  timesTen  OBJECT IDENTIFIER
                ::=  {  databaseStats  1  }

  perNbOpenedTransactions OBJECT-TYPE
    SYNTAX      Gauge32
    MAX-ACCESS    read-only
    STATUS      current
                DESCRIPTION
                                "Number of opened transaction with the database"
                ::=  {  databaseStats  2  }

  perNbCommittedTransactions  OBJECT-TYPE
    SYNTAX      Counter32
    MAX-ACCESS    read-write
    STATUS      current
                DESCRIPTION
                                "Total number of committed transactions to the database since the last restart"
                ::=  {  databaseStats  3  }

  perNbFailedTransactions OBJECT-TYPE
    SYNTAX      Counter32
    MAX-ACCESS    read-write
    STATUS      current
                DESCRIPTION
                                "Number of failed transactions with the database"
                ::=  {  databaseStats  4  }

  perNbCriticalErrors OBJECT-TYPE
    SYNTAX      Counter32
    MAX-ACCESS    read-write
    STATUS      current
                DESCRIPTION
                                "Total number of critical errors encountered during processing with the database"
                ::=  {  databaseStats  5  }

  ttNbConnectionsCreated  OBJECT-TYPE
    SYNTAX      Counter32
    MAX-ACCESS    read-write
    STATUS      current
                DESCRIPTION
                                "Number of total transaction created to the database"
                ::=  {  timesTen  1  }

  ttConnectionPoolSize  OBJECT-TYPE
    SYNTAX      Gauge32
    MAX-ACCESS    read-only
    STATUS      current
                DESCRIPTION
                                "Current size of the database connection pool"
                ::=  {  timesTen  2  }

  ttNbBackdoorUpdates OBJECT-TYPE
    SYNTAX      Counter32
    MAX-ACCESS    read-write
    STATUS      obsolete
                DESCRIPTION
                                "Total number of backdoor notification"
                ::=  {  timesTen  3  }

  ttNbFailedCheckpoints OBJECT-TYPE
    SYNTAX      Counter32
    MAX-ACCESS    read-write
    STATUS      obsolete
                DESCRIPTION
                                "Total number of fail check pointing to the dabatase"
                ::=  {  timesTen  4  }

  -- ::= { timesTen 5 } is used by remoteXla (look a couple of lines down)

  bwXSAvgUpdateTime OBJECT-TYPE
  SYNTAX      Gauge32
    MAX-ACCESS    read-only
    STATUS      current
                DESCRIPTION
                                "Average DB update time in milliseconds"
                ::=  {  timesTen  6  }

  bwXSAvgRowsUpdated  OBJECT-TYPE
  SYNTAX      Gauge32
    MAX-ACCESS    read-only
    STATUS      current
                DESCRIPTION
                                "Average number of rows affected in DB updates"
                ::=  {  timesTen  7  }

  bwXSAvgQueryTime OBJECT-TYPE
  SYNTAX      Gauge32
    MAX-ACCESS    read-only
    STATUS      current
                DESCRIPTION
                                "Average DB query time in milliseconds"
                ::=  {  timesTen  8  }

  bwXSAvgRowsQueried OBJECT-TYPE
  SYNTAX      Gauge32
    MAX-ACCESS    read-only
    STATUS      current
                DESCRIPTION
                                "Average number of rows processed in DB queries"
                ::=  {  timesTen  9 }

  bwXSUpdateCount OBJECT-TYPE
    SYNTAX      Counter32
    MAX-ACCESS    read-write
    STATUS      current
                DESCRIPTION
                                "Number of DB updates performed since the application started"
                ::=  {  timesTen  10  }

  bwXSQueryCount OBJECT-TYPE
    SYNTAX      Counter32
    MAX-ACCESS    read-write
    STATUS      current
                DESCRIPTION
                                "Number of DB queries performed since the application started"
                ::=  {  timesTen  11  }

-- XS TimesTen High Water Mark table  ...........................................

  bwXSTTHWMTable  OBJECT-TYPE
    SYNTAX    SEQUENCE  OF  BwXSTTHWMEntry
    MAX-ACCESS  not-accessible
    STATUS    current
                DESCRIPTION
                        "This table contains counters for the XS TimesTen high water marks."
                ::=  { timesTen  12 }

  bwXSTTHWMEntry  OBJECT-TYPE
    SYNTAX    BwXSTTHWMEntry
    MAX-ACCESS  not-accessible
    STATUS    current
                DESCRIPTION
                        "Definition of the entries for bwXSTTHWMTable."
    INDEX   {  bwXSTTHWMIndex  }
                ::=  { bwXSTTHWMTable 1 }

        BwXSTTHWMEntry  ::=  SEQUENCE {
    bwXSTTHWMIndex Unsigned32,
    bwXSTTHWMName DisplayString,
    bwXSTTHWMValue Gauge32,
    bwXSTTHWMTimestamp DisplayString,
    bwXSTTHWMStackTrace DisplayString
  }

  bwXSTTHWMIndex  OBJECT-TYPE
    SYNTAX      Unsigned32
    MAX-ACCESS    read-only
    STATUS      current
                DESCRIPTION
                                "This integer represents an index in table bwXSTTHWMTable. This is the index to a specific high water mark."
                ::=  {  bwXSTTHWMEntry  1  }

  bwXSTTHWMName OBJECT-TYPE
    SYNTAX      DisplayString
    MAX-ACCESS    read-only
    STATUS      current
                DESCRIPTION
                                "The name of an XS TimesTen high water mark."
                ::=  {  bwXSTTHWMEntry  2  }

  bwXSTTHWMValue  OBJECT-TYPE
    SYNTAX      Gauge32
    MAX-ACCESS    read-write
    STATUS      current
                DESCRIPTION
                                "The value of an XS TimesTen high water mark."
                ::=  {  bwXSTTHWMEntry  3  }

  bwXSTTHWMTimestamp  OBJECT-TYPE
    SYNTAX      DisplayString
    MAX-ACCESS    read-write
    STATUS      current
                DESCRIPTION
                                "The timestamp of an XS TimesTen high water mark."
                ::=  {  bwXSTTHWMEntry  4  }

  bwXSTTHWMStackTrace OBJECT-TYPE
    SYNTAX      DisplayString
    MAX-ACCESS    read-write
    STATUS      current
                DESCRIPTION
                                "The stack trace of an XS TimesTen high water mark."
                ::=  {  bwXSTTHWMEntry  5  }

-- RemoteXla

  xsRemoteXla OBJECT IDENTIFIER
                ::=  {  timesTen  5  }

  xsRemoteXlaNbTimesConnected OBJECT-TYPE
    SYNTAX      Counter32
    MAX-ACCESS    read-write
    STATUS      current
                DESCRIPTION
                                "Number of times a connection was made to the RemoteXla server"
                ::=  {  xsRemoteXla  1  }

  xsRemoteXlaNbTimesDisconnected  OBJECT-TYPE
    SYNTAX      Counter32
    MAX-ACCESS    read-write
    STATUS      current
                DESCRIPTION
                                "Number of times the process was disconnected from the RemoteXla server"
                ::=  {  xsRemoteXla  2  }

  xsRemoteXlaUpdatesProcessed OBJECT-TYPE
    SYNTAX      Counter32
    MAX-ACCESS    read-write
    STATUS      current
                DESCRIPTION
                                "Number of XLA updates processed"
                ::=  {  xsRemoteXla  3  }

  xsRemoteXlaUpdatesPending OBJECT-TYPE
    SYNTAX      Gauge32
    MAX-ACCESS    read-write
    STATUS      current
                DESCRIPTION
                                "Number of XLA updates pending to be processed"
                ::=  {  xsRemoteXla  4  }


-- Protocol :: Protocol Monitor  ...........................................

  bwPMTNumMonitorsCreated OBJECT-TYPE
    SYNTAX      Counter32
    MAX-ACCESS    read-write
    STATUS      current
                DESCRIPTION
                                "This counter is incremented when a monitor is created"
                ::=  {  pmtStats  1  }

  bwPMTNumMonitorsOpen  OBJECT-TYPE
    SYNTAX      Gauge32
    MAX-ACCESS    read-only
    STATUS      current
                DESCRIPTION
                                "Number of open monitors in the system"
                ::=  {  pmtStats  2  }

  bwPMTNumLoggerCreated OBJECT-TYPE
    SYNTAX      Counter32
    MAX-ACCESS    read-write
    STATUS      current
                DESCRIPTION
                                "This counter is incremented when a logger registers"
                ::=  {  pmtStats  3  }

  bwPMTNumLoggerOpen  OBJECT-TYPE
    SYNTAX      Gauge32
    MAX-ACCESS    read-only
    STATUS      current
                DESCRIPTION
                                "The number of loggers registered in the system"
                ::=  {  pmtStats  4  }


-- system statistics ...........................................

  systemStats OBJECT IDENTIFIER
                ::=  {  systemModule  1  }

  bwSystemName    OBJECT-TYPE
    SYNTAX      DisplayString
    MAX-ACCESS    read-only
    STATUS      current
                DESCRIPTION
                                "Gives the BroadWorks system name"
                ::=  {  systemStats  1  }

  bwNumberOfUsers   OBJECT-TYPE
    SYNTAX      Gauge32
    MAX-ACCESS    read-only
    STATUS      current
                DESCRIPTION
                                "Gives the total of users configured on the BroadWorks system"
                ::=  {  systemStats  2  }

  bwNumberOfGroups  OBJECT-TYPE
    SYNTAX      Gauge32
    MAX-ACCESS    read-only
    STATUS      current
                DESCRIPTION
                                "Gives the total of groups configured on the BroadWorks system"
                ::=  {  systemStats  3  }

  bwNumberOfServProv  OBJECT-TYPE
    SYNTAX      Gauge32
    MAX-ACCESS    read-only
    STATUS      current
                DESCRIPTION
                                "Gives the total of groups configured on the BroadWorks system"
                ::=  {  systemStats  4  }

  bwNumberOfDNDefined OBJECT-TYPE
    SYNTAX      Gauge32
    MAX-ACCESS    read-only
    STATUS      current
                DESCRIPTION
                                "Gives the total of phone numbers configured on the BroadWorks system"
                ::=  {  systemStats  5  }

  bwNumberOfDNAssigned  OBJECT-TYPE
    SYNTAX      Gauge32
    MAX-ACCESS    read-only
    STATUS      current
                DESCRIPTION
                                "Gives the total of phone numbers assigned to service provivers on the BroadWorks system"
                ::=  {  systemStats  6  }

  bwNumberOfDeviceType  OBJECT-TYPE
    SYNTAX      Gauge32
    MAX-ACCESS    read-only
    STATUS      current
                DESCRIPTION
                                "Gives the total of device types defined on the BroadWorks system"
                ::=  {  systemStats  7  }

  bwNumberOfServiceType OBJECT-TYPE
    SYNTAX      Gauge32
    MAX-ACCESS    read-only
    STATUS      current
                DESCRIPTION
                                "Gives the total of service types on the BroadWorks system"
                ::=  {  systemStats  8  }

  bwDeviceTypeSystemTable OBJECT-TYPE
    SYNTAX    SEQUENCE  OF  BwDeviceTypeSystemEntry
    MAX-ACCESS  not-accessible
    STATUS    current
                DESCRIPTION
                        "This table contains statistics for each device types supported on the BroadWorks system"
                ::=  { systemStats  9 }

  bwServiceTypeSystemTable  OBJECT-TYPE
    SYNTAX    SEQUENCE  OF  BwServiceTypeSystemEntry
    MAX-ACCESS  not-accessible
    STATUS    current
                DESCRIPTION
                        "This table contains statistics for each service types supported on the BroadWorks system"
                ::=  { systemStats  10 }

  bwSystemSPTable   OBJECT-TYPE
    SYNTAX    SEQUENCE  OF  BwSystemSPEntry
    MAX-ACCESS  not-accessible
    STATUS    current
                DESCRIPTION
                        "This table contains system level statistics for each groups on the BroadWorks system"
                ::=  { systemStats  11 }

  bwSystemGroupTable    OBJECT-TYPE
    SYNTAX    SEQUENCE  OF  BwSystemGroupEntry
    MAX-ACCESS  not-accessible
    STATUS    current
                DESCRIPTION
                        "This table contains system level statistics for each groups on the BroadWorks system"
                ::=  { systemStats  12 }

-- System system tables defintions ...........................................

  bwDeviceTypeSystemEntry OBJECT-TYPE
    SYNTAX    BwDeviceTypeSystemEntry
    MAX-ACCESS  not-accessible
    STATUS    current
                DESCRIPTION
                        "This row contains the statistics for a given device type in the system"
    INDEX   {  bwDeviceTypeSystemIndex  }
                ::=  { bwDeviceTypeSystemTable 1 }

        BwDeviceTypeSystemEntry  ::=  SEQUENCE {
                bwDeviceTypeSystemIndex  Unsigned32,
                bwDeviceTypeSystemID  DisplayString,
                bwNumberOfDeviceTypeSystem  Gauge32
                }


  bwDeviceTypeSystemIndex OBJECT-TYPE
    SYNTAX      Unsigned32
    MAX-ACCESS    read-only
    STATUS      current
                DESCRIPTION
                                "This integer represents a device type index in the system"
                ::=  {  bwDeviceTypeSystemEntry  1  }


  bwDeviceTypeSystemID  OBJECT-TYPE
    SYNTAX      DisplayString
    MAX-ACCESS    read-only
    STATUS      current
                DESCRIPTION
                                "This string represents a device type ID"
                ::=  {  bwDeviceTypeSystemEntry  2  }

  bwNumberOfDeviceTypeSystem  OBJECT-TYPE
    SYNTAX      Gauge32
    MAX-ACCESS    read-only
    STATUS      current
                DESCRIPTION
                                "Gives the total of number of a device type defined in the system"
                ::=  {  bwDeviceTypeSystemEntry  3  }

-- Per service system statistics ...........................................

  bwServiceTypeSystemEntry  OBJECT-TYPE
    SYNTAX    BwServiceTypeSystemEntry
    MAX-ACCESS  not-accessible
    STATUS    current
                DESCRIPTION
                        "This row contains the statistics for a given service type in the system"
    INDEX   {  bwServiceTypeSystemIndex  }
                ::=  { bwServiceTypeSystemTable 1 }

        BwServiceTypeSystemEntry  ::=  SEQUENCE {
                bwServiceTypeSystemIndex  Unsigned32,
                bwServiceTypeSystemID  DisplayString,
                bwNumberOfServiceTypeAssignedSystem Gauge32
                }


  bwServiceTypeSystemIndex  OBJECT-TYPE
    SYNTAX      Unsigned32
    MAX-ACCESS    read-only
    STATUS      current
                DESCRIPTION
                                "This integer represents a service type index in the system"
                ::=  {  bwServiceTypeSystemEntry  1  }

  bwServiceTypeSystemID OBJECT-TYPE
    SYNTAX      DisplayString
    MAX-ACCESS    read-only
    STATUS      current
                DESCRIPTION
                                "This string represents a service type ID"
                ::=  {  bwServiceTypeSystemEntry  2  }

  bwNumberOfServiceTypeAssignedSystem OBJECT-TYPE
    SYNTAX      Gauge32
    MAX-ACCESS    read-only
    STATUS      current
                DESCRIPTION
                                "Gives the total of number of a service type assigned in the system"
                ::=  {  bwServiceTypeSystemEntry  3  }

-- Service provider system statistics ...........................................

  bwSystemSPEntry   OBJECT-TYPE
    SYNTAX      BwSystemSPEntry
    MAX-ACCESS    not-accessible
    STATUS      current
                DESCRIPTION
                                "This row contains the system statistics for a given service provider in the system"
    INDEX   {  bwSystemSPIndex  }
                ::=  { bwSystemSPTable 1 }

        BwSystemSPEntry  ::=  SEQUENCE {
                bwSystemSPIndex  Unsigned32,
                bwSystemSPID  DisplayString,
                bwSystemSPName  DisplayString,
                bwNumberOfSPUsers  Gauge32,
                bwNumberOfSPGroups  Gauge32,
                bwNumberOfSPDNDefined  Gauge32,
                bwNumberOfSPDNAssigned  Gauge32,
                bwNumberOfSPDeviceType  Gauge32
                }


  bwSystemSPIndex OBJECT-TYPE
    SYNTAX      Unsigned32
    MAX-ACCESS    read-only
    STATUS      current
                DESCRIPTION
                                "This integer represents a service provider index in the system"
                ::=  {  bwSystemSPEntry  1  }


  bwSystemSPID  OBJECT-TYPE
    SYNTAX      DisplayString
    MAX-ACCESS    read-only
    STATUS      current
                DESCRIPTION
                                "This string represents a service provider ID"
                ::=  {  bwSystemSPEntry  2  }


  bwSystemSPName    OBJECT-TYPE
    SYNTAX      DisplayString
    MAX-ACCESS    read-only
    STATUS      current
                DESCRIPTION
                                "Gives the BroadWorks system name"
                ::=  {  bwSystemSPEntry  3  }

  bwNumberOfSPUsers OBJECT-TYPE
    SYNTAX      Gauge32
    MAX-ACCESS    read-only
    STATUS      current
                DESCRIPTION
                                "Gives the total of users configured for a service provider"
                ::=  {  bwSystemSPEntry  4  }

  bwNumberOfSPGroups  OBJECT-TYPE
    SYNTAX      Gauge32
    MAX-ACCESS    read-only
    STATUS      current
                DESCRIPTION
                                "Gives the total of groups configured for a service provider"
                ::=  {  bwSystemSPEntry  5  }

  bwNumberOfSPDNDefined OBJECT-TYPE
    SYNTAX      Gauge32
    MAX-ACCESS    read-only
    STATUS      current
                DESCRIPTION
                                "Gives the total of phone numbers configured for a service provider"
                ::=  {  bwSystemSPEntry  6  }

  bwNumberOfSPDNAssigned  OBJECT-TYPE
    SYNTAX      Gauge32
    MAX-ACCESS    read-only
    STATUS      current
                DESCRIPTION
                                "Gives the total of phone numbers assigned to groups by a service provider"
                ::=  {  bwSystemSPEntry  7  }

  bwNumberOfSPDeviceType  OBJECT-TYPE
    SYNTAX      Gauge32
    MAX-ACCESS    read-only
    STATUS      current
                DESCRIPTION
                                "Gives the total of device types defined for a service provider"
                ::=  {  bwSystemSPEntry  8  }

-- Group system statistics ...........................................

  bwSystemGroupEntry    OBJECT-TYPE
    SYNTAX      BwSystemGroupEntry
    MAX-ACCESS    not-accessible
    STATUS      current
                DESCRIPTION
                                "This row contains the system statistics for a given group in the system"
    INDEX   {  bwSystemGroupIndex  }
                ::=  { bwSystemGroupTable 1 }

        BwSystemGroupEntry  ::=  SEQUENCE {
                bwSystemGroupIndex  Unsigned32,
                bwSystemGroupSPID  DisplayString,
                bwSystemGroupID  DisplayString,
                bwSystemGroupName DisplayString,
                bwNumberOfGroupUsers Gauge32,
                bwNumberOfGroupDNDefined Gauge32,
                bwNumberOfGroupDNAssigned Gauge32,
                bwNumberOfGroupDeviceType Gauge32
                }


  bwSystemGroupIndex  OBJECT-TYPE
    SYNTAX      Unsigned32
    MAX-ACCESS    read-only
    STATUS      current
                DESCRIPTION
                                "This integer represents a group index in the system"
                ::=  {  bwSystemGroupEntry  1  }


  bwSystemGroupSPID OBJECT-TYPE
    SYNTAX      DisplayString
    MAX-ACCESS    read-only
    STATUS      current
                DESCRIPTION
                                "This string represents a service provider ID"
                ::=  {  bwSystemGroupEntry  2  }

  bwSystemGroupID OBJECT-TYPE
    SYNTAX      DisplayString
    MAX-ACCESS    read-only
    STATUS      current
                DESCRIPTION
                                "This string represents a group ID"
                ::=  {  bwSystemGroupEntry  3  }


  bwSystemGroupName     OBJECT-TYPE
    SYNTAX      DisplayString
    MAX-ACCESS    read-only
    STATUS      current
                DESCRIPTION
                                "Gives the BroadWorks system name"
                ::=  {  bwSystemGroupEntry  4  }

  bwNumberOfGroupUsers  OBJECT-TYPE
    SYNTAX      Gauge32
    MAX-ACCESS    read-only
    STATUS      current
                DESCRIPTION
                                "Gives the total of users configured in a group"
                ::=  {  bwSystemGroupEntry  5  }

  bwNumberOfGroupDNDefined  OBJECT-TYPE
    SYNTAX      Gauge32
    MAX-ACCESS    read-only
    STATUS      current
                DESCRIPTION
                                "Gives the total of phone numbers configured for a group"
                ::=  {  bwSystemGroupEntry  6  }

  bwNumberOfGroupDNAssigned OBJECT-TYPE
    SYNTAX      Gauge32
    MAX-ACCESS    read-only
    STATUS      current
                DESCRIPTION
                                "Gives the total of phone numbers assigned to a group"
                ::=  {  bwSystemGroupEntry  7  }

  bwNumberOfGroupDeviceType OBJECT-TYPE
    SYNTAX      Gauge32
    MAX-ACCESS    read-only
    STATUS      current
                DESCRIPTION
                                "Gives the total of device types for a group"
                ::=  {  bwSystemGroupEntry  8  }

-- system statistics ...........................................

  internalStats OBJECT IDENTIFIER
                ::=  {  systemModule   2 }

  bySystemInternalQueueResets OBJECT-TYPE
    SYNTAX      Counter32
    MAX-ACCESS    read-write
    STATUS      current
    DESCRIPTION "When set to a value other then 0, all the internal queue statistic stored under bwSystemInternalQueueTable are reset to 0."
                ::=  {  internalStats  1  }

  bwSystemInternalQueueTable    OBJECT-TYPE
    SYNTAX    SEQUENCE  OF  BwSystemInternalQueueEntry
    MAX-ACCESS  not-accessible
    STATUS    current
                DESCRIPTION
                        "This table contains statistics about the BroadWorks internal queues"
                ::=  { internalStats  2 }

  bwSystemInternalQueueEntry    OBJECT-TYPE
    SYNTAX      BwSystemInternalQueueEntry
    MAX-ACCESS    not-accessible
    STATUS      current
                DESCRIPTION
                                "This row contains the statistics for a given internal queue in the system"
    INDEX   {  bwSystemInternalQueueIndex  }
                ::=  { bwSystemInternalQueueTable 1 }

        BwSystemInternalQueueEntry  ::=  SEQUENCE {
                bwSystemInternalQueueIndex  Unsigned32,
                bwSystemInternalQueueName  DisplayString,
                bwSystemInternalQueueSize  Counter32,
                bwSystemInternalQueueTimeAvg Gauge32,
                bwSystemInternalQueueTimeMin Gauge32,
                bwSystemInternalQueueTimeMax Gauge32,
                bwSystemInternalQueueLengthCurrent Gauge32,
                bwSystemInternalQueueLengthAvg Gauge32,
                bwSystemInternalQueueLengthMax Gauge32,
                bwSystemInternalQueueTimeMaxTimestampMSB Gauge32,
                bwSystemInternalQueueLengthMaxTimestampMSB Gauge32,
                bwSystemInternalQueueLengthMaxTimestampLSB Gauge32,
                bwSystemInternalQueueTimeMaxTimestampLSB Gauge32
                }

  bwSystemInternalQueueIndex  OBJECT-TYPE
    SYNTAX      Unsigned32
    MAX-ACCESS    read-only
    STATUS      current
                DESCRIPTION
                                "This integer represents an index to an internal queue in the system."
                ::=  {  bwSystemInternalQueueEntry  1  }

  bwSystemInternalQueueName OBJECT-TYPE
    SYNTAX      DisplayString
    MAX-ACCESS    read-only
    STATUS      current
                DESCRIPTION
                                "This string represents the name of an internal queue."
                ::=  {  bwSystemInternalQueueEntry  2  }

  bwSystemInternalQueueSize OBJECT-TYPE
    SYNTAX      Counter32
    MAX-ACCESS    read-only
    STATUS      current
                DESCRIPTION
                                "The number of sample elements that the average, minimum and maximum holding time were calculated from."
                ::=  {  bwSystemInternalQueueEntry  3  }

  bwSystemInternalQueueTimeAvg  OBJECT-TYPE
    SYNTAX      Gauge32
    MAX-ACCESS    read-only
    STATUS      current
                DESCRIPTION
                                "The average queue holding time. Note that this value is in 1/1000 of millisec, i.e. divide by 1000 to get the value in milliseconds."
                ::=  {  bwSystemInternalQueueEntry  4  }

  bwSystemInternalQueueTimeMin  OBJECT-TYPE
    SYNTAX      Gauge32
    MAX-ACCESS    read-only
    STATUS      current
                DESCRIPTION
                                "The smallest queue sample holding time."
                ::=  {  bwSystemInternalQueueEntry  5  }

  bwSystemInternalQueueTimeMax  OBJECT-TYPE
    SYNTAX      Gauge32
    MAX-ACCESS    read-only
    STATUS      current
                DESCRIPTION
                                "The biggest queue sample holding time."
                ::=  {  bwSystemInternalQueueEntry  6  }

  bwSystemInternalQueueTimeMaxTimestamp OBJECT-TYPE
    SYNTAX      Gauge32
    MAX-ACCESS    read-only
    STATUS      obsolete
                DESCRIPTION
                                "This counter was replaced by bwSystemInternalQueueTimeMaxTimestampMSB and bwSystemInternalQueueTimeMaxTimestampLSB."
                ::=  {  bwSystemInternalQueueEntry  7 }

  bwSystemInternalQueueLengthCurrent  OBJECT-TYPE
    SYNTAX      Gauge32
    MAX-ACCESS    read-only
    STATUS      current
                DESCRIPTION
                                "The number of elements currently hold in the queue."
                ::=  {  bwSystemInternalQueueEntry  8  }

  bwSystemInternalQueueLengthAvg  OBJECT-TYPE
    SYNTAX      Gauge32
    MAX-ACCESS    read-only
    STATUS      current
                DESCRIPTION
                                "The average number of elements simultaneously held in the queue multiple by 1000. Divide by 1000 to get the value in units."
                ::=  {  bwSystemInternalQueueEntry  9 }

  bwSystemInternalQueueLengthMax  OBJECT-TYPE
    SYNTAX      Gauge32
    MAX-ACCESS    read-only
    STATUS      current
                DESCRIPTION
                                "The maximum number of elements simultaneously held in the queue multiple by 1000. Divide by 1000 to get the value in units."
                ::=  {  bwSystemInternalQueueEntry  10 }

  bwSystemInternalQueueLengthMaxTimestamp OBJECT-TYPE
    SYNTAX      Gauge32
    MAX-ACCESS    read-only
    STATUS      obsolete
                DESCRIPTION
                                "This counter was replaced by bwSystemInternalQueueLengthMaxTimestampMSB and bwSystemInternalQueueLengthMaxTimestampLSB."
                ::=  {  bwSystemInternalQueueEntry  11 }

  bwSystemInternalQueueTimeMaxTimestampMSB  OBJECT-TYPE
    SYNTAX      Gauge32
    MAX-ACCESS    read-only
    STATUS      current
                DESCRIPTION
                                "The most significant part of the timestamp (4 most significant bytes) of when bwSystemInternalQueueTimeMax was obtained."
                ::=  {  bwSystemInternalQueueEntry  12 }

  bwSystemInternalQueueLengthMaxTimestampMSB  OBJECT-TYPE
    SYNTAX      Gauge32
    MAX-ACCESS    read-only
    STATUS      current
                DESCRIPTION
                                "The most significant part of the timestamp (4 most significant bytes) of when bwSystemInternalQueueLengthMax was obtained."
                ::=  {  bwSystemInternalQueueEntry  13 }
                
  bwSystemInternalQueueLengthMaxTimestampLSB  OBJECT-TYPE
    SYNTAX      Gauge32
    MAX-ACCESS    read-only
    STATUS      current
                DESCRIPTION
                                "The least significant part of the timestamp (4 least significant bytes) of when bwSystemInternalQueueLengthMax was obtained."
    ::=  {  bwSystemInternalQueueEntry  14 }    
                
  bwSystemInternalQueueTimeMaxTimestampLSB  OBJECT-TYPE
    SYNTAX      Gauge32
    MAX-ACCESS    read-only
    STATUS      current
                DESCRIPTION
                                "The least significant part of the timestamp (4 least significant bytes) of when bwSystemInternalQueueTimeMax was obtained."
                ::=  {  bwSystemInternalQueueEntry  15 }

-- system statistics ...........................................

  overloadStats OBJECT IDENTIFIER
                ::=  {  systemModule   3 }

  bwCurrentOverloadZone OBJECT-TYPE
    SYNTAX      DisplayString
    MAX-ACCESS    read-only
    STATUS      obsolete
    DESCRIPTION "The current overload zone. Value is a string indicating Green, Yellow, or Red.
This object is obsolete. Call and non-call objects shall be used."
                ::=  {  overloadStats  1  }

  bwNumYellowZoneOverloadTrans  OBJECT-TYPE
    SYNTAX      Counter32
    MAX-ACCESS    read-write
    STATUS      obsolete
    DESCRIPTION "The number of times that the server has transitioned to the yellow overload zone.
This object is obsolete. Call and non-call objects shall be used."
                ::=  {  overloadStats  2  }

  bwNumRedZoneOverloadTrans OBJECT-TYPE
    SYNTAX      Counter32
    MAX-ACCESS    read-write
    STATUS      obsolete
    DESCRIPTION "The number of times that the server has transitioned to the red overload zone.
This object is obsolete. Call and non-call objects shall be used."
                ::=  {  overloadStats  3  }

  bwCurrentCallOverloadZone OBJECT-TYPE
    SYNTAX      DisplayString
    MAX-ACCESS    read-only
    STATUS      current
    DESCRIPTION "The current call related overload zone. Value is a string indicating Green, Yellow, or Red."
                ::=  {  overloadStats  4  }

  bwNumCallYellowZoneOverloadTrans  OBJECT-TYPE
    SYNTAX      Counter32
    MAX-ACCESS    read-write
    STATUS      current
    DESCRIPTION "The number of times that the server has transitioned to the call related yellow overload zone."
                ::=  {  overloadStats  5  }

  bwNumCallRedZoneOverloadTrans OBJECT-TYPE
    SYNTAX      Counter32
    MAX-ACCESS    read-write
    STATUS      current
    DESCRIPTION "The number of times that the server has transitioned to the call related red overload zone."
                ::=  {  overloadStats  6 }

  bwCurrentNonCallOverloadZone  OBJECT-TYPE
    SYNTAX      DisplayString
    MAX-ACCESS    read-only
    STATUS      current
    DESCRIPTION "The current non-call related overload zone. Value is a string indicating Green, Yellow, or Red."
                ::=  {  overloadStats  7  }

  bwNumNonCallYellowZoneOverloadTrans OBJECT-TYPE
    SYNTAX      Counter32
    MAX-ACCESS    read-write
    STATUS      current
    DESCRIPTION "The number of times that the server has transitioned to the non-call related yellow overload zone."
                ::=  {  overloadStats  8  }

  bwNumNonCallRedZoneOverloadTrans  OBJECT-TYPE
    SYNTAX      Counter32
    MAX-ACCESS    read-write
    STATUS      current
    DESCRIPTION "The number of times that the server has transitioned to the non-call related red overload zone."
                ::=  {  overloadStats  9 }

        bwNumDiscardedMessage           OBJECT-TYPE
    SYNTAX      Counter32
    MAX-ACCESS    read-write
    STATUS      current
    DESCRIPTION "The number of messages that were dropped from the SIP or MGCP decoder queues."
                ::=  {  overloadStats  10  }

        bwTimeLastDiscardedMessage      OBJECT-TYPE
    SYNTAX      DisplayString
    MAX-ACCESS    read-write
    STATUS      current
    DESCRIPTION "The last time a message was dropped from the SIP or MGCP decoded queues."
                ::=  {  overloadStats  11  }

-- Redundancy .................

  nbOfMigratedUsers OBJECT-TYPE
    SYNTAX      Gauge32
    MAX-ACCESS    read-only
    STATUS      current
                DESCRIPTION
                                "This value represents the actual number of users migrated to the secondary application server"
                ::=  {  redundancyStats  1  }


-- PS :: Persistence :: TimesTen  ...........................................

  psTimesTen  OBJECT IDENTIFIER
                ::=  {  psDatabaseStats  1  }

  psPerNbOpenedTransactions OBJECT-TYPE
    SYNTAX      Gauge32
    MAX-ACCESS    read-only
    STATUS      current
                DESCRIPTION
                                "Number of opened transaction with the database"
                ::=  {  psDatabaseStats  2  }

  psPerNbCommittedTransactions  OBJECT-TYPE
    SYNTAX      Counter32
    MAX-ACCESS    read-write
    STATUS      current
                DESCRIPTION
                                "Total number of committed transactions to the database since the last restart"
                ::=  {  psDatabaseStats  3  }

  psPerNbFailedTransactions OBJECT-TYPE
    SYNTAX      Counter32
    MAX-ACCESS    read-write
    STATUS      current
                DESCRIPTION
                                "Number of failed transactions with the database"
                ::=  {  psDatabaseStats  4  }

  psPerNbCriticalErrors OBJECT-TYPE
    SYNTAX      Counter32
    MAX-ACCESS    read-write
    STATUS      current
                DESCRIPTION
                                "Total number of critical errors encountered during processing with the database"
                ::=  {  psDatabaseStats  5  }

  psTtNbConnectionsCreated  OBJECT-TYPE
    SYNTAX      Counter32
    MAX-ACCESS    read-write
    STATUS      current
                DESCRIPTION
                                "Number of total transaction created to the database"
                ::=  {  psTimesTen  1  }

  psTtConnectionPoolSize  OBJECT-TYPE
    SYNTAX      Gauge32
    MAX-ACCESS    read-only
    STATUS      current
                DESCRIPTION
                                "Current size of the database connection pool"
                ::=  {  psTimesTen  2  }

  psTtNbBackdoorUpdates OBJECT-TYPE
    SYNTAX      Counter32
    MAX-ACCESS    read-write
    STATUS      obsolete
                DESCRIPTION
                                "Total number of backdoor notification"
                ::=  {  psTimesTen  3  }

  psTtNbFailedCheckpoints OBJECT-TYPE
    SYNTAX      Counter32
    MAX-ACCESS    read-write
    STATUS      obsolete
                DESCRIPTION
                                "Total number of fail check pointing to the dabatase"
                ::=  {  psTimesTen  4  }

  -- ::=  {  psTimesTen  5  } used by RemoteXla (look a couple of lines down)

  bwPSAvgUpdateTime OBJECT-TYPE
  SYNTAX      Gauge32
    MAX-ACCESS    read-only
    STATUS      current
                DESCRIPTION
                                "Average DB update time in milliseconds"
                ::=  {  psTimesTen  6  }

  bwPSAvgRowsUpdated  OBJECT-TYPE
  SYNTAX      Gauge32
    MAX-ACCESS    read-only
    STATUS      current
                DESCRIPTION
                                "Average number of rows affected in DB updates"
                ::=  {  psTimesTen  7  }

  bwPSAvgQueryTime OBJECT-TYPE
  SYNTAX      Gauge32
    MAX-ACCESS    read-only
    STATUS      current
                DESCRIPTION
                                "Average DB query time in milliseconds"
                ::=  {  psTimesTen  8  }    

  bwPSAvgRowsQueried OBJECT-TYPE
  SYNTAX      Gauge32
    MAX-ACCESS    read-only
    STATUS      current
                DESCRIPTION
                                "Average number of rows processed in DB queries"
                ::=  {  psTimesTen  9  }


  bwPSUpdateCount OBJECT-TYPE
    SYNTAX      Counter32
    MAX-ACCESS    read-write
    STATUS      current
                DESCRIPTION
                                "Number of DB updates performed since the application started"
                ::=  {  psTimesTen  10  }

  bwPSQueryCount OBJECT-TYPE
    SYNTAX      Counter32
    MAX-ACCESS    read-write
    STATUS      current
                DESCRIPTION
                                "Number of DB queries performed since the application started"
                ::=  {  psTimesTen  11  }

-- PS TimesTen High Water Mark table  ...........................................

  bwPSTTHWMTable  OBJECT-TYPE
    SYNTAX    SEQUENCE  OF  BwPSTTHWMEntry
    MAX-ACCESS  not-accessible
    STATUS    current
                DESCRIPTION
                        "This table contains counters for the PS TimesTen high water marks."
                ::=  { psTimesTen  12 }

  bwPSTTHWMEntry  OBJECT-TYPE
    SYNTAX    BwPSTTHWMEntry
    MAX-ACCESS  not-accessible
    STATUS    current
                DESCRIPTION
                        "Definition of the entries for bwPSTTHWMTable."
    INDEX   {  bwPSTTHWMIndex  }
                ::=  { bwPSTTHWMTable 1 }

        BwPSTTHWMEntry  ::=  SEQUENCE {
    bwPSTTHWMIndex Unsigned32,
    bwPSTTHWMName DisplayString,
    bwPSTTHWMValue Gauge32,
    bwPSTTHWMTimestamp DisplayString,
    bwPSTTHWMStackTrace DisplayString
  }

  bwPSTTHWMIndex  OBJECT-TYPE
    SYNTAX      Unsigned32
    MAX-ACCESS    read-only
    STATUS      current
                DESCRIPTION
                                "This integer represents an index in table bwPSTTHWMTable. This is the index to a specific high water mark."
                ::=  {  bwPSTTHWMEntry  1  }

  bwPSTTHWMName OBJECT-TYPE
    SYNTAX      DisplayString
    MAX-ACCESS    read-only
    STATUS      current
                DESCRIPTION
                                "The name of an PS TimesTen high water mark."
                ::=  {  bwPSTTHWMEntry  2  }

  bwPSTTHWMValue  OBJECT-TYPE
    SYNTAX      Gauge32
    MAX-ACCESS    read-write
    STATUS      current
                DESCRIPTION
                                "The value of an PS TimesTen high water mark."
                ::=  {  bwPSTTHWMEntry  3  }

  bwPSTTHWMTimestamp  OBJECT-TYPE
    SYNTAX      DisplayString
    MAX-ACCESS    read-write
    STATUS      current
                DESCRIPTION
                                "The timestamp of an PS TimesTen high water mark."
                ::=  {  bwPSTTHWMEntry  4  }

  bwPSTTHWMStackTrace OBJECT-TYPE
    SYNTAX      DisplayString
    MAX-ACCESS    read-write
    STATUS      current
                DESCRIPTION
                                "The stack trace of an PS TimesTen high water mark."
                ::=  {  bwPSTTHWMEntry  5  }

-- RemoteXla

  psRemoteXla OBJECT IDENTIFIER
                ::=  {  psTimesTen  5  }

  psRemoteXlaNbTimesConnected OBJECT-TYPE
    SYNTAX      Counter32
    MAX-ACCESS    read-write
    STATUS      current
                DESCRIPTION
                                "Number of times a connection was made to the RemoteXla server"
                ::=  {  psRemoteXla  1  }

  psRemoteXlaNbTimesDisconnected  OBJECT-TYPE
    SYNTAX      Counter32
    MAX-ACCESS    read-write
    STATUS      current
                DESCRIPTION
                                "Number of times the process was disconnected from the RemoteXla server"
                ::=  {  psRemoteXla  2  }

  psRemoteXlaUpdatesProcessed OBJECT-TYPE
    SYNTAX      Counter32
    MAX-ACCESS    read-write
    STATUS      current
                DESCRIPTION
                                "Number of XLA updates processed"
                ::=  {  psRemoteXla  3  }

  psRemoteXlaUpdatesPending OBJECT-TYPE
    SYNTAX      Gauge32
    MAX-ACCESS    read-write
    STATUS      current
                DESCRIPTION
                                "Number of XLA updates pending to be processed"
                ::=  {  psRemoteXla  4  }


-- PS External Call Logs module ...........................................

  bwExternalCallLogsRetrievalAttempts OBJECT-TYPE
    SYNTAX      Counter32
    MAX-ACCESS    read-write
    STATUS      current
    DESCRIPTION "Incremented each time a request to retrieve call logs from the external call detail server is attempted."
                ::=  {  psExternalCallLogsStats  1  }

  bwExternalCallLogsRetrievalFailures OBJECT-TYPE
    SYNTAX      Counter32
    MAX-ACCESS    read-write
    STATUS      current
    DESCRIPTION "Incremented each time a request to retrieve call logs from the external call detail server has failed."
                ::=  {  psExternalCallLogsStats  2  }

-- OCI module ...........................................

  psOciStatsNbUpdateRequests  OBJECT-TYPE
    SYNTAX      Counter32
    MAX-ACCESS    read-write
    STATUS      current
    DESCRIPTION "This counter is incremented upon receipt of an OCI modification request."
                ::=  {  psOciStats  1  }

  psOciStatsNbUpdateRequestFailures OBJECT-TYPE
    SYNTAX      Counter32
    MAX-ACCESS    read-write
    STATUS      current
    DESCRIPTION "This counter is incremented whenever processing of an OCI modification request results in an error response."
                ::=  {  psOciStats  2  }

  psOciStatsNbQueryRequests OBJECT-TYPE
    SYNTAX      Counter32
    MAX-ACCESS    read-write
    STATUS      current
    DESCRIPTION "This counter is incremented upon receipt of an OCI get request."
                ::=  {  psOciStats  3  }

  psOciStatsNbQueryRequestFailures  OBJECT-TYPE
    SYNTAX      Counter32
    MAX-ACCESS    read-write
    STATUS      current
    DESCRIPTION "This counter is incremented whenever processing of an OCI get request results in an error response."
                ::=  {  psOciStats  4  }

  psOciStatsNbAuthorizationRequests OBJECT-TYPE
    SYNTAX      Counter32
    MAX-ACCESS    read-write
    STATUS      current
    DESCRIPTION "This counter is incremented upon receipt of an OCI login request."
                ::=  {  psOciStats  5  }

  psOciStatsNbAuthorizationRequestFailures  OBJECT-TYPE
    SYNTAX      Counter32
    MAX-ACCESS    read-write
    STATUS      current
    DESCRIPTION "This counter is incremented whenever processing of an OCI login request results in an error response."
                ::=  {  psOciStats  6  }

  psOciStatsNbReportingAclViolations  OBJECT-TYPE
    SYNTAX      Counter32
    MAX-ACCESS    read-write
    STATUS      current
    DESCRIPTION "This counter is incremented whenever an incoming OCI reporting connection is rejected because the external system isn't in access control list."
                ::=  {  psOciStats  7  }

  psOciStatsNbReportNotificationsOut  OBJECT-TYPE
    SYNTAX      Counter32
    MAX-ACCESS    read-write
    STATUS      current
    DESCRIPTION "This counter is incremented whenever the system transmits an OCIReportingReportNotification."
                ::=  {  psOciStats  8  }

  psOciStatsActiveSessions  OBJECT-TYPE
    SYNTAX      Gauge32
    MAX-ACCESS    read-only
    STATUS      current
                DESCRIPTION
                                "Indicates the number of OCI sessions currently open."
                ::=  {  psOciStats  9  }

  psOciStatsSystemRequestsPerHour OBJECT-TYPE
    SYNTAX      Gauge32
    MAX-ACCESS    read-only
    STATUS      current
                DESCRIPTION
                                "Indicates the rate at which the Application Server receives OCI system requests.  It uses the timestamps of the last 100 OCI system requests received to calculate the rate."
                ::=  {  psOciStats  10 }

  psOciStatsSystemRequestResponseTime OBJECT-TYPE
    SYNTAX      Gauge32
    MAX-ACCESS    read-only
    STATUS      current
                DESCRIPTION
                                "Indicates the average time (in milliseconds based on a rolling average of the last 100 samples) it takes to process a system level OCI request."
                ::=  {  psOciStats  11 }

  psOciStatsMinSystemRequestResponseTime  OBJECT-TYPE
    SYNTAX      Gauge32
    MAX-ACCESS    read-write
    STATUS      current
                DESCRIPTION
                                "Indicates the shortest OCI system request response time sampled since the system was started or since this measurement was cleared."
                ::=  {  psOciStats  12 }

  psOciStatsMaxSystemRequestResponseTime  OBJECT-TYPE
    SYNTAX      Gauge32
    MAX-ACCESS    read-write
    STATUS      current
                DESCRIPTION
                                "Indicates the longest OCI system request response time sampled since the system was started or since this measurement was cleared."
                ::=  {  psOciStats  13 }

  psOciStatsMaxSystemRequestName  OBJECT-TYPE
    SYNTAX      DisplayString
    MAX-ACCESS    read-only
    STATUS      current
                DESCRIPTION
                                "Indicates the name of the system level OCI request corresponding to the ociMaxSystemRequestResponseTime gauge."
                ::=  {  psOciStats  14 }

  psOciStatsServiceProviderRequestsPerHour  OBJECT-TYPE
    SYNTAX      Gauge32
    MAX-ACCESS    read-only
    STATUS      current
                DESCRIPTION
                                "Indicates the rate at which the Application Server receives OCI service provider requests.  It uses the timestamps of the last 100 OCI service provider requests received to calculate the rate."
                ::=  {  psOciStats  15 }

  psOciStatsServiceProviderRequestResponseTime  OBJECT-TYPE
    SYNTAX      Gauge32
    MAX-ACCESS    read-only
    STATUS      current
                DESCRIPTION
                                "Indicates the average time (in milliseconds based on a rolling average of the last 100 samples) it takes to process a service provider level OCI request."
                ::=  {  psOciStats  16 }

  psOciStatsMinServiceProviderRequestResponseTime OBJECT-TYPE
    SYNTAX      Gauge32
    MAX-ACCESS    read-write
    STATUS      current
                DESCRIPTION
                                "Indicates the shortest OCI service provider request response time sampled since the system was started or since this measurement was cleared."
                ::=  {  psOciStats  17 }

  psOciStatsMaxServiceProviderRequestResponseTime OBJECT-TYPE
    SYNTAX      Gauge32
    MAX-ACCESS    read-write
    STATUS      current
                DESCRIPTION
                                "Indicates the longest OCI service provider request response time sampled since the system was started or since this measurement was cleared."
                ::=  {  psOciStats  18 }

  psOciStatsMaxServiceProviderRequestName OBJECT-TYPE
    SYNTAX      DisplayString
    MAX-ACCESS    read-only
    STATUS      current
                DESCRIPTION
                                "Indicates the name of the service provider level OCI request corresponding to the ociMaxServiceProviderRequestResponseTime gauge."
                ::=  {  psOciStats  19 }

  psOciStatsGroupRequestsPerHour  OBJECT-TYPE
    SYNTAX      Gauge32
    MAX-ACCESS    read-only
    STATUS      current
                DESCRIPTION
                                "Indicates the rate at which the Application Server receives OCI group requests.  It uses the timestamps of the last 100 OCI group requests received to calculate the rate."
                ::=  {  psOciStats  20 }

  psOciStatsGroupRequestResponseTime  OBJECT-TYPE
    SYNTAX      Gauge32
    MAX-ACCESS    read-only
    STATUS      current
                DESCRIPTION
                                "Indicates the average time (in milliseconds based on a rolling average of the last 100 samples) it takes to process a group level OCI request."
                ::=  {  psOciStats  21 }

  psOciStatsMinGroupRequestResponseTime OBJECT-TYPE
    SYNTAX      Gauge32
    MAX-ACCESS    read-write
    STATUS      current
                DESCRIPTION
                                "Indicates the shortest OCI group request response time sampled since the system was started or since this measurement was cleared."
                ::=  {  psOciStats  22 }

  psOciStatsMaxGroupRequestResponseTime OBJECT-TYPE
    SYNTAX      Gauge32
    MAX-ACCESS    read-write
    STATUS      current
                DESCRIPTION
                                "Indicates the longest OCI group request response time sampled since the system was started or since this measurement was cleared."
                ::=  {  psOciStats  23 }

  psOciStatsMaxGroupRequestName OBJECT-TYPE
    SYNTAX      DisplayString
    MAX-ACCESS    read-only
    STATUS      current
                DESCRIPTION
                                "Indicates the name of the group level OCI request corresponding to the ociMaxGroupRequestResponseTime gauge."
                ::=  {  psOciStats  24 }

  psOciStatsUserRequestsPerHour OBJECT-TYPE
    SYNTAX      Gauge32
    MAX-ACCESS    read-only
    STATUS      current
                DESCRIPTION
                                "Indicates the rate at which the Application Server receives OCI user requests.  It uses the timestamps of the last 100 OCI user requests received to calculate the rate."
                ::=  {  psOciStats  25 }

  psOciStatsUserRequestResponseTime OBJECT-TYPE
    SYNTAX      Gauge32
    MAX-ACCESS    read-only
    STATUS      current
                DESCRIPTION
                                "Indicates the average time (in milliseconds based on a rolling average of the last 100 samples) it takes to process a user level OCI request."
                ::=  {  psOciStats  26 }

  psOciStatsMinUserRequestResponseTime  OBJECT-TYPE
    SYNTAX      Gauge32
    MAX-ACCESS    read-write
    STATUS      current
                DESCRIPTION
                                "Indicates the shortest OCI user request response time sampled since the system was started or since this measurement was cleared."
                ::=  {  psOciStats  27 }

  psOciStatsMaxUserRequestResponseTime  OBJECT-TYPE
    SYNTAX      Gauge32
    MAX-ACCESS    read-write
    STATUS      current
                DESCRIPTION
                                "Indicates the longest OCI user request response time sampled since the system was started or since this measurement was cleared."
                ::=  {  psOciStats  28 }

  psOciStatsMaxUserRequestName  OBJECT-TYPE
    SYNTAX      DisplayString
    MAX-ACCESS    read-only
    STATUS      current
                DESCRIPTION
                                "Indicates the name of the user level OCI request corresponding to the ociMaxUserRequestResponseTime gauge."
                ::=  {  psOciStats  29 }

  psOciStatsRequestsPerHour OBJECT-TYPE
    SYNTAX      Gauge32
    MAX-ACCESS    read-only
    STATUS      current
                DESCRIPTION
                                "Indicates the rate at which the Application Server receives OCI requests.  It uses the timestamps of the last 100 OCI requests received to calculate the rate."
                ::=  {  psOciStats  30 }

  psOciStatsRequestResponseTime OBJECT-TYPE
    SYNTAX      Gauge32
    MAX-ACCESS    read-only
    STATUS      current
                DESCRIPTION
                                "Indicates the average time (in milliseconds based on a rolling average of the last 100 samples) it takes to process an OCI request."
                ::=  {  psOciStats  31 }

  psOciStatsMinRequestResponseTime  OBJECT-TYPE
    SYNTAX      Gauge32
    MAX-ACCESS    read-write
    STATUS      current
                DESCRIPTION
                                "Indicates the shortest OCI request response time sampled since the system was started or since this measurement was cleared."
                ::=  {  psOciStats  32 }

  psOciStatsMaxRequestResponseTime  OBJECT-TYPE
    SYNTAX      Gauge32
    MAX-ACCESS    read-write
    STATUS      current
                DESCRIPTION
                                "Indicates the longest OCI request response time sampled since the system was started or since this measurement was cleared."
                ::=  {  psOciStats  33 }

  psOciStatsMaxRequestName  OBJECT-TYPE
    SYNTAX      DisplayString
    MAX-ACCESS    read-only
    STATUS      current
                DESCRIPTION
                                "Indicates the name of the OCI request corresponding to the ociMaxRequestResponseTime gauge."
                ::=  {  psOciStats  34 }

  psOCIReportingBackLogMessageTable OBJECT-TYPE
    SYNTAX        SEQUENCE  OF  PsOCIReportingBackLogMessageEntry
    MAX-ACCESS      not-accessible
    STATUS        current
                DESCRIPTION
                                "This table contains statistics about the OCI Reporting backlog messages."
                ::=  {  psOciStats  35 }

  psOCIReportingBackLogMessageEntry OBJECT-TYPE
    SYNTAX        PsOCIReportingBackLogMessageEntry
    MAX-ACCESS      not-accessible
    STATUS        current
                DESCRIPTION
                                "This row contains statistics about the OCI Reporting backlog messages."
    INDEX   {  psOCIReportingBackLogMessageIndex  }
                ::=  { psOCIReportingBackLogMessageTable 1 }

        PsOCIReportingBackLogMessageEntry  ::=  SEQUENCE {
                psOCIReportingBackLogMessageIndex  Unsigned32,
                psOCIReportingBackLogMessageHost   DisplayString,
                psOCIReportingBackLogMessageSaved  Counter32,
                psOCIReportingBackLogMessageSent   Counter32
                }

  psOCIReportingBackLogMessageIndex OBJECT-TYPE
    SYNTAX        Unsigned32
    MAX-ACCESS      read-only
    STATUS        current
                DESCRIPTION
                                "This integer represents an index to an OCI Reporting host in the Provisioning Server."
                ::=  {  psOCIReportingBackLogMessageEntry  1  }

  psOCIReportingBackLogMessageHost  OBJECT-TYPE
    SYNTAX        DisplayString
    MAX-ACCESS      read-only
    STATUS        current
                DESCRIPTION
                                "This represents the host name/IP address of a reporting host."
                ::=  {  psOCIReportingBackLogMessageEntry  2  }

  psOCIReportingBackLogMessageSaved OBJECT-TYPE
    SYNTAX        Counter32
    MAX-ACCESS      read-only
    STATUS        current
                DESCRIPTION
                                "The number of OCI reporting message written to the backlog files."
                ::=  {  psOCIReportingBackLogMessageEntry  3  }

  psOCIReportingBackLogMessageSent  OBJECT-TYPE
    SYNTAX        Counter32
    MAX-ACCESS      read-only
    STATUS        current
                DESCRIPTION
                                "The number of OCI reporting message sent from the backlog files."
                ::=  {  psOCIReportingBackLogMessageEntry  4  }

-- system statistics ...........................................

  psSystemInternalQueueResets OBJECT-TYPE
    SYNTAX      Counter32
    MAX-ACCESS    read-write
    STATUS      current
    DESCRIPTION "When set to a value other then 0, all the internal queue statistic stored under psSystemInternalQueueTable are reset to 0."
                ::=  {  psInternalStats  1  }

  psSystemInternalQueueTable    OBJECT-TYPE
    SYNTAX    SEQUENCE  OF  PsSystemInternalQueueEntry
    MAX-ACCESS  not-accessible
    STATUS    current
                DESCRIPTION
                        "This table contains statistics about the BroadWorks internal queues"
                ::=  { psInternalStats  2 }

  psSystemInternalQueueEntry    OBJECT-TYPE
    SYNTAX      PsSystemInternalQueueEntry
    MAX-ACCESS    not-accessible
    STATUS      current
                DESCRIPTION
                                "This row contains the statistics for a given internal queue in the system"
    INDEX   {  psSystemInternalQueueIndex  }
                ::=  { psSystemInternalQueueTable 1 }

        PsSystemInternalQueueEntry  ::=  SEQUENCE {
                psSystemInternalQueueIndex  Unsigned32,
                psSystemInternalQueueName  DisplayString,
                psSystemInternalQueueSize  Counter32,
                psSystemInternalQueueTimeAvg Gauge32,
                psSystemInternalQueueTimeMin Gauge32,
                psSystemInternalQueueTimeMax Gauge32,
                psSystemInternalQueueLengthCurrent Gauge32,
                psSystemInternalQueueLengthAvg Gauge32,
                psSystemInternalQueueLengthMax Gauge32,
                psSystemInternalQueueLengthMaxTimestampMSB Gauge32,
                psSystemInternalQueueTimeMaxTimestampMSB Gauge32,
                psSystemInternalQueueLengthMaxTimestampLSB Gauge32,
                psSystemInternalQueueTimeMaxTimestampLSB Gauge32
                }

  psSystemInternalQueueIndex  OBJECT-TYPE
    SYNTAX      Unsigned32
    MAX-ACCESS    read-only
    STATUS      current
                DESCRIPTION
                                "This integer represents an index to an internal queue in the system."
                ::=  {  psSystemInternalQueueEntry  1  }

  psSystemInternalQueueName OBJECT-TYPE
    SYNTAX      DisplayString
    MAX-ACCESS    read-only
    STATUS      current
                DESCRIPTION
                                "This string represents the name of an internal queue."
                ::=  {  psSystemInternalQueueEntry  2  }

  psSystemInternalQueueSize OBJECT-TYPE
    SYNTAX      Counter32
    MAX-ACCESS    read-only
    STATUS      current
                DESCRIPTION
                                "The number of sample elements that the average, minimum and maximum holding time were calculated from."
                ::=  {  psSystemInternalQueueEntry  3  }

  psSystemInternalQueueTimeAvg  OBJECT-TYPE
    SYNTAX      Gauge32
    MAX-ACCESS    read-only
    STATUS      current
                DESCRIPTION
                                "The average queue holding time. Note that this value is in 1/1000 of millisec, i.e. divide by 1000 to get the value in milliseconds."
                ::=  {  psSystemInternalQueueEntry  4  }

  psSystemInternalQueueTimeMin  OBJECT-TYPE
    SYNTAX      Gauge32
    MAX-ACCESS    read-only
    STATUS      current
                DESCRIPTION
                                "The smallest queue sample holding time."
                ::=  {  psSystemInternalQueueEntry  5  }

  psSystemInternalQueueTimeMax  OBJECT-TYPE
    SYNTAX      Gauge32
    MAX-ACCESS    read-only
    STATUS      current
                DESCRIPTION
                                "The biggest queue sample holding time."
                ::=  {  psSystemInternalQueueEntry  6  }

  psSystemInternalQueueTimeMaxTimestamp OBJECT-TYPE
    SYNTAX      Gauge32
    MAX-ACCESS    read-only
    STATUS      obsolete
                DESCRIPTION
                                "This counter was replaced by psSystemInternalQueueTimeMaxTimestampMSB and psSystemInternalQueueTimeMaxTimestampLSB."
                ::=  {  psSystemInternalQueueEntry  7 }

  psSystemInternalQueueLengthCurrent  OBJECT-TYPE
    SYNTAX      Gauge32
    MAX-ACCESS    read-only
    STATUS      current
                DESCRIPTION
                                "The number of elements currently hold in the queue."
                ::=  {  psSystemInternalQueueEntry  8  }

  psSystemInternalQueueLengthAvg  OBJECT-TYPE
    SYNTAX      Gauge32
    MAX-ACCESS    read-only
    STATUS      current
                DESCRIPTION
                                "The average number of elements simultaneously held in the queue multiple by 1000. Divide by 1000 to get the value in units."
                ::=  {  psSystemInternalQueueEntry  9 }

  psSystemInternalQueueLengthMax  OBJECT-TYPE
    SYNTAX      Gauge32
    MAX-ACCESS    read-only
    STATUS      current
                DESCRIPTION
                                "The maximum number of elements simultaneously held in the queue multiple by 1000. Divide by 1000 to get the value in units."
                ::=  {  psSystemInternalQueueEntry  10 }

  psSystemInternalQueueLengthMaxTimestamp OBJECT-TYPE
    SYNTAX      Gauge32
    MAX-ACCESS    read-only
    STATUS      obsolete
                DESCRIPTION
                                "This counter was replaced with psSystemInternalQueueLengthMaxTimestampMSB and psSystemInternalQueueLengthMaxTimestampLSB."
                ::=  {  psSystemInternalQueueEntry  11 }
                
  psSystemInternalQueueTimeMaxTimestampMSB  OBJECT-TYPE
    SYNTAX      Gauge32
    MAX-ACCESS    read-only
    STATUS      current
                DESCRIPTION
                                "The most significant part of the timestamp (4 most significant bytes) of when psSystemInternalQueueTimeMax was obtained."
                ::=  {  psSystemInternalQueueEntry  12 }

  psSystemInternalQueueLengthMaxTimestampMSB  OBJECT-TYPE
    SYNTAX      Gauge32
    MAX-ACCESS    read-only
    STATUS      current
                DESCRIPTION
                                "The most significant part of the timestamp (4 most significant bytes) of when psSystemInternalQueueLengthMax was obtained."
                ::=  {  psSystemInternalQueueEntry  13 }
                
  psSystemInternalQueueLengthMaxTimestampLSB  OBJECT-TYPE
    SYNTAX      Gauge32
    MAX-ACCESS    read-only
    STATUS      current
                DESCRIPTION
                                "The least significant part of the timestamp (4 least significant bytes) of when psSystemInternalQueueLengthMax was obtained."
                ::=  {  psSystemInternalQueueEntry  14 }
                
  psSystemInternalQueueTimeMaxTimestampLSB  OBJECT-TYPE
    SYNTAX      Gauge32
    MAX-ACCESS    read-only
    STATUS      current
                DESCRIPTION
                                "The least significant part of the timestamp (4 least significant bytes) of when psSystemInternalQueueTimeMax was obtained."
    ::=  {  psSystemInternalQueueEntry  15 }  

-- LDAP module ...........................................

  bwLDAPIntegrationNumQueryAttempts OBJECT-TYPE
    SYNTAX      Counter32
    MAX-ACCESS    read-write
    STATUS      current
    DESCRIPTION "Total number of query attempts to an LDAP server by LDAP Integration feature system-wide."
                ::=  {  ldapModule  1  }

  bwLDAPIntegrationNumConnectionFailures  OBJECT-TYPE
    SYNTAX      Counter32
    MAX-ACCESS    read-write
    STATUS      current
    DESCRIPTION "Total number of connection failures to a LDAP server system-wide made by LDAP Integration feature."
                ::=  {  ldapModule  2  }

-- PS - BroadWorks Common Communication Protocol ........................

  bwCommonCommPSStatsTable  OBJECT-TYPE
    SYNTAX    SEQUENCE  OF  BwCommonCommPSStatsEntry
    MAX-ACCESS  not-accessible
    STATUS    current
                DESCRIPTION
                        "This table contains counters for BCCT for the PS process."
                ::=  { psCommonCommStats  1 }

  bwCommonCommPSStatsEntry  OBJECT-TYPE
    SYNTAX    BwCommonCommPSStatsEntry
    MAX-ACCESS  not-accessible
    STATUS    current
                DESCRIPTION
                        "Definition of the entries for bwCommonCommPSStatsTable."
    INDEX   {  bwCommonCommPSStatsIndex  }
                ::=  { bwCommonCommPSStatsTable 1 }

        BwCommonCommPSStatsEntry  ::=  SEQUENCE {
                bwCommonCommPSStatsIndex  Unsigned32,
                bwCommonCommPSHost  DisplayString,
                bwCommonCommPSInterface  DisplayString,
                bwCommonCommPSProtocol  DisplayString,
                bwCommonCommPSAcceptedOutboundConnections  Counter32,
                bwCommonCommPSAcceptedInboundConnections  Counter32,
                bwCommonCommPSRejectedOutboundConnections  Counter32,
                bwCommonCommPSRejectedInboundConnections  Counter32,
                bwCommonCommPSOutputMessagesProcessed  Counter32,
                bwCommonCommPSInputMessagesProcessed  Counter32,
                bwCommonCommPSOutputCommunicationErrors  Counter32,
                bwCommonCommPSInputCommunicationErrors  Counter32
                }

  bwCommonCommPSStatsIndex  OBJECT-TYPE
    SYNTAX      Unsigned32
    MAX-ACCESS    read-only
    STATUS      current
                DESCRIPTION
                                "This integer represents an index in table bwCommonCommPSStatsTable. The index represents a connection for a specific Host-Interfacece-Protocol combination."
                ::=  {  bwCommonCommPSStatsEntry  1  }

  bwCommonCommPSHost  OBJECT-TYPE
    SYNTAX      DisplayString
    MAX-ACCESS    read-only
    STATUS      current
                DESCRIPTION
                                "The address of a host connected to the BroadWorks Common Communication Protocol."
                ::=  {  bwCommonCommPSStatsEntry  2  }


  bwCommonCommPSInterface OBJECT-TYPE
    SYNTAX      DisplayString
    MAX-ACCESS    read-only
    STATUS      current
                DESCRIPTION
                                "The IP address of a local interface that a protocol is bound to."
                ::=  {  bwCommonCommPSStatsEntry  3  }

  bwCommonCommPSProtocol  OBJECT-TYPE
    SYNTAX      DisplayString
    MAX-ACCESS    read-only
    STATUS      current
                DESCRIPTION
                                "The name of a BroadWorks Common Communication Protocol client protocol, e.g. OCI or SyncApi."
                ::=  {  bwCommonCommPSStatsEntry  4  }

  bwCommonCommPSAcceptedOutboundConnections OBJECT-TYPE
    SYNTAX      Counter32
    MAX-ACCESS    read-write
    STATUS      current
                DESCRIPTION
                                "This counter is incremented whenever a client in this process connects to the framework to a remote host, using the interface and protocol."
                ::=  {  bwCommonCommPSStatsEntry  5  }

  bwCommonCommPSAcceptedInboundConnections  OBJECT-TYPE
    SYNTAX      Counter32
    MAX-ACCESS    read-write
    STATUS      current
                DESCRIPTION
                                "This counter is incremented whenever a client in this process connects to the framework from a remote host, using the interface and protocol."
                ::=  {  bwCommonCommPSStatsEntry  6  }

  bwCommonCommPSRejectedOutboundConnections OBJECT-TYPE
    SYNTAX      Counter32
    MAX-ACCESS    read-write
    STATUS      current
                DESCRIPTION
                                "This counter is incremented whenever a client connection request going from this process to a remote host and going through this interface has been rejected for a particular protocol."
                ::=  {  bwCommonCommPSStatsEntry  7  }

  bwCommonCommPSRejectedInboundConnections  OBJECT-TYPE
    SYNTAX      Counter32
    MAX-ACCESS    read-write
    STATUS      current
                DESCRIPTION
                                "This counter is incremented whenever a client connection request coming to this host and going through this interface has been rejected by the framework for a particular protocol."
                ::=  {  bwCommonCommPSStatsEntry  8  }

  bwCommonCommPSOutputMessagesProcessed OBJECT-TYPE
    SYNTAX      Counter32
    MAX-ACCESS    read-write
    STATUS      current
                DESCRIPTION
                                "This counter is incremented whenever a message has been sent and processed for this host, interface and protocol."
                ::=  {  bwCommonCommPSStatsEntry  9  }

  bwCommonCommPSInputMessagesProcessed  OBJECT-TYPE
    SYNTAX      Counter32
    MAX-ACCESS    read-write
    STATUS      current
                DESCRIPTION
                                "This counter is incremented whenever a message has been received and processed for this host, interface and protocol."
                ::=  {  bwCommonCommPSStatsEntry  10  }

  bwCommonCommPSOutputCommunicationErrors OBJECT-TYPE
    SYNTAX      Counter32
    MAX-ACCESS    read-write
    STATUS      current
                DESCRIPTION
                                "This counter is incremented whenever a message could not be read because the TCP stack returned an error."
                ::=  {  bwCommonCommPSStatsEntry  11  }

  bwCommonCommPSInputCommunicationErrors  OBJECT-TYPE
    SYNTAX      Counter32
    MAX-ACCESS    read-write
    STATUS      current
                DESCRIPTION
                                "This counter is incremented whenever a message has been sent and processed for this host, interface and protocol."
                ::=  {  bwCommonCommPSStatsEntry  12  }

-- PS - Concurrent Framework ........................

  bwPSMonitoringExecutorTable OBJECT-TYPE
    SYNTAX    SEQUENCE  OF  BwPSMonitoringExecutorEntry
    MAX-ACCESS  not-accessible
    STATUS    current
                DESCRIPTION
                        "This table contains counters for the concurrent framework."
                ::=  { psConcurrentStats  1 }

  bwPSMonitoringExecutorEntry OBJECT-TYPE
    SYNTAX    BwPSMonitoringExecutorEntry
    MAX-ACCESS  not-accessible
    STATUS    current
                DESCRIPTION
                        "Definition of the entries for bwPSMonitoringExecutorTable."
    INDEX   {  bwPSMonitoringExecutorIndex  }
                ::=  { bwPSMonitoringExecutorTable 1 }

        BwPSMonitoringExecutorEntry  ::=  SEQUENCE {
                bwPSMonitoringExecutorIndex  Unsigned32,
                bwPSMonitoringExecutorName   DisplayString,
                bwPSMonitoringExecutorCurrentPoolSize  Gauge32,
                bwPSMonitoringExecutorMaxPoolSize      Gauge32,
                bwPSMonitoringExecutorAvgActiveThreads Gauge32,
                bwPSMonitoringExecutorTaskQueueSize     Gauge32,
                bwPSMonitoringExecutorNbTasksRun       Counter32,
                bwPSMonitoringExecutorNbWarnings       Counter32,
                bwPSMonitoringExecutorNbErrors         Counter32,
                bwPSMonitoringExecutorLongestTaskMs    Gauge32,
                bwPSMonitoringExecutorLongestTaskName  DisplayString
                }

  bwPSMonitoringExecutorIndex OBJECT-TYPE
    SYNTAX      Unsigned32
    MAX-ACCESS    read-only
    STATUS      current
                DESCRIPTION
                                "This integer represents an index in table bwPSMonitoringExecutorTable. This is the index to a specific Monitoring Executor name."
                ::=  {  bwPSMonitoringExecutorEntry  1  }

  bwPSMonitoringExecutorName  OBJECT-TYPE
    SYNTAX      DisplayString
    MAX-ACCESS    read-only
    STATUS      current
                DESCRIPTION
                                "The name of the Monitoring Executor - Names are internally defined at the application level."
                ::=  {  bwPSMonitoringExecutorEntry  2  }

  bwPSMonitoringExecutorCurrentPoolSize OBJECT-TYPE
    SYNTAX      Gauge32
    MAX-ACCESS    read-only
    STATUS      current
                DESCRIPTION
                                "The current thread pool size"
                ::=  {  bwPSMonitoringExecutorEntry  3  }

  bwPSMonitoringExecutorMaxPoolSize OBJECT-TYPE
    SYNTAX      Gauge32
    MAX-ACCESS    read-only
    STATUS      current
                DESCRIPTION
                                "The maximum thread pool size"
                ::=  {  bwPSMonitoringExecutorEntry  4  }

  bwPSMonitoringExecutorAvgActiveThreads  OBJECT-TYPE
    SYNTAX      Gauge32
    MAX-ACCESS    read-only
    STATUS      current
                DESCRIPTION
                                "The average number of active threads, rounded up"
                ::=  {  bwPSMonitoringExecutorEntry  5  }

  bwPSMonitoringExecutorTaskQueueSize OBJECT-TYPE
    SYNTAX      Gauge32
    MAX-ACCESS    read-only
    STATUS      current
                DESCRIPTION
                                "Number of tasks in the queue (includes scheduled and recurring tasks)"
                ::=  {  bwPSMonitoringExecutorEntry  6  }

  bwPSMonitoringExecutorNbTasksRun  OBJECT-TYPE
    SYNTAX      Counter32
    MAX-ACCESS    read-write
    STATUS      current
                DESCRIPTION
                                "Number of tasks run"
                ::=  {  bwPSMonitoringExecutorEntry  7  }

  bwPSMonitoringExecutorNbWarnings  OBJECT-TYPE
    SYNTAX      Counter32
    MAX-ACCESS    read-write
    STATUS      current
                DESCRIPTION
                                "Number of warnings that occured"
                ::=  {  bwPSMonitoringExecutorEntry  8  }

  bwPSMonitoringExecutorNbErrors  OBJECT-TYPE
    SYNTAX      Counter32
    MAX-ACCESS    read-write
    STATUS      current
                DESCRIPTION
                                "Number of errors that occured"
                ::=  {  bwPSMonitoringExecutorEntry  9  }

  bwPSMonitoringExecutorLongestTaskMs OBJECT-TYPE
    SYNTAX      Gauge32
    MAX-ACCESS    read-only
    STATUS      current
                DESCRIPTION
                                "Longest completed task execution time in milliseconds"
                ::=  {  bwPSMonitoringExecutorEntry  10  }

  bwPSMonitoringExecutorLongestTaskName OBJECT-TYPE
    SYNTAX      DisplayString
    MAX-ACCESS    read-only
    STATUS      current
                DESCRIPTION
                                "Longest completed task name"
                ::=  {  bwPSMonitoringExecutorEntry  11  }

-- PS - TCP Framework ........................

  bwPSTcpServersStatsTable  OBJECT-TYPE
    SYNTAX    SEQUENCE  OF  BwPSTcpServersStatsEntry
    MAX-ACCESS  not-accessible
    STATUS    current
                DESCRIPTION
                        "This table contains counters for TCP underlying framework for the PS process."
                ::=  { psTcpStats  1 }

  bwPSTcpServersStatsEntry  OBJECT-TYPE
    SYNTAX    BwPSTcpServersStatsEntry
    MAX-ACCESS  not-accessible
    STATUS    current
                DESCRIPTION
                        "Definition of the entries for bwPSTcpServersStatsTable."
    INDEX   {  bwPSTcpServersStatsIndex  }
                ::=  { bwPSTcpServersStatsTable 1 }

        BwPSTcpServersStatsEntry  ::=  SEQUENCE {
                bwPSTcpServersStatsIndex  Unsigned32,
                bwPSTcpServersName  DisplayString,
                bwPSTcpServersNbConnectionsAccepted  Counter32,
                bwPSTcpServersNbConnectionsRefused  Counter32,
                bwPSTcpServersNbConnectionsInitiated  Counter32,
                bwPSTcpServersNbConnectionsClosed  Counter32,
                bwPSTcpServersNbBytesSent        Gauge32,
                bwPSTcpServersNbBytesReceived    Gauge32,
                bwPSTcpServersOutgoingQueueSize  Gauge32,
                bwPSTcpServersIncomingQueueSize  Gauge32,
                bwPSTcpServersNbBytesSentSecure Gauge32,
                bwPSTcpServersNbBytesReceivedSecure Gauge32
                }

  bwPSTcpServersStatsIndex  OBJECT-TYPE
    SYNTAX      Unsigned32
    MAX-ACCESS    read-only
    STATUS      current
                DESCRIPTION
                                "This integer represents an index in table bwPSTcpServersStatsTable. This is the index to a specific TCP server name."
                ::=  {  bwPSTcpServersStatsEntry  1  }

  bwPSTcpServersName  OBJECT-TYPE
    SYNTAX      DisplayString
    MAX-ACCESS    read-only
    STATUS      current
                DESCRIPTION
                                "The name of TCP server - Names are internally defined at at the application level."
                ::=  {  bwPSTcpServersStatsEntry  2  }

  bwPSTcpServersNbConnectionsAccepted OBJECT-TYPE
    SYNTAX      Counter32
    MAX-ACCESS    read-write
    STATUS      current
                DESCRIPTION
                                "This counter represents the number of connections accepted by the TCP server."
                ::=  {  bwPSTcpServersStatsEntry  3  }

  bwPSTcpServersNbConnectionsRefused  OBJECT-TYPE
    SYNTAX      Counter32
    MAX-ACCESS    read-write
    STATUS      current
                DESCRIPTION
                                "This counter represents the number of connections refused by the TCP server."
                ::=  {  bwPSTcpServersStatsEntry  4  }

  bwPSTcpServersNbConnectionsInitiated  OBJECT-TYPE
    SYNTAX      Counter32
    MAX-ACCESS    read-write
    STATUS      current
                DESCRIPTION
                                "This counter represents the number of connections initiated by the TCP server."
                ::=  {  bwPSTcpServersStatsEntry  5  }

  bwPSTcpServersNbConnectionsClosed OBJECT-TYPE
    SYNTAX      Counter32
    MAX-ACCESS    read-write
    STATUS      current
                DESCRIPTION
                                "This counter represents the number of connections closed by the TCP server or remote hosts."
                ::=  {  bwPSTcpServersStatsEntry  6  }

  bwPSTcpServersNbBytesSent OBJECT-TYPE
    SYNTAX      Gauge32
    MAX-ACCESS    read-write
    STATUS      current
                DESCRIPTION
                                "This counter represents the number of bytes sent by the TCP server."
                ::=  {  bwPSTcpServersStatsEntry  7  }

  bwPSTcpServersNbBytesReceived OBJECT-TYPE
    SYNTAX      Gauge32
    MAX-ACCESS    read-write
    STATUS      current
                DESCRIPTION
                                "This counter represents the number of bytes received by the TCP server."
                ::=  {  bwPSTcpServersStatsEntry  8  }

  bwPSTcpServersOutgoingQueueSize OBJECT-TYPE
    SYNTAX      Gauge32
    MAX-ACCESS    read-only
    STATUS      current
                DESCRIPTION
                                "This counter represents the number of bytes in the outgoing queue."
                ::=  {  bwPSTcpServersStatsEntry  9  }

  bwPSTcpServersIncomingQueueSize OBJECT-TYPE
    SYNTAX      Gauge32
    MAX-ACCESS    read-only
    STATUS      current
                DESCRIPTION
                                "This counter represents the number of bytes in the incoming queue."
                ::=  {  bwPSTcpServersStatsEntry  10  }


  bwPSTcpServersNbBytesSentSecure OBJECT-TYPE
    SYNTAX      Gauge32
    MAX-ACCESS  read-write
    STATUS      current
                DESCRIPTION
                                "This counter represents the number of bytes sent by the TCP server over secure connections."
                ::=  {  bwPSTcpServersStatsEntry  11  }

  bwPSTcpServersNbBytesReceivedSecure OBJECT-TYPE
    SYNTAX      Gauge32
    MAX-ACCESS  read-write
    STATUS      current
                DESCRIPTION
                                "This counter represents the number of bytes received by the TCP server over secure connections."
                ::=  {  bwPSTcpServersStatsEntry  12  }
-- PS Activatable feature ...........................................
                
  bwActivatableFeatureTable OBJECT-TYPE
    SYNTAX    SEQUENCE  OF  BwActivatableFeatureEntry
    MAX-ACCESS  not-accessible
    STATUS    current
                DESCRIPTION
                        "This table contains the activatable feature status."
                ::=  { psActivatableFeatureStats  1 }

  bwActivatableFeatureEntry OBJECT-TYPE
    SYNTAX    BwActivatableFeatureEntry
    MAX-ACCESS  not-accessible
    STATUS    current
                DESCRIPTION
                        "This row contains the activatable feature status."
    INDEX   {  bwActivatableFeatureIndex  }
                ::=  { bwActivatableFeatureTable 1 }

        BwActivatableFeatureEntry  ::=  SEQUENCE {
                bwActivatableFeatureIndex        Unsigned32,
                bwActivatableFeatureId           DisplayString,
                bwActivatableFeatureDescription  DisplayString,
                bwActivatableFeatureActivated    INTEGER
                }

  bwActivatableFeatureIndex OBJECT-TYPE
    SYNTAX      Unsigned32
    MAX-ACCESS    read-only
    STATUS      current
                DESCRIPTION
                                "This integer is an index of the activatable feature installed on the system."
                ::=  {  bwActivatableFeatureEntry  1  }

  bwActivatableFeatureId  OBJECT-TYPE
    SYNTAX      DisplayString
    MAX-ACCESS    read-only
    STATUS      current
                DESCRIPTION
                                "This string represents the activatable feature identifier."
                ::=  {  bwActivatableFeatureEntry  2  }

  bwActivatableFeatureDescription OBJECT-TYPE
    SYNTAX      DisplayString
    MAX-ACCESS    read-only
    STATUS      current
                DESCRIPTION
                                "This string holds the activatable feature's description."
                ::=  {  bwActivatableFeatureEntry  3  }

  bwActivatableFeatureActivated OBJECT-TYPE
    SYNTAX      INTEGER { notActive(0), active(1) }
    MAX-ACCESS    read-only
    STATUS      current
                DESCRIPTION
                                "This integer holds the state of the activatable feature."
                ::=  {  bwActivatableFeatureEntry  4  }

-- SH Interface module ...........................................

        bwShInterfaceRequestsIn OBJECT-TYPE
                SYNTAX                  Counter32
                MAX-ACCESS              read-write
                STATUS                  current
                DESCRIPTION
                                "This counter holds the number of times an Sh Interface request is received."
                ::=  {  psShInterfaceStats  1  }

        bwShInterfaceRequestsOut        OBJECT-TYPE
                SYNTAX                  Counter32
                MAX-ACCESS              read-write
                STATUS                  current
                DESCRIPTION
                                "This counter holds the number of times an Sh Interface request is transmitted."
                ::=  {  psShInterfaceStats  2  }

        bwShInterfaceResponsesIn        OBJECT-TYPE
                SYNTAX                  Counter32
                MAX-ACCESS              read-write
                STATUS                  current
                DESCRIPTION
                                "This counter holds the number of times an Sh Interface answer is received."
                ::=  {  psShInterfaceStats  3  }

        bwShInterfaceResponsesOut       OBJECT-TYPE
                SYNTAX                  Counter32
                MAX-ACCESS              read-write
                STATUS                  current
                DESCRIPTION
                                "This counter holds the number of times an Sh Interface answer is transmitted."
                ::=  {  psShInterfaceStats  4  }

        bwShInterfaceRequestTimeout     OBJECT-TYPE
                SYNTAX                  Counter32
                MAX-ACCESS              read-write
                STATUS                  current
                DESCRIPTION
                                "This counter holds the number of times an Sh Interface request timer expired prior to receipt of corresponding answer."
                ::=  {  psShInterfaceStats  5  }

        bwShInterfaceRequestResourceLimitation  OBJECT-TYPE
                SYNTAX                  Counter32
                MAX-ACCESS              read-write
                STATUS                  current
                DESCRIPTION
                                "This counter holds the number of times an Sh Interface request could not be sent due to local resource limitation."
                ::=  {  psShInterfaceStats  6  }

        bwShInterfaceUserDataRequest    OBJECT-TYPE
                SYNTAX                  Counter32
                MAX-ACCESS              read-write
                STATUS                  current
                DESCRIPTION
                                "This counter holds the number of times a User-Data-Request is transmitted."
                ::=  {  psShInterfaceStats  7  }

        bwShInterfaceUserDataRequestFailure     OBJECT-TYPE
                SYNTAX                  Counter32
                MAX-ACCESS              read-write
                STATUS                  current
                DESCRIPTION
                                "This counter holds the number of times the User-Data-Request resulted in a failure."
                ::=  {  psShInterfaceStats  8  }

        bwShInterfaceSubscribeNotificationsRequest      OBJECT-TYPE
                SYNTAX                  Counter32
                MAX-ACCESS              read-write
                STATUS                  current
                DESCRIPTION
                                "This counter holds the number of times a Subscribe-Notifications-Request is transmitted."
                ::=  {  psShInterfaceStats  9  }

        bwShInterfaceSubscribeNotificationsRequestFailure       OBJECT-TYPE
                SYNTAX                  Counter32
                MAX-ACCESS              read-write
                STATUS                  current
                DESCRIPTION
                                "This counter holds the number of times the Subscribe-Notifications-Request resulted in a failure."
                ::=  {  psShInterfaceStats  10  }

        bwShInterfacePushNotificationRequest    OBJECT-TYPE
                SYNTAX                  Counter32
                MAX-ACCESS              read-write
                STATUS                  current
                DESCRIPTION
                                "This counter holds the number of times a Push-Notification-Request is received."
                ::=  {  psShInterfaceStats  11  }

        bwShInterfacePushNotificationRequestFailure     OBJECT-TYPE
                SYNTAX                  Counter32
                MAX-ACCESS              read-write
                STATUS                  current
                DESCRIPTION
                                "This counter holds the number of times the Push-Notifications-Request resulted in a failure."
                ::=  {  psShInterfaceStats  12  }

        bwShInterfacePublicIdentityRefreshInitiated     OBJECT-TYPE
                SYNTAX                  Counter32
                MAX-ACCESS              read-write
                STATUS                  current
                DESCRIPTION
                                "This counter holds the number of times the Public Identity refresh procedure is dispatched."
                ::=  {  psShInterfaceStats  13  }

        bwShInterfacePublicIdentityRefreshFailure       OBJECT-TYPE
                SYNTAX                  Counter32
                MAX-ACCESS              read-write
                STATUS                  current
                DESCRIPTION
                                "This counter holds the number of times the Public Identity refresh procedure ended in failure."
                ::=  {  psShInterfaceStats  14  }

        bwShInterfaceSystemRefreshInitiated     OBJECT-TYPE
                SYNTAX                  Counter32
                MAX-ACCESS              read-write
                STATUS                  current
                DESCRIPTION
                                "This counter holds the number of times the system refresh procedure is dispatched."
                ::=  {  psShInterfaceStats  15  }

-- XSI Support for VoiceXML ..............................................
  psBwVMRNumLoginAttempts OBJECT-TYPE
    SYNTAX          Counter32
    MAX-ACCESS      read-write
    STATUS          current
    DESCRIPTION
      "This counter is incremented when the PS receives a request to verify authentication of user by DN and passcode."
    ::=  {  psVoiceMessaging  1  }

  psBwVMRNumLoginFailures  OBJECT-TYPE
    SYNTAX          Counter32
    MAX-ACCESS      read-write
    STATUS          current
    DESCRIPTION
      "This counter is incremented when the request to verify authentication of user by DN and passcode fails."
    ::=  {  psVoiceMessaging  2  }

-- XSI Support for VoiceXML SP statistics ...........................................

  psBwVMRSPEntry OBJECT-TYPE
    SYNTAX      PsBwVMRSPEntry
    MAX-ACCESS    not-accessible
    STATUS      current
                DESCRIPTION
                                "This row contains the voice messaging statistics for a given service provider in the system"
    INDEX   {  psBwVMRSPIndex  }
                ::=  { psBwVMRSPTable 1 }

  PsBwVMRSPEntry  ::=  SEQUENCE {
    psBwVMRSPIndex  Unsigned32,
    psBwVMRSPID     DisplayString,
    psBwVMRSPNumLoginAttempts Counter32,
    psBwVMRSPNumLoginFailures Counter32
  }

  psBwVMRSPTable  OBJECT-TYPE
    SYNTAX    SEQUENCE  OF  PsBwVMRSPEntry
    MAX-ACCESS  not-accessible
    STATUS    current
    DESCRIPTION
            "This table contains the counters for PS Voice Messaging measurements for service providers"
    ::=  { psVoiceMessaging  3 }

  psBwVMRSPIndex  OBJECT-TYPE
    SYNTAX      Unsigned32
    MAX-ACCESS  read-only
    STATUS      current
    DESCRIPTION
      "This integer represents a service provider index in the system"
    ::=  {  psBwVMRSPEntry  1  }

  psBwVMRSPID OBJECT-TYPE
    SYNTAX       DisplayString
    MAX-ACCESS   read-only
    STATUS       current
    DESCRIPTION
      "This string represents a Service Provider ID."
    ::=  {  psBwVMRSPEntry  2  }

  psBwVMRSPNumLoginAttempts OBJECT-TYPE
    SYNTAX          Counter32
    MAX-ACCESS      read-write
    STATUS          current
    DESCRIPTION
      "This counter is incremented when the PS receives a request to verify authentication of user by DN and passcode under the service provider."
    ::=  {  psBwVMRSPEntry  3  }

  psBwVMRSPNumLoginFailures  OBJECT-TYPE
    SYNTAX          Counter32
    MAX-ACCESS      read-write
    STATUS          current
    DESCRIPTION
      "This counter is incremented when the request to verify authentication of user by DN and passcode fails under the service provider."
    ::=  {  psBwVMRSPEntry  4  }

-- XSI Support for VoiceXML Group statistics ...........................................

  psBwVMRGroupEntry OBJECT-TYPE
    SYNTAX      PsBwVMRGroupEntry
    MAX-ACCESS    not-accessible
    STATUS      current
                DESCRIPTION
                                "This row contains the voice messaging statistics for a given service provider in the system"
    INDEX   {  psBwVMRGroupIndex  }
                ::=  { psBwVMRGroupTable 1 }

  PsBwVMRGroupEntry  ::=  SEQUENCE {
    psBwVMRGroupIndex  Unsigned32,
    psBwVMRGroupID     DisplayString,
    psBwVMRGroupNumLoginAttempts Counter32,
    psBwVMRGroupNumLoginFailures Counter32
  }

  psBwVMRGroupTable  OBJECT-TYPE
    SYNTAX    SEQUENCE  OF  PsBwVMRGroupEntry
    MAX-ACCESS  not-accessible
    STATUS    current
    DESCRIPTION
            "This table contains the counters for PS Voice Messaging measurements for groups"
    ::=  { psVoiceMessaging  4 }

  psBwVMRGroupIndex  OBJECT-TYPE
    SYNTAX      Unsigned32
    MAX-ACCESS  read-only
    STATUS      current
    DESCRIPTION
      "This integer represents a service provider index in the system"
    ::=  {  psBwVMRGroupEntry  1  }

  psBwVMRGroupID OBJECT-TYPE
    SYNTAX       DisplayString
    MAX-ACCESS   read-only
    STATUS       current
    DESCRIPTION
      "This string represents a Group ID."
    ::=  {  psBwVMRGroupEntry  2  }

  psBwVMRGroupNumLoginAttempts OBJECT-TYPE
    SYNTAX          Counter32
    MAX-ACCESS      read-write
    STATUS          current
    DESCRIPTION
      "This counter is incremented when the PS receives a request to verify authentication of user by DN and passcode under the group."
    ::=  {  psBwVMRGroupEntry  3  }

  psBwVMRGroupNumLoginFailures  OBJECT-TYPE
    SYNTAX          Counter32
    MAX-ACCESS      read-write
    STATUS          current
    DESCRIPTION
      "This counter is incremented when the request to verify authentication of user by DN and passcode fails under the group."
    ::=  {  psBwVMRGroupEntry  4  }

-- Polycom Phone Service  .........................
  bwPolycomPhoneDirectoryNumDownloads OBJECT-TYPE
                SYNTAX  Counter32
                MAX-ACCESS read-write
                STATUS  current
                DESCRIPTION
                  "This counter reflects the number of times devices download a Polycom phone directory from the system."
                ::= { polycomPhoneServices 1 }

-- Polycom Phone Service SP statistics ...........................................
  polycomSPTableEntry  OBJECT-TYPE
                SYNTAX          PolycomSPTableEntry
                MAX-ACCESS      not-accessible
                STATUS          current
                DESCRIPTION
                        "Each row contains the service counters for the Polycom Phone service for each service provider in the system"
                INDEX           {  polycomSPIndex  }
                ::=  { polycomSPTable 1 }

  PolycomSPTableEntry  ::=  SEQUENCE {
    polycomSPIndex Unsigned32,
    polycomSPID    DisplayString,
    bwPolycomPhoneDirectorySPNumDownloads     Counter32 }

  polycomSPTable  OBJECT-TYPE
                SYNTAX                  SEQUENCE  OF  PolycomSPTableEntry
                MAX-ACCESS              not-accessible
                STATUS                  current
                DESCRIPTION
                        "Each row contains the service counters for the Polycom Phone service for each service provider in the system"
                ::=  { polycomPhoneServices 2 }

  polycomSPIndex  OBJECT-TYPE
                SYNTAX                  Unsigned32
                MAX-ACCESS              read-only
                STATUS                  current
                DESCRIPTION
                                "This column represents the index of the Service Provider in the system."
                ::=  {  polycomSPTableEntry  1  }

  polycomSPID OBJECT-TYPE
                SYNTAX                  DisplayString
                MAX-ACCESS              read-only
                STATUS                  current
                DESCRIPTION
                                "This string represents a Service Provider ID."
                ::=  {  polycomSPTableEntry  2  }
                
  bwPolycomPhoneDirectorySPNumDownloads OBJECT-TYPE
                SYNTAX  Counter32
                MAX-ACCESS read-write
                STATUS  current
                DESCRIPTION
                  "This counter reflects the number of times devices download a Polycom phone directory from the system, one counter per service provider/enterprise."
                ::= { polycomSPTableEntry 3 }

-- Polycom Phone Service Group statistics ...........................................
  polycomGroupTableEntry  OBJECT-TYPE
                SYNTAX          PolycomGroupTableEntry
                MAX-ACCESS      not-accessible
                STATUS          current
                DESCRIPTION
                        "Each row contains the service counters for the Polycom Phone service for each group in the system"
                INDEX           {  polycomGroupIndex  }
                ::=  { polycomGroupTable 1 }

  polycomGroupTable   OBJECT-TYPE
                SYNTAX                  SEQUENCE  OF  PolycomGroupTableEntry
                MAX-ACCESS              not-accessible
                STATUS                  current
                DESCRIPTION
                        "Each row contains the service counters for the Polycom Phone service for each group in the system"
                ::=  { polycomPhoneServices 3 }

  PolycomGroupTableEntry  ::=  SEQUENCE {
    polycomGroupIndex Unsigned32,
    polycomGroupID    DisplayString,  
    bwPolycomPhoneDirectoryGroupNumDownloads     Counter32 }

  polycomGroupIndex  OBJECT-TYPE
                SYNTAX                  Unsigned32
                MAX-ACCESS              read-only
                STATUS                  current
                DESCRIPTION
                                "This column represents the index of the Group in the system."
                ::=  {  polycomGroupTableEntry  1  }

  polycomGroupID OBJECT-TYPE
                SYNTAX                  DisplayString
                MAX-ACCESS              read-only
                STATUS                  current
                DESCRIPTION
                                "This string represents a Group ID."
                ::=  {  polycomGroupTableEntry  2  }
                
  bwPolycomPhoneDirectoryGroupNumDownloads OBJECT-TYPE
                SYNTAX  Counter32
                MAX-ACCESS read-write
                STATUS  current
                DESCRIPTION
                  "This counter reflects the number of times devices download a Polycom phone directory from the system, one counter per group."
                ::= { polycomGroupTableEntry 3 }               

-- Management module ...........................................

  resetAllCounters  OBJECT-TYPE
    SYNTAX      Counter32
    MAX-ACCESS    read-write
    STATUS      current
    DESCRIPTION "When set to a value other then 0, all the counters in the system are reset to 0."
                ::=  {  management  1  }


-- Management module ...........................................

  psReservedCounter OBJECT-TYPE
    SYNTAX      Counter32
    MAX-ACCESS    read-only
    STATUS      obsolete
    DESCRIPTION "Temporary place holder. Unused counter."
                ::=  {  psReservedModule  1 }

-- BroadWorks Application Server MIB Conformance Definition  ...........................................

bwAsMibGroups   OBJECT IDENTIFIER ::= { bwAsMibConformance 1 }
bwAsMibCompliancy OBJECT IDENTIFIER ::= { bwAsMibConformance 2 }

-- units of conformance

bwAsMgcpGroup    OBJECT-GROUP
    OBJECTS { bwMGCPStatsMGCPCommandOuts, bwMGCPStatsMGCPCommandIns, bwMGCPStatsMGCPResponseOuts, bwMGCPStatsMGCPResponseIns, bwMGCPStatsAuditConnectionOuts, bwMGCPStatsAuditEndpointOuts, bwMGCPStatsCreateConnectionOuts, bwMGCPStatsDeleteAgentConnectionOuts, bwMGCPStatsDeleteConnectionOuts, bwMGCPStatsDeleteGatewayConnectionIns, bwMGCPStatsEndpointConfigurationOuts, bwMGCPStatsExtraCommandOuts, bwMGCPStatsModifyConnectionOuts, bwMGCPStatsNotificationRequestOuts, bwMGCPStatsNotifyIns, bwMGCPStatsRestartInProgressIns, bwMGCPStatsMGCPCommandResponseTable, bwMGCPStatsMGCPCommandResponseCodeValue, bwMGCPStatsMGCPCommandResponseOuts, bwMGCPStatsMGCPCommandResponseIns, bwMGCPStatsAuditConnectionResponseTable, bwMGCPStatsAuditConnectionResponseCodeValue, bwMGCPStatsAuditConnectionResponseIns, bwMGCPStatsAuditEndpointResponseTable, bwMGCPStatsAuditEndpointResponseCodeValue, bwMGCPStatsAuditEndpointResponseIns, bwMGCPStatsCreateConnectionResponseTable, bwMGCPStatsCreateConnectionResponseCodeValue, bwMGCPStatsCreateConnectionResponseIns, bwMGCPStatsDeleteConnectionResponseTable, bwMGCPStatsDeleteConnectionResponseCodeValue, bwMGCPStatsDeleteAgentConnectionResponseIns, bwMGCPStatsDeleteConnectionResponseIns, bwMGCPStatsDeleteGatewayConnectionResponseOuts, bwMGCPStatsEndpointConfigurationResponseTable, bwMGCPStatsEndpointConfigurationResponseCodeValue, bwMGCPStatsEndpointConfigurationResponseIns, bwMGCPStatsExtraCommandResponseTable, bwMGCPStatsExtraCommandResponseCodeValue, bwMGCPStatsExtraCommandResponseIns, bwMGCPStatsModifyConnectionResponseTable, bwMGCPStatsModifyConnectionResponseCodeValue, bwMGCPStatsModifyConnectionResponseIns, bwMGCPStatsNotificationRequestResponseTable, bwMGCPStatsNotificationRequestResponseCodeValue, bwMGCPStatsNotificationRequestResponseIns, bwMGCPStatsNotifyResponseTable, bwMGCPStatsNotifyResponseCodeValue, bwMGCPStatsNotifyResponseOuts, bwMGCPStatsRestartInProgressResponseTable, bwMGCPStatsRestartInProgressResponseCodeValue, bwMGCPStatsRestartInProgressResponseOuts, bwMGCPStatsDialToneDelay, bwMGCPStatsMinDialToneDelay, bwMGCPStatsMaxDialToneDelay, bwMGCPStatsSetupSignalDelay, bwMGCPStatsMinSetupSignalDelay, bwMGCPStatsMaxSetupSignalDelay, bwMGCPStatsAnswerSignalDelay, bwMGCPStatsMinAnswerSignalDelay, bwMGCPStatsMaxAnswerSignalDelay, bwMGCPStatsMessageRetryPercentage }
    STATUS  current
    DESCRIPTION
       "This group defines the statistics for the MGCP protocol."
    ::= { bwAsMibGroups 1 }

bwAsMcpGroup    OBJECT-GROUP
    OBJECTS { bwMCPCommandsTransmitted, bwMCPCommandsRetransmitted, bwMCPNotificationsReceived, bwMCPResourceAllocAttempts, bwMCPResourceAllocFailures }
    STATUS  current
    DESCRIPTION
       "This group defines the statistics for the MCP protocol."
    ::= { bwAsMibGroups 2 }

bwAsImsGroup    OBJECT-GROUP
    OBJECTS { bwIMSSuccessfulConnectionAttempts, bwIMSUnsuccessfulConnectionAttempts, bwIMSSuccessfulDownLoadAttempts, bwIMSUnsuccessfulDownLoadAttempts, bwIMSMaxSessions, bwIMSAvgSessions, bwIMSMaxThreads, bwIMSAvgThreads, bwIMSMaxServiceTime, bwIMSAvgServiceTime, bwIMSNumKeepAlive, bwIMSNumDroppedRequests }
    STATUS  current
    DESCRIPTION
       "This group defines the statistics for the IMS protocol."
    ::= { bwAsMibGroups 3 }

bwAsCapGroup    OBJECT-GROUP
    OBJECTS { bwCAPStatsRegisterRequests, bwCAPStatsUnRegistersIn, bwCAPStatsUnRegistersOut, bwCAPStatsSessionUpdatesOut, bwCAPStatsProfileUpdatesOut, bwCAPStatsCallUpdatesOut, bwCAPStatsCallActionsIn, bwCAPStatsAcknowledgementsIn, bwCAPStatsAcknowledgementsOut, bwCAPStatsAclViolations, bwCAPStatsUnsuccessfulRegisterResponses, bwCAPStatsRegisterResponsesTable, bwCAPStatsCallControlInfosOut, bwCAPStatsRegisterAuthentications, bwCAPStatsResponseAuthentications, bwCAPStatsInfoRequests, bwCAPStatsInfoResponses, bwCAPStatsExternalNotifies, bwCAPMonitoringUsersRequests, bwCAPMonitoringUsersResponses, bwCAPStatsQueueUpdatesOut, bwCAPStatsQueueActionsIn, bwCAPStatsDatagramsIn, bwCAPStatsDatagramsOut, bwCAPStatsTotalMsgs, bwCAPStatsRegisterResponsesType, bwCAPStatsRegisterResponses }
    STATUS  current
    DESCRIPTION
       "This group defines the statistics for the CAP protocol."
    ::= { bwAsMibGroups 4 }

bwAsSmdiGroup    OBJECT-GROUP
    OBJECTS { bwSmdiNbOfActiveConnection, bwSmdiNbOfOpenedConnection, bwSmdiIncomingMWIActivationRequests, bwSmdiIncomingMWIDesactivationRequests, bwSmdiInvalidRequestsReceived, bwSmdiBlockResponsesSent, bwSmdiInvalidResponsesSent, bwSmdiOutgoingMWIActivationRequests, bwSmdiOutgoingMWIDeactivationRequests, bwSmdiBlockResponsesReceived, bwSmdiInvalidResponsesReceived, bwSMDIMessageDeskMessageSent }
    STATUS  current
    DESCRIPTION
       "This group defines the statistics for the SMDI protocol."
    ::= { bwAsMibGroups 5 }

bwAsMediaResourceGroup    OBJECT-GROUP
    OBJECTS { bwMediaCommandsTransmitted, bwMediaNotificationsReceived, bwMediaResourceAllocAttempts, bwMediaResourceAllocFailures }
    STATUS  current
    DESCRIPTION
       "This group defines the statistics for the Media Resource protocol."
    ::= { bwAsMibGroups 6 }

bwAsWholeSalesGroup    OBJECT-GROUP
    OBJECTS { bwWSPStatsServiceRequestsIn, bwWSPStatsServiceActionsOut, bwWSPStatsServiceUpdatesIn, bwWSPStatsServiceAcknowledgementsOut }
    STATUS  current
    DESCRIPTION
       "This group defines the statistics for the Whole Sales protocol."
    ::= { bwAsMibGroups 7 }

bwAsRealTimeAccntGroup    OBJECT-GROUP
    OBJECTS { bwRealtimeAccountingRequestsTransmitted, bwRealtimeAccountingRequestsRetransmitted, bwRealtimeAccountingRequestsDropped }
    STATUS  current
    DESCRIPTION
       "This group defines the statistics for the Real Time Accounting protocol."
    ::= { bwAsMibGroups 8 }

bwAsExtCallLogsGroup    OBJECT-GROUP
    OBJECTS { bwExternalCallLogsTransmitted, bwExternalCallLogsRetransmitted, bwExternalCallLogsDropped }
    STATUS  current
    DESCRIPTION
       "This group defines the statistics for the External Call Logs protocol."
    ::= { bwAsMibGroups 9 }

bwAsXsBcctGroup    OBJECT-GROUP
    OBJECTS { bwCommonCommXSStatsTable, bwCommonCommXSStatsIndex, bwCommonCommXSHost, bwCommonCommXSInterface, bwCommonCommXSProtocol, bwCommonCommXSAcceptedOutboundConnections, bwCommonCommXSAcceptedInboundConnections, bwCommonCommXSRejectedOutboundConnections, bwCommonCommXSRejectedInboundConnections, bwCommonCommXSOutputMessagesProcessed, bwCommonCommXSInputMessagesProcessed, bwCommonCommXSOutputCommunicationErrors, bwCommonCommXSInputCommunicationErrors }
    STATUS  current
    DESCRIPTION
       "This group defines the statistics for the BCCT protocol for the Application Server Execution Server process."
    ::= { bwAsMibGroups 10 }

bwAsCpeDeviceGroup    OBJECT-GROUP
    OBJECTS { bwCPEDeviceStatsTable, bwCPEDeviceStatsIndex, bwCPEDeviceName, bwCPEDeviceReset, bwCPEDeviceFileRebuilt }
    STATUS  current
    DESCRIPTION
       "This group defines the statistics for CPE Device Management."
    ::= { bwAsMibGroups 11 }

bwAsCallpGroup    OBJECT-GROUP
    OBJECTS { bwCallpNetworkOriginationAttempts, bwCallpNetworkTerminationAttempts, bwCallpNetworkTerminationsAnswered, bwCallpUserOriginationAttempts, bwCallpUserTerminationAttempts, bwCallpUserTerminationsAnswered, bwCallpEmergencyCallAttempts, bwCallpEmergencyCallAlarms, bwCallpSPTable, bwCallpActiveCalls, bwCallpGroupTable, bwCallpCallsPerSecond, bwCallpMaximumNumberofSimCallsExceeded, bwCallpMaximumCallTimeforAnsweredCallsExceeded, bwCallpMaximumCallTimeforUnansweredCallsExceeded, bwCallpActiveCallsAsPercentOfLicense, bwCallpMaximumNumberofSimVideoCallsExceeded, bwCallpMediaTypeNotSupported, bwCallpSPIndex, bwCallpSPID, bwCallpSPUserOriginationAttempts, bwCallpSPUserTerminationAttempts, bwCallpSPUserTerminationsAnswered, bwCallpSPEmergencyCallAttempts, bwCallpSPMaximumNumberofSimCallsExceeded, bwCallpSPMaximumCallTimeforAnsweredCallsExceeded, bwCallpSPMaximumCallTimeforUnansweredCallsExceeded, bwCallpSPMaximumNumberofSimVideoCallsExceeded, bwCallpSPMediaTypeNotSupported, bwCallpGroupIndex, bwCallpGroupID, bwCallpGroupUserOriginationAttempts, bwCallpGroupUserTerminationAttempts, bwCallpGroupUserTerminationsAnswered, bwCallpGroupEmergencyCallAttempts, bwCallpGroupMaximumNumberofSimCallsExceeded, bwCallpGroupMaximumCallTimeforAnsweredCallsExceeded, bwCallpGroupMaximumCallTimeforUnansweredCallsExceeded, bwCallpGroupMaximumNumberofSimVideoCallsExceeded, bwCallpGroupMediaTypeNotSupported }
    STATUS  current
    DESCRIPTION
       "This group defines the statistics for call processing."
    ::= { bwAsMibGroups 12 }

bwAsSmtpGroup    OBJECT-GROUP
    OBJECTS { bwSMTPTotalPrimaryEmailSendAttempts, bwSMTPTotalSecondaryEmailSendAttempts, bwSMTPPrimaryUnSuccessfulEmailSendAttempts, bwSMTPSecondaryUnSuccessfulEmailSendAttempts }
    STATUS  current
    DESCRIPTION
       "This group defines the statistics for the SMTP protocol."
    ::= { bwAsMibGroups 13 }

bwAsSipGroup    OBJECT-GROUP
    OBJECTS { bwSipSummaryTotalTransactions, bwSipStatsInviteIns, bwSipStatsInviteOuts, bwSipStatsAckIns, bwSipStatsAckOuts, bwSipStatsByeIns, bwSipStatsByeOuts, bwSipStatsCancelIns, bwSipStatsCancelOuts, bwSipStatsOptionsIns, bwSipStatsOptionsOuts, bwSipStatsRegisterIns, bwSipStatsRegisterOuts, bwSipStatsInfoIns, bwSipStatsInfoOuts, bwSipStatsNotifyIns, bwSipStatsNotifyOuts, bwSipStatsPrackIns, bwSipStatsPrackOuts, bwSipStatsOtherIns, bwSipStatsOtherOuts, bwSipStatsInviteResponsesTable, bwSipStatsInviteResponseCodeValue, bwSipStatsInviteResponseIns, bwSipStatsInviteResponseOuts, bwSipStatsByeResponsesTable, bwSipStatsByeResponseCodeValue, bwSipStatsByeResponseIns, bwSipStatsByeResponseOuts, bwSipStatsCancelResponsesTable, bwSipStatsCancelResponseCodeValue, bwSipStatsCancelResponseIns, bwSipStatsCancelResponseOuts, bwSipStatsOptionsResponsesTable, bwSipStatsOptionsResponseCodeValue, bwSipStatsOptionsResponseIns, bwSipStatsOptionsResponseOuts, bwSipStatsRegisterResponsesTable, bwSipStatsRegisterResponseCodeValue, bwSipStatsRegisterResponseIns, bwSipStatsRegisterResponseOuts, bwSipStatsPrackResponsesTable, bwSipStatsPrackResponseCodeValue, bwSipStatsPrackResponseIns, bwSipStatsPrackResponseOuts, bwSipStatsInfoResponsesTable, bwSipStatsInfoResponseCodeValue, bwSipStatsInfoResponseIns, bwSipStatsInfoResponseOuts, bwSipStatsNotifyResponsesTable, bwSipStatsNotifyResponseCodeValue, bwSipStatsNotifyResponseIns, bwSipStatsNotifyResponseOuts, bwSipStatsOtherResponsesTable, bwSipStatsOtherResponseCodeValue, bwSipStatsOtherResponseIns, bwSipStatsOtherResponseOuts, bwSipStatsRetryInvites, bwSipStatsRetryByes, bwSipStatsRetryCancels, bwSipStatsRetryResponses, bwSipStatsSubscribeIns, bwSipStatsSubscribeOuts, bwSipStatsMessageIns, bwSipStatsMessageOuts, bwSipStatsSubscribeResponsesTable, bwSipStatsSubscribeResponseCodeValue, bwSipStatsSubscribeResponseIns, bwSipStatsSubscribeResponseOuts, bwSipStatsMessageResponsesTable, bwSipStatsMessageResponseCodeValue, bwSipStatsMessageResponseIns, bwSipStatsMessageResponseOuts, bwSipStatsUpdateIns, bwSipStatsUpdateOuts, bwSipStatsUpdateResponseTable, bwSipStatsUpdateResponseCodeValue, bwSipStatsUpdateResponseIns, bwSipStatsUpdateResponseOuts, bwSipStatsSetupSignalDelay, bwSipStatsMinSetupSignalDelay, bwSipStatsMaxSetupSignalDelay, bwSipStatsAnswerSignalDelay, bwSipStatsMinAnswerSignalDelay, bwSipStatsMaxAnswerSignalDelay, bwSipStatsRegistrationsPerMinute, bwSipStatsMsgRetryPercentageToOther, bwSipStatsMsgRetryToNeTable, bwSipStatsMsgRetryToNeID, bwSipStatsMsgRetryToNeAddr, bwSipStatsMsgRetryToNePercentage, bwSipStatsActiveTcpConnections, bwSipStatsTcpIns, bwSipStatsTcpOuts, bwSipStatsTcpFailures, bwSipStatsUdpIns, bwSipStatsUdpOuts, bwSIPReclaimedStaleTcpConnections, bwSIPTcpTotalConnections }
    STATUS  current
    DESCRIPTION
       "This group defines the statistics for the SIP protocol."
    ::= { bwAsMibGroups 14 }

bwAsAccntCodeServiceGroup    OBJECT-GROUP
    OBJECTS { bwAuthCodeNumAttempts, bwAuthCodeNumValidations, bwAccountCodeNumAttempts, bwAccountCodesSPTable, bwAccountCodesGroupTable, bwAccountCodeNumPerCallAttempts, bwAccountCodesSPIndex, bwAccountCodesSPID, bwAuthCodeSPNumAttempts, bwAuthCodeSPNumValidations, bwAccountCodeSPNumAttempts, bwAccountCodeSPNumPerCallAttempts, bwAccountCodesGroupIndex, bwAccountCodesGroupID, bwAuthCodeGroupNumAttempts, bwAuthCodeGroupNumValidations, bwAccountCodeGroupNumAttempts, bwAccountCodeGroupNumPerCallAttempts }
    STATUS  current
    DESCRIPTION
       "This group defines the statistics for the Account Code Service."
    ::= { bwAsMibGroups 15 }

bwAsAnonymousCallRejectionServiceGroup    OBJECT-GROUP
    OBJECTS { bwAnonymousCallsNumRejected, bwAnonymousCallRejectionSPTable, bwAnonymousCallRejectionGroupTable, bwAnonymousCallRejectionSPIndex, bwAnonymousCallRejectionSPID, bwAnonymousCallsSPNumRejected, bwAnonymousCallRejectionGroupIndex, bwAnonymousCallRejectionGroupID, bwAnonymousCallsGroupNumRejected }
    STATUS  current
    DESCRIPTION
       "This group defines the statistics for the Anonymous Call Rejection Service."
    ::= { bwAsMibGroups 16 }

bwAsAuthenticationServiceGroup    OBJECT-GROUP
    OBJECTS { bwAuthenticationNumChallenges, bwAuthenticationNumValidResponses, bwAuthenticationSPTable, bwAuthenticationGroupTable, bwAuthenticationSPIndex, bwAuthenticationSPID, bwAuthenticationSPNumChallenges, bwAuthenticationSPNumValidResponses, bwAuthenticationGroupIndex, bwAuthenticationGroupID, bwAuthenticationGroupNumChallenges, bwAuthenticationGroupNumValidResponses }
    STATUS  current
    DESCRIPTION
       "This group defines the statistics for the Authentication Service."
    ::= { bwAsMibGroups 17 }

bwAsAutoAttendantServiceGroup    OBJECT-GROUP
    OBJECTS { bwAutoAttendantNumAnswers, bwAutoAttendantNumTransfers, bwAutoAttendantSPTable, bwAutoAttendantGroupTable, bwAutoAttendantSPIndex, bwAutoAttendantSPID, bwAutoAttendantSPNumAnswers, bwAutoAttendantSPNumTransfers, bwAutoAttendantGroupIndex, bwAutoAttendantGroupID, bwAutoAttendantGroupNumAnswers, bwAutoAttendantGroupNumTransfers }
    STATUS  current
    DESCRIPTION
       "This group defines the statistics for the Auto Attendant Service."
    ::= { bwAsMibGroups 18 }

bwAsCallCapacityServiceGroup    OBJECT-GROUP
    OBJECTS { bwCallCapacityNumCallsAttempted, bwCallCapacityNumCallsBlocked, bwCallCapacitySPTable, bwCallCapacityGroupTable, bwCallCapacitySPIndex, bwCallCapacitySPID, bwCallCapacitySPNumCallsAttempted, bwCallCapacitySPNumCallsBlocked, bwCallCapacityGroupIndex, bwCallCapacityGroupID, bwCallCapacityGroupNumCallsAttempted, bwCallCapacityGroupNumCallsBlocked }
    STATUS  current
    DESCRIPTION
       "This group defines the statistics for the Call Capacity Service."
    ::= { bwAsMibGroups 19 }

bwAsCFAlwaysServiceGroup    OBJECT-GROUP
    OBJECTS { bwCFANumForwarded, bwCFANumPhoneActivations, bwCFANumPhoneDeactivations, bwCallForwardingAlwaysSPTable, bwCFADestinationChanged, bwCallForwardingAlwaysGroupTable, bwCallForwardingAlwaysSPIndex, bwCallForwardingAlwaysSPID, bwCFASPNumForwarded, bwCFASPNumPhoneActivations, bwCFASPNumPhoneDeactivations, bwCFASPDestinationChanged, bwCallForwardingAlwaysGroupIndex, bwCallForwardingAlwaysGroupID, bwCFAGroupNumForwarded, bwCFAGroupNumPhoneActivations, bwCFAGroupNumPhoneDeactivations, bwCFAGroupDestinationChanged }
    STATUS  current
    DESCRIPTION
       "This group defines the statistics for the Call Forward Always Service."
    ::= { bwAsMibGroups 20 }

bwAsCFBusyServiceGroup    OBJECT-GROUP
    OBJECTS { bwCFBNumForwarded, bwCallForwardingBusySPTable, bwCFBNumPhoneActivations, bwCFBNumPhoneDeactivations, bwCFBDestinationChanged, bwCallForwardingBusyGroupTable, bwCallForwardingBusySPIndex, bwCallForwardingBusySPID, bwCFBSPNumForwarded, bwCFBSPNumPhoneActivations, bwCFBSPNumPhoneDeactivations, bwCFBSPDestinationChanged, bwCallForwardingBusyGroupIndex, bwCallForwardingBusyGroupID, bwCFBGroupNumForwarded, bwCFBGroupNumPhoneActivations, bwCFBGroupNumPhoneDeactivations, bwCFBGroupDestinationChanged }
    STATUS  current
    DESCRIPTION
       "This group defines the statistics for the Call Forward Busy Service."
    ::= { bwAsMibGroups 21 }

bwAsCFNoAnswerServiceGroup    OBJECT-GROUP
    OBJECTS { bwCFNANumForwarded, bwCallForwardingNoAnswerSPTable, bwCFNADestinationChanged, bwCFNANumPhoneActivations, bwCFNANumPhoneDeactivations, bwCallForwardingNoAnswerGroupTable, bwCallForwardingNoAnswerSPIndex, bwCallForwardingNoAnswerSPID, bwCFNASPNumForwarded, bwCFNASPDestinationChanged, bwCFNASPNumPhoneActivations, bwCFNASPNumPhoneDeactivations, bwCallForwardingNoAnswerGroupIndex, bwCallForwardingNoAnswerGroupID, bwCFNAGroupNumForwarded, bwCFNAGroupDestinationChanged, bwCFNAGroupNumPhoneActivations, bwCFNAGroupNumPhoneDeactivations }
    STATUS  current
    DESCRIPTION
       "This group defines the statistics for the Call Forward No-Answer Service."
    ::= { bwAsMibGroups 22 }

bwAsCallNotifyServiceGroup    OBJECT-GROUP
    OBJECTS { bwCallNotifyNumNotifications, bwCallNotifySPTable, bwCallNotifyGroupTable, bwCallNotifySPIndex, bwCallNotifySPID, bwCallNotifySPNumNotifications, bwCallNotifyGroupIndex, bwCallNotifyGroupID, bwCallNotifyGroupNumNotifications }
    STATUS  current
    DESCRIPTION
       "This group defines the statistics for the Call Notify Service."
    ::= { bwAsMibGroups 23 }

bwAsCallParkServiceGroup    OBJECT-GROUP
    OBJECTS { bwCallParkNumAttempts, bwCallParkNumFailures, bwCallParkNumRetrieveAttempts, bwCallParkNumRetrieveFailures, bwCallParkSPTable, bwCallParkGroupTable, bwCallParkSPIndex, bwCallParkSPID, bwCallParkSPNumAttempts, bwCallParkSPNumFailures, bwCallParkSPNumRetrieveAttempts, bwCallParkSPNumRetrieveFailures, bwCallParkGroupIndex, bwCallParkGroupID, bwCallParkGroupNumAttempts, bwCallParkGroupNumFailures, bwCallParkGroupNumRetrieveAttempts, bwCallParkGroupNumRetrieveFailures }
    STATUS  current
    DESCRIPTION
       "This group defines the statistics for the Call Park Service."
    ::= { bwAsMibGroups 24 }

bwAsCallPickupServiceGroup    OBJECT-GROUP
    OBJECTS { bwCallPickupNumAttempts, bwCallPickupNumFailures, bwCallPickupSPTable, bwCallPickupGroupTable, bwCallPickupSPIndex, bwCallPickupSPID, bwCallPickupSPNumAttempts, bwCallPickupSPNumFailures, bwCallPickupGroupIndex, bwCallPickupGroupID, bwCallPickupGroupNumAttempts, bwCallPickupGroupNumFailures }
    STATUS  current
    DESCRIPTION
       "This group defines the statistics for the Call Pickup Service."
    ::= { bwAsMibGroups 25 }

bwAsCallReturnServiceGroup    OBJECT-GROUP
    OBJECTS { bwCallReturnNumReturns, bwCallReturnSPTable, bwCallReturnGroupTable, bwCallReturnSPIndex, bwCallReturnSPID, bwCallReturnSPNumReturns, bwCallReturnGroupIndex, bwCallReturnGroupID, bwCallReturnGroupNumReturns }
    STATUS  current
    DESCRIPTION
       "This group defines the statistics for the Call Return Service."
    ::= { bwAsMibGroups 26 }

bwAsCompilotCallMgrServiceGroup    OBJECT-GROUP
    OBJECTS { bwCommPilotCallMgrNumDial, bwCommPilotCallMgrNumAnswer, bwCommPilotCallMgrNumRelease, bwCommPilotCallMgrNumHold, bwCommPilotCallMgrNumTransfer, bwCommPilotCallMgrNumConference, bwCommPilotCallMgrNumTransferVM, bwCommPilotCallManagerSPTable, bwCommPilotCallMgrNumConferenceAnswer, bwCommPilotCallMgrNumConferenceHold, bwCommPilotCallMgrNumConferenceRelease, bwCommPilotCallManagerGroupTable, bwCommPilotCallMgrNumTransferCC, bwCommPilotCallMgrNumConferenceAdd, bwCommPilotCallManagerSPIndex, bwCommPilotCallManagerSPID, bwCommPilotCallMgrSPNumDial, bwCommPilotCallMgrSPNumAnswer, bwCommPilotCallMgrSPNumRelease, bwCommPilotCallMgrSPNumHold, bwCommPilotCallMgrSPNumTransfer, bwCommPilotCallMgrSPNumConference, bwCommPilotCallMgrSPNumTransferVM, bwCommPilotCallMgrSPNumConferenceAnswer, bwCommPilotCallMgrSPNumConferenceHold, bwCommPilotCallMgrSPNumConferenceRelease, bwCommPilotCallMgrSPNumTransferCC, bwCommPilotCallMgrSPNumConferenceAdd, bwCommPilotCallManagerGroupIndex, bwCommPilotCallManagerGroupID, bwCommPilotCallMgrGroupNumDial, bwCommPilotCallMgrGroupNumAnswer, bwCommPilotCallMgrGroupNumRelease, bwCommPilotCallMgrGroupNumHold, bwCommPilotCallMgrGroupNumTransfer, bwCommPilotCallMgrGroupNumConference, bwCommPilotCallMgrGroupNumTransferVM, bwCommPilotCallMgrGroupNumConferenceAnswer, bwCommPilotCallMgrGroupNumConferenceHold, bwCommPilotCallMgrGroupNumConferenceRelease, bwCommPilotCallMgrGroupNumTransferCC, bwCommPilotCallMgrGroupNumConferenceAdd, bwCommPilotCallMgrNumCallPark, bwCommPilotCallMgrNumGroupCallPark, bwCommPilotCallMgrNumCallParkRetrieve, bwCommPilotCallMgrSPNumCallPark, bwCommPilotCallMgrSPNumGroupCallPark, bwCommPilotCallMgrSPNumCallParkRetrieve, bwCommPilotCallMgrGroupNumCallPark, bwCommPilotCallMgrGroupNumGroupCallPark, bwCommPilotCallMgrGroupNumCallParkRetrieve }
    STATUS  current
    DESCRIPTION
       "This group defines the statistics for the CommPilot Call Manager Service."
    ::= { bwAsMibGroups 27 }

bwAsDoNotDisturbServiceGroup    OBJECT-GROUP
    OBJECTS { bwDoNotDisturbNumInvoked, bwDoNotDisturbSPTable, bwDndPhoneActivations, bwDndPhoneDeactivations, bwDoNotDisturbGroupTable, bwDoNotDisturbSPIndex, bwDoNotDisturbSPID, bwDoNotDisturbSPNumInvoked, bwDNDSPNumPhoneActivations, bwDNDSPNumPhoneDeactivations, bwDoNotDisturbGroupIndex, bwDoNotDisturbGroupID, bwDoNotDisturbGroupNumInvoked, bwDNDGroupNumPhoneActivations, bwDNDGroupNumPhoneDeactivations }
    STATUS  current
    DESCRIPTION
       "This group defines the statistics for the Do Not Disturb Service."
    ::= { bwAsMibGroups 28 }

bwAsFlashCallXferServiceGroup    OBJECT-GROUP
    OBJECTS { bwFlashCallTransferNumTransfers, bwFlashCallTransferSPTable, bwFlashCallTransferGroupTable, bwFlashCallTransferSPIndex, bwFlashCallTransferSPID, bwFlashCallTransferSPNumTransfers, bwFlashCallTransferGroupIndex, bwFlashCallTransferGroupID, bwFlashCallTransferGroupNumTransfers }
    STATUS  current
    DESCRIPTION
       "This group defines the statistics for Flash Call Xfer Service."
    ::= { bwAsMibGroups 29 }

bwAsFlashCallWaitingServiceGroup    OBJECT-GROUP
    OBJECTS { bwFlashCallWaitingNumAnswers, bwFlashCallWaitingSPTable, bwFlashCallWaitingGroupTable, bwFlashCallWaitingSPIndex, bwFlashCallWaitingSPID, bwFlashCallWaitingSPNumAnswers, bwFlashCallWaitingGroupIndex, bwFlashCallWaitingGroupID, bwFlashCallWaitingGroupNumAnswers }
    STATUS  current
    DESCRIPTION
       "This group defines the statistics for Flash Call Waiting Service."
    ::= { bwAsMibGroups 30 }

bwAsFlashConsultationServiceGroup    OBJECT-GROUP
    OBJECTS { bwFlashConsultationNumCalls, bwFlashConsultationSPTable, bwFlashConsultationGroupTable, bwFlashConsultationSPIndex, bwFlashConsultationSPID, bwFlashConsultationSPNumCalls, bwFlashConsultationGroupIndex, bwFlashConsultationGroupID, bwFlashConsultationGroupNumCalls }
    STATUS  current
    DESCRIPTION
       "This group defines the statistics for Flash Consultation Service."
    ::= { bwAsMibGroups 31 }

bwAsFlash3wcServiceGroup    OBJECT-GROUP
    OBJECTS { bwFlashThreeWayCallNum3WC, bwFlashThreeWayCallSPTable, bwFlashThreeWayCallGroupTable, bwFlashThreeWayCallSPIndex, bwFlashThreeWayCallSPID, bwFlashThreeWayCallSPNum3WC, bwFlashThreeWayCallGroupIndex, bwFlashThreeWayCallGroupID, bwFlashThreeWayCallGroupNum3WC }
    STATUS  current
    DESCRIPTION
       "This group defines the statistics for Flash Three Way Calling Service."
    ::= { bwAsMibGroups 32 }

bwAsHuntGroupServiceGroup    OBJECT-GROUP
    OBJECTS { bwHuntGroupNumAttempts, bwHuntGroupNumBusy, bwHuntGroupsDNHIncomingCalls, bwHuntGroupsSPTable, bwHuntGroupsGroupTable, bwHuntGroupsSPIndex, bwHuntGroupsSPID, bwHuntGroupSPNumAttempts, bwHuntGroupSPNumBusy, bwHuntGroupsSPDNHIncomingCalls, bwHuntGroupsGroupIndex, bwHuntGroupsGroupID, bwHuntGroupsGroupNumAttempts, bwHuntGroupsGroupNumBusy, bwHuntGroupsGroupDNHIncomingCalls }
    STATUS  current
    DESCRIPTION
       "This group defines the statistics for the Hunt Group Service."
    ::= { bwAsMibGroups 33 }

bwAsIcpServiceGroup    OBJECT-GROUP
    OBJECTS { bwICPNumInterGroupBlocks, bwIncomingCallingPlanSPTable, bwIncomingCallingPlanGroupTable, bwICPNumCollectCallBlocks, bwICPNumIntraGroupBlocks, bwICPNumOutsideCallerBlocks, bwIncomingCallingPlanSPIndex, bwIncomingCallingPlanSPID, bwICPSPNumInterGroupBlocks, bwICPSPNumCollectCallBlocks, bwICPSPNumIntraGroupBlocks, bwICPSPNumOutsideCallerBlocks, bwIncomingCallingPlanGroupIndex, bwIncomingCallingPlanGroupID, bwICPGroupNumInterGroupBlocks, bwICPGroupNumCollectCallBlocks, bwICPGroupNumIntraGroupBlocks, bwICPGroupNumOutsideCallerBlocks }
    STATUS  current
    DESCRIPTION
       "This group defines the statistics for the Incoming Calling Plan Service."
    ::= { bwAsMibGroups 34 }

bwAsIpPhoneServiceGroup    OBJECT-GROUP
    OBJECTS { bwIPPhoneNumForwards, bwIPPhoneSPTable, bwIPPhoneGroupTable, bwIPPhoneSPIndex, bwIPPhoneSPID, bwIPPhoneSPNumForwards, bwIPPhoneGroupIndex, bwIPPhoneGroupID, bwIPPhoneGroupNumForwards }
    STATUS  current
    DESCRIPTION
       "This group defines the statistics for the IP Phone Service."
    ::= { bwAsMibGroups 35 }

bwAsLastNumberRedialServiceGroup    OBJECT-GROUP
    OBJECTS { bwLNRNumRedials, bwLastNumberRedialSPTable, bwLastNumberRedialGroupTable, bwLastNumberRedialSPIndex, bwLastNumberRedialSPID, bwLNRSPNumRedials, bwLastNumberRedialGroupIndex, bwLastNumberRedialGroupID, bwLNRGroupNumRedials }
    STATUS  current
    DESCRIPTION
       "This group defines the statistics for the Last Number Redial Service."
    ::= { bwAsMibGroups 36 }

bwAsOcpServiceGroup    OBJECT-GROUP
    OBJECTS { bwOCPNumGroupCallsBlocked, bwOCPNumLocalCallsBlocked, bwOCPNumTollFreeCallsBlocked, bwOCPNumTollCallsBlocked, bwOCPNumIntlCallsBlocked, bwOCPNumOperatorAssistedCallsBlocked, bwOCPNumChargeableDirAssistCallsBlocked, bwOCPNumSpecialServices1CallsBlocked, bwOCPNumSpecialServices2CallsBlocked, bwOCPNumPremiumServices1CallsBlocked, bwOCPNumPremiumServices2CallsBlocked, bwOCPNumCasualCallsBlocked, bwOCPNumURLDialingCallsBlocked, bwOCPNumUnknownCallsBlocked, bwOutgoingCallingPlanSPTable, bwOutgoingCallingPlanGroupTable, bwOCPNumSuccessfulAuthorizations, bwOCPNumUnsuccessfulAuthorizations, bwOCPNumTransfers, bwOCPSACNumSuccessfulLock, bwOCPSACNumSuccessfulUnlock, bwOCPSACNumUnsuccessfulLock, bwOCPSACNumUnsuccessfulUnlock, bwOCPSACNumUnsuccessfulCodeUsage, bwOCPNumOutsideGroupTransferBlocks, bwOutgoingCallingPlanSPIndex, bwOutgoingCallingPlanSPID, bwOCPSPNumGroupCallsBlocked, bwOCPSPNumLocalCallsBlocked, bwOCPSPNumTollFreeCallsBlocked, bwOCPSPNumTollCallsBlocked, bwOCPSPNumIntlCallsBlocked, bwOCPSPNumOperatorAssistedCallsBlocked, bwOCPSPNumChargeableDirAssistCallsBlocked, bwOCPSPNumSpecialServices1CallsBlocked, bwOCPSPNumSpecialServices2CallsBlocked, bwOCPSPNumPremiumServices1CallsBlocked, bwOCPSPNumPremiumServices2CallsBlocked, bwOCPSPNumCasualCallsBlocked, bwOCPSPNumURLDialingCallsBlocked, bwOCPSPNumUnknownCallsBlocked, bwOCPSPNumSuccessfulAuthorizations, bwOCPSPNumUnsuccessfulAuthorizations, bwOCPSPNumTransfers, bwOCPSACSPNumSuccessfulLock, bwOCPSACSPNumSuccessfulUnlock, bwOCPSACSPNumUnsuccessfulLock, bwOCPSACSPNumUnsuccessfulUnlock, bwOCPSACSPNumUnsuccessfulCodeUsage, bwOCPSPNumOutsideGroupTransferBlocks, bwOutgoingCallingPlanGroupIndex, bwOutgoingCallingPlanGroupID, bwOCPGroupNumGroupCallsBlocked, bwOCPGroupNumLocalCallsBlocked, bwOCPGroupNumTollFreeCallsBlocked, bwOCPGroupNumTollCallsBlocked, bwOCPGroupNumIntlCallsBlocked, bwOCPGroupNumOperatorAssistedCallsBlocked, bwOCPGroupNumChargeableDirAssistCallsBlocked, bwOCPGroupNumSpecialServices1CallsBlocked, bwOCPGroupNumSpecialServices2CallsBlocked, bwOCPGroupNumPremiumServices1CallsBlocked, bwOCPGroupNumPremiumServices2CallsBlocked, bwOCPGroupNumCasualCallsBlocked, bwOCPGroupNumURLDialingCallsBlocked, bwOCPGroupNumUnknownCallsBlocked, bwOCPGroupNumSuccessfulAuthorizations, bwOCPGroupNumUnsuccessfulAuthorizations, bwOCPGroupNumTransfers, bwOCPSACGroupNumSuccessfulLock, bwOCPSACGroupNumSuccessfulUnlock, bwOCPSACGroupNumUnsuccessfulLock, bwOCPSACGroupNumUnsuccessfulUnlock, bwOCPSACGroupNumUnsuccessfulCodeUsage, bwOCPGroupNumOutsideGroupTransferBlocks }
    STATUS  current
    DESCRIPTION
       "This group defines the statistics for the Outgoing Calling Plan Service."
    ::= { bwAsMibGroups 37 }

bwAsPriorityAlertServiceGroup    OBJECT-GROUP
    OBJECTS { bwPriorityAlertNumDistinctive, bwPriorityAlertSPTable, bwPriorityAlertGroupTable, bwPriorityAlertSPIndex, bwPriorityAlertSPID, bwPriorityAlertSPNumDistinctive, bwPriorityAlertGroupIndex, bwPriorityAlertGroupID, bwPriorityAlertGroupNumDistinctive }
    STATUS  current
    DESCRIPTION
       "This group defines the statistics for the Priority Alert Service."
    ::= { bwAsMibGroups 38 }

bwAsSelectiveCallAcceptanceServiceGroup    OBJECT-GROUP
    OBJECTS { bwSCANumAcceptances, bwSelectiveCallAcceptanceSPTable, bwSelectiveCallAcceptanceGroupTable, bwSelectiveCallAcceptanceSPIndex, bwSelectiveCallAcceptanceSPID, bwSCASPNumAcceptances, bwSelectiveCallAcceptanceGroupIndex, bwSelectiveCallAcceptanceGroupID, bwSCAGroupNumAcceptances }
    STATUS  current
    DESCRIPTION
       "This group defines the statistics for the Selective Call Acceptance Service."
    ::= { bwAsMibGroups 39 }

bwAsSelectiveCallForwardServiceGroup    OBJECT-GROUP
    OBJECTS { bwSCFNumForwards, bwSelectiveCallForwardSPTable, bwSelectiveCallForwardGroupTable, bwSelectiveCallForwardSPIndex, bwSelectiveCallForwardSPID, bwSCFSPNumForwards, bwSelectiveCallForwardGroupIndex, bwSelectiveCallForwardGroupID, bwSCFGroupNumForwards }
    STATUS  current
    DESCRIPTION
       "This group defines the statistics for the Selective Call Forward Service."
    ::= { bwAsMibGroups 40 }

bwAsSelectiveCallRejectionServiceGroup    OBJECT-GROUP
    OBJECTS { bwSCRNumRejects, bwSelectiveCallRejectionSPTable, bwSelectiveCallRejectionGroupTable, bwSelectiveCallRejectionSPIndex, bwSelectiveCallRejectionSPID, bwSCRSPNumRejects, bwSelectiveCallRejectionGroupIndex, bwSelectiveCallRejectionGroupID, bwSCRGroupNumRejects }
    STATUS  current
    DESCRIPTION
       "This group defines the statistics for the Selective Call Rejection Service."
    ::= { bwAsMibGroups 41 }

bwAsSimRingServiceGroup    OBJECT-GROUP
    OBJECTS { bwSimRingPersonalNumAttempts, bwSimRingPersonalNumBusy, bwSimRingPersonalSPTable, bwSimRingPersonalGroupTable, bwSimRingPersonalSPIndex, bwSimRingPersonalSPID, bwSimRingPersonalSPNumAttempts, bwSimRingPersonalSPNumBusy, bwSimRingPersonalGroupIndex, bwSimRingPersonalGroupID, bwSimRingPersonalGroupNumAttempts, bwSimRingPersonalGroupNumBusy }
    STATUS  current
    DESCRIPTION
       "This group defines the statistics for the Simultaneous Ringing Service."
    ::= { bwAsMibGroups 42 }

bwAsVoiceMessagingServiceGroup    OBJECT-GROUP
    OBJECTS { bwVMNumBusyGreetingsPlayed, bwVMNumNoAnswerGreetingsPlayed, bwVMNumMessagesLeft, bwVMRNumBusyGreetingsRecorded, bwVMRNumNoAnswerGreetingsRecorded, bwVMRNumPersonalizedNamesRecorded, bwVMRNumLoginAttempts, bwVMRNumLoginFailures, bwVMRNumComposeSendAttempts, bwVMRNumComposeSendGroupAttempts, bwVMRNumForwardSendAttempts, bwVMRNumForwardSendGroupAttempts, bwVMRNumReplySendAttempts, bwVMRNumSendFailed, bwVMRNumSendGroupFailed, bwVMRDeleteAllMsgsAttempts, bwVMRCallBackAttempts, bwVMRCallBackFailures, bwVPNumAABusHoursGreetingRecorded, bwVPNumAAAfterHoursGreetingRecorded, bwVPNumCFADestinationChanged, bwVPNumPasscodeChanged, bwVoiceMessagingSPTable, bwVMRNumComposeSendListAttempts, bwVMRNumForwardSendListAttempts, bwVMRNumSendListFailed, bwVPGreetingRecorded, bwVMGreetingRecorded, bwVoiceMessagingGroupTable, bwVPCCall, bwMultiMediaMsgDeposit, bwVMMultiMediaGreetingRecorded, bwAutoAttendantMultiMediaPromptRecorded, bwVoiceMessagingSPIndex, bwVoiceMessagingSPID, bwVMSPNumBusyGreetingsPlayed, bwVMSPNumNoAnswerGreetingsPlayed, bwVMSPNumMessagesLeft, bwVMRSPNumBusyGreetingsRecorded, bwVMRSPNumNoAnswerGreetingsRecorded, bwVMRSPNumPersonalizedNamesRecorded, bwVMRSPNumLoginAttempts, bwVMRSPNumLoginFailures, bwVMRSPNumComposeSendAttempts, bwVMRSPNumComposeSendGroupAttempts, bwVMRSPNumForwardSendAttempts, bwVMRSPNumForwardSendGroupAttempts, bwVMRSPNumReplySendAttempts, bwVMRSPNumSendFailed, bwVMRSPNumSendGroupFailed, bwVMRSPDeleteAllMsgsAttempts, bwVMRSPCallBackAttempts, bwVPSPNumAABusHoursGreetingRecorded, bwVPSPNumAAAfterHoursGreetingRecorded, bwVPSPNumCFADestinationChanged, bwVPSPNumPasscodeChanged, bwVMRSPNumComposeSendListAttempts, bwVMRSPNumForwardSendListAttempts, bwVMRSPNumSendListFailed, bwVPSPGreetingRecorded, bwVMSPGreetingRecorded, bwVPCSPCall, bwSPMultiMediaMsgDeposit, bwVMSPMultiMediaGreetingRecorded, bwAutoAttendantSPMultiMediaPromptRecorded, bwVoiceMessagingGroupIndex, bwVoiceMessagingGroupID, bwVMGroupNumBusyGreetingsPlayed, bwVMGroupNumNoAnswerGreetingsPlayed, bwVMGroupNumMessagesLeft, bwVMRGroupNumBusyGreetingsRecorded, bwVMRGroupNumNoAnswerGreetingsRecorded, bwVMRGroupNumPersonalizedNamesRecorded, bwVMRGroupNumLoginAttempts, bwVMRGroupNumLoginFailures, bwVMRGroupNumComposeSendAttempts, bwVMRGroupNumComposeSendGroupAttempts, bwVMRGroupNumForwardSendAttempts, bwVMRGroupNumForwardSendGroupAttempts, bwVMRGroupNumReplySendAttempts, bwVMRGroupNumSendFailed, bwVMRGroupNumSendGroupFailed, bwVMRGroupDeleteAllMsgsAttempts, bwVMRGroupCallBackAttempts, bwVMRGroupCallBackFailures, bwVPGroupNumAABusHoursGreetingRecorded, bwVPGroupNumAAAfterHoursGreetingRecorded, bwVPGroupNumCFADestinationChanged, bwVPGroupNumPasscodeChanged, bwVMRGroupNumComposeSendListAttempts, bwVMRGroupNumForwardSendListAttempts, bwVMRGroupNumSendListFailed, bwVPGroupGreetingRecorded, bwVMGroupGreetingRecorded, bwVPCGroupCall, bwGroupMultiMediaMsgDeposit, bwVMGroupMultiMediaGreetingRecorded, bwAutoAttendantGroupMultiMediaPromptRecorded, bwMessagingQuery, bwMessagingQueryNoUser, bwMessagingQueryNoMailbox, bwMessagingSPQuery, bwMessagingSPQueryNoUser, bwMessagingSPQueryNoMailbox, bwMessagingGroupQuery, bwMessagingGroupQueryNoUser, bwMessagingGroupQueryNoMailbox }
    STATUS  current
    DESCRIPTION
       "This group defines the statistics for the Voice Messaging Service."
    ::= { bwAsMibGroups 43 }

bwAsSeriesCompletionServiceGroup    OBJECT-GROUP
    OBJECTS { bwSeriesCompletionNumAttempts, bwSeriesCompletionNumBusy, bwSeriesCompletionSPTable, bwSeriesCompletionGroupTable, bwSeriesCompletionSPIndex, bwSeriesCompletionSPID, bwSeriesCompletionSPNumAttempts, bwSeriesCompletionSPNumBusy, bwSeriesCompletionGroupIndex, bwSeriesCompletionGroupID, bwSeriesCompletionGroupNumAttempts, bwSeriesCompletionGroupNumBusy }
    STATUS  current
    DESCRIPTION
       "This group defines the statistics for the Series Completion Service."
    ::= { bwAsMibGroups 44 }

bwAsInterceptServiceGroup    OBJECT-GROUP
    OBJECTS { bwInterceptUserOriginationInvocations, bwInterceptGroupOriginationInvocations, bwInterceptUserTerminationInvocations, bwInterceptGroupTerminationInvocations, bwInterceptTransfers, bwInterceptSPTable, bwInterceptGroupTable, bwInterceptSPIndex, bwInterceptSPID, bwInterceptSPUserOriginationInvocations, bwInterceptSPGroupOriginationInvocations, bwInterceptSPUserTerminationInvocations, bwInterceptSPGroupTerminationInvocations, bwInterceptSPTransfers, bwInterceptGroupIndex, bwInterceptGroupID, bwInterceptGroupUserOriginationInvocations, bwInterceptGroupGroupOriginationInvocations, bwInterceptGroupUserTerminationInvocations, bwInterceptGroupGroupTerminationInvocations, bwInterceptGroupTransfers }
    STATUS  current
    DESCRIPTION
       "This group defines the statistics for the Intercept Service."
    ::= { bwAsMibGroups 45 }

bwAsInstantConferencingServiceGroup    OBJECT-GROUP
    OBJECTS { bwICGroupPortLimitExceeded, bwICNumAttempts, bwInstantConferencingSPTable, bwInstantConferencingGroupTable, bwInstantConferencingBridgeTable, bwICOutdialNumAttempts, bwInstantConferencingSPIndex, bwInstantConferencingSPID, bwICSPGroupPortLimitExceeded, bwICSPNumAttempts, bwICSPOutdialNumAttempts, bwInstantConferencingGroupIndex, bwInstantConferencingGroupID, bwICGroupGroupPortLimitExceeded, bwICGroupNumAttempts, bwICGroupOutdialNumAttempts, bwInstantConferencingBridgeIndex, bwInstantConferencingBridgeName, bwInstantConferencingBridgeGroupName, bwInstantConferencingCurrentUsage, bwInstantConferencingTodaysPeakUsage, bwInstantConferencingYesterdaysPeakUsage }
    STATUS  current
    DESCRIPTION
       "This group defines the statistics for the Instant Conferencing Service."
    ::= { bwAsMibGroups 46 }

bwAsCallingLineIdBlockingServiceGroup    OBJECT-GROUP
    OBJECTS { bwCallingLineIDDeliveryBlockPerCallBlocks, bwCallingLineIDDeliveryBlockSPTable, bwCallingLineIDDeliveryBlockGroupTable, bwCallingLineIDDeliveryPerCall, bwCallingLineIDDeliveryBlockSPIndex, bwCallingLineIDDeliveryBlockSPID, bwCallingLineIDDeliveryBlockSPPerCallBlocks, bwCallingLineIDDeliveryPerCallSP, bwCallingLineIDDeliveryBlockGroupIndex, bwCallingLineIDDeliveryBlockGroupID, bwCallingLineIDDeliveryBlockGroupPerCallBlocks, bwCallingLineIDDeliveryPerCallGroup }
    STATUS  current
    DESCRIPTION
       "This group defines the statistics for the Calling Line ID Blocking Service."
    ::= { bwAsMibGroups 47 }

bwAsSessionAuditServiceGroup    OBJECT-GROUP
    OBJECTS { bwSessionAuditNumCallsAudited, bwSessionAuditNumEndpointsAudited, bwSessionAuditNumCallsFailedAudit, bwSessionAuditNumEndpointsFailedAudit, bwSessionAuditSPTable, bwSessionAuditGroupTable, bwSessionAuditSPIndex, bwSessionAuditSPID, bwSessionAuditSPNumCallsAudited, bwSessionAuditSPNumEndpointsAudited, bwSessionAuditSPNumCallsFailedAudit, bwSessionAuditSPNumEndpointsFailedAudit, bwSessionAuditGroupIndex, bwSessionAuditGroupID, bwSessionAuditGroupNumCallsAudited, bwSessionAuditGroupNumEndpointsAudited, bwSessionAuditGroupNumCallsFailedAudit, bwSessionAuditGroupNumEndpointsFailedAudit }
    STATUS  current
    DESCRIPTION
       "This group defines the statistics for the Session Audit Service."
    ::= { bwAsMibGroups 48 }

bwAsWindowsMessagingServiceGroup    OBJECT-GROUP
    OBJECTS { bwWindowsMessagingIMSessionSuccessCounter }
    STATUS  current
    DESCRIPTION
       "This group defines the statistics for the Windows Messaging Service."
    ::= { bwAsMibGroups 49 }

bwAsCalWaitingServiceGroup    OBJECT-GROUP
    OBJECTS { bwCallWaitingSPTable, bwCWNumPhoneCancellations, bwCallWaitingGroupTable, bwCallWaitingSPIndex, bwCallWaitingSPID, bwCWSPNumPhoneCancellations, bwCallWaitingGroupIndex, bwCallWaitingGroupID, bwCWGroupNumPhoneCancellations }
    STATUS  current
    DESCRIPTION
       "This group defines the statistics for the Call Waiting Service."
    ::= { bwAsMibGroups 50 }

bwAsAlternateNumberServiceGroup    OBJECT-GROUP
    OBJECTS { bwAlternateNumbersSPTable, bwAlternateNumbersUsage, bwAlternateNumbersGroupTable, bwAlternateNumbersSPIndex, bwAlternateNumbersSPID, bwAlternateNumbersSPUsage, bwAlternateNumbersGroupIndex, bwAlternateNumbersGroupID, bwAlternateNumbersGroupUsage }
    STATUS  current
    DESCRIPTION
       "This group defines the statistics for the Alternate Number Service."
    ::= { bwAsMibGroups 51 }

bwAsCustomerOriginatedTraceServiceGroup    OBJECT-GROUP
    OBJECTS { bwCotActivation, bwCotFailureNoId, bwCotSPTable, bwCotGroupTable, bwCotSPIndex, bwCotSPID, bwCotSPActivation, bwCotSPFailureNoId, bwCotGroupIndex, bwCotGroupID, bwCotGroupActivation, bwCotGroupFailureNoId }
    STATUS  current
    DESCRIPTION
       "This group defines the statistics for the Customer Originated Trace Service."
    ::= { bwAsMibGroups 52 }

bwAsSpeedDialing8ServiceGroup    OBJECT-GROUP
    OBJECTS { bwSD8NumTimesDialed, bwSD8NumTimesProgrammed, bwSD8SPTable, bwSD8GroupTable, bwSD8SPIndex, bwSD8SPID, bwSD8SPNumTimesDialed, bwSD8SPNumTimesProgrammed, bwSD8GroupIndex, bwSD8GroupID, bwSD8GroupNumTimesDialed, bwSD8GroupNumTimesProgrammed }
    STATUS  current
    DESCRIPTION
       "This group defines the statistics for the Speed Dialing 8 Service."
    ::= { bwAsMibGroups 53 }

bwAsMusicOnHoldServiceGroup    OBJECT-GROUP
    OBJECTS { bwMusicOnHoldNumUses, bwMusicOnHoldSPTable, bwMusicOnHoldGroupTable, bwMusicOnHoldExternalSourceNumFailures, bwMusicOnHoldSPIndex, bwMusicOnHoldSPID, bwMusicOnHoldSPNumUses, bwMusicOnHoldSPExternalSourceNumFailures, bwMusicOnHoldGroupIndex, bwMusicOnHoldGroupID, bwMusicOnHoldGroupNumUses, bwMusicOnHoldGroupExternalSourceNumFailures }
    STATUS  current
    DESCRIPTION
       "This group defines the statistics for the Music On Hold Service."
    ::= { bwAsMibGroups 54 }

bwAsCallingNameQueriesServiceGroup    OBJECT-GROUP
    OBJECTS { bwCNAMQueriesSent, bwCNAMQueriesFailed, bwCNAMQueriesTimeout }
    STATUS  current
    DESCRIPTION
       "This group defines the statistics for the Calling Name Queries Service."
    ::= { bwAsMibGroups 55 }

bwAsThirdPartyMWIControlServiceGroup    OBJECT-GROUP
    OBJECTS { bwThirdPartyMWIControlNotifyIns, bwThirdPartyMWIControlNotifyFailures }
    STATUS  current
    DESCRIPTION
       "This group defines the statistics for the Third Party Message Waiting Indicator Control Service."
    ::= { bwAsMibGroups 56 }

bwAsCallCenterServiceGroup    OBJECT-GROUP
    OBJECTS { bwCallCenterReportEmailed, bwCallCenterSPTable, bwCallCenterGroupTable, bwCallCenterSPIndex, bwCallCenterSPID, bwCallCenterSPReportEmailed, bwCallCenterGroupIndex, bwCallCenterGroupID, bwCallCenterGroupReportEmailed }
    STATUS  current
    DESCRIPTION
       "This group defines the statistics for the Call Center Service."
    ::= { bwAsMibGroups 57 }

bwAsCallForwardGroupNoAnswerServiceGroup    OBJECT-GROUP
    OBJECTS { bwCFGNAForward, bwCFGNAOverflowForward, bwCFGNAOverflowNoForward, bwCFGNASPTable, bwCFGNAGroupTable, bwCFGNAExternalForward, bwCFGNAExternalNoForward, bwCFGNASPIndex, bwCFGNASPID, bwCFGNASPForward, bwCFGNASPOverflowForward, bwCFGNASPOverflowNoForward, bwCFGNASPExternalForward, bwCFGNASPExternalNoForward, bwCFGNAGroupIndex, bwCFGNAGroupID, bwCFGNAGroupForward, bwCFGNAGroupOverflowForward, bwCFGNAGroupOverflowNoForward, bwCFGNAGroupExternalForward, bwCFGNAGroupExternalNoForward }
    STATUS  current
    DESCRIPTION
       "This group defines the statistics for the Call Forward Group No Answer Service."
    ::= { bwAsMibGroups 58 }

bwAsSpeedDialing100ServiceGroup    OBJECT-GROUP
    OBJECTS { bwSD100Program, bwSD100Call, bwSD100SPTable, bwSD100GroupTable, bwSD100SPIndex, bwSD100SPID, bwSD100SPProgram, bwSD100SPCall, bwSD100GroupIndex, bwSD100GroupID, bwSD100GroupProgram, bwSD100GroupCall }
    STATUS  current
    DESCRIPTION
       "This group defines the statistics for the Speed Dialing 100 Service."
    ::= { bwAsMibGroups 59 }

bwAsThirdPartyVoiceMailServiceGroup    OBJECT-GROUP
    OBJECTS { bwThirdPartyVoiceMailNbOfCFWBusy, bwThirdPartyVoiceMailNbOfCFWNoAnswer, bwThirdPartyVMailSPTable, bwThirdPartyVMailGroupTable, bwThirdPartyVMailSPIndex, bwThirdPartyVMailSPID, bwThirdPartyVoiceMailSPNbOfCFWBusy, bwThirdPartyVoiceMailSPNbOfCFWNoAnswer, bwThirdPartyVMailGroupIndex, bwThirdPartyVMailGroupID, bwThirdPartyVoiceMailGroupNbOfCFWBusy, bwThirdPartyVoiceMailGroupNbOfCFWNoAnswer }
    STATUS  current
    DESCRIPTION
       "This group defines the statistics for the Third Party Voice Mail Service."
    ::= { bwAsMibGroups 60 }

bwAsDirectedCallPickupServiceGroup    OBJECT-GROUP
    OBJECTS { bwDirectedCallPickupNumAttempts, bwDirectedCallPickupNumFailures, bwDirectedCallPickupSPTable, bwDirectedCallPickupGroupTable, bwDirectedCallPickupSPIndex, bwDirectedCallPickupSPID, bwDirectedCallPickupSPNumAttempts, bwDirectedCallPickupSPNumFailures, bwDirectedCallPickupGroupIndex, bwDirectedCallPickupGroupID, bwDirectedCallPickupGroupNumAttempts, bwDirectedCallPickupGroupNumFailures }
    STATUS  current
    DESCRIPTION
       "This group defines the statistics for the Directed Call Pickup Service."
    ::= { bwAsMibGroups 61 }

bwAsFlashCallHoldServiceGroup    OBJECT-GROUP
    OBJECTS { bwFlashCallHoldNumActivations, bwFlashCallHoldSPTable, bwFlashCallHoldGroupTable, bwFlashCallHoldSPIndex, bwFlashCallHoldSPID, bwFlashCallHoldSPNumActivations, bwFlashCallHoldGroupIndex, bwFlashCallHoldGroupID, bwFlashCallHoldGroupNumActivations }
    STATUS  current
    DESCRIPTION
       "This group defines the statistics for the Flash Call Hold Service."
    ::= { bwAsMibGroups 62 }

bwAsEmergencyZoneServiceGroup    OBJECT-GROUP
    OBJECTS { bwEZRegistrationsRejected, bwEZEmergencyCallsRejected, bwEZNormalCallsRejected, bwEZSPTable, bwEZGroupTable, bwEZSPIndex, bwEZSPID, bwEZSPRegistrationsRejected, bwEZSPEmergencyCallsRejected, bwEZSPNormalCallsRejected, bwEZGroupIndex, bwEZGroupID, bwEZGroupRegistrationsRejected, bwEZGroupEmergencyCallsRejected, bwEZGroupNormalCallsRejected }
    STATUS  current
    DESCRIPTION
       "This group defines the statistics for the Emergency Zone Service."
    ::= { bwAsMibGroups 63 }

bwAsDirectedCallPickupWithBargeInServiceGroup    OBJECT-GROUP
    OBJECTS { bwDPUBIAttempt, bwDPUBIFailure, bwDPUBIBargeIn, bwDPUBIBargeInFailure, bwDPUBISPTable, bwDPUBIGroupTable, bwDPUBIExempt, bwDPUBISPIndex, bwDPUBISPID, bwDPUBISPAttempt, bwDPUBISPFailure, bwDPUBISPBargeIn, bwDPUBISPBargeInFailure, bwDPUBISPExempt, bwDPUBIGroupIndex, bwDPUBIGroupID, bwDPUBIGroupAttempt, bwDPUBIGroupFailure, bwDPUBIGroupBargeIn, bwDPUBIGroupBargeInFailure, bwDPUBIGroupExempt }
    STATUS  current
    DESCRIPTION
       "This group defines the statistics for the Directed Call Pickup With Barge In Service."
    ::= { bwAsMibGroups 64 }

bwAsAutomaticCallBackServiceGroup    OBJECT-GROUP
    OBJECTS { bwACBStarted, bwACBExpired, bwACBMaxSession, bwACBSPTable, bwACBGroupTable, bwACBSPIndex, bwACBSPID, bwACBSPStarted, bwACBSPExpired, bwACBSPMaxSession, bwACBGroupIndex, bwACBGroupID, bwACBGroupStarted, bwACBGroupExpired, bwACBGroupMaxSession }
    STATUS  current
    DESCRIPTION
       "This group defines the statistics for the Automatic Call Back Service."
    ::= { bwAsMibGroups 65 }

bwAsRingTimeoutServiceGroup    OBJECT-GROUP
    OBJECTS { bwRingTimeoutNumExpires, bwRingTimeoutSPTable, bwRingTimeoutGroupTable, bwRingTimeoutSPIndex, bwRingTimeoutSPID, bwRingTimeoutSPNumExpires, bwRingTimeoutGroupIndex, bwRingTimeoutGroupID, bwRingTimeoutGroupNumExpires }
    STATUS  current
    DESCRIPTION
       "This group defines the statistics for the Ring Timeout Service."
    ::= { bwAsMibGroups 66 }

bwAsSequentialRingServiceGroup    OBJECT-GROUP
    OBJECTS { bwSequentialRingNumAttempts, bwSequentialRingNumNoAnswer, bwSequentialRingSPTable, bwSequentialRingGroupTable, bwSequentialRingActivations, bwSequentialRingAnswered, bwSequentialRingAbandoned, bwSequentialRingSPIndex, bwSequentialRingSPID, bwSequentialRingSPNumAttempts, bwSequentialRingSPNumNoAnswer, bwSequentialRingSPActivations, bwSequentialRingSPAnswered, bwSequentialRingSPAbandoned, bwSequentialRingGroupIndex, bwSequentialRingGroupID, bwSequentialRingGroupNumAttempts, bwSequentialRingGroupNumNoAnswer, bwSequentialRingGroupActivations, bwSequentialRingGroupAnswered, bwSequentialRingGroupAbandoned }
    STATUS  current
    DESCRIPTION
       "This group defines the statistics for the Sequential Ring Service."
    ::= { bwAsMibGroups 67 }

bwAsVideoAddOnServiceGroup    OBJECT-GROUP
    OBJECTS { bwVAOOutgoingAttempts, bwVAOOutgoingSuccess, bwVAOIncomingAttempts, bwVAOIncomingSuccess, bwVAOSPTable, bwVAOGroupTable, bwVAOSPIndex, bwVAOSPID, bwVAOSPOutgoingAttempts, bwVAOSPOutgoingSuccess, bwVAOSPIncomingAttempts, bwVAOSPIncomingSuccess, bwVAOGroupIndex, bwVAOGroupID, bwVAOGroupOutgoingAttempts, bwVAOGroupOutgoingSuccess, bwVAOGroupIncomingAttempts, bwVAOGroupIncomingSuccess }
    STATUS  current
    DESCRIPTION
       "This group defines the statistics for the Video Add-On Service."
    ::= { bwAsMibGroups 68 }

bwAsMaliciousCallTraceServiceGroup    OBJECT-GROUP
    OBJECTS { bwMaliciousCallTraceApplied, bwMaliciousCallTraceSPTable, bwMaliciousCallTraceGroupTable, bwMaliciousCallTraceSPIndex, bwMaliciousCallTraceSPID, bwMaliciousCallTraceSPApplied, bwMaliciousCallTraceGroupIndex, bwMaliciousCallTraceGroupID, bwMaliciousCallTraceGroupApplied }
    STATUS  current
    DESCRIPTION
       "This group defines the statistics for the Malicious Call Trace Service."
    ::= { bwAsMibGroups 69 }

bwAsPushToTalkServiceGroup    OBJECT-GROUP
    OBJECTS { bwPTTInvoke, bwPTTReject, bwPTTSPTable, bwPTTGroupTable, bwPTTSPIndex, bwPTTSPID, bwPTTSPInvoke, bwPTTSPReject, bwPTTGroupIndex, bwPTTGroupID, bwPTTGroupInvoke, bwPTTGroupReject }
    STATUS  current
    DESCRIPTION
       "This group defines the statistics for the Push To Talk Service."
    ::= { bwAsMibGroups 70 }

bwAsHotelingServiceGroup    OBJECT-GROUP
    OBJECTS { bwHotelingAssociate, bwHotelingDisassociate, bwHotelingTimeout, bwHotelingSPTable, bwHotelingGroupTable, bwHotelingSPIndex, bwHotelingSPID, bwHotelingSPAssociate, bwHotelingSPDisassociate, bwHotelingSPTimeout, bwHotelingGroupIndex, bwHotelingGroupID, bwHotelingGroupAssociate, bwHotelingGroupDisassociate, bwHotelingGroupTimeout }
    STATUS  current
    DESCRIPTION
       "This group defines the statistics for the Hoteling Service."
    ::= { bwAsMibGroups 71 }

bwAsPreferredCarrierServiceGroup    OBJECT-GROUP
    OBJECTS { bwSubscriptionUserPIC, bwSubscriptionGroupPIC, bwSubscriptionServiceProviderPIC, bwSubscriptionDialedUserPIC, bwSubscriptionDialedGroupPIC, bwSubscriptionDialedServiceProviderPIC, bwNonSubscriptionDialedUserPIC, bwNonSubscriptionDialedGroupPIC, bwNonSubscriptionDialedServiceProviderPIC, bwNoIndicationUserPIC, bwNoIndicationGroupPIC, bwNoIndicationServiceProviderPIC, bwPreferredCarrierSPTable, bwPreferredCarrierGroupTable, bwPreferredCarrierSPIndex, bwPreferredCarrierSPID, bwSPSubscriptionUserPIC, bwSPSubscriptionGroupPIC, bwSPSubscriptionServiceProviderPIC, bwSPSubscriptionDialedUserPIC, bwSPSubscriptionDialedGroupPIC, bwSPSubscriptionDialedServiceProviderPIC, bwSPNonSubscriptionDialedUserPIC, bwSPNonSubscriptionDialedGroupPIC, bwSPNonSubscriptionDialedServiceProviderPIC, bwSPNoIndicationUserPIC, bwSPNoIndicationGroupPIC, bwSPNoIndicationServiceProviderPIC, bwPreferredCarrierGroupIndex, bwPreferredCarrierGroupID, bwGroupSubscriptionUserPIC, bwGroupSubscriptionGroupPIC, bwGroupSubscriptionServiceProviderPIC, bwGroupSubscriptionDialedUserPIC, bwGroupSubscriptionDialedGroupPIC, bwGroupSubscriptionDialedServiceProviderPIC, bwGroupNonSubscriptionDialedUserPIC, bwGroupNonSubscriptionDialedGroupPIC, bwGroupNonSubscriptionDialedServiceProviderPIC, bwGroupNoIndicationUserPIC, bwGroupNoIndicationGroupPIC, bwGroupNoIndicationServiceProviderPIC }
    STATUS  current
    DESCRIPTION
       "This group defines the statistics for the Preferred Carrier Service."
    ::= { bwAsMibGroups 72 }

bwAsFamilySimRingServiceGroup    OBJECT-GROUP
    OBJECTS { bwFamilySimRingNumAttempts, bwFamilySimRingNumBusy, bwFamilySimRingSPTable, bwFamilySimRingGroupTable, bwFamilySimRingSPIndex, bwFamilySimRingSPID, bwFamilySimRingSPNumAttempts, bwFamilySimRingSPNumBusy, bwFamilySimRingGroupIndex, bwFamilySimRingGroupID, bwFamilySimRingGroupNumAttempts, bwFamilySimRingGroupNumBusy }
    STATUS  current
    DESCRIPTION
       "This group defines the statistics for the Family SimRing Service."
    ::= { bwAsMibGroups 73 }

bwAsDiversionInhibitorServiceGroup    OBJECT-GROUP
    OBJECTS { bwDiversionInhibited, bwDiversionInhibitorSPTable, bwDiversionInhibitorGroupTable, bwDiversionInhibitorSPIndex, bwDiversionInhibitorSPID, bwSPDiversionInhibited, bwDiversionInhibitorGroupIndex, bwDiversionInhibitorGroupID, bwGroupDiversionInhibited }
    STATUS  current
    DESCRIPTION
       "This group defines the statistics for the Diversion Inhibitor Service."
    ::= { bwAsMibGroups 74 }

bwAsInstantGroupCallServiceGroup    OBJECT-GROUP
    OBJECTS { bwIGCPushToTalkInvoke, bwIGCNormalInvoke, bwIGCSPTable, bwIGCGroupTable, bwIGCSPIndex, bwIGCSPID, bwIGCSPPushToTalkInvoke, bwIGCSPNormalInvoke, bwIGCGroupIndex, bwIGCGroupID, bwIGCGroupPushToTalkInvoke, bwIGCGroupNormalInvoke }
    STATUS  current
    DESCRIPTION
       "This group defines the statistics for the Instant Group Call Service."
    ::= { bwAsMibGroups 75 }

bwAsAutomaticHoldAndRetrieveServiceGroup    OBJECT-GROUP
    OBJECTS { bwAHRHold, bwAHRRetrieve, bwAHRSPTable, bwAHRGroupTable, bwAHRSPIndex, bwAHRSPID, bwAHRSPHold, bwAHRSPRetrieve, bwAHRGroupIndex, bwAHRGroupID, bwAHRGroupHold, bwAHRGroupRetrieve }
    STATUS  current
    DESCRIPTION
       "This group defines the statistics for the Automatic Hold And Retrieve Service."
    ::= { bwAsMibGroups 76 }

bwAsBusinessTrunkGroupServiceGroup    OBJECT-GROUP
    OBJECTS { bwTrunkOriginationAttempt, bwTrunkOriginationBlocked, bwTrunkTerminationAttempt, bwTrunkTerminationBlocked, bwTrunkSPTable, bwTrunkGroupTable, bwTrunkSPIndex, bwTrunkSPID, bwTrunkSPOriginationAttempt, bwTrunkSPOriginationBlocked, bwTrunkSPTerminationAttempt, bwTrunkSPTerminationBlocked, bwTrunkGroupIndex, bwTrunkGroupID, bwTrunkGroupOriginationAttempt, bwTrunkGroupOriginationBlocked, bwTrunkGroupTerminationAttempt, bwTrunkGroupTerminationBlocked, bwTrunkGroupPerTGTable, bwTrunkGroupPerTGIndex, bwTrunkGroupPerTGName, bwTrunkGroupPerTGCapacityExceeded, bwTrunkGroupPerTGUnreachableDestination, bwTrunkGroupPerTGMaxActiveCalls, bwTrunkGroupPerTGMaxOutgoingActiveCalls, bwTrunkGroupPerTGMaxIncomingActiveCalls, bwTrunkGroupPerTGCapacityExceededInitialValue, bwTrunkGroupPerTGCapacityExceededOffsetValue, bwTrunkGroupPerTGUnreachableDestinationExceededInitialValue, bwTrunkGroupPerTGUnreachableDestinationExceededOffsetValue, bwTrunkGroupPerTGGroupID }
    STATUS  current
    DESCRIPTION
       "This group defines the statistics for the Business Trunk Group Service."
    ::= { bwAsMibGroups 77 }

bwAsCustomRingbackServiceGroup    OBJECT-GROUP
    OBJECTS { bwCustomRingbackUserAudioAttempts, bwCustomRingbackUserVideoAttempts, bwCustomRingbackUserAudioFailures, bwCustomRingbackUserVideoFailures, bwCustomRingbackGroupAudioAttempts, bwCustomRingbackGroupVideoAttempts, bwCustomRingbackGroupAudioFailures, bwCustomRingbackGroupVideoFailures, bwCustomRingbackSPTable, bwCustomRingbackGroupTable, bwCustomRingbackSPIndex, bwCustomRingbackSPID, bwCustomRingbackUserAudioSPAttempts, bwCustomRingbackUserVideoSPAttempts, bwCustomRingbackUserAudioSPFailures, bwCustomRingbackUserVideoSPFailures, bwCustomRingbackGroupAudioSPAttempts, bwCustomRingbackGroupVideoSPAttempts, bwCustomRingbackGroupAudioSPFailures, bwCustomRingbackGroupVideoSPFailures, bwCustomRingbackGroupIndex, bwCustomRingbackGroupID, bwCustomRingbackUserAudioGroupAttempts, bwCustomRingbackUserVideoGroupAttempts, bwCustomRingbackUserAudioGroupFailures, bwCustomRingbackUserVideoGroupFailures, bwCustomRingbackGroupAudioGroupAttempts, bwCustomRingbackGroupVideoGroupAttempts, bwCustomRingbackGroupAudioGroupFailures, bwCustomRingbackGroupVideoGroupFailures }
    STATUS  current
    DESCRIPTION
       "This group defines the statistics for the Custom Ringback Service."
    ::= { bwAsMibGroups 78 }

bwAsMssGroup    OBJECT-GROUP
    OBJECTS { bwNSqueryRequestsTransmitted, bwNSqueryRequestsRetransmitted, bwNSqueryCommFailures }
    STATUS  current
    DESCRIPTION
       "This group defines the statistics for the Media Server Selection."
    ::= { bwAsMibGroups 79 }

bwAsNrsGroup    OBJECT-GROUP
    OBJECTS { bwNbInvalidMessagesReceived, bwNbRequestsReceived, bwNbResponsesReceived, bwNbErrorsReceived, bwNbRequestsSent, bwNbResponsesSent, bwNbErrorsSent, bwNbRequestsResent, bwNbResponsesResent, bwNbRequestsUnanswered, bwNRSStatsTable, bwNRSStatsTableIndex, bwNRSStatsTableProtocolName, bwNRSStatsTableNbRequestsReceived, bwNRSStatsTableNbResponsesReceived, bwNRSStatsTableNbErrorsReceived, bwNRSStatsTableNbRequestsSent, bwNRSStatsTableNbResponsesSent, bwNRSStatsTableNbErrorsSent, bwNRSStatsTableNbRequestsResent, bwNRSStatsTableNbResponsesResent, bwNRSStatsTableNbRequestsUnanswered }
    STATUS  current
    DESCRIPTION
       "This group defines the statistics for the NRS based protocols."
    ::= { bwAsMibGroups 80 }

bwAsXsPersistencyGroup    OBJECT-GROUP
    OBJECTS { perNbOpenedTransactions, perNbCommittedTransactions, perNbFailedTransactions, perNbCriticalErrors, ttNbConnectionsCreated, ttConnectionPoolSize, ttNbBackdoorUpdates, ttNbFailedCheckpoints, xsRemoteXlaNbTimesConnected, xsRemoteXlaNbTimesDisconnected, xsRemoteXlaUpdatesProcessed, xsRemoteXlaUpdatesPending }
    STATUS  current
    DESCRIPTION
       "This group defines the statistics for the Application Server Execution Server process persistency."
    ::= { bwAsMibGroups 81 }

bwAsProtocolMonitorGroup    OBJECT-GROUP
    OBJECTS { bwPMTNumMonitorsCreated, bwPMTNumMonitorsOpen, bwPMTNumLoggerCreated, bwPMTNumLoggerOpen }
    STATUS  current
    DESCRIPTION
       "This group defines the statistics for the Protocol Monitor."
    ::= { bwAsMibGroups 82 }

bwAsSystemStatsGroup    OBJECT-GROUP
    OBJECTS { bwSystemName, bwNumberOfUsers, bwNumberOfGroups, bwNumberOfServProv, bwNumberOfDNDefined, bwNumberOfDNAssigned, bwNumberOfDeviceType, bwNumberOfServiceType, bwDeviceTypeSystemTable, bwServiceTypeSystemTable, bwSystemSPTable, bwSystemGroupTable, bwDeviceTypeSystemIndex, bwDeviceTypeSystemID, bwNumberOfDeviceTypeSystem, bwServiceTypeSystemIndex, bwServiceTypeSystemID, bwNumberOfServiceTypeAssignedSystem, bwSystemSPIndex, bwSystemSPID, bwSystemSPName, bwNumberOfSPUsers, bwNumberOfSPGroups, bwNumberOfSPDNDefined, bwNumberOfSPDNAssigned, bwNumberOfSPDeviceType, bwSystemGroupIndex, bwSystemGroupSPID, bwSystemGroupID, bwSystemGroupName, bwNumberOfGroupUsers, bwNumberOfGroupDNDefined, bwNumberOfGroupDNAssigned, bwNumberOfGroupDeviceType }
    STATUS  current
    DESCRIPTION
       "This group defines the system level statistics for the Application Server."
    ::= { bwAsMibGroups 83 }

bwAsQueueStatsGroup    OBJECT-GROUP
    OBJECTS { bySystemInternalQueueResets, bwSystemInternalQueueTable, bwSystemInternalQueueIndex, bwSystemInternalQueueName, bwSystemInternalQueueSize, bwSystemInternalQueueTimeAvg, bwSystemInternalQueueTimeMin, bwSystemInternalQueueTimeMax, bwSystemInternalQueueTimeMaxTimestampMSB, bwSystemInternalQueueLengthCurrent, bwSystemInternalQueueLengthAvg, bwSystemInternalQueueLengthMax, bwSystemInternalQueueLengthMaxTimestampMSB, bwSystemInternalQueueLengthMaxTimestampLSB, bwSystemInternalQueueTimeMaxTimestampLSB }
    STATUS  current
    DESCRIPTION
       "This group defines the statistics for the Application Server processing internal queues."
    ::= { bwAsMibGroups 84 }

bwAsOverloadControlStatsGroup    OBJECT-GROUP
    OBJECTS { bwCurrentOverloadZone, bwNumYellowZoneOverloadTrans, bwNumRedZoneOverloadTrans, bwCurrentCallOverloadZone, bwNumCallYellowZoneOverloadTrans, bwNumCallRedZoneOverloadTrans, bwCurrentNonCallOverloadZone, bwNumNonCallYellowZoneOverloadTrans, bwNumNonCallRedZoneOverloadTrans, bwNumDiscardedMessage,  bwTimeLastDiscardedMessage }
    STATUS  current
    DESCRIPTION
       "This group defines the statistics for the Overload Control feature on the Application Server."
    ::= { bwAsMibGroups 85 }

bwAsRedundancyStatsGroup    OBJECT-GROUP
    OBJECTS { nbOfMigratedUsers }
    STATUS  current
    DESCRIPTION
       "This group defines the statistics for the Application Server Redundancy feature."
    ::= { bwAsMibGroups 86 }

bwAsPsPersistencyGroup    OBJECT-GROUP
    OBJECTS { psPerNbOpenedTransactions, psPerNbCommittedTransactions, psPerNbFailedTransactions, psPerNbCriticalErrors, psTtNbConnectionsCreated, psTtConnectionPoolSize, psTtNbBackdoorUpdates, psTtNbFailedCheckpoints, psRemoteXlaNbTimesConnected, psRemoteXlaNbTimesDisconnected, psRemoteXlaUpdatesProcessed, psRemoteXlaUpdatesPending }
    STATUS  current
    DESCRIPTION
       "This group defines the statistics for the Application Server Provisioning Server process persistency."
    ::= { bwAsMibGroups 87 }

bwAsPsExtCallLogsGroup    OBJECT-GROUP
    OBJECTS { bwExternalCallLogsRetrievalAttempts, bwExternalCallLogsRetrievalFailures }
    STATUS  current
    DESCRIPTION
       "This group defines the statistics for the External Call Logs service on the Provisioning Server process."
    ::= { bwAsMibGroups 88 }

bwAsPsOciGroup    OBJECT-GROUP
    OBJECTS { psOciStatsNbUpdateRequests, psOciStatsNbUpdateRequestFailures, psOciStatsNbQueryRequests, psOciStatsNbQueryRequestFailures, psOciStatsNbAuthorizationRequests, psOciStatsNbAuthorizationRequestFailures, psOciStatsNbReportingAclViolations, psOciStatsNbReportNotificationsOut, psOciStatsActiveSessions, psOciStatsSystemRequestsPerHour, psOciStatsSystemRequestResponseTime, psOciStatsMinSystemRequestResponseTime, psOciStatsMaxSystemRequestResponseTime, psOciStatsMaxSystemRequestName, psOciStatsServiceProviderRequestsPerHour, psOciStatsServiceProviderRequestResponseTime, psOciStatsMinServiceProviderRequestResponseTime, psOciStatsMaxServiceProviderRequestResponseTime, psOciStatsMaxServiceProviderRequestName, psOciStatsGroupRequestsPerHour, psOciStatsGroupRequestResponseTime, psOciStatsMinGroupRequestResponseTime, psOciStatsMaxGroupRequestResponseTime, psOciStatsMaxGroupRequestName, psOciStatsUserRequestsPerHour, psOciStatsUserRequestResponseTime, psOciStatsMinUserRequestResponseTime, psOciStatsMaxUserRequestResponseTime, psOciStatsMaxUserRequestName, psOciStatsRequestsPerHour, psOciStatsRequestResponseTime, psOciStatsMinRequestResponseTime, psOciStatsMaxRequestResponseTime, psOciStatsMaxRequestName, psOCIReportingBackLogMessageTable, psOCIReportingBackLogMessageIndex, psOCIReportingBackLogMessageHost, psOCIReportingBackLogMessageSaved, psOCIReportingBackLogMessageSent }
    STATUS  current
    DESCRIPTION
       "This group defines the statistics for the OCI protocol running on Provisioning Server process."
    ::= { bwAsMibGroups 89 }

bwAsPsQueueStatsGroup    OBJECT-GROUP
    OBJECTS { psSystemInternalQueueResets, psSystemInternalQueueTable, psSystemInternalQueueIndex, psSystemInternalQueueName, psSystemInternalQueueSize, psSystemInternalQueueTimeAvg, psSystemInternalQueueTimeMin, psSystemInternalQueueTimeMax, psSystemInternalQueueTimeMaxTimestampMSB, psSystemInternalQueueLengthCurrent, psSystemInternalQueueLengthAvg, psSystemInternalQueueLengthMax, psSystemInternalQueueLengthMaxTimestampMSB, psSystemInternalQueueLengthMaxTimestampLSB, psSystemInternalQueueTimeMaxTimestampLSB }
    STATUS  current
    DESCRIPTION
       "This group defines the statistics for the Application Server processing internal queues for the Provisioning Server process."
    ::= { bwAsMibGroups 90 }

bwAsPsLdapGroup    OBJECT-GROUP
    OBJECTS { bwLDAPIntegrationNumQueryAttempts, bwLDAPIntegrationNumConnectionFailures }
    STATUS  current
    DESCRIPTION
       "This group defines the statistics for the LDAP protocol."
    ::= { bwAsMibGroups 91 }

bwAsPsBcctGroup    OBJECT-GROUP
    OBJECTS { bwCommonCommPSStatsTable, bwCommonCommPSStatsIndex, bwCommonCommPSHost, bwCommonCommPSInterface, bwCommonCommPSProtocol, bwCommonCommPSAcceptedOutboundConnections, bwCommonCommPSAcceptedInboundConnections, bwCommonCommPSRejectedOutboundConnections, bwCommonCommPSRejectedInboundConnections, bwCommonCommPSOutputMessagesProcessed, bwCommonCommPSInputMessagesProcessed, bwCommonCommPSOutputCommunicationErrors, bwCommonCommPSInputCommunicationErrors }
    STATUS  current
    DESCRIPTION
       "This group defines the statistics for the BCCT protocol from the Provisioning Server process."
    ::= { bwAsMibGroups 92 }

bwAsMoCountersGroup    OBJECT-GROUP
    OBJECTS { resetAllCounters }
    STATUS  current
    DESCRIPTION
       "This group defines statistics to perform managed object work for the Application Server."
    ::= { bwAsMibGroups 93 }

bwAsReservedGroup    OBJECT-GROUP
    OBJECTS { psReservedCounter }
    STATUS  current
    DESCRIPTION
       "MIB reserved section."
    ::= { bwAsMibGroups 94 }

bwAsPhysicalLocationServiceGroup    OBJECT-GROUP
    OBJECTS { bwPhysicalLocationOriginationBlocked, bwPhysicalLocationSPTable, bwPhysicalLocationGroupTable, bwPhysicalLocationSPIndex, bwPhysicalLocationSPID, bwPhysicalLocationSPOriginationBlocked, bwPhysicalLocationGroupIndex, bwPhysicalLocationGroupID, bwPhysicalLocationGroupOriginationBlocked }
    STATUS  current
    DESCRIPTION
       "This group defines the statistics for the Automatic Hold And Retrieve Service."
    ::= { bwAsMibGroups 95 }

bwAsFaxMessagingServiceGroup    OBJECT-GROUP
    OBJECTS { bwFaxMessagingReceived, bwFaxMessagingReceptionFailure, bwFaxMessagingPrinted, bwFaxMessagingPrintingFailure, bwFaxMessagingSPTable, bwFaxMessagingGroupTable, bwFaxMessagingSPIndex, bwFaxMessagingSPID, bwFaxMessagingSPReceived, bwFaxMessagingSPReceptionFailure, bwFaxMessagingSPPrinted, bwFaxMessagingSPPrintingFailure, bwFaxMessagingGroupIndex, bwFaxMessagingGroupID, bwFaxMessagingGroupReceived, bwFaxMessagingGroupReceptionFailure, bwFaxMessagingGroupPrinted, bwFaxMessagingGroupPrintingFailure }
    STATUS  current
    DESCRIPTION
       "This group defines the statistics for the Automatic Hold And Retrieve Service."
    ::= { bwAsMibGroups 96 }

bwPSTcpStatsGroup    OBJECT-GROUP
    OBJECTS { bwPSTcpServersStatsTable, bwPSTcpServersStatsIndex, bwPSTcpServersName, bwPSTcpServersNbConnectionsAccepted, bwPSTcpServersNbConnectionsClosed, bwPSTcpServersOutgoingQueueSize, bwPSTcpServersIncomingQueueSize, bwPSTcpServersNbBytesSentSecure, bwPSTcpServersNbBytesReceivedSecure }
    STATUS  current
    DESCRIPTION
       "This group defines the statistics for the Automatic Hold And Retrieve Service."
    ::= { bwAsMibGroups 97 }

bwXSTcpStatsGroup    OBJECT-GROUP
    OBJECTS { bwXSTcpServersStatsTable, bwXSTcpServersStatsIndex, bwXSTcpServersName, bwXSTcpServersNbConnectionsAccepted, bwXSTcpServersNbConnectionsClosed, bwXSTcpServersOutgoingQueueSize, bwXSTcpServersIncomingQueueSize, bwXSTcpServersNbBytesSentSecure, bwXSTcpServersNbBytesReceivedSecure }
    STATUS  current
    DESCRIPTION
       "This group defines the statistics for the Automatic Hold And Retrieve Service."
    ::= { bwAsMibGroups 98 }

bwPSConcurrentFrameworkStatsGroup    OBJECT-GROUP
    OBJECTS { bwPSMonitoringExecutorTable, bwPSMonitoringExecutorIndex, bwPSMonitoringExecutorName, bwPSMonitoringExecutorCurrentPoolSize, bwPSMonitoringExecutorMaxPoolSize, bwPSMonitoringExecutorAvgActiveThreads, bwPSMonitoringExecutorTaskQueueSize, bwPSMonitoringExecutorNbTasksRun, bwPSMonitoringExecutorNbWarnings, bwPSMonitoringExecutorNbErrors, bwPSMonitoringExecutorLongestTaskMs, bwPSMonitoringExecutorLongestTaskName }
    STATUS  current
    DESCRIPTION
       "This group defines the statistics for the Automatic Hold And Retrieve Service."
    ::= { bwAsMibGroups 99 }

bwXSConcurrentFrameworkStatsGroup    OBJECT-GROUP
    OBJECTS { bwXSMonitoringExecutorTable, bwXSMonitoringExecutorIndex, bwXSMonitoringExecutorName, bwXSMonitoringExecutorCurrentPoolSize, bwXSMonitoringExecutorMaxPoolSize, bwXSMonitoringExecutorAvgActiveThreads, bwXSMonitoringExecutorTaskQueueSize, bwXSMonitoringExecutorNbTasksRun, bwXSMonitoringExecutorNbWarnings, bwXSMonitoringExecutorNbErrors, bwXSMonitoringExecutorLongestTaskMs, bwXSMonitoringExecutorLongestTaskName }
    STATUS  current
    DESCRIPTION
       "This group defines the statistics for the Automatic Hold And Retrieve Service."
    ::= { bwAsMibGroups 100 }

bwAsExtEmergencyRtgStatsGroup    OBJECT-GROUP
    OBJECTS { bwExtEmergencyRtgQuerySent, bwExtEmergencyRtgQueryFailure, bwExtEmergencyRtgENServerTimeout }
    STATUS  current
    DESCRIPTION
       "This group defines the statistics for the Automatic Hold And Retrieve Service."
    ::= { bwAsMibGroups 101 }

bwAsSoapGroup    OBJECT-GROUP
    OBJECTS { bwSOAPMaxSessions, bwSOAPAvgSessions, bwSOAPMaxThreads, bwSOAPAvgThreads, bwSOAPMaxServiceTime, bwSOAPAvgServiceTime, bwSOAPNumDroppedRequests }
    STATUS  current
    DESCRIPTION
       "This group defines the statistics for SOAP."
    ::= { bwAsMibGroups 103 }
        
bwAsTwoStageDialingServiceGroup    OBJECT-GROUP
    OBJECTS { bwTwoStageDialingInvocation, bwTwoStageDialingSPTable, bwTwoStageDialingSPIndex, bwTwoStageDialingSPID, bwTwoStageDialingSPInvocation, bwTwoStageDialingGroupTable, bwTwoStageDialingGroupIndex, bwTwoStageDialingGroupID, bwTwoStageDialingGroupInvocation }
    STATUS  current
    DESCRIPTION
       "This group defines the statistics for the Two Stage Dialing Service."
    ::= { bwAsMibGroups 102 }

bwAsActivatableFeatureGroup    OBJECT-GROUP
    OBJECTS { bwActivatableFeatureTable, bwActivatableFeatureEntry, bwActivatableFeatureIndex, bwActivatableFeatureId, bwActivatableFeatureDescription, bwActivatableFeatureActivated }
    STATUS  current
    DESCRIPTION
       "This group defines the statistics for Activatable feature."
    ::= { bwAsMibGroups 104 } 

bwAsCallForwardingNotReachableGroup    OBJECT-GROUP
    OBJECTS { bwCFNRcNumForwarded, bwCFNRcNumPhoneActivations, bwCFNRcNumPhoneDeactivations, bwCFNRcDestinationChanged, bwCallForwardingNotReachableSPTable, bwCallForwardingNotReachableGroupTable, bwCFNRcSPIndex, bwCFNRcSPID, bwCFNRcSPNumForwarded, bwCFNRcSPNumPhoneActivations, bwCFNRcSPNumPhoneDeactivations, bwCFNRcSPDestinationChanged, bwCFNRcGroupIndex, bwCFNRcGroupID, bwCFNRcGroupNumForwarded, bwCFNRcGroupNumPhoneActivations, bwCFNRcGroupNumPhoneDeactivations, bwCFNRcGroupDestinationChanged }
    STATUS  current
    DESCRIPTION
       "This group defines the statistics for Call Forwarding Not Reachable."
    ::= { bwAsMibGroups 105 } 

bwMWIDeliveryToMobileGroup    OBJECT-GROUP
    OBJECTS { bwMWISMSSent, bwMWIDeliveryToMobileSPTable, bwMWISPIndex, bwMWISPID, bwSPMWISMSSent, bwMWIDeliveryToMobileGroupTable, bwMWIGroupIndex, bwMWIGroupID, bwGroupMWISMSSent }
    STATUS  current
    DESCRIPTION
       "This group defines the statistics for MWI Delivery to Mobile."
    ::= { bwAsMibGroups 106 } 

bwSharedCallAppearanceGroup    OBJECT-GROUP
    OBJECTS { bwSCASPTable, bwSCAGroupTable, bwSCACallRetrieveSuccess, bwSCALocationControlActivationSuccess, bwSCALocationControlDeactivationSuccess, bwSCASPIndex, bwSCASPIndex, bwSCASPCallRetrieveSuccess, bwSCASPLocationControlActivationSuccess, bwSCASPLocationControlDeactivationSuccess, bwSCAGroupIndex, bwSCAGroupID, bwSCAGroupCallRetrieveSuccess, bwSCAGroupLocationControlActivationSuccess, bwSCAGroupLocationControlDeactivationSuccess }
    STATUS  current
    DESCRIPTION
       "This group defines the statistics for Shared Call Appearance."
    ::= { bwAsMibGroups 107 } 

bwExternalCustomRingbackGroup    OBJECT-GROUP
    OBJECTS { bwExternalCustomRingbackAttempts, bwExternalCustomRingbackFailures, bwExternalCustomRingbackSPTable, bwExternalCustomRingbackGroupTable, bwExternalCustomRingbackSPEntry, bwExternalCustomRingbackSPIndex, bwExternalCustomRingbackSPID, bwExternalCustomRingbackSPAttempts, bwExternalCustomRingbackSPFailures, bwExternalCustomRingbackGroupEntry, bwExternalCustomRingbackGroupIndex, bwExternalCustomRingbackGroupID, bwExternalCustomRingbackGroupAttempts, bwExternalCustomRingbackGroupFailures }
    STATUS  current
    DESCRIPTION
       "This group defines the statistics for External Custom Ringback."
    ::= { bwAsMibGroups 109 }   

bwAsInCallServiceActivationGroup    OBJECT-GROUP
    OBJECTS { bwICSAMonitoringStarted, bwICSAMonitoringFailure, bwICSAFlashDigitsDetected, bwInCallServiceActivationSPTable, bwInCallServiceActivationGroupTable, bwICSASPIndex, bwICSASPID, bwICSASPMonitoringStarted, bwICSASPMonitoringFailure, bwICSASPFlashDigitsDetected, bwICSAGroupIndex, bwICSAGroupID, bwICSAGroupMonitoringStarted, bwICSAGroupMonitoringFailure, bwICSAGroupFlashDigitsDetected }
    STATUS  current
    DESCRIPTION
       "This group defines the statistics for In Call Service Activation."
    ::= { bwAsMibGroups 110 }   

bwCongestionManagementGroup    OBJECT-GROUP
    OBJECTS { bwCongestionManagementNeighborTable, bwCongestionManagementNeighborIndex, bwCongestionManagementNeighborIpAddress, bwCongestionManagementNeighborInviteIn, bwCongestionManagementNeighborInviteOut, bwCongestionManagementNeighborRegisterIn, bwCongestionManagementNeighborOptionsIn, bwCongestionManagementNeighborOptionsOut, bwCongestionManagementNeighborSubscribeNotifyIn, bwCongestionManagementNeighborSubscribeNotifyOut, bwCongestionManagementNeighbor5xxIn, bwCongestionManagementNeighborCallpMessageInRate,  bwCongestionManagementNeighborCallpMessageOutRate, bwCongestionManagementNeighborCallpRequestInRate, bwCongestionManagementNeighborNonCallpMessageInRate, bwCongestionManagementNeighborNonCallpMessageOutRate, bwCongestionManagementNeighborNonCallpRequestInRate, bwCongestionManagementNeighborState, bwCongestionManagementNeighborCapability }
    STATUS  current
    DESCRIPTION
       "This group defines the statistics for Congestion Management."
    ::= { bwAsMibGroups 111 }

bwShInterfaceGroup    OBJECT-GROUP
    OBJECTS { bwShInterfaceRequestsIn, bwShInterfaceRequestsOut, bwShInterfaceResponsesIn, bwShInterfaceResponsesOut, bwShInterfaceRequestTimeout, bwShInterfaceRequestResourceLimitation, bwShInterfaceUserDataRequest, bwShInterfaceUserDataRequestFailure, bwShInterfaceSubscribeNotificationsRequest, bwShInterfaceSubscribeNotificationsRequestFailure, bwShInterfacePushNotificationRequest, bwShInterfacePushNotificationRequestFailure, bwShInterfacePublicIdentityRefreshInitiated, bwShInterfacePublicIdentityRefreshFailure, bwShInterfaceSystemRefreshInitiated }
    STATUS  current
    DESCRIPTION
       "This group defines the statistics for the SH Interface."
    ::= { bwAsMibGroups 112 }

bwDnsQueryGroup     OBJECT-GROUP
    OBJECTS { bwDnsQueryTimeMax, bwDnsQueryTimeMaxTimestampMSB, bwDnsQueryTimeMaxTimestampLSB, bwDnsQueryTimeAvg, bwDnsStatsQueriesTable, bwDnsStatsQueriesEntry, bwDnsStatsQueryIndex, bwDnsStatsQueryType, bwDnsStatsQueries, bwDnsStatsQueryTimeouts }
    STATUS  current
    DESCRIPTION
       "This group defines the statistics for DNS query."
    ::= { bwAsMibGroups 113 } 

bwAsExpensiveCallNotificationGroup OBJECT-GROUP
  OBJECTS { bwECNWarningAnnouncementAttempts, bwECNExpensiveCallReleased }
  STATUS current
  DESCRIPTION
    "This group defines the statistics for expensive call notification."
  ::= { bwAsMibGroups 114 }

bwLocationControlGroup OBJECT-GROUP
    OBJECTS { bwLocationControlSPTable, bwLocationControlGroupTable, bwLocationControlActivationSuccess, bwLocationControlDeactivationSuccess, bwLocationControlSPEntry, bwLocationControlSPIndex, bwLocationControlSPID, bwLocationControlSPActivationSuccess, bwLocationControlSPDeactivationSuccess, bwLocationControlGroupEntry, bwLocationControlGroupIndex, bwLocationControlGroupID, bwLocationControlGroupActivationSuccess, bwLocationControlGroupDeactivationSuccess }
    STATUS current
    DESCRIPTION
      "This group defines the location control service."
    ::= { bwAsMibGroups 115 }

bwCallRetrieveGroup OBJECT-GROUP
    OBJECTS {   bwCallRetrieveSPTable, bwCallRetrieveGroupTable, bwCallRetrieveSuccess, bwCallRetrieveSPEntry, bwCallRetrieveSPIndex, bwCallRetrieveSPID, bwCallRetrieveSPSuccess, bwCallRetrieveGroupEntry, bwCallRetrieveGroupIndex, bwCallRetrieveGroupID, bwCallRetrieveGroupSuccess }
    STATUS current
    DESCRIPTION
      "This group defines the call retrieve service."
    ::= { bwAsMibGroups 116 }

bwBroadworksAnywhereGroup OBJECT-GROUP
    OBJECTS { bwBroadWorksAnywhereSPTable, bwBroadWorksAnywhereGroupTable, bwBACallOriginations, bwBACallTerminations, bwBroadWorksAnywhereSPEntry, bwBroadWorksAnywhereSPIndex, bwBroadWorksAnywhereSPID, bwBASPCallOriginations, bwBASPCallTerminations, bwBroadWorksAnywhereGroupEntry, bwBroadWorksAnywhereGroupIndex, bwBroadWorksAnywhereGroupID, bwBAGroupCallOriginations, bwBAGroupCallTerminations }
      STATUS current
    DESCRIPTION
      "This group defines the BroadWorks Anywhere service."
    ::= { bwAsMibGroups 117 }  


psVoiceMessagingGroup OBJECT-GROUP
  OBJECTS { psBwVMRNumLoginAttempts, psBwVMRNumLoginFailures, psBwVMRSPIndex, psBwVMRSPID, psBwVMRSPNumLoginAttempts, psBwVMRSPNumLoginFailures, psBwVMRGroupIndex, psBwVMRGroupID, psBwVMRGroupNumLoginAttempts, psBwVMRGroupNumLoginFailures }
  STATUS current
  DESCRIPTION
    "This group defines the Voice Messaging service."
  ::= { bwAsMibGroups 121 }          

psPolycomPhoneServiceGroup OBJECT-GROUP
  OBJECTS { bwPolycomPhoneDirectoryNumDownloads, polycomSPIndex, polycomSPID, bwPolycomPhoneDirectorySPNumDownloads, polycomGroupIndex, polycomGroupID, bwPolycomPhoneDirectoryGroupNumDownloads  }
  STATUS current
  DESCRIPTION
    "This group defines the Polycom Phone service."
  ::= { bwAsMibGroups 122 }
  
-- 
bwAsBasicCompliance MODULE-COMPLIANCE
        STATUS current
        DESCRIPTION
                "BroadWorks Application Server MIB compliance"
        MODULE -- this module
    MANDATORY-GROUPS { bwAsMgcpGroup, bwAsMcpGroup, bwAsImsGroup, bwAsCapGroup, bwAsSmdiGroup, bwAsMediaResourceGroup, bwAsWholeSalesGroup, bwAsRealTimeAccntGroup, bwAsExtCallLogsGroup, bwAsXsBcctGroup, bwAsCpeDeviceGroup, bwAsCallpGroup, bwAsSmtpGroup, bwAsSipGroup, bwAsAccntCodeServiceGroup, bwAsAnonymousCallRejectionServiceGroup, bwAsAuthenticationServiceGroup, bwAsAutoAttendantServiceGroup, bwAsCallCapacityServiceGroup, bwAsCFAlwaysServiceGroup, bwAsCFBusyServiceGroup, bwAsCFNoAnswerServiceGroup, bwAsCallNotifyServiceGroup, bwAsCallParkServiceGroup, bwAsCallPickupServiceGroup, bwAsCallReturnServiceGroup, bwAsCompilotCallMgrServiceGroup, bwAsDoNotDisturbServiceGroup, bwAsFlashCallXferServiceGroup, bwAsFlashCallWaitingServiceGroup, bwAsFlashConsultationServiceGroup, bwAsFlash3wcServiceGroup, bwAsHuntGroupServiceGroup, bwAsIcpServiceGroup, bwAsIpPhoneServiceGroup, bwAsLastNumberRedialServiceGroup, bwAsOcpServiceGroup, bwAsPriorityAlertServiceGroup, bwAsSelectiveCallAcceptanceServiceGroup, bwAsSelectiveCallForwardServiceGroup, bwAsSelectiveCallRejectionServiceGroup, bwAsSimRingServiceGroup, bwAsVoiceMessagingServiceGroup, bwAsSeriesCompletionServiceGroup, bwAsInterceptServiceGroup, bwAsInstantConferencingServiceGroup, bwAsCallingLineIdBlockingServiceGroup, bwAsSessionAuditServiceGroup, bwAsWindowsMessagingServiceGroup, bwAsCalWaitingServiceGroup, bwAsAlternateNumberServiceGroup, bwAsCustomerOriginatedTraceServiceGroup, bwAsSpeedDialing8ServiceGroup, bwAsMusicOnHoldServiceGroup, bwAsCallingNameQueriesServiceGroup, bwAsThirdPartyMWIControlServiceGroup, bwAsCallCenterServiceGroup, bwAsCallForwardGroupNoAnswerServiceGroup, bwAsSpeedDialing100ServiceGroup, bwAsThirdPartyVoiceMailServiceGroup, bwAsDirectedCallPickupServiceGroup, bwAsFlashCallHoldServiceGroup, bwAsEmergencyZoneServiceGroup, bwAsDirectedCallPickupWithBargeInServiceGroup, bwAsAutomaticCallBackServiceGroup, bwAsRingTimeoutServiceGroup, bwAsSequentialRingServiceGroup, bwAsVideoAddOnServiceGroup, bwAsMaliciousCallTraceServiceGroup, bwAsPushToTalkServiceGroup, bwAsHotelingServiceGroup, bwAsPreferredCarrierServiceGroup, bwAsFamilySimRingServiceGroup, bwAsDiversionInhibitorServiceGroup, bwAsInstantGroupCallServiceGroup, bwAsAutomaticHoldAndRetrieveServiceGroup, bwAsBusinessTrunkGroupServiceGroup, bwAsCustomRingbackServiceGroup, bwAsMssGroup, bwAsNrsGroup, bwAsXsPersistencyGroup, bwAsProtocolMonitorGroup, bwAsSystemStatsGroup, bwAsQueueStatsGroup, bwAsOverloadControlStatsGroup, bwAsRedundancyStatsGroup, bwAsPsPersistencyGroup, bwAsPsExtCallLogsGroup, bwAsPsOciGroup, bwAsPsQueueStatsGroup, bwAsPsLdapGroup, bwAsPsBcctGroup, bwAsMoCountersGroup, bwAsReservedGroup, bwAsPhysicalLocationServiceGroup, bwAsFaxMessagingServiceGroup, bwPSTcpStatsGroup, bwXSTcpStatsGroup, bwPSConcurrentFrameworkStatsGroup, bwXSConcurrentFrameworkStatsGroup, bwAsExtEmergencyRtgStatsGroup, bwAsTwoStageDialingServiceGroup, bwAsSoapGroup, bwAsActivatableFeatureGroup, bwAsCallForwardingNotReachableGroup, bwMWIDeliveryToMobileGroup, bwSharedCallAppearanceGroup, bwExternalCustomRingbackGroup, bwAsInCallServiceActivationGroup, bwCongestionManagementGroup, bwShInterfaceGroup, bwDnsQueryGroup, bwAsExpensiveCallNotificationGroup, bwLocationControlGroup, bwCallRetrieveGroup, bwBroadworksAnywhereGroup, psVoiceMessagingGroup, psPolycomPhoneServiceGroup }
        ::= { bwAsMibCompliancy 1 }

-- End of MIB file - Do not put anything behind this line ...........................................

END
