ACC-DN DEFINITIONS ::= BEGIN

    IMPORTS
	 OBJECT-TYPE, TimeTicks, Counter FROM RFC1155-SMI
                              accTrapLogSeqNum FROM ACC-SYSTEM
accBRG, DisplayString, RowStatus, IfIndex, SmdsAddress
             FROM ACC-MIB;
-- DECnet Group
      accDn        OBJECT IDENTIFIER  ::= { accBRG 19 }
	accDnNumber	OBJECT-TYPE  
			SYNTAX	INTEGER
			ACCESS read-only
			STATUS mandatory
			DESCRIPTION
			 " Number of DECNET circuits"
			::= { accDn 1 }
	accDnID		OBJECT-TYPE  
			SYNTAX	INTEGER
			ACCESS read-write
			STATUS mandatory
			DESCRIPTION
			 " Node ID;  Least 10 bits identify the node,
			   six bits above that identify the area."
			::= { accDn 2 }
	accDnMaxNode	OBJECT-TYPE  
			SYNTAX	INTEGER (1..1023)
			ACCESS read-write
			STATUS mandatory
			DESCRIPTION
			 " Maximum node number permitted in the local area"
			::= { accDn 3 }
	accDnMaxArea	OBJECT-TYPE  
			SYNTAX	INTEGER (1..63)
			ACCESS read-write
			STATUS mandatory
			DESCRIPTION
			 " Maximum area number permitted"
			::= { accDn 4 }
	accDnMaxAdjRtr	OBJECT-TYPE  
			SYNTAX	INTEGER (1..64)
			ACCESS read-write
			STATUS mandatory
			DESCRIPTION
			 " Maximum number of adjacent routers "
			::= { accDn 5 }
	accDnMaxEndNode OBJECT-TYPE  
			SYNTAX	INTEGER (1..1023)
			ACCESS read-write
			STATUS mandatory
			DESCRIPTION
			 " Maximum number of broadcast endnode adjacencies"
			::= { accDn 6 }
	accDnMaxLocHop	OBJECT-TYPE  
			SYNTAX	INTEGER (1..30)
			ACCESS read-write
			STATUS mandatory
			DESCRIPTION
			 " Maximum number of hops allowed within this area"
			::= { accDn 7 }
	accDnMaxLocCost OBJECT-TYPE  
			SYNTAX	INTEGER (1..1022)
			ACCESS read-write
			STATUS mandatory
			DESCRIPTION
			 " Maximum cost allowed on a path within this area"
			::= { accDn 8 }
	accDnMaxVisit	OBJECT-TYPE  
			SYNTAX	INTEGER (1..63)
			ACCESS read-write
			STATUS mandatory
			DESCRIPTION
			 " Maximum number of node visits allowed for a packet"
			::= { accDn 9 }
	accDnMaxForHop	OBJECT-TYPE  
			SYNTAX	INTEGER (1..30)
			ACCESS read-write
			STATUS mandatory
			DESCRIPTION
			 " Maximum number of hops allowed to another area"
			::= { accDn 10 }
	accDnMaxForCost OBJECT-TYPE  
			SYNTAX	INTEGER (1..1022)
			ACCESS read-write
			STATUS mandatory
			DESCRIPTION
			 " Maximum cost allowed on a path to another area"
			::= { accDn 11 }
	accDnBCT1		OBJECT-TYPE  
			SYNTAX	TimeTicks
			ACCESS read-write
			STATUS mandatory
			DESCRIPTION
			 " Interval between retranmissions of routing
			   database updates on Broadcast Address"
			::= { accDn 12 }
	accDnT1		OBJECT-TYPE  
			SYNTAX	TimeTicks
			ACCESS read-write
			STATUS mandatory
			DESCRIPTION
			 " Interval between retranmissions of routing
			   database updates  non-broadcast"
			::= { accDn 13 }
	accDnMsgLev	OBJECT-TYPE  
			SYNTAX	INTEGER (1..7)
			ACCESS read-write
			STATUS mandatory
			DESCRIPTION
			 " Message level for generation of trap messages
			   describing DECNET operational phenonomena
			   See Trap level for description"
			::= { accDn 14 }
	accDnNodeState	OBJECT-TYPE  
			SYNTAX	INTEGER {
			off(1),
			level1(2),
			level2(3)
			}
			ACCESS read-write
			STATUS mandatory
			DESCRIPTION
			 " Operational state of the node "
			::= { accDn 15 }
	accDnUnreachs	OBJECT-TYPE  
			SYNTAX	Counter
			ACCESS read-only
			STATUS mandatory
			DESCRIPTION
			 " Packets dropped due to node unreachable"
			::= { accDn 16 }
	accDnVisitXcds	OBJECT-TYPE  
			SYNTAX	Counter
			ACCESS read-only
			STATUS mandatory
			DESCRIPTION
			 " Packets dropped due to visits exceeded"
			::= { accDn 17 }
	accDnBadNodes	OBJECT-TYPE  
			SYNTAX	Counter
			ACCESS read-only
			STATUS mandatory
			DESCRIPTION
			 " Packets dropped due to illegal node number"
			::= { accDn 18 }
	accDnPktOsizes OBJECT-TYPE  
			SYNTAX	Counter
			ACCESS read-only
			STATUS mandatory
			DESCRIPTION
			 " Packets dropped due to oversize packet"
			::= { accDn 19 }
	accDnFmtErrs	OBJECT-TYPE  
			SYNTAX	Counter
			ACCESS read-only
			STATUS mandatory
			DESCRIPTION
			 " Packets dropped due to packet format error"
			::= { accDn 20 }
	accDnCktTable  OBJECT-TYPE
			SYNTAX  SEQUENCE OF AccDnCktEntry
			ACCESS not-accessible
			STATUS mandatory
			DESCRIPTION
                         " DECnet circuit table
			   Entries are added/deleted via management action."
			::= { accDn 21 }
	  accDnCktEntry	 OBJECT-TYPE
			SYNTAX AccDnCktEntry
			ACCESS not-accessible
			STATUS mandatory
	  		DESCRIPTION
			 " The instance of an entry is the circuit number.
			   Existing entries can be modified."
                        INDEX { accDnCktIndex }
	  		::= { accDnCktTable 1 }
	    AccDnCktEntry ::= SEQUENCE {
			accDnCktIndex		INTEGER,
			accDnCktStatus		INTEGER,
			accDnCktState		INTEGER,
			accDnCktCost		INTEGER,
			accDnMaxRtr		INTEGER,
			accDnHelloInt		TimeTicks,
			accDnRtrPriority	INTEGER,
			accDnDesRtrId		OCTET STRING,
			accDnDesRtrPrio		INTEGER,
			accDnTrnPktRecs		Counter,
			accDnTrnPktSnds		Counter,
			accDnEndNodePktRecs	Counter,
			accDnEndNodePktSnds	Counter,
			accDnCktDowns		Counter,
			accDnCktType		INTEGER,
			accDnCktPort		INTEGER,
			accDnX25InOutAddr	DisplayString,
			accDnX25InAddr		DisplayString,
			accDnX25Idle		TimeTicks,
			accDnX25PktVal		INTEGER,
			accDnX25PktWin		INTEGER,
			accDnEntryStatus	INTEGER,
			accDnX25FacIndex	INTEGER
		    	}
	    accDnCktIndex  OBJECT-TYPE	
			SYNTAX	INTEGER
			ACCESS	read-write
			STATUS	mandatory
			DESCRIPTION
			 " Circuit number "
			::= { accDnCktEntry 1 }
	    accDnCktStatus  OBJECT-TYPE	 
			SYNTAX	INTEGER {
				on(1),
				off(2)
			}
			ACCESS	read-write
			STATUS	mandatory
			DESCRIPTION
			 " Administrative DECNET state of this circuit"
                        DEFVAL { off }
			::= { accDnCktEntry 2 }
	    accDnCktState  OBJECT-TYPE	
			SYNTAX	INTEGER {
				up(1),
				down(2),
				shut(3),
				start(4),
				test(5)
			   }
			ACCESS	read-only
			STATUS	mandatory
			DESCRIPTION
			 " Operational DECNET state of this circuit"
			::= { accDnCktEntry 3 }
	    accDnCktCost  OBJECT-TYPE  
			SYNTAX	INTEGER (1..1022)
			ACCESS	read-write
			STATUS	mandatory
			DESCRIPTION
			 " Administrative circuit cost
			   Object will be set to a circuit-type
                           dependent value if not present
			      in entry-adding SET PDU."
			::= { accDnCktEntry 4 }
	    accDnMaxRtr	 OBJECT-TYPE  
			SYNTAX	INTEGER (1..32)
			ACCESS	read-write
			STATUS	mandatory
			DESCRIPTION
			 " Maximum number of routers that can be
			   communicated with over this circuit"
                        DEFVAL { 4 }
			::= { accDnCktEntry 5 }
	    accDnHelloInt  OBJECT-TYPE	
			SYNTAX	TimeTicks
			ACCESS	read-write
			STATUS	mandatory
			DESCRIPTION
			 " Interval between transmission of Router Hello
			   messages to other DECNET routers on this circuit"
                        DEFVAL { 15 }
			::= { accDnCktEntry 6 }
	    accDnRtrPriority  OBJECT-TYPE  
			SYNTAX	INTEGER (0..255)
			ACCESS	read-write
			STATUS	mandatory
			DESCRIPTION
			 " Priority of this Decnet router to become
			   designated router on this circuit."
                        DEFVAL { 15 }
			::= { accDnCktEntry 7 }
	    accDnDesRtrId  OBJECT-TYPE	
			SYNTAX  OCTET STRING -- (SIZE(3))	
			ACCESS	read-only
			STATUS	mandatory
			DESCRIPTION
			 " ID of router which is designated router on
			   this circuit.  Lower 10 bits is node number,
			   six bits above that are area number."
			::= { accDnCktEntry 8 }
	    accDnDesRtrPrio  OBJECT-TYPE  
			SYNTAX	INTEGER (0..255)
			ACCESS	read-only
			STATUS	mandatory
			DESCRIPTION
			 " Priority of router which is designated router on
			   this circuit.  "
			::= { accDnCktEntry 9 }
	    accDnTrnPktRecs  OBJECT-TYPE	 
			SYNTAX	Counter
			ACCESS	read-only
			STATUS	mandatory
			DESCRIPTION
			 " Number of transit packets received on
			   this circuit."
			::= { accDnCktEntry 10 }
	    accDnTrnPktSnds  OBJECT-TYPE	 
			SYNTAX	Counter
			ACCESS	read-only
			STATUS	mandatory
			DESCRIPTION
			 " Number of transit packets sent on
			   this circuit."
			::= { accDnCktEntry 11 }
	    accDnEndNodePktRecs	OBJECT-TYPE  
			SYNTAX	Counter
			ACCESS	read-only
			STATUS	mandatory
			DESCRIPTION
			 " Number of end-node packets received on
			   this circuit."
			::= { accDnCktEntry 12 }
	    accDnEndNodePktSnds	OBJECT-TYPE  
			SYNTAX	Counter
			ACCESS	read-only
			STATUS	mandatory
			DESCRIPTION
			 " Number of end-node packets sent on
			   this circuit."
			::= { accDnCktEntry 13 }
	    accDnCktDowns  OBJECT-TYPE  
			SYNTAX	Counter
			ACCESS	read-only
			STATUS	mandatory
			DESCRIPTION
			 " Number of circuit down events noted on
			   this circuit."
			::= { accDnCktEntry 14 }
	    accDnCktType  OBJECT-TYPE  
			SYNTAX	INTEGER {
				enet(6),
				trn(9),
				lapb(16),
				mlink(129),
				x25(130),
				fr(131)
			    }
			ACCESS	read-write
			STATUS	mandatory
			DESCRIPTION
			 " Circuit type
			   Object required in entry-adding SET PDU."
			::= { accDnCktEntry 15 }
	    accDnCktPort  OBJECT-TYPE  
			SYNTAX	INTEGER {
				j1(1),
				j2(2),
				j3(3)
			    }
			ACCESS	read-write
			STATUS	mandatory
			DESCRIPTION
			 " Physical port that this circuit is on
			   Object required in entry-adding SET PDU."
			::= { accDnCktEntry 16 }
	    accDnX25InOutAddr  OBJECT-TYPE  
			SYNTAX  DisplayString	
			ACCESS	read-write
			STATUS	mandatory
			DESCRIPTION
			 " X25 address for other end of circuit; we'll
			   send to this address and will accept packets from
			   this address for this circuit.
			   Object required in entry-adding SET PDU if
			      circuit type is X.25"
			::= { accDnCktEntry 17 }
	    accDnX25InAddr  OBJECT-TYPE  
			SYNTAX  DisplayString	
			ACCESS	read-write
			STATUS	mandatory
			DESCRIPTION
			 "  Packets from this address are accepted 
			   on this circuit.
			   Object will be set to default value if not present
			       in entry-adding SET PDU."
			::= { accDnCktEntry 18 }
	    accDnX25Idle  OBJECT-TYPE  
			SYNTAX	TimeTicks
			ACCESS	read-write
			STATUS	mandatory
			DESCRIPTION
			 " Maximum idle time before this circuit is 
			   considered unused.
			   Object will be set to default value if not present
			       in entry-adding SET PDU."
			::= { accDnCktEntry 19 }
	    accDnX25PktVal  OBJECT-TYPE  
			SYNTAX	INTEGER (0..1024)
			ACCESS	read-write
			STATUS	mandatory
			DESCRIPTION
			 " Maximum X25 packet size
			   Object will be set to default value if not present
			       in entry-adding SET PDU."
			::= { accDnCktEntry 20 }
	    accDnX25PktWin  OBJECT-TYPE  
			SYNTAX	INTEGER (0..127)
			ACCESS	read-write
			STATUS	mandatory
			DESCRIPTION
			 " X25 packet window
			   Object will be set to default value if not present
			       in entry-adding SET PDU."
			::= { accDnCktEntry 21 }
	    accDnEntryStatus  OBJECT-TYPE  
			SYNTAX	INTEGER {
				other(1),
				invalid(2)
			    }
			ACCESS	read-write
			STATUS	mandatory
			DESCRIPTION
			 " Setting this object to invalid deletes entry"
			::= { accDnCktEntry 22 }
	accDnX25FacIndex  OBJECT-TYPE
	           SYNTAX  INTEGER (0..255)
	           ACCESS  read-write
	           STATUS  mandatory
	           DESCRIPTION
	                " Index of optional facility string or 0."
	           DEFVAL { 0 }
	           ::= { accDnCktEntry 23 }
	accDnRtTable  OBJECT-TYPE
			SYNTAX  SEQUENCE OF AccDnRtEntry
			ACCESS not-accessible
			STATUS mandatory
			DESCRIPTION
			 " DECnet routing table"
			::= { accDn 22 }
	  accDnRtEntry	OBJECT-TYPE
			SYNTAX AccDnRtEntry
			ACCESS not-accessible
			STATUS mandatory
	  		DESCRIPTION
		            " Detail on specific route "
                        INDEX { accDnRtNode }
	  		::= { accDnRtTable 1 }
             AccDnRtEntry ::= SEQUENCE {
			accDnRtNode		INTEGER,
			accDnRtHops		INTEGER,
			accDnRtCost		INTEGER,
			accDnRtCkt		INTEGER,
			accDnRtNextHop		INTEGER
			}
	    accDnRtNode	 OBJECT-TYPE  
			SYNTAX	INTEGER
			ACCESS	read-only
			STATUS	mandatory
			DESCRIPTION
			 " Destination node"
			::= { accDnRtEntry 1 }
	    accDnRtHops	 OBJECT-TYPE  
			SYNTAX	INTEGER
			ACCESS	read-only
			STATUS	mandatory
			DESCRIPTION
			 " Number of hops to destination"
			::= { accDnRtEntry 2 }
	    accDnRtCost	 OBJECT-TYPE  
			SYNTAX	INTEGER
			ACCESS	read-only
			STATUS	mandatory
			DESCRIPTION
			 " Cost to destination"
			::= { accDnRtEntry 3 }
	    accDnRtCkt	OBJECT-TYPE  
			SYNTAX	INTEGER
			ACCESS	read-only
			STATUS	mandatory
			DESCRIPTION
			 " Circuit number to use to get to destination"
			::= { accDnRtEntry 4 }
	    accDnRtNextHop  OBJECT-TYPE	 
			SYNTAX	INTEGER
			ACCESS	read-only
			STATUS	mandatory
			DESCRIPTION
			 " Next router along the way to destination"
			::= { accDnRtEntry 5 }
	accDnAreaTable	OBJECT-TYPE
			SYNTAX SEQUENCE OF AccDnAreaEntry
			ACCESS not-accessible
			STATUS mandatory
			DESCRIPTION
			 " DECnet area table."
			::= { accDn 23 }
	  accDnAreaEntry  OBJECT-TYPE
			SYNTAX  AccDnAreaEntry
			ACCESS not-accessible
			STATUS mandatory
			DESCRIPTION
		        " Details on specific area "
                        INDEX { accDnAreaArea }
			::= { accDnAreaTable 1 }
	      AccDnAreaEntry ::= SEQUENCE {
			accDnAreaArea		INTEGER,
			accDnAreaHops		INTEGER,
			accDnAreaCost		INTEGER,
			accDnAreaCkt		INTEGER,
			accDnAreaNextHop	INTEGER
			}
	    accDnAreaArea  OBJECT-TYPE	
			SYNTAX	INTEGER
			ACCESS	read-only
			STATUS	mandatory
			DESCRIPTION
			 " Remote area"
			::= { accDnAreaEntry 1 }
	    accDnAreaHops  OBJECT-TYPE	
			SYNTAX	INTEGER
			ACCESS	read-only
			STATUS	mandatory
			DESCRIPTION
			 " Hops to Remote area"
			::= { accDnAreaEntry 2 }
	    accDnAreaCost  OBJECT-TYPE	
			SYNTAX	INTEGER
			ACCESS	read-only
			STATUS	mandatory
			DESCRIPTION
			 " Cost to Remote area"
			::= { accDnAreaEntry 3 }
	    accDnAreaCkt  OBJECT-TYPE  
			SYNTAX	INTEGER
			ACCESS	read-only
			STATUS	mandatory
			DESCRIPTION
			 " Circuit over which remote area can be reached."
			::= { accDnAreaEntry 4 }
	    accDnAreaNextHop  OBJECT-TYPE  
			SYNTAX	INTEGER
			ACCESS	read-only
			STATUS	mandatory
			DESCRIPTION
			 " Next hop to remote area."
			::= { accDnAreaEntry 5 }
     --  DECNET IV Route Filters are used to suppress acceptance of
     --  advertisements of level 1 and level 2 routes.
     accDnRouteFilterTable OBJECT-TYPE
         SYNTAX   SEQUENCE OF AccDnRouteFilterEntry
         ACCESS   not-accessible
         STATUS   mandatory
         DESCRIPTION
             " The DECNET IV Routes that the Network Manager wants to
               be careful about."
         ::= { accDn 24 }
       accDnRouteFilterEntry OBJECT-TYPE
           SYNTAX   AccDnRouteFilterEntry
           ACCESS   not-accessible
           STATUS   mandatory
           DESCRIPTION
               " A single controlled DECNET Route."
           INDEX { accDnRouteFilterAdj, accDnRouteFilterNode }
           ::= { accDnRouteFilterTable 1 }
       AccDnRouteFilterEntry ::=
           SEQUENCE {
               accDnRouteFilterAdj
                   INTEGER,
               accDnRouteFilterNode
                   INTEGER,
               accDnRouteFilterDisposition
                   INTEGER,
               accDnRouteFilterEntStat
                   INTEGER
       }
         accDnRouteFilterAdj OBJECT-TYPE
             SYNTAX   INTEGER (0..65535)
             ACCESS   read-write
             STATUS   mandatory
            DESCRIPTION
                 " If 0, all adjacent systems.
                   If a DECNET Area with host id 0,  all  adjacent
                   systems in that area.
                   If a DECNET Host ID, that adjacent system."
            ::= { accDnRouteFilterEntry 1 }
         accDnRouteFilterNode OBJECT-TYPE
             SYNTAX   INTEGER (0..65535)
             ACCESS   read-write
             STATUS   mandatory
            DESCRIPTION
                 " If 0, all routing information.
                   If a DECNET Area with Host ID 0, relevant level
                   2 routing information.
                   If a DECNET Host ID, level 1  routing  informa-
                   tion for that host."
            ::= { accDnRouteFilterEntry 2 }
         accDnRouteFilterDisposition OBJECT-TYPE
             SYNTAX   INTEGER {
                         accept(1),
                         reject(2)
                      }
             ACCESS   read-write
             STATUS   mandatory
            DESCRIPTION
                 " This variable indicates what to  do  with  the
                   indicated  routing information.  Where overlaps
                   occur ('accept no routing information from area
                   3.0 except from router 3.27'), the most specif-
                   ic match applies."
            ::= { accDnRouteFilterEntry 3 }
         accDnRouteFilterEntStat OBJECT-TYPE
             SYNTAX   INTEGER {
                         invalid(1),
                         valid(2)
                      }
             ACCESS   read-write
             STATUS   mandatory
            DESCRIPTION
                 " setting this variable to 'invalid' has the ef-
                   fect  of  invalidating it as of the next system
                   reset."
            ::= { accDnRouteFilterEntry 4 }
     --  DECNET Forwarding Filter Table
     --  DECNET Forwarding Filter indicates routes from source
     --  to destination.  Traffic on those routes is affected.
     accDnForwardFilterTable OBJECT-TYPE
         SYNTAX   SEQUENCE OF AccDnForwardFilterEntry
         ACCESS   not-accessible
         STATUS   mandatory
         DESCRIPTION
             " The DECNET traffic that the Network Manager wants
               selectively treated."
         ::= { accDn 25 }
     accDnForwardFilterEntry OBJECT-TYPE
         SYNTAX   AccDnForwardFilterEntry
         ACCESS   not-accessible
         STATUS   mandatory
         DESCRIPTION
             " A single set of messages that the Network Manager
               wants selectively treated."
         INDEX { accDnForwardFilterDest, 
                 accDnForwardFilterSource }
         ::= { accDnForwardFilterTable 1 }
     AccDnForwardFilterEntry ::=
         SEQUENCE {
             accDnForwardFilterDest
                 INTEGER,
             accDnForwardFilterSource
                 INTEGER,
             accDnForwardFilterDisposition
                 INTEGER,
             accDnForwardFilterEntStat
                 INTEGER
     }
         accDnForwardFilterDest OBJECT-TYPE
             SYNTAX   INTEGER (0..65535)
             ACCESS   read-write
             STATUS   mandatory
            DESCRIPTION
                 " If 0, all DECNET Addresses.
                   If an Area with Host Part  0,  all  traffic  to
                   that Area.
                   If a DECNET Host ID, all traffic to that Host."
            ::= { accDnForwardFilterEntry 1 }
         accDnForwardFilterSource OBJECT-TYPE
             SYNTAX   INTEGER (0..65535)
             ACCESS   read-write
             STATUS   mandatory
            DESCRIPTION
                 " If 0, all DECNET Traffic.
                   If an Area with Host Part 0, all  traffic  from
                   that Area.
                   If a DECNET Host  ID,  all  traffic  from  that
                   Host."
            ::= { accDnForwardFilterEntry 2 }
         accDnForwardFilterDisposition OBJECT-TYPE
             SYNTAX   INTEGER {
                         discard(0),
                         lowPriority(1),
                         normalPriority(2),
                         highPriority(3)
                      }
             ACCESS   read-write
             STATUS   mandatory
            DESCRIPTION
                 " This variable indicates what  is  to  be  done
                   with  traffic  from accDnForwardFilterSource to
                   accDnForwardFilterDest.   When  overlaps  occur
                   ('discard all traffic from Area 4.0 to Anywhere
                   except traffic  from  Host  4.123'),  the  most
                   specific match applies.
		"
            ::= { accDnForwardFilterEntry 3 }
         accDnForwardFilterEntStat OBJECT-TYPE
             SYNTAX   INTEGER {
                         invalid(1),
                         valid(2)
                      }
             ACCESS   read-write
             STATUS   mandatory
            DESCRIPTION
                 " setting accDnForwardFilterEntStat  to  invalid
                   has  the  effect  of removing the filter on the
                   next system reset."
            ::= { accDnForwardFilterEntry 4 }
     --  DECNET Adjacent System Table
     --  This table displays all systems maintaining current DECNET
     --  adjacencies with the system being queried.
     accDnAdjTable OBJECT-TYPE
         SYNTAX   SEQUENCE OF AccDnAdjEntry
         ACCESS   not-accessible
         STATUS   mandatory
         DESCRIPTION
             " The set of systems adjacent to this router."
         ::= { accDn 26 }
     accDnAdjEntry OBJECT-TYPE
         SYNTAX   AccDnAdjEntry
         ACCESS   not-accessible
         STATUS   mandatory
         DESCRIPTION
             " One of the systems adjacent to this router."
         INDEX { accDnAdjNode }
         ::= { accDnAdjTable 1 }
     AccDnAdjEntry ::=
         SEQUENCE {
             accDnAdjNode
                 INTEGER,
             accDnAdjType
                 INTEGER,
             accDnAdjCircuit
                 INTEGER,
             accDnAdjState
                 INTEGER
     }
         accDnAdjNode OBJECT-TYPE
             SYNTAX   INTEGER (0..65535)
             ACCESS   read-only
             STATUS   mandatory
            DESCRIPTION
                 " The Host Identifier of the adjacent node."
            ::= { accDnAdjEntry 1 }
         accDnAdjType OBJECT-TYPE
             SYNTAX   INTEGER {
                         level2Only(1),
                         level2(2),
                         level1(3),
                         endNode(4)
                      }
             ACCESS   read-only
             STATUS   mandatory
            DESCRIPTION
                 " The type of DECNET adjacency being sustained."
            ::= { accDnAdjEntry 2 }
         accDnAdjCircuit OBJECT-TYPE
             SYNTAX   INTEGER
             ACCESS   read-only
             STATUS   mandatory
            DESCRIPTION
                 " The DECNET Circuit Number."
            ::= { accDnAdjEntry 3 }
         accDnAdjState OBJECT-TYPE
             SYNTAX   INTEGER {
                         up(1),
                         initializing(2),
                         circuitFailed(3),
                         timedOut(4)
                      }
             ACCESS   read-only
             STATUS   mandatory
            DESCRIPTION
                 " The state of the adjacency."
            ::= { accDnAdjEntry 4 }

END
