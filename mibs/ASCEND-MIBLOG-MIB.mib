--			Ascend miblog MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBLOG-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    miblogProfile  OBJECT IDENTIFIER ::= { configuration 93}

	-- The miblogProfile table
	--
	-- This table contains parameters for the miblogProfile profile
	--

    miblogProfileTable	OBJECT-TYPE
	SYNTAX		SEQUENCE OF MiblogProfileEntry
	ACCESS		not-accessible
	STATUS		mandatory
	DESCRIPTION	"A list of miblogProfile profile entries."
	::= { miblogProfile 1 }

    miblogProfileEntry	OBJECT-TYPE
	SYNTAX		MiblogProfileEntry
	ACCESS		not-accessible
	STATUS		mandatory
	DESCRIPTION	"A miblogProfile entry containing objects that
			 maps to the parameters of miblogProfile profile."
	INDEX		{ logProfile-Index-o }
	::= { miblogProfileTable 1 }

    MiblogProfileEntry ::=
	SEQUENCE {
	    logProfile-Index-o
		INTEGER,
	    logProfile-SaveLevel
		INTEGER,
	    logProfile-SaveNumber
		INTEGER,
	    logProfile-CallInfo
		INTEGER,
	    logProfile-SyslogEnabled
		INTEGER,
	    logProfile-Host
		IpAddress,
	    logProfile-Port
		INTEGER,
	    logProfile-Facility
		INTEGER,
	    logProfile-SyslogFormat
		INTEGER,
	    logProfile-LogCallProgress
		INTEGER,
	    logProfile-LogSoftwareVersion
		INTEGER,
	    logProfile-SyslogLevel
		INTEGER,
	    logProfile-Action-o
		INTEGER
	}

    logProfile-Index-o	OBJECT-TYPE
	SYNTAX	INTEGER
	ACCESS	read-only
	STATUS	mandatory
	DESCRIPTION	""
	::= { miblogProfileEntry 1 }

    logProfile-SaveLevel	OBJECT-TYPE
	SYNTAX	INTEGER {
		    none (1),
		    emergency (2),
		    alert (3),
		    critical (4),
		    error (5),
		    warning (6),
		    notice (7),
		    info (8),
		    debug (9)
		}
	ACCESS	read-write
	STATUS	mandatory
	DESCRIPTION	"The lowest level of message to be saved for status display."
	::= { miblogProfileEntry 2 }

    logProfile-SaveNumber	OBJECT-TYPE
	SYNTAX	INTEGER
	ACCESS	read-write
	STATUS	mandatory
	DESCRIPTION	"The maximum number of message to be saved for status display."
	::= { miblogProfileEntry 3 }

    logProfile-CallInfo	OBJECT-TYPE
	SYNTAX	INTEGER {
		    none (1),
		    endOfCall (2)
		}
	ACCESS	read-write
	STATUS	mandatory
	DESCRIPTION	"Specifies when call status changes are logged."
	::= { miblogProfileEntry 4 }

    logProfile-SyslogEnabled	OBJECT-TYPE
	SYNTAX	INTEGER {
		    no (1),
		    yes (2)
		}
	ACCESS	read-write
	STATUS	mandatory
	DESCRIPTION	"TRUE if log messages are to be forwarded to a remote host running syslogd."
	::= { miblogProfileEntry 5 }

    logProfile-Host	OBJECT-TYPE
	SYNTAX	IpAddress
	ACCESS	read-write
	STATUS	mandatory
	DESCRIPTION	"The IP address of the log host for syslog updating."
	::= { miblogProfileEntry 6 }

    logProfile-Port	OBJECT-TYPE
	SYNTAX	INTEGER
	ACCESS	read-write
	STATUS	mandatory
	DESCRIPTION	"The Port number on the log host for syslog updating. Usual value: 514."
	::= { miblogProfileEntry 7 }

    logProfile-Facility	OBJECT-TYPE
	SYNTAX	INTEGER {
		    local0 (1),
		    local1 (2),
		    local2 (3),
		    local3 (4),
		    local4 (5),
		    local5 (6),
		    local6 (7),
		    local7 (8)
		}
	ACCESS	read-write
	STATUS	mandatory
	DESCRIPTION	"The syslogd facility code for messages logged from this box."
	::= { miblogProfileEntry 8 }

    logProfile-SyslogFormat	OBJECT-TYPE
	SYNTAX	INTEGER {
		    tnt (1),
		    max (2)
		}
	ACCESS	read-write
	STATUS	mandatory
	DESCRIPTION	"Specifies the syslog output format to use."
	::= { miblogProfileEntry 9 }

    logProfile-LogCallProgress	OBJECT-TYPE
	SYNTAX	INTEGER {
		    no (1),
		    yes (2)
		}
	ACCESS	read-write
	STATUS	mandatory
	DESCRIPTION	"Log incoming call progress messages. Default is No."
	::= { miblogProfileEntry 10 }

    logProfile-LogSoftwareVersion	OBJECT-TYPE
	SYNTAX	INTEGER {
		    no (1),
		    yes (2)
		}
	ACCESS	read-write
	STATUS	mandatory
	DESCRIPTION	"TRUE if the software version is to be logged."
	::= { miblogProfileEntry 11 }

    logProfile-SyslogLevel	OBJECT-TYPE
	SYNTAX	INTEGER {
		    none (1),
		    emergency (2),
		    alert (3),
		    critical (4),
		    error (5),
		    warning (6),
		    notice (7),
		    info (8),
		    debug (9)
		}
	ACCESS	read-write
	STATUS	mandatory
	DESCRIPTION	"The lowest level of message to be saved for syslog."
	::= { miblogProfileEntry 12 }

    logProfile-Action-o	OBJECT-TYPE
	SYNTAX	INTEGER {
		    noAction (1),
		    createProfile (2),
		    deleteProfile (3)
		}
	ACCESS	read-write
	STATUS	mandatory
	DESCRIPTION	""
	::= { miblogProfileEntry 13 }


	-- The miblogProfile__auxiliary_syslog table
	--
	-- This table contains parameters for the miblogProfile__auxiliary_syslog profile
	--

    miblogProfile-AuxiliarySyslogTable	OBJECT-TYPE
	SYNTAX		SEQUENCE OF MiblogProfile-AuxiliarySyslogEntry
	ACCESS		not-accessible
	STATUS		mandatory
	DESCRIPTION	"A list of miblogProfile__auxiliary_syslog profile entries."
	::= { miblogProfile 2 }

    miblogProfile-AuxiliarySyslogEntry	OBJECT-TYPE
	SYNTAX		MiblogProfile-AuxiliarySyslogEntry
	ACCESS		not-accessible
	STATUS		mandatory
	DESCRIPTION	"A miblogProfile__auxiliary_syslog entry containing objects that
			 maps to the parameters of miblogProfile__auxiliary_syslog profile."
	INDEX		{ logProfile-AuxiliarySyslog-Index-o, logProfile-AuxiliarySyslog-Index1-o }
	::= { miblogProfile-AuxiliarySyslogTable 1 }

    MiblogProfile-AuxiliarySyslogEntry ::=
	SEQUENCE {
	    logProfile-AuxiliarySyslog-Index-o
		INTEGER,
	    logProfile-AuxiliarySyslog-Index1-o
		INTEGER,
	    logProfile-AuxiliarySyslog-SyslogEnabled
		INTEGER,
	    logProfile-AuxiliarySyslog-SyslogLevel
		INTEGER,
	    logProfile-AuxiliarySyslog-Host
		IpAddress,
	    logProfile-AuxiliarySyslog-Port
		INTEGER,
	    logProfile-AuxiliarySyslog-Facility
		INTEGER
	}

    logProfile-AuxiliarySyslog-Index-o	OBJECT-TYPE
	SYNTAX	INTEGER
	ACCESS	read-only
	STATUS	mandatory
	DESCRIPTION	""
	::= { miblogProfile-AuxiliarySyslogEntry 1 }

    logProfile-AuxiliarySyslog-Index1-o	OBJECT-TYPE
	SYNTAX	INTEGER
	ACCESS	read-only
	STATUS	mandatory
	DESCRIPTION	""
	::= { miblogProfile-AuxiliarySyslogEntry 2 }

    logProfile-AuxiliarySyslog-SyslogEnabled	OBJECT-TYPE
	SYNTAX	INTEGER {
		    no (1),
		    yes (2)
		}
	ACCESS	read-write
	STATUS	mandatory
	DESCRIPTION	"TRUE if log messages are to be forwarded to a remote host running syslogd."
	::= { miblogProfile-AuxiliarySyslogEntry 3 }

    logProfile-AuxiliarySyslog-SyslogLevel	OBJECT-TYPE
	SYNTAX	INTEGER {
		    none (1),
		    emergency (2),
		    alert (3),
		    critical (4),
		    error (5),
		    warning (6),
		    notice (7),
		    info (8),
		    debug (9)
		}
	ACCESS	read-write
	STATUS	mandatory
	DESCRIPTION	"The lowest level of message to be saved for syslog."
	::= { miblogProfile-AuxiliarySyslogEntry 4 }

    logProfile-AuxiliarySyslog-Host	OBJECT-TYPE
	SYNTAX	IpAddress
	ACCESS	read-write
	STATUS	mandatory
	DESCRIPTION	"The IP address of the log host for syslog updating."
	::= { miblogProfile-AuxiliarySyslogEntry 5 }

    logProfile-AuxiliarySyslog-Port	OBJECT-TYPE
	SYNTAX	INTEGER
	ACCESS	read-write
	STATUS	mandatory
	DESCRIPTION	"The Port number on the log host for syslog updating. Usual value: 514."
	::= { miblogProfile-AuxiliarySyslogEntry 6 }

    logProfile-AuxiliarySyslog-Facility	OBJECT-TYPE
	SYNTAX	INTEGER {
		    local0 (1),
		    local1 (2),
		    local2 (3),
		    local3 (4),
		    local4 (5),
		    local5 (6),
		    local6 (7),
		    local7 (8)
		}
	ACCESS	read-write
	STATUS	mandatory
	DESCRIPTION	"The syslogd facility code for messages logged from this box."
	::= { miblogProfile-AuxiliarySyslogEntry 7 }

END
