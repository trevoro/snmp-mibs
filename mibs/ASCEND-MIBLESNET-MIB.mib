--			Ascend miblesnet MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBLESNET-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    miblesNetworkProfile  OBJECT IDENTIFIER ::= { configuration 178}

	-- The miblesNetworkProfile table
	--
	-- This table contains parameters for the miblesNetworkProfile profile
	--

    miblesNetworkProfileTable	OBJECT-TYPE
	SYNTAX		SEQUENCE OF MiblesNetworkProfileEntry
	ACCESS		not-accessible
	STATUS		mandatory
	DESCRIPTION	"A list of miblesNetworkProfile profile entries."
	::= { miblesNetworkProfile 1 }

    miblesNetworkProfileEntry	OBJECT-TYPE
	SYNTAX		MiblesNetworkProfileEntry
	ACCESS		not-accessible
	STATUS		mandatory
	DESCRIPTION	"A miblesNetworkProfile entry containing objects that
			 maps to the parameters of miblesNetworkProfile profile."
	INDEX		{ lesNetworkProfile-Shelf-o, lesNetworkProfile-Slot-o, lesNetworkProfile-Item-o }
	::= { miblesNetworkProfileTable 1 }

    MiblesNetworkProfileEntry ::=
	SEQUENCE {
	    lesNetworkProfile-Shelf-o
		INTEGER,
	    lesNetworkProfile-Slot-o
		INTEGER,
	    lesNetworkProfile-Item-o
		INTEGER,
	    lesNetworkProfile-Name
		DisplayString,
	    lesNetworkProfile-PhysicalAddress-Shelf
		INTEGER,
	    lesNetworkProfile-PhysicalAddress-Slot
		INTEGER,
	    lesNetworkProfile-PhysicalAddress-ItemNumber
		INTEGER,
	    lesNetworkProfile-Enabled
		INTEGER,
	    lesNetworkProfile-NailedGroup
		INTEGER,
	    lesNetworkProfile-Action-o
		INTEGER
	}

    lesNetworkProfile-Shelf-o	OBJECT-TYPE
	SYNTAX	INTEGER
	ACCESS	read-only
	STATUS	mandatory
	DESCRIPTION	""
	::= { miblesNetworkProfileEntry 1 }

    lesNetworkProfile-Slot-o	OBJECT-TYPE
	SYNTAX	INTEGER
	ACCESS	read-only
	STATUS	mandatory
	DESCRIPTION	""
	::= { miblesNetworkProfileEntry 2 }

    lesNetworkProfile-Item-o	OBJECT-TYPE
	SYNTAX	INTEGER
	ACCESS	read-only
	STATUS	mandatory
	DESCRIPTION	""
	::= { miblesNetworkProfileEntry 3 }

    lesNetworkProfile-Name	OBJECT-TYPE
	SYNTAX	DisplayString
	ACCESS	read-write
	STATUS	mandatory
	DESCRIPTION	"For future use. The current design does not use the name field but instead references lines by the physical address; we may in the future support referencing lines by name as well as by address. The name consists of a null terminated ascii string supplied by the user; it defaults to the ascii form of the line physical address."
	::= { miblesNetworkProfileEntry 4 }

    lesNetworkProfile-PhysicalAddress-Shelf	OBJECT-TYPE
	SYNTAX	INTEGER {
		    anyShelf (1),
		    shelf1 (2),
		    shelf2 (3),
		    shelf3 (4),
		    shelf4 (5),
		    shelf5 (6),
		    shelf6 (7),
		    shelf7 (8),
		    shelf8 (9),
		    shelf9 (10)
		}
	ACCESS	read-write
	STATUS	mandatory
	DESCRIPTION	"The number of the shelf that the addressed physical device resides on."
	::= { miblesNetworkProfileEntry 5 }

    lesNetworkProfile-PhysicalAddress-Slot	OBJECT-TYPE
	SYNTAX	INTEGER {
		    anySlot (1),
		    slot1 (2),
		    slot2 (3),
		    slot3 (4),
		    slot4 (5),
		    slot5 (6),
		    slot6 (7),
		    slot7 (8),
		    slot8 (9),
		    slot9 (10),
		    slot10 (11),
		    slot11 (12),
		    slot12 (13),
		    slot13 (14),
		    slot14 (15),
		    slot15 (16),
		    slot16 (17),
		    slot17 (18),
		    slot18 (19),
		    slot19 (20),
		    slot20 (21),
		    slot21 (22),
		    slot22 (23),
		    slot23 (24),
		    slot24 (25),
		    slot25 (26),
		    slot26 (27),
		    slot27 (28),
		    slot28 (29),
		    slot29 (30),
		    slot30 (31),
		    slot31 (32),
		    slot32 (33),
		    slot33 (34),
		    slot34 (35),
		    slot35 (36),
		    slot36 (37),
		    slot37 (38),
		    slot38 (39),
		    slot39 (40),
		    slot40 (41),
		    aLim (55),
		    bLim (56),
		    cLim (57),
		    dLim (58),
		    leftController (49),
		    rightController (50),
		    controller (42),
		    firstControlModule (53),
		    secondControlModule (54),
		    trunkModule1 (45),
		    trunkModule2 (46),
		    controlModule (51),
		    slotPrimary (59)
		}
	ACCESS	read-write
	STATUS	mandatory
	DESCRIPTION	"The number of the slot that the addressed physical device resides on."
	::= { miblesNetworkProfileEntry 6 }

    lesNetworkProfile-PhysicalAddress-ItemNumber	OBJECT-TYPE
	SYNTAX	INTEGER
	ACCESS	read-write
	STATUS	mandatory
	DESCRIPTION	"A number that specifies an addressable entity within the context of shelf and slot."
	::= { miblesNetworkProfileEntry 7 }

    lesNetworkProfile-Enabled	OBJECT-TYPE
	SYNTAX	INTEGER {
		    no (1),
		    yes (2)
		}
	ACCESS	read-write
	STATUS	mandatory
	DESCRIPTION	"TRUE if Loop Emulation Services are enabled, otherwise FALSE."
	::= { miblesNetworkProfileEntry 8 }

    lesNetworkProfile-NailedGroup	OBJECT-TYPE
	SYNTAX	INTEGER
	ACCESS	read-write
	STATUS	mandatory
	DESCRIPTION	"A number that identifies the set of lines that makes up a nailed group. 0 means this line is not part of a nailed group."
	::= { miblesNetworkProfileEntry 9 }

    lesNetworkProfile-Action-o	OBJECT-TYPE
	SYNTAX	INTEGER {
		    noAction (1),
		    createProfile (2),
		    deleteProfile (3)
		}
	ACCESS	read-write
	STATUS	mandatory
	DESCRIPTION	""
	::= { miblesNetworkProfileEntry 10 }


	-- The miblesNetworkProfile__pots_line_config table
	--
	-- This table contains parameters for the miblesNetworkProfile__pots_line_config profile
	--

    miblesNetworkProfile-PotsLineConfigTable	OBJECT-TYPE
	SYNTAX		SEQUENCE OF MiblesNetworkProfile-PotsLineConfigEntry
	ACCESS		not-accessible
	STATUS		mandatory
	DESCRIPTION	"A list of miblesNetworkProfile__pots_line_config profile entries."
	::= { miblesNetworkProfile 2 }

    miblesNetworkProfile-PotsLineConfigEntry	OBJECT-TYPE
	SYNTAX		MiblesNetworkProfile-PotsLineConfigEntry
	ACCESS		not-accessible
	STATUS		mandatory
	DESCRIPTION	"A miblesNetworkProfile__pots_line_config entry containing objects that
			 maps to the parameters of miblesNetworkProfile__pots_line_config profile."
	INDEX		{ lesNetworkProfile-PotsLineConfig-Shelf-o, lesNetworkProfile-PotsLineConfig-Slot-o, lesNetworkProfile-PotsLineConfig-Item-o, lesNetworkProfile-PotsLineConfig-Index-o }
	::= { miblesNetworkProfile-PotsLineConfigTable 1 }

    MiblesNetworkProfile-PotsLineConfigEntry ::=
	SEQUENCE {
	    lesNetworkProfile-PotsLineConfig-Shelf-o
		INTEGER,
	    lesNetworkProfile-PotsLineConfig-Slot-o
		INTEGER,
	    lesNetworkProfile-PotsLineConfig-Item-o
		INTEGER,
	    lesNetworkProfile-PotsLineConfig-Index-o
		INTEGER,
	    lesNetworkProfile-PotsLineConfig-Enabled
		INTEGER,
	    lesNetworkProfile-PotsLineConfig-Mode
		INTEGER,
	    lesNetworkProfile-PotsLineConfig-EncodingFormatProfile
		INTEGER,
	    lesNetworkProfile-PotsLineConfig-FwdDisc
		INTEGER,
	    lesNetworkProfile-PotsLineConfig-OverRideCid
		INTEGER
	}

    lesNetworkProfile-PotsLineConfig-Shelf-o	OBJECT-TYPE
	SYNTAX	INTEGER
	ACCESS	read-only
	STATUS	mandatory
	DESCRIPTION	""
	::= { miblesNetworkProfile-PotsLineConfigEntry 1 }

    lesNetworkProfile-PotsLineConfig-Slot-o	OBJECT-TYPE
	SYNTAX	INTEGER
	ACCESS	read-only
	STATUS	mandatory
	DESCRIPTION	""
	::= { miblesNetworkProfile-PotsLineConfigEntry 2 }

    lesNetworkProfile-PotsLineConfig-Item-o	OBJECT-TYPE
	SYNTAX	INTEGER
	ACCESS	read-only
	STATUS	mandatory
	DESCRIPTION	""
	::= { miblesNetworkProfile-PotsLineConfigEntry 3 }

    lesNetworkProfile-PotsLineConfig-Index-o	OBJECT-TYPE
	SYNTAX	INTEGER
	ACCESS	read-only
	STATUS	mandatory
	DESCRIPTION	""
	::= { miblesNetworkProfile-PotsLineConfigEntry 4 }

    lesNetworkProfile-PotsLineConfig-Enabled	OBJECT-TYPE
	SYNTAX	INTEGER {
		    no (1),
		    yes (2)
		}
	ACCESS	read-write
	STATUS	mandatory
	DESCRIPTION	"TRUE if this loop is enabled, otherwise FALSE."
	::= { miblesNetworkProfile-PotsLineConfigEntry 5 }

    lesNetworkProfile-PotsLineConfig-Mode	OBJECT-TYPE
	SYNTAX	INTEGER {
		    groundStart (1),
		    loopStart (2)
		}
	ACCESS	read-write
	STATUS	mandatory
	DESCRIPTION	"POT's loop mode."
	::= { miblesNetworkProfile-PotsLineConfigEntry 6 }

    lesNetworkProfile-PotsLineConfig-EncodingFormatProfile	OBJECT-TYPE
	SYNTAX	INTEGER
	ACCESS	read-write
	STATUS	mandatory
	DESCRIPTION	"ITU-T standardized Encoding Format Profiles. From Annex B through H of I.366.2."
	::= { miblesNetworkProfile-PotsLineConfigEntry 7 }

    lesNetworkProfile-PotsLineConfig-FwdDisc	OBJECT-TYPE
	SYNTAX	INTEGER {
		    no (1),
		    yes (2)
		}
	ACCESS	read-write
	STATUS	mandatory
	DESCRIPTION	"TRUE if Forward Disconnect feature is enabled, otherwise FALSE."
	::= { miblesNetworkProfile-PotsLineConfigEntry 8 }

    lesNetworkProfile-PotsLineConfig-OverRideCid	OBJECT-TYPE
	SYNTAX	INTEGER
	ACCESS	read-write
	STATUS	mandatory
	DESCRIPTION	"Override default allocation of CID's when ELCP is not used."
	::= { miblesNetworkProfile-PotsLineConfigEntry 9 }

END
