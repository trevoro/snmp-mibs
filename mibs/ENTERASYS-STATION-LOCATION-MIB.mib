ENTERASYS-STATION-LOCATION-MIB DEFINITIONS ::= BEGIN

--
--  enterasys-station-location-mib.txt
--
--  Part Number:
--
--

--  This module provides authoritative definitions for Extreme
--  Networks' Station Location MIB.

--
--  This module will be extended, as needed.

--  Extreme Networks reserves the right to make changes in this
--  specification and other information contained in this document
--  without prior notice.  The reader should consult Extreme Networks
--  to determine whether any such changes have been made.
--
--  In no event shall Extreme Networks be liable for any incidental,
--  indirect, special, or consequential damages whatsoever (including
--  but not limited to lost profits) arising out of or related to this
--  document or the information contained in it, even if Extreme
--  Networks has been advised of, known, or should have known, the
--  possibility of such damages.
--
--  Extreme Networks grants vendors, end-users, and other interested
--  parties a non-exclusive license to use this Specification in
--  connection with the management of Extreme Networks products.

--  Copyright May 2016 Extreme Networks, Inc.

 
IMPORTS
    OBJECT-GROUP, MODULE-COMPLIANCE
        FROM SNMPv2-CONF
    Integer32, Unsigned32, OBJECT-TYPE, MODULE-IDENTITY
        FROM SNMPv2-SMI            
    MacAddress, RowStatus, TruthValue, TEXTUAL-CONVENTION
        FROM SNMPv2-TC
    SnmpAdminString
        FROM SNMP-FRAMEWORK-MIB
    etsysModules            
        FROM ENTERASYS-MIB-NAMES;            


etsysStationLocationMIB MODULE-IDENTITY 
    LAST-UPDATED "201605111936Z"  -- Wed May 11 19:36 UTC 2016
    ORGANIZATION "Extreme Networks"
    CONTACT-INFO
        "Postal:  Extreme Networks, Inc.
                  145 Rio Robles
                  San Jose, CA 95134 USA

         Phone:   +1 408 579-2800
         E-mail:  support@extremenetworks.com
         WWW:     http://www.extremenetworks.com"

    DESCRIPTION 
        "This MIB provides an interface to manage the wireless station 
         localization application. It allows configuration of the 
         application as well retrieving information about location of 
         managed Station that are associated to controller or are 
         configured to be tracked even without being associated."

    REVISION    "201605111936Z"  -- Wed May 11 19:36 UTC 2016
    DESCRIPTION 
        "Added etsysPublishLocationUserId and 
         etsysPublishLocationPassword to etsysPublishLocationURLTable."

    REVISION    "201509101618Z"  -- Thursday Sept 10 16:18 UTC 2015
    DESCRIPTION 
        "Added etsysLocationEngineTrackMode to 
         etsysLocationConfiguration."

    REVISION    "201406131610Z"  -- Fri Jun 13 16:10 UTC 2014
    DESCRIPTION 
        "Added location batch report to provide a way for consumer 
         programs to receive the list of the locations of all associated 
         stations. Added etsysLocationEngineTrackAreaChange to 
         etsysLocationConfiguration."

    REVISION    "201304181520Z"  -- Thu Apr 18 15:20 UTC 2013
    DESCRIPTION 
        "The initial version of this MIB module."
    ::= { etsysModules 98 }

-- -------------------------------------------------------------
-- Textual conventions
-- -------------------------------------------------------------
FloorEnvironmentType ::= TEXTUAL-CONVENTION
    STATUS     current
    DESCRIPTION
         "Type of indoor construction materials used on its floor.
     
          openSpace(0):        Indoor open space (halls, auditoriums)
          lightDivision(1):    Office environment with light divisions 
                                (cubicles)
          dryWallsDivision(2): Office environment with dry walls divisions
          hardDivision(3):     Office Environment with hard divisions 
                                (brick)
          interiorWalls(4):    Interior Walls (need be defined in the 
                                floor plan) "
    SYNTAX INTEGER  {
             openSpace(0),
             lightDivision(1),
             dryWallsDivision(2),
             hardDivision(3),
             interiorWalls(4)
           }


-- -------------------------------------------------------------
-- MIB Objects
-- -------------------------------------------------------------
etsysStationLocationMIBObjects OBJECT IDENTIFIER 
                               ::= { etsysStationLocationMIB 1 }

etsysLocationConfiguration             OBJECT IDENTIFIER 
                               ::= { etsysStationLocationMIBObjects 1 }

etsysLocationEngineEnable OBJECT-TYPE
    SYNTAX     TruthValue
    MAX-ACCESS read-write
    STATUS     current
    DESCRIPTION
        "Setting this value to true (1), enables the location engine 
        to track stations, otherwise no station will be tracked."
    ::= { etsysLocationConfiguration 1 }

etsysLocationEngineAutoTrkEnable OBJECT-TYPE
    SYNTAX     TruthValue
    MAX-ACCESS read-write
    STATUS     current
    DESCRIPTION
        "If this variable is set to true and etsysLocationEngineEnable 
         is set to true then all associated stations will be tracked up to
         the platform limit for location tracking."
    ::= { etsysLocationConfiguration 2 }

etsysLocationEngineGlblAPHeight OBJECT-TYPE
    SYNTAX     Unsigned32 (0..1000)
    UNITS      "centimeters"
    MAX-ACCESS read-write
    STATUS     current
    DESCRIPTION
        "Default height of access point to be used if the floor 
         configuration has not provided any height for any AP servicing 
         the floor. The range of height is 0 to 1000 in centimeters."
    ::= { etsysLocationConfiguration 3 }

etsysLocationEngineGlobalEnv OBJECT-TYPE
    SYNTAX     FloorEnvironmentType
    MAX-ACCESS read-write
    STATUS     current
    DESCRIPTION
        "Type of indoor construction materials assumed when the floor
         plan does not specify the primary construction materials used 
         on its floor."
    ::= { etsysLocationConfiguration 4 }

-- -------------------------------------------------------------
-- The Location Floors Group
-- -------------------------------------------------------------

etsysLocationFloors            OBJECT IDENTIFIER 
                               ::= { etsysLocationConfiguration 5 }

etsysLocationMaxFloorLimit OBJECT-TYPE
    SYNTAX     Unsigned32
    MAX-ACCESS read-only
    STATUS     current
    DESCRIPTION
        "The maximum number of floor plan files that can be stored and 
        used on this controller."
    ::= { etsysLocationFloors 1 }

etsysLocationFloorConfigured OBJECT-TYPE
    SYNTAX     Unsigned32
    MAX-ACCESS read-only
    STATUS     current
    DESCRIPTION
        "The number of floors that have been configured and currently 
         used."
    ::= { etsysLocationFloors 2 }

etsysFloorTable OBJECT-TYPE
    SYNTAX     SEQUENCE OF EtsysFloorEntry
    MAX-ACCESS not-accessible
    STATUS     current
    DESCRIPTION
        "A table that describes attributes of floors configured for use
        by the Location Engine."
    ::= { etsysLocationFloors 3 }

etsysFloorEntry OBJECT-TYPE
    SYNTAX     EtsysFloorEntry
    MAX-ACCESS not-accessible
    STATUS     current
    DESCRIPTION
        "An entry describing a single floor in the location engine's 
         database."
    INDEX { etsysFloorID }
    ::= { etsysFloorTable 1 }

EtsysFloorEntry ::=
    SEQUENCE { 
        etsysFloorID
            Unsigned32,
        etsysFloorRowStatus
            RowStatus,
        etsysFloorName
            SnmpAdminString,
        etsysFloorNumberOfAPs
            Unsigned32,
        etsysFloorWidth
            Unsigned32,
        etsysFloorLength
            Unsigned32,
        etsysFloorNumberOfCells
            Unsigned32,
        etsysFloorCellWidth
            Unsigned32,
        etsysFloorCellLength
            Unsigned32,
        etsysFloorEnvironment
            FloorEnvironmentType,
        etsysFloorHashString
            OCTET STRING
     }

etsysFloorID OBJECT-TYPE
    SYNTAX     Unsigned32
    MAX-ACCESS not-accessible
    STATUS     current
    DESCRIPTION
        "Floor ID associated to the floor. This index ranges from one 
         to etsysLocationMaxFloorLimit. This ID persists over reboots and 
         upgrades."
    ::= { etsysFloorEntry 1 }

etsysFloorRowStatus OBJECT-TYPE
    SYNTAX     RowStatus
    MAX-ACCESS read-create
    STATUS     current
    DESCRIPTION
        "RowStatus of the entry, though currently only deletion is allowed
         for this field."
    ::= { etsysFloorEntry 2 }

etsysFloorName OBJECT-TYPE
    SYNTAX     SnmpAdminString (SIZE (1..64))
    MAX-ACCESS read-create
    STATUS     current
    DESCRIPTION
        "Textual string identifying floor name. Supports UTF-8 character 
         set, except Double Quotes and ASCII control characters."
    ::= { etsysFloorEntry 3 }

etsysFloorNumberOfAPs OBJECT-TYPE
    SYNTAX     Unsigned32
    MAX-ACCESS read-create
    STATUS     current
    DESCRIPTION
        "Number of access point have been assigned to this floor to 
         track stations on this floor."
    ::= { etsysFloorEntry 4 }

etsysFloorWidth OBJECT-TYPE
    SYNTAX     Unsigned32
    UNITS      "centimeters"
    MAX-ACCESS read-create
    STATUS     current
    DESCRIPTION
        "Width of the floor in centimeters."
    ::= { etsysFloorEntry 5 }

etsysFloorLength OBJECT-TYPE
    SYNTAX     Unsigned32
    UNITS      "centimeters"
    MAX-ACCESS read-create
    STATUS     current
    DESCRIPTION
        "Length of the floor in centimeters."
    ::= { etsysFloorEntry 6 }

etsysFloorNumberOfCells OBJECT-TYPE
    SYNTAX     Unsigned32
    UNITS      "centimeters"
    MAX-ACCESS read-create
    STATUS     current
    DESCRIPTION
        "Number of cells on this floor."
    ::= { etsysFloorEntry 7 }

etsysFloorCellWidth OBJECT-TYPE
    SYNTAX     Unsigned32
    UNITS      "centimeters"
    MAX-ACCESS read-create
    STATUS     current
    DESCRIPTION
        "Width of each cell for this floor in centimeters."
    ::= { etsysFloorEntry 8 }

etsysFloorCellLength OBJECT-TYPE
    SYNTAX     Unsigned32
    UNITS      "centimeters"
    MAX-ACCESS read-create
    STATUS     current
    DESCRIPTION
        "Length of each cell for this floor in centimeters."
    ::= { etsysFloorEntry 9 }

etsysFloorEnvironment OBJECT-TYPE
    SYNTAX     FloorEnvironmentType
    MAX-ACCESS read-create
    STATUS     current
    DESCRIPTION
        "Type of propagation model for the floor."
    ::= { etsysFloorEntry 10 }

etsysFloorHashString OBJECT-TYPE
    SYNTAX     OCTET STRING (SIZE (16))
    MAX-ACCESS read-create
    STATUS     current
    DESCRIPTION
        "MD5 hash of the file as received during download."
    ::= { etsysFloorEntry 11 }

-- -------------------------------------------------------------
-- The Location Stations Group
-- -------------------------------------------------------------

etsysLocationStations          OBJECT IDENTIFIER 
                               ::= { etsysLocationConfiguration 6 }

etsysMaxTrackedStationLimit OBJECT-TYPE
    SYNTAX     Unsigned32
    MAX-ACCESS read-only
    STATUS     current
    DESCRIPTION
        "Maximum number of stations that this platform can track.
         Stations are tracked on the basis of either being associated
         to the controller or administratively added to the
         'On-Demand Tracking' list "
    ::= { etsysLocationStations 1 }

etsysMaxOnDemandStationLimit OBJECT-TYPE
    SYNTAX     Unsigned32 (0..32)
    MAX-ACCESS read-only
    STATUS     current
    DESCRIPTION
        "Maximum number of stations that can be configured
         to be tracked as on-demand basis."
    ::= { etsysLocationStations 2 }

etsysOnDemandStationTable OBJECT-TYPE
    SYNTAX     SEQUENCE OF EtsysOnDemandStationEntry
    MAX-ACCESS not-accessible
    STATUS     current
    DESCRIPTION
        "A list of stations to be tracked by the Location Engine.
         Location tracking of a station may stop when it is removed
         from the list. The list is configured by the administrator
         and is used to reserve capacity to ensure that the addresses
         in the list are among those tracked by the location engine."
    ::= { etsysLocationStations 3 }

etsysOnDemandStationEntry OBJECT-TYPE
    SYNTAX     EtsysOnDemandStationEntry
    MAX-ACCESS not-accessible
    STATUS     current
    DESCRIPTION
        "The address of a single station to be tracked."
    INDEX { etsysOnDemandStationMAC }
    ::= { etsysOnDemandStationTable 1 }

EtsysOnDemandStationEntry ::=
    SEQUENCE { 
        etsysOnDemandStationMAC
            MacAddress,
        etsysOnDemandStationRowStatus
            RowStatus
     }

etsysOnDemandStationMAC OBJECT-TYPE
    SYNTAX     MacAddress
    MAX-ACCESS not-accessible
    STATUS     current
    DESCRIPTION
        "MAC address of the station to be tracked."
    ::= { etsysOnDemandStationEntry 1 }

etsysOnDemandStationRowStatus OBJECT-TYPE
    SYNTAX     RowStatus
    MAX-ACCESS read-create
    STATUS     current
    DESCRIPTION
        "RowStatus of the entry."
    ::= { etsysOnDemandStationEntry 2 }

etsysLocationEngineTrackAreaChange OBJECT-TYPE
    SYNTAX     INTEGER {
        disable(0),
        enable(1)
    }
    MAX-ACCESS read-write
    STATUS     current
    DESCRIPTION
        "Setting this value to enable(1), the location engine will 
        track the area changes, otherwise, the area information is 
        determined by the associated AP."
    ::= { etsysLocationConfiguration 7 }

etsysLocationEngineTrackMode OBJECT-TYPE
    SYNTAX     INTEGER {
        trackClients(1),
        trackAll(2),
        trackNone(3)
    }
    MAX-ACCESS read-write
    STATUS     current
    DESCRIPTION
        "trackClients(1) :  All associated stations will be tracked up to
                            the platform limit.
         trackAll(2)     :  All Mac address will be tracked up to the 
                            platform limit.
         trackNone(3)    :  Location engine is tracking the on demand 
                            list only."
    ::= { etsysLocationConfiguration 8 }

-- -------------------------------------------------------------
-- The Location Reports Group
-- -------------------------------------------------------------

etsysLocationReports           OBJECT IDENTIFIER 
                               ::= { etsysStationLocationMIBObjects 2 }

etsysTrackedStationTable OBJECT-TYPE
    SYNTAX     SEQUENCE OF EtsysTrackedStationEntry
    MAX-ACCESS not-accessible
    STATUS     current
    DESCRIPTION
        "Table containing information about tracked stations."
    ::= { etsysLocationReports 1 }

etsysTrackedStationEntry OBJECT-TYPE
    SYNTAX     EtsysTrackedStationEntry
    MAX-ACCESS not-accessible
    STATUS     current
    DESCRIPTION
        "An entry describing the location of one tracked station."
    INDEX { etsysTrackedStationMAC }
    ::= { etsysTrackedStationTable 1 }

EtsysTrackedStationEntry ::=
    SEQUENCE { 
        etsysTrackedStationMAC
            MacAddress,
        etsysTrackedStationFloorID
            Unsigned32,
        etsysTrackedStationLocationType
            INTEGER,
        etsysTrackedStationReportingAPSN
            SnmpAdminString,
        etsysTrackedStationAPDistance
            Integer32
     }

etsysTrackedStationMAC OBJECT-TYPE
    SYNTAX     MacAddress
    MAX-ACCESS not-accessible
    STATUS     current
    DESCRIPTION
        "MAC address associated to the station that is being tracked."
    ::= { etsysTrackedStationEntry 1 }

etsysTrackedStationFloorID OBJECT-TYPE
    SYNTAX     Unsigned32
    MAX-ACCESS read-only
    STATUS     current
    DESCRIPTION
        "The ID of the floor on which the station appears to be active."
    ::= { etsysTrackedStationEntry 2 }

etsysTrackedStationLocationType OBJECT-TYPE
    SYNTAX     INTEGER {
                 unknown(0),
                 rssBasedLocation(1),
                 cellOfOrigin(2)
               }
    MAX-ACCESS read-only
    STATUS     current
    DESCRIPTION
        "This object identifies the type of location report for the 
         station.  The meaning of other fields in this table and the 
         etsysLocationGridTable depend on the value of this object.
         If this object has a value of 'cellOfOrigin' then 
         etsysStationLocnGridX and etsysStationLocationGridY
         will be set to -1 in the etsysStationLocationGridTable 
         entry for this station."
    ::= { etsysTrackedStationEntry 3 }

etsysTrackedStationReportingAPSN OBJECT-TYPE
    SYNTAX     SnmpAdminString
    MAX-ACCESS read-only
    STATUS     current
    DESCRIPTION
        "The serial number of the access point that reported an 
         RSS value for the station. This object is meaningful only when 
         the value of etsysTrackedStationLocationType is cellOfOrigin. The
         cell of origin method determines location based on the probable 
         distance of the subject from a known location, in this case, the 
         location of the AP that reported the RSS value. Cell of Origin is 
         used when fewer than three APs report seeing the station at one
         time. If two APs report the station then the serial number 
         of the AP reporting the strongest RSS is reported as the 
         station's etsysTrackedStationReportingAPSN."
    ::= { etsysTrackedStationEntry 6 }

etsysTrackedStationAPDistance OBJECT-TYPE
    SYNTAX     Integer32
    UNITS      "meters"
    MAX-ACCESS read-only
    STATUS     current
    DESCRIPTION
        "The distance (in meters) of the station from the access point 
         with the serial number in etsysTrackedStationReportingAPSN.
         This object is meaningful only when the value of 
         etsysTrackedStationLocationType is cellOfOrigin."
    ::= { etsysTrackedStationEntry 7 }

etsysStationLocationGridTable OBJECT-TYPE
    SYNTAX     SEQUENCE OF EtsysStationLocationGridEntry
    MAX-ACCESS not-accessible
    STATUS     current
    DESCRIPTION
        "When the location type is rssBasedLocation it is likely that 
         there will be a number of probable locations calculated for 
         one station. This table lists the most recently 
         rssBasedLocation-calculated probable locations of each
         tracked station. Each row of the table represents one probable
         location of one tracked station. The table is indexed by the 
         subject station's MAC address and an internal identifier for 
         the cell described by the entry. The cell is a cell on the floor
         identified by the etsysTrackedStationFloorID object in the 
         etsysTrackedStationEntry for the subject station."
    ::= { etsysLocationReports 2 }

etsysStationLocationGridEntry OBJECT-TYPE
    SYNTAX     EtsysStationLocationGridEntry
    MAX-ACCESS not-accessible
    STATUS     current
    DESCRIPTION
        "One entry in this table providing one of the possible location 
         for the station with associated probability."
    INDEX { etsysTrackedStationMAC, etsysStationLocnGridIndex }
    ::= { etsysStationLocationGridTable 1 }

EtsysStationLocationGridEntry ::=
    SEQUENCE { 
        etsysStationLocnGridIndex
            Unsigned32,
        etsysStationLocnGridX
            Integer32,
        etsysStationLocnGridY
            Integer32,
        etsysStationLocnGridProbability
            Integer32
     }

etsysStationLocnGridIndex OBJECT-TYPE
    SYNTAX     Unsigned32
    MAX-ACCESS not-accessible
    STATUS     current
    DESCRIPTION
        "Internally assigned number to those location starting from 
         one to the maximum number of reported locations. This 
         field has no meaning by itself."
    ::= { etsysStationLocationGridEntry 1 }

etsysStationLocnGridX OBJECT-TYPE
    SYNTAX     Integer32
    MAX-ACCESS read-only
    STATUS     current
    DESCRIPTION
        "X-coordinate associated to the location of the reported cell."
    ::= { etsysStationLocationGridEntry 2 }

etsysStationLocnGridY OBJECT-TYPE
    SYNTAX     Integer32
    MAX-ACCESS read-only
    STATUS     current
    DESCRIPTION
        "Y-coordinate associated to the location of the reported cell."
    ::= { etsysStationLocationGridEntry 3 }

etsysStationLocnGridProbability OBJECT-TYPE
    SYNTAX     Integer32 (0..100)
    MAX-ACCESS read-only
    STATUS     current
    DESCRIPTION
        "Estimated percentage chance that the station is actually
         located in the identified cell. A value of zero means the
         location is not known."
    ::= { etsysStationLocationGridEntry 4 }

-- -------------------------------------------------------------
-- The Location Batch Reports Group
-- -------------------------------------------------------------
etsysLocationBatchReport           OBJECT IDENTIFIER 
                               ::= { etsysStationLocationMIBObjects 3 }


etsysLocationBatchReportEnable OBJECT-TYPE
    SYNTAX     TruthValue
    MAX-ACCESS read-write
    STATUS     current
    DESCRIPTION
        "Setting this value to true (1) enables the location batch 
         reporting feature."
    ::= { etsysLocationBatchReport 1 }

etsysLocationBatchReportFrequency OBJECT-TYPE
    SYNTAX     Unsigned32 (60..4294967295)
    MAX-ACCESS read-write
    STATUS     current
    DESCRIPTION
        "The report frequency setting in seconds. Currently 60, 120, 300,
         600, 1200, 1800, 3600, 7200 and 14400 seconds are supported. 
         Other values are un-supported and will be rejected."
    ::= { etsysLocationBatchReport 2 }

etsysPublishLocationURLMaxEntries OBJECT-TYPE
    SYNTAX     Unsigned32
    MAX-ACCESS read-only
    STATUS     current
    DESCRIPTION
        "Maximum number of URLs supported by the controller."
    ::= { etsysLocationBatchReport 3 }

etsysPublishLocationURLNumEntries OBJECT-TYPE
    SYNTAX     Unsigned32
    MAX-ACCESS read-only
    STATUS     current
    DESCRIPTION
        "The current number of entries in the 
         etsysPublishLocationURLTable."
    ::= { etsysLocationBatchReport 4 }

etsysPublishLocationURLTable OBJECT-TYPE
    SYNTAX     SEQUENCE OF EtsysPublishLocationURLEntry
    MAX-ACCESS not-accessible
    STATUS     current
    DESCRIPTION
        "Table containing destination URLs to which the controller posts
         location information.  Only http and https are supported."
    ::= { etsysLocationBatchReport 5 }

etsysPublishLocationURLEntry OBJECT-TYPE
    SYNTAX     EtsysPublishLocationURLEntry
    MAX-ACCESS not-accessible
    STATUS     current
    DESCRIPTION
        "An entry describing the destination URL."
    INDEX { etsysPublishLocationIndex }
    ::= { etsysPublishLocationURLTable 1 }

EtsysPublishLocationURLEntry ::=
    SEQUENCE { 
        etsysPublishLocationIndex
            Unsigned32,
        etsysPublishLocationURL
            OCTET STRING,
        etsysPublishLocationRowStatus
            RowStatus,
        etsysPublishLocationUserId
            SnmpAdminString,
        etsysPublishLocationPassword
            SnmpAdminString
     }

etsysPublishLocationIndex OBJECT-TYPE
    SYNTAX     Unsigned32 (1..4294967295)
    MAX-ACCESS not-accessible
    STATUS     current
    DESCRIPTION
        "The index for a configured destination URL."
    ::= { etsysPublishLocationURLEntry 1 }

etsysPublishLocationURL OBJECT-TYPE
    SYNTAX     OCTET STRING (SIZE(1..512))
    MAX-ACCESS read-create
    STATUS     current
    DESCRIPTION
        "The URL of the destination to which a report is pushed."
    DEFVAL { ''H }
    ::= { etsysPublishLocationURLEntry 2 }

etsysPublishLocationRowStatus OBJECT-TYPE
    SYNTAX     RowStatus
    MAX-ACCESS read-create
    STATUS     current
    DESCRIPTION
        "A control that will allow one entry to be added,
         activated, deactivated, or removed from the table."
    ::= { etsysPublishLocationURLEntry 3 }

etsysPublishLocationUserId OBJECT-TYPE
    SYNTAX     SnmpAdminString
    MAX-ACCESS read-create
    STATUS     current
    DESCRIPTION
        "The login name for the destination URL server."
    ::= { etsysPublishLocationURLEntry 4 }

etsysPublishLocationPassword OBJECT-TYPE
    SYNTAX     SnmpAdminString
    MAX-ACCESS read-create
    STATUS     current
    DESCRIPTION
        "The password for the destination URL server.
        On a read, a dummy (not real password) will be returned."
    ::= { etsysPublishLocationURLEntry 5 }

etsysLocationBatchReportDimensionUnit OBJECT-TYPE
    SYNTAX     INTEGER {
        meter(0),
        feet(1)
    }
    MAX-ACCESS read-write
    STATUS     current
    DESCRIPTION
        "The units for reported x and y location coordinates. "
    ::= { etsysLocationBatchReport 6 }

-- -------------------------------------------------------------
-- Conformance Information
-- -------------------------------------------------------------

etsysStationLocationConformance OBJECT IDENTIFIER 
                                ::= { etsysStationLocationMIB 2 }

etsysStationLocationGroups      OBJECT IDENTIFIER 
                                ::= { etsysStationLocationConformance 1 }

etsysStationLocationCompliances OBJECT IDENTIFIER 
                                ::= { etsysStationLocationConformance 2 }

-- -------------------------------------------------------------
-- Units of conformance
-- -------------------------------------------------------------

etsysLocationEngineGlobalGroup OBJECT-GROUP
    OBJECTS { 
        etsysLocationEngineEnable, 
        etsysLocationEngineAutoTrkEnable, 
        etsysLocationEngineGlblAPHeight, 
        etsysLocationEngineGlobalEnv
    }
    STATUS     deprecated
    DESCRIPTION 
        "Objects defining configuration attributes of a location tracking 
         components."
    ::= { etsysStationLocationGroups 1 }

etsysFloorGroup OBJECT-GROUP
    OBJECTS { 
        etsysFloorRowStatus, 
        etsysFloorName, 
        etsysFloorNumberOfAPs, 
        etsysFloorWidth, 
        etsysFloorLength,
        etsysFloorNumberOfCells, 
        etsysFloorCellWidth, 
        etsysFloorCellLength, 
        etsysFloorHashString,
        etsysFloorEnvironment, 
        etsysLocationMaxFloorLimit,
        etsysLocationFloorConfigured 
    }
    STATUS     current
    DESCRIPTION 
        "List of objects that defines attributes of a configured floor."
    ::= { etsysStationLocationGroups 2 }

etsysOnDemandStationsGroup OBJECT-GROUP
    OBJECTS { etsysOnDemandStationRowStatus }
    STATUS     current
    DESCRIPTION 
        "List of objects that define attribute of a on-demand stations
         to be tracked."
    ::= { etsysStationLocationGroups 3 }

etsysTrackedStationsGroup OBJECT-GROUP
    OBJECTS {
        etsysTrackedStationFloorID, 
        etsysTrackedStationLocationType, 
        etsysTrackedStationReportingAPSN, 
        etsysTrackedStationAPDistance,  
        etsysStationLocnGridX, 
        etsysStationLocnGridY,
        etsysStationLocnGridProbability,
        etsysMaxOnDemandStationLimit,
        etsysMaxTrackedStationLimit
    }
    STATUS     current
    DESCRIPTION 
        "List of objects that define a tracked stations attributes."
    ::= { etsysStationLocationGroups 4 }

etsysLocationBatchReportGroup OBJECT-GROUP
    OBJECTS {
        etsysLocationBatchReportEnable, 
        etsysLocationBatchReportFrequency, 
        etsysLocationBatchReportDimensionUnit,
        etsysPublishLocationURLMaxEntries,
        etsysPublishLocationURLNumEntries,
        etsysPublishLocationURL, 
        etsysPublishLocationRowStatus
    }
    STATUS     deprecated
    DESCRIPTION 
        "List of objects that define location batch reporting attributes."
    ::= { etsysStationLocationGroups 5 }

etsysLocationEngineGlobalGroup2 OBJECT-GROUP
    OBJECTS { 
        etsysLocationEngineEnable, 
        etsysLocationEngineAutoTrkEnable,
        etsysLocationEngineGlblAPHeight,
        etsysLocationEngineGlobalEnv,
        etsysLocationEngineTrackAreaChange
    }
    STATUS     deprecated
    DESCRIPTION 
        "Objects defining configuration attributes of a location tracking
         components."
    ::= { etsysStationLocationGroups 6 }

etsysLocationEngineGlobalGroup3 OBJECT-GROUP
    OBJECTS {
        etsysLocationEngineEnable,
        etsysLocationEngineAutoTrkEnable,
        etsysLocationEngineGlblAPHeight,
        etsysLocationEngineGlobalEnv,
        etsysLocationEngineTrackAreaChange,
        etsysLocationEngineTrackMode
    }
    STATUS     current
    DESCRIPTION
        "Objects defining configuration attributes of a location tracking
         components."
    ::= { etsysStationLocationGroups 7 }

etsysLocationBatchReportGroup2 OBJECT-GROUP
    OBJECTS {
        etsysLocationBatchReportEnable,
        etsysLocationBatchReportFrequency,
        etsysLocationBatchReportDimensionUnit,
        etsysPublishLocationURLMaxEntries,
        etsysPublishLocationURLNumEntries,
        etsysPublishLocationURL,
        etsysPublishLocationRowStatus,
        etsysPublishLocationUserId,
        etsysPublishLocationPassword
    }
    STATUS     current
    DESCRIPTION
        "List of objects that define location batch reporting attributes."
    ::= { etsysStationLocationGroups 8 }

-- -------------------------------------------------------------
-- Compliance statements
-- -------------------------------------------------------------

etsysStationLocationCompliance MODULE-COMPLIANCE
    STATUS     deprecated
    DESCRIPTION 
        "This group is mandatory for all devices that support 
         reporting and configuration of station location."

    MODULE -- this module
        MANDATORY-GROUPS { 
            etsysLocationEngineGlobalGroup, 
            etsysFloorGroup, 
            etsysOnDemandStationsGroup, 
            etsysTrackedStationsGroup 
        }
    ::= { etsysStationLocationCompliances 1 }

etsysStationLocationCompliance2 MODULE-COMPLIANCE
    STATUS     deprecated
    DESCRIPTION 
        "This group is mandatory for all devices that support
         reporting and configuration of station location."
    
    MODULE -- this module
        MANDATORY-GROUPS { 
            etsysLocationEngineGlobalGroup2,
            etsysFloorGroup, 
            etsysOnDemandStationsGroup,
            etsysTrackedStationsGroup,
            etsysLocationBatchReportGroup
        }
    ::= { etsysStationLocationCompliances 2 }

etsysStationLocationCompliance3 MODULE-COMPLIANCE
    STATUS     current
    DESCRIPTION
        "This group is mandatory for all devices that support
         reporting and configuration of station location."

    MODULE -- this module
        MANDATORY-GROUPS {
            etsysLocationEngineGlobalGroup3,
            etsysFloorGroup,
            etsysOnDemandStationsGroup,
            etsysTrackedStationsGroup,
            etsysLocationBatchReportGroup2
        }
    ::= { etsysStationLocationCompliances 3 }

END
