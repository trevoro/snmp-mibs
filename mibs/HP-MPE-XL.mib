HP-MPE-XL DEFINITIONS ::= BEGIN

-- Title:       MPE/XL additions to HP MIB
-- Date:	February 6, 1992
-- By:		Lisa Gullicksen <lmg@cup.hp.com> 
--              Jon Lewis <jkl@cup.hp.com> 
-- RCS Revision:$Header: /tmp/ccaseimp12088.12148,v /main/1 1994/06/26 06:55 UTC build Exp $

IMPORTS
	enterprises, NetworkAddress, IpAddress, Counter, Gauge,
			Timeticks
		FROM RFC1155-SMI
	OBJECT-TYPE
	        FROM RFC-1212
        DisplayString
                FROM RFC1213-MIB;

hp 		OBJECT IDENTIFIER ::= { enterprises 11 }
nm		OBJECT IDENTIFIER ::= { hp 2 }
system		OBJECT IDENTIFIER ::= { nm 3 }
general		OBJECT IDENTIFIER ::= { system 1 }
mpeXLSystem     OBJECT IDENTIFIER ::= { general 3 }
volume          OBJECT IDENTIFIER ::= { mpeXLSystem 1 }
processor       OBJECT IDENTIFIER ::= { mpeXLSystem 2 }


-- object types

-- The Volume Group
-- On MPE XL systems, a volume is equivalent to a logical disc drive
-- which is primarily used for file system storage.
--
volumeMounted OBJECT-TYPE
	SYNTAX	INTEGER
	ACCESS 	read-only
	STATUS	mandatory
	DESCRIPTION
		"The number of volumes that are currently mounted
		on the system."
	::= { volume 1 }

-- The Volume Table

volumeTable OBJECT-TYPE
	SYNTAX	SEQUENCE OF VolumeEntry
	ACCESS 	not-accessible
	STATUS	mandatory
	DESCRIPTION
		"Volume table"
	::= { volume 2 }

volumeEntry OBJECT-TYPE
	SYNTAX	VolumeEntry
	ACCESS 	not-accessible
	STATUS	mandatory
	DESCRIPTION
		"Each entry contains objects that define the volume."
	INDEX	{ volumeName }
	::= { volumeTable 1 }

VolumeEntry ::= SEQUENCE {
	volumeLDEV
	    INTEGER,
	volumeName
	    DisplayString,
	volumeDriveType
            DisplayString,
	volumeSectorSize
	    INTEGER,
	volumeType
	    INTEGER,
	volumeCapacity
	    INTEGER,
	volumeMPEOverhead
	    INTEGER,
	volumeMPETransOverhead
	    INTEGER,
	volumeMPEConfigMaxTrans
	    INTEGER,
	volumeDirSpaceOverhead
	    INTEGER,
	volumeFileLabelOverhead
	    INTEGER,
	volumeTransactionMgmtOverhead
	    INTEGER,
	volumeSpoolFileDiscUsage
	    INTEGER,
	volumePermFiles
	    INTEGER,
	volumeTempFiles
	    INTEGER,
	volumeTotalFreeSpace
	    INTEGER,
	volumeLargestContigFree
	    INTEGER,
	volumePercentUtilized
	    INTEGER
        }

volumeLDEV OBJECT-TYPE
	SYNTAX	INTEGER
	ACCESS	read-only
	STATUS	mandatory
	DESCRIPTION
		"The logical device number for the volume."
	::= { volumeEntry 1 }

volumeName OBJECT-TYPE
	SYNTAX	DisplayString
	ACCESS	read-only
	STATUS	mandatory
	DESCRIPTION
		"This is the volume set name combined with the member name
		that uniquely distinguishes the actual volume on the system."
	::= { volumeEntry 2 }

volumeDriveType OBJECT-TYPE
	SYNTAX	DisplayString
	ACCESS	read-only
	STATUS	mandatory
	DESCRIPTION
		"The type of the actual hardware device, e.g. HP7935."
	::= { volumeEntry 3 }

volumeSectorSize OBJECT-TYPE
	SYNTAX	INTEGER
	ACCESS	read-only
	STATUS	mandatory
	DESCRIPTION
		"The logical sector size of the volume in bytes"
	::= { volumeEntry 4 }

volumeType OBJECT-TYPE
	SYNTAX	INTEGER {
		system(1),
		nonSystem(2)
		}
	ACCESS	read-only
	STATUS	mandatory
	DESCRIPTION
		"The type of volume set."
	::= { volumeEntry 5 }

volumeCapacity OBJECT-TYPE
	SYNTAX	INTEGER
	ACCESS	read-only
	STATUS	mandatory
	DESCRIPTION
		"The capacity of the volume in sectors."
	::= { volumeEntry 6 }

volumeMPEOverhead OBJECT-TYPE
	SYNTAX	INTEGER
	ACCESS	read-only
	STATUS	mandatory
	DESCRIPTION
		"The total overhead which consists of everything on
		a volume that is not set aside for file space use.  This
		includes volume label, file label table, directory, volume
		set information table, free space map, transient space, 
		and transaction management overhead."
	::= { volumeEntry 7 }

volumeMPETransOverhead OBJECT-TYPE
	SYNTAX	INTEGER
	ACCESS	read-only
	STATUS	mandatory
	DESCRIPTION
		"The total MPE XL transient space overhead for the volume."
	::= { volumeEntry 8 }

volumeMPEConfigMaxTrans OBJECT-TYPE
	SYNTAX	INTEGER
	ACCESS	read-only
	STATUS	mandatory
	DESCRIPTION
		"The configured maximum transient space for the volume."
	::= { volumeEntry 9 }

volumeDirSpaceOverhead OBJECT-TYPE
	SYNTAX	INTEGER
	ACCESS	read-only
	STATUS	mandatory
	DESCRIPTION
		"The directory space overhead that is reserved for
		accounting information."
	::= { volumeEntry 10 }

volumeFileLabelOverhead OBJECT-TYPE
	SYNTAX	INTEGER
	ACCESS	read-only
	STATUS	mandatory
	DESCRIPTION
		"The file label overhead for this volume."
	::= { volumeEntry 11 }

volumeTransactionMgmtOverhead OBJECT-TYPE
	SYNTAX	INTEGER
	ACCESS	read-only
	STATUS	mandatory
	DESCRIPTION
		"The transaction management overhead for this volume."
	::= { volumeEntry 12 }

volumeSpoolFileDiscUsage OBJECT-TYPE
	SYNTAX	INTEGER
	ACCESS	read-only
	STATUS	mandatory
	DESCRIPTION
		"The spool file disc space usage which consists of the 
		volume space that is used by hidden spool files that are
		not part of the permanent file space."
	::= { volumeEntry 13 }

volumePermFiles OBJECT-TYPE
	SYNTAX	INTEGER
	ACCESS	read-only
	STATUS	mandatory
	DESCRIPTION
		"The space used for permanent files on this volume."
	::= { volumeEntry 14 }

volumeTempFiles OBJECT-TYPE
	SYNTAX	INTEGER
	ACCESS	read-only
	STATUS	mandatory
	DESCRIPTION
		"The space used for temporary files on this volume."
	::= { volumeEntry 15 }

volumeTotalFreeSpace OBJECT-TYPE
	SYNTAX	INTEGER
	ACCESS	read-only
	STATUS	mandatory
	DESCRIPTION
		"The total free space for the volume."
	::= { volumeEntry 16 }

volumeLargestContigFree OBJECT-TYPE
	SYNTAX	INTEGER
	ACCESS	read-only
	STATUS	mandatory
	DESCRIPTION
		"The largest contiguous free space area on the volume."
	::= { volumeEntry 17 }

volumePercentUtilized OBJECT-TYPE
	SYNTAX	INTEGER
	ACCESS	read-only
	STATUS	mandatory
	DESCRIPTION
		"The percent of the volume currently being used for
		file storage and operating system overhead."
	::= { volumeEntry 18 }

-- The Processor Group

numActive OBJECT-TYPE
	SYNTAX	INTEGER
	ACCESS 	read-only
	STATUS	mandatory
	DESCRIPTION
		"Number of processors currently active, in the system.  A
		processor is considered active if it is capable of begin
		dispatched."
	::= { processor 1 }

numPresent OBJECT-TYPE
	SYNTAX	INTEGER
	ACCESS 	read-only
	STATUS	mandatory
	DESCRIPTION
		"The number of processors physically present in the system."
	::= { processor 2 }

processorMIstate OBJECT-TYPE
	SYNTAX	INTEGER {
		enabled(1),
		disabled(2)
		}
	ACCESS	read-write
	STATUS	mandatory
	DESCRIPTION
		"Setting this object to 1 will result in the measurement
		interface being turned on for the global processor statistics
		which will increase the amount of CPU used by the SNMP/XL 
		Agent.  Setting this object to 0 will cause the measurement
		interface to be disabled for the global processor statistics.
		When the measurement interface is enabled, the cpuUtilization
		object described below may be obtained."
	::= { processor 3 }

cpuUtilization OBJECT-TYPE
	SYNTAX	INTEGER
	ACCESS 	read-only
	STATUS	mandatory
	DESCRIPTION
		"The overall CPU utilization percentage on the system.  If
		the system has more than one processor, the value returned
		is averaged out over all of the processors that are present.
		The measurement interface must be enabled in order to get
		a valid value returned for this object ( see above object ).
		The number returned is the percentage of the CPU that was
		used since the last time the number was sampled.  This 
		value is consistent with various HP performance tools such
		as Glance/XL.  If the measurement interface is not enabled,
		the value returned will be 0."
	::= { processor 4 }

END
