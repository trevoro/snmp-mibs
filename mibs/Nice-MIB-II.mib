Nice-MIB-II DEFINITIONS ::= BEGIN
 
          --
          -- 
          --

          IMPORTS
	TEXTUAL-CONVENTION FROM SNMPv2-TC
					enterprises,
					TimeTicks
                         FROM RFC1155-SMI
					OBJECT-TYPE
                          FROM RFC-1212
					DisplayString
                          FROM RFC1213-MIB
					TRAP-TYPE       
		                  FROM RFC-1215;

          ----------------------------------------------------
          -- Textual conventions

    HostLocalTime  ::= TEXTUAL-CONVENTION
    DISPLAY-HINT "YYMMDDHHMMSS"
    STATUS       current
    DESCRIPTION
            "A date-time specification.

             field    octets   contents                  range
             -----    ------   --------                  -----
               YY     1-2      year                      00..99
               MM     3-4      month                     01..12
               DD     5-6      day                       01..31
               HH     7-8      hour                      00..23
               MM     9-10     minutes                   00..59
               SS     11-12    seconds                   00..60

            For example, Tuesday May 26, 1992 at 1:30:15 PM would be
            displayed as:   920526133015"

    SYNTAX       OCTET STRING (SIZE (12))


          ----------------------------------------------------
          -- Enumerations

          YesNo			::=	INTEGER { no(0), yes(1) }
          SeverityType	::= INTEGER { noError(1), warning(2), error(3), criticalError(4) }
          ClsErrorType  ::= INTEGER { callServerIsDown(1), rcmIsDown(2), 
                schedulerServerIsDown(3), dBServerIsDown(4), dispatchIsDown(5), 
                callServerLinkIsDown(6), recordingOnDemandIsNotEnabled(7), 
                schedulerServerIsNotInitializedProperly(8), failureConnectionToDB(9), 
                dBServerIsNotInitializedProperly(10), dBSpaceIsFull(11), 
                communicationProblemWithLogger(12), problematicClockDifferencesWithLogger(13), 
                noAvailableResources(14), loggerIsNotInitializedProperly(15), 
                rcmIsNotInitializedProperly(16), problemWithNPLUS1Loggers(17), 
                callServerTableIsFull(18), allCLSModulesInitFailed(19), 
                clsModuleRestartFailed(20), osDiskFailure(21) }
          RecordedMediaType ::= INTEGER { voice(1), screen(2), voiceAndScreen(3) }
          LoggerInitializationStatus ::= INTEGER { rcmInternalComponentsError(1), 
                noLoggerWasFound(2), noConnectionToSwitch(3), channelWasNotInitialized(4) }
          OsDiskFailureType ::= INTEGER { faileDisk(1), fixStarted(2), shutdownDirty(3), 
                missingDisk(4), unknownFailure(5) }
          ClsTableType ::= INTEGER { dbRecordsTable(1), callsTable(2), loginTable(3)}
          ApplicationErrorType ::= INTEGER { hostIsDown(1), applicationServerIsDown(2), 
                sysAdminHostConnectionIsDown(3), dataBaseConnectionIsDown(4), userAdminHostConnectionIsDown(5),
		storageCenterHostConnectionIsDown(6), playbackServerHostConnectionIsDown(7),
		queryExecuterHostConnectionIsDown(8), loggerWasNotAttachedToACLS(9), clsConnectionIsDown(10),
		loggerConnectionIsDown(11), scConnectionIsDown(12), ctiDbConnectionIsDown(13),
		caDbConnectionIsDown(14), nifDBConnectionIsDown(15), interactionDBConnectionIsDown(16),
		ruleEngineEventProviderFailed(17), ruleEngineEventProviderIdle(18), ruleEngineRuleGeneratorFailed(19),
		ruleEngineRuleGeneratorIdle(20), ruleEngineActionExecuterFailed(21), ruleEngineActionExecuterIdle(22),
		ruleEngineConfigurationError(23)}
          DriverErrorType ::= INTEGER { driverIsUp(1), driverIsDown(2), configurationFileIsMissing(3) }
          CTIEventsDBServerErrorType ::= INTEGER { ctiDBServerIsNotInitializedProperly(1), ctiDBSpaceIsFull(2),
					 ctiDBLogSpaceIsFull(3) , ctiFailureConnectionToCTIDB(4),
					 ctiMissingLookUpTable(5), ctiFailureInsertCTIEvent(6),
					 ctiInvalidMessageReceived(7), ctiRetentionFailure(8)}
          LoggingInstanceType ::= INTEGER { general(0), audioManagerModule(1), dataBaseModule(2), diskModule(3),
          		channelsModule(4), autoDeletionModule(5), hardwareDriverModule(6), voipDriverModule(7),
			dliDriverModule(8), nPlus1Module(9), dongleModule(10), checkSumModule(11)}
          LoggingErrorType ::= INTEGER {communicationFailure(1), loggerQueryFailure(2), initializationFailure(3),
				diskProblem(4), nplus1RobMalfunction(5), nplus1RobPowerFailure(6), lowFreeDiskSpace(7),
				noFreeDiskSpace(8), lowKeptDiskSpace(9), noKeptDiskSpace(10), dongleProblem(11),
				invalidChecksum(12), lineErrorOnChannels(13), someChannelsNotRecording(14),
				lowStatisticsAlarmOnChannels(15), highStatisticslarmOnChannels(16)}
          CaptureInstanceType ::= INTEGER {adifBoard(0), adif3Board(1), apaBoard(2) ,isdnBoard(3) ,etaiBoard(4) ,
				etai2Board(5), ntcmBoard(6), tdaBoard(7) ,natiBoard(8) ,nati2Board(9),
				isacBoard(10), isac2Board(11), dliBoard(12), lafBoard(13) ,udaBoard(14),
				lmopBoard(15), aliBoard(16), ali4Board(17), btai2Board(18)}     
          CaptureErrorType ::= INTEGER {dspProblemInRecordingBoard(1), dspProblemInAlgorithmsBoard(2),
				dspProblemInInterfaceBoard(3), dspProblemInPlaybackBoard(4),
				internalProblemInRecordingBoard(5), internalProblemInAlgorithmsBoard(6),
				internalProblemInInterfaceBoard(7), internalProblemInPlaybackBoard(8),
				lineProblemInRecordingBoard(9), lineProblemInAlgorithmsBoard(10),
				lineProblemInInterfaceBoard(11), lineProblemInPlaybackBoard(12)} 
          BackupErrorType ::= INTEGER { mediaError(1), deviceError(2), retrievalError(3), communicationError(4),
	          	hardDiskError(5), recoveryFailed(6), archivingSuspended(7)} 
          BackupInstanceType ::= INTEGER { hpDatDDS2Device(0), hpDatDDS3Device(1), hpDatDDS3AutoLoaderDevice(2), 
				sonyDatDDS2Device(3), sonyDatDDS3Device(4), sonyMo1Device(5), sonyAit1Device(6), hpMo1Device(7),
				sonyMo2Device(8), hpDatDDS2AutoLoaderDevice(9), sonyDatDDS3AutoLoaderDevice(10), 
				sonyait1autoloaderDevice(11), srvsonyDatDDS2sdt7000Device(12), hpDDS4Device(13), seaGateDatDDS4Device(49),
				sonyDatDDS4Device(50), sonyAit2Device(51), matsushitaDVDRam1Device(52), hitachiDVDRam1Device(53),   
				hitachiDVDRam2Device(54), matsushitaDVDRam2Device(55)} 
          BackupErrorBSRVErrorCode ::= INTEGER {
				bsrv-ErrCode-DeviceOk(0), bsrv-ErrCode-NoFreeTokens(1), bsrv-ErrCode-DiskIsFull(2) ,
				bsrv-ErrCode-WrongFileSize(3), bsrv-ErrCode-CannotAppendToMedia(4), bsrv-ErrCode-MediaHasNotYetExpired(5) ,
				bsrv-ErrCode-DeviceHasTimedOut(6), bsrv-ErrCode-MediaHasBadHeader(7), bsrv-ErrCode-TapeHasNoData(8) ,
				bsrv-ErrCode-WrongLoggerId(9), bsrv-ErrCode-RecoveryFailed(10), bsrv-ErrCode-DeviceNotConnected(11) ,
				bsrv-ErrCode-MediaWasManualyEjected-NoMagazine(1310732), bsrv-ErrCode-MediaWasManualyEjected-NotReady(-983028) ,
				bsrv-ErrCode-MediaWasManualyEjected-TargetAbort(-1441780), bsrv-ErrCode-MediumError-Medium(-1048563) ,
				bsrv-ErrCode-MediumError-CRCError(-3735539), bsrv-ErrCode-MediumError-ReadFromPbuFailed(720909), bsrv-ErrCode-MediaIsWriteProtected(14) ,
				bsrv-ErrCode-MediaIsBlank(15), bsrv-ErrCode-EndOfMediumWasReached-PBUEOMEarlyWarn(-2424816) ,
				bsrv-ErrCode-EndOfMediumWasReached-PBUVolOverflow(-1507312), bsrv-ErrCode-GeneralHardwareError-NoAdapter(-458735) ,
				bsrv-ErrCode-GeneralHardwareError-DataOverrun(-655343), bsrv-ErrCode-GeneralHardwareError-BusFree(-720879) ,
				bsrv-ErrCode-GeneralHardwareError-BusFail(-786415), bsrv-ErrCode-GeneralHardwareError-Hardware(-1114095) ,
				bsrv-ErrCode-GeneralHardwareError-PBUIOErr(-1638383), bsrv-ErrCode-GeneralHardwareError-PBUHostBusReset(-2818031) ,
				bsrv-ErrCode-InternalError-NoAspi(-65518), bsrv-ErrCode-InternalError-Busy(-131054) ,
				bsrv-ErrCode-InternalError-AspiErr(-196590), bsrv-ErrCode-InternalError-NoMem(-262126) ,
				bsrv-ErrCode-InternalError-NoDevice(-327662), bsrv-ErrCode-InternalError-AspiInval(-393198) ,
				bsrv-ErrCode-InternalError-Abort(-524270), bsrv-ErrCode-InternalError-TargetBusy(-851950) ,
				bsrv-ErrCode-InternalError-Reservation(-917486), bsrv-ErrCode-InternalError-IllegalReq(-1179630) ,
				bsrv-ErrCode-InternalError-InternalError(1835026), bsrv-ErrCode-InternalError-Miscompare(-1572846) ,
				bsrv-ErrCode-NoInitHeader(19), bsrv-ErrCode-BadMediaType(20), bsrv-ErrCode-DiskFailure(21) ,
				bsrv-ErrCode-BadCassette(22), bsrv-ErrCode-CleaningCartridge(23), bsrv-ErrCode-DeviceCleaningRequired(24) ,
				bsrv-ErrCode-OldVersionCassette(25), bsrv-ErrCode-AccessDeniedToMedia(26), bsrv-ErrCode-AutoloaderHardware(27) ,
				bsrv-ErrCode-CommToRemoteTapeErr(28), bsrv-ErrCode-LoadCountExceeded(29), bsrv-ErrCode-CannotEjectMedia(30) ,
				bsrv-ErrCode-TablesSizeMismatch(31), bsrv-ErrCode-FatNotSupported(32), bsrv-ErrCode-DeviceStillWorking(33) ,
				bsrv-ErrCode-NewMediaWasDetected(34) }
		  BackupConfig ::= INTEGER {bsrv-conf-null(-1), bsrv-conf-not-used(0), bsrv-conf-autoarch-pool-continousmode(100), bsrv-conf-autoarch-pool-periodicbackupmode(101),	
				bsrv-conf-autoarch-pool-periodicejectmode(102), bsrv-conf-autoarch-mirroring-continousmode(110), bsrv-conf-autoarch-mirroring-periodicbackupmode(111),
				bsrv-conf-autoarch-mirroring-periodicejectmode(112), bsrv-conf-autoarch-channalization-continousmode(120),
				bsrv-conf-autoarch-channalization-periodicbackupmode(121), bsrv-conf-autoarch-channalizationperiodicejectmode(122),
				bsrv-conf-manual-archiving(2), bsrv-conf-retrieval(3), bsrv-conf-init(4),
				bsrv-conf-erase(5), bsrv-conf-retrieve-while-archiving(6)}  			
  		  BackupDeviceState ::= INTEGER { deviceEmpty(1), deviceLoadingForWrite(2), deviceReadyForWrite(3), 
	   			deviceArchiving(4),deviceFull(5), deviceError(6), 
	   			deviceLoadingForReading(7), deviceReadyForReading(8), deviceRetrieving(9), 
	   			deviceClosing(10),deviceRecovering(11), deviceMirroringSuspended(12), 
	   			deviceCleaning(13), deviceMagazineIsExhausted (14), deviceErasing(15), 
	   			deviceVerifyingMagazine(16), deviceConnectingToRTS(19), deviceWaitingForBSRVRestart(20), 
	   			deviceConnectionToRTSFailed(21), occupiedRemoteDevice(22), cannotAppendOldMedia(25), 
	   			deviceWaitingForUserEject(26)}   			
          LineErrorType ::= INTEGER { fer(1), mlos(2), pra(3), flos(4), ais(5),
          		nos(6), los(7), ubal(8), lsig(9),mfas(10), ito(11), swf(12), rai(13), voipErr(14)}  
		  BoardType ::= INTEGER {hc-adif3-board(0), hc-etai2-board(1), hc-isac2-board(2), hc-btai2-board(3),
				hc-nati2-board(4), hc-ali4-board(5), board-type-none(-1), board-type-adif(6),
				board-type-etai(7), board-type-dli(8), board-type-ali(9), board-type-isdn(10),
				board-type-ntcm(11), board-type-isac(12), board-type-nati(13), board-type-external	(14)}  
          RdTaskType ::= INTEGER {totalCompare (8),sampleCompare (9)}
		  TaskState ::= INTEGER {notActive (0), active (1), endingDueTime (2), stuck (3)} 
		  RdErrorType ::= INTEGER {exceptionWhileProcessing (0),failedToInitializeApplication (1),
		  		keepAliveHearbeatFailure (2), connectionToCLSLost (3), connectionToLoggerLost (4),
		  		clsAddressingGeneralError (5)} 
		  RdConnStatus ::= INTEGER { connectionNotActive (0), connectionIsActive (1), connectionLost(2)}
          ----------------------------------------------------
          -- Tree root definitions

          nice        OBJECT IDENTIFIER ::= { enterprises 3167 }
 
          niceMib-2        OBJECT IDENTIFIER ::= { nice 1 }
		  
          storageCenter OBJECT IDENTIFIER   ::= { niceMib-2 6 }
		  
		  
          ----------------------------------------------------
          -- Traps info sub tree

          trapsInfo OBJECT IDENTIFIER  ::= { niceMib-2 1 }
          
          trapSeverity OBJECT-TYPE
              SYNTAX  SeverityType
              ACCESS  not-accessible
              STATUS  mandatory
              DESCRIPTION
                      "The trap severity level." 
              ::= { trapsInfo 1 }

          trapLoggerId OBJECT-TYPE
              SYNTAX  DisplayString
              ACCESS  not-accessible
              STATUS  mandatory
              DESCRIPTION
                      "A logger ID." 
              ::= { trapsInfo 2 }

          trapRecordedMedia OBJECT-TYPE
              SYNTAX  RecordedMediaType
              ACCESS  not-accessible
              STATUS  mandatory
              DESCRIPTION
                      "A recorded media type." 
              ::= { trapsInfo 3 }

          trapLoggerInitialization OBJECT-TYPE
              SYNTAX  LoggerInitializationStatus
              ACCESS  not-accessible
              STATUS  mandatory
              DESCRIPTION
                      "A status in the logger initialization phases." 
              ::= { trapsInfo 4 }

          trapDBErrorCode OBJECT-TYPE
              SYNTAX  INTEGER
              ACCESS  not-accessible
              STATUS  mandatory
              DESCRIPTION
                      "An error code retrieved fron the SQL server." 
              ::= { trapsInfo 5 }

          trapOsDiskFailure OBJECT-TYPE
              SYNTAX  OsDiskFailureType
              ACCESS  not-accessible
              STATUS  mandatory
              DESCRIPTION
                      "An Operating system Disk Failure type." 
              ::= { trapsInfo 6 }

          trapClsTableType OBJECT-TYPE
              SYNTAX  ClsTableType
              ACCESS  not-accessible
              STATUS  mandatory
              DESCRIPTION
                      "A type of a CLS table." 
              ::= { trapsInfo 7 }

          trapDiskUsage OBJECT-TYPE
              SYNTAX  INTEGER
              ACCESS  not-accessible
              STATUS  mandatory
              DESCRIPTION
                      "Disk usage in Mega-Bytes." 
              ::= { trapsInfo 8 }

          trapLoggerInitializationStatus OBJECT-TYPE
              SYNTAX  LoggerInitializationStatus
              ACCESS  not-accessible
              STATUS  mandatory
              DESCRIPTION
                      "Logger Initialization status reported to CLS." 
              ::= { trapsInfo 9 }

          trapHostTime OBJECT-TYPE
              SYNTAX  HostLocalTime
              ACCESS  not-accessible
              STATUS  mandatory
              DESCRIPTION
                      "The Host's time stamp at the time the trap was sent (local time)." 
              ::= { trapsInfo 10 } 
     
          trapCLSId OBJECT-TYPE
              SYNTAX  DisplayString
              ACCESS  not-accessible
              STATUS  mandatory
              DESCRIPTION
                      "A CLS ID." 
              ::= { trapsInfo 11 }

          trapSCId OBJECT-TYPE
              SYNTAX  DisplayString
              ACCESS  not-accessible
              STATUS  mandatory
              DESCRIPTION
                      "A SC ID." 
              ::= { trapsInfo 12 }

          trapDBId OBJECT-TYPE
              SYNTAX  DisplayString
              ACCESS  not-accessible
              STATUS  mandatory
              DESCRIPTION
                      "A DB ID." 
              ::= { trapsInfo 13 }
     
	 trapFileName OBJECT-TYPE
              SYNTAX  DisplayString
              ACCESS  not-accessible
              STATUS  mandatory
              DESCRIPTION
                      "A File name." 
              ::= { trapsInfo 14 }
     
     trapDeviceId OBJECT-TYPE
              SYNTAX  DisplayString
              ACCESS  not-accessible
              STATUS  mandatory
              DESCRIPTION
                      "A device Id ." 
              ::= { trapsInfo 15 }   
                                    
     trapRegistryKey OBJECT-TYPE
              SYNTAX  DisplayString
              ACCESS  not-accessible
              STATUS  mandatory
              DESCRIPTION
                      "Registry key." 
              ::= { trapsInfo 16 }  
          trapVLModuleName OBJECT-TYPE
              SYNTAX  DisplayString
              ACCESS  not-accessible
              STATUS  mandatory
              DESCRIPTION
                      "The name of the Voice Logger module." 
              ::= { trapsInfo 17 }

          trapVLModuleStatus OBJECT-TYPE
              SYNTAX  SeverityType
              ACCESS  not-accessible
              STATUS  mandatory
              DESCRIPTION
                      "The status of the Voice Logger module." 
              ::= { trapsInfo 18 }

          trapDiskDrive OBJECT-TYPE
              SYNTAX  DisplayString
              ACCESS  not-accessible
              STATUS  mandatory
              DESCRIPTION
                      "Disk Drive." 
              ::= { trapsInfo 19 }
          trapLoggerIdInChain OBJECT-TYPE
              SYNTAX  INTEGER
              ACCESS  not-accessible
              STATUS  mandatory
              DESCRIPTION
                      "Logger ID in chain." 
              ::= { trapsInfo 20 }
          trapFreeSpacePercentage OBJECT-TYPE
              SYNTAX  INTEGER
              ACCESS  not-accessible
              STATUS  mandatory
              DESCRIPTION
                      "The percentage of available free space." 
              ::= { trapsInfo 21 }
          trapKeptSpacePercentage OBJECT-TYPE
              SYNTAX  INTEGER
              ACCESS  not-accessible
              STATUS  mandatory
              DESCRIPTION
                      "The Percentage of kept space." 
              ::= { trapsInfo 22 }
          trapChannelNumber OBJECT-TYPE
              SYNTAX  INTEGER
              ACCESS  not-accessible
              STATUS  mandatory
              DESCRIPTION
                      "Channel number." 
              ::= { trapsInfo 23 }
          trapBoardNumber OBJECT-TYPE
              SYNTAX  INTEGER
              ACCESS  not-accessible
              STATUS  mandatory
              DESCRIPTION
                      "Board number." 
              ::= { trapsInfo 24 }
          trapDspNumber OBJECT-TYPE
              SYNTAX  INTEGER
              ACCESS  not-accessible
              STATUS  mandatory
              DESCRIPTION
                      "DSP number." 
              ::= { trapsInfo 25 }
          trapLineNumber OBJECT-TYPE
              SYNTAX  INTEGER
              ACCESS  not-accessible
              STATUS  mandatory
              DESCRIPTION
                      "Line Number." 
              ::= { trapsInfo 26 }
          trapLineProblem OBJECT-TYPE
              SYNTAX  DisplayString
              ACCESS  not-accessible
              STATUS  mandatory
              DESCRIPTION
                      "Description of the line problem." 
              ::= { trapsInfo 27 }
          trapDataLineNumber OBJECT-TYPE
              SYNTAX  INTEGER
              ACCESS  not-accessible
              STATUS  mandatory
              DESCRIPTION
                      "Data Line number." 
              ::= { trapsInfo 28 }
          trapDaughterBoardNumber OBJECT-TYPE
              SYNTAX  INTEGER
              ACCESS  not-accessible
              STATUS  mandatory
              DESCRIPTION
                      "Daughter Board Number." 
              ::= { trapsInfo 29 }
          trapSQLTableName OBJECT-TYPE
              SYNTAX  DisplayString
              ACCESS  not-accessible
              STATUS  mandatory
              DESCRIPTION
                      "Name of SQL Table." 
              ::= { trapsInfo 30 }   
         trapEventProviderId OBJECT-TYPE
              SYNTAX  INTEGER
              ACCESS  not-accessible
              STATUS  mandatory
              DESCRIPTION
                      "Rule engine event provider Id." 
              ::= { trapsInfo 31 }
          trapRuleGeneratorId OBJECT-TYPE
              SYNTAX  INTEGER
              ACCESS  not-accessible
              STATUS  mandatory
              DESCRIPTION
                      "Rule engine rule generator Id." 
              ::= { trapsInfo 32 }
         trapActionExecuterId OBJECT-TYPE
              SYNTAX  INTEGER
              ACCESS  not-accessible
              STATUS  mandatory
              DESCRIPTION
                      "Rule engine action executer Id." 
              ::= { trapsInfo 33 }
	trapLineErrorType OBJECT-TYPE
              SYNTAX  LineErrorType
              ACCESS  not-accessible
              STATUS  mandatory
              DESCRIPTION
                      "The Line Error Type." 
              ::= { trapsInfo 34 }

          trapRecordingChannel OBJECT-TYPE
              SYNTAX  INTEGER
              ACCESS  not-accessible
              STATUS  mandatory
              DESCRIPTION
                      "A recording channel." 
              ::= { trapsInfo 35 }
          
          trapRecordingStartTime OBJECT-TYPE
              SYNTAX  HostLocalTime
              ACCESS  not-accessible
              STATUS  mandatory
              DESCRIPTION
                      "A recording start time ." 
              ::= { trapsInfo 36 }
                           
          trapRecordingStopTime OBJECT-TYPE
              SYNTAX  HostLocalTime
              ACCESS  not-accessible
              STATUS  mandatory
              DESCRIPTION
                      "A recording stop time ." 
              ::= { trapsInfo 37 }
          trapNumOfChannels OBJECT-TYPE
              SYNTAX  INTEGER
              ACCESS  not-accessible
              STATUS  mandatory
              DESCRIPTION
                      "Number of channels." 
              ::= { trapsInfo 38 }
          trapBoardOrLogicalTrunk OBJECT-TYPE
              SYNTAX  INTEGER
              ACCESS  not-accessible
              STATUS  mandatory
              DESCRIPTION
                      "Board number or Logical Trunk number." 
              ::= { trapsInfo 39 }
          trapChannelOrTimeslot OBJECT-TYPE
              SYNTAX  INTEGER
              ACCESS  not-accessible
              STATUS  mandatory
              DESCRIPTION
                      "Channel number or Timeslot number." 
              ::= { trapsInfo 40 }
          trapMateLogicalTrunk OBJECT-TYPE
              SYNTAX  INTEGER
              ACCESS  not-accessible
              STATUS  mandatory
              DESCRIPTION
                      "Mate Trunk Number." 
              ::= { trapsInfo 41 }
          trapMateTimeslot OBJECT-TYPE
              SYNTAX  INTEGER
              ACCESS  not-accessible
              STATUS  mandatory
              DESCRIPTION
                      "Mate Timeslot Number." 
              ::= { trapsInfo 42 }
          trapBoardType OBJECT-TYPE
              SYNTAX  BoardType
              ACCESS  not-accessible
              STATUS  mandatory
              DESCRIPTION
                      "Type of board." 
              ::= { trapsInfo 43 }
          trapLogicalStreamNumber OBJECT-TYPE
              SYNTAX  INTEGER
              ACCESS  not-accessible
              STATUS  mandatory
              DESCRIPTION
                      "Logical Stream Number." 
              ::= { trapsInfo 44 }
          trapBackupConfig OBJECT-TYPE
              SYNTAX  BackupConfig
              ACCESS  not-accessible
              STATUS  mandatory
              DESCRIPTION
                      "The configuration of the backup device." 
              ::= { trapsInfo 45 }
          trapBackupDeviceState OBJECT-TYPE
              SYNTAX  BackupDeviceState
              ACCESS  not-accessible
              STATUS  mandatory
              DESCRIPTION
                      "The state of the backup device." 
              ::= { trapsInfo 46 }
              
              
          ----------------------------------------------------
		  -- CLS subtree definition


          cls OBJECT IDENTIFIER  ::= { niceMib-2 2 }

          clsRcm OBJECT IDENTIFIER  ::= { cls 1 }
          
          rcmName OBJECT-TYPE
              SYNTAX  DisplayString
              ACCESS  read-only
              STATUS  mandatory
              DESCRIPTION
                      "The Module name." 
              ::= { clsRcm 1 }
 
          rcmStatus OBJECT-TYPE
              SYNTAX  SeverityType
              ACCESS  read-only
              STATUS  mandatory
              DESCRIPTION
                      "The Resource Manager current status"
              ::= { clsRcm 2 }

          rcmPendingErrorsTable OBJECT-TYPE
              SYNTAX  SEQUENCE OF RcmPendingErrorsEntry
              ACCESS  not-accessible
              STATUS  mandatory
              DESCRIPTION
                      "A list of pending errors for the CLS's Resource Manager."
              ::= { clsRcm 3 }

          rcmPendingErrorsEntry OBJECT-TYPE
              SYNTAX  RcmPendingErrorsEntry
              ACCESS  not-accessible
              STATUS  mandatory
              DESCRIPTION
                      "A pending error for the CLS's Resource Manager."
              INDEX   { rcmErrorIndex }
              ::= { rcmPendingErrorsTable 1 }

          RcmPendingErrorsEntry ::=
              SEQUENCE 
              {
					rcmErrorType
						ClsErrorType,
					rcmErrorReflectedStatus
						SeverityType,
					rcmErrorLoggerId
						DisplayString,
					rcmErrorIndex
						INTEGER 
              }
 
           rcmErrorType OBJECT-TYPE
              SYNTAX  ClsErrorType
              ACCESS  read-only
              STATUS  mandatory
              DESCRIPTION 
                      "The specific error type pending for the Resource Manager."
              ::= { rcmPendingErrorsEntry 1 }

           rcmErrorReflectedStatus OBJECT-TYPE
              SYNTAX  SeverityType
              ACCESS  read-only
              STATUS  mandatory
              DESCRIPTION 
                      "The specific error status reflected on the Resource Manager
                      as a result of the pending error."
              ::= { rcmPendingErrorsEntry 2 }

           rcmErrorLoggerId OBJECT-TYPE
              SYNTAX  DisplayString
              ACCESS  read-only
              STATUS  optional
              DESCRIPTION 
                      "The logger ID related to the pending error (if any)"
              ::= { rcmPendingErrorsEntry 3 }

           rcmErrorIndex OBJECT-TYPE
              SYNTAX  INTEGER
              ACCESS  read-only
              STATUS  mandatory
              DESCRIPTION 
                      "The error index in the table."
              ::= { rcmPendingErrorsEntry 4 }
              
          clsCallServer OBJECT IDENTIFIER  ::= { cls 2 }
          
          callServerName OBJECT-TYPE
              SYNTAX  DisplayString
              ACCESS  read-only
              STATUS  mandatory
              DESCRIPTION
                      "The Module name." 
              ::= { clsCallServer 1 }
 
          callServerStatus OBJECT-TYPE
              SYNTAX  SeverityType
              ACCESS  read-only
              STATUS  mandatory
              DESCRIPTION
                      "The Call server current status"
              ::= { clsCallServer 2 }

          callServerPendingErrorsTable OBJECT-TYPE
              SYNTAX  SEQUENCE OF CallServerPendingErrorsEntry
              ACCESS  not-accessible
              STATUS  mandatory
              DESCRIPTION
                      "A list of pending errors for the CLS's Call Server."
              ::= { clsCallServer 3 }

          callServerPendingErrorsEntry OBJECT-TYPE
              SYNTAX  CallServerPendingErrorsEntry
              ACCESS  not-accessible
              STATUS  mandatory
              DESCRIPTION
                      "A pending error for the CLS's Call Server."
              INDEX   { callServerErrorIndex }
              ::= { callServerPendingErrorsTable 1 }

          CallServerPendingErrorsEntry ::=
              SEQUENCE 
              {
					callServerErrorType
						ClsErrorType,
					callServerErrorReflectedStatus
						SeverityType,
					callServerErrorIndex
						INTEGER 
              }
 
           callServerErrorType OBJECT-TYPE
              SYNTAX  ClsErrorType
              ACCESS  read-only
              STATUS  mandatory
              DESCRIPTION 
                      "The specific error type pending for the Module."
              ::= { callServerPendingErrorsEntry 1 }

           callServerErrorReflectedStatus OBJECT-TYPE
              SYNTAX  SeverityType
              ACCESS  read-only
              STATUS  mandatory
              DESCRIPTION 
                      "The specific error status reflected on the Module
                      as a result of the pending error."
              ::= { callServerPendingErrorsEntry 2 }

           callServerErrorIndex OBJECT-TYPE
              SYNTAX  INTEGER
              ACCESS  read-only
              STATUS  mandatory
              DESCRIPTION 
                      "The error index in the table."
              ::= { callServerPendingErrorsEntry 3 }

          clsSchedulerServer OBJECT IDENTIFIER  ::= { cls 3 }
          
          schedulerServerName OBJECT-TYPE
              SYNTAX  DisplayString
              ACCESS  read-only
              STATUS  mandatory
              DESCRIPTION
                      "The Module name." 
              ::= { clsSchedulerServer 1 }
 
          schedulerServerStatus OBJECT-TYPE
              SYNTAX  SeverityType
              ACCESS  read-only
              STATUS  mandatory
              DESCRIPTION
                      "The Scheduler Server current status"
              ::= { clsSchedulerServer 2 }

          schedulerServerPendingErrorsTable OBJECT-TYPE
              SYNTAX  SEQUENCE OF SchedulerServerPendingErrorsEntry
              ACCESS  not-accessible
              STATUS  mandatory
              DESCRIPTION
                      "A list of pending errors for the CLS's Scheduler Server."
              ::= { clsSchedulerServer 3 }

          schedulerServerPendingErrorsEntry OBJECT-TYPE
              SYNTAX  SchedulerServerPendingErrorsEntry
              ACCESS  not-accessible
              STATUS  mandatory
              DESCRIPTION
                      "A pending error for the CLS's Scheduler Server."
              INDEX   { schedulerServerErrorIndex }
              ::= { schedulerServerPendingErrorsTable 1 }

          SchedulerServerPendingErrorsEntry ::=
              SEQUENCE 
              {
					schedulerServerErrorType
						ClsErrorType,
					schedulerServerErrorReflectedStatus
						SeverityType,
					schedulerServerErrorIndex
						INTEGER 
              }
 
           schedulerServerErrorType OBJECT-TYPE
              SYNTAX  ClsErrorType
              ACCESS  read-only
              STATUS  mandatory
              DESCRIPTION 
                      "The specific error type pending for the Module."
              ::= { schedulerServerPendingErrorsEntry 1 }

           schedulerServerErrorReflectedStatus OBJECT-TYPE
              SYNTAX  SeverityType
              ACCESS  read-only
              STATUS  mandatory
              DESCRIPTION 
                      "The specific error status reflected on the Module
                      as a result of the pending error."
              ::= { schedulerServerPendingErrorsEntry 2 }

           schedulerServerErrorIndex OBJECT-TYPE
              SYNTAX  INTEGER
              ACCESS  read-only
              STATUS  mandatory
              DESCRIPTION 
                      "The error index in the table."
              ::= { schedulerServerPendingErrorsEntry 3 }
              
          clsDbServer OBJECT IDENTIFIER  ::= { cls 4 }
          
          dbServerName OBJECT-TYPE
              SYNTAX  DisplayString
              ACCESS  read-only
              STATUS  mandatory
              DESCRIPTION
                      "The Module name." 
              ::= { clsDbServer 1 }
 
          dbServerStatus OBJECT-TYPE
              SYNTAX  SeverityType
              ACCESS  read-only
              STATUS  mandatory
              DESCRIPTION
                      "The Database Server current status"
              ::= { clsDbServer 2 }

          dbServerPendingErrorsTable OBJECT-TYPE
              SYNTAX  SEQUENCE OF DbServerPendingErrorsEntry
              ACCESS  not-accessible
              STATUS  mandatory
              DESCRIPTION
                      "A list of pending errors for the CLS's Database Server."
              ::= { clsDbServer 3 }

          dbServerPendingErrorsEntry OBJECT-TYPE
              SYNTAX  DbServerPendingErrorsEntry
              ACCESS  not-accessible
              STATUS  mandatory
              DESCRIPTION
                      "A pending error for the CLS's Database Server."
              INDEX   { dbServerErrorIndex }
              ::= { dbServerPendingErrorsTable 1 }

          DbServerPendingErrorsEntry ::=
              SEQUENCE 
              {
					dbServerErrorType
						ClsErrorType,
					dbServerErrorReflectedStatus
						SeverityType,
					dbServerDBErrorCode
						INTEGER,						
					dbServerErrorIndex
						INTEGER 
              }
 
           dbServerErrorType OBJECT-TYPE
              SYNTAX  ClsErrorType
              ACCESS  read-only
              STATUS  mandatory
              DESCRIPTION 
                      "The specific error type pending for the Module."
              ::= { dbServerPendingErrorsEntry 1 }

           dbServerErrorReflectedStatus OBJECT-TYPE
              SYNTAX  SeverityType
              ACCESS  read-only
              STATUS  mandatory
              DESCRIPTION 
                      "The specific error status reflected on the Module
                      as a result of the pending error."
              ::= { dbServerPendingErrorsEntry 2 }

           dbServerDBErrorCode OBJECT-TYPE
              SYNTAX  INTEGER
              ACCESS  read-only
              STATUS  optional
              DESCRIPTION 
                      "The SQL error code ID related to the pending error (if any)"
              ::= { dbServerPendingErrorsEntry 3 }

           dbServerErrorIndex OBJECT-TYPE
              SYNTAX  INTEGER
              ACCESS  read-only
              STATUS  mandatory
              DESCRIPTION 
                      "The error index in the table."
              ::= { dbServerPendingErrorsEntry 4 }

          clsDispatcher OBJECT IDENTIFIER  ::= { cls 5 }
          
          clsDispatcherName OBJECT-TYPE
              SYNTAX  DisplayString
              ACCESS  read-only
              STATUS  mandatory
              DESCRIPTION
                      "The Module name." 
              ::= { clsDispatcher 1 }
 
          clsDispatcherStatus OBJECT-TYPE
              SYNTAX  SeverityType
              ACCESS  read-only
              STATUS  mandatory
              DESCRIPTION
                      "The CLS Dispatcher current status"
              ::= { clsDispatcher 2 }

          clsDispatcherPendingErrorsTable OBJECT-TYPE
              SYNTAX  SEQUENCE OF ClsDispatcherPendingErrorsEntry
              ACCESS  not-accessible
              STATUS  mandatory
              DESCRIPTION
                      "A list of pending errors for the CLS's Dispatcher Server."
              ::= { clsDispatcher 3 }

          clsDispatcherPendingErrorsEntry OBJECT-TYPE
              SYNTAX  ClsDispatcherPendingErrorsEntry
              ACCESS  not-accessible
              STATUS  mandatory
              DESCRIPTION
                      "A pending error for the CLS's Dispatcher Server."
              INDEX   { clsDispatcherErrorIndex }
              ::= { clsDispatcherPendingErrorsTable 1 }

          ClsDispatcherPendingErrorsEntry ::=
              SEQUENCE 
              {
					clsDispatcherErrorType
						ClsErrorType,
					clsDispatcherErrorReflectedStatus
						SeverityType,
					clsDispatcherErrorIndex
						INTEGER 
              }
 
           clsDispatcherErrorType OBJECT-TYPE
              SYNTAX  ClsErrorType
              ACCESS  read-only
              STATUS  mandatory
              DESCRIPTION 
                      "The specific error type pending for the Module."
              ::= { clsDispatcherPendingErrorsEntry 1 }

           clsDispatcherErrorReflectedStatus OBJECT-TYPE
              SYNTAX  SeverityType
              ACCESS  read-only
              STATUS  mandatory
              DESCRIPTION 
                      "The specific error status reflected on the Module
                      as a result of the pending error."
              ::= { clsDispatcherPendingErrorsEntry 2 }

           clsDispatcherErrorIndex OBJECT-TYPE
              SYNTAX  INTEGER
              ACCESS  read-only
              STATUS  mandatory
              DESCRIPTION 
                      "The error index in the table."
              ::= { clsDispatcherPendingErrorsEntry 3 }

          clsAgentConfig OBJECT IDENTIFIER  ::= { cls 6 }
          
          clsAgentIsRepeatingTraps OBJECT-TYPE
              SYNTAX  YesNo
              ACCESS  read-write
              STATUS  mandatory
              DESCRIPTION
                      "Defining whether the agent will repeat sending traps for each 
                      pending error of it's modules." 
              ::= { clsAgentConfig 1 }

          clsAgentTrapsRepeatInterval OBJECT-TYPE
              SYNTAX  INTEGER
              ACCESS  read-write
              STATUS  mandatory
              DESCRIPTION
                      "Defining the interval between repeated traps in minutes." 
              ::= { clsAgentConfig 2 }

          clsAgentVersion OBJECT-TYPE
              SYNTAX  DisplayString
              ACCESS  read-only
              STATUS  mandatory
              DESCRIPTION
                      "the agent version number as a sequence of 4 numbers (in the following format 'a.b.c.d')." 
              ::= { clsAgentConfig 3 }

          ----------------------------------------------------
		  -- CLS traps (starting at specific trap 1000)
            
          clsRcmIsDown TRAP-TYPE
            ENTERPRISE  clsRcm
            VARIABLES   { trapSeverity, 
						  rcmName,
	          			  rcmStatus,
	          			  trapHostTime }
            DESCRIPTION
                    "RCM Is DownRule Engine Action Executer Failed. Trap Severity = {1}, RCM Name = {2}, RCM Status = {3}, Trap Host Time = {4}"
            ::= 1001
            
            
          clsRcmIsUp TRAP-TYPE
            ENTERPRISE  clsRcm
            VARIABLES   { trapSeverity,rcmName,
            		rcmStatus,   trapHostTime
 }
            DESCRIPTION
                    "RCM Is Up. Trap Severity = {1}, RCM Name = {2}, RCM Status = {3}, Trap Host Time = {4}"
            ::= 1002
                        
          
          clsCallServerIsDown TRAP-TYPE
            ENTERPRISE  clsCallServer
            VARIABLES   { trapSeverity, 
						  callServerName,
						  callServerStatus,
						  trapHostTime
 }
						  
            DESCRIPTION
                    "Call Server Is Down. Trap Severity = {1}, Call Server Name = {2}, Call Server Status = {3}, Trap Host Time = {4}"
            ::= 1003
            
            
         clsCallServerIsUp TRAP-TYPE
            ENTERPRISE  clsCallServer
            VARIABLES   { trapSeverity, 
						  callServerName,
						  callServerStatus,
						  trapHostTime
 }
            DESCRIPTION
                    "Call Server Is Up. Trap Severity = {1}, Call Server Name = {2}, Call Server Status = {3}, Trap Host Time = {4}"
            ::= 1004
            
                      
    
          clsSchedulerServerIsDown TRAP-TYPE
            ENTERPRISE  clsSchedulerServer
            VARIABLES   { trapSeverity, 
						  schedulerServerName,
						  schedulerServerStatus
,
						  trapHostTime
 }
            DESCRIPTION
                    "Scheduler Server Is Down. Trap Severity = {1}, Scheduler Server Name = {2}, Scheduler Server Status = {3}, Trap Host Time = {4}"
            ::= 1005
 
 
          clsSchedulerServerIsUp TRAP-TYPE
            ENTERPRISE  clsSchedulerServer
            VARIABLES   { trapSeverity, 
						  schedulerServerName,
						  schedulerServerStatus,
						  trapHostTime
 }
            DESCRIPTION
                    "Scheduler Server Is Up. Trap Severity = {1}, Scheduler Server Name = {2}, Scheduler Server Status = {3}, Trap Host Time = {4}"
            ::= 1006
                      
            
          clsDBServerIsDown TRAP-TYPE
            ENTERPRISE  clsDbServer
            VARIABLES   { trapSeverity, 
						  dbServerName,
						  dbServerStatus,
						  trapHostTime
 }
            DESCRIPTION
                    "DB Server Is Down. Trap Severity = {1}, Database Server Name = {2}, Database Server Status = {3}, Trap Host Time = {4}"
            ::= 1007


          clsDBServerIsUp TRAP-TYPE
            ENTERPRISE  clsDbServer
            VARIABLES   { trapSeverity, 
						  dbServerName,
						  dbServerStatus,
						  trapHostTime
 }
            DESCRIPTION
                    "DB Server Is Up. Trap Severity = {1}, Database Server Name = {2}, Database Server Status = {3}, Trap Host Time = {4}"
            ::= 1008
            
                                  
          
          clsDispatchIsDown TRAP-TYPE
            ENTERPRISE  clsDispatcher
            VARIABLES   { trapSeverity, 
						  clsDispatcherName,
						  clsDispatcherStatus,
						  trapHostTime }
            DESCRIPTION
                    "Dispatch Is Down. Trap Severity = {1}, CLS Dispatcher Name = {2}, CLS Dispatcher Status = {3}, Trap Host Time = {4}"
            ::= 1009


          clsDispatchIsUp TRAP-TYPE
            ENTERPRISE  clsDispatcher
            VARIABLES   { trapSeverity, 
						  clsDispatcherName,
						  clsDispatcherStatus,
						  trapHostTime }
            DESCRIPTION
                    "Dispatch Is Up. Trap Severity = {1}, CLS Dispatcher Name = {2}, CLS Dispatcher Status = {3}, Trap Host Time = {4}"
            ::= 1010
                                    
          clsCallServerLinkIsDown TRAP-TYPE
            ENTERPRISE  clsCallServer
            VARIABLES   { trapSeverity, 
						  callServerName,
            					  callServerStatus,
						  trapHostTime
 }
            DESCRIPTION
                    "Call Server Link Is Down. Trap Severity = {1}, Call Server Name = {2}, Call Server Status = {3}, Trap Host Time = {4}"
            ::= 1011
            
          clsCallServerLinkIsUp TRAP-TYPE
            ENTERPRISE  clsCallServer
            VARIABLES   { trapSeverity, 
						  callServerName,
            					  callServerStatus,
						  trapHostTime
 }
            DESCRIPTION
                    "Call Server Link Is Up. Trap Severity = {1}, Call Server Name = {2}, Call Server Status = {3}, Trap Host Time = {4}"
            ::= 1012
                        
          clsRecordingOnDemandIsNotEnabled TRAP-TYPE
            ENTERPRISE  clsSchedulerServer
            VARIABLES   { trapSeverity, 
						  schedulerServerName,
						  schedulerServerStatus,
						  trapHostTime
 }
            DESCRIPTION
                    "CLS RecordingOnDemand Is Not Enabled. Trap Severity = {1}, Scheduler Server Name = {2}, Scheduler Server Status = {3}, Trap Host Time = {4}"
            ::= 1013
            
          clsRecordingOnDemandIsEnabled TRAP-TYPE
            ENTERPRISE  clsSchedulerServer
            VARIABLES   { trapSeverity, 
						  schedulerServerName,
						  schedulerServerStatus,
						  trapHostTime
 }
            DESCRIPTION
                    "CLS RecordingOnDemand Is Enabled. Trap Severity = {1}, Scheduler Server Name = {2}, Scheduler Server Status = {3}, Trap Host Time = {4}"
            ::= 1014

          clsSchedulerServerIsNotInitializedProperly TRAP-TYPE
            ENTERPRISE  clsSchedulerServer
            VARIABLES   { trapSeverity, 
						  schedulerServerName,
						  schedulerServerStatus,
						  trapHostTime
 }
            DESCRIPTION
                    "CLS Scheduler Server Is Not Initialized Properly. Trap Severity = {1}, Scheduler Server Name = {2}, Scheduler Server Status = {3}, Trap Host Time = {4}"
            ::= 1015
                                    
          clsSchedulerServerIsInitializedProperly TRAP-TYPE
            ENTERPRISE  clsSchedulerServer
            VARIABLES   { trapSeverity, 
						  schedulerServerName,
						  schedulerServerStatus,
						  trapHostTime
 }
            DESCRIPTION
                    "CLS Scheduler Server Is Initialized Properly. Trap Severity = {1}, Scheduler Server Name = {2}, Scheduler Server Status = {3}, Trap Host Time = {4}"
            ::= 1016

          clsFailureConnectionToDB TRAP-TYPE
            ENTERPRISE  clsDbServer
            VARIABLES   { trapSeverity, 
						  dbServerName,
						  dbServerStatus,
						  trapHostTime, 
						  trapDBErrorCode }
            DESCRIPTION
                    "CLS Failure Connection To DB. Trap Severity = {1}, Database Server Name = {2}, Database Server Status = {3}, Trap Host Time = {4}, Database Error Code = {5}"
            ::= 1017                                                                        

          clsConnectionToDBIsOK TRAP-TYPE
            ENTERPRISE  clsDbServer
            VARIABLES   { trapSeverity, 
						  dbServerName,
						  dbServerStatus,
						  trapHostTime
 }
            DESCRIPTION
                    "CLS Connection To DB Is OK. Trap Severity = {1}, Database Server Name = {2}, Database Server Status = {3}, Trap Host Time = {4}"
            ::= 1018                                    
            
          clsDBServerIsNotInitializedProperly TRAP-TYPE
            ENTERPRISE  clsDbServer
            VARIABLES   { trapSeverity, 
						  dbServerName,
						  dbServerStatus,
						  trapHostTime
 }
            DESCRIPTION
                    "DB Server Is Not Initialized Properly. Trap Severity = {1}, Database Server Name = {2}, Database Server Status = {3}, Trap Host Time = {4}"
            ::= 1019                                    

          clsDBServerIsInitializedProperly TRAP-TYPE
            ENTERPRISE  clsDbServer
            VARIABLES   { trapSeverity, 
						  dbServerName,
						  dbServerStatus,
						  trapHostTime
 }
            DESCRIPTION
                    "DB Server Is Initialized Properly. Trap Severity = {1}, Database Server Name = {2}, Database Server Status = {3}, Trap Host Time = {4}"
            ::= 1020                                   

          clsDBSpaceIsFull TRAP-TYPE
            ENTERPRISE  clsDbServer
            VARIABLES   { trapSeverity, 
						  dbServerName,
						  dbServerStatus,
						  trapHostTime,
						  trapDBErrorCode }
            DESCRIPTION
                    "DB Space Is Full. Trap Severity = {1}, Database Server Name = {2}, Database Server Status = {3}, Trap Host Time = {4}, Database Error code = {5}"
            ::= 1021                                

          clsDBSpaceIsOK TRAP-TYPE
            ENTERPRISE  clsDbServer
            VARIABLES   { trapSeverity, 
						  dbServerName,
						  dbServerStatus,
						  trapHostTime
 }
            DESCRIPTION
                    "DB Space Is OK. Trap Severity = {1}, Database Server Name = {2}, Database Server Status = {3}, Trap Host Time = {4}"
            ::= 1022                

          clsRecordIsNotInsertedToDBTheRecordIsLost TRAP-TYPE
            ENTERPRISE  clsDbServer
            VARIABLES   { trapSeverity, 
						  dbServerName,
						  dbServerStatus,
						  trapHostTime,
						  trapDBErrorCode }
            DESCRIPTION
                    "Record Is Not Inserted To DB, The Record Is Lost. Trap Severity = {1}, Database Server Name = {2}, Database Server Status = {3}, Trap Host Time = {4}, Database Error code = {5}"
            ::= 1023              
            
          clsRecordIsInsertedToDB TRAP-TYPE
            ENTERPRISE  clsRcm
            VARIABLES   { trapSeverity, 
						  rcmName,
						  rcmStatus,
						  trapHostTime
 }
            DESCRIPTION
                    "Record Is Inserted To DB. Trap Severity = {1}, RCM Name = {2}, RCM Status = {3}, Trap Host Time = {4}"
            ::= 1024                          
            
          clsCommunicationProblemWithLogger TRAP-TYPE
            ENTERPRISE  clsRcm
            VARIABLES   { trapSeverity, 
			              rcmName,
			              rcmStatus,
			              trapHostTime, 
						  trapLoggerId }
            DESCRIPTION
                    "Communication Problem With Logger. Trap Severity = {1}, RCM Name = {2}, RCM Status = {3}, Trap Host Time = {4}, Logger ID = {5}"
            ::= 1025                          

          clsCommunicationToLoggerIsOK TRAP-TYPE
            ENTERPRISE  clsRcm
            VARIABLES   { trapSeverity, 
						  rcmName,
						  rcmStatus,
						  trapHostTime
 }
            DESCRIPTION
                    "Communication To Logger Is OK. Trap Severity = {1}, RCM Name = {2}, RCM Status = {3}, Trap Host Time = {4}"
            ::= 1026                          

          clsProblematicClockDifferencesWithLogger TRAP-TYPE
            ENTERPRISE  clsRcm
            VARIABLES   { trapSeverity, 
						  rcmName,
						  rcmStatus,
						  trapHostTime,
						  trapLoggerId }
            DESCRIPTION
                    "Problematic Clock Differences With Logger. Trap Severity = {1}, RCM Name = {2}, RCM Status = {3}, Trap Host Time = {4}, Logger ID = {5}"
            ::= 1027                          

          clsNoClockDifferencesWithLogger TRAP-TYPE
            ENTERPRISE  clsRcm
            VARIABLES   { trapSeverity, 
						  rcmName,
						  rcmStatus,
						  trapHostTime
 }
            DESCRIPTION
                    "No Clock Differences With Logger. Trap Severity = {1}, RCM Name = {2}, RCM Status = {3}, Trap Host Time = {4}"
            ::= 1028                          

          clsNoAvailableResources TRAP-TYPE
            ENTERPRISE  clsRcm
            VARIABLES   { trapSeverity, 
						  rcmName,
						  rcmStatus,
						  trapHostTime, 
						  trapRecordedMedia }
            DESCRIPTION
                    "No Available Resources. Trap Severity = {1}, RCM Name = {2}, RCM Status = {3}, Trap Host Time = {4}, Recorded Media Type = {5}"
            ::= 1029                          

          clsResourcesAreAvailable TRAP-TYPE
            ENTERPRISE  clsRcm
            VARIABLES   { trapSeverity, 
						  rcmName,
						  rcmStatus,
						  trapHostTime
 }
            DESCRIPTION
                    "Resources Are Available. Trap Severity = {1}, RCM Name = {2}, RCM Status = {3}, Trap Host Time = {4}"
            ::= 1030                          

          clsLoggerIsNotInitializedProperly TRAP-TYPE
            ENTERPRISE  clsRcm
            VARIABLES   { trapSeverity, 
						  rcmName,
						  rcmStatus,
						  trapHostTime,
						  trapLoggerInitializationStatus }
            DESCRIPTION
                    "Logger Is Not Initialized Properly. Trap Severity = {1}, RCM Name = {2}, RCM Status = {3}, Trap Host Time = {4}, Logger Inititalization Status = {5}"
            ::= 1031                          

          clsLoggerIsInitializedProperly TRAP-TYPE
            ENTERPRISE  clsRcm
            VARIABLES   { trapSeverity, 
						  rcmName,
						  rcmStatus,
						  trapHostTime
 }
            DESCRIPTION
                    "Logger Is Initialized Properly. Trap Severity = {1}, RCM Name = {2}, RCM Status = {3}, Trap Host Time = {4}"
            ::= 1032                          

          clsRCMIsNotInitializedProperly TRAP-TYPE
            ENTERPRISE  clsRcm
            VARIABLES   { trapSeverity, 
						  rcmName,
						  rcmStatus,
						  trapHostTime
 }
            DESCRIPTION
                    "RCM Is Not Initialized Properly. Trap Severity = {1}, RCM Name = {2}, RCM Status = {3}, Trap Host Time = {4}"
            ::= 1033                          

          clsRCMIsInitializedProperly TRAP-TYPE
            ENTERPRISE  clsRcm
            VARIABLES   { trapSeverity, 
						  rcmName,
						  rcmStatus,
						  trapHostTime
 }
						  
            DESCRIPTION
                    "RCM Is Initialized Properly. Trap Severity = {1}, RCM Name = {2}, RCM Status = {3}, Trap Host Time = {4}"
            ::= 1034                          

          clsProblemWithNPLUS1Loggers TRAP-TYPE
            ENTERPRISE  clsRcm
            VARIABLES   { trapSeverity, 
						  rcmName,
						  rcmStatus,
						  trapHostTime,
						  trapLoggerId }
            DESCRIPTION
                    "Problem With NPLUS1 Loggers. Trap Severity = {1}, RCM Name = {2}, RCM Status = {3}, Trap Host Time = {4}, Logger ID = {5}"
            ::= 1035                          

          clsNPLUS1LoggersAreOK TRAP-TYPE
            ENTERPRISE  clsRcm
            VARIABLES   { trapSeverity, 
						  rcmName,
						  rcmStatus,
						  trapHostTime
 }
            DESCRIPTION
                    "NPLUS1 Loggers Are OK. Trap Severity = {1}, RCM Name = {2}, RCM Status = {3}, Trap Host Time = {4}"
            ::= 1036                          
          
          clsCallServerTableIsFull TRAP-TYPE
            ENTERPRISE  clsCallServer
            VARIABLES   { trapSeverity, 
						  callServerName,
						  callServerStatus,
						  trapHostTime,
						  trapClsTableType }
            DESCRIPTION
                    "Call Server Table Is Full. Trap Severity = {1}, Call Server Name = {2}, Call Server Status = {3}, Trap Host Time = {4}, CLS Table Type = {5}"
            ::= 1037                          

          clsCallServerTableIsOK TRAP-TYPE
            ENTERPRISE  clsCallServer
            VARIABLES   { trapSeverity, 
						  callServerName,
						  callServerStatus,
						  trapHostTime
 }
            DESCRIPTION
                    "Call Server Table Is OK. Trap Severity = {1}, Call Server Name = {2}, Call Server Status = {3}, Trap Host Time = {4}"
            ::= 1038                          

          clsALLCLSModulesInitFailed TRAP-TYPE
            ENTERPRISE  clsDispatcher
            VARIABLES   { trapSeverity, 
						  clsDispatcherName,
						  clsDispatcherStatus,
						  trapHostTime }
            DESCRIPTION
                    "ALL CLS Modules Init Failed. Trap Severity = {1}, CLS Dispatcher Name = {2}, CLS Dispatcher Status = {3}, Trap Host Time = {4}"
            ::= 1039                          

          clsALLCLSModulesInitOK TRAP-TYPE
            ENTERPRISE  clsDispatcher
            VARIABLES   { trapSeverity, 
						  clsDispatcherName,
						  clsDispatcherStatus,
						  trapHostTime  }
            DESCRIPTION
                    "ALL CLS Modules Init OK. Trap Severity = {1}, CLS Dispatcher Name = {2}, CLS Dispatcher Status = {3}, Trap Host Time = {4}"
            ::= 1040                          

          clsCLSModuleRestartFailed TRAP-TYPE
            ENTERPRISE  clsDispatcher
            VARIABLES   { trapSeverity, 
						  clsDispatcherName,
						  clsDispatcherStatus,
						  trapHostTime }
            DESCRIPTION
                    "CLS Module Restart Failed. Trap Severity = {1}, CLS Dispatcher Name = {2}, CLS Dispatcher Status = {3}, Trap Host Time = {4}"
            ::= 1041                          

          clsCLSModuleRestartOK TRAP-TYPE
            ENTERPRISE  clsDispatcher
            VARIABLES   { trapSeverity, 
						  clsDispatcherName,
						  clsDispatcherStatus,
						  trapHostTime }
            DESCRIPTION
                    "CLS Module Restart OK. Trap Severity = {1}, CLS Dispatcher Name = {2}, CLS Dispatcher Status = {3}, Trap Host Time = {4}"
            ::= 1042                          

          clsOSDiskFailure TRAP-TYPE
            ENTERPRISE  clsDispatcher
            VARIABLES   { trapSeverity, 
						  clsDispatcherName,
						  clsDispatcherStatus,
						  trapHostTime,
						  trapOsDiskFailure }
            DESCRIPTION
                    "OS Disk Failure. Trap Severity = {1}, CLS Dispatcher Name = {2}, CLS Dispatcher Status = {3}, Trap Host Time = {4}"
            ::= 1043                          

          clsOSDiskOK TRAP-TYPE
            ENTERPRISE  clsDispatcher
            VARIABLES   { trapSeverity, 
						  clsDispatcherName,
						  clsDispatcherStatus,
						  trapHostTime }
            DESCRIPTION
                    "OS Disk OK. Trap Severity = {1}, CLS Dispatcher Name = {2}, CLS Dispatcher Status = {3}, Trap Host Time = {4}"
            ::= 1044                          
            
            
          ----------------------------------------------------
		  -- Applications subtree definition

          applicationsServer OBJECT IDENTIFIER   ::= { niceMib-2 5 }

          applicationsTable OBJECT-TYPE
              SYNTAX  SEQUENCE OF ApplicationsEntry
              ACCESS  not-accessible
              STATUS  mandatory
              DESCRIPTION
                      "A list of all application servers availiable on this machine."
              ::= { applicationsServer 1 }

          applicationsEntry OBJECT-TYPE
              SYNTAX  ApplicationsEntry
              ACCESS  not-accessible
              STATUS  mandatory
              DESCRIPTION
                      "An application server entry."
              INDEX   { applicationsTableIndex }
              ::= { applicationsTable 1 }

          ApplicationsEntry ::=
              SEQUENCE 
              {
					applicationName
						DisplayString,
					applicationStatus
						SeverityType,
					applicationsTableIndex
						INTEGER 
              }
 
           applicationName OBJECT-TYPE
              SYNTAX  DisplayString
              ACCESS  read-only
              STATUS  mandatory
              DESCRIPTION 
                      "The application server name."
              ::= { applicationsEntry 1 }

           applicationStatus OBJECT-TYPE
              SYNTAX  SeverityType
              ACCESS  read-only
              STATUS  mandatory
              DESCRIPTION 
                      "The application server status."
              ::= { applicationsEntry 2 }

           applicationsTableIndex OBJECT-TYPE
              SYNTAX  INTEGER
              ACCESS  read-only
              STATUS  mandatory
              DESCRIPTION 
                      "The table index."
              ::= { applicationsEntry 3 }

          applicationsPendingErrorsTable OBJECT-TYPE
              SYNTAX  SEQUENCE OF ApplicationsPendingErrorsEntry
              ACCESS  not-accessible
              STATUS  mandatory
              DESCRIPTION
                      "A list of all pending errors for application servers."
              ::= { applicationsServer 2 }

          applicationsPendingErrorsEntry OBJECT-TYPE
              SYNTAX  ApplicationsPendingErrorsEntry
              ACCESS  not-accessible
              STATUS  mandatory
              DESCRIPTION
                      "An application server pending error entry."
              INDEX   { applicationsErrorsTableApplicationIndex, applicationsErrorsTableErrorIndex }
              ::= { applicationsPendingErrorsTable 1 }

          ApplicationsPendingErrorsEntry ::=
              SEQUENCE 
              {
					applicationErrorType
						ApplicationErrorType,
					applicationErrorReflectedStatus
						SeverityType,
					applicationsErrorsTableApplicationIndex
						INTEGER,
					applicationsErrorsTableErrorIndex
						INTEGER
              }
 
           applicationErrorType OBJECT-TYPE
              SYNTAX  ApplicationErrorType
              ACCESS  read-only
              STATUS  mandatory
              DESCRIPTION 
                      "The error type."
              ::= { applicationsPendingErrorsEntry 1 }

           applicationErrorReflectedStatus OBJECT-TYPE
              SYNTAX  SeverityType
              ACCESS  read-only
              STATUS  mandatory
              DESCRIPTION 
                      "The error's severity type."
              ::= { applicationsPendingErrorsEntry 2 }

           applicationsErrorsTableApplicationIndex OBJECT-TYPE
              SYNTAX  INTEGER
              ACCESS  read-only
              STATUS  mandatory
              DESCRIPTION 
                      "The first table index."
              ::= { applicationsPendingErrorsEntry 3 }

           applicationsErrorsTableErrorIndex OBJECT-TYPE
              SYNTAX  INTEGER
              ACCESS  read-only
              STATUS  mandatory
              DESCRIPTION 
                      "The second table index."
              ::= { applicationsPendingErrorsEntry 4 }
              
           applicationsNumberLoggedInUsers OBJECT-TYPE
              SYNTAX  INTEGER
              ACCESS  read-only
              STATUS  mandatory
              DESCRIPTION 
                      "The number of users currently logged in to the application."
              ::= { applicationsServer 3 }
   
          applicationsSnmpAgentConfig OBJECT IDENTIFIER  ::= { applicationsServer 4 }
          
          applicationsAgentIsRepeatingTraps OBJECT-TYPE
              SYNTAX  YesNo
              ACCESS  read-write
              STATUS  mandatory
              DESCRIPTION
                      "Defining whether the agent will repeat sending traps for each 
                      pending error of it's modules." 
              ::= { applicationsSnmpAgentConfig 1 }

          applicationsAgentTrapsRepeatInterval OBJECT-TYPE
              SYNTAX  INTEGER
              ACCESS  read-write
              STATUS  mandatory
              DESCRIPTION
                      "Defining the interval between repeated traps in minutes. -1 means no repeating traps" 
              ::= { applicationsSnmpAgentConfig 2 }

          applicationsAgentVersion OBJECT-TYPE
              SYNTAX  DisplayString
              ACCESS  read-only
              STATUS  mandatory
              DESCRIPTION
                      "the agent version number as a sequence of 4 numbers (in the following format 'a.b.c.d')." 
              ::= { applicationsSnmpAgentConfig 3 }
           
		  ctiEventsDbServer OBJECT IDENTIFIER  ::= { niceMib-2 8 }
          
          ctiDBServerName OBJECT-TYPE
              SYNTAX  DisplayString
              ACCESS  read-only
              STATUS  mandatory
              DESCRIPTION
                      "The Module name." 
              ::= { ctiEventsDbServer 1 }
 
          ctiDBServerStatus OBJECT-TYPE
              SYNTAX  SeverityType
              ACCESS  read-only
              STATUS  mandatory
              DESCRIPTION
                      "The CTI Events Database Server current status"
              ::= { ctiEventsDbServer 2 }

          ctiDBServerPendingErrorsTable OBJECT-TYPE
              SYNTAX  SEQUENCE OF CtiDBServerPendingErrorsEntry
              ACCESS  not-accessible
              STATUS  mandatory
              DESCRIPTION
                      "A list of pending errors for the CTI Events Database Server."
              ::= { ctiEventsDbServer 3 }

          ctiDBServerPendingErrorsEntry OBJECT-TYPE
              SYNTAX  CtiDBServerPendingErrorsEntry
              ACCESS  not-accessible
              STATUS  mandatory
              DESCRIPTION
                      "A pending error for the CTI Events Database Server."
              INDEX   { ctiDBServerErrorIndex }
              ::= { ctiDBServerPendingErrorsTable 1 }

          CtiDBServerPendingErrorsEntry ::=
              SEQUENCE 
              {
					ctiDBServerErrorType
						ClsErrorType,
					ctiDBServerErrorReflectedStatus
						SeverityType,
					ctiDBServerDBErrorCode
						INTEGER,						
					ctiDBServerErrorIndex
						INTEGER 
              }
 
           ctiDBServerErrorType OBJECT-TYPE
              SYNTAX  CTIEventsDBServerErrorType
              ACCESS  read-only
              STATUS  mandatory
              DESCRIPTION 
                      "The specific error type pending for the Module."
              ::= { ctiDBServerPendingErrorsEntry 1 }

           ctiDBServerErrorReflectedStatus OBJECT-TYPE
              SYNTAX  SeverityType
              ACCESS  read-only
              STATUS  mandatory
              DESCRIPTION 
                      "The specific error status reflected on the Module
                      as a result of the pending error."
              ::= { ctiDBServerPendingErrorsEntry 2 }

           ctiDBServerDBErrorCode OBJECT-TYPE
              SYNTAX  INTEGER
              ACCESS  read-only
              STATUS  optional
              DESCRIPTION 
                      "The SQL error code ID related to the pending error (if any)"
              ::= { ctiDBServerPendingErrorsEntry 3 }

           ctiDBServerErrorIndex OBJECT-TYPE
              SYNTAX  INTEGER
              ACCESS  read-only
              STATUS  mandatory
              DESCRIPTION 
                      "The error index in the table."
              ::= { ctiDBServerPendingErrorsEntry 4 }
                                                        
          ctiDBServerSnmpAgentConfig OBJECT IDENTIFIER  ::= { ctiEventsDbServer 4 }
          
          ctiDBServerAgentIsRepeatingTraps OBJECT-TYPE
              SYNTAX  YesNo
              ACCESS  read-write
              STATUS  mandatory
              DESCRIPTION
                      "Defining whether the agent will repeat sending traps for each 
                      pending error of it's modules." 
              ::= { ctiDBServerSnmpAgentConfig 1 }

          ctiDBServerAgentTrapsRepeatInterval OBJECT-TYPE
              SYNTAX  INTEGER
              ACCESS  read-write
              STATUS  mandatory
              DESCRIPTION
                      "Defining the interval between repeated traps in minutes." 
              ::= { ctiDBServerSnmpAgentConfig 2 }

          ctiDBServerAgentVersion OBJECT-TYPE
              SYNTAX  DisplayString
              ACCESS  read-only
              STATUS  mandatory
              DESCRIPTION
                      "the agent version number as a sequence of 4 numbers (in the following format 'a.b.c.d')." 
              ::= { ctiDBServerSnmpAgentConfig 3 }          
          ----------------------------------------------------
		  -- Applications servers traps (starting at specific trap 5000)

          appsServerIsDown TRAP-TYPE
            ENTERPRISE  applicationsTable
            VARIABLES   { trapSeverity,
            			  applicationName,
						  applicationStatus,
            			  trapHostTime }
            DESCRIPTION
                    "Application server is down. Trap Severity = {1}, Application Name = {2}, Application Status = {3}, Trap Host Time = {4}"
            ::= 5001
           
          appsServerIsUp TRAP-TYPE
            ENTERPRISE  applicationsTable
            VARIABLES   { trapSeverity,
            			  applicationName,
						  applicationStatus,
            			  trapHostTime }
            DESCRIPTION
                    "Application server is up. Trap Severity = {1}, Application Name = {2}, Application Status = {3}, Trap Host Time = {4}"
            ::= 5002         

          appsSystemAdminHostConnectionIsDown TRAP-TYPE
            ENTERPRISE  applicationsTable
            VARIABLES   { trapSeverity,
            			  applicationName,
						  applicationStatus,
            			  trapHostTime }
            DESCRIPTION
                    "System Admin Host Connection Is Down. Trap Severity = {1}, Application Name = {2}, Application Status = {3}, Trap Host Time = {4}"
            ::= 5003         

          appsSystemAdminHostConnectionIsUp TRAP-TYPE
            ENTERPRISE  applicationsTable
            VARIABLES   { trapSeverity,
            			  applicationName,
						  applicationStatus,
            			  trapHostTime }
            DESCRIPTION
                    "System Admin Host Connection Is Up. Trap Severity = {1}, Application Name = {2}, Application Status = {3}, Trap Host Time = {4}"
            ::= 5004

          appsAdminDataBaseConnectionIsDown TRAP-TYPE
            ENTERPRISE  applicationsTable
            VARIABLES   { trapSeverity,
            			  applicationName,
						  applicationStatus,
            			  trapHostTime }
            DESCRIPTION
                    "Data Base Connection Is Down. Trap Severity = {1}, Application Name = {2}, Application Status = {3}, Trap Host Time = {4}"
            ::= 5005         

          appsAdminDataBaseConnectionIsUp TRAP-TYPE
            ENTERPRISE  applicationsTable
            VARIABLES   { trapSeverity,
            			  applicationName,
						  applicationStatus,
            			  trapHostTime }
            DESCRIPTION
                    "Data Base Connection Is Up. Trap Severity = {1}, Application Name = {2}, Application Status = {3}, Trap Host Time = {4}"
            ::= 5006         

          appsLoggerIsNotAttachToACLS TRAP-TYPE
            ENTERPRISE  applicationsTable
            VARIABLES   { trapSeverity,
            			  applicationName,
						  applicationStatus,
            			  trapHostTime, 
						  trapLoggerId }
            DESCRIPTION
                    "Logger Is Not Attach To A CLS. Trap Severity = {1}, Application Name = {2}, Application Status = {3}, Trap Host Time = {4}, Logger ID = {5}"
            ::= 5007   
  
          appsCLSConnectionIsDown TRAP-TYPE
            ENTERPRISE  applicationsTable
            VARIABLES   { trapSeverity,
						  applicationName,
						  applicationStatus,
						  trapHostTime, 
						  trapCLSId }
            DESCRIPTION
                    "CLS Connection Is Down. Trap Severity = {1}, Application Name = {2}, Application Status = {3}, Trap Host Time = {4}, CLS ID = {5}"
            ::= 5008   

          appsCLSConnectionIsUp TRAP-TYPE
            ENTERPRISE  applicationsTable
            VARIABLES   { trapSeverity, 
						  applicationName,
						  applicationStatus,
						  trapHostTime, 
						  trapCLSId }
            DESCRIPTION
                    "CLS Connection Is Up. Trap Severity = {1}, Application Name = {2}, Application Status = {3}, Trap Host Time = {4}, CLS ID = {5}"
            ::= 5009   

          appsLoggerConnectionIsDown TRAP-TYPE
            ENTERPRISE  applicationsTable
            VARIABLES   { trapSeverity, 
						  applicationName,
						  applicationStatus,
						  trapHostTime, 
						  trapLoggerId }
            DESCRIPTION
                    "Logger Connection Is Down. Trap Severity = {1}, Application Name = {2}, Application Status = {3}, Trap Host Time = {4}, Logger ID = {5}"
            ::= 5010   

          appsLoggerConnectionIsUp TRAP-TYPE
            ENTERPRISE  applicationsTable
            VARIABLES   { trapSeverity, 
						  applicationName,
						  applicationStatus,
						  trapHostTime, 
						  trapLoggerId }
            DESCRIPTION
                    "Logger Connection Is Up. Trap Severity = {1}, Application Name = {2}, Application Status = {3}, Trap Host Time = {4}, Logger ID = {5}"
            ::= 5011   

          appsSCConnectionIsDown TRAP-TYPE
            ENTERPRISE  applicationsTable
            VARIABLES   { trapSeverity, 
						  applicationName,
						  applicationStatus,
						  trapHostTime, 
						  trapSCId }
            DESCRIPTION
                    "SC Connection Is Down. Trap Severity = {1}, Application Name = {2}, Application Status = {3}, Trap Host Time = {4}, Storage Center ID = {5}"
            ::= 5012   

          appsSCConnectionIsUp TRAP-TYPE
            ENTERPRISE  applicationsTable
            VARIABLES   { trapSeverity, 
						  applicationName,
						  applicationStatus,
						  trapHostTime, 
						  trapSCId }
            DESCRIPTION
                    "SC Connection Is Up. Trap Severity = {1}, Application Name = {2}, Application Status = {3}, Trap Host Time = {4}, Storage Center ID = {5}"
            ::= 5013   

          appsCTIDBConnectionIsDown TRAP-TYPE
            ENTERPRISE  applicationsTable
            VARIABLES   { trapSeverity, 
						  applicationName,
						  applicationStatus,
						  trapHostTime, 
						  trapDBId }
            DESCRIPTION
                    "CTI DB Connection Is Down. Trap Severity = {1}, Application Name = {2}, Application Status = {3}, Trap Host Time = {4}, Database ID = {5}"
            ::= 5014   

          appsCTIDBConnectionIsUp TRAP-TYPE
            ENTERPRISE  applicationsTable
            VARIABLES   { trapSeverity, 
						  applicationName,
						  applicationStatus,
						  trapHostTime, 
						  trapDBId }
            DESCRIPTION
                    "CTI DB Connection Is Up. Trap Severity = {1}, Application Name = {2}, Application Status = {3}, Trap Host Time = {4}, Database ID = {5}"
            ::= 5015   

          appsCADBConnectionIsDown TRAP-TYPE
            ENTERPRISE  applicationsTable
            VARIABLES   { trapSeverity, 
					      applicationName,
						  applicationStatus,
						  trapHostTime, 
						  trapDBId }
            DESCRIPTION
                    "CA DB Connection Is Down. Trap Severity = {1}, Application Name = {2}, Application Status = {3}, Trap Host Time = {4}, Database ID = {5}"
            ::= 5016   

          appsCADBConnectionIsUp TRAP-TYPE
            ENTERPRISE  applicationsTable
            VARIABLES   { trapSeverity, 
						  applicationName,
						  applicationStatus,
						  trapHostTime, 
						  trapDBId }
            DESCRIPTION
                    "CA DB Connection Is Up. Trap Severity = {1}, Application Name = {2}, Application Status = {3}, Trap Host Time = {4}, Database ID = {5}"
            ::= 5017   

          appsNIFDBConnectionIsDown TRAP-TYPE
            ENTERPRISE  applicationsTable
            VARIABLES   { trapSeverity, 
						  applicationName,
						  applicationStatus,
						  trapHostTime, 
						  trapDBId }
            DESCRIPTION
                    "NIF DB Connection Is Down. Trap Severity = {1}, Application Name = {2}, Application Status = {3}, Trap Host Time = {4}, Database ID = {5}"
            ::= 5018   

          appsNIFDBConnectionIsUp TRAP-TYPE
            ENTERPRISE  applicationsTable
            VARIABLES   { trapSeverity, 
						  applicationName,
						  applicationStatus,
						  trapHostTime, 
						  trapDBId }
            DESCRIPTION
                    "NIF DB Connection Is Up. Trap Severity = {1}, Application Name = {2}, Application Status = {3}, Trap Host Time = {4}, Database ID = {5}"
            ::= 5019   
   
          appsInteractionDBConnectionIsDown TRAP-TYPE
            ENTERPRISE  applicationsTable
            VARIABLES   { trapSeverity, 
						  applicationName,
						  applicationStatus,
						  trapHostTime }
            DESCRIPTION
                    "Interaction DB Connection Is Down. Trap Severity = {1}, Application Name = {2}, Application Status = {3}, Trap Host Time = {4}"
            ::= 5020   

         appsInteractionDBConnectionIsUp TRAP-TYPE
            ENTERPRISE  applicationsTable
            VARIABLES   { trapSeverity, 
						  applicationName,
						  applicationStatus,
						  trapHostTime }
            DESCRIPTION
                    "Interaction DB Connection Is Up. Trap Severity = {1}, Application Name = {2}, Application Status = {3}, Trap Host Time = {4}"
            ::= 5021   
                           
         appsUserAdminHostConnectionIsDown TRAP-TYPE
            ENTERPRISE  applicationsTable
            VARIABLES   { trapSeverity, 
						  applicationName,
						  applicationStatus,
						  trapHostTime }
            DESCRIPTION
                    "User admin Connection Is Down. Trap Severity = {1}, Application Name = {2}, Application Status = {3}, Trap Host Time = {4}"
            ::= 5022   

         appsUserAdminHostConnectionIsUp TRAP-TYPE
            ENTERPRISE  applicationsTable
            VARIABLES   { trapSeverity, 
						  applicationName,
						  applicationStatus,
						  trapHostTime }
            DESCRIPTION
                    "User Admin Connection Is Up. Trap Severity = {1}, Application Name = {2}, Application Status = {3}, Trap Host Time = {4}"
            ::= 5023     
            
         appsRuleEngineEventProviderFailed TRAP-TYPE
            ENTERPRISE  applicationsTable
            VARIABLES   { trapSeverity, 
						  applicationName,
						  applicationStatus,
						  trapHostTime,
						  trapEventProviderId }
            DESCRIPTION
                    "Rule Engine Event Provider Failed. Trap Severity = {1}, Application Name = {2}, Application Status = {3}, Trap Host Time = {4}, Event Provider ID = {5}"
            ::= 5024   

         appsRuleEngineEventProviderSucceeded TRAP-TYPE
            ENTERPRISE  applicationsTable
            VARIABLES   { trapSeverity, 
						  applicationName,
						  applicationStatus,
						  trapHostTime,
						  trapEventProviderId }
            DESCRIPTION
                    "Rule Engine Event Provider Succeeded. Trap Severity = {1}, Application Name = {2}, Application Status = {3}, Trap Host Time = {4}, Event Provider ID = {5}"
            ::= 5025      

         appsRuleEngineEventProviderIdle TRAP-TYPE
            ENTERPRISE  applicationsTable
            VARIABLES   { trapSeverity, 
						  applicationName,
						  applicationStatus,
						  trapHostTime,
						  trapEventProviderId }
            DESCRIPTION
                    "Rule Engine Event Provider Idle. Trap Severity = {1}, Application Name = {2}, Application Status = {3}, Trap Host Time = {4}, Event Provider ID = {5}"
            ::= 5026   

         appsRuleEngineEventProviderActive TRAP-TYPE
            ENTERPRISE  applicationsTable
            VARIABLES   { trapSeverity, 
						  applicationName,
						  applicationStatus,
						  trapHostTime,
						  trapEventProviderId }
            DESCRIPTION
                    "Rule Engine Event Provider Active. Trap Severity = {1}, Application Name = {2}, Application Status = {3}, Trap Host Time = {4}, Event Provider ID = {5}"
            ::= 5027   

         appsRuleEngineRuleGeneratorFailed TRAP-TYPE
            ENTERPRISE  applicationsTable
            VARIABLES   { trapSeverity, 
						  applicationName,
						  applicationStatus,
						  trapHostTime,
						  trapRuleGeneratorId }
            DESCRIPTION
                    "Rule Engine Rule Generator Failed. Trap Severity = {1}, Application Name = {2}, Application Status = {3}, Trap Host Time = {4}, Rule Generator ID = {5}"
            ::= 5028   

         appsRuleEngineRuleGeneratorSucceeded TRAP-TYPE
            ENTERPRISE  applicationsTable
            VARIABLES   { trapSeverity, 
						  applicationName,
						  applicationStatus,
						  trapHostTime,
						  trapRuleGeneratorId }
            DESCRIPTION
                    "Rule Engine Rule Generator Succeeded. Trap Severity = {1}, Application Name = {2}, Application Status = {3}, Trap Host Time = {4}, Rule Generator ID = {5}"
            ::= 5029   

         appsRuleEngineRuleGeneratorIdle TRAP-TYPE
            ENTERPRISE  applicationsTable
            VARIABLES   { trapSeverity, 
						  applicationName,
						  applicationStatus,
						  trapHostTime,
						  trapRuleGeneratorId }
            DESCRIPTION
                    "Rule Engine Rule Generator Idle. Trap Severity = {1}, Application Name = {2}, Application Status = {3}, Trap Host Time = {4}, Rule Generator ID = {5}"
            ::= 5030   

         appsRuleEngineRuleGeneratorActive TRAP-TYPE
            ENTERPRISE  applicationsTable
            VARIABLES   { trapSeverity, 
						  applicationName,
						  applicationStatus,
						  trapHostTime,
						  trapRuleGeneratorId }
            DESCRIPTION
                    "Rule Engine Rule Generator Active. Trap Severity = {1}, Application Name = {2}, Application Status = {3}, Trap Host Time = {4}, Rule Generator ID = {5}"
            ::= 5031   

         appsRuleEngineActionExecuterFailed TRAP-TYPE
            ENTERPRISE  applicationsTable
            VARIABLES   { trapSeverity, 
						  applicationName,
						  applicationStatus,
						  trapHostTime,
						  trapActionExecuterId }
            DESCRIPTION
                    "Rule Engine Action Executer Failed. Trap Severity = {1}, Application Name = {2}, Application Status = {3}, Trap Host Time = {4}, Action Executer ID = {5}"
            ::= 5032   
                          
         appsRuleEngineActionExecuterSucceeded TRAP-TYPE
            ENTERPRISE  applicationsTable
            VARIABLES   { trapSeverity, 
						  applicationName,
						  applicationStatus,
						  trapHostTime,
						  trapActionExecuterId }
            DESCRIPTION
                    "Rule Engine Action Executer SucceededRule Engine Action Executer Failed. Trap Severity = {1}, Application Name = {2}, Application Status = {3}, Trap Host Time = {4}, Action Executer ID = {5}"
            ::= 5033
            
         appsRuleEngineActionExecuterIdle TRAP-TYPE
            ENTERPRISE  applicationsTable
            VARIABLES   { trapSeverity, 
						  applicationName,
						  applicationStatus,
						  trapHostTime,
						  trapActionExecuterId }
            DESCRIPTION
                    "Rule Engine Action Executer IdleRule Engine Action Executer Failed. Trap Severity = {1}, Application Name = {2}, Application Status = {3}, Trap Host Time = {4}, Action Executer ID = {5}"
            ::= 5034
               
         appsRuleEngineActionExecuterActive TRAP-TYPE
            ENTERPRISE  applicationsTable
            VARIABLES   { trapSeverity, 
						  applicationName,
						  applicationStatus,
						  trapHostTime,
						  trapActionExecuterId }
            DESCRIPTION
                    "Rule Engine Action Executer ActiveRule Engine Action Executer Failed. Trap Severity = {1}, Application Name = {2}, Application Status = {3}, Trap Host Time = {4}, Action Executer ID = {5}"
            ::= 5035   

         appsRuleMngrDataBaseConnectionIsDown TRAP-TYPE
            ENTERPRISE  applicationsTable
            VARIABLES   { trapSeverity, 
						  applicationName,
						  applicationStatus,
						  trapHostTime, 
						  trapDBId }
            DESCRIPTION
                    "Rule Mngr Data Base Connection Is DownRule Engine Action Executer Failed. Trap Severity = {1}, Application Name = {2}, Application Status = {3}, Trap Host Time = {4}, Database ID = {5}"
            ::= 5036   

         appsRuleMngrDataBaseConnectionIsUp TRAP-TYPE
            ENTERPRISE  applicationsTable
            VARIABLES   { trapSeverity, 
						  applicationName,
						  applicationStatus,
						  trapHostTime, 
						  trapDBId }
            DESCRIPTION
                    "Rule Mngr Data Base Connection Is UpRule Engine Action Executer Failed. Trap Severity = {1}, Application Name = {2}, Application Status = {3}, Trap Host Time = {4}, Database ID = {5}"
            ::= 5037   
                         
      ----------------------------------------------------
		  -- Drivers subtree definition

          drivers OBJECT IDENTIFIER ::= { niceMib-2 4 }

          driversTable OBJECT-TYPE
              SYNTAX  SEQUENCE OF DriversEntry
              ACCESS  not-accessible
              STATUS  mandatory
              DESCRIPTION
                      "A list of all NICE drivers availiable on this machine."
              ::= { drivers 1 }

          driversEntry OBJECT-TYPE
              SYNTAX  DriversEntry
              ACCESS  not-accessible
              STATUS  mandatory
              DESCRIPTION
                      "A NICE driver entry."
              INDEX   { driverId }
              ::= { driversTable 1 }

          DriversEntry ::=
              SEQUENCE 
              {
					driverName
						DisplayString,
					driverStatus
						SeverityType,
					driverId
						INTEGER,
					driverNumberOfDevicesMonitored
						INTEGER,
					driverNumberOfSegments
						INTEGER,
					driverNumberOfCompound
						INTEGER
              }

          driverName OBJECT-TYPE
              SYNTAX  DisplayString
              ACCESS  read-only
              STATUS  mandatory
              DESCRIPTION
                      "The NICE driver name."
              ::= { driversEntry 1 }

          driverStatus OBJECT-TYPE
              SYNTAX  SeverityType
              ACCESS  read-only
              STATUS  mandatory
              DESCRIPTION
                      "The NICE driver status."
              ::= { driversEntry 2 }
 
          driverId OBJECT-TYPE
              SYNTAX  INTEGER
              ACCESS  read-only
              STATUS  mandatory
              DESCRIPTION
                      "The NICE driver ID."
              ::= { driversEntry 3 }
 
          driverNumberOfDevicesMonitored OBJECT-TYPE
              SYNTAX  INTEGER
              ACCESS  read-only
              STATUS  mandatory
              DESCRIPTION
                      "The NICE driver's number of devices monitored."
              ::= { driversEntry 4 }

          driverNumberOfSegments OBJECT-TYPE
              SYNTAX  INTEGER
              ACCESS  read-only
              STATUS  mandatory
              DESCRIPTION
                      "The NICE driver's number of segments."
              ::= { driversEntry 5 }
 
          driverNumberOfCompound OBJECT-TYPE
              SYNTAX  INTEGER
              ACCESS  read-only
              STATUS  mandatory
              DESCRIPTION
                      "The NICE driver's number of current compund calls."
              ::= { driversEntry 6 }
         
          driverModulesTable OBJECT-TYPE
              SYNTAX  SEQUENCE OF DriverModulesEntry
              ACCESS  not-accessible
              STATUS  mandatory
              DESCRIPTION
                      "A list of all modules within the NICE drivers availiable on 
                      this machine."
              ::= { drivers 2 }

          driverModulesEntry OBJECT-TYPE
              SYNTAX  DriverModulesEntry
              ACCESS  not-accessible
              STATUS  mandatory
              DESCRIPTION
                      "A NICE driver module entry."
              INDEX   { driverIdInModulesTable, driverModuleId }
              ::= { driverModulesTable 1 }

          DriverModulesEntry ::=
              SEQUENCE 
              {
					driverModuleName
						DisplayString,
					driverModuleStatus
						SeverityType,
					driverIdInModulesTable
						INTEGER,
					driverModuleId
						INTEGER
              }

          driverModuleName OBJECT-TYPE
              SYNTAX  DisplayString
              ACCESS  read-only
              STATUS  mandatory
              DESCRIPTION
                      "The NICE driver module name."
              ::= { driverModulesEntry 1 }

          driverModuleStatus OBJECT-TYPE
              SYNTAX  SeverityType
              ACCESS  read-only
              STATUS  mandatory
              DESCRIPTION
                      "The NICE driver module status."
              ::= { driverModulesEntry 2 }
 
          driverIdInModulesTable OBJECT-TYPE
              SYNTAX  INTEGER
              ACCESS  read-only
              STATUS  mandatory
              DESCRIPTION
                      "The NICE driver ID."
              ::= { driverModulesEntry 3 }
 
          driverModuleId OBJECT-TYPE
              SYNTAX  INTEGER
              ACCESS  read-only
              STATUS  mandatory
              DESCRIPTION
                      "The NICE driver module ID."
              ::= { driverModulesEntry 4 }

          driversPendingErrorsTable OBJECT-TYPE
              SYNTAX  SEQUENCE OF DriversPendingErrorsEntry
              ACCESS  not-accessible
              STATUS  mandatory
              DESCRIPTION
                      "A list of all pending errors for drivers."
              ::= { drivers 3 }

          driversPendingErrorsEntry OBJECT-TYPE
              SYNTAX  DriversPendingErrorsEntry
              ACCESS  not-accessible
              STATUS  mandatory
              DESCRIPTION
                      "A driver's pending error entry."
              INDEX   { driverIdInDriversErrors, driverErrorIndex }
              ::= { driversPendingErrorsTable 1 }

          DriversPendingErrorsEntry ::=
              SEQUENCE 
              {
					driverErrorType
						DriverErrorType,
					driverErrorReflectedStatus
						SeverityType,
					driverIdInDriversErrors
						INTEGER,
					driverErrorIndex
						INTEGER
              }
 
           driverErrorType OBJECT-TYPE
              SYNTAX  DriverErrorType
              ACCESS  read-only
              STATUS  mandatory
              DESCRIPTION 
                      "The error type."
              ::= { driversPendingErrorsEntry 1 }

           driverErrorReflectedStatus OBJECT-TYPE
              SYNTAX  SeverityType
              ACCESS  read-only
              STATUS  mandatory
              DESCRIPTION 
                      "The error's severity type."
              ::= { driversPendingErrorsEntry 2 }

           driverIdInDriversErrors OBJECT-TYPE
              SYNTAX  INTEGER
              ACCESS  read-only
              STATUS  mandatory
              DESCRIPTION 
                      "The first table index."
              ::= { driversPendingErrorsEntry 3 }

           driverErrorIndex OBJECT-TYPE
              SYNTAX  INTEGER
              ACCESS  read-only
              STATUS  mandatory
              DESCRIPTION 
                      "The second table index."
              ::= { driversPendingErrorsEntry 4 }

          driversModulePendingErrorsTable OBJECT-TYPE
              SYNTAX  SEQUENCE OF DriversModulePendingErrorsEntry
              ACCESS  not-accessible
              STATUS  mandatory
              DESCRIPTION
                      "A list of all pending errors for a driver's module."
              ::= { drivers 4 }

          driversModulePendingErrorsEntry OBJECT-TYPE
              SYNTAX  DriversModulePendingErrorsEntry
              ACCESS  not-accessible
              STATUS  mandatory
              DESCRIPTION
                      "A driver's pending error entry."
              INDEX   { driverIdInDriversErrors, driverErrorIndex }
              ::= { driversModulePendingErrorsTable 1 }

          DriversModulePendingErrorsEntry ::=
              SEQUENCE 
              {
					driverModuleErrorType
						DriverErrorType,
					driverModuleErrorReflectedStatus
						SeverityType,
					driverIdInDriverModulesErrors
						INTEGER,
					moduleIdInModulesErrors
					    INTEGER,
					driverModuleErrorIndex
						INTEGER
              }
 
           driverModuleErrorType OBJECT-TYPE
              SYNTAX  DriverErrorType
              ACCESS  read-only
              STATUS  mandatory
              DESCRIPTION 
                      "The error type."
              ::= { driversModulePendingErrorsEntry 1 }

           driverModuleErrorReflectedStatus OBJECT-TYPE
              SYNTAX  SeverityType
              ACCESS  read-only
              STATUS  mandatory
              DESCRIPTION 
                      "The error's severity type."
              ::= { driversModulePendingErrorsEntry 2 }

           driverIdInDriverModulesErrors OBJECT-TYPE
              SYNTAX  INTEGER
              ACCESS  read-only
              STATUS  mandatory
              DESCRIPTION 
                      "The first table index."
              ::= { driversModulePendingErrorsEntry 3 }

           moduleIdInModulesErrors OBJECT-TYPE
              SYNTAX  INTEGER
              ACCESS  read-only
              STATUS  mandatory
              DESCRIPTION 
                      "The second table index."
              ::= { driversModulePendingErrorsEntry 4 }

           driverModuleErrorIndex OBJECT-TYPE
              SYNTAX  INTEGER
              ACCESS  read-only
              STATUS  mandatory
              DESCRIPTION 
                      "The third table index."
              ::= { driversModulePendingErrorsEntry 5 }
              
          driversSnmpAgentConfig OBJECT IDENTIFIER  ::= { drivers 5 }
          
          driversAgentIsRepeatingTraps OBJECT-TYPE
              SYNTAX  YesNo
              ACCESS  read-write
              STATUS  mandatory
              DESCRIPTION
                      "Defining whether the agent will repeat sending traps for each 
                      pending error of it's modules." 
              ::= { driversSnmpAgentConfig 1 }

          driversAgentTrapsRepeatInterval OBJECT-TYPE
              SYNTAX  INTEGER
              ACCESS  read-write
              STATUS  mandatory
              DESCRIPTION
                      "Defining the interval between repeated traps in minutes." 
              ::= { driversSnmpAgentConfig 2 }

          driversAgentVersion OBJECT-TYPE
              SYNTAX  DisplayString
              ACCESS  read-only
              STATUS  mandatory
              DESCRIPTION
                      "the agent version number as a sequence of 4 numbers (in the following format 'a.b.c.d')." 
              ::= { driversSnmpAgentConfig 3 }

          ----------------------------------------------------
		  -- Drivers traps (starting at specific trap 4000)

          driverIsUp TRAP-TYPE
            ENTERPRISE  drivers
            VARIABLES   { trapSeverity, 
						  driverName,
						  driverStatus,
            			  trapHostTime }
            DESCRIPTION
                    "Driver is up. Trap Severity = {1}, Driver Name = {2}, Driver Status = {3}, Trap Host Time = {4}"
            ::= 4001
            
          driverIsDown TRAP-TYPE
            ENTERPRISE  driversTable
            VARIABLES   { trapSeverity, 
						  driverName,
						  driverStatus,
            			  trapHostTime }
            DESCRIPTION
                    "Driver is down. Trap Severity = {1}, Driver Name = {2}, Driver Status = {3}, Trap Host Time = {4}"
            ::= 4002   
            
          driverConfigurationFileIsMissing  TRAP-TYPE
            ENTERPRISE  driversTable
            VARIABLES   { 	trapSeverity, 
				driverName,
				driverStatus,
				trapHostTime,
				trapFileName }
            DESCRIPTION
                    "Configuration file is missing. Trap Severity = {1}, Driver Name = {2}, Driver Status = {3}, Trap Host Time = {4}, File Name = {5}"
            ::= 4003
           
          driverSignificantConfigurationFileDataIsMissing TRAP-TYPE
            ENTERPRISE  driversTable
            VARIABLES   { trapSeverity, 
						  driverName,
						  driverStatus,
						  trapHostTime,
						  trapFileName }
            DESCRIPTION
                    "Significant configuration file data is missing. Trap Severity = {1}, Driver Name = {2}, Driver Status = {3}, Trap Host Time = {4}, File Name = {5}"
            ::= 4004  
                      
          driverConfigurationFileDataIsMissing TRAP-TYPE
            ENTERPRISE  driversTable
            VARIABLES   { trapSeverity, 
						  driverName,
						  driverStatus,
						  trapHostTime,
						  trapFileName }
            DESCRIPTION
                    "Configuration file data is missing. Trap Severity = {1}, Driver Name = {2}, Driver Status = {3}, Trap Host Time = {4}, File Name = {5}"
            ::= 4005  
            
          driverConnectionToCapiIsDown TRAP-TYPE
            ENTERPRISE  driverModulesTable
            VARIABLES   { trapSeverity, 
						  driverModuleName,
						  driverModuleStatus,
						  trapHostTime }
            DESCRIPTION
                    "Connection to CAPI is down. Trap Severity = {1}, Driver Module Name = {2}, Driver Module Status = {3}, Trap Host Time = {4}"
            ::= 4006   
          
          driverConnectionToCapiIsUp TRAP-TYPE
            ENTERPRISE  driverModulesTable
            VARIABLES   { trapSeverity, 
						  driverModuleName,
						  driverModuleStatus,
						  trapHostTime }
            DESCRIPTION
                    "Connection to CAPI is up. Trap Severity = {1}, Driver Module Name = {2}, Driver Module Status = {3}, Trap Host Time = {4}"
            ::= 4007  
          
          driverConnectionToSwitchIsDown TRAP-TYPE
            ENTERPRISE  driverModulesTable
            VARIABLES   { trapSeverity, 
						  driverModuleName,
						  driverModuleStatus,
						  trapHostTime }
            DESCRIPTION
                    "Connection to switch is down. Trap Severity = {1}, Driver Module Name = {2}, Driver Module Status = {3}, Trap Host Time = {4}"
            ::= 4008                              
          
          driverConnectionToSwitchIsUp TRAP-TYPE
            ENTERPRISE  driverModulesTable
            VARIABLES   { trapSeverity, 
						  driverModuleName,
						  driverModuleStatus,
						  trapHostTime }
            DESCRIPTION
                    "Connection to switch is up. Trap Severity = {1}, Driver Module Name = {2}, Driver Module Status = {3}, Trap Host Time = {4}"
            ::= 4009   
          
          driverInternalEngineError TRAP-TYPE
            ENTERPRISE  driverModulesTable
            VARIABLES   { trapSeverity, 
						  driverModuleName,
						  driverModuleStatus,
						  trapHostTime }
            DESCRIPTION
                    "Internal engine error. Trap Severity = {1}, Driver Module Name = {2}, Driver Module Status = {3}, Trap Host Time = {4}"
            ::= 4010  
          
          driverInternalEngineOK TRAP-TYPE
            ENTERPRISE  driverModulesTable
            VARIABLES   { trapSeverity, 
						  driverModuleName,
						  driverModuleStatus,
						  trapHostTime }
            DESCRIPTION
                    "Internal engine OK. Trap Severity = {1}, Driver Module Name = {2}, Driver Module Status = {3}, Trap Host Time = {4}"
            ::= 4011  
          
          driverCapiError TRAP-TYPE
            ENTERPRISE  driverModulesTable
            VARIABLES   { trapSeverity, 
						  driverModuleName,
						  driverModuleStatus,
						  trapHostTime }
            DESCRIPTION
                    "Capi error. Trap Severity = {1}, Driver Module Name = {2}, Driver Module Status = {3}, Trap Host Time = {4}"
            ::= 4012   
          
          driverCapiOK TRAP-TYPE
            ENTERPRISE  driverModulesTable
            VARIABLES   { trapSeverity, 
						  driverModuleName,
						  driverModuleStatus,
						  trapHostTime }
            DESCRIPTION
                    "Capi OK. Trap Severity = {1}, Driver Module Name = {2}, Driver Module Status = {3}, Trap Host Time = {4}"
            ::= 4013 
            
          driverCTIEngineError TRAP-TYPE
            ENTERPRISE  driverModulesTable
            VARIABLES   { trapSeverity, 
						  driverModuleName,
						  driverModuleStatus,
						  trapHostTime }
            DESCRIPTION
                    "CTI engine error. Trap Severity = {1}, Driver Module Name = {2}, Driver Module Status = {3}, Trap Host Time = {4}"
            ::= 4014 
          
          driverCTIEngineWarning TRAP-TYPE
            ENTERPRISE  driverModulesTable
            VARIABLES   { trapSeverity, 
						  driverModuleName,
						  driverModuleStatus,
						  trapHostTime }
            DESCRIPTION
                    "CTI engine warning. Trap Severity = {1}, Driver Module Name = {2}, Driver Module Status = {3}, Trap Host Time = {4}"
            ::= 4015
             
          driverCTIEngineOK TRAP-TYPE
            ENTERPRISE  driverModulesTable
            VARIABLES   { trapSeverity, 
						  driverModuleName,
						  driverModuleStatus,
						  trapHostTime }
            DESCRIPTION
                    "CTI engine OK. Trap Severity = {1}, Driver Module Name = {2}, Driver Module Status = {3}, Trap Host Time = {4}"
            ::= 4016
          
          driverMonitorEnd TRAP-TYPE
            ENTERPRISE  driverModulesTable
            VARIABLES   { trapSeverity, 
						  driverModuleName,
						  driverModuleStatus,
						  trapHostTime,
						  trapDeviceId }
            DESCRIPTION
                    "Monitor end. Trap Severity = {1}, Driver Module Name = {2}, Driver Module Status = {3}, Trap Host Time = {4}, Extension = {5}"
            ::= 4017
          
          driverRegistryError TRAP-TYPE
            ENTERPRISE  drivers
            VARIABLES   { trapSeverity, 
						  driverModuleName,
						  driverModuleStatus,
						  trapHostTime,
						  trapRegistryKey }
            DESCRIPTION
                    "Registry error. Trap Severity = {1}, Driver Module Name = {2}, Driver Module Status = {3}, Trap Host Time = {4}, Registry Key = {5}"
            ::= 4018 
            
         driverRegistryWarning TRAP-TYPE
            ENTERPRISE  drivers
            VARIABLES   { trapSeverity, 
						  driverModuleName,
						  driverModuleStatus,
						  trapHostTime,
						  trapRegistryKey }
            DESCRIPTION
                    "Registry warning. Trap Severity = {1}, Driver Module Name = {2}, Driver MOdule Status = {3}, Trap Host Time = {4}, Registry Key = {5}"
            ::= 4019               
           
		  -- End Drivers traps 
		  ----------------------------------------------------

              
            
          ----------------------------------------------------
		  -- Loggers subtree definition

          logger OBJECT IDENTIFIER   ::= { niceMib-2 3 }

          multiMediaLogger OBJECT IDENTIFIER   ::= { logger 1 }

          mmlName OBJECT-TYPE
              SYNTAX  DisplayString
              ACCESS  read-only
              STATUS  mandatory
              DESCRIPTION
                      "The Multi Media logger internal ID."
              ::= { multiMediaLogger 1 }

         mmlStatus OBJECT-TYPE
              SYNTAX  SeverityType
              ACCESS  read-only
              STATUS  mandatory
              DESCRIPTION 
                      "The Multi Media logger status."
              ::= { multiMediaLogger 2 }
              
         mmlStorageSystem OBJECT IDENTIFIER   ::= { multiMediaLogger 3 }

         mmlStorageSystemName OBJECT-TYPE
              SYNTAX  DisplayString
              ACCESS  read-only
              STATUS  mandatory
              DESCRIPTION
                      "The Multi Media logger's storage system name."
              ::= { mmlStorageSystem 1 }

         mmlStorageSystemStatus OBJECT-TYPE
              SYNTAX  SeverityType
              ACCESS  read-only
              STATUS  mandatory
              DESCRIPTION 
                      "The Multi Media logger storage system status."
              ::= { mmlStorageSystem 2 }

         mmlStorageSystemDiskUsage OBJECT-TYPE
              SYNTAX  INTEGER
              ACCESS  read-only
              STATUS  mandatory
              DESCRIPTION 
                      "The Multi Media total disk usage (percentage)."
              ::= { mmlStorageSystem 3 }

         mmlDataSystem OBJECT IDENTIFIER   ::= { multiMediaLogger 4 }

         mmlDataSystemName OBJECT-TYPE
              SYNTAX  DisplayString
              ACCESS  read-only
              STATUS  mandatory
              DESCRIPTION
                      "The Multi Media logger's data system name."
              ::= { mmlDataSystem 1 }

         mmlDataSystemStatus OBJECT-TYPE
              SYNTAX  SeverityType
              ACCESS  read-only
              STATUS  mandatory
              DESCRIPTION 
                      "The Multi Media logger data system status."
              ::= { mmlDataSystem 2 }

         mmlAutoDeletion OBJECT IDENTIFIER   ::= { multiMediaLogger 5 }

         mmlAutoDeletionName OBJECT-TYPE
              SYNTAX  DisplayString
              ACCESS  read-only
              STATUS  mandatory
              DESCRIPTION
                      "The Multi Media logger's auto deletion mechanism name."
              ::= { mmlAutoDeletion 1 }

         mmlAutoDeletionStatus OBJECT-TYPE
              SYNTAX  SeverityType
              ACCESS  read-only
              STATUS  mandatory
              DESCRIPTION 
                      "The Multi Media logger auto deletion mechanism status."
              ::= { mmlAutoDeletion 2 }

         mmlAgentConfig OBJECT IDENTIFIER   ::= { multiMediaLogger 6 }

         mmlAgentIsRepeatingTraps OBJECT-TYPE
              SYNTAX  YesNo
              ACCESS  read-write
              STATUS  mandatory
              DESCRIPTION
                      "Defining whether the agent will repeat sending traps for each 
                      pending error of it's modules." 
              ::= { mmlAgentConfig 1 }

         mmlAgentTrapsRepeatInterval OBJECT-TYPE
              SYNTAX  INTEGER
              ACCESS  read-write
              STATUS  mandatory
              DESCRIPTION
                      "Defining the interval between repeated traps in minutes." 
              ::= { mmlAgentConfig 2 }

         mmlAgentVersion OBJECT-TYPE
              SYNTAX  DisplayString
              ACCESS  read-only
              STATUS  mandatory
              DESCRIPTION
                      "the agent version number as a sequence of 4 numbers (in the following format 'a.b.c.d')." 
              ::= { mmlAgentConfig 3 }
              
          ----------------------------------------------------
	  -- MML traps (starting at specific trap 3000)
	
	-- MML Agent traps

          mmlSnmpAgentConnectedToLogger TRAP-TYPE
            ENTERPRISE  multiMediaLogger
            VARIABLES   { trapSeverity,mmlName,mmlStatus,trapHostTime  }
            DESCRIPTION
                    "MML SNMP Agent Connected to logger. Trap Severity = {1}, mml Name = {2}, mml Status = {3}, Trap Host Time = {4}"
            ::=  3001

          mmlConnectionToLoggerNotEstablished TRAP-TYPE
            ENTERPRISE  multiMediaLogger
            VARIABLES   { trapSeverity,mmlName,mmlStatus,trapHostTime}
            DESCRIPTION
                    "MML SNMP Agent tried to connect to logger but not established. Trap Severity = {1}, mml Name = {2}, mml Status = {3}, Trap Host Time = {4}"
            ::=  3002

	-- MML General logger traps
          mmlInvalidConfiguration TRAP-TYPE
            ENTERPRISE  multiMediaLogger
            VARIABLES   { trapSeverity,mmlName,mmlStatus,trapHostTime }
            DESCRIPTION
                    "Invalid configuration. Trap Severity = {1}, mml Name = {2}, mml Status = {3}, Trap Host Time = {4}"
            ::=  3100
            
          mmlPersistentMismatch TRAP-TYPE
            ENTERPRISE  multiMediaLogger
            VARIABLES   { trapSeverity,mmlName,mmlStatus,trapHostTime }
            DESCRIPTION
                    "Persistent mismatch. Trap Severity = {1}, mml Name = {2}, mml Status = {3}, Trap Host Time = {4}"
            ::=  3101
            
          mmlAbnormalPlaybackTermination TRAP-TYPE
            ENTERPRISE  multiMediaLogger
            VARIABLES   { trapSeverity, mmlName,mmlStatus ,trapHostTime }
            DESCRIPTION
                    "Abnormal playback termination. Trap Severity = {1}, mml Name = {2}, mml Status = {3}, Trap Host Time = {4}"
            ::=  3102
            
          mmlAbnormalRecordTermination TRAP-TYPE
            ENTERPRISE  multiMediaLogger
            VARIABLES   { trapSeverity, mmlName, mmlStatus, trapHostTime }
            DESCRIPTION
                    "Abnormal record termination. Trap Severity = {1}, mml Name = {2}, mml Status = {3}, Trap Host Time = {4}"
            ::=  3103
            
          mmlUnableToReplyDueToConnectionLoss  TRAP-TYPE
            ENTERPRISE  multiMediaLogger
            VARIABLES   { trapSeverity, mmlName, mmlStatus, trapHostTime }
            DESCRIPTION
                    "Unable to reply due to connection loss. Trap Severity = {1}, mml Name = {2}, mml Status = {3}, Trap Host Time = {4}"
            ::=  3104

          mmlFailToInitializeStorageDevice  TRAP-TYPE
            ENTERPRISE  multiMediaLogger
            VARIABLES   { trapSeverity, mmlName, mmlStatus, trapHostTime }
            DESCRIPTION
                    "The MML failed to initialize storage device. Trap Severity = {1}, mml Name = {2}, mml Status = {3}, Trap Host Time = {4}"
            ::=  3105
            
          mmlFailToInitializeDataSystem TRAP-TYPE
            ENTERPRISE  multiMediaLogger
            VARIABLES   { trapSeverity,  mmlName, mmlStatus, trapHostTime }
            DESCRIPTION
                    "The MML failed to initialize data system. Trap Severity = {1}, mml Name = {2}, mml Status = {3}, Trap Host Time = {4}"
            ::=  3106
            
          mmlFailToInitializeMemoryManager TRAP-TYPE
            ENTERPRISE  multiMediaLogger
            VARIABLES   { trapSeverity,  mmlName, mmlStatus, trapHostTime }
            DESCRIPTION
                    "The MML failed to initialize memory manager. Trap Severity = {1}, mml Name = {2}, mml Status = {3}, Trap Host Time = {4}"
            ::=  3107
            
          mmlUnexpectedDisconnect TRAP-TYPE
            ENTERPRISE  multiMediaLogger
            VARIABLES   { trapSeverity,  mmlName, mmlStatus, trapHostTime }
            DESCRIPTION
                    "The MML got Unexpected disconnect. Trap Severity = {1}, mml Name = {2}, mml Status = {3}, Trap Host Time = {4}"
            ::=  3108
            
          mmlConnectionCanNotBeEstablished TRAP-TYPE
            ENTERPRISE  multiMediaLogger
            VARIABLES   { trapSeverity,  mmlName, mmlStatus, trapHostTime }
            DESCRIPTION
                    "The MML failed to open connection. Trap Severity = {1}, mml Name = {2}, mml Status = {3}, Trap Host Time = {4}"
            ::=  3109
            
          mmlAllConnectionResourcesInUse TRAP-TYPE
            ENTERPRISE  multiMediaLogger
            VARIABLES   { trapSeverity,  mmlName, mmlStatus, trapHostTime }
            DESCRIPTION
                    "All MML connection resources in use. Trap Severity = {1}, mml Name = {2}, mml Status = {3}, Trap Host Time = {4}"
            ::=  3110
            
          mmlConnectionTimeoutExceeded TRAP-TYPE
            ENTERPRISE  multiMediaLogger
            VARIABLES   { trapSeverity,  mmlName, mmlStatus, trapHostTime }
            DESCRIPTION
                    "Connection timeout exceeded. Trap Severity = {1}, mml Name = {2}, mml Status = {3}, Trap Host Time = {4}"
            ::=  3111
            
          mmlMemoryManagerOverflow  TRAP-TYPE
            ENTERPRISE  multiMediaLogger
            VARIABLES   { trapSeverity,  mmlName, mmlStatus, trapHostTime }
            DESCRIPTION
                    "The MML Memory manager got overflow. Trap Severity = {1}, mml Name = {2}, mml Status = {3}, Trap Host Time = {4}"
            ::=  3112
            
          mmlAllocationFailure TRAP-TYPE
            ENTERPRISE  multiMediaLogger
            VARIABLES   { trapSeverity,  mmlName, mmlStatus, trapHostTime }
            DESCRIPTION
                    "The MML got allocation failure. Trap Severity = {1}, mml Name = {2}, mml Status = {3}, Trap Host Time = {4}"
            ::=  3113
            
          mmlResourceAllocationFailure  TRAP-TYPE
            ENTERPRISE  multiMediaLogger
            VARIABLES   { trapSeverity,  mmlName, mmlStatus, trapHostTime }
            DESCRIPTION
                    "The MML got resource allocation failure. Trap Severity = {1}, mml Name = {2}, mml Status = {3}, Trap Host Time = {4}"
            ::=  3114
            
          mmlOutputChannelAllocationFailure  TRAP-TYPE
            ENTERPRISE  multiMediaLogger
            VARIABLES   { trapSeverity,  mmlName, mmlStatus, trapHostTime }
            DESCRIPTION
                    "The MML got output channel allocation failure. Trap Severity = {1}, mml Name = {2}, mml Status = {3}, Trap Host Time = {4}"
            ::=  3115
            
          mmlInputChannelAllocationFailure  TRAP-TYPE
            ENTERPRISE  multiMediaLogger
            VARIABLES   { trapSeverity,  mmlName, mmlStatus, trapHostTime }
            DESCRIPTION
                    "The MML got input channel allocation failure. Trap Severity = {1}, mml Name = {2}, mml Status = {3}, Trap Host Time = {4}"
            ::=  3116
            
          mmlResourceAccessFailure TRAP-TYPE
            ENTERPRISE  multiMediaLogger
            VARIABLES   { trapSeverity,  mmlName, mmlStatus, trapHostTime }
            DESCRIPTION
                    "The MML got resource access failure. Trap Severity = {1}, mml Name = {2}, mml Status = {3}, Trap Host Time = {4}"
            ::=  3117
            
          mmlLoggerIsShuttingDown TRAP-TYPE
            ENTERPRISE  multiMediaLogger
            VARIABLES   { trapSeverity,  mmlName, mmlStatus, trapHostTime }
            DESCRIPTION
                    "The MML is shutting down. Trap Severity = {1}, mml Name = {2}, mml Status = {3}, Trap Host Time = {4}"
            ::=  3118
            
          mmlLoggerIsReady TRAP-TYPE
            ENTERPRISE  multiMediaLogger
            VARIABLES   { trapSeverity,  mmlName, mmlStatus, trapHostTime }
            DESCRIPTION
                    "The MML is ready. Trap Severity = {1}, mml Name = {2}, mml Status = {3}, Trap Host Time = {4}"
            ::=  3119
            
	-- MML Storage system traps
          mmlStorageSystemInvalidConfiguration TRAP-TYPE
            ENTERPRISE  mmlStorageSystem
            VARIABLES   { trapSeverity, mmlStorageSystemName, mmlStorageSystemStatus, trapHostTime }
            DESCRIPTION
                    "Storage system invalid configuration. Trap Severity = {1}, mml Storage System Name = {2}, mml Storage System Status = {3}, Trap Host Time = {4}"
            ::=  3200
            
          mmlStorageSystemPersistentMismatch TRAP-TYPE
            ENTERPRISE  mmlStorageSystem
            VARIABLES   { trapSeverity,  mmlStorageSystemName, mmlStorageSystemStatus, trapHostTime }
            DESCRIPTION
                    "Storage system persistent mismatch. Trap Severity = {1}, mml Storage System Name = {2}, mml Storage System Status = {3}, Trap Host Time = {4}"
            ::=  3201
            
          mmlConsistentDiskWriteFailure TRAP-TYPE
            ENTERPRISE  mmlStorageSystem
            VARIABLES   { trapSeverity,  mmlStorageSystemName, mmlStorageSystemStatus, trapHostTime }
            DESCRIPTION
                    "The MML is repeatedly failing to write to disk. Trap Severity = {1}, mml Storage System Name = {2}, mml Storage System Status = {3}, Trap Host Time = {4}"
            ::=  3202
            
          mmlConsistentDiskReadFailure TRAP-TYPE
            ENTERPRISE  mmlStorageSystem
            VARIABLES   { trapSeverity,  mmlStorageSystemName, mmlStorageSystemStatus, trapHostTime }
            DESCRIPTION
                    "The MML is repeatedly failing to read from disk. Trap Severity = {1}, mml Storage System Name = {2}, mml Storage System Status = {3}, Trap Host Time = {4}"
            ::=  3203
            
          mmlDiskUsage  TRAP-TYPE
            ENTERPRISE  mmlStorageSystem
            VARIABLES   { trapSeverity,  mmlStorageSystemName, mmlStorageSystemStatus, trapHostTime, trapDiskUsage }
            DESCRIPTION
                    "The MML Disk usage notification. Trap Severity = {1}, mml Storage System Name = {2}, mml Storage System Status = {3}, Trap Host Time = {4}, Trap Disk Usage = {5}"
            ::=  3204
            
          mmlDiskIsFull TRAP-TYPE
            ENTERPRISE  mmlStorageSystem
            VARIABLES   { trapSeverity,  mmlStorageSystemName, mmlStorageSystemStatus, trapHostTime }
            DESCRIPTION
                    "The MML Disk is full. Trap Severity = {1}, mml Storage System Name = {2}, mml Storage System Status = {3}, Trap Host Time = {4}"
            ::=  3205
            
          mmlDiskIOFailure TRAP-TYPE
            ENTERPRISE  mmlStorageSystem
            VARIABLES   { trapSeverity,  mmlStorageSystemName, mmlStorageSystemStatus, trapHostTime }
            DESCRIPTION
                    "The MML has Disk IO failure. Trap Severity = {1}, mml Storage System Name = {2}, mml Storage System Status = {3}, Trap Host Time = {4}"
            ::=  3206
            
	-- MML data system traps
          mmlDataSystemInvalidConfiguration TRAP-TYPE
            ENTERPRISE  mmlDataSystem
            VARIABLES   { trapSeverity, mmlDataSystemName, mmlDataSystemStatus, trapHostTime }
            DESCRIPTION
                    "Storage system invalid configuration. Trap Severity = {1}, mml Data System Name = {2}, mml Data System Status = {3}, Trap Host Time = {4}"
            ::=  3300
            
          mmlDataSystemPersistentMismatch TRAP-TYPE
            ENTERPRISE  mmlDataSystem
            VARIABLES   { trapSeverity,  mmlDataSystemName, mmlDataSystemStatus, trapHostTime }
            DESCRIPTION
                    "Storage system persistent mismatch. Trap Severity = {1}, mml Data System Name = {2}, mml Data System Status = {3}, Trap Host Time = {4}"
            ::=  3301
            
          mmlDataBaseConsistencyMismatch  TRAP-TYPE
            ENTERPRISE  mmlDataSystem
            VARIABLES   { trapSeverity,  mmlDataSystemName, mmlDataSystemStatus, trapHostTime }
            DESCRIPTION
                    "The MML database has Consistency mismatch. Trap Severity = {1}, mml Data System Name = {2}, mml Data System Status = {3}, Trap Host Time = {4}"
            ::=  3302
            
          mmlCriticalDataSystemError TRAP-TYPE
            ENTERPRISE  mmlDataSystem
            VARIABLES   { trapSeverity,  mmlDataSystemName, mmlDataSystemStatus, trapHostTime }
            DESCRIPTION
                    "General error at the MML data systen. Trap Severity = {1}, mml Data System Name = {2}, mml Data System Status = {3}, Trap Host Time = {4}"
            ::=  3303
            
          mmlTableAccessFailure TRAP-TYPE
            ENTERPRISE  mmlDataSystem
            VARIABLES   { trapSeverity,  mmlDataSystemName, mmlDataSystemStatus, trapHostTime }
            DESCRIPTION
                    "Table access failure in the MML data system. Trap Severity = {1}, mml Data System Name = {2}, mml Data System Status = {3}, Trap Host Time = {4}"
            ::=  3304

	-- MML Auto Deletion traps
          mmlAutoDeletionInvalidConfiguration TRAP-TYPE
            ENTERPRISE  mmlAutoDeletion
            VARIABLES   { trapSeverity, mmlAutoDeletionName, mmlAutoDeletionStatus, trapHostTime }
            DESCRIPTION
                    "Storage system invalid configuration. Trap Severity = {1}, mml Auto Deletion Name = {2}, mml Auto Deletion Status = {3}, Trap Host Time = {4}"
            ::=  3400
            
          mmlAutoDeletionPersistentMismatch TRAP-TYPE
            ENTERPRISE  mmlAutoDeletion
            VARIABLES   { trapSeverity,  mmlAutoDeletionName, mmlAutoDeletionStatus, trapHostTime }
            DESCRIPTION
                    "Storage system persistent mismatch. Trap Severity = {1}, mml Auto Deletion Name = {2}, mml Auto Deletion Status = {3}, Trap Host Time = {4}"
            ::=  3401
            
          mmlStartingAutoDeletionJob TRAP-TYPE
            ENTERPRISE  mmlAutoDeletion
            VARIABLES   { trapSeverity,  mmlAutoDeletionName, mmlAutoDeletionStatus, trapHostTime }
            DESCRIPTION
                    "Starting auto deletion job. Trap Severity = {1}, mml Auto Deletion Name = {2}, mml Auto Deletion Status = {3}, Trap Host Time = {4}"
            ::=  3402
            
          mmlFinishedNormal  TRAP-TYPE
            ENTERPRISE  mmlAutoDeletion
            VARIABLES   { trapSeverity,  mmlAutoDeletionName, mmlAutoDeletionStatus, trapHostTime }
            DESCRIPTION
                    "The MML Finished normal. Trap Severity = {1}, mml Auto Deletion Name = {2}, mml Auto Deletion Status = {3}, Trap Host Time = {4}"
            ::=  3403
            
          mmlDeletionCapacityNotReached TRAP-TYPE
            ENTERPRISE  mmlAutoDeletion
            VARIABLES   { trapSeverity,  mmlAutoDeletionName, mmlAutoDeletionStatus, trapHostTime }
            DESCRIPTION
                    "Deletion capacity not reached. Trap Severity = {1}, mml Auto Deletion Name = {2}, mml Auto Deletion Status = {3}, Trap Host Time = {4}"
            ::=  3404
              
------------------    Voice Logger Start >>>-------------------------------------
          voiceLogger OBJECT IDENTIFIER   ::= { logger 2 }     
          
          voiceLoggerName OBJECT-TYPE                               
              SYNTAX  DisplayString
              ACCESS  read-only
              STATUS  mandatory
              DESCRIPTION
                      "The Voice Logger Name\Id."
              ::= { voiceLogger 1 }      

          voiceLoggerStatus OBJECT-TYPE
              SYNTAX  SeverityType
              ACCESS  read-only
              STATUS  mandatory
              DESCRIPTION 
                      "The Voice Logger current status."
              ::= { voiceLogger 2 }        

          voiceLoggerLogging OBJECT IDENTIFIER   ::= { voiceLogger 3 } 
          
          loggingName OBJECT-TYPE                               
              SYNTAX  DisplayString
              ACCESS  read-only
              STATUS  mandatory
              DESCRIPTION
                      "The Module Name."
              ::= { voiceLoggerLogging 1 }

          loggingStatus OBJECT-TYPE
              SYNTAX  SeverityType
              ACCESS  read-only
              STATUS  mandatory
              DESCRIPTION 
                      "The Logging current status."
              ::= { voiceLoggerLogging 2 }   
              
           loggingInstanceTable OBJECT-TYPE
              SYNTAX  SEQUENCE OF LoggingInstanceEntry
              ACCESS  not-accessible
              STATUS  mandatory
              DESCRIPTION
                      "A list of all logging instances."
              ::= { voiceLoggerLogging 3 }

          loggingInstanceEntry OBJECT-TYPE
              SYNTAX  LoggingInstanceEntry
              ACCESS  not-accessible
              STATUS  mandatory
              DESCRIPTION
                      "A logging instance entry."
              INDEX   { loggingInstanceIndex }
              ::= { loggingInstanceTable 1 }

          LoggingInstanceEntry ::=
              SEQUENCE 
              {
					loggingInstanceName
						DisplayString,
					loggingInstanceStatus
						SeverityType, 
					loggingInstanceType
						LoggingInstanceType,
					loggingInstanceNumberInType
						INTEGER,				
					loggingInstanceIndex
						INTEGER
              }

          loggingInstanceName OBJECT-TYPE
              SYNTAX  DisplayString
              ACCESS  read-only
              STATUS  mandatory
              DESCRIPTION
                      "The logging instance name."
              ::= { loggingInstanceEntry 1 }

          loggingInstanceStatus OBJECT-TYPE
              SYNTAX  SeverityType
              ACCESS  read-only
              STATUS  mandatory
              DESCRIPTION
                      "The logging instance status."
              ::= { loggingInstanceEntry 2 }  
              
          loggingInstanceType OBJECT-TYPE
              SYNTAX  LoggingInstanceType
              ACCESS  read-only
              STATUS  mandatory
              DESCRIPTION
                      "The logging instance Type. For Example: Adif3"
              ::= { loggingInstanceEntry 3 } 
              
          loggingInstanceNumberInType OBJECT-TYPE
              SYNTAX  INTEGER
              ACCESS  read-only
              STATUS  mandatory
              DESCRIPTION
                      "The logging instance number of a certain Type."
              ::= { loggingInstanceEntry 4 }        
  
          loggingInstanceIndex OBJECT-TYPE
              SYNTAX  INTEGER
              ACCESS  read-only
              STATUS  mandatory
              DESCRIPTION
                      "The logging instance index."
              ::= { loggingInstanceEntry 5} 
              
          loggingPendingErrorsTable OBJECT-TYPE
              SYNTAX  SEQUENCE OF LoggingPendingErrorsEntry
              ACCESS  not-accessible
              STATUS  mandatory
              DESCRIPTION
                      "A list of pending errors for Logging instances."
              ::= { voiceLoggerLogging 4 }

          loggingPendingErrorsEntry OBJECT-TYPE
              SYNTAX  LoggingPendingErrorsEntry
              ACCESS  not-accessible
              STATUS  mandatory
              DESCRIPTION
                      "A pending error for Logging instances."
              INDEX   { loggingErrorInstanceIndex, loggingErrorIndex }
              ::= { loggingPendingErrorsTable 1 }

          LoggingPendingErrorsEntry ::=
              SEQUENCE 
              {
					loggingErrorType
						LoggingErrorType,
					loggingErrorReflectedStatus
						SeverityType,
					loggingErrorInstanceIndex
						INTEGER,
					loggingErrorIndex
						INTEGER, 
					loggingErrorCode
						INTEGER
              }  
 
           loggingErrorType OBJECT-TYPE
              SYNTAX  LoggingErrorType
              ACCESS  read-only
              STATUS  mandatory
              DESCRIPTION 
                      "The specific error type pending for Logging instances."
              ::= { loggingPendingErrorsEntry 1 }

           loggingErrorReflectedStatus OBJECT-TYPE
              SYNTAX  SeverityType
              ACCESS  read-only
              STATUS  mandatory
              DESCRIPTION 
                      "The specific error status reflected on the Logging instances
                      as a result of the pending error."
              ::= { loggingPendingErrorsEntry 2 }

           loggingErrorInstanceIndex OBJECT-TYPE
              SYNTAX  INTEGER
              ACCESS  read-only
              STATUS  mandatory
              DESCRIPTION 
                      "The logging instance index related to the pending error (if any)"
              ::= { loggingPendingErrorsEntry 3 }

           loggingErrorIndex OBJECT-TYPE
              SYNTAX  INTEGER
              ACCESS  read-only
              STATUS  mandatory
              DESCRIPTION 
                      "The error index in the table."
              ::= { loggingPendingErrorsEntry 4 }            
           
           loggingErrorCode OBJECT-TYPE
              SYNTAX  INTEGER
              ACCESS  read-only
              STATUS  mandatory
              DESCRIPTION 
                      "Error Code that match the code in the Traps Technical Description."
              ::= { loggingPendingErrorsEntry 5 }
           
          voiceLoggerCapture OBJECT IDENTIFIER   ::= { voiceLogger 4 }  
          
          captureName OBJECT-TYPE                               
              SYNTAX  DisplayString
              ACCESS  read-only
              STATUS  mandatory
              DESCRIPTION
                      "The Module Name."
              ::= { voiceLoggerCapture 1 }

          captureStatus OBJECT-TYPE
              SYNTAX  SeverityType
              ACCESS  read-only
              STATUS  mandatory
              DESCRIPTION 
                      "The Capture current status."
              ::= { voiceLoggerCapture 2 }    
              
          captureInstanceTable OBJECT-TYPE
              SYNTAX  SEQUENCE OF CaptureInstanceEntry
              ACCESS  not-accessible
              STATUS  mandatory
              DESCRIPTION
                      "A list of all capture boards."
              ::= { voiceLoggerCapture 3 }

          captureInstanceEntry OBJECT-TYPE
              SYNTAX  CaptureInstanceEntry
              ACCESS  not-accessible
              STATUS  mandatory
              DESCRIPTION
                      "A capture instance entry."
              INDEX   { captureInstanceIndex }
              ::= { captureInstanceTable 1 }

          CaptureInstanceEntry ::=
              SEQUENCE 
              {
					captureInstanceName
						DisplayString,
					captureInstanceStatus
						SeverityType, 
					captureInstanceType
						CaptureInstanceType,
					captureInstanceNumberInType
						INTEGER,	
					captureInstanceIndex
						INTEGER
              }

          captureInstanceName OBJECT-TYPE
              SYNTAX  DisplayString
              ACCESS  read-only
              STATUS  mandatory
              DESCRIPTION
                      "The capture instance name."
              ::= { captureInstanceEntry 1 }

          captureInstanceStatus OBJECT-TYPE
              SYNTAX  SeverityType
              ACCESS  read-only
              STATUS  mandatory
              DESCRIPTION
                      "The capture instance status."
              ::= { captureInstanceEntry 2 }
  
          captureInstanceType OBJECT-TYPE
              SYNTAX  CaptureInstanceType
              ACCESS  read-only
              STATUS  mandatory
              DESCRIPTION
                      "The capture instance Type. For Example: Adif3"
              ::= { captureInstanceEntry 3 } 
              
          captureInstanceNumberInType OBJECT-TYPE
              SYNTAX  INTEGER
              ACCESS  read-only
              STATUS  mandatory
              DESCRIPTION
                      "The capture instance number of a certain Type."
              ::= { captureInstanceEntry 4 }     
              
          captureInstanceIndex OBJECT-TYPE
              SYNTAX  INTEGER
              ACCESS  read-only
              STATUS  mandatory
              DESCRIPTION
                      "The internal capture instance index."
              ::= { captureInstanceEntry 5 }     
              
          capturePendingErrorsTable OBJECT-TYPE
              SYNTAX  SEQUENCE OF CapturePendingErrorsEntry
              ACCESS  not-accessible
              STATUS  mandatory
              DESCRIPTION
                      "A list of pending errors for Capture Instances."
              ::= { voiceLoggerCapture 4 }

          capturePendingErrorsEntry OBJECT-TYPE
              SYNTAX  CapturePendingErrorsEntry
              ACCESS  not-accessible
              STATUS  mandatory
              DESCRIPTION
                      "A pending error for a capture instance."
              INDEX   { captureErrorInstanceIndex, captureErrorIndex }
              ::= { capturePendingErrorsTable 1 }

          CapturePendingErrorsEntry ::=
              SEQUENCE 
              {
					captureErrorType
						CaptureErrorType,
					captureErrorReflectedStatus
						SeverityType,
					captureErrorInstanceIndex
						INTEGER,
					captureErrorIndex
						INTEGER, 
					captureErrorCode
						INTEGER
              }  
 
           captureErrorType OBJECT-TYPE
              SYNTAX  CaptureErrorType
              ACCESS  read-only
              STATUS  mandatory
              DESCRIPTION 
                      "The specific error type pending for a Capture Board."
              ::= { capturePendingErrorsEntry 1 }

           captureErrorReflectedStatus OBJECT-TYPE
              SYNTAX  SeverityType
              ACCESS  read-only
              STATUS  mandatory
              DESCRIPTION 
                      "The specific error status reflected on the Capture board
                      as a result of the pending error."
              ::= { capturePendingErrorsEntry 2 }

           captureErrorInstanceIndex OBJECT-TYPE
              SYNTAX  INTEGER
              ACCESS  read-only
              STATUS  mandatory
              DESCRIPTION 
                      "The capture instance index related to the pending error (if any) Eli - the index in the capture instance table"
              ::= { capturePendingErrorsEntry 3 }

           captureErrorIndex OBJECT-TYPE
              SYNTAX  INTEGER
              ACCESS  read-only
              STATUS  mandatory
              DESCRIPTION 
                      "The error index in the table."
              ::= { capturePendingErrorsEntry 4 }                                                                                   
          
           captureErrorCode OBJECT-TYPE
              SYNTAX  INTEGER
              ACCESS  read-only
              STATUS  mandatory
              DESCRIPTION 
                      "Error Code that match the code in the Traps Technical Description."
              ::= { capturePendingErrorsEntry 5 }
          
          voiceLoggerBackup OBJECT IDENTIFIER   ::= { voiceLogger 5 } 
                    
          backupName OBJECT-TYPE                               
              SYNTAX  DisplayString
              ACCESS  read-only
              STATUS  mandatory
              DESCRIPTION
                      "The Module Name."
              ::= { voiceLoggerBackup 1 }

          backupStatus OBJECT-TYPE
              SYNTAX  SeverityType
              ACCESS  read-only
              STATUS  mandatory
              DESCRIPTION 
                      "The Backup current status."
              ::= { voiceLoggerBackup 2 } 
              
          backupInstanceTable OBJECT-TYPE
              SYNTAX  SEQUENCE OF BackupInstanceEntry
              ACCESS  not-accessible
              STATUS  mandatory
              DESCRIPTION
                      "A list of all backup instances with in the Voice Logger."
              ::= { voiceLoggerBackup 3 }
           
          backupInstanceEntry OBJECT-TYPE
              SYNTAX  BackupInstanceEntry
              ACCESS  not-accessible
              STATUS  mandatory
              DESCRIPTION
                      "A backup instance entry."
              INDEX   { backupInstanceNumber }
              ::= { backupInstanceTable 1 }
           
          BackupInstanceEntry ::=
           	 SEQUENCE 
             {
          		backupInstanceName
						DisplayString,
				backupInstanceStatus
						SeverityType,
				backupInstanceNumber
						INTEGER,  
				backupInstanceRemoteNumber 
						INTEGER,
				backupInstanceType 
						BackupInstanceType 
             }  
             
          backupInstanceName OBJECT-TYPE
              SYNTAX  DisplayString
              ACCESS  read-only
              STATUS  mandatory
              DESCRIPTION
                      "The device name."
              ::= { backupInstanceEntry 1 }

          backupInstanceStatus OBJECT-TYPE
              SYNTAX  SeverityType
              ACCESS  read-only
              STATUS  mandatory
              DESCRIPTION
                      "The device status."
              ::= { backupInstanceEntry 2 }
  
          backupInstanceNumber OBJECT-TYPE
              SYNTAX  INTEGER
              ACCESS  read-only
              STATUS  mandatory
              DESCRIPTION
                      "The device number, which is also the index in the instance table."
              ::= { backupInstanceEntry 3 } 
              
          backupInstanceRemoteNumber OBJECT-TYPE
              SYNTAX  INTEGER
              ACCESS  read-only
              STATUS  mandatory
              DESCRIPTION
                      "The remote device index in RTS Server."
              ::= { backupInstanceEntry 4 }

          backupInstanceType OBJECT-TYPE
              SYNTAX  BackupInstanceType
              ACCESS  read-only
              STATUS  mandatory
              DESCRIPTION
                      "The device type."
              ::= { backupInstanceEntry 5 }
              
          backupPendingErrorsTable OBJECT-TYPE
              SYNTAX  SEQUENCE OF BackupPendingErrorsEntry
              ACCESS  not-accessible
              STATUS  mandatory
              DESCRIPTION
                      "A list of pending errors for Backup Instances."
              ::= { voiceLoggerBackup 4 }

          backupPendingErrorsEntry OBJECT-TYPE
              SYNTAX  BackupPendingErrorsEntry
              ACCESS  not-accessible
              STATUS  mandatory
              DESCRIPTION
                      "A pending error for a backup Instances."
              INDEX   { backupErrorInstanceIndex, backupErrorIndex }
              ::= { backupPendingErrorsTable 1 }

          BackupPendingErrorsEntry ::=
              SEQUENCE 
              {
					backupErrorType
						BackupErrorType,
					backupErrorReflectedStatus
						SeverityType, 
					backupErrorBSRVErrorCode
						BackupErrorBSRVErrorCode,
					backupErrorInstanceIndex
						INTEGER,
					backupErrorIndex
						INTEGER
              }  
 
           backupErrorType OBJECT-TYPE
              SYNTAX  BackupErrorType
              ACCESS  read-only
              STATUS  mandatory
              DESCRIPTION 
                      "The specific error type pending for a Backup device."
              ::= { backupPendingErrorsEntry 1 }

           backupErrorReflectedStatus OBJECT-TYPE
              SYNTAX  SeverityType
              ACCESS  read-only
              STATUS  mandatory
              DESCRIPTION 
                      "The specific error status reflected on the Backup device
                      as a result of the pending error."
              ::= { backupPendingErrorsEntry 2 }              
             
          backupErrorBSRVErrorCode OBJECT-TYPE
              SYNTAX  BackupErrorBSRVErrorCode
              ACCESS  read-only
              STATUS  mandatory
              DESCRIPTION
                      "The device bsrv error."
              ::= { backupPendingErrorsEntry 3 } 
                       

           backupErrorInstanceIndex OBJECT-TYPE
              SYNTAX  INTEGER
              ACCESS  read-only
              STATUS  mandatory
              DESCRIPTION 
                      "The backup instance index related to the pending error (if any)"
              ::= { backupPendingErrorsEntry 4 }

           backupErrorIndex OBJECT-TYPE
              SYNTAX  INTEGER
              ACCESS  read-only
              STATUS  mandatory
              DESCRIPTION 
                      "The backup error index in the table."
              ::= { backupPendingErrorsEntry 5 }     
           
          voiceLoggerSnmpAgentConfig OBJECT IDENTIFIER   ::= { voiceLogger 6 }   
            
          voiceLoggerAgentIsRepeatingTraps OBJECT-TYPE
              SYNTAX  YesNo
              ACCESS  read-write
              STATUS  mandatory
              DESCRIPTION
                      "Defining whether the agent will repeat sending traps for each 
                      pending error of it's modules." 
              ::= { voiceLoggerSnmpAgentConfig 1 }
          
          voiceLoggerTrapsRepeatInterval OBJECT-TYPE
              SYNTAX  INTEGER
              ACCESS  read-write
              STATUS  mandatory
              DESCRIPTION
                      "Defining the interval between repeated traps in minutes." 
              ::= { voiceLoggerSnmpAgentConfig 2 }

          voiceLoggerAgentVersion OBJECT-TYPE
              SYNTAX  DisplayString
              ACCESS  read-only
              STATUS  mandatory
              DESCRIPTION
                      "the agent version number as a sequence of 4 numbers (in the following format 'a.b.c.d')." 
              ::= { voiceLoggerSnmpAgentConfig 3 }
		
    vlLoggerNotResponding TRAP-TYPE
            ENTERPRISE  voiceLogger
            VARIABLES   { trapSeverity, trapVLModuleName, trapVLModuleStatus, trapHostTime}
            DESCRIPTION "Communication Failure. Trap Severity = {1}, VL Module Name = {2}, VL Module Status = {3}, Trap Host Time = {4}"
            ::= 6002
          vlApiQueryError TRAP-TYPE
            ENTERPRISE  voiceLogger
            VARIABLES   { trapSeverity,
						  trapVLModuleName,
						  trapVLModuleStatus,
            			  trapHostTime}
            DESCRIPTION
                    "Failed to Query the Logger. Trap Severity = {1}, VL Module Name = {2}, VL Module Status = {3}, Trap Host Time = {4}"
            ::= 6003
          vlDbmConsistencyFailed TRAP-TYPE
            ENTERPRISE  voiceLoggerLogging
            VARIABLES   { trapSeverity,
						  trapVLModuleName,
						  trapVLModuleStatus,
            			  trapHostTime}
            DESCRIPTION
                    "Initialization Failure. Trap Severity = {1}, VL Module Name = {2}, VL Module Status = {3}, Trap Host Time = {4}"
            ::= 6100
          vlDbmInitPartitionFailed TRAP-TYPE
            ENTERPRISE  voiceLoggerLogging
            VARIABLES   { trapSeverity,
						  trapVLModuleName,
						  trapVLModuleStatus,
            			  trapHostTime}
            DESCRIPTION
                    "Initialization Failure. Trap Severity = {1}, VL Module Name = {2}, VL Module Status = {3}, Trap Host Time = {4}"
            ::= 6101
          vlKernerHWDriverInitFailed TRAP-TYPE
            ENTERPRISE  voiceLoggerLogging
            VARIABLES   { trapSeverity,
						  trapVLModuleName,
						  trapVLModuleStatus,
            			  trapHostTime}
            DESCRIPTION
                    "Initialization Failure. Trap Severity = {1}, VL Module Name = {2}, VL Module Status = {3}, Trap Host Time = {4}"
            ::= 6102
          vlVoipDriverInitFailed TRAP-TYPE
            ENTERPRISE  voiceLoggerLogging
            VARIABLES   { trapSeverity,
						  trapVLModuleName,
						  trapVLModuleStatus,
            			  trapHostTime}
            DESCRIPTION
                    "Initialization Failure. Trap Severity = {1}, VL Module Name = {2}, VL Module Status = {3}, Trap Host Time = {4}"
            ::= 6103
          vlDliDriverInitFailed TRAP-TYPE
            ENTERPRISE  voiceLoggerLogging
            VARIABLES   { trapSeverity,
						  trapVLModuleName,
						  trapVLModuleStatus,
            			  trapHostTime}
            DESCRIPTION
                    "Initialization Failure. Trap Severity = {1}, VL Module Name = {2}, VL Module Status = {3}, Trap Host Time = {4}"
            ::= 6104
          vlAumGeneralInitFailure TRAP-TYPE
            ENTERPRISE  voiceLoggerLogging
            VARIABLES   { trapSeverity,
						  trapVLModuleName,
						  trapVLModuleStatus,
            			  trapHostTime}
            DESCRIPTION
                    "Initialization Failure. Trap Severity = {1}, VL Module Name = {2}, VL Module Status = {3}, Trap Host Time = {4}"
            ::= 6105
          vlDiskOpenPartitionFailed TRAP-TYPE
            ENTERPRISE  voiceLoggerLogging
            VARIABLES   { trapSeverity,
						  trapVLModuleName,
						  trapVLModuleStatus,
            			  trapHostTime,
            			  trapDiskDrive}
            DESCRIPTION
                    "Initialization Failure. Trap Severity = {1}, VL Module Name = {2}, VL Module Status = {3}, Trap Host Time = {4}, Trap Disk Drive = {5}"
            ::= 6106
          vlDiskDriveProblem TRAP-TYPE
            ENTERPRISE  voiceLoggerLogging
            VARIABLES   { trapSeverity,
						  trapVLModuleName,
						  trapVLModuleStatus,
            			  trapHostTime}
            DESCRIPTION
                    "Disk Problem. Trap Severity = {1}, VL Module Name = {2}, VL Module Status = {3}, Trap Host Time = {4}"
            ::= 6107
          vlNPlus1ManualSwitch TRAP-TYPE
            ENTERPRISE  voiceLoggerLogging
            VARIABLES   { trapSeverity,
						  trapVLModuleName,
						  trapVLModuleStatus,
            			  trapHostTime}
            DESCRIPTION
                    "NPLUS1 - logger was switched due to manual switch. Trap Severity = {1}, VL Module Name = {2}, VL Module Status = {3}, Trap Host Time = {4}"
            ::= 6108
          vlNPlus1SpareIsBackingUp TRAP-TYPE
            ENTERPRISE  voiceLoggerLogging
            VARIABLES   { trapSeverity,
						  trapVLModuleName,
						  trapVLModuleStatus,
            			  trapHostTime,
            			  trapLoggerIdInChain}
            DESCRIPTION
                    "NPLUS1 - Spare is backing up logger X. Trap Severity = {1}, VL Module Name = {2}, VL Module Status = {3}, Trap Host Time = {4}, Logger ID in Chain = {5}"
            ::= 6109
          vlNPlus1ROBMalfunction TRAP-TYPE
            ENTERPRISE  voiceLoggerLogging
            VARIABLES   { trapSeverity,
						  trapVLModuleName,
						  trapVLModuleStatus,
            			  trapHostTime}
            DESCRIPTION
                    "Nplus1 redundancy Malfunction [ROB]. Trap Severity = {1}, VL Module Name = {2}, VL Module Status = {3}, Trap Host Time = {4}"
            ::= 6110
          vlNPlus1ROBPowerFailure TRAP-TYPE
            ENTERPRISE  voiceLoggerLogging
            VARIABLES   { trapSeverity,
						  trapVLModuleName,
						  trapVLModuleStatus,
            			  trapHostTime}
            DESCRIPTION
                    "Nplus1 redundancy Power Failure [ROB]. Trap Severity = {1}, VL Module Name = {2}, VL Module Status = {3}, Trap Host Time = {4}"
            ::= 6111
          vlNPlus1SpareNeedLongUpdate TRAP-TYPE
            ENTERPRISE  voiceLoggerLogging
            VARIABLES   { trapSeverity,
						  trapVLModuleName,
						  trapVLModuleStatus,
            			  trapHostTime}
            DESCRIPTION
                    "NPLUS1 - Spare Needs Long Update. Trap Severity = {1}, VL Module Name = {2}, VL Module Status = {3}, Trap Host Time = {4}"
            ::= 6112
          vlAutoDeleteUnder3PercSpace TRAP-TYPE
            ENTERPRISE  voiceLoggerLogging
            VARIABLES   { trapSeverity,
						  trapVLModuleName,
						  trapVLModuleStatus,
            			  trapHostTime,
            			  trapFreeSpacePercentage}
            DESCRIPTION
                    "Low Free Disk Space. Trap Severity = {1}, VL Module Name = {2}, VL Module Status = {3}, Trap Host Time = {4}, Free Space = {5}"
            ::= 6113
          vlAutoDeleteNofreeSpace TRAP-TYPE
            ENTERPRISE  voiceLoggerLogging
            VARIABLES   { trapSeverity,
						  trapVLModuleName,
						  trapVLModuleStatus,
            			  trapHostTime,
            			  trapFreeSpacePercentage}
            DESCRIPTION
                    "No Free Disk Space. Trap Severity = {1}, VL Module Name = {2}, VL Module Status = {3}, Trap Host Time = {4}, Free Space = {5}"
            ::= 6114
          vlAutoDeleteLowKeptSpace TRAP-TYPE
            ENTERPRISE  voiceLoggerLogging
            VARIABLES   { trapSeverity,
						  trapVLModuleName,
						  trapVLModuleStatus,
            			  trapHostTime,
            			  trapKeptSpacePercentage}
            DESCRIPTION
                    "Low Kept Disk Space. Trap Severity = {1}, VL Module Name = {2}, VL Module Status = {3}, Trap Host Time = {4}, Kept Space = {5}"
            ::= 6115
          vlAutoDeleteNoKeptSpace TRAP-TYPE
            ENTERPRISE  voiceLoggerLogging
            VARIABLES   { trapSeverity,
						  trapVLModuleName,
						  trapVLModuleStatus,
            			  trapHostTime}
            DESCRIPTION
                    "No Kept Disk Space. Trap Severity = {1}, VL Module Name = {2}, VL Module Status = {3}, Trap Host Time = {4}"
            ::= 6116
          vlDongleNotInitialized TRAP-TYPE
            ENTERPRISE  voiceLoggerLogging
            VARIABLES   { trapSeverity,
						  trapVLModuleName,
						  trapVLModuleStatus,
            			  trapHostTime}
            DESCRIPTION
                    "Dongle Problem. Trap Severity = {1}, VL Module Name = {2}, VL Module Status = {3}, Trap Host Time = {4}"
            ::= 6117
          vlDongleAlreadyInitialized TRAP-TYPE
            ENTERPRISE  voiceLoggerLogging
            VARIABLES   { trapSeverity,
						  trapVLModuleName,
						  trapVLModuleStatus,
            			  trapHostTime}
            DESCRIPTION
                    "Dongle Problem. Trap Severity = {1}, VL Module Name = {2}, VL Module Status = {3}, Trap Host Time = {4}"
            ::= 6118
          vlDongleDeviceNotSupported TRAP-TYPE
            ENTERPRISE  voiceLoggerLogging
            VARIABLES   { trapSeverity,
						  trapVLModuleName,
						  trapVLModuleStatus,
            			  trapHostTime}
            DESCRIPTION
                    "Dongle Problem. Trap Severity = {1}, VL Module Name = {2}, VL Module Status = {3}, Trap Host Time = {4}"
            ::= 6119
          vlDongleInitFailed-function TRAP-TYPE
            ENTERPRISE  voiceLoggerLogging
            VARIABLES   { trapSeverity,
						  trapVLModuleName,
						  trapVLModuleStatus,
            			  trapHostTime}
            DESCRIPTION
                    "Dongle Problem. Trap Severity = {1}, VL Module Name = {2}, VL Module Status = {3}, Trap Host Time = {4}"
            ::= 6120
          vlDongleConnectFailed  TRAP-TYPE
            ENTERPRISE  voiceLoggerLogging
            VARIABLES   { trapSeverity,
						  trapVLModuleName,
						  trapVLModuleStatus,
            			  trapHostTime}
            DESCRIPTION
                    "Dongle Problem. Trap Severity = {1}, VL Module Name = {2}, VL Module Status = {3}, Trap Host Time = {4}"
            ::= 6121
          vlDongleInitFailed-network  TRAP-TYPE
            ENTERPRISE  voiceLoggerLogging
            VARIABLES   { trapSeverity,
						  trapVLModuleName,
						  trapVLModuleStatus,
            			  trapHostTime}
            DESCRIPTION
                    "Dongle Problem. Trap Severity = {1}, VL Module Name = {2}, VL Module Status = {3}, Trap Host Time = {4}"
            ::= 6122
          vlDongleNoDevice TRAP-TYPE
            ENTERPRISE  voiceLoggerLogging
            VARIABLES   { trapSeverity,
						  trapVLModuleName,
						  trapVLModuleStatus,
            			  trapHostTime}
            DESCRIPTION
                    "Dongle Problem. Trap Severity = {1}, VL Module Name = {2}, VL Module Status = {3}, Trap Host Time = {4}"
            ::= 6123
          vlDongleInitFailed-parameter TRAP-TYPE
            ENTERPRISE  voiceLoggerLogging
            VARIABLES   { trapSeverity,
						  trapVLModuleName,
						  trapVLModuleStatus,
            			  trapHostTime}
            DESCRIPTION
                    "Dongle Problem. Trap Severity = {1}, VL Module Name = {2}, VL Module Status = {3}, Trap Host Time = {4}"
            ::= 6124
          vlDongleInitFailed-HLApi  TRAP-TYPE
            ENTERPRISE  voiceLoggerLogging
            VARIABLES   { trapSeverity,
						  trapVLModuleName,
						  trapVLModuleStatus,
            			  trapHostTime}
            DESCRIPTION
                    "Dongle Problem. Trap Severity = {1}, VL Module Name = {2}, VL Module Status = {3}, Trap Host Time = {4}"
            ::= 6125
          vlDongleInitFailed-memory TRAP-TYPE
            ENTERPRISE  voiceLoggerLogging
            VARIABLES   { trapSeverity,
						  trapVLModuleName,
						  trapVLModuleStatus,
            			  trapHostTime}
            DESCRIPTION
                    "Dongle Problem. Trap Severity = {1}, VL Module Name = {2}, VL Module Status = {3}, Trap Host Time = {4}"
            ::= 6126
          vlDongleInitFailed-HLVDD TRAP-TYPE
            ENTERPRISE  voiceLoggerLogging
            VARIABLES   { trapSeverity,
						  trapVLModuleName,
						  trapVLModuleStatus,
            			  trapHostTime}
            DESCRIPTION
                    "Dongle Problem. Trap Severity = {1}, VL Module Name = {2}, VL Module Status = {3}, Trap Host Time = {4}"
            ::= 6127
          vlCheckSumInvalid TRAP-TYPE
            ENTERPRISE  voiceLoggerLogging
            VARIABLES   { trapSeverity,
						  trapVLModuleName,
						  trapVLModuleStatus,
            			  trapHostTime}
            DESCRIPTION
                    "Invalid Checksum. Trap Severity = {1}, VL Module Name = {2}, VL Module Status = {3}, Trap Host Time = {4}"
            ::= 6128
          vlChannelsLineError TRAP-TYPE
            ENTERPRISE  voiceLoggerLogging
            VARIABLES   { trapSeverity,
						  trapVLModuleName,
						  trapVLModuleStatus,
            			  trapHostTime,
            			  trapChannelNumber,
            			  trapLineErrorType,
            			  trapBoardType,
            			  trapBoardOrLogicalTrunk,
            			  trapChannelOrTimeslot,
            			  trapMateLogicalTrunk,
            			  trapMateTimeslot}
            DESCRIPTION
			"Line Error On Channels. Trap Severity = {1}, VL Module Name = {2}, VL Module Status = {3}, Trap Host Time = {4}, Channel Number = {5}, Line Error Type = {6}, Board Type = {7}, Board Or Logical Trunk = {8}, Channel Or Timeslot = {9}, Mate Logical Trunk = {10}, Mate Timeslot = {11}"
            ::= 6129
          vlChannelsSomeNotRecording TRAP-TYPE
            ENTERPRISE  voiceLoggerLogging
            VARIABLES   { trapSeverity,
						  trapVLModuleName,
						  trapVLModuleStatus,
            			  trapHostTime,
            			  trapNumOfChannels}
            DESCRIPTION
			"Some Input channels are not recording. Trap Severity = {1}, VL Module Name = {2}, VL Module Status = {3}, Trap Host Time = {4}, Num Of Channels = {5}"
            ::= 6130
          vlChannelsLowStatAlarm TRAP-TYPE
            ENTERPRISE  voiceLoggerLogging
            VARIABLES   { trapSeverity,
						  trapVLModuleName,
						  trapVLModuleStatus,
            			  trapHostTime,
            			  trapNumOfChannels}
            DESCRIPTION
			"Low statistics alarm on some input channels. Trap Severity = {1}, VL Module Name = {2}, VL Module Status = {3}, Trap Host Time = {4}, Num Of Channels = {5}"
            ::= 6131
          vlChannelsHighStatAlarm TRAP-TYPE
            ENTERPRISE  voiceLoggerLogging
            VARIABLES   { trapSeverity,
						  trapVLModuleName,
						  trapVLModuleStatus,
            			  trapHostTime,
            			  trapNumOfChannels}
            DESCRIPTION
			"High statistics alarm on some input channels. Trap Severity = {1}, VL Module Name = {2}, VL Module Status = {3}, Trap Host Time = {4}, Num Of Channels = {5}"
            ::= 6132
          vlAdifDspIllegalCommand TRAP-TYPE
            ENTERPRISE  voiceLoggerCapture
            VARIABLES   { trapSeverity,
						  trapVLModuleName,
						  trapVLModuleStatus,
            			  trapHostTime,
            			  trapBoardNumber}
            DESCRIPTION
                    "Dsp Problem In Recording Board [ADIF]. Trap Severity = {1}, VL Module Name = {2}, VL Module Status = {3}, Trap Host Time = {4}, Board Number = {5}"
            ::= 6300
          vlAdifDspNoSynch TRAP-TYPE
            ENTERPRISE  voiceLoggerCapture
            VARIABLES   { trapSeverity,
						  trapVLModuleName,
						  trapVLModuleStatus,
            			  trapHostTime,
            			  trapBoardNumber}
            DESCRIPTION
                    "Dsp Problem In Recording Board [ADIF]. Trap Severity = {1}, VL Module Name = {2}, VL Module Status = {3}, Trap Host Time = {4}, Board Number = {5}"
            ::= 6301
          vlAdifDspSSIRXError TRAP-TYPE
            ENTERPRISE  voiceLoggerCapture
            VARIABLES   { trapSeverity,
						  trapVLModuleName,
						  trapVLModuleStatus,
            			  trapHostTime,
            			  trapBoardNumber}
            DESCRIPTION
                    "Dsp Problem In Recording Board [ADIF]. Trap Severity = {1}, VL Module Name = {2}, VL Module Status = {3}, Trap Host Time = {4}, Board Number = {5}"
            ::= 6302
          vlAdifDspCodecError TRAP-TYPE
            ENTERPRISE  voiceLoggerCapture
            VARIABLES   { trapSeverity,
						  trapVLModuleName,
						  trapVLModuleStatus,
            			  trapHostTime,
            			  trapBoardNumber}
            DESCRIPTION
                    "Dsp Problem In Recording Board [ADIF]. Trap Severity = {1}, VL Module Name = {2}, VL Module Status = {3}, Trap Host Time = {4}, Board Number = {5}"
            ::= 6303
          vlAdifDspIllegalParameter TRAP-TYPE
            ENTERPRISE  voiceLoggerCapture
            VARIABLES   { trapSeverity,
						  trapVLModuleName,
						  trapVLModuleStatus,
            			  trapHostTime,
            			  trapBoardNumber}
            DESCRIPTION
                    "Dsp Problem In Recording Board [ADIF]. Trap Severity = {1}, VL Module Name = {2}, VL Module Status = {3}, Trap Host Time = {4}, Board Number = {5}"
            ::= 6304
          vlAdifDspMPMLQError TRAP-TYPE
            ENTERPRISE  voiceLoggerCapture
            VARIABLES   { trapSeverity,
						  trapVLModuleName,
						  trapVLModuleStatus,
            			  trapHostTime,
            			  trapBoardNumber}
            DESCRIPTION
                    "Dsp Problem In Recording Board [ADIF]. Trap Severity = {1}, VL Module Name = {2}, VL Module Status = {3}, Trap Host Time = {4}, Board Number = {5}"
            ::= 6305
          vlAdifDspStackOverflow TRAP-TYPE
            ENTERPRISE  voiceLoggerCapture
            VARIABLES   { trapSeverity,
						  trapVLModuleName,
						  trapVLModuleStatus,
            			  trapHostTime,
            			  trapBoardNumber}
            DESCRIPTION
                    "Dsp Problem In Recording Board [ADIF]. Trap Severity = {1}, VL Module Name = {2}, VL Module Status = {3}, Trap Host Time = {4}, Board Number = {5}"
            ::= 6306
          vlAdifDspIllegalInstruction TRAP-TYPE
            ENTERPRISE  voiceLoggerCapture
            VARIABLES   { trapSeverity,
						  trapVLModuleName,
						  trapVLModuleStatus,
            			  trapHostTime,
            			  trapBoardNumber}
            DESCRIPTION
                    "Dsp Problem In Recording Board [ADIF]. Trap Severity = {1}, VL Module Name = {2}, VL Module Status = {3}, Trap Host Time = {4}, Board Number = {5}"
            ::= 6307
          vlAdifNoInterrupts TRAP-TYPE
            ENTERPRISE  voiceLoggerCapture
            VARIABLES   { trapSeverity,
						  trapVLModuleName,
						  trapVLModuleStatus,
            			  trapHostTime,
            			  trapBoardNumber}
            DESCRIPTION
                    "Internal Problem In Recording Board [ADIF]. Trap Severity = {1}, VL Module Name = {2}, VL Module Status = {3}, Trap Host Time = {4}, Board Number = {5}"
            ::= 6308
          vlAdifInternalBoardError TRAP-TYPE
            ENTERPRISE  voiceLoggerCapture
            VARIABLES   { trapSeverity,
						  trapVLModuleName,
						  trapVLModuleStatus,
            			  trapHostTime,
            			  trapBoardNumber}
            DESCRIPTION
                    "Internal Problem In Recording Board [ADIF]. Trap Severity = {1}, VL Module Name = {2}, VL Module Status = {3}, Trap Host Time = {4}, Board Number = {5}"
            ::= 6309
          vlAdifNoSignal TRAP-TYPE
            ENTERPRISE  voiceLoggerCapture
            VARIABLES   { trapSeverity,
						  trapVLModuleName,
						  trapVLModuleStatus,
            			  trapHostTime,
            			  trapBoardNumber}
            DESCRIPTION
                    "Line Problem In Recording Board [ADIF]. Trap Severity = {1}, VL Module Name = {2}, VL Module Status = {3}, Trap Host Time = {4}, Board Number = {5}"
            ::= 6310
          vlAdifAlarmIndicationSignal TRAP-TYPE
            ENTERPRISE  voiceLoggerCapture
            VARIABLES   { trapSeverity,
						  trapVLModuleName,
						  trapVLModuleStatus,
            			  trapHostTime,
            			  trapBoardNumber}
            DESCRIPTION
                    "Line Problem In Recording Board [ADIF]. Trap Severity = {1}, VL Module Name = {2}, VL Module Status = {3}, Trap Host Time = {4}, Board Number = {5}"
            ::= 6311
          vlAdifLossOfSynch TRAP-TYPE
            ENTERPRISE  voiceLoggerCapture
            VARIABLES   { trapSeverity,
						  trapVLModuleName,
						  trapVLModuleStatus,
            			  trapHostTime,
            			  trapBoardNumber}
            DESCRIPTION
                    "Line Problem In Recording Board [ADIF]. Trap Severity = {1}, VL Module Name = {2}, VL Module Status = {3}, Trap Host Time = {4}, Board Number = {5}"
            ::= 6312
          vlAdifRemoteAlarmIndication TRAP-TYPE
            ENTERPRISE  voiceLoggerCapture
            VARIABLES   { trapSeverity,
						  trapVLModuleName,
						  trapVLModuleStatus,
            			  trapHostTime,
            			  trapBoardNumber}
            DESCRIPTION
                    "Line Problem In Recording Board [ADIF]. Trap Severity = {1}, VL Module Name = {2}, VL Module Status = {3}, Trap Host Time = {4}, Board Number = {5}"
            ::= 6313
          vlAdifFramingError TRAP-TYPE
            ENTERPRISE  voiceLoggerCapture
            VARIABLES   { trapSeverity,
						  trapVLModuleName,
						  trapVLModuleStatus,
            			  trapHostTime,
            			  trapBoardNumber}
            DESCRIPTION
                    "Line Problem In Recording Board [ADIF]. Trap Severity = {1}, VL Module Name = {2}, VL Module Status = {3}, Trap Host Time = {4}, Board Number = {5}"
            ::= 6314
          vlApaInternalSelfTestFailed TRAP-TYPE
            ENTERPRISE  voiceLoggerCapture
            VARIABLES   { trapSeverity,
						  trapVLModuleName,
						  trapVLModuleStatus,
            			  trapHostTime,
            			  trapBoardNumber}
            DESCRIPTION
                    "Line Problem In Algorithms Board [APA]. Trap Severity = {1}, VL Module Name = {2}, VL Module Status = {3}, Trap Host Time = {4}, Board Number = {5}"
            ::= 6315
          vlApaCommBoardDspError TRAP-TYPE
            ENTERPRISE  voiceLoggerCapture
            VARIABLES   { trapSeverity,
						  trapVLModuleName,
						  trapVLModuleStatus,
            			  trapHostTime,
            			  trapBoardNumber}
            DESCRIPTION
                    "Dsp Problem In Algorithms Board [APA]. Trap Severity = {1}, VL Module Name = {2}, VL Module Status = {3}, Trap Host Time = {4}, Board Number = {5}"
            ::= 6316
          vlApaIOError TRAP-TYPE
            ENTERPRISE  voiceLoggerCapture
            VARIABLES   { trapSeverity,
						  trapVLModuleName,
						  trapVLModuleStatus,
            			  trapHostTime,
            			  trapBoardNumber}
            DESCRIPTION
                    "Line Problem In Algorithms Board [APA]. Trap Severity = {1}, VL Module Name = {2}, VL Module Status = {3}, Trap Host Time = {4}, Board Number = {5}"
            ::= 6317
           vlApaDspFirmwareLoadFailed TRAP-TYPE
            ENTERPRISE  voiceLoggerCapture
            VARIABLES   { trapSeverity,
						  trapVLModuleName,
						  trapVLModuleStatus,
            			  trapHostTime,
            			  trapBoardNumber,
						  trapDspNumber}
            DESCRIPTION
                    "Dsp Problem In Algorithms Board [APA]. Trap Severity = {1}, VL Module Name = {2}, VL Module Status = {3}, Trap Host Time = {4}, Board Number = {5}, DSP Number = {6}"
            ::= 6318
           vlApaDspRuntimeError TRAP-TYPE
            ENTERPRISE  voiceLoggerCapture
            VARIABLES   { trapSeverity,
						  trapVLModuleName,
						  trapVLModuleStatus,
            			  trapHostTime,
            			  trapBoardNumber,
						  trapDspNumber}
            DESCRIPTION
                    "Dsp Problem In Algorithms Board [APA]. Trap Severity = {1}, VL Module Name = {2}, VL Module Status = {3}, Trap Host Time = {4}, Board Number = {5}, DSP Number = {6}"
            ::= 6319
          vlIsdnDspCommFailed TRAP-TYPE
            ENTERPRISE  voiceLoggerCapture
            VARIABLES   { trapSeverity,
						  trapVLModuleName,
						  trapVLModuleStatus,
            			  trapHostTime,
            			  trapBoardNumber,
						  trapDspNumber}
            DESCRIPTION
                    "Dsp Problem In interface Board [ISDN]. Trap Severity = {1}, VL Module Name = {2}, VL Module Status = {3}, Trap Host Time = {4}, Board Number = {5}, DSP Number = {6}"
            ::= 6320
          vlIsdnIniterror TRAP-TYPE
            ENTERPRISE  voiceLoggerCapture
            VARIABLES   { trapSeverity,
						  trapVLModuleName,
						  trapVLModuleStatus,
            			  trapHostTime,
            			  trapBoardNumber}
            DESCRIPTION
                    "Internal Problem In Interface Board [ISDN]. Trap Severity = {1}, VL Module Name = {2}, VL Module Status = {3}, Trap Host Time = {4}, Board Number = {5}"
            ::= 6321
          vlIsdnBSError TRAP-TYPE
            ENTERPRISE  voiceLoggerCapture
            VARIABLES   { trapSeverity,
						  trapVLModuleName,
						  trapVLModuleStatus,
            			  trapHostTime,
            			  trapBoardNumber}
            DESCRIPTION
                    "Internal Problem In Interface Board [ISDN]. Trap Severity = {1}, VL Module Name = {2}, VL Module Status = {3}, Trap Host Time = {4}, Board Number = {5}"
            ::= 6322
          vlIsdnLogicConnectError TRAP-TYPE
            ENTERPRISE  voiceLoggerCapture
            VARIABLES   { trapSeverity,
						  trapVLModuleName,
						  trapVLModuleStatus,
            			  trapHostTime,
            			  trapBoardNumber}
            DESCRIPTION
                    "Internal Problem In Interface Board [ISDN]. Trap Severity = {1}, VL Module Name = {2}, VL Module Status = {3}, Trap Host Time = {4}, Board Number = {5}"
            ::= 6323
          vlIsdnBoardSelfTestFailed TRAP-TYPE
            ENTERPRISE  voiceLoggerCapture
            VARIABLES   { trapSeverity,
						  trapVLModuleName,
						  trapVLModuleStatus,
            			  trapHostTime,
            			  trapBoardNumber}
            DESCRIPTION
                    "Internal Problem In Interface Board [ISDN]. Trap Severity = {1}, VL Module Name = {2}, VL Module Status = {3}, Trap Host Time = {4}, Board Number = {5}"
            ::= 6324
          vlIsdnLineError TRAP-TYPE
            ENTERPRISE  voiceLoggerCapture
            VARIABLES   { trapSeverity,
						  trapVLModuleName,
						  trapVLModuleStatus,
            			  trapHostTime,
            			  trapBoardNumber}
            DESCRIPTION
                    "Line Problem In Interface Board [ISDN]. Trap Severity = {1}, VL Module Name = {2}, VL Module Status = {3}, Trap Host Time = {4}, Board Number = {5}"
            ::= 6325
          vlEtaiInitBoardFailed TRAP-TYPE
            ENTERPRISE  voiceLoggerCapture
            VARIABLES   { trapSeverity,
						  trapVLModuleName,
						  trapVLModuleStatus,
            			  trapHostTime,
            			  trapBoardNumber}
            DESCRIPTION
                    "Internal Problem In Interface Board [ETAI]. Trap Severity = {1}, VL Module Name = {2}, VL Module Status = {3}, Trap Host Time = {4}, Board Number = {5}"
            ::= 6326
          vlEtaiLineError TRAP-TYPE
            ENTERPRISE  voiceLoggerCapture
            VARIABLES   { trapSeverity,
						  trapVLModuleName,
						  trapVLModuleStatus,
            			  trapHostTime,
            			  trapBoardNumber,
						  trapLineNumber,
						  trapLineProblem}
            DESCRIPTION
                    "Line Problem In Interface Board [ETAI]. Trap Severity = {1}, VL Module Name = {2}, VL Module Status = {3}, Trap Host Time = {4}, Board Number = {5}, Line Number = {6}, Line Problem = {7}"
            ::= 6327
          vlEtaiMatrixSwitchError TRAP-TYPE
            ENTERPRISE  voiceLoggerCapture
            VARIABLES   { trapSeverity,
						  trapVLModuleName,
						  trapVLModuleStatus,
            			  trapHostTime,
            			  trapBoardNumber}
            DESCRIPTION
                    "Internal Problem In Interface Board [ETAI]. Trap Severity = {1}, VL Module Name = {2}, VL Module Status = {3}, Trap Host Time = {4}, Board Number = {5}"
            ::= 6328
          vlEtaiDspError TRAP-TYPE
            ENTERPRISE  voiceLoggerCapture
            VARIABLES   { trapSeverity,
						  trapVLModuleName,
						  trapVLModuleStatus,
            			  trapHostTime,
            			  trapBoardNumber}
            DESCRIPTION
                    "Dsp Problem In interface Board [ETAI]. Trap Severity = {1}, VL Module Name = {2}, VL Module Status = {3}, Trap Host Time = {4}, Board Number = {5}"
            ::= 6329
          vlNtcmLoopError TRAP-TYPE
            ENTERPRISE  voiceLoggerCapture
            VARIABLES   { trapSeverity,
						  trapVLModuleName,
						  trapVLModuleStatus,
            			  trapHostTime,
            			  trapBoardNumber}
            DESCRIPTION
                    "Internal Problem In Interface Board [NTCM]. Trap Severity = {1}, VL Module Name = {2}, VL Module Status = {3}, Trap Host Time = {4}, Board Number = {5}"
            ::= 6330
          vlNtcmInitError TRAP-TYPE
            ENTERPRISE  voiceLoggerCapture
            VARIABLES   { trapSeverity,
						  trapVLModuleName,
						  trapVLModuleStatus,
            			  trapHostTime,
            			  trapBoardNumber}
            DESCRIPTION
                    "Internal Problem In Interface Board [NTCM]. Trap Severity = {1}, VL Module Name = {2}, VL Module Status = {3}, Trap Host Time = {4}, Board Number = {5}"
            ::= 6331
          vlNtcmMatrixSwitchError TRAP-TYPE
            ENTERPRISE  voiceLoggerCapture
            VARIABLES   { trapSeverity,
						  trapVLModuleName,
						  trapVLModuleStatus,
            			  trapHostTime,
            			  trapBoardNumber}
            DESCRIPTION
                    "Internal Problem In Interface Board [NTCM]. Trap Severity = {1}, VL Module Name = {2}, VL Module Status = {3}, Trap Host Time = {4}, Board Number = {5}"
            ::= 6332
          vlTdaMatrizSwitchError TRAP-TYPE
            ENTERPRISE  voiceLoggerCapture
            VARIABLES   { trapSeverity,
						  trapVLModuleName,
						  trapVLModuleStatus,
            			  trapHostTime,
            			  trapBoardNumber}
            DESCRIPTION
                    "Internal Problem In Algorithms Board [TDA]. Trap Severity = {1}, VL Module Name = {2}, VL Module Status = {3}, Trap Host Time = {4}, Board Number = {5}"
            ::= 6333
          vlTdaDspError TRAP-TYPE
            ENTERPRISE  voiceLoggerCapture
            VARIABLES   { trapSeverity,
						  trapVLModuleName,
						  trapVLModuleStatus,
            			  trapHostTime,
            			  trapBoardNumber}
            DESCRIPTION
                    "Dsp Problem In Algorithms Board [TDA]. Trap Severity = {1}, VL Module Name = {2}, VL Module Status = {3}, Trap Host Time = {4}, Board Number = {5}"
            ::= 6334
          vlTdaGeneralError TRAP-TYPE
            ENTERPRISE  voiceLoggerCapture
            VARIABLES   { trapSeverity,
						  trapVLModuleName,
						  trapVLModuleStatus,
            			  trapHostTime,
            			  trapBoardNumber}
            DESCRIPTION
                    "Internal Problem In Algorithms Board [TDA]. Trap Severity = {1}, VL Module Name = {2}, VL Module Status = {3}, Trap Host Time = {4}, Board Number = {5}"
            ::= 6335
          vlNatiChannelError TRAP-TYPE
            ENTERPRISE  voiceLoggerCapture
            VARIABLES   { trapSeverity,
						  trapVLModuleName,
						  trapVLModuleStatus,
            			  trapHostTime,
            			  trapBoardNumber}
            DESCRIPTION
                    "line Problem In Interface Board [NATI]. Trap Severity = {1}, VL Module Name = {2}, VL Module Status = {3}, Trap Host Time = {4}, Board Number = {5}"
            ::= 6336
          vlNatiInitBoardError TRAP-TYPE
            ENTERPRISE  voiceLoggerCapture
            VARIABLES   { trapSeverity,
						  trapVLModuleName,
						  trapVLModuleStatus,
            			  trapHostTime,
            			  trapBoardNumber}
            DESCRIPTION
                    "Internal Problem In Interface Board [NATI]. Trap Severity = {1}, VL Module Name = {2}, VL Module Status = {3}, Trap Host Time = {4}, Board Number = {5}"
            ::= 6337
          vlNatiMatrixSwitchError TRAP-TYPE
            ENTERPRISE  voiceLoggerCapture
            VARIABLES   { trapSeverity,
						  trapVLModuleName,
						  trapVLModuleStatus,
            			  trapHostTime,
            			  trapBoardNumber}
            DESCRIPTION
                    "Internal Problem In Interface Board [NATI]. Trap Severity = {1}, VL Module Name = {2}, VL Module Status = {3}, Trap Host Time = {4}, Board Number = {5}"
            ::= 6338
          vlNatiDspA3mError TRAP-TYPE
            ENTERPRISE  voiceLoggerCapture
            VARIABLES   { trapSeverity,
						  trapVLModuleName,
						  trapVLModuleStatus,
            			  trapHostTime,
            			  trapBoardNumber}
            DESCRIPTION
                    "Dsp Problem In Interface Board [NATI]. Trap Severity = {1}, VL Module Name = {2}, VL Module Status = {3}, Trap Host Time = {4}, Board Number = {5}"
            ::= 6339
          vlIsacSelectedClockError TRAP-TYPE
            ENTERPRISE  voiceLoggerCapture
            VARIABLES   { trapSeverity,
						  trapVLModuleName,
						  trapVLModuleStatus,
            			  trapHostTime,
            			  trapBoardNumber}
            DESCRIPTION
                    "Internal Problem In Interface Board [ISAC]. Trap Severity = {1}, VL Module Name = {2}, VL Module Status = {3}, Trap Host Time = {4}, Board Number = {5}"
            ::= 6340
          vlIsacRightClockError TRAP-TYPE
            ENTERPRISE  voiceLoggerCapture
            VARIABLES   { trapSeverity,
						  trapVLModuleName,
						  trapVLModuleStatus,
            			  trapHostTime,
            			  trapBoardNumber}
            DESCRIPTION
                    "Internal Problem In Interface Board [ISAC]. Trap Severity = {1}, VL Module Name = {2}, VL Module Status = {3}, Trap Host Time = {4}, Board Number = {5}"
            ::= 6341
          vlIsacLeftClockError TRAP-TYPE
            ENTERPRISE  voiceLoggerCapture
            VARIABLES   { trapSeverity,
						  trapVLModuleName,
						  trapVLModuleStatus,
            			  trapHostTime,
            			  trapBoardNumber}
            DESCRIPTION
                    "Internal Problem In Interface Board [ISAC]. Trap Severity = {1}, VL Module Name = {2}, VL Module Status = {3}, Trap Host Time = {4}, Board Number = {5}"
            ::= 6342
          vlIsacRightFameSynchError TRAP-TYPE
            ENTERPRISE  voiceLoggerCapture
            VARIABLES   { trapSeverity,
						  trapVLModuleName,
						  trapVLModuleStatus,
            			  trapHostTime,
            			  trapBoardNumber}
            DESCRIPTION
                    "Internal Problem In Interface Board [ISAC]. Trap Severity = {1}, VL Module Name = {2}, VL Module Status = {3}, Trap Host Time = {4}, Board Number = {5}"
            ::= 6343
          vlIsacLeftFrameSynchError TRAP-TYPE
            ENTERPRISE  voiceLoggerCapture
            VARIABLES   { trapSeverity,
						  trapVLModuleName,
						  trapVLModuleStatus,
            			  trapHostTime,
            			  trapBoardNumber}
            DESCRIPTION
                    "Internal Problem In Interface Board [ISAC]. Trap Severity = {1}, VL Module Name = {2}, VL Module Status = {3}, Trap Host Time = {4}, Board Number = {5}"
            ::= 6344
          vlIsacBoardError TRAP-TYPE
            ENTERPRISE  voiceLoggerCapture
            VARIABLES   { trapSeverity,
						  trapVLModuleName,
						  trapVLModuleStatus,
            			  trapHostTime,
            			  trapBoardNumber}
            DESCRIPTION
                    "Internal Problem In Interface Board [ISAC]. Trap Severity = {1}, VL Module Name = {2}, VL Module Status = {3}, Trap Host Time = {4}, Board Number = {5}"
            ::= 6345
          vlIsacTestToneError TRAP-TYPE
            ENTERPRISE  voiceLoggerCapture
            VARIABLES   { trapSeverity,
						  trapVLModuleName,
						  trapVLModuleStatus,
            			  trapHostTime,
            			  trapBoardNumber,
						  trapDataLineNumber}
            DESCRIPTION
                    "Line Problem In Interface Board [ISAC]. Trap Severity = {1}, VL Module Name = {2}, VL Module Status = {3}, Trap Host Time = {4}, Board Number = {5}, Data Line Number = {6}"
            ::= 6346
          vlIsacCriticalSystemError TRAP-TYPE
            ENTERPRISE  voiceLoggerCapture
            VARIABLES   { trapSeverity,
						  trapVLModuleName,
						  trapVLModuleStatus,
            			  trapHostTime}
            DESCRIPTION
                    "Internal Problem In Interface Board [ISAC]. Trap Severity = {1}, VL Module Name = {2}, VL Module Status = {3}, Trap Host Time = {4}"
            ::= 6347
          vlDliBoardCommError TRAP-TYPE
            ENTERPRISE  voiceLoggerCapture
            VARIABLES   { trapSeverity,
						  trapVLModuleName,
						  trapVLModuleStatus,
            			  trapHostTime,
            			  trapBoardNumber}
            DESCRIPTION
                    "Internal Problem In Interface Board [DLI]. Trap Severity = {1}, VL Module Name = {2}, VL Module Status = {3}, Trap Host Time = {4}, Board Number = {5}"
            ::= 6348
          vlDliChannelError TRAP-TYPE
            ENTERPRISE  voiceLoggerCapture
            VARIABLES   { trapSeverity,
						  trapVLModuleName,
						  trapVLModuleStatus,
            			  trapHostTime,
            			  trapBoardNumber}
            DESCRIPTION
                    "Line Problem In Interface Board [DLI]. Trap Severity = {1}, VL Module Name = {2}, VL Module Status = {3}, Trap Host Time = {4}, Board Number = {5}"
            ::= 6349
          vlLafDspCommError TRAP-TYPE
            ENTERPRISE  voiceLoggerCapture
            VARIABLES   { trapSeverity,
						  trapVLModuleName,
						  trapVLModuleStatus,
            			  trapHostTime,
            			  trapBoardNumber}
            DESCRIPTION
                    "Dsp Problem In Playback Board [LAF]. Trap Severity = {1}, VL Module Name = {2}, VL Module Status = {3}, Trap Host Time = {4}, Board Number = {5}"
            ::= 6350
          vlLafFirmwareLoadError TRAP-TYPE
            ENTERPRISE  voiceLoggerCapture
            VARIABLES   { trapSeverity,
						  trapVLModuleName,
						  trapVLModuleStatus,
            			  trapHostTime,
            			  trapBoardNumber}
            DESCRIPTION
                    "Dsp Problem In Playback Board [LAF]. Trap Severity = {1}, VL Module Name = {2}, VL Module Status = {3}, Trap Host Time = {4}, Board Number = {5}"
            ::= 6351
          vlLafinitFailed TRAP-TYPE
            ENTERPRISE  voiceLoggerCapture
            VARIABLES   { trapSeverity,
						  trapVLModuleName,
						  trapVLModuleStatus,
            			  trapHostTime,
            			  trapBoardNumber}
            DESCRIPTION
                    "Internal Problem In Playback Board [LAF]. Trap Severity = {1}, VL Module Name = {2}, VL Module Status = {3}, Trap Host Time = {4}, Board Number = {5}"
            ::= 6352
          vlLafConfigError TRAP-TYPE
            ENTERPRISE  voiceLoggerCapture
            VARIABLES   { trapSeverity,
						  trapVLModuleName,
						  trapVLModuleStatus,
            			  trapHostTime,
            			  trapBoardNumber}
            DESCRIPTION
                    "Internal Problem In Playback Board [LAF]. Trap Severity = {1}, VL Module Name = {2}, VL Module Status = {3}, Trap Host Time = {4}, Board Number = {5}"
            ::= 6353
          vlLafInvalidTime TRAP-TYPE
            ENTERPRISE  voiceLoggerCapture
            VARIABLES   { trapSeverity,
						  trapVLModuleName,
						  trapVLModuleStatus,
            			  trapHostTime,
            			  trapBoardNumber}
            DESCRIPTION
                    "Internal Problem In Playback Board [LAF]. Trap Severity = {1}, VL Module Name = {2}, VL Module Status = {3}, Trap Host Time = {4}, Board Number = {5}"
            ::= 6354
          vlLafLostSynch TRAP-TYPE
            ENTERPRISE  voiceLoggerCapture
            VARIABLES   { trapSeverity,
						  trapVLModuleName,
						  trapVLModuleStatus,
            			  trapHostTime,
            			  trapBoardNumber}
            DESCRIPTION
                    "Internal Problem In Playback Board [LAF]. Trap Severity = {1}, VL Module Name = {2}, VL Module Status = {3}, Trap Host Time = {4}, Board Number = {5}"
            ::= 6355
          vlLafPowerProblem TRAP-TYPE
            ENTERPRISE  voiceLoggerCapture
            VARIABLES   { trapSeverity,
						  trapVLModuleName,
						  trapVLModuleStatus,
            			  trapHostTime,
            			  trapBoardNumber}
            DESCRIPTION
                    "Internal Problem In Playback Board [LAF]. Trap Severity = {1}, VL Module Name = {2}, VL Module Status = {3}, Trap Host Time = {4}, Board Number = {5}"
            ::= 6356
          vlLafMirrorFault TRAP-TYPE
            ENTERPRISE  voiceLoggerCapture
            VARIABLES   { trapSeverity,
						  trapVLModuleName,
						  trapVLModuleStatus,
            			  trapHostTime,
            			  trapBoardNumber}
            DESCRIPTION
                    "Internal Problem In Playback Board [LAF]. Trap Severity = {1}, VL Module Name = {2}, VL Module Status = {3}, Trap Host Time = {4}, Board Number = {5}"
            ::= 6357
          vlAdif3InitFailed-Dsp TRAP-TYPE
            ENTERPRISE  voiceLoggerCapture
            VARIABLES   { trapSeverity,
						  trapVLModuleName,
						  trapVLModuleStatus,
            			  trapHostTime,
            			  trapBoardNumber,
						  trapDspNumber}
            DESCRIPTION
                    "Dsp Problem In Recording Board [ADIF3]. Trap Severity = {1}, VL Module Name = {2}, VL Module Status = {3}, Trap Host Time = {4}, Board Number = {5}, DSP Number = {6}"
            ::= 6358
          vlAdif3InitFailed-timing TRAP-TYPE
            ENTERPRISE  voiceLoggerCapture
            VARIABLES   { trapSeverity,
						  trapVLModuleName,
						  trapVLModuleStatus,
            			  trapHostTime,
            			  trapBoardNumber}
            DESCRIPTION
                    "Internal Problem In Recording Board [ADIF3]. Trap Severity = {1}, VL Module Name = {2}, VL Module Status = {3}, Trap Host Time = {4}, Board Number = {5}"
            ::= 6359
          vlAdif3InitFailed-ADPCM TRAP-TYPE
            ENTERPRISE  voiceLoggerCapture
            VARIABLES   { trapSeverity,
						  trapVLModuleName,
						  trapVLModuleStatus,
            			  trapHostTime,
            			  trapBoardNumber}
            DESCRIPTION
                    "Internal Problem In Recording Board [ADIF3]. Trap Severity = {1}, VL Module Name = {2}, VL Module Status = {3}, Trap Host Time = {4}, Board Number = {5}"
            ::= 6360
          vlAdif3InitFailed-HW TRAP-TYPE
            ENTERPRISE  voiceLoggerCapture
            VARIABLES   { trapSeverity,
						  trapVLModuleName,
						  trapVLModuleStatus,
            			  trapHostTime,
            			  trapBoardNumber}
            DESCRIPTION
                    "Internal Problem In Recording Board [ADIF3]. Trap Severity = {1}, VL Module Name = {2}, VL Module Status = {3}, Trap Host Time = {4}, Board Number = {5}"
            ::= 6361
          vlAdif3ExternalClockSynchError TRAP-TYPE
            ENTERPRISE  voiceLoggerCapture
            VARIABLES   { trapSeverity,
						  trapVLModuleName,
						  trapVLModuleStatus,
            			  trapHostTime,
            			  trapBoardNumber}
            DESCRIPTION
                    "Internal Problem In Recording Board [ADIF3]. Trap Severity = {1}, VL Module Name = {2}, VL Module Status = {3}, Trap Host Time = {4}, Board Number = {5}"
            ::= 6362
          vlUdaInitFailed-Dsp TRAP-TYPE
            ENTERPRISE  voiceLoggerCapture
            VARIABLES   { trapSeverity,
						  trapVLModuleName,
						  trapVLModuleStatus,
            			  trapHostTime,
            			  trapBoardNumber,
						  trapDspNumber,
						  trapDaughterBoardNumber}
            DESCRIPTION
                    "Dsp Problem In Algorithms Board [UDA]. Trap Severity = {1}, VL Module Name = {2}, VL Module Status = {3}, Trap Host Time = {4}, Board Number = {5}, DSP Number = {6}, Daughter Board Number = {7}"
            ::= 6363
          vlUdaMatrixInitFailed TRAP-TYPE
            ENTERPRISE  voiceLoggerCapture
            VARIABLES   { trapSeverity,
						  trapVLModuleName,
						  trapVLModuleStatus,
            			  trapHostTime,
            			  trapBoardNumber}
            DESCRIPTION
                    "Internal Problem In Algorithms Board [UDA]. Trap Severity = {1}, VL Module Name = {2}, VL Module Status = {3}, Trap Host Time = {4}, Board Number = {5}"
            ::= 6364
          vlUdaInitBoardFailed TRAP-TYPE
            ENTERPRISE  voiceLoggerCapture
            VARIABLES   { trapSeverity,
						  trapVLModuleName,
						  trapVLModuleStatus,
            			  trapHostTime,
            			  trapBoardNumber}
            DESCRIPTION
                    "Internal Problem In Algorithms Board [UDA]. Trap Severity = {1}, VL Module Name = {2}, VL Module Status = {3}, Trap Host Time = {4}, Board Number = {5}"
            ::= 6365
          vlEtai2InitFailed-Dsp TRAP-TYPE
            ENTERPRISE  voiceLoggerCapture
            VARIABLES   { trapSeverity,
						  trapVLModuleName,
						  trapVLModuleStatus,
            			  trapHostTime,
            			  trapBoardNumber,
						  trapDspNumber}
            DESCRIPTION
                    "Dsp Problem In Interface Board [ETAI2]. Trap Severity = {1}, VL Module Name = {2}, VL Module Status = {3}, Trap Host Time = {4}, Board Number = {5}, DSP Number = {6}"
            ::= 6366
          vlEtai2MatrixInitError TRAP-TYPE
            ENTERPRISE  voiceLoggerCapture
            VARIABLES   { trapSeverity,
						  trapVLModuleName,
						  trapVLModuleStatus,
            			  trapHostTime,
            			  trapBoardNumber}
            DESCRIPTION
                    "Internal Problem In Interface Board [ETAI2]. Trap Severity = {1}, VL Module Name = {2}, VL Module Status = {3}, Trap Host Time = {4}, Board Number = {5}"
            ::= 6367
          vlEtai2InitBoardFailed TRAP-TYPE
            ENTERPRISE  voiceLoggerCapture
            VARIABLES   { trapSeverity,
						  trapVLModuleName,
						  trapVLModuleStatus,
            			  trapHostTime,
            			  trapBoardNumber}
            DESCRIPTION
                    "Internal Problem In Interface Board [ETAI2]. Trap Severity = {1}, VL Module Name = {2}, VL Module Status = {3}, Trap Host Time = {4}, Board Number = {5}"
            ::= 6368
          vlEtai2LineProblem TRAP-TYPE
            ENTERPRISE  voiceLoggerCapture
            VARIABLES   { trapSeverity,
						  trapVLModuleName,
						  trapVLModuleStatus,
            			  trapHostTime,
            			  trapBoardNumber,
						  trapLineNumber,
						  trapLineErrorType,
						  trapLogicalStreamNumber}
            DESCRIPTION
                    "Line Problem In Interface Board [ETAI2]. Trap Severity = {1}, VL Module Name = {2}, VL Module Status = {3}, Trap Host Time = {4}, Board Number = {5}, Line Number = {6}, Error Type = {7}, Logical Stream Number = {8}"
            ::= 6369
          vlBtai2InitFailed-Dsp TRAP-TYPE
            ENTERPRISE  voiceLoggerCapture
            VARIABLES   { trapSeverity,
						  trapVLModuleName,
						  trapVLModuleStatus,
            			  trapHostTime,
            			  trapBoardNumber,
						  trapDspNumber}
            DESCRIPTION
                    "Dsp Problem In Interface Board [BTAI2]. Trap Severity = {1}, VL Module Name = {2}, VL Module Status = {3}, Trap Host Time = {4}, Board Number = {5}, DSP Number = {6}"
            ::= 6370
          vlBtai2MatrixInitError TRAP-TYPE
            ENTERPRISE  voiceLoggerCapture
            VARIABLES   { trapSeverity,
						  trapVLModuleName,
						  trapVLModuleStatus,
            			  trapHostTime,
            			  trapBoardNumber}
            DESCRIPTION
                    "Internal Problem In Algorithms Board [BTAI2]. Trap Severity = {1}, VL Module Name = {2}, VL Module Status = {3}, Trap Host Time = {4}, Board Number = {5}"
            ::= 6371
          vlBtai2InitBoardFailed TRAP-TYPE
            ENTERPRISE  voiceLoggerCapture
            VARIABLES   { trapSeverity,
						  trapVLModuleName,
						  trapVLModuleStatus,
            			  trapHostTime,
            			  trapBoardNumber}
            DESCRIPTION
                    "Internal Problem In Algorithms Board [BTAI2]. Trap Severity = {1}, VL Module Name = {2}, VL Module Status = {3}, Trap Host Time = {4}, Board Number = {5}"
            ::= 6372
          vlBtai2FpgaError TRAP-TYPE
            ENTERPRISE  voiceLoggerCapture
            VARIABLES   { trapSeverity,
						  trapVLModuleName,
						  trapVLModuleStatus,
            			  trapHostTime,
            			  trapBoardNumber}
            DESCRIPTION
                    "Internal Problem In Algorithms Board [BTAI2]. Trap Severity = {1}, VL Module Name = {2}, VL Module Status = {3}, Trap Host Time = {4}, Board Number = {5}"
            ::= 6373
          vlBtai2LineError TRAP-TYPE
            ENTERPRISE  voiceLoggerCapture
            VARIABLES   { trapSeverity,
						  trapVLModuleName,
						  trapVLModuleStatus,
            			  trapHostTime,
            			  trapBoardNumber,
						  trapLineNumber,
						  trapLineErrorType,
						  trapLogicalStreamNumber}
            DESCRIPTION
                    "Line Problem In Interface Board [BTAI2]. Trap Severity = {1}, VL Module Name = {2}, VL Module Status = {3}, Trap Host Time = {4}, Board Number = {5}, Line Number = {6}, Error Type = {7}, Logical Stream Number = {8}"
            ::= 6374
          vlIsac2RightClockError TRAP-TYPE
            ENTERPRISE  voiceLoggerCapture
            VARIABLES   { trapSeverity,
						  trapVLModuleName,
						  trapVLModuleStatus,
            			  trapHostTime,
            			  trapBoardNumber}
            DESCRIPTION
                    "Internal Problem In Interface Board [ISAC2]. Trap Severity = {1}, VL Module Name = {2}, VL Module Status = {3}, Trap Host Time = {4}, Board Number = {5}"
            ::= 6375
          vlIsac2LeftClockError TRAP-TYPE
            ENTERPRISE  voiceLoggerCapture
            VARIABLES   { trapSeverity,
						  trapVLModuleName,
						  trapVLModuleStatus,
            			  trapHostTime,
            			  trapBoardNumber}
            DESCRIPTION
                    "Internal Problem In Interface Board [ISAC2]. Trap Severity = {1}, VL Module Name = {2}, VL Module Status = {3}, Trap Host Time = {4}, Board Number = {5}"
            ::= 6376
          vlIsac2RightFrameSynchError TRAP-TYPE
            ENTERPRISE  voiceLoggerCapture
            VARIABLES   { trapSeverity,
						  trapVLModuleName,
						  trapVLModuleStatus,
            			  trapHostTime,
            			  trapBoardNumber}
            DESCRIPTION
                    "Internal Problem In Interface Board [ISAC2]. Trap Severity = {1}, VL Module Name = {2}, VL Module Status = {3}, Trap Host Time = {4}, Board Number = {5}"
            ::= 6377
          vlIsac2LeftFrameSynchError TRAP-TYPE
            ENTERPRISE  voiceLoggerCapture
            VARIABLES   { trapSeverity,
						  trapVLModuleName,
						  trapVLModuleStatus,
            			  trapHostTime,
            			  trapBoardNumber}
            DESCRIPTION
                    "Internal Problem In Interface Board [ISAC2]. Trap Severity = {1}, VL Module Name = {2}, VL Module Status = {3}, Trap Host Time = {4}, Board Number = {5}"
            ::= 6378
          vlIsac2BoardProblem TRAP-TYPE
            ENTERPRISE  voiceLoggerCapture
            VARIABLES   { trapSeverity,
						  trapVLModuleName,
						  trapVLModuleStatus,
            			  trapHostTime,
            			  trapBoardNumber}
            DESCRIPTION
                    "Internal Problem In Interface Board [ISAC2]. Trap Severity = {1}, VL Module Name = {2}, VL Module Status = {3}, Trap Host Time = {4}, Board Number = {5}"
            ::= 6379
          vlIsac2TestToneProblem TRAP-TYPE
            ENTERPRISE  voiceLoggerCapture
            VARIABLES   { trapSeverity,
						  trapVLModuleName,
						  trapVLModuleStatus,
            			  trapHostTime,
            			  trapBoardNumber,
						  trapDataLineNumber}
            DESCRIPTION
                    "Line Problem In Interface Board [ISAC2]. Trap Severity = {1}, VL Module Name = {2}, VL Module Status = {3}, Trap Host Time = {4}, Board Number = {5}, Data Line Number = {6}"
            ::= 6380
          vlIsac2SystemCriticalError TRAP-TYPE
            ENTERPRISE  voiceLoggerCapture
            VARIABLES   { trapSeverity,
						  trapVLModuleName,
						  trapVLModuleStatus,
            			  trapHostTime,
            			  trapBoardNumber}
            DESCRIPTION
                    "Internal Problem In Interface Board [ISAC2]. Trap Severity = {1}, VL Module Name = {2}, VL Module Status = {3}, Trap Host Time = {4}, Board Number = {5}"
            ::= 6381
          vlLmopRedunPowerProblem TRAP-TYPE
            ENTERPRISE  voiceLoggerCapture
            VARIABLES   { trapSeverity,
						  trapVLModuleName,
						  trapVLModuleStatus,
            			  trapHostTime,
            			  trapBoardNumber}
            DESCRIPTION
                    "Internal Problem In Playback Board [LMOP ]. Trap Severity = {1}, VL Module Name = {2}, VL Module Status = {3}, Trap Host Time = {4}, Board Number = {5}"
            ::= 6382
          vlLmopRedunDiskMirrorProblem TRAP-TYPE
            ENTERPRISE  voiceLoggerCapture
            VARIABLES   { trapSeverity,
						  trapVLModuleName,
						  trapVLModuleStatus,
            			  trapHostTime,
            			  trapBoardNumber}
            DESCRIPTION
                    "Internal Problem In Playback Board [LMOP]. Trap Severity = {1}, VL Module Name = {2}, VL Module Status = {3}, Trap Host Time = {4}, Board Number = {5}"
            ::= 6383
          vlLmopGeneralHWProblem TRAP-TYPE
            ENTERPRISE  voiceLoggerCapture
            VARIABLES   { trapSeverity,
						  trapVLModuleName,
						  trapVLModuleStatus,
            			  trapHostTime,
            			  trapBoardNumber}
            DESCRIPTION
                    "Internal Problem In Playback Board [LMOP]. Trap Severity = {1}, VL Module Name = {2}, VL Module Status = {3}, Trap Host Time = {4}, Board Number = {5}"
            ::= 6384
          vlNati2A3mDspInitProblem TRAP-TYPE
            ENTERPRISE  voiceLoggerCapture
            VARIABLES   { trapSeverity,
						  trapVLModuleName,
						  trapVLModuleStatus,
            			  trapHostTime,
            			  trapBoardNumber,
						  trapDspNumber}
            DESCRIPTION
			"Dsp Problem In Interface Board [NATI2]. Trap Severity = {1}, VL Module Name = {2}, VL Module Status = {3}, Trap Host Time = {4}, Board Number = {5}, Dsp Number = {6}"
            ::= 6385
          vlNati2McvpDspProblem TRAP-TYPE
            ENTERPRISE  voiceLoggerCapture
            VARIABLES   { trapSeverity,
						  trapVLModuleName,
						  trapVLModuleStatus,
            			  trapHostTime,
            			  trapBoardNumber}
            DESCRIPTION
			"Dsp Problem In Interface Board [NATI2]. Trap Severity = {1}, VL Module Name = {2}, VL Module Status = {3}, Trap Host Time = {4}, Board Number = {5}"
            ::= 6386
          vlNati2MatrixInitProblem TRAP-TYPE
            ENTERPRISE  voiceLoggerCapture
            VARIABLES   { trapSeverity,
						  trapVLModuleName,
						  trapVLModuleStatus,
            			  trapHostTime,
            			  trapBoardNumber}
            DESCRIPTION
			"Internal Problem In Interface Board [NATI2]. Trap Severity = {1}, VL Module Name = {2}, VL Module Status = {3}, Trap Host Time = {4}, Board Number = {5}"
            ::= 6387
          vlNati2InitBoardProblem TRAP-TYPE
            ENTERPRISE  voiceLoggerCapture
            VARIABLES   { trapSeverity,
						  trapVLModuleName,
						  trapVLModuleStatus,
            			  trapHostTime,
            			  trapBoardNumber}
            DESCRIPTION
			"Internal Problem In Interface Board [NATI2]. Trap Severity = {1}, VL Module Name = {2}, VL Module Status = {3}, Trap Host Time = {4}, Board Number = {5}"
            ::= 6388
          vlNati2FpgaProblem TRAP-TYPE
            ENTERPRISE  voiceLoggerCapture
            VARIABLES   { trapSeverity,
						  trapVLModuleName,
						  trapVLModuleStatus,
            			  trapHostTime,
            			  trapBoardNumber}
            DESCRIPTION
			"Internal Problem In Interface Board [NATI2]. Trap Severity = {1}, VL Module Name = {2}, VL Module Status = {3}, Trap Host Time = {4}, Board Number = {5}"
            ::= 6389
          vlNati2LineProblem TRAP-TYPE
            ENTERPRISE  voiceLoggerCapture
            VARIABLES   { trapSeverity,
						  trapVLModuleName,
						  trapVLModuleStatus,
            			  trapHostTime,
            			  trapBoardNumber,
						  trapLineNumber,
						  trapLineErrorType,
						  trapLogicalStreamNumber}
            DESCRIPTION
			"Line Problem In Interface Board [NATI2]. Trap Severity = {1}, VL Module Name = {2}, VL Module Status = {3}, Trap Host Time = {4}, Board Number = {5}, Line Number = {6}, Error Type = {7}, Logical Stream Number = {8}"
            ::= 6390
          vlAli4DspInitProblem TRAP-TYPE
            ENTERPRISE  voiceLoggerCapture
            VARIABLES   { trapSeverity,
						  trapVLModuleName,
						  trapVLModuleStatus,
            			  trapHostTime,
            			  trapBoardNumber}
            DESCRIPTION
			"Dsp Problem In Interface Board [ALI4]. Trap Severity = {1}, VL Module Name = {2}, VL Module Status = {3}, Trap Host Time = {4}, Board Number = {5}"
            ::= 6391
          vlAli4MatrixInitProblem TRAP-TYPE
            ENTERPRISE  voiceLoggerCapture
            VARIABLES   { trapSeverity,
						  trapVLModuleName,
						  trapVLModuleStatus,
            			  trapHostTime,
            			  trapBoardNumber}
            DESCRIPTION
			"Internal Problem In Interface Board [ALI4]. Trap Severity = {1}, VL Module Name = {2}, VL Module Status = {3}, Trap Host Time = {4}, Board Number = {5}"
            ::= 6392
          vlAli4CpldProblem TRAP-TYPE
            ENTERPRISE  voiceLoggerCapture
            VARIABLES   { trapSeverity,
						  trapVLModuleName,
						  trapVLModuleStatus,
            			  trapHostTime,
            			  trapBoardNumber}
            DESCRIPTION
			"Internal Problem In Interface Board [ALI4]. Trap Severity = {1}, VL Module Name = {2}, VL Module Status = {3}, Trap Host Time = {4}, Board Number = {5}"
            ::= 6393
          vlAli4InitBoardProblem TRAP-TYPE
            ENTERPRISE  voiceLoggerCapture
            VARIABLES   { trapSeverity,
						  trapVLModuleName,
						  trapVLModuleStatus,
            			  trapHostTime,
            			  trapBoardNumber}
            DESCRIPTION
			"Internal Problem In Interface Board [ALI4]. Trap Severity = {1}, VL Module Name = {2}, VL Module Status = {3}, Trap Host Time = {4}, Board Number = {5}"
            ::= 6394
          vlAli4LineProblem TRAP-TYPE
            ENTERPRISE  voiceLoggerCapture
            VARIABLES   { trapSeverity,
						  trapVLModuleName,
						  trapVLModuleStatus,
            			  trapHostTime,
            			  trapBoardNumber,
						  trapLineNumber,
						  trapLineErrorType,
						  trapLogicalStreamNumber}
            DESCRIPTION
			"Line Problem In Interface Board [ALI4]. Trap Severity = {1}, VL Module Name = {2}, VL Module Status = {3}, Trap Host Time = {4}, Board Number = {5}, Line Number = {6}, Error Type = {7}, Logical Stream Number = {8}"
            ::= 6395
          vlAli4ExtSqlshDisconnected TRAP-TYPE
            ENTERPRISE  voiceLoggerCapture
            VARIABLES   { trapSeverity,
						  trapVLModuleName,
						  trapVLModuleStatus,
            			  trapHostTime,
            			  trapBoardNumber}
            DESCRIPTION
			"External Squelch Disconnected In Interface Board [ALI4]. Trap Severity = {1}, VL Module Name = {2}, VL Module Status = {3}, Trap Host Time = {4}, Board Number = {5}"
            ::= 6396
          vlBsvrNoMediaRetrieval TRAP-TYPE
            ENTERPRISE  voiceLoggerBackup
            VARIABLES   { trapSeverity,
						  trapVLModuleName,
						  trapVLModuleStatus,
            			  trapHostTime,
						  backupInstanceNumber}
            DESCRIPTION
                    "No media inserted in deck for retrieval. Trap Severity = {1}, VL Module Name = {2}, VL Module Status = {3}, Trap Host Time = {4}, Backup Instance Number = {5}"
            ::= 6700
          vlBsvrNoMediaManualArchive TRAP-TYPE
            ENTERPRISE  voiceLoggerBackup
            VARIABLES   { trapSeverity,
						  trapVLModuleName,
						  trapVLModuleStatus,
            			  trapHostTime,
						  backupInstanceNumber}
            DESCRIPTION
                    "No media inserted in deck for manual archiving. Trap Severity = {1}, VL Module Name = {2}, VL Module Status = {3}, Trap Host Time = {4}, Backup Instance Number = {5}"
            ::= 6701
          vlBsvrAutoArchiveSuspend TRAP-TYPE
            ENTERPRISE  voiceLoggerBackup
            VARIABLES   { trapSeverity,
						  trapVLModuleName,
						  trapVLModuleStatus,
            			  trapHostTime,
						  backupInstanceNumber}
            DESCRIPTION
                    "No media inserted in deck. Automatic archiving suspended. Trap Severity = {1}, VL Module Name = {2}, VL Module Status = {3}, Trap Host Time = {4}, Backup Instance Number = {5}"
            ::= 6702
          vlBsvrRetrievalFailed TRAP-TYPE
            ENTERPRISE  voiceLoggerBackup
            VARIABLES   { trapSeverity,
						  trapVLModuleName,
						  trapVLModuleStatus,
            			  trapHostTime,
						  backupInstanceNumber,
						  backupErrorBSRVErrorCode}
            DESCRIPTION
                    "Retrieval failed. Trap Severity = {1}, VL Module Name = {2}, VL Module Status = {3}, Trap Host Time = {4}, Backup Instance Number = {5}, Backup Error Code = {6}"
            ::= 6703
          vlBsvrOverwMediaFailedrite TRAP-TYPE
            ENTERPRISE  voiceLoggerBackup
            VARIABLES   { trapSeverity,
						  trapVLModuleName,
						  trapVLModuleStatus,
            			  trapHostTime,
						  backupInstanceNumber,
						  backupErrorBSRVErrorCode}
            DESCRIPTION
                    "Failed to overwrite media. Media retention period has not expired yet. Trap Severity = {1}, VL Module Name = {2}, VL Module Status = {3}, Trap Host Time = {4}, Backup Instance Number = {5}, Backup Error Code = {6}"
            ::= 6704
          vlDeviceNotResponding TRAP-TYPE
            ENTERPRISE  voiceLoggerBackup
            VARIABLES   { trapSeverity,
						  trapVLModuleName,
						  trapVLModuleStatus,
            			  trapHostTime,
						  backupInstanceNumber,
						  backupErrorBSRVErrorCode,
						  trapBackupConfig,
						  trapBackupDeviceState}
            DESCRIPTION
                    "Media device error. Trap Severity = {1}, VL Module Name = {2}, VL Module Status = {3}, Trap Host Time = {4}, Backup Instance Number = {5}, Backup Error Code = {6}"
            ::= 6705
          vlBsvrNoMediaRecognized TRAP-TYPE
            ENTERPRISE  voiceLoggerBackup
            VARIABLES   { trapSeverity,
						  trapVLModuleName,
						  trapVLModuleStatus,
            			  trapHostTime,
						  backupInstanceNumber,
						  backupErrorBSRVErrorCode,
						  trapBackupConfig}
            DESCRIPTION
                    "Device does not recognize any media. Operation cancelled. Trap Severity = {1}, VL Module Name = {2}, VL Module Status = {3}, Trap Host Time = {4}, Backup Instance Number = {5}, Backup Error Code = {6}"
            ::= 6706
          vlBsvrMediaError TRAP-TYPE
            ENTERPRISE  voiceLoggerBackup
            VARIABLES   { trapSeverity,
						  trapVLModuleName,
						  trapVLModuleStatus,
            			  trapHostTime,
						  backupInstanceNumber,
						  backupErrorBSRVErrorCode,
						  trapBackupConfig,
						  trapBackupDeviceState}
            DESCRIPTION
                    "The device encountered an error on this media. Trap Severity = {1}, VL Module Name = {2}, VL Module Status = {3}, Trap Host Time = {4}, Backup Instance Number = {5}, Backup Error Code = {6}"
            ::= 6707
          vlBsvrMediaWriteProtected TRAP-TYPE
            ENTERPRISE  voiceLoggerBackup
            VARIABLES   { trapSeverity,
						  trapVLModuleName,
						  trapVLModuleStatus,
            			  trapHostTime,
						  backupInstanceNumber}
            DESCRIPTION
                    "Media is write-protected. Trap Severity = {1}, VL Module Name = {2}, VL Module Status = {3}, Trap Host Time = {4}, Backup Instance Number = {5}, Backup Error Code = {6}"
            ::= 6708
          vlBsvrCannotAppend TRAP-TYPE
            ENTERPRISE  voiceLoggerBackup
            VARIABLES   { trapSeverity,
						  trapVLModuleName,
						  trapVLModuleStatus,
            			  trapHostTime,
						  backupInstanceNumber,
						  backupErrorBSRVErrorCode}
            DESCRIPTION
                    "Data cannot be appended to this media. Trap Severity = {1}, VL Module Name = {2}, VL Module Status = {3}, Trap Host Time = {4}, Backup Instance Number = {5}, Backup Error Code = {6}"
            ::= 6709
          vlBsvrNoMediaDataFound TRAP-TYPE
            ENTERPRISE  voiceLoggerBackup
            VARIABLES   { trapSeverity,
						  trapVLModuleName,
						  trapVLModuleStatus,
            			  trapHostTime,
						  backupInstanceNumber}
            DESCRIPTION
                    "No data found on media. Trap Severity = {1}, VL Module Name = {2}, VL Module Status = {3}, Trap Host Time = {4}, Backup Instance Number = {5}"
            ::= 6710
          vlBsvrDeviceOperationFailed TRAP-TYPE
            ENTERPRISE  voiceLoggerBackup
            VARIABLES   { trapSeverity,
						  trapVLModuleName,
						  trapVLModuleStatus,
            			  trapHostTime,
						  backupInstanceNumber,
						  backupErrorBSRVErrorCode,
						  trapBackupConfig,
						  trapBackupDeviceState}
            DESCRIPTION
                    "Media device operation failed. Trap Severity = {1}, VL Module Name = {2}, VL Module Status = {3}, Trap Host Time = {4}, Backup Instance Number = {5}, Backup Error Code = {6}"
            ::= 6711
          vlBsvrRecoveryFailed TRAP-TYPE
            ENTERPRISE  voiceLoggerBackup
            VARIABLES   { trapSeverity,
						  trapVLModuleName,
						  trapVLModuleStatus,
            			  trapHostTime,
						  backupInstanceNumber}
            DESCRIPTION
                    "Recovery process failed. Media is unreadable. Trap Severity = {1}, VL Module Name = {2}, VL Module Status = {3}, Trap Host Time = {4}, Backup Instance Number = {5}"
            ::= 6712
          vlBsvrArchivingFailed TRAP-TYPE
            ENTERPRISE  voiceLoggerBackup
            VARIABLES   { trapSeverity,
						  trapVLModuleName,
						  trapVLModuleStatus,
            			  trapHostTime,
						  backupInstanceNumber,
						  backupErrorBSRVErrorCode}
            DESCRIPTION
                    "Archiving Failed. Failed to copy data from disk to media. Trap Severity = {1}, VL Module Name = {2}, VL Module Status = {3}, Trap Host Time = {4}, Backup Instance Number = {5}, Backup Error Code = {6}"
            ::= 6713
          vlBsvrOverwriteUsageExceeded TRAP-TYPE
            ENTERPRISE  voiceLoggerBackup
            VARIABLES   { trapSeverity,
						  trapVLModuleName,
						  trapVLModuleStatus,
            			  trapHostTime,
						  backupInstanceNumber}
            DESCRIPTION
                    "Cannot overwrite media - overwrite usage is exceeded. Trap Severity = {1}, VL Module Name = {2}, VL Module Status = {3}, Trap Host Time = {4}, Backup Instance Number = {5}"
            ::= 6714
          vlBsvrMediaAccessDenied TRAP-TYPE
            ENTERPRISE  voiceLoggerBackup
            VARIABLES   { trapSeverity,
						  trapVLModuleName,
						  trapVLModuleStatus,
            			  trapHostTime,
						  backupInstanceNumber,
						  trapBackupConfig}
            DESCRIPTION                    
                    "Cannot read media - access authorization is denied. Trap Severity = {1}, VL Module Name = {2}, VL Module Status = {3}, Trap Host Time = {4}, Backup Instance Number = {5}"
            ::= 6715
          vlBsvrDeviceShouldBeCleaned TRAP-TYPE
            ENTERPRISE  voiceLoggerBackup
            VARIABLES   { trapSeverity,
						  trapVLModuleName,
						  trapVLModuleStatus,
            			  trapHostTime,
						  backupInstanceNumber,
						  trapBackupConfig,
						  trapBackupDeviceState}
            DESCRIPTION
                    "Media device should be cleaned. Trap Severity = {1}, VL Module Name = {2}, VL Module Status = {3}, Trap Host Time = {4}, Backup Instance Number = {5}"
            ::= 6716
          vlBsvrConnectRTSFailed TRAP-TYPE
            ENTERPRISE  voiceLoggerBackup
            VARIABLES   { trapSeverity,
						  trapVLModuleName,
						  trapVLModuleStatus,
            			  trapHostTime,
						  backupInstanceNumber,
						  trapBackupConfig,
						  trapBackupDeviceState}
            DESCRIPTION
                    "Failed to connect to RTS. Trap Severity = {1}, VL Module Name = {2}, VL Module Status = {3}, Trap Host Time = {4}, Backup Instance Number = {5}"
            ::= 6717
          vlBsvrAppendFailed-version TRAP-TYPE
            ENTERPRISE  voiceLoggerBackup
            VARIABLES   { trapSeverity,
						  trapVLModuleName,
						  trapVLModuleStatus,
            			  trapHostTime,
						  backupInstanceNumber}
            DESCRIPTION
                    "Data cannot be appended to this media. Media version not compatible with Logger version. Trap Severity = {1}, VL Module Name = {2}, VL Module Status = {3}, Trap Host Time = {4}, Backup Instance Number = {5}"
            ::= 6718
          vlBsvrAutoArchiveSuspended-Retrieval TRAP-TYPE
            ENTERPRISE  voiceLoggerBackup
            VARIABLES   { trapSeverity,
						  trapVLModuleName,
						  trapVLModuleStatus,
            			  trapHostTime,
						  backupInstanceNumber,
						  trapBackupConfig}
            DESCRIPTION
                    "Automatic archiving suspended for retrieval operation. Trap Severity = {1}, VL Module Name = {2}, VL Module Status = {3}, Trap Host Time = {4}, Backup Instance Number = {5}"
            ::= 6719
          vlBsvrAutoArchiveSuspended-Manual TRAP-TYPE
            ENTERPRISE  voiceLoggerBackup
            VARIABLES   { trapSeverity,
						  trapVLModuleName,
						  trapVLModuleStatus,
            			  trapHostTime,
						  backupInstanceNumber,
						  trapBackupConfig}
            DESCRIPTION
                    "Automatic archiving suspended for manual archiving. Trap Severity = {1}, VL Module Name = {2}, VL Module Status = {3}, Trap Host Time = {4}, Backup Instance Number = {5}"
            ::= 6720
          vlBsvrAutoArchiveSuspended-Erase TRAP-TYPE
            ENTERPRISE  voiceLoggerBackup
            VARIABLES   { trapSeverity,
						  trapVLModuleName,
						  trapVLModuleStatus,
            			  trapHostTime,
						  backupInstanceNumber,
						  trapBackupConfig}
            DESCRIPTION
                    "Automatic archiving suspended for erase operation. Trap Severity = {1}, VL Module Name = {2}, VL Module Status = {3}, Trap Host Time = {4}, Backup Instance Number = {5}"
            ::= 6721
          vlBsrvDvdArchiveCompleted TRAP-TYPE
            ENTERPRISE  voiceLoggerBackup
            VARIABLES   { trapSeverity,
						  trapVLModuleName,
						  trapVLModuleStatus,
            			  trapHostTime,
						  backupInstanceNumber}
            DESCRIPTION
                    "Archiving on DVD media completed. Open the logger backup device door and replace the media to continue archiving. Trap Severity = {1}, VL Module Name = {2}, VL Module Status = {3}, Trap Host Time = {4}, Backup Instance Number = {5}"
            ::= 6722
          vlBsrvBackupServerError TRAP-TYPE
            ENTERPRISE  voiceLoggerBackup
            VARIABLES   { trapSeverity,
						  trapVLModuleName,
						  trapVLModuleStatus,
            			  trapHostTime,
						  backupInstanceNumber,
						  trapBackupConfig,
						  trapBackupDeviceState}
            DESCRIPTION
                    "Backup server error. Trap Severity = {1}, VL Module Name = {2}, VL Module Status = {3}, Trap Host Time = {4}, Backup Instance Number = {5}"
            ::= 6723

          
          ----------------------------------------------------
	  -- Database traps (starting at specific trap 7000)

          dbCallsBackupFinished TRAP-TYPE
            ENTERPRISE  databaseUtilities
            VARIABLES   { trapSeverity }
            DESCRIPTION
                    "NICE Database calls Backup finished successfully. Trap Severity = {1}"
            ::= 7001
              
          dbCallsBackupFailed TRAP-TYPE
            ENTERPRISE  databaseUtilities
            VARIABLES   { trapSeverity }
            DESCRIPTION
                    "NICE Database Calls backup has failed. Trap Severity = {1}"
            ::= 7002

          dbAdminBackupFinished TRAP-TYPE
            ENTERPRISE  databaseUtilities
            VARIABLES   { trapSeverity }
            DESCRIPTION
                    "NICE Database admin Backup finished successfully. Trap Severity = {1}"
            ::= 7003
              
          dbAdminBackupFailed TRAP-TYPE
            ENTERPRISE  databaseUtilities
            VARIABLES   { trapSeverity }
            DESCRIPTION
                    "NICE Database admin backup has failed. Trap Severity = {1}"
            ::= 7004

          dbAuditBackupFinished TRAP-TYPE
            ENTERPRISE  databaseUtilities
            VARIABLES   { trapSeverity }
            DESCRIPTION
                    "NICE Database audit Backup finished successfully. Trap Severity = {1}"
            ::= 7005
              
          dbAuditBackupFailed TRAP-TYPE
            ENTERPRISE  databaseUtilities
            VARIABLES   { trapSeverity }
            DESCRIPTION
                    "NICE Database audit backup has failed. Trap Severity = {1}"
            ::= 7006

          dbReindexJobFinished TRAP-TYPE
            ENTERPRISE  databaseUtilities
            VARIABLES   { trapSeverity }
            DESCRIPTION
                    "NICE Database Reindex job finished successfully. Trap Severity = {1}"
            ::= 7007

          dbReindexJobFailed TRAP-TYPE
            ENTERPRISE  databaseUtilities
            VARIABLES   { trapSeverity }
            DESCRIPTION
                    "NICE Database Reindex job has failed. Trap Severity = {1}"
            ::= 7008

          dbAuditAutoDeletionFinished TRAP-TYPE
            ENTERPRISE  databaseUtilities
            VARIABLES   { trapSeverity }
            DESCRIPTION
                    "NICE Database AuditAutoDeletion job finished successfully. Trap Severity = {1}"
            ::= 7009

          dbAuditAutoDeletionFailed TRAP-TYPE
            ENTERPRISE  databaseUtilities
            VARIABLES   { trapSeverity }
            DESCRIPTION
                    "NICE Database AuditAutoDeletion job has failed. Trap Severity = {1}"
            ::= 7010

          dbCallsDbSpaceIsLow TRAP-TYPE
            ENTERPRISE  databaseUtilities
            VARIABLES   { trapSeverity }
            DESCRIPTION
                    "NICE Database Calls database free space is low. Trap Severity = {1}"
            ::= 7011

          dbCallsDbFull TRAP-TYPE
            ENTERPRISE  databaseUtilities
            VARIABLES   { trapSeverity }
            DESCRIPTION
                    "NICE Database Calls database is full. Trap Severity = {1}"
            ::= 7012

          dbAuditDbSpaceIsLow TRAP-TYPE
            ENTERPRISE  databaseUtilities
            VARIABLES   { trapSeverity }
            DESCRIPTION
                    "NICE Database Audit database free space is low. Trap Severity = {1}"
            ::= 7013

          dbAuditDbFull TRAP-TYPE
            ENTERPRISE  databaseUtilities
            VARIABLES   { trapSeverity }
            DESCRIPTION
                    "NICE Database Audit database is full. Trap Severity = {1}"
            ::= 7014

          dbAdminDbSpaceIsLow TRAP-TYPE
            ENTERPRISE  databaseUtilities
            VARIABLES   { trapSeverity }
            DESCRIPTION
                    "NICE Database Administrative database free space is low. Trap Severity = {1}"
            ::= 7015

          dbAdminDbFull TRAP-TYPE
            ENTERPRISE  databaseUtilities
            VARIABLES   { trapSeverity }
            DESCRIPTION
                    "NICE Database Administrative database is full. Trap Severity = {1}"
            ::= 7016

          dbInserterMissingCalls TRAP-TYPE
            ENTERPRISE  databaseUtilities
            VARIABLES   { trapSeverity }
            DESCRIPTION
                    "NICE Database Inserter has inserted missing calls into the calls database. Trap Severity = {1}"
            ::= 7017

          dbReplicationFailed TRAP-TYPE
            ENTERPRISE  databaseUtilities
            VARIABLES   { trapSeverity }
            DESCRIPTION
                    "NICE Database Replication has failed. Trap Severity = {1}"
            ::= 7018          
            
          dbRuleBackupFinished TRAP-TYPE
            ENTERPRISE  databaseUtilities
            VARIABLES   { trapSeverity }
            DESCRIPTION
                    "NICE Database Rule backup has finished succesfully. Trap Severity = {1}"
            ::= 7019

          dbRuleBackupFailed TRAP-TYPE
            ENTERPRISE  databaseUtilities
            VARIABLES   { trapSeverity }
            DESCRIPTION
                    "NICE Database Rule backup failed. Trap Severity = {1}"
            ::= 7020

          dbMsdbBackupFinished TRAP-TYPE
            ENTERPRISE  databaseUtilities
            VARIABLES   { trapSeverity }
            DESCRIPTION
                    "Database Msdb backup has finished succesfully. Trap Severity = {1}"
            ::= 7021

          dbMsdbBackupFailed TRAP-TYPE
            ENTERPRISE  databaseUtilities
            VARIABLES   { trapSeverity }
            DESCRIPTION
                    "Database Msdb backup has failed. Trap Severity = {1}"
            ::= 7022

          dbMasterBackupFinished TRAP-TYPE
            ENTERPRISE  databaseUtilities
            VARIABLES   { trapSeverity }
            DESCRIPTION
                    "Database Master backup has finished succesfully. Trap Severity = {1}"
            ::= 7023

          dbMasterBackupFailed TRAP-TYPE
            ENTERPRISE  databaseUtilities
            VARIABLES   { trapSeverity }
            DESCRIPTION
                    "Database Master backup has failed. Trap Severity = {1}"
            ::= 7024

          dbRuleDBFull TRAP-TYPE
            ENTERPRISE  databaseUtilities
            VARIABLES   { trapSeverity }
            DESCRIPTION
                    "NICE Database Rule database is full. Trap Severity = {1}"
            ::= 7025

          dbRuleDBSpaceIsLow TRAP-TYPE
            ENTERPRISE  databaseUtilities
            VARIABLES   { trapSeverity }
            DESCRIPTION
                    "NICE Database Rule database free space is low. Trap Severity = {1}"
            ::= 7026

          --------------------------------------------------------------------
		  -- CTI Events Database Server traps (starting at specific trap 8000)

          ctiDBServerIsUp TRAP-TYPE
            ENTERPRISE  ctiEventsDbServer
            VARIABLES   { trapSeverity, 
						  ctiDBServerName,
						  ctiDBServerStatus,
						  trapHostTime
 }
            DESCRIPTION
                    "CTI DB Server Is Up. Trap Severity = {1}, CTI DB Server Name = {2}, CTI DB Server Status = {3}, Trap Host Time = {4}"
            ::= 8001
            
          ctiDBServerIsDown TRAP-TYPE
            ENTERPRISE  ctiEventsDbServer
            VARIABLES   { trapSeverity, 
						  ctiDBServerName,
						  ctiDBServerStatus,
						  trapHostTime
 }
            DESCRIPTION
                    "CTI DB Server Is Down. Trap Severity = {1}, CTI DB Server Name = {2}, CTI DB Server Status = {3}, Trap Host Time = {4}"
            ::= 8002
                      
          ctiDBServerIsNotInitializedProperly TRAP-TYPE
            ENTERPRISE  ctiEventsDbServer
            VARIABLES   { trapSeverity, 
						  ctiDBServerName,
						  ctiDBServerStatus,
						  trapHostTime
 }
            DESCRIPTION
                    "CTI DB Server Is Not Initialized Properly. Trap Severity = {1}, CTI DB Server Name = {2}, CTI DB Server Status = {3}, Trap Host Time = {4}"
            ::= 8003                                    

          ctiDBServerIsInitializedProperly TRAP-TYPE
            ENTERPRISE  ctiEventsDbServer
            VARIABLES   { trapSeverity, 
						  ctiDBServerName,
						  ctiDBServerStatus,
						  trapHostTime
 }
            DESCRIPTION
                    "CTI DB Server Is Initialized Properly. Trap Severity = {1}, CTI DB Server Name = {2}, CTI DB Server Status = {3}, Trap Host Time = {4}"
            ::= 8004                                   

          ctiDBSpaceIsFull TRAP-TYPE
            ENTERPRISE  ctiEventsDbServer
            VARIABLES   { trapSeverity, 
						  ctiDBServerName,
						  ctiDBServerStatus,
						  trapHostTime
,
						  trapDBErrorCode }
            DESCRIPTION
                    "CTI DB Space Is Full. Trap Severity = {1}, CTI DB Server Name = {2}, CTI DB Server Status = {3}, Trap Host Time = {4}, DB Error Code = {5}"
            ::= 8005                                

          ctiDBSpaceIsOK TRAP-TYPE
            ENTERPRISE  ctiEventsDbServer
            VARIABLES   { trapSeverity, 
						  ctiDBServerName,
						  ctiDBServerStatus,
						  trapHostTime
 }
            DESCRIPTION
                    "CTI DB Space Is OK. Trap Severity = {1}, CTI DB Server Name = {2}, CTI DB Server Status = {3}, Trap Host Time = {4}"
            ::= 8006                

          ctiDBLogSpaceIsFull TRAP-TYPE
            ENTERPRISE  ctiEventsDbServer
            VARIABLES   { trapSeverity, 
						  ctiDBServerName,
						  ctiDBServerStatus,
						  trapHostTime
,
						  trapDBErrorCode }
            DESCRIPTION
                    "CTI DB Log Space Is Full. Trap Severity = {1}, CTI DB Server Name = {2}, CTI DB Server Status = {3}, Trap Host Time = {4}, DB Error Code = {5}"
            ::= 8007                                

          ctiDBLogSpaceIsOK TRAP-TYPE
            ENTERPRISE  ctiEventsDbServer
            VARIABLES   { trapSeverity, 
						  ctiDBServerName,
						  ctiDBServerStatus,
						  trapHostTime
 }
            DESCRIPTION
                    "CTI DB Log Space Is OK. Trap Severity = {1}, CTI DB Server Name = {2}, CTI DB Server Status = {3}, Trap Host Time = {4}"
            ::= 8008        

          ctiConnectionToDBIsOK TRAP-TYPE
            ENTERPRISE  ctiEventsDbServer
            VARIABLES   { trapSeverity, 
						  ctiDBServerName,
						  ctiDBServerStatus,
						  trapHostTime
 }
            DESCRIPTION
                    "Connection to the CTI DB Is OK. Trap Severity = {1}, CTI DB Server Name = {2}, CTI DB Server Status = {3}, Trap Host Time = {4}"
            ::= 8009 
            
          ctiFailedConnectToDB TRAP-TYPE
            ENTERPRISE  ctiEventsDbServer
            VARIABLES   { trapSeverity, 
						  ctiDBServerName,
						  ctiDBServerStatus,
						  trapHostTime,
						  trapDBErrorCode
 }
            DESCRIPTION
                    "Failed to connect to the CTI DB. Trap Severity = {1}, CTI DB Server Name = {2}, CTI DB Server Status = {3}, Trap Host Time = {4}, DB Error Code = {5}"
            ::= 8010 
            
          ctiMissingLookUpTable TRAP-TYPE
            ENTERPRISE  ctiEventsDbServer
            VARIABLES   { trapSeverity, 
						  ctiDBServerName,
						  ctiDBServerStatus,
						  trapHostTime,
						  trapSQLTableName
 }
            DESCRIPTION
                    "CTI DB Is Missing A LookUp Table. Trap Severity = {1}, CTI DB Server Name = {2}, CTI DB Server Status = {3}, Trap Host Time = {4}, SQL Table Name = {5}"
            ::= 8011 
            
          ctiFailedToInsertCTIEvent TRAP-TYPE
            ENTERPRISE  ctiEventsDbServer
            VARIABLES   { trapSeverity, 
						  ctiDBServerName,
						  ctiDBServerStatus,
						  trapHostTime,
						  trapDBErrorCode
 }
            DESCRIPTION
                    "Failed To Insert CTI Event Into CTI DB. Trap Severity = {1}, CTI DB Server Name = {2}, CTI DB Server Status = {3}, Trap Host Time = {4}, DB Error Code = {5}"
            ::= 8012      

          ctiDBRetentionFailure TRAP-TYPE
            ENTERPRISE  ctiEventsDbServer
            VARIABLES   { trapSeverity, 
						  ctiDBServerName,
						  ctiDBServerStatus,
						  trapHostTime,
						  trapDBErrorCode
 }
            DESCRIPTION
                    "Failed To Perform Retention On The CTI DB. Trap Severity = {1}, CTI DB Server Name = {2}, CTI DB Server Status = {3}, Trap Host Time = {4}, DB Error Code = {5}"
            ::= 8013      

          ctiInvalidMessageReceived TRAP-TYPE
            ENTERPRISE  ctiEventsDbServer
            VARIABLES   { trapSeverity, 
						  ctiDBServerName,
						  ctiDBServerStatus,
						  trapHostTime }
            DESCRIPTION
                    "Invalid CTI Event Received. Trap Severity = {1}, CTI DB Server Name = {2}, CTI DB Server Status = {3}, Trap Host Time = {4}"
            ::= 8014      

		  -- End CTI Events Database Server traps
		  ----------------------------------------------------

          ----------------------------------------------------
	  -- System Tools subtree definition

          systemTools OBJECT IDENTIFIER   ::= { niceMib-2 7 }  
          
          recordingsDiagnostic OBJECT IDENTIFIER   ::= { systemTools 1 }
          
		  rdName OBJECT-TYPE
              SYNTAX  DisplayString
              ACCESS  read-only
              STATUS  mandatory
              DESCRIPTION
                      "The application name."
              ::= { recordingsDiagnostic 1 }

          rdStatus OBJECT-TYPE
              SYNTAX  SeverityType
              ACCESS  read-only
              STATUS  mandatory
              DESCRIPTION 
                      "The application status."
              ::= { recordingsDiagnostic 2 }  
              
          rdVersion OBJECT-TYPE
              SYNTAX  DisplayString
              ACCESS  read-only
              STATUS  mandatory
              DESCRIPTION 
                      "The application version."
              ::= { recordingsDiagnostic 3 }
              
          rdServerName OBJECT-TYPE
              SYNTAX  DisplayString
              ACCESS  read-only
              STATUS  mandatory
              DESCRIPTION 
                      "The name of the server running the application."
              ::= { recordingsDiagnostic 4 }  
                      
              
          rdServerAddress OBJECT-TYPE
              SYNTAX  DisplayString
              ACCESS  read-only
              STATUS  mandatory
              DESCRIPTION 
                      "The address of the server running the application."
              ::= { recordingsDiagnostic 5 }           
              
          rdCLSConnectionTable OBJECT-TYPE
              SYNTAX  SEQUENCE OF RdCLSConnectionEntry
              ACCESS  not-accessible
              STATUS  mandatory
              DESCRIPTION
                      "A list of all CLS Connection exist in the application."
              ::= { recordingsDiagnostic 6 }

		  rdCLSConnectionEntry OBJECT-TYPE
              SYNTAX  RdCLSConnectionEntry
              ACCESS  not-accessible
              STATUS  mandatory
              DESCRIPTION
                      "A CLS Connection entry."
              INDEX   { rdCLSConnectionTableIndex }
              ::= { rdCLSConnectionTable 1 }

          RdCLSConnectionEntry ::=
              SEQUENCE 
              {
					rdCLSID 
						INTEGER,
					rdCLSIpAddress
						DisplayString,
					rdCLSConnectionTableIndex
						INTEGER 
              }   
              
          rdCLSID OBJECT-TYPE
              SYNTAX  INTEGER
              ACCESS  read-only
              STATUS  mandatory
              DESCRIPTION 
                      "The CLS ID."
              ::= { rdCLSConnectionEntry 1 }
         
          rdCLSIpAddress OBJECT-TYPE
              SYNTAX  DisplayString
              ACCESS  read-only
              STATUS  mandatory
              DESCRIPTION 
                      "The CLS Ip address."
              ::= { rdCLSConnectionEntry 2 }
        
                           
          rdCLSConnectionTableIndex OBJECT-TYPE
              SYNTAX  INTEGER
              ACCESS  read-only
              STATUS  mandatory
              DESCRIPTION 
                      "The table index."
              ::= { rdCLSConnectionEntry 3}
              
          rdLoggerConnectionTable OBJECT-TYPE
              SYNTAX  SEQUENCE OF RdLoggerConnectionEntry
              ACCESS  not-accessible
              STATUS  mandatory
              DESCRIPTION
                      "A list of all logger Connections exist in the application."
              ::= { recordingsDiagnostic 7 }

		  rdLoggerConnectionEntry OBJECT-TYPE
              SYNTAX  RdLoggerConnectionEntry
              ACCESS  not-accessible
              STATUS  mandatory
              DESCRIPTION
                      "A logger Connection entry."
              INDEX   { rdLoggerConnectionTableIndex }
              ::= { rdLoggerConnectionTable 1 }

          RdLoggerConnectionEntry ::=
              SEQUENCE 
              {
					rdLoggerID 
						INTEGER,
					rdLoggerIpAddress
						DisplayString,
					rdLoggerSpareloggerID
						INTEGER,
					rdLoggerConnectionTableIndex
						INTEGER 
              }  
              
          rdLoggerID OBJECT-TYPE
              SYNTAX  INTEGER
              ACCESS  read-only
              STATUS  mandatory
              DESCRIPTION 
                      "The logger ID."
              ::= { rdLoggerConnectionEntry 1 }
         
          rdLoggerIpAddress OBJECT-TYPE
              SYNTAX  DisplayString
              ACCESS  read-only
              STATUS  mandatory
              DESCRIPTION 
                      "The logger Ip address."
              ::= { rdLoggerConnectionEntry 2 }
          
          rdLoggerSpareloggerID OBJECT-TYPE
              SYNTAX  INTEGER
              ACCESS  read-only
              STATUS  mandatory
              DESCRIPTION 
                      "The Spare logger ID."
              ::= { rdLoggerConnectionEntry 3 }
                             
          rdLoggerConnectionTableIndex OBJECT-TYPE
              SYNTAX  INTEGER
              ACCESS  read-only
              STATUS  mandatory
              DESCRIPTION 
                      "The table index."
              ::= { rdLoggerConnectionEntry 4 }
              
          rdTasksTable OBJECT-TYPE
              SYNTAX  SEQUENCE OF RdTasksEntry
              ACCESS  not-accessible
              STATUS  mandatory
              DESCRIPTION
                      "A list of recordings diagnostics tasks."
              ::= { recordingsDiagnostic 8 }

		  rdTasksEntry OBJECT-TYPE
              SYNTAX  RdTasksEntry
              ACCESS  not-accessible
              STATUS  mandatory
              DESCRIPTION
                      "A recordings diagnostics task entry."
              INDEX   { rdTasksTableIndex }
              ::= { rdTasksTable 1 }

          RdTasksEntry ::=
              SEQUENCE {
					rdTaskType
						RdTaskType,
					rdTaskName
						DisplayString,
					rdTaskDescription
						DisplayString,
					rdTaskCreationTime
						HostLocalTime,
					rdTaskStartTime
						HostLocalTime,
					rdTaskQuery
						DisplayString,
					rdTaskExecElements
						INTEGER,
					rdTaskExecFailElements
						INTEGER,
					rdTaskCurrentState
						TaskState,
					rdTaskLastError
						DisplayString,
					rdTasksTableIndex
						INTEGER
					}

         rdTaskType OBJECT-TYPE
              SYNTAX  RdTaskType
              ACCESS  read-only
              STATUS  mandatory
              DESCRIPTION
                      "The Type of the task executed." 
              ::= { rdTasksEntry 1 }

		 
		 rdTaskName OBJECT-TYPE
              SYNTAX  DisplayString
              ACCESS  read-only
              STATUS  mandatory
              DESCRIPTION
                      "The name of the task." 
              ::= { rdTasksEntry 2 }


	 	rdTaskDescription OBJECT-TYPE
              SYNTAX  DisplayString
              ACCESS  read-only
              STATUS  mandatory
              DESCRIPTION
                      "A short description of the task." 
              ::= { rdTasksEntry 3 }

		rdTaskCreationTime OBJECT-TYPE
              SYNTAX  HostLocalTime
              ACCESS  read-only
              STATUS  mandatory
              DESCRIPTION
                      "The time when the task was created." 
              ::= { rdTasksEntry 4 }
              
		rdTaskStartTime OBJECT-TYPE
              SYNTAX  HostLocalTime
              ACCESS  read-only
              STATUS  mandatory
              DESCRIPTION
                      "The time when the task started." 
              ::= { rdTasksEntry 5 }

		rdTaskQuery OBJECT-TYPE
              SYNTAX  DisplayString
              ACCESS  read-only
              STATUS  mandatory
              DESCRIPTION
                      "The SQL query used by the task ." 
              ::= { rdTasksEntry 6 } 


		rdTaskExecElements OBJECT-TYPE
              SYNTAX  INTEGER
              ACCESS  read-only
              STATUS  mandatory
              DESCRIPTION
                      "The number of processed elements." 
              ::= { rdTasksEntry 7 } 
                                          

		rdTaskExecFailElements OBJECT-TYPE
              SYNTAX  INTEGER
              ACCESS  read-only
              STATUS  mandatory
              DESCRIPTION
                      "The number of processed elements that failed." 
              ::= { rdTasksEntry 8 } 
                                                       
		rdTaskCurrentState OBJECT-TYPE
              SYNTAX  TaskState
              ACCESS  read-only
              STATUS  mandatory
              DESCRIPTION
                      "The current task State." 
              ::= { rdTasksEntry 9 } 
             
		rdTaskLastError OBJECT-TYPE
              SYNTAX  DisplayString
              ACCESS  read-only
              STATUS  mandatory
              DESCRIPTION
                      "The last error occured while executing the task." 
              ::= { rdTasksEntry 10 } 
        
        rdTasksTableIndex OBJECT-TYPE
              SYNTAX  INTEGER
              ACCESS  read-only
              STATUS  mandatory
              DESCRIPTION 
                      "The table index."
              ::= { rdTasksEntry 11 }
              
        rdCLSPendingErrorsTable OBJECT-TYPE
              SYNTAX  SEQUENCE OF RdCLSPendingErrorsEntry
              ACCESS  not-accessible
              STATUS  mandatory
              DESCRIPTION
                      "A list of CLS pending errors for the recordings diagnostics."
              ::= { recordingsDiagnostic 9 }

          rdCLSPendingErrorsEntry OBJECT-TYPE
              SYNTAX  RdCLSPendingErrorsEntry
              ACCESS  not-accessible
              STATUS  mandatory
              DESCRIPTION
                      "A Recording Diagnostics CLS pending error entry."
              INDEX   { rdCLSPendingErrorsTableIndex }
              ::= { rdCLSPendingErrorsTable 1 }

          RdCLSPendingErrorsEntry ::=
              SEQUENCE 
              {
					rdCLSErrorType
						RdErrorType,
					rdCLSErrorReflectedStatus
						SeverityType, 
					rdCLSExtendedErrorinformation
						DisplayString,
					rdCLSErrorCLSTableIndex
						INTEGER,
					rdCLSPendingErrorsTableIndex
						INTEGER
              }
          
          rdCLSErrorType OBJECT-TYPE
              SYNTAX  RdErrorType
              ACCESS  read-only
              STATUS  mandatory
              DESCRIPTION 
                      "The error type."
              ::= { rdCLSPendingErrorsEntry 1 }

           rdCLSErrorReflectedStatus OBJECT-TYPE
              SYNTAX  SeverityType
              ACCESS  read-only
              STATUS  mandatory
              DESCRIPTION 
                      "The error's severity type."
              ::= { rdCLSPendingErrorsEntry 2 } 
              
           rdCLSExtendedErrorinformation OBJECT-TYPE
           	  SYNTAX  DisplayString
              ACCESS  read-only
              STATUS  mandatory
              DESCRIPTION 
                      "The error's extanded information ."
              ::= { rdCLSPendingErrorsEntry 3 } 	
              
           rdCLSErrorCLSTableIndex OBJECT-TYPE
              SYNTAX  INTEGER
              ACCESS  read-only
              STATUS  mandatory
              DESCRIPTION 
                      "The index of the Errornours CLS in the CLS connection table."
              ::= { rdCLSPendingErrorsEntry 4 }

           rdCLSPendingErrorsTableIndex OBJECT-TYPE
              SYNTAX  INTEGER
              ACCESS  read-only
              STATUS  mandatory
              DESCRIPTION 
                      "The first table index."
              ::= { rdCLSPendingErrorsEntry 5 }
              
        rdLoggerPendingErrorsTable OBJECT-TYPE
              SYNTAX  SEQUENCE OF RdLoggerPendingErrorsEntry
              ACCESS  not-accessible
              STATUS  mandatory
              DESCRIPTION
                      "A list of Logger pending errors for the recordings diagnostics."
              ::= { recordingsDiagnostic 10 }

          rdLoggerPendingErrorsEntry OBJECT-TYPE
              SYNTAX  RdLoggerPendingErrorsEntry
              ACCESS  not-accessible
              STATUS  mandatory
              DESCRIPTION
                      "A Recording Diagnostics Logger pending error entry."
              INDEX   { rdLoggerPendingErrorsTableIndex }
              ::= { rdLoggerPendingErrorsTable 1 }

          RdLoggerPendingErrorsEntry ::=
              SEQUENCE 
              {
					rdLoggerErrorType
						RdErrorType,
					rdLoggerErrorReflectedStatus
						SeverityType, 
					rdLoggerExtendedErrorinformation
						DisplayString,
					rdLoggerErrorLoggerTableIndex
						INTEGER,
					rdLoggerPendingErrorsTableIndex
						INTEGER
              }
          
          rdLoggerErrorType OBJECT-TYPE
              SYNTAX  RdErrorType
              ACCESS  read-only
              STATUS  mandatory
              DESCRIPTION 
                      "The error type."
              ::= { rdLoggerPendingErrorsEntry 1 }

           rdLoggerErrorReflectedStatus OBJECT-TYPE
              SYNTAX  SeverityType
              ACCESS  read-only
              STATUS  mandatory
              DESCRIPTION 
                      "The error's severity type."
              ::= { rdLoggerPendingErrorsEntry 2 } 
              
           rdLoggerExtendedErrorinformation OBJECT-TYPE
           	  SYNTAX  DisplayString
              ACCESS  read-only
              STATUS  mandatory
              DESCRIPTION 
                      "The error's extanded information ."
              ::= { rdLoggerPendingErrorsEntry 3 } 	
              
           rdLoggerErrorLoggerTableIndex OBJECT-TYPE
              SYNTAX  INTEGER
              ACCESS  read-only
              STATUS  mandatory
              DESCRIPTION 
                      "The index of the Errornours Logger in the Logger connection table."
              ::= { rdLoggerPendingErrorsEntry 4 }

           rdLoggerPendingErrorsTableIndex OBJECT-TYPE
              SYNTAX  INTEGER
              ACCESS  read-only
              STATUS  mandatory
              DESCRIPTION 
                      "The first table index."
              ::= { rdLoggerPendingErrorsEntry 5 }              

----------------------------------------------------
	  -- Recording diagnostics traps (starting at specific trap 8000)   
	             
	       rdExceptionWhileProcessing TRAP-TYPE
              ENTERPRISE  recordingsDiagnostic
              VARIABLES   {trapSeverity,
              			   rdName,	 
              			   rdStatus,
            			   trapHostTime}
              DESCRIPTION
                    "Recordings Diagnostics encountered an exception while processing. Trap Severity = {1}, Application Name = {2}, Application Status = {3}, Trap Host Time = {4}"
              ::=  8000
              
           rdApplicationFailedToInitialize TRAP-TYPE
              ENTERPRISE  recordingsDiagnostic
              VARIABLES   {trapSeverity,
              			   rdName,	 
              			   rdStatus,
            			   trapHostTime}
              DESCRIPTION
                    "Recordings Diagnostics failed to initialize. Trap Severity = {1}, Application Name = {2}, Application Status = {3}, Trap Host Time = {4}"
              ::=  8001                                           
            
           rdApplicationStartUp TRAP-TYPE
              ENTERPRISE  recordingsDiagnostic
              VARIABLES   {trapSeverity,
              			   rdName,	 
              			   rdStatus,
            			   trapHostTime}
              DESCRIPTION
                    "Recordings Diagnostics startup. Trap Severity = {1}, Application Name = {2}, Application Status = {3}, Trap Host Time = {4}"
              ::=  8002
 
           rdKeepAliveHeartBeatFail TRAP-TYPE
              ENTERPRISE  recordingsDiagnostic
              VARIABLES   {trapSeverity,
              			   rdName,	 
              			   rdStatus,
            			   trapHostTime}
              DESCRIPTION
                    "Recordings Diagnostics keep alive heartbeat failed. Trap Severity = {1}, Application Name = {2}, Application Status = {3}, Trap Host Time = {4}"
              ::=  8003

           rdConnectionToCLSIsActive TRAP-TYPE
              ENTERPRISE  recordingsDiagnostic
              VARIABLES   {trapSeverity,
              			   rdName,	 
              			   rdStatus,
            			   trapHostTime,
						   rdCLSID,
						   rdCLSIpAddress}
              DESCRIPTION
                    "Recordings Diagnostics connection to CLS is active. Trap Severity = {1}, Application Name = {2}, Application Status = {3}, Trap Host Time = {4}, CLS server id = {5}, CLS server IP address = {6}"
              ::=  8004

           rdConnectionToCLSIsNotActive TRAP-TYPE
              ENTERPRISE  recordingsDiagnostic
              VARIABLES   {trapSeverity,
              			   rdName,	 
              			   rdStatus,
            			   trapHostTime,
						   rdCLSID,
						   rdCLSIpAddress}
              DESCRIPTION
                    "Recordings Diagnostics connection to CLS is not active. Trap Severity = {1}, Application Name = {2}, Application Status = {3}, Trap Host Time = {4}, CLS server id = {5}, CLS server IP address = {6}"
              ::=  8005

           rdConnectionToCLSLost TRAP-TYPE
              ENTERPRISE  recordingsDiagnostic
              VARIABLES   {trapSeverity,
              			   rdName,	 
              			   rdStatus,
            			   trapHostTime,
						   rdCLSID,
						   rdCLSIpAddress}
              DESCRIPTION
                    "Recordings Diagnostics connection to CLS is lost. Trap Severity = {1}, Application Name = {2}, Application Status = {3}, Trap Host Time = {4}, CLS server id = {5}, CLS server IP address = {6}"
              ::=  8006

           rdConnectionToLoggerIsActive TRAP-TYPE
              ENTERPRISE  recordingsDiagnostic
              VARIABLES   {trapSeverity,
              			   rdName,	 
              			   rdStatus,
            			   trapHostTime,
						   rdLoggerID,
						   rdLoggerIpAddress}
              DESCRIPTION
                    "Recordings Diagnostics connection to logger is active. Trap Severity = {1}, Application Name = {2}, Application Status = {3}, Trap Host Time = {4}, Logger id = {5}, Logger IP address = {6}"
              ::=  8007
              
           rdConnectionToLoggerIsNotActive TRAP-TYPE
              ENTERPRISE  recordingsDiagnostic
              VARIABLES   {trapSeverity,
              			   rdName,	 
              			   rdStatus,
            			   trapHostTime,
						   rdLoggerID,
						   rdLoggerIpAddress}
              DESCRIPTION
                    "Recordings Diagnostics connection to logger is not active. Trap Severity = {1}, Application Name = {2}, Application Status = {3}, Trap Host Time = {4}, Logger id = {5}, Logger IP address = {6}"
              ::=  8008              

           rdConnectionToLoggerLost TRAP-TYPE
              ENTERPRISE  recordingsDiagnostic
              VARIABLES   {trapSeverity,
              			   rdName,	 
              			   rdStatus,
            			   trapHostTime,
						   rdLoggerID,
						   rdLoggerIpAddress}
              DESCRIPTION
                    "Recordings Diagnostics connection to logger is lost. Trap Severity = {1}, Application Name = {2}, Application Status = {3}, Trap Host Time = {4}, Logger id = {5}, Logger IP address = {6}"
              ::=  8009              
              
           rdTaskStarted TRAP-TYPE
              ENTERPRISE  recordingsDiagnostic
              VARIABLES   {trapSeverity,
              			   rdName,	 
              			   rdStatus,
            			   trapHostTime,
						   rdTaskName,
						   rdTaskType}
              DESCRIPTION
                    "Recordings Diagnostics Task started. Trap Severity = {1}, Application Name = {2}, Application Status = {3}, Trap Host Time = {4}, Task Name = {5}, Task Type = {6}"
              ::=  8010              

           rdTaskCompleted TRAP-TYPE
              ENTERPRISE  recordingsDiagnostic
              VARIABLES   {trapSeverity,
              			   rdName,	 
              			   rdStatus,
            			   trapHostTime,
						   rdTaskName,
						   rdTaskType,
						   rdTaskCurrentState,
						   rdTaskExecElements,
						   rdTaskExecFailElements,
						   rdTaskLastError}
              DESCRIPTION
                    "Recordings Diagnostics Task completed.  Trap Severity = {1}, Application Name = {2}, Application Status = {3}, Trap Host Time = {4}, Task Name = {5}, Task Type = {6}, Task Current State = {7}, Executed elements = {8}, Failed Elements = {9}, Last Error = {10}"
              ::=  8011             
              
           rdMatchingSessionFailed TRAP-TYPE
              ENTERPRISE  recordingsDiagnostic
              VARIABLES   {trapSeverity,
              			   rdName,	 
              			   rdStatus,
            			   trapHostTime,
						   rdTaskName,
						   trapCLSId,
						   trapLoggerId,
						   trapRecordingChannel,
						   trapRecordingStartTime,
						   trapRecordingStopTime}
               DESCRIPTION
                    "Recordings Diagnostics failed to locate a matching session for the time period. Trap Severity = {1}, Application Name = {2}, Application Status = {3}, Trap Host Time = {4}, Task Name = {5}, CLS Server id = {6}, Logger id = {7}, Recording Channel = {8}, Recording Start Time = {9}, Recording Stop Time = {10}"
              ::=  8012             
              
           rdMatchingPerdiodFailed TRAP-TYPE
              ENTERPRISE  recordingsDiagnostic
              VARIABLES   {trapSeverity,
              			   rdName,	 
              			   rdStatus,
            			   trapHostTime,
						   rdTaskName,
						   trapCLSId,
						   trapLoggerId,
						   trapRecordingChannel,
						   trapRecordingStartTime,
						   trapRecordingStopTime}
               DESCRIPTION
                    "Recordings Diagnostics failed to locate sessions for the entire time period. Trap Severity = {1}, Application Name = {2}, Application Status = {3}, Trap Host Time = {4}, Task Name = {5}, CLS Server id = {6}, Logger id = {7}, Recording Channel = {8}, Recording Start Time = {9}, Recording Stop Time = {10}"
              ::=  8013 

		   rdCLSGeneralError TRAP-TYPE
              ENTERPRISE  recordingsDiagnostic
              VARIABLES   {trapSeverity,
              			   rdName,	 
              			   rdStatus,
            			   trapHostTime,
						   rdCLSID,
						   rdCLSIpAddress}
              DESCRIPTION
                    "Recordings Diagnostics connection to CLS is lost. Trap Severity = {1}, Application Name = {2}, Application Status = {3}, Trap Host Time = {4}, CLS server id = {5}, CLS server IP address = {6}"
              ::=  8014
                          

          --------------------------------------------------------
          -- Database Utilities subtree

          databaseUtilities OBJECT IDENTIFIER   ::= { systemTools 2 }

END
