-- extracted from draft-kajos-hmultimediamib-00.txt
-- at Mon Nov 15 17:11:06 1999

        H323TERMINAL-MIB DEFINITIONS ::= BEGIN
             IMPORTS
                  MODULE-IDENTITY, OBJECT-TYPE, Integer32,
                  experimental, TimeTicks, IpAddress
                       FROM SNMPv2-SMI
                  DisplayString, DateAndTime
                       FROM SNMPv2-TC
                  MODULE-COMPLIANCE, OBJECT-GROUP
                       FROM SNMPv2-CONF;

             h323TerminalMIB MODULE-IDENTITY
                  LAST-UPDATED "9805251400Z" -- May 25, 1998
                  ORGANIZATION "VTEL Corp."
                  CONTACT-INFO
                       "Joon Maeng
                       VTEL Corp.
                       Postal: 108 Wild Basin Rd.
                                            Austin, TX 78746
                                            USA
                       TEL: (512)437-4567
                       Email: Joon_Maeng@vtel.com"
                  DESCRIPTION
                       "This MIB module supports the functions of an
                       ITU H.323 terminal"
                  REVISION "9805251400Z" -- May 25, 1998
                  DESCRIPTION
                       " The initial version of the H323 terminal mib"
             ::= {experimental 323 3} -- temporary OID.  TBD.
             h323TerminalDescr        OBJECT IDENTIFIER ::= {h323TerminalMIB 1}
             h323TerminalCaps         OBJECT IDENTIFIER ::= {h323TerminalMIB 2}
             h323TerminalConfig  OBJECT IDENTIFIER ::= { h323TerminalMIB 3}
             h323TerminalControl OBJECT IDENTIFIER ::= { h323TerminalMIB 4}
        
        -- Terminal description group
        -- Implementation of the terminal description group is mandatory for all
        -- H.323 terminals. If an agent is not configured to have a value for any
        -- of these variables, a string of length 0 is returned.  In addition to
        -- objects defined in this group, implementation of the System group in
        -- MIB-II [  ] is mandatory for implementers of the H.323 Terminal MIB.
        
             h323t35CountryCode OBJECT-TYPE
                       SYNTAX INTEGER (0..255)
                       MAX-ACCESS read-only
                       STATUS current
                       DESCRIPTION
                       "Country code, per T.35."
                  ::= { h323TerminalDescr 1 }
        
             h323t35CountryCodeExtention OBJECT-TYPE
                       SYNTAX INTEGER (0..255)
                       MAX-ACCESS read-only
                       STATUS current
                       DESCRIPTION
                       "Assigned nationally."
                  ::= { h323TerminalDescr 2 }

             h323t35ManufacturerCode OBJECT-TYPE
                       SYNTAX INTEGER (0..65535)
                       MAX-ACCESS read-only
                       STATUS current
                       DESCRIPTION
                       "Assigned nationally."
                  ::= { h323TerminalDescr 3 }
        
             h323TerminalUptime OBJECT-TYPE
                       SYNTAX TimeTicks
                       MAX-ACCESS read-only
                       STATUS current
                       DESCRIPTION
                       "The amount of time (in hundredths of a second) since
                       this H323 terminal was last initialized.  Note that this
                       is different from sysUpTime in MIB-II [ ] because
                       sysUpTime  is the uptime of the network management
                       portion of the system."
                  ::= { h323TerminalDescr 4 }
        
        
             h323TerminalLocalTime OBJECT-TYPE
                       SYNTAX DateAndTime
                       MAX-ACCESS read-write
                       STATUS current
                       DESCRIPTION
                                 "The local date and time of day."
             ::= { h323TerminalDescr 5 }
        
             h323TerminalDiagnostics OBJECT-TYPE
                       SYNTAX Integer32
                       MAX-ACCESS read-only
                       STATUS current
                       DESCRIPTION
                                 "Indicates the results of the last
        diagnostic routine
                       performed
                       noResults(1)        No diagnostic has yet been performed,
                       passed(2)      the diagnostic has been passed, hardwareFault(3)         				
					Hardware fault was detected,
                       softwareFault(4)         Software fault was detected"
             ::= { h323TerminalDescr 6 }
        
             h323TerminalStatus OBJECT-TYPE
                       SYNTAX INTEGER {
                       callSetup (1),
                            callinProgress(2),
                            callHangUp(3),
                            idle(4)
                       }
                       MAX-ACCESS read-only
                       STATUS current
                       DESCRIPTION
                       "General status of the terminal"
             ::= { h323TerminalDescr 7 }
        
        
             -- H323 Terminal capabilities
             --
             h323TerminalMaxLineRate OBJECT-TYPE
                  SYNTAX Integer32
                  MAX-ACCESS read-only
                  STATUS current
                  DESCRIPTION
                       "This object represents maximum line rate of combined
                       audio/video and data of this terminal."
             ::= { h323TerminalCaps 1 }
        
                  h323TerminalVideoCaps OBJECT-TYPE
                  SYNTAX Integer32
                       MAX-ACCESS read-only
                  STATUS current
                  DESCRIPTION
                       "This object represents the video capabilities of this
                       terminal. This includes the various video algorithms that
                       it supports. It is encoded as bits in an octet string,
                       with the following definitions:
        
                       Capability             Bit #
        
                       h261CIFVideo        	0
                       h261QCIFVideo       	1
                       h263SQCIFVideo          	2
                       h263QCIFVideo      	3
                       h263CIFVideo        	4
                       h263CIF4Video       	5
                       h263CIF16Video      	6
                       h262SPMLSIFVideo    	7
                       h262SPML2SIFVideo        8
                       h262SPML4SIFVideo        9
                       h262MPMLSIFVideo         10
                       h262MPML2SIFVideo        11
                       h262MPML4SIFVideo        12
        
                       Bits are numbered starting with the most
                       significant bit of the first byte being bit 0, the
                       least significant bit of the first byte being bit
                       7, the most significant bit of the second byte
                       being bit 8, and so on.  A one bit encodes that
                       the capability is supported, a zero bit encodes that
                       the capability is not supported."
             ::= { h323TerminalCaps 2 }
        
             h323TerminalMaxVideoRate OBJECT-TYPE
                  SYNTAX  Integer32
                  MAX-ACCESS  read-only
                  STATUS  current
                  DESCRIPTION
                       "The maximum bit rate that the video channel can do."
             ::= { h323TerminalCaps 3 }
        
             h323TerminalAudioCaps OBJECT-TYPE
                  SYNTAX Integer32
                  MAX-ACCESS read-only
                  STATUS current
                  DESCRIPTION
                       "This object represents the audio capabilities of this
                       terminal. This includes the various audio algorithms that
                       it supports. It is encoded as bits in an octet string,
                       with the following definitions:
        
                                      Capability          Bit #
        
                                 g711-ALaw64KAudio 	0
                                 g711-ALaw56KAudio   	1
                                 g711-ULaw64KAudio   	2
                                 g711-ULaw56KAudio   	3
                                 g722-64KAudio	  	4
                                 g722-56KAudio  	5
                                 g722-48KAudio  	6
                                 g728Audio      	7
                                 g723.1-5.3KAudio    	8
                                 g723.1-6.4KAudio    	9
                                 g729Audio      	10
        
                       Bits are numbered starting with the most
                       significant bit of the first byte being bit 0, the
                       least significant bit of the first byte being bit
                       7, the most significant bit of the second byte
                       being bit 8, and so on.  A one bit encodes that
                       the capability is supported, a zero bit encodes that
                       the capability is not supported."
                  ::= { h323TerminalCaps 4 }
        
                       h323TerminalDataCaps OBJECT-TYPE
                  SYNTAX Integer32
                  MAX-ACCESS read-only
                  STATUS current
                  DESCRIPTION
                       "This object represents the data application
                       capability of the terminal. It is encoded as bits in
                       an octet string, with the following definitions:
        
                            Capability          	Bit #
                                t.120               	0
                       		dsm-cc              	1
                            	userData       		2
                            	t84            		3
                            	t434           		4	
                       		h224                	5
                            	nlpid               	6
                            	dsvdControl         	7
                            	h222DataPartitioning    8
                       		t30fax              	9
                            	t140                	10
                                 Others              	11
        
                       Bits are numbered starting with the most
                       significant bit of the first byte being bit 0, the
                       least significant bit of the first byte being bit
                       7, the most significant bit of the second byte
                       being bit 8, and so on.  A one bit encodes that
                       the capability is supported, a zero bit encodes that
                       the capability is not supported."
             ::= { h323TerminalCaps 5 }
        
             h323TerminalEncrypCaps OBJECT-TYPE
                  SYNTAX Integer32
                  MAX-ACCESS read-only
                  STATUS current
                  DESCRIPTION
                       "This object represents the encryption capability of the
                       terminal.
        
                                 Capability          Bit #
                                 H.235               0
                                 Others              1
        
                       Bits are numbered starting with the most
                       significant bit of the first byte being bit 0, the
                       least significant bit of the first byte being bit
                       7, the most significant bit of the second byte
                       being bit 8, and so on.  A one bit encodes that
                       the capability is supported, a zero bit encodes that
                       the capability is not supported."
             ::= { h323TerminalCaps 6 }
        
             h323TerminalRDCCaps OBJECT-TYPE
                  SYNTAX Integer32
                  MAX-ACCESS read-only
                  STATUS current
                  DESCRIPTION
                       "This object represents the Remote Device Control
                       capability of the terminal.
                            FECC           0   -- Far-end Camera Control
                            Others              1
        
                       Bits are numbered starting with the most
                       significant bit of the first byte being bit 0, the
                       least significant bit of the first byte being bit
                       7, the most significant bit of the second byte
                       being bit 8, and so on.  A one bit encodes that
                       the capability is supported, a zero bit encodes that
                       the capability is not supported."
                  ::= { h323TerminalCaps 7 }
        
             -- H323 terminal configuration
             -- This group contains objects to configure the terminal.
        
             h323TerminalSiteName OBJECT-TYPE
                       SYNTAX DisplayString (SIZE (0..255))
                       MAX-ACCESS read-write
                       STATUS current
                       DESCRIPTION
                       "Name of the site where the H323 terminal is located. "
             ::= { h323TerminalConfig 1 }
        
             h323TerminalVideoSystem OBJECT-TYPE
                       SYNTAX INTEGER {
                       ntsc(1),
                       pal(2),
                       secam(3),
                       others(4)
                       }
                  MAX-ACCESS read-write
                       STATUS current
                       DESCRIPTION
                       "Video format standard"
             ::= { h323TerminalConfig 2 }
        
             h323TerminalfType OBJECT-TYPE
                  SYNTAX  Integer32
                  MAX-ACCESS  read-write
                  STATUS  current
                  DESCRIPTION
                       "The interface type on which this site can be called.
                       The interface type identified by this value is the
                       same type of as the ifType from Interface Table
                       in RFC1213."
             ::= { h323TerminalConfig 3 }
        
             h323TerminalIPAddress OBJECT-TYPE
                       SYNTAX IpAddress
                       MAX-ACCESS read-write
                       STATUS current
                       DESCRIPTION
                       "The IP address of the terminal."
             ::= { h323TerminalConfig 4  }
        
             -- Terminal control group
             -- This group contains variables used to control a H.323 terminal.
        
             h323TerminalAdminControl OBJECT-TYPE
                       SYNTAX INTEGER { run(1), reset(2), diagnose(3), stop(4) }
                       MAX-ACCESS read-write
                       STATUS current
                       DESCRIPTION
                       "The desired state of the H323 terminal.  Setting the value
                       if this object to these values will have the
                       following actions:
                       run(1)    The H323 terminal will enter the run state,
                       reset(2)  The H323 terminal will reset,
                       diagnose(3)    Will activate the diagnostic routine
                       stop(4)   Will halt the H323 terminal."
             ::= { h323TerminalControl 1 }
        
             h323TerminalCallSetUp  OBJECT-TYPE
                  SYNTAX  Integer32
                  MAX-ACCESS  read-write
                  STATUS  current
                  DESCRIPTION
                       "establish a call to another video conference terminal.
                       Set this value to the index of the site of the video
                       conference site you want to dial in the Site Table and
                       the system will be dialed."
             ::= { h323TerminalControl 2 }
        
             h323TerminalCallHangup OBJECT-TYPE
                  SYNTAX  Integer32
                  MAX-ACCESS  read-write
                  STATUS  current
                  DESCRIPTION
                       "Hang up the video conference call in progess now."
             ::= { h323TerminalControl 3 }
        
             h323EnableLocalLoopback  OBJECT-TYPE
                  SYNTAX  INTEGER {
                            enable(1),
                            disable(2)
                            }
                  MAX-ACCESS  read-write
                  STATUS  current
                  DESCRIPTION
                       "Enable or disable local loop back on a video
                       conference system. Local loopbacks loop back the
        audio,
                       video and data streams in a call. Once looped back,
                       a new call will show up in the Call Table and the
                       user can observe the audio/video/data rates to assure
                       that these components are working properly."
             ::= { h323TerminalControl 4 }
        
             h323EnableRemoteLoopback  OBJECT-TYPE
                  SYNTAX  INTEGER{
                            enable(1),
                            disable(2)
                            }
                  MAX-ACCESS  read-write
                  STATUS  current
                  DESCRIPTION
                       "Enable or disable remote loop back on a video conference
                       system. Remote loopbacks loop back the audio
                       and video streams from the remote system in
                       a call.. When the remote system
                       calls in, a new call will show up in the
                       Call Table and the user can observe the
                       audio/video/data rates to assure that these
                       components are coming in properly from the
                       remote system."
             ::= { h323TerminalControl 5 }
        
             --
             -- CONFORMANCE
             --
        
             h323TerminalMIBConfs     OBJECT IDENTIFIER ::= {
        h323TerminalMIB 5 }
             h323TerminalMIBGroups    OBJECT IDENTIFIER ::= {
        h323TerminalMIBConfs 1
        }
             h323TerminalMIBCompl     OBJECT IDENTIFIER ::= {
        h323TerminalMIBConfs 2
        }
        
             --
             -- Groups for conformance
             --
        
             h323TerminalDesrGroup    OBJECT-GROUP
                  OBJECTS {
                       h323t35CountryCode,
                       h323t35CountryCodeExtention,
                       h323t35ManufacturerCode,
                       h323TerminalUptime,
                       h323TerminalLocalTime,
                       h323TerminalDiagnostics,
                       h323TerminalStatus
                  }
                  STATUS current
                  DESCRIPTION
                       "A collection of objects providing the description
                       of the terminal"
             ::= { h323TerminalMIBGroups 1}
        
             h323TerminalCapsGroup    OBJECT-GROUP
                  OBJECTS {
                       h323TerminalMaxLineRate,
                       h323TerminalVideoCaps,
                       h323TerminalMaxVideoRate,
                       h323TerminalAudioCaps,
                                 h323TerminalDataCaps,
                       h323TerminalEncrypCaps,
                       h323TerminalRDCCaps
                       }
                  STATUS current
                  DESCRIPTION
                       "A collection of objects providing capabilities of
                       the terminal"
             ::= { h323TerminalMIBGroups 2}
        
             h323TerminalConfigGroup  OBJECT-GROUP
                  OBJECTS {
                       h323TerminalSiteName ,
                       h323TerminalVideoSystem,
                       h323TerminalfType,
                       h323TerminalIPAddress
                  }
                  STATUS current
                  DESCRIPTION
                       "A collection of objects providing the ability to
                       configure the terminal"
             ::= { h323TerminalMIBGroups 3}
        
             h323TerminalControlGroup  OBJECT-GROUP
                  OBJECTS {
                       h323TerminalAdminControl,
                       h323TerminalCallSetUp,
                       h323TerminalCallHangup,
                       h323EnableLocalLoopback,
                       h323EnableRemoteLoopback
                       }
                  STATUS current
                  DESCRIPTION
                       "A collection of objects providing the ability
                       to invoke terminal functions"
             ::= { h323TerminalMIBGroups 4}
        
             h323TerminalCompliance   MODULE-COMPLIANCE
                  STATUS    current
                  DESCRIPTION
                       "The set of objects required for compliance"
                  MODULE
                       MANDATORY-GROUPS     {
                            h323TerminalDesrGroup,
                            h323TerminalCapsGroup,
                            h323TerminalConfigGroup
                            }
        
                  GROUP          h323TerminalControlGroup
                  DESCRIPTION
                       "This group is optional.  H323 terminals under a
		           centralized control via  a network management protocol
                       are  strongly encouraged to use this group to enable the
                       remote control functions such as call establishment
                       and hang up."
        
             ::= { h323TerminalMIBCompl 1 }
        
        END
