-- *****************************************************************************
-- Unisphere-Data-Entity-CONF
--
-- SNMP Agent Capabilities definitions for the Entity MIBs.
--
-- Copyright (c) 2001 Unisphere Networks, Inc.  All rights reserved.
-- *****************************************************************************

Unisphere-Data-Entity-CONF DEFINITIONS ::= BEGIN

IMPORTS
    MODULE-IDENTITY
        FROM SNMPv2-SMI
    AGENT-CAPABILITIES
        FROM SNMPv2-CONF
    usDataAgents
        FROM Unisphere-Data-Agents
    entityLogicalGroup,
    entityPhysical2Group,
    entityLogical2Group,
    entityMappingGroup,
    entPhysicalSerialNum,
    entLPPhysicalIndex,
    entAliasMappingIdentifier
        FROM ENTITY-MIB;

usdEntityAgent MODULE-IDENTITY
    LAST-UPDATED "200104271316Z"  -- 27-Apr-01 09:16 AM EDT
    ORGANIZATION "Unisphere Networks, Inc."
    CONTACT-INFO
        "       Unisphere Networks, Inc.
        Postal: 10 Technology Park Drive
                Westford, MA  01886
                USA
        Tel:    +1 978 589 5800
        E-mail: mib@UnisphereNetworks.com"
    DESCRIPTION
        "The agent capabilities definitions for the physical and logical entity
        components of the SNMP agent in the Unisphere Routing Switch family of
        products."
    -- Revision History
    REVISION    "200104271316Z"  -- 27-Apr-01 09:16 AM EDT  - RX 3.2
    DESCRIPTION
        "The initial release of this management information module."
    ::= { usDataAgents 13 }

usdEntityAgentV1 AGENT-CAPABILITIES
    PRODUCT-RELEASE
        "Version 1 of the logical Entity component of the Unisphere Routing
        Switch SNMP agent.  This version of the logical Entity component was
        supported in the Unisphere RX 2.x system releases."
    STATUS      obsolete
    DESCRIPTION
        "The MIB supported by the SNMP agent for the Router Agent (logical
        entity) application in the Unisphere Routing Switch.  These capabilities
        became obsolete when support was add for the physical entity table, the
        physical entity contains table, and RFC 2737 enhancements to the logical
        entity table."
    SUPPORTS    ENTITY-MIB
        INCLUDES  {
            entityLogicalGroup }
    ::= { usdEntityAgent 1 }

usdEntityAgentV2 AGENT-CAPABILITIES
    PRODUCT-RELEASE
        "Version 2 of the physical and logical Entity components of the
        Unisphere Routing Switch SNMP agent.  This version of the physical and
        logical Entity components is supported in the Unisphere RX 3.0 and
        subsequent system releases."
    STATUS      current
    DESCRIPTION
        "The MIB supported by the SNMP agent for the System (physical entity)
        and Router Agent (logical entity) applications in the Unisphere Routing
        Switch."
    SUPPORTS    ENTITY-MIB
        INCLUDES  {
            entityPhysical2Group,
            entityLogical2Group,
            entityMappingGroup }
        VARIATION   entPhysicalSerialNum
            ACCESS      read-only
            DESCRIPTION
                "Serial numbers cannot be modified in this Agent."
        VARIATION   entLPPhysicalIndex
            ACCESS      not-implemented
            DESCRIPTION
                "The logical entity to physical equipment mapping table is not
                supported in this version of the Agent."
        VARIATION   entAliasMappingIdentifier
            ACCESS      not-implemented
            DESCRIPTION
                "The alias mapping table is not supported in this version of the
                Agent."
    ::= { usdEntityAgent 2 }

END
