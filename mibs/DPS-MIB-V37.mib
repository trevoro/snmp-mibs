--  Title:    DPS-V36.MIB
--  Version:  v3.7
--
--  Copyright @ 1997-1998 DPS Inc. All Rights Reserved
--
--  This MIB defines objects for the DPS products.
--
--

DPS-MIB-V37 DEFINITIONS ::= BEGIN

IMPORTS
	TRAP-TYPE FROM RFC-1215
	DisplayString, sysDescr, sysLocation
		FROM RFC1213-MIB
	OBJECT-TYPE
		FROM RFC-1212
	enterprises
		FROM RFC1155-SMI;

dpsInc OBJECT IDENTIFIER ::= {enterprises  2682}

dpsAlarmControl OBJECT IDENTIFIER ::= {dpsInc 1}

tMonXM OBJECT IDENTIFIER ::= {dpsAlarmControl 1}

tmonIdent OBJECT IDENTIFIER ::= {tMonXM 1}

tmonIdentManufacturer OBJECT-TYPE
	SYNTAX  DisplayString
	ACCESS  read-only
	STATUS  mandatory
	DESCRIPTION "The TMON/XM Unit manufacturer."
	::= {tmonIdent  1}

tmonIdentModel OBJECT-TYPE
	SYNTAX  DisplayString
	ACCESS  read-only
	STATUS  mandatory
	DESCRIPTION "The TMON/XM model designation."
	::= {tmonIdent  2}

tmonIdentSoftwareVersion OBJECT-TYPE
	SYNTAX  DisplayString
	ACCESS  read-only
	STATUS  mandatory
	DESCRIPTION "The TMON/XM SNMP Agent software version."
	::= {tmonIdent  3}

tmonAlarmTable OBJECT-TYPE
	SYNTAX  SEQUENCE OF TMonAlarmEntry
	ACCESS  not-accessible
	STATUS  mandatory
	DESCRIPTION "A table of TMon Alarm-specific information."
	::= {tMonXM 2}

tmonAlarmEntry OBJECT-TYPE
	SYNTAX  TMonAlarmEntry
	ACCESS  not-accessible
	STATUS  mandatory
	DESCRIPTION "Information about a particular TMon alarm."
	INDEX   {tmonAIndex}
	::= {tmonAlarmTable 1}

TMonAlarmEntry ::= SEQUENCE  {tmonAIndex		INTEGER,
										tmonASite		DisplayString,
										tmonADesc		DisplayString,
										tmonAState		DisplayString,
										tmonASeverity	DisplayString,
										tmonAChgDate	DisplayString,
										tmonAChgTime	DisplayString,
										tmonAAuxDesc   DisplayString,
										tmonADispDesc  DisplayString,
										tmonAPntType	INTEGER,
										tmonAPort		INTEGER,
										tmonAAddress	INTEGER,
										tmonADisplay	INTEGER,
										tmonAPoint		INTEGER}

tmonAIndex OBJECT-TYPE
	SYNTAX  INTEGER
	ACCESS  read-only
	STATUS  mandatory
	DESCRIPTION "Tmon alarm table index (1..NumberOfAlarms)."
	::={tmonAlarmEntry 1}

tmonASite OBJECT-TYPE
	SYNTAX  DisplayString (SIZE (14))
	ACCESS  read-only
	STATUS  mandatory
	DESCRIPTION "The site of the alarm (i.e. Atlanta Hub, Sub-Station H32)."
	::= {tmonAlarmEntry 2}

tmonADesc OBJECT-TYPE
	SYNTAX  DisplayString (SIZE (40))
	ACCESS  read-only
	STATUS  mandatory
	DESCRIPTION "A user-defined text string associated with the alarm 
					 (i.e. South Door, Generator, Power Grid 1)."
	::= {tmonAlarmEntry 3}

tmonAState OBJECT-TYPE
	SYNTAX  DisplayString (SIZE (8))
	ACCESS  read-only
	STATUS  mandatory
	DESCRIPTION "The current alarm state."
	::= {tmonAlarmEntry 4}

tmonASeverity OBJECT-TYPE
	SYNTAX  DisplayString (SIZE (8))
	ACCESS  read-only
	STATUS  mandatory
	DESCRIPTION "The severity of the last alarm event."
	::= {tmonAlarmEntry 5}

tmonAChgDate OBJECT-TYPE
	SYNTAX  DisplayString (SIZE (8))
	ACCESS  read-only
	STATUS  mandatory
	DESCRIPTION "The date (mm/dd/yy) of the last alarm event."
	::= {tmonAlarmEntry 6}

tmonAChgTime OBJECT-TYPE
	SYNTAX  DisplayString (SIZE (8))
	ACCESS  read-only
	STATUS  mandatory
	DESCRIPTION "The time (hh:mm:ss) of the last alarm event."
	::= {tmonAlarmEntry 7}

tmonAAuxDesc OBJECT-TYPE
	SYNTAX  DisplayString (SIZE (30))
	ACCESS  read-only
	STATUS  mandatory
	DESCRIPTION "An auxiliary user-defined text string associated with the
					 alarm (i.e. This remote needs servicing)."
	::= {tmonAlarmEntry 8}

tmonADispDesc OBJECT-TYPE
	SYNTAX  DisplayString (SIZE (14))
	ACCESS  read-only
	STATUS  mandatory
	DESCRIPTION "A description of the display on which this point appears."
	::= {tmonAlarmEntry 9}

tmonAPntType OBJECT-TYPE
	SYNTAX  INTEGER
	ACCESS  read-only
	STATUS  mandatory
	DESCRIPTION "Type of this point."
	::={tmonAlarmEntry 10}

tmonAPort OBJECT-TYPE
	SYNTAX  INTEGER
	ACCESS  read-only
	STATUS  mandatory
	DESCRIPTION "Port on which this point is reported."
	::={tmonAlarmEntry 11}

tmonAAddress OBJECT-TYPE
	SYNTAX  INTEGER
	ACCESS  read-only
	STATUS  mandatory
	DESCRIPTION "Address of unit reporting this point."
	::={tmonAlarmEntry 12}

tmonADisplay OBJECT-TYPE
	SYNTAX  INTEGER
	ACCESS  read-only
	STATUS  mandatory
	DESCRIPTION "Display on which this point appears."
	::={tmonAlarmEntry 13}

tmonAPoint OBJECT-TYPE
	SYNTAX  INTEGER
	ACCESS  read-only
	STATUS  mandatory
	DESCRIPTION "Index into display of this point."
	::={tmonAlarmEntry 14}


-- structure used to issue a command to TMonXM element

tmonCommandGrid OBJECT IDENTIFIER ::= {tMonXM 3}

tmonCPType OBJECT-TYPE
	SYNTAX  INTEGER
	ACCESS  read-write
	STATUS  mandatory
	DESCRIPTION "Tmon point type."
	::= {tmonCommandGrid 1}

tmonCPort OBJECT-TYPE
	SYNTAX  INTEGER
	ACCESS  read-write
	STATUS  mandatory
	DESCRIPTION "Tmon port number."
	::= {tmonCommandGrid 2}

tmonCAddress OBJECT-TYPE
	SYNTAX  INTEGER
	ACCESS  read-write
	STATUS  mandatory
	DESCRIPTION "Tmon-port address number."
	::= {tmonCommandGrid 3}

tmonCDisplay OBJECT-TYPE
	SYNTAX  INTEGER
	ACCESS  read-write
	STATUS  mandatory
	DESCRIPTION "Tmon-port-address display number."
	::= {tmonCommandGrid 4}

tmonCPoint OBJECT-TYPE
	SYNTAX  INTEGER (1..64)
	ACCESS  read-write
	STATUS  mandatory
	DESCRIPTION "Tmon-port-display point number (1-64)."
	::= {tmonCommandGrid 5}

tmonCEvent OBJECT-TYPE
	SYNTAX  INTEGER
	ACCESS  read-write
	STATUS  mandatory
	DESCRIPTION "Tmon event ID."
	::= {tmonCommandGrid 6}

tmonCAction OBJECT-TYPE
	SYNTAX  INTEGER {	latch(1),
							release(2),
							momentary(3),
							ack(17),
							tag(18),
							untag(19)
						 }
	ACCESS  read-write
	STATUS  mandatory
	DESCRIPTION "Requested command action (TMonXM will ignore if invalid)."
	::= {tmonCommandGrid 7}

tmonCAuxText OBJECT-TYPE
	SYNTAX  DisplayString (SIZE (30))
	ACCESS  read-write
	STATUS  mandatory
	DESCRIPTION "An auxiliary user-defined text string associated with the
					 command (i.e. User-initials)."
	::= {tmonCommandGrid 8}

tmonCResult OBJECT-TYPE
	SYNTAX  INTEGER { success(1),
							failure(2),
							pending(3)
						 }
	ACCESS  read-only
	STATUS  mandatory
	DESCRIPTION "Command result."
	::= {tmonCommandGrid 9}



dpsRTU OBJECT IDENTIFIER ::= {dpsAlarmControl 2}

dpsRTUIdent OBJECT IDENTIFIER ::= {dpsRTU 1}

dpsRTUManufacturer OBJECT-TYPE
	SYNTAX  DisplayString (SIZE (30))
	ACCESS  read-only
	STATUS  mandatory
	DESCRIPTION "The Remote Telemetry Unit manufacturer."
	::= {dpsRTUIdent  1}

dpsRTUModel OBJECT-TYPE
	SYNTAX  DisplayString (SIZE (30))
	ACCESS  read-only
	STATUS  mandatory
	DESCRIPTION "The RTU model designation."
	::= {dpsRTUIdent  2}

dpsRTUFirmwareVersion OBJECT-TYPE
	SYNTAX  DisplayString (SIZE (20))
	ACCESS  read-only
	STATUS  mandatory
	DESCRIPTION "The RTU firmware version."
	::= {dpsRTUIdent  3}

dpsRTUDateTime OBJECT-TYPE
	SYNTAX  DisplayString (SIZE (23))
	ACCESS  read-write
	STATUS  mandatory
	DESCRIPTION "The RTU system date and time."
	::= {dpsRTUIdent  4}

dpsRTUSyncReq OBJECT-TYPE
	SYNTAX  INTEGER {	sync(1) }
	ACCESS  read-write
	STATUS  mandatory
	DESCRIPTION "Caution: SETting this object initiates traps for all
					 standing alarms."
	::= {dpsRTUIdent  5}


-- structure used to access displays managed by this RTU

dpsRTUDisplayGrid OBJECT-TYPE
	SYNTAX  SEQUENCE OF DPSrtuDispEntry
	ACCESS  not-accessible
	STATUS  mandatory
	DESCRIPTION "Holds information on displays managed by the RTU."
	::= {dpsRTU 2}

dpsRTUDisplayEntry OBJECT-TYPE
	SYNTAX  DPSrtuDispEntry
	ACCESS  not-accessible
	STATUS  mandatory
	DESCRIPTION "Information about a particular RTU display."
	INDEX   {dpsRTUPort, dpsRTUAddress, dpsRTUDisplay}
	::= {dpsRTUDisplayGrid 1}

DPSrtuDispEntry ::= SEQUENCE 	{	dpsRTUPort			INTEGER,
											dpsRTUAddress		INTEGER,
											dpsRTUDisplay		INTEGER,
											dpsRTUDispDesc		DisplayString,
											dpsRTUPntMap		DisplayString}

dpsRTUPort OBJECT-TYPE
	SYNTAX  INTEGER
	ACCESS  read-only
	STATUS  mandatory
	DESCRIPTION "RTU port number."
	::= {dpsRTUDisplayEntry 1}

dpsRTUAddress OBJECT-TYPE
	SYNTAX  INTEGER
	ACCESS  read-only
	STATUS  mandatory
	DESCRIPTION "RTU-port address number."
	::= {dpsRTUDisplayEntry 2}

dpsRTUDisplay OBJECT-TYPE
	SYNTAX  INTEGER
	ACCESS  read-only
	STATUS  mandatory
	DESCRIPTION "RTU-port-address display number."
	::= {dpsRTUDisplayEntry 3}

dpsRTUDispDesc OBJECT-TYPE
	SYNTAX  DisplayString (SIZE (20))
	ACCESS  read-only
	STATUS  mandatory
	DESCRIPTION "A description of the associated display."
	::= {dpsRTUDisplayEntry 4}

dpsRTUPntMap OBJECT-TYPE
	SYNTAX  DisplayString (SIZE (71))
	ACCESS  read-only
	STATUS  mandatory
	DESCRIPTION "A map of the points appearing in this display."
	::= {dpsRTUDisplayEntry 5}


-- structure used to issue a control to a managed point

dpsRTUControlGrid OBJECT IDENTIFIER ::= {dpsRTU 3}

dpsRTUCPort OBJECT-TYPE
	SYNTAX  INTEGER
	ACCESS  read-write
	STATUS  mandatory
	DESCRIPTION "RTU port number."
	::= {dpsRTUControlGrid 1}

dpsRTUCAddress OBJECT-TYPE
	SYNTAX  INTEGER
	ACCESS  read-write
	STATUS  mandatory
	DESCRIPTION "RTU-port address number."
	::= {dpsRTUControlGrid 2}

dpsRTUCDisplay OBJECT-TYPE
	SYNTAX  INTEGER
	ACCESS  read-write
	STATUS  mandatory
	DESCRIPTION "RTU-port-address display number."
	::= {dpsRTUControlGrid 3}

dpsRTUCPoint OBJECT-TYPE
	SYNTAX  INTEGER (1..64)
	ACCESS  read-write
	STATUS  mandatory
	DESCRIPTION "RTU-port-display point number (1-64)."
	::= {dpsRTUControlGrid 4}

dpsRTUCAction OBJECT-TYPE
	SYNTAX  INTEGER {	latch(1),
							release(2),
							momentary(3)
						 }
	ACCESS  read-write
	STATUS  mandatory
	DESCRIPTION "Requested action on point (RTU will ignore if invalid)."
	::= {dpsRTUControlGrid 5}


-- structure used to access NVram on this RTU

dpsRTUNVramGrid OBJECT-TYPE
	SYNTAX  SEQUENCE OF DPSrtuNVramEntry
	ACCESS  not-accessible
	STATUS  mandatory
	DESCRIPTION "Contains raw NVram data."
	::= {dpsRTU 4}

dpsRTUNVramSection OBJECT-TYPE
	SYNTAX  DPSrtuNVramEntry
	ACCESS  not-accessible
	STATUS  mandatory
	DESCRIPTION "Information about a specific RTU NVram section."
	INDEX   {dpsRTUNVsNmbr}
	::= {dpsRTUNVramGrid 1}

DPSrtuNVramEntry ::= SEQUENCE	{	dpsRTUNVsNmbr		INTEGER,
											dpsRTUNVsData		OCTET STRING,
											dpsRTUNVsStatus	INTEGER}

dpsRTUNVsNmbr OBJECT-TYPE
	SYNTAX  INTEGER
	ACCESS  read-only
	STATUS  mandatory
	DESCRIPTION "RTU NVram section number."
	::= {dpsRTUNVramSection 1}

dpsRTUNVsData OBJECT-TYPE
	SYNTAX  OCTET STRING (SIZE (32))
	ACCESS  read-only
	STATUS  mandatory
	DESCRIPTION "RTU-NVram-section raw data."
	::= {dpsRTUNVramSection 2}

dpsRTUNVsStatus OBJECT-TYPE
	SYNTAX  INTEGER { notReady(1),
							ok(2),
							download(3)
						 }
	ACCESS  read-only
	STATUS  mandatory
	DESCRIPTION "RTU-NVram-section status."
	::= {dpsRTUNVramSection 3}


-- structure used to access individual alarm points on this RTU

dpsRTUAlarmGrid OBJECT-TYPE
	SYNTAX  SEQUENCE OF DPSrtuAlarmEntry
	ACCESS  not-accessible
	STATUS  mandatory
	DESCRIPTION "Holds individual alarm point information."
	::= {dpsRTU 5}

dpsRTUAlarmEntry OBJECT-TYPE
	SYNTAX  DPSrtuAlarmEntry
	ACCESS  not-accessible
	STATUS  mandatory
	DESCRIPTION "Detailed information about a particular RTU display."
	INDEX   {dpsRTUAPort, dpsRTUAAddress, dpsRTUADisplay, dpsRTUAPoint}
	::= {dpsRTUAlarmGrid 1}

DPSrtuAlarmEntry ::= SEQUENCE	 {	dpsRTUAPort			INTEGER,
											dpsRTUAAddress		INTEGER,
											dpsRTUADisplay		INTEGER,
											dpsRTUAPoint		INTEGER,
											dpsRTUAPntDesc		DisplayString,
											dpsRTUAState		DisplayString}

dpsRTUAPort OBJECT-TYPE
	SYNTAX  INTEGER
	ACCESS  read-only
	STATUS  mandatory
	DESCRIPTION "RTU port number."
	::= {dpsRTUAlarmEntry 1}

dpsRTUAAddress OBJECT-TYPE
	SYNTAX  INTEGER
	ACCESS  read-only
	STATUS  mandatory
	DESCRIPTION "RTU-port address number."
	::= {dpsRTUAlarmEntry 2}

dpsRTUADisplay OBJECT-TYPE
	SYNTAX  INTEGER
	ACCESS  read-only
	STATUS  mandatory
	DESCRIPTION "RTU-port-address display number."
	::= {dpsRTUAlarmEntry 3}

dpsRTUAPoint OBJECT-TYPE
	SYNTAX  INTEGER
	ACCESS  read-only
	STATUS  mandatory
	DESCRIPTION "RTU-port-address-display point number."
	::= {dpsRTUAlarmEntry 4}

dpsRTUAPntDesc OBJECT-TYPE
	SYNTAX  DisplayString (SIZE (21))
	ACCESS  read-only
	STATUS  mandatory
	DESCRIPTION "A description of this point."
	::= {dpsRTUAlarmEntry 5}

dpsRTUAState OBJECT-TYPE
	SYNTAX  DisplayString (SIZE (8))
	ACCESS  read-only
	STATUS  mandatory
	DESCRIPTION "The current state of this point."
	::= {dpsRTUAlarmEntry 6}


-- TRAP definitions

cRalarmSet TRAP-TYPE
	ENTERPRISE  { tMonXM }
	VARIABLES {	tmonASite, tmonADesc, tmonAState, tmonASeverity, tmonAChgDate,
					tmonAChgTime, tmonAAuxDesc, tmonADispDesc, tmonAPntType,
					tmonAPort, tmonAAddress, tmonADisplay, tmonAPoint, tmonCEvent }
	DESCRIPTION "Generated when a critical alarm is set."
	::= 10

cRalarmClr TRAP-TYPE
	ENTERPRISE  { tMonXM }
	VARIABLES {	tmonASite, tmonADesc, tmonAState, tmonASeverity, tmonAChgDate,
					tmonAChgTime, tmonAAuxDesc, tmonADispDesc, tmonAPntType,
					tmonAPort, tmonAAddress, tmonADisplay, tmonAPoint, tmonCEvent }
	DESCRIPTION "Generated when a critical alarm clears."
	::= 11

mJalarmSet TRAP-TYPE
	ENTERPRISE  { tMonXM }
	VARIABLES {	tmonASite, tmonADesc, tmonAState, tmonASeverity, tmonAChgDate,
					tmonAChgTime, tmonAAuxDesc, tmonADispDesc, tmonAPntType,
					tmonAPort, tmonAAddress, tmonADisplay, tmonAPoint, tmonCEvent }
	DESCRIPTION "Generated when a major alarm is set."
	::= 12

mJalarmClr TRAP-TYPE
	ENTERPRISE  { tMonXM }
	VARIABLES {	tmonASite, tmonADesc, tmonAState, tmonASeverity, tmonAChgDate,
					tmonAChgTime, tmonAAuxDesc, tmonADispDesc, tmonAPntType,
					tmonAPort, tmonAAddress, tmonADisplay, tmonAPoint, tmonCEvent }
	DESCRIPTION "Generated when a major alarm clears."
	::= 13

mNalarmSet TRAP-TYPE
	ENTERPRISE  { tMonXM }
	VARIABLES {	tmonASite, tmonADesc, tmonAState, tmonASeverity, tmonAChgDate,
					tmonAChgTime, tmonAAuxDesc, tmonADispDesc, tmonAPntType,
					tmonAPort, tmonAAddress, tmonADisplay, tmonAPoint, tmonCEvent }
	DESCRIPTION "Generated when a minor alarm is set."
	::= 14

mNalarmClr TRAP-TYPE
	ENTERPRISE  { tMonXM }
	VARIABLES {	tmonASite, tmonADesc, tmonAState, tmonASeverity, tmonAChgDate,
					tmonAChgTime, tmonAAuxDesc, tmonADispDesc, tmonAPntType,
					tmonAPort, tmonAAddress, tmonADisplay, tmonAPoint, tmonCEvent }
	DESCRIPTION "Generated when a minor alarm clears."
	::= 15

sTalarmSet TRAP-TYPE
	ENTERPRISE  { tMonXM }
	VARIABLES {	tmonASite, tmonADesc, tmonAState, tmonASeverity, tmonAChgDate,
					tmonAChgTime, tmonAAuxDesc, tmonADispDesc, tmonAPntType,
					tmonAPort, tmonAAddress, tmonADisplay, tmonAPoint, tmonCEvent }
	DESCRIPTION "Generated when a status alarm is set."
	::= 16

sTalarmClr TRAP-TYPE
	ENTERPRISE  { tMonXM }
	VARIABLES {	tmonASite, tmonADesc, tmonAState, tmonASeverity, tmonAChgDate,
					tmonAChgTime, tmonAAuxDesc, tmonADispDesc, tmonAPntType,
					tmonAPort, tmonAAddress, tmonADisplay, tmonAPoint, tmonCEvent }
	DESCRIPTION "Generated when a status alarm clears."
	::= 17

dpsRTUPointSet TRAP-TYPE
	ENTERPRISE  { dpsRTU }
	VARIABLES {	sysDescr, sysLocation, dpsRTUDateTime,
					dpsRTUAPort, dpsRTUAAddress, dpsRTUADisplay, dpsRTUAPoint,
					dpsRTUAPntDesc, dpsRTUAState }
	DESCRIPTION "Generated when a point is set."
	::= 20

dpsRTUPointClr TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when a point clears."
	::= 21

dpsRTUsumPSet TRAP-TYPE
	ENTERPRISE  { dpsRTU }
	VARIABLES {	sysDescr, sysLocation, dpsRTUDateTime }
	DESCRIPTION "Generated when any point is set."
	::= 101

dpsRTUsumPClr TRAP-TYPE
	ENTERPRISE  { dpsRTU }
	VARIABLES {	sysDescr, sysLocation, dpsRTUDateTime }
	DESCRIPTION "Generated when all points clear."
	::= 102

dpsRTUcomFailed TRAP-TYPE
	ENTERPRISE  { dpsRTU }
	VARIABLES {	sysDescr, sysLocation, dpsRTUDateTime }
	DESCRIPTION "Generated when polled unit fails to respond."
	::= 103

dpsRTUcomRestored TRAP-TYPE
	ENTERPRISE  { dpsRTU }
	VARIABLES {	sysDescr, sysLocation, dpsRTUDateTime }
	DESCRIPTION "Generated when failed unit resumes responding."
	::= 104

-- **************************************************************************
-- Granular TRAP definitions
--
--    The following section supports granular trapping available on selected
-- DPS remote telemetry units.  This software selectable facility changes the
-- trap sent by a remote so equipped.  The standard trap identifies a SET or
-- CLR event in the trap ID and binds variables identifying the specific
-- remote point associated with the event.  A granular trap identifies a SET
-- or CLR event and the specific point associated with the event all in the
-- trap ID.  This is accomplished by mapping all SET event/points into the
-- trap ID range 10001-19999 and all CLR event/points into the trap ID range
-- 20001-29999.
--    If the unit manages multiple displays, the displays are mapped
-- sequentially with each display occupying a 64 point range.  For example, a
-- standalone standard or timestamp KDA which manages two displays, reports
-- SET event/points in the first display (discrete alarm points) in the range
-- 10001-10064.  The CLR event/points for the same display would be reported
-- in the range 20001-20064.  The second display (controls & housekeeping
-- alarm points) would have its SET event/points reported in the range 10065-
-- 10128 and its CLR event/points reported in the range 20065-20128.
--    SET and CLR definitions for the first 64 points have been included and
-- can be used as is for driving most SNMP manager mechanisms designed to key
-- on the trap ID for distinguishing and managing events.  Additional events
-- can be added simply by editing the following trap definitions prior to
-- compiling this file into your SNMP manager.  We recommend managing the SET
-- and CLR event definitions for a specific point as a single unit and using
-- the following simple rules:
--  + Adjust the numeric portion of the label preceeding TRAP-TYPE.
--  + Adjust the numeric reference in the DESCRIPTION text.
--  + Adjust the number on the last line of the definition.
--
--    Using these rules a definition for the 65th point would be:
-- 
-- dpsRTUp0065Set TRAP-TYPE
-- 	ENTERPRISE  { dpsRTU }
--		VARIABLES {	sysDescr, sysLocation, dpsRTUDateTime,
--						dpsRTUAPort, dpsRTUCAddress, dpsRTUADisplay, dpsRTUAPoint,
--						dpsRTUAPntDesc, dpsRTUAState }
--    DESCRIPTION "Generated when granular point 65 is set."
--    ::= 10065
--
-- dpsRTUp0065Clr TRAP-TYPE
--    ENTERPRISE  { dpsRTU }
--		VARIABLES {	sysDescr, sysLocation, dpsRTUDateTime,
--						dpsRTUAPort, dpsRTUCAddress, dpsRTUADisplay, dpsRTUAPoint,
--						dpsRTUAPntDesc, dpsRTUAState }
--    DESCRIPTION "Generated when granular point 65 clears."
--    ::= 20065
--
--    This editing can can be accomplished quite easily using a plain ASCII
-- file editor.  The repetitive structure of the definitions also makes for
-- rapid scripted or programmed generation if any such tools are available.
-- A compressed file containing event/point definitions for 144 displays is
-- available (DPS-G36.zip 150K) which uncompressed (DPS-G36.mib 6.2M) can be
-- used for cut-and-paste editing if desired.
--    The definitions can be further customized if desired by similar editing
-- prior to compiling carefully observing the following conventions:
--  + The label preceeding the TRAP-TYPE designator can be edited with some
--    freedom but the label must be utterly unique among all trap definitions.
--  + The ENTERPRISE and VARIABLES sections must not be changed.
--  + The DESCRIPTION can be edited with complete freedom and is typically
--    ignored within the context of standard SNMP manager trap handling.  The
--    quote mark before and after the text of the description are required.
--  + The number on the last line of the definition is the actual trap ID
--    defined and must also be utterly unique.
--
--    For example:
-- 
-- dpsRTUp0001Set TRAP-TYPE
-- 	ENTERPRISE  { dpsRTU }
--		VARIABLES {	sysDescr, sysLocation, dpsRTUDateTime,
--						dpsRTUAPort, dpsRTUCAddress, dpsRTUADisplay, dpsRTUAPoint,
--						dpsRTUAPntDesc, dpsRTUAState }
--    DESCRIPTION "Generated when granular point 1 is set."
--    ::= 10001
--
-- dpsRTUp0001Clr TRAP-TYPE
--    ENTERPRISE  { dpsRTU }
--		VARIABLES {	sysDescr, sysLocation, dpsRTUDateTime,
--						dpsRTUAPort, dpsRTUCAddress, dpsRTUADisplay, dpsRTUAPoint,
--						dpsRTUAPntDesc, dpsRTUAState }
--    DESCRIPTION "Generated when granular point 1 clears."
--    ::= 20001
--
--    Could be customized as:
--
-- dpsRTUFireAlarm TRAP-TYPE
--    ENTERPRISE  { dpsRTU }
--		VARIABLES {	sysDescr, sysLocation, dpsRTUDateTime,
--						dpsRTUAPort, dpsRTUCAddress, dpsRTUADisplay, dpsRTUAPoint,
--						dpsRTUAPntDesc, dpsRTUAState }
--    DESCRIPTION "Generated when smoke detector activates."
--    ::= 10001
--
-- dpsRTUFireOut TRAP-TYPE
--    ENTERPRISE  { dpsRTU }
--		VARIABLES {	sysDescr, sysLocation, dpsRTUDateTime,
--						dpsRTUAPort, dpsRTUCAddress, dpsRTUADisplay, dpsRTUAPoint,
--						dpsRTUAPntDesc, dpsRTUAState }
--    DESCRIPTION "Generated when smoke detector deactivates."
--    ::= 20001
-- **************************************************************************

dpsRTUp0001Set TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 1 is set."
	::= 10001

dpsRTUp0001Clr TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 1 clears."
	::= 20001

dpsRTUp0002Set TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 2 is set."
	::= 10002

dpsRTUp0002Clr TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 2 clears."
	::= 20002

dpsRTUp0003Set TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 3 is set."
	::= 10003

dpsRTUp0003Clr TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 3 clears."
	::= 20003

dpsRTUp0004Set TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 4 is set."
	::= 10004

dpsRTUp0004Clr TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 4 clears."
	::= 20004

dpsRTUp0005Set TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 5 is set."
	::= 10005

dpsRTUp0005Clr TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 5 clears."
	::= 20005

dpsRTUp0006Set TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 6 is set."
	::= 10006

dpsRTUp0006Clr TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 6 clears."
	::= 20006

dpsRTUp0007Set TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 7 is set."
	::= 10007

dpsRTUp0007Clr TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 7 clears."
	::= 20007

dpsRTUp0008Set TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 8 is set."
	::= 10008

dpsRTUp0008Clr TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 8 clears."
	::= 20008

dpsRTUp0009Set TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 9 is set."
	::= 10009

dpsRTUp0009Clr TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 9 clears."
	::= 20009

dpsRTUp0010Set TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 10 is set."
	::= 10010

dpsRTUp0010Clr TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 10 clears."
	::= 20010

dpsRTUp0011Set TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 11 is set."
	::= 10011

dpsRTUp0011Clr TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 11 clears."
	::= 20011

dpsRTUp0012Set TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 12 is set."
	::= 10012

dpsRTUp0012Clr TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 12 clears."
	::= 20012

dpsRTUp0013Set TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 13 is set."
	::= 10013

dpsRTUp0013Clr TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 13 clears."
	::= 20013

dpsRTUp0014Set TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 14 is set."
	::= 10014

dpsRTUp0014Clr TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 14 clears."
	::= 20014

dpsRTUp0015Set TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 15 is set."
	::= 10015

dpsRTUp0015Clr TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 15 clears."
	::= 20015

dpsRTUp0016Set TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 16 is set."
	::= 10016

dpsRTUp0016Clr TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 16 clears."
	::= 20016

dpsRTUp0017Set TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 17 is set."
	::= 10017

dpsRTUp0017Clr TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 17 clears."
	::= 20017

dpsRTUp0018Set TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 18 is set."
	::= 10018

dpsRTUp0018Clr TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 18 clears."
	::= 20018

dpsRTUp0019Set TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 19 is set."
	::= 10019

dpsRTUp0019Clr TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 19 clears."
	::= 20019

dpsRTUp0020Set TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 20 is set."
	::= 10020

dpsRTUp0020Clr TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 20 clears."
	::= 20020

dpsRTUp0021Set TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 21 is set."
	::= 10021

dpsRTUp0021Clr TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 21 clears."
	::= 20021

dpsRTUp0022Set TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 22 is set."
	::= 10022

dpsRTUp0022Clr TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 22 clears."
	::= 20022

dpsRTUp0023Set TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 23 is set."
	::= 10023

dpsRTUp0023Clr TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 23 clears."
	::= 20023

dpsRTUp0024Set TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 24 is set."
	::= 10024

dpsRTUp0024Clr TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 24 clears."
	::= 20024

dpsRTUp0025Set TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 25 is set."
	::= 10025

dpsRTUp0025Clr TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 25 clears."
	::= 20025

dpsRTUp0026Set TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 26 is set."
	::= 10026

dpsRTUp0026Clr TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 26 clears."
	::= 20026

dpsRTUp0027Set TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 27 is set."
	::= 10027

dpsRTUp0027Clr TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 27 clears."
	::= 20027

dpsRTUp0028Set TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 28 is set."
	::= 10028

dpsRTUp0028Clr TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 28 clears."
	::= 20028

dpsRTUp0029Set TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 29 is set."
	::= 10029

dpsRTUp0029Clr TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 29 clears."
	::= 20029

dpsRTUp0030Set TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 30 is set."
	::= 10030

dpsRTUp0030Clr TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 30 clears."
	::= 20030

dpsRTUp0031Set TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 31 is set."
	::= 10031

dpsRTUp0031Clr TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 31 clears."
	::= 20031

dpsRTUp0032Set TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 32 is set."
	::= 10032

dpsRTUp0032Clr TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 32 clears."
	::= 20032

dpsRTUp0033Set TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 33 is set."
	::= 10033

dpsRTUp0033Clr TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 33 clears."
	::= 20033

dpsRTUp0034Set TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 34 is set."
	::= 10034

dpsRTUp0034Clr TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 34 clears."
	::= 20034

dpsRTUp0035Set TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 35 is set."
	::= 10035

dpsRTUp0035Clr TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 35 clears."
	::= 20035

dpsRTUp0036Set TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 36 is set."
	::= 10036

dpsRTUp0036Clr TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 36 clears."
	::= 20036

dpsRTUp0037Set TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 37 is set."
	::= 10037

dpsRTUp0037Clr TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 37 clears."
	::= 20037

dpsRTUp0038Set TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 38 is set."
	::= 10038

dpsRTUp0038Clr TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 38 clears."
	::= 20038

dpsRTUp0039Set TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 39 is set."
	::= 10039

dpsRTUp0039Clr TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 39 clears."
	::= 20039

dpsRTUp0040Set TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 40 is set."
	::= 10040

dpsRTUp0040Clr TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 40 clears."
	::= 20040

dpsRTUp0041Set TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 41 is set."
	::= 10041

dpsRTUp0041Clr TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 41 clears."
	::= 20041

dpsRTUp0042Set TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 42 is set."
	::= 10042

dpsRTUp0042Clr TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 42 clears."
	::= 20042

dpsRTUp0043Set TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 43 is set."
	::= 10043

dpsRTUp0043Clr TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 43 clears."
	::= 20043

dpsRTUp0044Set TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 44 is set."
	::= 10044

dpsRTUp0044Clr TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 44 clears."
	::= 20044

dpsRTUp0045Set TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 45 is set."
	::= 10045

dpsRTUp0045Clr TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 45 clears."
	::= 20045

dpsRTUp0046Set TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 46 is set."
	::= 10046

dpsRTUp0046Clr TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 46 clears."
	::= 20046

dpsRTUp0047Set TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 47 is set."
	::= 10047

dpsRTUp0047Clr TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 47 clears."
	::= 20047

dpsRTUp0048Set TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 48 is set."
	::= 10048

dpsRTUp0048Clr TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 48 clears."
	::= 20048

dpsRTUp0049Set TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 49 is set."
	::= 10049

dpsRTUp0049Clr TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 49 clears."
	::= 20049

dpsRTUp0050Set TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 50 is set."
	::= 10050

dpsRTUp0050Clr TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 50 clears."
	::= 20050

dpsRTUp0051Set TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 51 is set."
	::= 10051

dpsRTUp0051Clr TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 51 clears."
	::= 20051

dpsRTUp0052Set TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 52 is set."
	::= 10052

dpsRTUp0052Clr TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 52 clears."
	::= 20052

dpsRTUp0053Set TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 53 is set."
	::= 10053

dpsRTUp0053Clr TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 53 clears."
	::= 20053

dpsRTUp0054Set TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 54 is set."
	::= 10054

dpsRTUp0054Clr TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 54 clears."
	::= 20054

dpsRTUp0055Set TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 55 is set."
	::= 10055

dpsRTUp0055Clr TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 55 clears."
	::= 20055

dpsRTUp0056Set TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 56 is set."
	::= 10056

dpsRTUp0056Clr TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 56 clears."
	::= 20056

dpsRTUp0057Set TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 57 is set."
	::= 10057

dpsRTUp0057Clr TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 57 clears."
	::= 20057

dpsRTUp0058Set TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 58 is set."
	::= 10058

dpsRTUp0058Clr TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 58 clears."
	::= 20058

dpsRTUp0059Set TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 59 is set."
	::= 10059

dpsRTUp0059Clr TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 59 clears."
	::= 20059

dpsRTUp0060Set TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 60 is set."
	::= 10060

dpsRTUp0060Clr TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 60 clears."
	::= 20060

dpsRTUp0061Set TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 61 is set."
	::= 10061

dpsRTUp0061Clr TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 61 clears."
	::= 20061

dpsRTUp0062Set TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 62 is set."
	::= 10062

dpsRTUp0062Clr TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 62 clears."
	::= 20062

dpsRTUp0063Set TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 63 is set."
	::= 10063

dpsRTUp0063Clr TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 63 clears."
	::= 20063

dpsRTUp0064Set TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 64 is set."
	::= 10064

dpsRTUp0064Clr TRAP-TYPE
	ENTERPRISE  { dpsRTU }
	VARIABLES {	sysDescr, sysLocation, dpsRTUDateTime,
					dpsRTUAPort, dpsRTUCAddress, dpsRTUADisplay, dpsRTUAPoint,
					dpsRTUAPntDesc, dpsRTUAState }
	DESCRIPTION "Generated when granular point 64 clears."
	::= 20064

END
