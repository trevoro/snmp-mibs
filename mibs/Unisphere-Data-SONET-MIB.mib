-- *****************************************************************
-- Unisphere-Data-SONET-MIB
--
-- Unisphere Networks Inc. Enterprise MIB
-- SONET MIB
--
-- Copyright (c) 1998 Redstone Communications, Incorporated.
-- Copyright (c) 1999, 2002 Unisphere Networks, Incorporated.
-- All Rights Reserved.
-- *****************************************************************

Unisphere-Data-SONET-MIB DEFINITIONS ::= BEGIN

IMPORTS
    MODULE-IDENTITY, OBJECT-TYPE, Unsigned32
        FROM SNMPv2-SMI
    DisplayString, TruthValue, TEXTUAL-CONVENTION, RowStatus
        FROM SNMPv2-TC
    MODULE-COMPLIANCE, OBJECT-GROUP
        FROM SNMPv2-CONF
    ifIndex, InterfaceIndex, InterfaceIndexOrZero
        FROM IF-MIB
    UsdNextIfIndex
        FROM Unisphere-Data-TC
    usDataMibs
        FROM Unisphere-Data-MIBs;

usdSonetMIB  MODULE-IDENTITY
    LAST-UPDATED "200110102042Z"  -- 10-Oct-01 04:42 PM EDT
    ORGANIZATION "Unisphere Networks, Inc."
    CONTACT-INFO
        "       Unisphere Networks, Inc.
        Postal: 10 Technology Park Drive
                Westford, MA  01886
                USA
        Tel:    +1 978 589 5800
        Email:  mib@UnisphereNetworks.com"
    DESCRIPTION
        "The SONET MIB for the Unisphere Networks Inc. enterprise."
    -- Revision History
    REVISION    "200110102042Z"  -- 10-Oct-01 04:42 PM EDT  - RX 3.2
    DESCRIPTION
        "Deprecated usdSonetMediumType, usdSonetMediumCircuitIdentifier and
        usdSonetVTType."
    REVISION    "200101021800Z"  -- 02-Jan-01 01:00 PM EST  - RX 3.0
    DESCRIPTION
       "Expanded MIB to include following tables and objects:
                usdSonetPathCapabilityTable
                usdSonetPathNextIfIndex
                usdSonetPathTable
                usdSonetVTNextIfIndex
                usdSonetVTTable "
    REVISION    "9811130000Z"    -- 13-Nov-98               - RX 1.0
    DESCRIPTION
        "Initial version of this MIB module."
    ::= { usDataMibs 7 }

-- ++++++++++++++++++++++++++++++++++++++++++++++++++++++++++++++++++++++
-- Textual conventions
-- ++++++++++++++++++++++++++++++++++++++++++++++++++++++++++++++++++++++

UsdSonetLineSpeed ::= TEXTUAL-CONVENTION
    STATUS       current
    DESCRIPTION
        "The set of SONET Line Speeds."
    SYNTAX       INTEGER {
                     sonetUnknownSpeed(0),
                     sonetOc1Stm0(1),
                     sonetOc3Stm1(2),
                     sonetOc12Stm3(3),
                     sonetOc48Stm16(4)
                 }

UsdSonetLogicalPathChannel ::= TEXTUAL-CONVENTION
    STATUS       current
    DESCRIPTION
        "A SONET Path channel description that uniquely identifies the SONET
        Path and is administratively assigned."
    SYNTAX      INTEGER (0..2147483647)

UsdSonetPathHierarchy ::= TEXTUAL-CONVENTION
    DISPLAY-HINT "32a"
    STATUS       current
    DESCRIPTION
        "Represents textual information taken from the NVT ASCII character set.

        The SONET path hierarchy is based upon the SONET line capacity.
        Configuration examples follow the diagram below, which depicts the SONET
        Path hierarchy.

                             OC-192/STM-64
                                   ^
                                   |
                             OC-48/STM-16 (1-4)
                                   ^
                                   |
                             OC-12/STM-4  (1-4)
                                   ^
                                   |
                             OC-3/STM-1   (1-4)
                                   ^
                                   |
                             OC-1/STM-0   (1-3)
                                   ^
                                   |
                  ^----------------^----------------^
                  |                |                |
                DS3 (1)   VT1.5/TU11 DS1 (1-28)  VT2/TU12 (1-21)

         For Line Speed = OC-48/STM-16:
                 When the entire capacity contains only one path, no specifier
                 is used.

             OC-12/STM-4 Path
                 To specify an OC-12 path over OC-48 provide a single digit of
                 the form a where:

                     a - OC-12/STM-4 path number (1-4)

             OC-3/STM-1 Path
                 To specify an OC-3 Path over OC-48 provide two digits of the
                 form a/b where:

                     a - OC-12/STM-4 path number (1-4)
                     b - OC-3/STM-1 path within the OC-12 (1-4) 

             OC-1/STM-0 Path
                 To specify an OC1 Path over OC-48 provide three digits of the 
                 form a/b/c where:

                     a - OC-12/STM-4 path number (1-4)
                     b - OC-3/STM-1 path number within OC-12 (1-4)
                     c - OC-1/STM-0 path number within OC-3 (1-3)

         For Line Speed = OC-12/STM-4:

             OC-12/STM-4 Path:
                 When entire line capacity contains only one path, no
                 channel-specifier is used.

             OC-3/STM-1 Path:
                 To specify an OC-3 path over OC-12 provide a single digit of
                 the form a where:

                     a - OC-3/STM-1 path within the OC-12 (1-4)

             OC-1 Path:
                 To specify an OC-1 path over OC-12 provide two digits of the
                 form a/b where:

                     a - OC-3/STM-1 path within the OC-12 (1-4)
                     b - OC-1/STM-0 path within the OC-3 (1-3)
         
         For Line Speed = OC-3/STM-1:

             OC-3/STM-1 Path:
                 When entire line capacity contains only one path, no
                 channel-specifier is used.

             OC-1 Path:
                 To specify an OC-1 path over OC-3 provide one digit of the
                 form a where:

                     a - OC-1/STM-1 path within the OC-3 (1-3)
        "
    REFERENCE
        "RFC 854: NVT ASCII character set.  See SNMPv2-TC.DisplayString
        DESCRIPTION for a summary."
    SYNTAX      OCTET STRING (SIZE (0..32))

UsdSonetVTType ::= TEXTUAL-CONVENTION
    STATUS      deprecated
    DESCRIPTION
        "The SONET Virtual Tributary Type.  This TC has been deprecated because
        RFC2558 provides this information in SONET-MIB.sonetVTCurrentWidth."
    SYNTAX      INTEGER  {
                    tribVT15TU11(0),
                    tribVT20TU12(1),
                    tribVT3(3),
                    tribVT6(4),
                    tribVT6c(5)
                }
               

-- ++++++++++++++++++++++++++++++++++++++++++++++++++++++++++++++++++++++
-- Managed objects
-- ++++++++++++++++++++++++++++++++++++++++++++++++++++++++++++++++++++++

usdSonetObjects     OBJECT IDENTIFIER ::= { usdSonetMIB 1 }
usdSonetPathObjects OBJECT IDENTIFIER ::= { usdSonetMIB 2 }
usdSonetVTObjects   OBJECT IDENTIFIER ::= { usdSonetMIB 3 }

-- 
-- This MIB contains managed objects for SONET interfaces.  It contains
-- management objects for configuration of interface attributes that either are
-- absent from, or read-only in the standard SONET-MIB.
--


-- //////////////////////////////////////////////////////////////////////
--
-- SONET Interfaces
--
-- //////////////////////////////////////////////////////////////////////

--
-- The SONET Interface Table
--

usdSonetMediumTable OBJECT-TYPE
    SYNTAX      SEQUENCE OF UsdSonetMediumEntry
    MAX-ACCESS  not-accessible
    STATUS      current
    DESCRIPTION
        "This table contains entries for SONET interfaces present in the
        system."
    ::= { usdSonetObjects 1 }

usdSonetMediumEntry OBJECT-TYPE
    SYNTAX      UsdSonetMediumEntry
    MAX-ACCESS  not-accessible
    STATUS      current
    DESCRIPTION
        "Each entry describes the characteristics of an SONET interface."
    INDEX       { ifIndex }
    ::= { usdSonetMediumTable 1 }

UsdSonetMediumEntry ::= SEQUENCE {
    usdSonetMediumType
        INTEGER,
    usdSonetMediumLoopbackConfig
        INTEGER,
    usdSonetMediumTimingSource
        INTEGER,
    usdSonetMediumCircuitIdentifier
        DisplayString
}

usdSonetMediumType OBJECT-TYPE
    SYNTAX      INTEGER {
                    sonet(1),
                    sdh(2)
                }
    MAX-ACCESS  read-write
    STATUS      deprecated
    DESCRIPTION
        "This variable identifies whether a SONET or a SDH signal is used across
        this interface.  This object was deprecated because the same information
        is provided by the SONET-MIB.sonetMediumType object (RFC 2558)."
    ::= { usdSonetMediumEntry 1 }

usdSonetMediumLoopbackConfig OBJECT-TYPE
    SYNTAX      INTEGER {
                    sonetNoLoop(0),
                    sonetFacilityLoop(1),
                    sonetTerminalLoop(2),
                    sonetOtherLoop(3) }
    MAX-ACCESS  read-write
    STATUS      current
    DESCRIPTION
        "The current loopback state of the SONET/SDH interface.
        The values mean:

        sonetNoLoop        Not in the loopback state.  A device that is not
                           capable of performing a loopback on this interface
                           shall always return this value.

        sonetFacilityLoop  The received signal at this interface is looped back
                           out through the corresponding transmitter in the
                           return direction.

        sonetTerminalLoop  The signal that is about to be transmitted is
                           connected to the associated incoming receiver.

        sonetOtherLoop     Loopbacks that are not defined here."
    ::= { usdSonetMediumEntry 2 }


usdSonetMediumTimingSource OBJECT-TYPE
    SYNTAX      INTEGER {
                    loop(0),
                    internalModule(1),
                    internalChassis(2)
                }
    MAX-ACCESS  read-write
    STATUS      current
    DESCRIPTION
        "Selects the source from which transmit timing is derived.  loop(0)
        indicates timing is recovered from the receiver; internalModule(1)
        indicates timing is from the module associated with this interface;
        internalChassis(3) indicates timing is taken from the internal system
        timing reference."
    ::= { usdSonetMediumEntry 3 }


usdSonetMediumCircuitIdentifier OBJECT-TYPE
    SYNTAX      DisplayString
    MAX-ACCESS  read-write
    STATUS      deprecated
    DESCRIPTION
        "This variable contains the transmission vendor's circuit identifier,
        for the purpose of facilitating troubleshooting.  This object was
        deprecated because the same information is provided by the
        SONET-MIB.sonetMediumCircuitIdentifier object (RFC 2558)."
    ::= { usdSonetMediumEntry 4 }


--
-- The SONET Path Capabilities Table
--

usdSonetPathCapabilityTable OBJECT-TYPE
    SYNTAX      SEQUENCE OF UsdSonetPathCapabilityEntry
    MAX-ACCESS  not-accessible
    STATUS      current
    DESCRIPTION
        "This table contains entries for SONET Paths present in the system."
    ::= { usdSonetPathObjects 1 }

usdSonetPathCapabilityEntry OBJECT-TYPE
    SYNTAX      UsdSonetPathCapabilityEntry
    MAX-ACCESS  not-accessible
    STATUS      current
    DESCRIPTION
        "Each entry describes the SONET path capability of a SONET interface.
        This table is index by the ifIndex of the SONET interface."
    INDEX       { ifIndex }
    ::= { usdSonetPathCapabilityTable 1 }

UsdSonetPathCapabilityEntry ::= SEQUENCE {
    usdSonetPathRemoveFlag
        TruthValue,
    usdSonetPathChannelized
        TruthValue,
    usdSonetPathMaximumChannels
        Unsigned32,
    usdSonetPathMinimumPathSpeed
        UsdSonetLineSpeed,
    usdSonetPathMaximumPathSpeed
        UsdSonetLineSpeed
}

usdSonetPathRemoveFlag OBJECT-TYPE
    SYNTAX      TruthValue
    MAX-ACCESS  read-only
    STATUS      current
    DESCRIPTION
        "This variable identifies whether a SONET/SDH supports the deletion of
         SONET Paths.  A value of true(1) indicates the SONET path is removable;
         a value of false(2) indicates the SONET path cannot be removed. " 
    ::= { usdSonetPathCapabilityEntry 1 }

usdSonetPathChannelized OBJECT-TYPE
    SYNTAX      TruthValue 
    MAX-ACCESS  read-only
    STATUS      current
    DESCRIPTION
        "Identifies whether or not this SONET interface supports channelization.
         A value of true(1) indicates the SONET path is channelized; a value of
         false(2) indicates the SONET path is not channelized."
    ::= { usdSonetPathCapabilityEntry 2 }

usdSonetPathMaximumChannels OBJECT-TYPE
    SYNTAX      Unsigned32
    MAX-ACCESS  read-only
    STATUS      current
    DESCRIPTION
        "Identifies the maximum number of SONET paths/channels for this
        interface."
    ::= { usdSonetPathCapabilityEntry 3 }

usdSonetPathMinimumPathSpeed OBJECT-TYPE
    SYNTAX      UsdSonetLineSpeed
    MAX-ACCESS  read-only
    STATUS      current
    DESCRIPTION
        "Identifies the minimum SONET path speed for this interface."
    ::= { usdSonetPathCapabilityEntry 4 }

usdSonetPathMaximumPathSpeed OBJECT-TYPE
    SYNTAX      UsdSonetLineSpeed
    MAX-ACCESS  read-only
    STATUS      current
    DESCRIPTION
        "Identifies the maximum SONET path speed for this interface."
    ::= { usdSonetPathCapabilityEntry 5 }

--
-- The SONET Path Interface Objects 
--

usdSonetPathNextIfIndex OBJECT-TYPE
    SYNTAX      UsdNextIfIndex
    MAX-ACCESS  read-only
    STATUS      current
    DESCRIPTION
        "Coordinate ifIndex value allocation for entries in usdSonetPathTable.

        A GET of this object returns the next available ifIndex value to be used
        to create an entry in the associated interface table; or zero, if no
        valid ifIndex value is available.  This object also returns a value of
        zero when it is the lexicographic successor of a varbind presented in an
        SNMP GETNEXT or GETBULK request, for which circumstance it is assumed
        that ifIndex allocation is unintended.

        Successive GETs will typically return different values, thus avoiding
        collisions among cooperating management clients seeking to create table
        entries simultaneously."
    ::= { usdSonetPathObjects 2 }

--
-- The SONET Path Interface Table
--

usdSonetPathTable OBJECT-TYPE
    SYNTAX      SEQUENCE OF UsdSonetPathEntry
    MAX-ACCESS  not-accessible
    STATUS      current
    DESCRIPTION
        "This table contains entries for SONET Path interfaces present in the
        system."
    ::= { usdSonetPathObjects 3 }

usdSonetPathEntry OBJECT-TYPE
    SYNTAX      UsdSonetPathEntry
    MAX-ACCESS  not-accessible
    STATUS      current
    DESCRIPTION
        "Each entry describes the characteristics of an SONET Path interface."
    INDEX       { usdSonetPathIfIndex }
    ::= { usdSonetPathTable 1 }

UsdSonetPathEntry ::= SEQUENCE {
    usdSonetPathIfIndex
        InterfaceIndex,
    usdSonetPathLogicalChannel
        UsdSonetLogicalPathChannel,
    usdSonetPathSpeed
        UsdSonetLineSpeed,
    usdSonetPathHierarchy
       UsdSonetPathHierarchy,
    usdSonetPathLowerIfIndex
       InterfaceIndexOrZero,
    usdSonetPathRowStatus
       RowStatus
}

usdSonetPathIfIndex OBJECT-TYPE
    SYNTAX      InterfaceIndex
    MAX-ACCESS  not-accessible
    STATUS      current
    DESCRIPTION
        "The ifIndex of the SONET Path interface.  When creating entries in this
        table, suitable values for this object are determined by reading
        usdSonetPathNextIfIndex."
    ::= { usdSonetPathEntry 1 }

usdSonetPathLogicalChannel OBJECT-TYPE
    SYNTAX      UsdSonetLogicalPathChannel
    MAX-ACCESS  read-create
    STATUS      current
    DESCRIPTION
        "The logical channel number assigned to this SONET Path.  If the
        underlying SONET interface does not support channelization, the value of
        this object is zero."
    ::= { usdSonetPathEntry 2 }

usdSonetPathSpeed OBJECT-TYPE
    SYNTAX      UsdSonetLineSpeed
    MAX-ACCESS  read-create
    STATUS      current
    DESCRIPTION
        "The line speed associated with this SONET PATH."
    ::= { usdSonetPathEntry 3 }

usdSonetPathHierarchy OBJECT-TYPE
    SYNTAX      UsdSonetPathHierarchy
    MAX-ACCESS  read-create
    STATUS      current
    DESCRIPTION
        "The SONET Path hierarchy associated with this path."
    ::= { usdSonetPathEntry 4 }

usdSonetPathLowerIfIndex OBJECT-TYPE
    SYNTAX      InterfaceIndexOrZero
    MAX-ACCESS  read-create
    STATUS      current
    DESCRIPTION
        "The ifIndex of the interface over which this SONET Path interface is to
        be layered - typically a SONET/SDH interface.  A value of zero indicates
        no layering.  An implementation may choose to require that a nonzero
        value be configured at entry creation."
    ::= { usdSonetPathEntry 5 }

usdSonetPathRowStatus OBJECT-TYPE
    SYNTAX      RowStatus
    MAX-ACCESS  read-create
    STATUS      current
    DESCRIPTION
        "Controls creation/deletion of entries in this table according to the
        RowStatus textual convention, constrained to support the following
        values only:

            createAndGo
            destroy

        To create an entry in this table, the following entry objects MUST be
        explicitly configured:

            usdSonetPathRowStatus
            usdSonetPathLogicalChannel
            usdSonetPathSpeed
            usdSonetPathHierarchy
            usdSonetPathLowerIfIndex

        In addition, when creating an entry the following conditions must hold:

            A value for usdSonetPathIfIndex must have been determined
            previously, by reading usdSonetPathNextIfIndex.

            The interface identified by the usdSonetPathLowerIfIndex must exist.

            The usdSonetPathSpeed must be consistent with the speed for the
            channel specified by the usdSonetPathHierarchy, based on the speed
            of the interface identified by the usdSonetPathLowerIfIndex.

        A corresponding entry in ifTable/ifXTable/usdIfTable is created/
        destroyed as a result of creating/destroying an entry in this table."
    ::= { usdSonetPathEntry 6 }


--
-- The SONET Virtual Tributary Interface Objects 
--

usdSonetVTNextIfIndex OBJECT-TYPE
    SYNTAX      UsdNextIfIndex
    MAX-ACCESS  read-only
    STATUS      current
    DESCRIPTION
        "Coordinate ifIndex value allocation for entries in usdSonetVTTable.

        A GET of this object returns the next available ifIndex value to be used
        to create an entry in the associated interface table; or zero, if no
        valid ifIndex value is available.  This object also returns a value of
        zero when it is the lexicographic successor of a varbind presented in an
        SNMP GETNEXT or GETBULK request, for which circumstance it is assumed
        that ifIndex allocation is unintended.

        Successive GETs will typically return different values, thus avoiding
        collisions among cooperating management clients seeking to create table
        entries simultaneously."
    ::= { usdSonetVTObjects 1 }

--
-- The SONET Virtual Tributary Interface Table
--

usdSonetVTTable OBJECT-TYPE
    SYNTAX      SEQUENCE OF UsdSonetVTEntry
    MAX-ACCESS  not-accessible
    STATUS      current
    DESCRIPTION
        "This table contains entries for SONET Virtual Tributary interfaces
        present in the system.  This table augments the standard
        SONET-MIB.sonetVTCurrentTable."
    ::= { usdSonetVTObjects 2 }

usdSonetVTEntry OBJECT-TYPE
    SYNTAX      UsdSonetVTEntry
    MAX-ACCESS  not-accessible
    STATUS      current
    DESCRIPTION
        "Each entry describes the characteristics of an SONET Virtual Tributary
        interface."
    INDEX    { usdSonetVTIfIndex }
    ::= { usdSonetVTTable 1 }

UsdSonetVTEntry ::= SEQUENCE {
    usdSonetVTIfIndex
        InterfaceIndex,
    usdSonetVTPathLogicalChannel
        UsdSonetLogicalPathChannel,
    usdSonetVTType
        UsdSonetVTType,
    usdSonetVTPathPayload
        Unsigned32,
    usdSonetVTTributaryGroup
        Unsigned32,
    usdSonetVTTributarySubChannel
        Unsigned32,
    usdSonetVTLowerIfIndex
       InterfaceIndexOrZero,
    usdSonetVTRowStatus
       RowStatus
}

usdSonetVTIfIndex OBJECT-TYPE
    SYNTAX      InterfaceIndex
    MAX-ACCESS  not-accessible
    STATUS      current
    DESCRIPTION
        "The ifIndex of the SONET Virtual Tributary interface.  When creating
        entries in this table, suitable values for this object are determined by
        reading usdSonetVTNextIfIndex."
    ::= { usdSonetVTEntry 1 }

usdSonetVTPathLogicalChannel OBJECT-TYPE
    SYNTAX      UsdSonetLogicalPathChannel
    MAX-ACCESS  read-create
    STATUS      current
    DESCRIPTION
        "The SONET Path logical channel number associated with this virtual
        tributary."
    ::= { usdSonetVTEntry 2 }

usdSonetVTType OBJECT-TYPE
    SYNTAX      UsdSonetVTType
    MAX-ACCESS  read-create
    STATUS      deprecated
    DESCRIPTION
        "The SONET virtual tributary type.  This object was deprecated because
        the same information is provided in the SONET-MIB.sonetVTCurrentWidth
        object."
    ::= { usdSonetVTEntry 3 }
  
usdSonetVTPathPayload OBJECT-TYPE
    SYNTAX      Unsigned32
    MAX-ACCESS  read-create
    STATUS      current
    DESCRIPTION
        "The SONET Path payload number associated with this virtual tributary.
        For SDH mode, this is a value with a range from 1-3.  For SONET mode,
        the value of this object is always 1."
    ::= { usdSonetVTEntry 4 }

usdSonetVTTributaryGroup OBJECT-TYPE
    SYNTAX      Unsigned32
    MAX-ACCESS  read-create
    STATUS      current
    DESCRIPTION
        "The SONET Path group number for this virtual tributary.  In SONET and
        SDH mode, the value of this object is 1-7."
    ::= { usdSonetVTEntry 5 }

usdSonetVTTributarySubChannel OBJECT-TYPE
    SYNTAX      Unsigned32
    MAX-ACCESS  read-create
    STATUS      current
    DESCRIPTION
        "Specifies the virtual tributary number within the tributary group
        defined by usdSonetVTTributaryGroup object.  The value of this object
        ranges from 1-4 if the tributary type is tribVT15/TU11(0); and the
        values 1-3 if the tributary type is tribVT20/TU12(1)."
    ::= { usdSonetVTEntry 6 }

usdSonetVTLowerIfIndex OBJECT-TYPE
    SYNTAX      InterfaceIndexOrZero 
    MAX-ACCESS  read-create
    STATUS      current
    DESCRIPTION
        "The ifIndex of the interface over which this SONET Virtual Tributary
        interface is to be layered - typically a SONET PATH interface.

        A value of zero indicates no layering.  An implementation may choose to
        require that a nonzero value be configured at entry creation."
    ::= { usdSonetVTEntry 7 }

usdSonetVTRowStatus OBJECT-TYPE
    SYNTAX      RowStatus
    MAX-ACCESS  read-create
    STATUS      current
    DESCRIPTION
        "Controls creation/deletion of entries in this table according to the
        RowStatus textual convention, constrained to support the following
        values only:

            createAndGo
            destroy

        To create an entry in this table, the following entry objects MUST be
        explicitly configured:

            usdSonetVTRowStatus
            usdSonetVTPathLogicalChannel
            usdSonetVTType
            usdSonetVTPathPayload
            usdSonetVTTributaryGroup
            usdSonetVTTributarySubChannel
            usdSonetVTLowerIfIndex

        In addition, when creating an entry the following conditions must hold:

            A value for usdSonetVTIfIndex must have been determined previously,
            by reading usdSonetVTNextIfIndex.

            The interface identified by usdSonetVTLowerIfIndex must exist.

        A corresponding entry in ifTable/ifXTable/usdIfTable is created/
        destroyed as a result of creating/destroying an entry in this table."
    ::= { usdSonetVTEntry 8 }


-- ++++++++++++++++++++++++++++++++++++++++++++++++++++++++++++++++++++++
-- Notification control objects
-- ++++++++++++++++++++++++++++++++++++++++++++++++++++++++++++++++++++++

-- No notifications are defined in this MIB. Placeholder follows.

-- usdSonetTrapControl      OBJECT IDENTIFIER ::= { usdSonetMIB 2 }

-- ++++++++++++++++++++++++++++++++++++++++++++++++++++++++++++++++++++++
-- Notifications
-- ++++++++++++++++++++++++++++++++++++++++++++++++++++++++++++++++++++++

-- No notifications are defined in this MIB. Placeholder follows.

-- The following two OBJECT IDENTIFIERS are used to define SNMPv2 
-- Notifications that are easily translated into SNMPv1 Traps.

-- usdSonetTraps            OBJECT IDENTIFIER ::= { usdSonetMIB 3 }
-- usdSonetTrapPrefix       OBJECT IDENTIFIER ::= { usdSonetTraps 0 }


-- ++++++++++++++++++++++++++++++++++++++++++++++++++++++++++++++++++++++
-- Conformance information
-- ++++++++++++++++++++++++++++++++++++++++++++++++++++++++++++++++++++++

usdSonetConformance OBJECT IDENTIFIER ::= { usdSonetMIB 4 }
usdSonetCompliances OBJECT IDENTIFIER ::= { usdSonetConformance 1 }
usdSonetGroups      OBJECT IDENTIFIER ::= { usdSonetConformance 2 }

-- compliance statements

usdSonetCompliance MODULE-COMPLIANCE
    STATUS      obsolete
    DESCRIPTION
        "Obsolete compliance statement for entities which implement the
        Unisphere SONET MIB.  This statement became obsolete when the SONET Path
        and SONET VT groups of objects were added."
    MODULE  -- this module
        MANDATORY-GROUPS { usdSonetGroup }
    ::= { usdSonetCompliances 1 }                                      -- RX 1.0

usdSonetCompliance2 MODULE-COMPLIANCE
    STATUS      deprecated
    DESCRIPTION
        "Deprecated compliance statement for entities which implement the
        Unisphere SONET MIB.  This statement became deprecated when the
        usdSonetMediumType, usdSonetMediumCircuitIdentifier and usdSonetVTType
        objects were deprecated."
    MODULE  -- this module
        MANDATORY-GROUPS {
            usdSonetGroup,
            usdSonetPathGroup }
        GROUP       usdSonetVirtualTributaryGroup
        DESCRIPTION
            "This group is mandatory only for those entities that support SONET
            virtual tributaries."
    ::= { usdSonetCompliances 2 }                                      -- RX 3.0

usdSonetCompliance3 MODULE-COMPLIANCE
    STATUS      current
    DESCRIPTION
        "The compliance statement for entities which implement the Unisphere
        SONET MIB."
    MODULE  -- this module
        MANDATORY-GROUPS {
            usdSonetGroup2,
            usdSonetPathGroup }
        GROUP       usdSonetVirtualTributaryGroup2
        DESCRIPTION
            "This group is mandatory only for those entities that support SONET
            virtual tributaries."
    ::= { usdSonetCompliances 3 }                                      -- RX 3.2

-- units of conformance

usdSonetGroup OBJECT-GROUP
    OBJECTS {
        usdSonetMediumType,
        usdSonetMediumLoopbackConfig,
        usdSonetMediumTimingSource,
        usdSonetMediumCircuitIdentifier
    }
    STATUS      deprecated
    DESCRIPTION
        "Deprecated collection of objects providing management of SONET/SDH
        interfaces in a Unisphere product.  This group became deprecated when
        the usdSonetMediumType and usdSonetMediumCircuitIdentifier objects were
        deprecated."
    ::= { usdSonetGroups 1 }

usdSonetPathGroup OBJECT-GROUP
    OBJECTS {
        usdSonetPathRemoveFlag,
        usdSonetPathChannelized,
        usdSonetPathMaximumChannels,
        usdSonetPathMinimumPathSpeed,
        usdSonetPathMaximumPathSpeed,
        usdSonetPathNextIfIndex,
        usdSonetPathLogicalChannel,
        usdSonetPathSpeed,
        usdSonetPathHierarchy,
        usdSonetPathLowerIfIndex,
        usdSonetPathRowStatus
    }
    STATUS      current
    DESCRIPTION
        "A collection of objects providing management of SONET/SDH and SONET
        Path interfaces in a Unisphere product."
    ::= { usdSonetGroups 2 }

usdSonetVirtualTributaryGroup OBJECT-GROUP
    OBJECTS {
        usdSonetVTNextIfIndex,
        usdSonetVTPathLogicalChannel,
        usdSonetVTType,
        usdSonetVTPathPayload,
        usdSonetVTTributaryGroup,
        usdSonetVTTributarySubChannel,
        usdSonetVTLowerIfIndex,
        usdSonetVTRowStatus
    }
    STATUS      deprecated
    DESCRIPTION
        "Deprecated collection of objects providing management of SONET virtual
        tributaries in a Unisphere product.  This group became deprecated when
        usdSonetVTType was deprecated."
    ::= { usdSonetGroups 3 }
        
usdSonetGroup2 OBJECT-GROUP
    OBJECTS {
        usdSonetMediumLoopbackConfig,
        usdSonetMediumTimingSource
    }
    STATUS      current
    DESCRIPTION
        "A collection of objects providing management of SONET/SDH interfaces in
        a Unisphere product."
    ::= { usdSonetGroups 4 }

usdSonetVirtualTributaryGroup2 OBJECT-GROUP
    OBJECTS {
        usdSonetVTNextIfIndex,
        usdSonetVTPathLogicalChannel,
        usdSonetVTPathPayload,
        usdSonetVTTributaryGroup,
        usdSonetVTTributarySubChannel,
        usdSonetVTLowerIfIndex,
        usdSonetVTRowStatus
    }
    STATUS      current
    DESCRIPTION
        "A collection of objects providing management of SONET virtual
        tributaries in a Unisphere product."
    ::= { usdSonetGroups 5 }
        
END
